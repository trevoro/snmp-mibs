Nortel-Magellan-Passport-CasTestMIB
DEFINITIONS ::= BEGIN



IMPORTS

      OBJECT-TYPE
   FROM RFC-1212

      IpAddress
   FROM RFC1155-SMI

      components,
      passportMIBs
   FROM Nortel-Magellan-Passport-UsefulDefinitionsMIB

      Counter32,
      TimeInterval,
      RowPointer,
      DisplayString,
      StorageType,
      RowStatus,
      PassportCounter64,
      Gauge32,
      Integer32,
      Unsigned32
   FROM Nortel-Magellan-Passport-StandardTextualConventionsMIB

      AsciiString,
      Hex,
      Gauge64,
      FixedPoint4,
      NonReplicated,
      FixedPoint3,
      HexString,
      EnterpriseDateAndTime,
      FixedPoint1,
      IntegerSequence,
      Link,
      DashedHexString,
      AsciiStringIndex,
      DigitString,
      FixedPoint2,
      ExtendedAsciiString,
      Unsigned64,
      WildcardedDigitString
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     CasTest Enterprise MIB."

casTestMIB OBJECT IDENTIFIER ::= { passportMIBs 103 }











example OBJECT IDENTIFIER ::= { components 5000 }



exampleRowStatusTable OBJECT-TYPE
   SYNTAX     SEQUENCE OF ExampleRowStatusEntry
   ACCESS     not-accessible
   STATUS     mandatory
   DESCRIPTION
     "This entry controls the addition and deletion of 
      example components."
::= { example 1 }

exampleRowStatusEntry OBJECT-TYPE
   SYNTAX     ExampleRowStatusEntry
   ACCESS     not-accessible
   STATUS     mandatory
   DESCRIPTION
     "A single entry in the table represents a single 
      example component."
   INDEX {
      exampleIndex }
::= { exampleRowStatusTable 1 }

ExampleRowStatusEntry ::= SEQUENCE {
   exampleRowStatus
      RowStatus,
   exampleComponentName
      DisplayString,
   exampleStorageType
      StorageType,
   exampleIndex
      NonReplicated }

exampleRowStatus OBJECT-TYPE
   SYNTAX     RowStatus 
   ACCESS     read-write
   STATUS     mandatory
   DESCRIPTION
     "This variable is used as the basis for SNMP naming of
      example components.
      These components can be added and deleted."
::= { exampleRowStatusEntry 1 }

exampleComponentName OBJECT-TYPE
   SYNTAX     DisplayString 
   ACCESS     read-only
   STATUS     mandatory
   DESCRIPTION
     "This variable provides the component's string name for
      use with the ASCII Console Interface"
::= { exampleRowStatusEntry 2 }

exampleStorageType OBJECT-TYPE
   SYNTAX     StorageType 
   ACCESS     read-only
   STATUS     mandatory
   DESCRIPTION
     "This variable represents the storage type value for the
      example tables."
::= { exampleRowStatusEntry 4 }

exampleIndex OBJECT-TYPE
   SYNTAX     NonReplicated 
   ACCESS     not-accessible
   STATUS     mandatory
   DESCRIPTION
     "This variable represents the index for the example tables."
::= { exampleRowStatusEntry 10 }

exampleOperationalTable OBJECT-TYPE
   SYNTAX     SEQUENCE OF ExampleOperationalEntry
   ACCESS     not-accessible
   STATUS     mandatory
   DESCRIPTION
     ""
::= { example 100 }

exampleOperationalEntry OBJECT-TYPE
   SYNTAX     ExampleOperationalEntry
   ACCESS     not-accessible
   STATUS     mandatory
   DESCRIPTION
     "An entry in the exampleOperationalTable."
   INDEX {
      exampleIndex }
::= { exampleOperationalTable 1 }

ExampleOperationalEntry ::= SEQUENCE {
   exampleOperMyComponentName
      RowPointer }

exampleOperMyComponentName OBJECT-TYPE
   SYNTAX     RowPointer 
   ACCESS     read-write
   STATUS     mandatory
   DESCRIPTION
     ""
::= { exampleOperationalEntry 1 }

exampleProvisionalTable OBJECT-TYPE
   SYNTAX     SEQUENCE OF ExampleProvisionalEntry
   ACCESS     not-accessible
   STATUS     mandatory
   DESCRIPTION
     ""
::= { example 101 }

exampleProvisionalEntry OBJECT-TYPE
   SYNTAX     ExampleProvisionalEntry
   ACCESS     not-accessible
   STATUS     mandatory
   DESCRIPTION
     "An entry in the exampleProvisionalTable."
   INDEX {
      exampleIndex }
::= { exampleProvisionalTable 1 }

ExampleProvisionalEntry ::= SEQUENCE {
   exampleProvMyComponentName
      RowPointer }

exampleProvMyComponentName OBJECT-TYPE
   SYNTAX     RowPointer 
   ACCESS     read-write
   STATUS     mandatory
   DESCRIPTION
     ""
::= { exampleProvisionalEntry 1 }

exampleOperDecimalSubCreatedTable OBJECT-TYPE
   SYNTAX     SEQUENCE OF ExampleOperDecimalSubCreatedEntry
   ACCESS     not-accessible
   STATUS     mandatory
   DESCRIPTION
     ""
::= { example 1002 }

exampleOperDecimalSubCreatedEntry OBJECT-TYPE
   SYNTAX     ExampleOperDecimalSubCreatedEntry
   ACCESS     not-accessible
   STATUS     mandatory
   DESCRIPTION
     "An entry in the exampleOperDecimalSubCreatedTable."
   INDEX {
      exampleIndex,
      exampleOperDecimalSubCreatedValue }
::= { exampleOperDecimalSubCreatedTable 1 }

ExampleOperDecimalSubCreatedEntry ::= SEQUENCE {
   exampleOperDecimalSubCreatedValue
      RowPointer,
   exampleOperDecimalSubCreatedRowStatus
      RowStatus }

exampleOperDecimalSubCreatedValue OBJECT-TYPE
   SYNTAX     RowPointer 
   ACCESS     read-write
   STATUS     mandatory
   DESCRIPTION
     "This variable represents both the value and the index for the
      exampleOperDecimalSubCreatedTable."
::= { exampleOperDecimalSubCreatedEntry 1 }

exampleOperDecimalSubCreatedRowStatus OBJECT-TYPE
   SYNTAX     RowStatus 
   ACCESS     write-only
   STATUS     mandatory
   DESCRIPTION
     "This variable is used to control the addition and deletion 
      of individual values of the exampleOperDecimalSubCreatedTable."
::= { exampleOperDecimalSubCreatedEntry 2 }

exampleOperFixedPtSubcomponentsCreatedTable OBJECT-TYPE
   SYNTAX     SEQUENCE OF ExampleOperFixedPtSubcomponentsCreatedEntry
   ACCESS     not-accessible
   STATUS     mandatory
   DESCRIPTION
     ""
::= { example 1003 }

exampleOperFixedPtSubcomponentsCreatedEntry OBJECT-TYPE
   SYNTAX     ExampleOperFixedPtSubcomponentsCreatedEntry
   ACCESS     not-accessible
   STATUS     mandatory
   DESCRIPTION
     "An entry in the exampleOperFixedPtSubcomponentsCreatedTable."
   INDEX {
      exampleIndex,
      exampleOperFixedPtSubcomponentsCreatedValue }
::= { exampleOperFixedPtSubcomponentsCreatedTable 1 }

ExampleOperFixedPtSubcomponentsCreatedEntry ::= SEQUENCE {
   exampleOperFixedPtSubcomponentsCreatedValue
      RowPointer,
   exampleOperFixedPtSubcomponentsCreatedRowStatus
      RowStatus }

exampleOperFixedPtSubcomponentsCreatedValue OBJECT-TYPE
   SYNTAX     RowPointer 
   ACCESS     read-write
   STATUS     mandatory
   DESCRIPTION
     "This variable represents both the value and the index for the
      exampleOperFixedPtSubcomponentsCreatedTable."
::= { exampleOperFixedPtSubcomponentsCreatedEntry 1 }

exampleOperFixedPtSubcomponentsCreatedRowStatus OBJECT-TYPE
   SYNTAX     RowStatus 
   ACCESS     write-only
   STATUS     mandatory
   DESCRIPTION
     "This variable is used to control the addition and deletion 
      of individual values of the exampleOperFixedPtSubcomponentsCreatedTable."
::= { exampleOperFixedPtSubcomponentsCreatedEntry 2 }

exampleOperStringSubCreatedTable OBJECT-TYPE
   SYNTAX     SEQUENCE OF ExampleOperStringSubCreatedEntry
   ACCESS     not-accessible
   STATUS     mandatory
   DESCRIPTION
     ""
::= { example 1004 }

exampleOperStringSubCreatedEntry OBJECT-TYPE
   SYNTAX     ExampleOperStringSubCreatedEntry
   ACCESS     not-accessible
   STATUS     mandatory
   DESCRIPTION
     "An entry in the exampleOperStringSubCreatedTable."
   INDEX {
      exampleIndex,
      exampleOperStringSubCreatedValue }
::= { exampleOperStringSubCreatedTable 1 }

ExampleOperStringSubCreatedEntry ::= SEQUENCE {
   exampleOperStringSubCreatedValue
      RowPointer,
   exampleOperStringSubCreatedRowStatus
      RowStatus }

exampleOperStringSubCreatedValue OBJECT-TYPE
   SYNTAX     RowPointer 
   ACCESS     read-write
   STATUS     mandatory
   DESCRIPTION
     "This variable represents both the value and the index for the
      exampleOperStringSubCreatedTable."
::= { exampleOperStringSubCreatedEntry 1 }

exampleOperStringSubCreatedRowStatus OBJECT-TYPE
   SYNTAX     RowStatus 
   ACCESS     write-only
   STATUS     mandatory
   DESCRIPTION
     "This variable is used to control the addition and deletion 
      of individual values of the exampleOperStringSubCreatedTable."
::= { exampleOperStringSubCreatedEntry 2 }

exampleOperEnumSubCreatedTable OBJECT-TYPE
   SYNTAX     SEQUENCE OF ExampleOperEnumSubCreatedEntry
   ACCESS     not-accessible
   STATUS     mandatory
   DESCRIPTION
     ""
::= { example 1005 }

exampleOperEnumSubCreatedEntry OBJECT-TYPE
   SYNTAX     ExampleOperEnumSubCreatedEntry
   ACCESS     not-accessible
   STATUS     mandatory
   DESCRIPTION
     "An entry in the exampleOperEnumSubCreatedTable."
   INDEX {
      exampleIndex,
      exampleOperEnumSubCreatedValue }
::= { exampleOperEnumSubCreatedTable 1 }

ExampleOperEnumSubCreatedEntry ::= SEQUENCE {
   exampleOperEnumSubCreatedValue
      RowPointer,
   exampleOperEnumSubCreatedRowStatus
      RowStatus }

exampleOperEnumSubCreatedValue OBJECT-TYPE
   SYNTAX     RowPointer 
   ACCESS     read-write
   STATUS     mandatory
   DESCRIPTION
     "This variable represents both the value and the index for the
      exampleOperEnumSubCreatedTable."
::= { exampleOperEnumSubCreatedEntry 1 }

exampleOperEnumSubCreatedRowStatus OBJECT-TYPE
   SYNTAX     RowStatus 
   ACCESS     write-only
   STATUS     mandatory
   DESCRIPTION
     "This variable is used to control the addition and deletion 
      of individual values of the exampleOperEnumSubCreatedTable."
::= { exampleOperEnumSubCreatedEntry 2 }

exampleOperSignedSubCreatedTable OBJECT-TYPE
   SYNTAX     SEQUENCE OF ExampleOperSignedSubCreatedEntry
   ACCESS     not-accessible
   STATUS     mandatory
   DESCRIPTION
     ""
::= { example 1006 }

exampleOperSignedSubCreatedEntry OBJECT-TYPE
   SYNTAX     ExampleOperSignedSubCreatedEntry
   ACCESS     not-accessible
   STATUS     mandatory
   DESCRIPTION
     "An entry in the exampleOperSignedSubCreatedTable."
   INDEX {
      exampleIndex,
      exampleOperSignedSubCreatedValue }
::= { exampleOperSignedSubCreatedTable 1 }

ExampleOperSignedSubCreatedEntry ::= SEQUENCE {
   exampleOperSignedSubCreatedValue
      RowPointer,
   exampleOperSignedSubCreatedRowStatus
      RowStatus }

exampleOperSignedSubCreatedValue OBJECT-TYPE
   SYNTAX     RowPointer 
   ACCESS     read-write
   STATUS     mandatory
   DESCRIPTION
     "This variable represents both the value and the index for the
      exampleOperSignedSubCreatedTable."
::= { exampleOperSignedSubCreatedEntry 1 }

exampleOperSignedSubCreatedRowStatus OBJECT-TYPE
   SYNTAX     RowStatus 
   ACCESS     write-only
   STATUS     mandatory
   DESCRIPTION
     "This variable is used to control the addition and deletion 
      of individual values of the exampleOperSignedSubCreatedTable."
::= { exampleOperSignedSubCreatedEntry 2 }

exampleProvDecimalSubCreatedTable OBJECT-TYPE
   SYNTAX     SEQUENCE OF ExampleProvDecimalSubCreatedEntry
   ACCESS     not-accessible
   STATUS     mandatory
   DESCRIPTION
     ""
::= { example 1007 }

exampleProvDecimalSubCreatedEntry OBJECT-TYPE
   SYNTAX     ExampleProvDecimalSubCreatedEntry
   ACCESS     not-accessible
   STATUS     mandatory
   DESCRIPTION
     "An entry in the exampleProvDecimalSubCreatedTable."
   INDEX {
      exampleIndex,
      exampleProvDecimalSubCreatedValue }
::= { exampleProvDecimalSubCreatedTable 1 }

ExampleProvDecimalSubCreatedEntry ::= SEQUENCE {
   exampleProvDecimalSubCreatedValue
      Link,
   exampleProvDecimalSubCreatedRowStatus
      RowStatus }

exampleProvDecimalSubCreatedValue OBJECT-TYPE
   SYNTAX     Link 
   ACCESS     read-write
   STATUS     mandatory
   DESCRIPTION
     "This variable represents both the value and the index for the
      exampleProvDecimalSubCreatedTable."
::= { exampleProvDecimalSubCreatedEntry 1 }

exampleProvDecimalSubCreatedRowStatus OBJECT-TYPE
   SYNTAX     RowStatus 
   ACCESS     write-only
   STATUS     mandatory
   DESCRIPTION
     "This variable is used to control the addition and deletion 
      of individual values of the exampleProvDecimalSubCreatedTable."
::= { exampleProvDecimalSubCreatedEntry 2 }

exampleProvFixedPtSubCreatedTable OBJECT-TYPE
   SYNTAX     SEQUENCE OF ExampleProvFixedPtSubCreatedEntry
   ACCESS     not-accessible
   STATUS     mandatory
   DESCRIPTION
     ""
::= { example 1008 }

exampleProvFixedPtSubCreatedEntry OBJECT-TYPE
   SYNTAX     ExampleProvFixedPtSubCreatedEntry
   ACCESS     not-accessible
   STATUS     mandatory
   DESCRIPTION
     "An entry in the exampleProvFixedPtSubCreatedTable."
   INDEX {
      exampleIndex,
      exampleProvFixedPtSubCreatedValue }
::= { exampleProvFixedPtSubCreatedTable 1 }

ExampleProvFixedPtSubCreatedEntry ::= SEQUENCE {
   exampleProvFixedPtSubCreatedValue
      Link,
   exampleProvFixedPtSubCreatedRowStatus
      RowStatus }

exampleProvFixedPtSubCreatedValue OBJECT-TYPE
   SYNTAX     Link 
   ACCESS     read-write
   STATUS     mandatory
   DESCRIPTION
     "This variable represents both the value and the index for the
      exampleProvFixedPtSubCreatedTable."
::= { exampleProvFixedPtSubCreatedEntry 1 }

exampleProvFixedPtSubCreatedRowStatus OBJECT-TYPE
   SYNTAX     RowStatus 
   ACCESS     write-only
   STATUS     mandatory
   DESCRIPTION
     "This variable is used to control the addition and deletion 
      of individual values of the exampleProvFixedPtSubCreatedTable."
::= { exampleProvFixedPtSubCreatedEntry 2 }

exampleProvSignedSubCreatedTable OBJECT-TYPE
   SYNTAX     SEQUENCE OF ExampleProvSignedSubCreatedEntry
   ACCESS     not-accessible
   STATUS     mandatory
   DESCRIPTION
     ""
::= { example 1009 }

exampleProvSignedSubCreatedEntry OBJECT-TYPE
   SYNTAX     ExampleProvSignedSubCreatedEntry
   ACCESS     not-accessible
   STATUS     mandatory
   DESCRIPTION
     "An entry in the exampleProvSignedSubCreatedTable."
   INDEX {
      exampleIndex,
      exampleProvSignedSubCreatedValue }
::= { exampleProvSignedSubCreatedTable 1 }

ExampleProvSignedSubCreatedEntry ::= SEQUENCE {
   exampleProvSignedSubCreatedValue
      Link,
   exampleProvSignedSubCreatedRowStatus
      RowStatus }

exampleProvSignedSubCreatedValue OBJECT-TYPE
   SYNTAX     Link 
   ACCESS     read-write
   STATUS     mandatory
   DESCRIPTION
     "This variable represents both the value and the index for the
      exampleProvSignedSubCreatedTable."
::= { exampleProvSignedSubCreatedEntry 1 }

exampleProvSignedSubCreatedRowStatus OBJECT-TYPE
   SYNTAX     RowStatus 
   ACCESS     write-only
   STATUS     mandatory
   DESCRIPTION
     "This variable is used to control the addition and deletion 
      of individual values of the exampleProvSignedSubCreatedTable."
::= { exampleProvSignedSubCreatedEntry 2 }

exampleProvStringSubCreatedTable OBJECT-TYPE
   SYNTAX     SEQUENCE OF ExampleProvStringSubCreatedEntry
   ACCESS     not-accessible
   STATUS     mandatory
   DESCRIPTION
     ""
::= { example 1010 }

exampleProvStringSubCreatedEntry OBJECT-TYPE
   SYNTAX     ExampleProvStringSubCreatedEntry
   ACCESS     not-accessible
   STATUS     mandatory
   DESCRIPTION
     "An entry in the exampleProvStringSubCreatedTable."
   INDEX {
      exampleIndex,
      exampleProvStringSubCreatedValue }
::= { exampleProvStringSubCreatedTable 1 }

ExampleProvStringSubCreatedEntry ::= SEQUENCE {
   exampleProvStringSubCreatedValue
      Link,
   exampleProvStringSubCreatedRowStatus
      RowStatus }

exampleProvStringSubCreatedValue OBJECT-TYPE
   SYNTAX     Link 
   ACCESS     read-write
   STATUS     mandatory
   DESCRIPTION
     "This variable represents both the value and the index for the
      exampleProvStringSubCreatedTable."
::= { exampleProvStringSubCreatedEntry 1 }

exampleProvStringSubCreatedRowStatus OBJECT-TYPE
   SYNTAX     RowStatus 
   ACCESS     write-only
   STATUS     mandatory
   DESCRIPTION
     "This variable is used to control the addition and deletion 
      of individual values of the exampleProvStringSubCreatedTable."
::= { exampleProvStringSubCreatedEntry 2 }

exampleProvEnumSubCreatedTable OBJECT-TYPE
   SYNTAX     SEQUENCE OF ExampleProvEnumSubCreatedEntry
   ACCESS     not-accessible
   STATUS     mandatory
   DESCRIPTION
     ""
::= { example 1011 }

exampleProvEnumSubCreatedEntry OBJECT-TYPE
   SYNTAX     ExampleProvEnumSubCreatedEntry
   ACCESS     not-accessible
   STATUS     mandatory
   DESCRIPTION
     "An entry in the exampleProvEnumSubCreatedTable."
   INDEX {
      exampleIndex,
      exampleProvEnumSubCreatedValue }
::= { exampleProvEnumSubCreatedTable 1 }

ExampleProvEnumSubCreatedEntry ::= SEQUENCE {
   exampleProvEnumSubCreatedValue
      Link,
   exampleProvEnumSubCreatedRowStatus
      RowStatus }

exampleProvEnumSubCreatedValue OBJECT-TYPE
   SYNTAX     Link 
   ACCESS     read-write
   STATUS     mandatory
   DESCRIPTION
     "This variable represents both the value and the index for the
      exampleProvEnumSubCreatedTable."
::= { exampleProvEnumSubCreatedEntry 1 }

exampleProvEnumSubCreatedRowStatus OBJECT-TYPE
   SYNTAX     RowStatus 
   ACCESS     write-only
   STATUS     mandatory
   DESCRIPTION
     "This variable is used to control the addition and deletion 
      of individual values of the exampleProvEnumSubCreatedTable."
::= { exampleProvEnumSubCreatedEntry 2 }



exampleDecimal OBJECT IDENTIFIER ::= { example 2 }



exampleDecimalRowStatusTable OBJECT-TYPE
   SYNTAX     SEQUENCE OF ExampleDecimalRowStatusEntry
   ACCESS     not-accessible
   STATUS     mandatory
   DESCRIPTION
     "This entry controls the addition and deletion of 
      exampleDecimal components."
::= { exampleDecimal 1 }

exampleDecimalRowStatusEntry OBJECT-TYPE
   SYNTAX     ExampleDecimalRowStatusEntry
   ACCESS     not-accessible
   STATUS     mandatory
   DESCRIPTION
     "A single entry in the table represents a single 
      exampleDecimal component."
   INDEX {
      exampleIndex,
      exampleDecimalIndex }
::= { exampleDecimalRowStatusTable 1 }

ExampleDecimalRowStatusEntry ::= SEQUENCE {
   exampleDecimalRowStatus
      RowStatus,
   exampleDecimalComponentName
      DisplayString,
   exampleDecimalStorageType
      StorageType,
   exampleDecimalIndex
      Integer32 }

exampleDecimalRowStatus OBJECT-TYPE
   SYNTAX     RowStatus 
   ACCESS     read-write
   STATUS     mandatory
   DESCRIPTION
     "This variable is used as the basis for SNMP naming of
      exampleDecimal components.
      These components can be added and deleted."
::= { exampleDecimalRowStatusEntry 1 }

exampleDecimalComponentName OBJECT-TYPE
   SYNTAX     DisplayString 
   ACCESS     read-only
   STATUS     mandatory
   DESCRIPTION
     "This variable provides the component's string name for
      use with the ASCII Console Interface"
::= { exampleDecimalRowStatusEntry 2 }

exampleDecimalStorageType OBJECT-TYPE
   SYNTAX     StorageType 
   ACCESS     read-only
   STATUS     mandatory
   DESCRIPTION
     "This variable represents the storage type value for the
      exampleDecimal tables."
::= { exampleDecimalRowStatusEntry 4 }

exampleDecimalIndex OBJECT-TYPE
   SYNTAX     Integer32 (0..1023)
   ACCESS     not-accessible
   STATUS     mandatory
   DESCRIPTION
     "This variable represents the index for the exampleDecimal tables."
::= { exampleDecimalRowStatusEntry 10 }

exampleDecimalOperationalTable OBJECT-TYPE
   SYNTAX     SEQUENCE OF ExampleDecimalOperationalEntry
   ACCESS     not-accessible
   STATUS     mandatory
   DESCRIPTION
     ""
::= { exampleDecimal 10 }

exampleDecimalOperationalEntry OBJECT-TYPE
   SYNTAX     ExampleDecimalOperationalEntry
   ACCESS     not-accessible
   STATUS     mandatory
   DESCRIPTION
     "An entry in the exampleDecimalOperationalTable."
   INDEX {
      exampleIndex,
      exampleDecimalIndex }
::= { exampleDecimalOperationalTable 1 }

ExampleDecimalOperationalEntry ::= SEQUENCE {
   exampleDecimalOperStructInteger
      Unsigned32,
   exampleDecimalOperStructIntSet
      OCTET STRING,
   exampleDecimalOperFreeInteger
      Unsigned32,
   exampleDecimalOperFreeIntSet
      OCTET STRING,
   exampleDecimalOperFreeCounter32
      Counter32,
   exampleDecimalOperFreeGauge32
      Gauge32,
   exampleDecimalOperFreeTimeInterval
      TimeInterval }

exampleDecimalOperStructInteger OBJECT-TYPE
   SYNTAX     Unsigned32 (0..255)
   ACCESS     read-write
   STATUS     mandatory
   DESCRIPTION
     ""
::= { exampleDecimalOperationalEntry 1 }

exampleDecimalOperStructIntSet OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)"
::= { exampleDecimalOperationalEntry 2 }

exampleDecimalOperFreeInteger OBJECT-TYPE
   SYNTAX     Unsigned32 (0..10 | 100..200)
   ACCESS     read-write
   STATUS     mandatory
   DESCRIPTION
     ""
::= { exampleDecimalOperationalEntry 3 }

exampleDecimalOperFreeIntSet OBJECT-TYPE
   SYNTAX     OCTET STRING (SIZE (1))
   ACCESS     read-write
   STATUS     mandatory
   DESCRIPTION
     "Description of bits:
      n0(0)
      n1(1)
      n2(2)
      n3(3)
      n4(4)
      n5(5)"
::= { exampleDecimalOperationalEntry 4 }

exampleDecimalOperFreeCounter32 OBJECT-TYPE
   SYNTAX     Counter32 
   ACCESS     read-only
   STATUS     mandatory
   DESCRIPTION
     ""
::= { exampleDecimalOperationalEntry 5 }

exampleDecimalOperFreeGauge32 OBJECT-TYPE
   SYNTAX     Gauge32 (0..65535)
   ACCESS     read-write
   STATUS     mandatory
   DESCRIPTION
     ""
::= { exampleDecimalOperationalEntry 6 }

exampleDecimalOperFreeTimeInterval OBJECT-TYPE
   SYNTAX     TimeInterval (0..2147483647)
   ACCESS     read-write
   STATUS     mandatory
   DESCRIPTION
     ""
::= { exampleDecimalOperationalEntry 7 }

exampleDecimalProvisionalTable OBJECT-TYPE
   SYNTAX     SEQUENCE OF ExampleDecimalProvisionalEntry
   ACCESS     not-accessible
   STATUS     mandatory
   DESCRIPTION
     ""
::= { exampleDecimal 11 }

exampleDecimalProvisionalEntry OBJECT-TYPE
   SYNTAX     ExampleDecimalProvisionalEntry
   ACCESS     not-accessible
   STATUS     mandatory
   DESCRIPTION
     "An entry in the exampleDecimalProvisionalTable."
   INDEX {
      exampleIndex,
      exampleDecimalIndex }
::= { exampleDecimalProvisionalTable 1 }

ExampleDecimalProvisionalEntry ::= SEQUENCE {
   exampleDecimalProvDecimalSub
      Link,
   exampleDecimalProvStructInteger
      Unsigned32,
   exampleDecimalProvStructIntSet
      OCTET STRING,
   exampleDecimalProvFreeInteger
      Unsigned32,
   exampleDecimalProvFreeInteger1
      Unsigned32,
   exampleDecimalProvFreeInteger2
      Unsigned32,
   exampleDecimalProvFreeIntSet
      OCTET STRING,
   exampleDecimalProvFreeIntSet1
      OCTET STRING }

exampleDecimalProvDecimalSub OBJECT-TYPE
   SYNTAX     Link 
   ACCESS     read-write
   STATUS     mandatory
   DESCRIPTION
     ""
::= { exampleDecimalProvisionalEntry 1 }

exampleDecimalProvStructInteger OBJECT-TYPE
   SYNTAX     Unsigned32 (0..252 | 253 | 254 | 255)
   ACCESS     read-write
   STATUS     mandatory
   DESCRIPTION
     "VALUES (

      253 = infinity

      254 = notApplicable

      255 = notMeasured

      )"
   DEFVAL     { 253 }
::= { exampleDecimalProvisionalEntry 2 }

exampleDecimalProvStructIntSet OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)"
   DEFVAL     { 'aaaa'H }
::= { exampleDecimalProvisionalEntry 3 }

exampleDecimalProvFreeInteger OBJECT-TYPE
   SYNTAX     Unsigned32 (0..10 | 100..200)
   ACCESS     read-write
   STATUS     mandatory
   DESCRIPTION
     ""
   DEFVAL     { 101 }
::= { exampleDecimalProvisionalEntry 4 }

exampleDecimalProvFreeInteger1 OBJECT-TYPE
   SYNTAX     Unsigned32 (1..10 | 100..200)
   ACCESS     read-write
   STATUS     mandatory
   DESCRIPTION
     ""
   DEFVAL     { 1 }
::= { exampleDecimalProvisionalEntry 5 }

exampleDecimalProvFreeInteger2 OBJECT-TYPE
   SYNTAX     Unsigned32 (0..65535)
   ACCESS     read-write
   STATUS     mandatory
   DESCRIPTION
     ""
   DEFVAL     { 0 }
::= { exampleDecimalProvisionalEntry 6 }

exampleDecimalProvFreeIntSet OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)"
   DEFVAL     { '5555'H }
::= { exampleDecimalProvisionalEntry 7 }

exampleDecimalProvFreeIntSet1 OBJECT-TYPE
   SYNTAX     OCTET STRING (SIZE (4))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
   DEFVAL     { '80000001'H }
::= { exampleDecimalProvisionalEntry 8 }

exampleDecimalOsIntVectorTable OBJECT-TYPE
   SYNTAX     SEQUENCE OF ExampleDecimalOsIntVectorEntry
   ACCESS     not-accessible
   STATUS     mandatory
   DESCRIPTION
     ""
::= { exampleDecimal 1012 }

exampleDecimalOsIntVectorEntry OBJECT-TYPE
   SYNTAX     ExampleDecimalOsIntVectorEntry
   ACCESS     not-accessible
   STATUS     mandatory
   DESCRIPTION
     "An entry in the exampleDecimalOsIntVectorTable."
   INDEX {
      exampleIndex,
      exampleDecimalIndex,
      exampleDecimalOsIntVectorIndex }
::= { exampleDecimalOsIntVectorTable 1 }

ExampleDecimalOsIntVectorEntry ::= SEQUENCE {
   exampleDecimalOsIntVectorIndex
      Integer32,
   exampleDecimalOsIntVectorValue
      Unsigned32 }

exampleDecimalOsIntVectorIndex OBJECT-TYPE
   SYNTAX     Integer32 (0..9)
   ACCESS     not-accessible
   STATUS     mandatory
   DESCRIPTION
     "This variable represents the exampleDecimalOsIntVectorTable
      specific index for the exampleDecimalOsIntVectorTable."
::= { exampleDecimalOsIntVectorEntry 1 }

exampleDecimalOsIntVectorValue OBJECT-TYPE
   SYNTAX     Unsigned32 (0..100)
   ACCESS     read-write
   STATUS     mandatory
   DESCRIPTION
     "This variable represents an individual value for the
      exampleDecimalOsIntVectorTable."
::= { exampleDecimalOsIntVectorEntry 2 }

exampleDecimalOsIntArrayTable OBJECT-TYPE
   SYNTAX     SEQUENCE OF ExampleDecimalOsIntArrayEntry
   ACCESS     not-accessible
   STATUS     mandatory
   DESCRIPTION
     ""
::= { exampleDecimal 1013 }

exampleDecimalOsIntArrayEntry OBJECT-TYPE
   SYNTAX     ExampleDecimalOsIntArrayEntry
   ACCESS     not-accessible
   STATUS     mandatory
   DESCRIPTION
     "An entry in the exampleDecimalOsIntArrayTable."
   INDEX {
      exampleIndex,
      exampleDecimalIndex,
      exampleDecimalOsIntArrayRowIndex,
      exampleDecimalOsIntArrayColumnIndex }
::= { exampleDecimalOsIntArrayTable 1 }

ExampleDecimalOsIntArrayEntry ::= SEQUENCE {
   exampleDecimalOsIntArrayRowIndex
      Integer32,
   exampleDecimalOsIntArrayColumnIndex
      Integer32,
   exampleDecimalOsIntArrayValue
      Unsigned32 }

exampleDecimalOsIntArrayRowIndex OBJECT-TYPE
   SYNTAX     Integer32 (0..2)
   ACCESS     not-accessible
   STATUS     mandatory
   DESCRIPTION
     "This variable represents the next to last index for the 
      exampleDecimalOsIntArrayTable."
::= { exampleDecimalOsIntArrayEntry 1 }

exampleDecimalOsIntArrayColumnIndex OBJECT-TYPE
   SYNTAX     Integer32 (0..3)
   ACCESS     not-accessible
   STATUS     mandatory
   DESCRIPTION
     "This variable represents the final index for the 
      exampleDecimalOsIntArrayTable."
::= { exampleDecimalOsIntArrayEntry 2 }

exampleDecimalOsIntArrayValue OBJECT-TYPE
   SYNTAX     Unsigned32 (0..255)
   ACCESS     read-write
   STATUS     mandatory
   DESCRIPTION
     "This variable represents an individual value for the
      exampleDecimalOsIntArrayTable."
::= { exampleDecimalOsIntArrayEntry 3 }

exampleDecimalOfIntVectorTable OBJECT-TYPE
   SYNTAX     SEQUENCE OF ExampleDecimalOfIntVectorEntry
   ACCESS     not-accessible
   STATUS     mandatory
   DESCRIPTION
     ""
::= { exampleDecimal 1014 }

exampleDecimalOfIntVectorEntry OBJECT-TYPE
   SYNTAX     ExampleDecimalOfIntVectorEntry
   ACCESS     not-accessible
   STATUS     mandatory
   DESCRIPTION
     "An entry in the exampleDecimalOfIntVectorTable."
   INDEX {
      exampleIndex,
      exampleDecimalIndex,
      exampleDecimalOfIntVectorIndex }
::= { exampleDecimalOfIntVectorTable 1 }

ExampleDecimalOfIntVectorEntry ::= SEQUENCE {
   exampleDecimalOfIntVectorIndex
      Integer32,
   exampleDecimalOfIntVectorValue
      Unsigned32 }

exampleDecimalOfIntVectorIndex OBJECT-TYPE
   SYNTAX     Integer32 (0..9)
   ACCESS     not-accessible
   STATUS     mandatory
   DESCRIPTION
     "This variable represents the exampleDecimalOfIntVectorTable
      specific index for the exampleDecimalOfIntVectorTable."
::= { exampleDecimalOfIntVectorEntry 1 }

exampleDecimalOfIntVectorValue OBJECT-TYPE
   SYNTAX     Unsigned32 (0..100)
   ACCESS     read-write
   STATUS     mandatory
   DESCRIPTION
     "This variable represents an individual value for the
      exampleDecimalOfIntVectorTable."
::= { exampleDecimalOfIntVectorEntry 2 }

exampleDecimalOfIntArrayTable OBJECT-TYPE
   SYNTAX     SEQUENCE OF ExampleDecimalOfIntArrayEntry
   ACCESS     not-accessible
   STATUS     mandatory
   DESCRIPTION
     ""
::= { exampleDecimal 1015 }

exampleDecimalOfIntArrayEntry OBJECT-TYPE
   SYNTAX     ExampleDecimalOfIntArrayEntry
   ACCESS     not-accessible
   STATUS     mandatory
   DESCRIPTION
     "An entry in the exampleDecimalOfIntArrayTable."
   INDEX {
      exampleIndex,
      exampleDecimalIndex,
      exampleDecimalOfIntArrayRowIndex,
      exampleDecimalOfIntArrayColumnIndex }
::= { exampleDecimalOfIntArrayTable 1 }

ExampleDecimalOfIntArrayEntry ::= SEQUENCE {
   exampleDecimalOfIntArrayRowIndex
      Integer32,
   exampleDecimalOfIntArrayColumnIndex
      Integer32,
   exampleDecimalOfIntArrayValue
      Unsigned32 }

exampleDecimalOfIntArrayRowIndex OBJECT-TYPE
   SYNTAX     Integer32 (0..2)
   ACCESS     not-accessible
   STATUS     mandatory
   DESCRIPTION
     "This variable represents the next to last index for the 
      exampleDecimalOfIntArrayTable."
::= { exampleDecimalOfIntArrayEntry 1 }

exampleDecimalOfIntArrayColumnIndex OBJECT-TYPE
   SYNTAX     Integer32 (0..3)
   ACCESS     not-accessible
   STATUS     mandatory
   DESCRIPTION
     "This variable represents the final index for the 
      exampleDecimalOfIntArrayTable."
::= { exampleDecimalOfIntArrayEntry 2 }

exampleDecimalOfIntArrayValue OBJECT-TYPE
   SYNTAX     Unsigned32 (0..255)
   ACCESS     read-write
   STATUS     mandatory
   DESCRIPTION
     "This variable represents an individual value for the
      exampleDecimalOfIntArrayTable."
::= { exampleDecimalOfIntArrayEntry 3 }

exampleDecimalOfIntReplicatedTable OBJECT-TYPE
   SYNTAX     SEQUENCE OF ExampleDecimalOfIntReplicatedEntry
   ACCESS     not-accessible
   STATUS     mandatory
   DESCRIPTION
     ""
::= { exampleDecimal 1016 }

exampleDecimalOfIntReplicatedEntry OBJECT-TYPE
   SYNTAX     ExampleDecimalOfIntReplicatedEntry
   ACCESS     not-accessible
   STATUS     mandatory
   DESCRIPTION
     "An entry in the exampleDecimalOfIntReplicatedTable."
   INDEX {
      exampleIndex,
      exampleDecimalIndex,
      exampleDecimalOfIntReplicatedIndex }
::= { exampleDecimalOfIntReplicatedTable 1 }

ExampleDecimalOfIntReplicatedEntry ::= SEQUENCE {
   exampleDecimalOfIntReplicatedIndex
      Integer32,
   exampleDecimalOfIntReplicatedValue
      Unsigned32,
   exampleDecimalOfIntReplicatedRowStatus
      RowStatus }

exampleDecimalOfIntReplicatedIndex OBJECT-TYPE
   SYNTAX     Integer32 (0..9)
   ACCESS     not-accessible
   STATUS     mandatory
   DESCRIPTION
     "This variable represents the index for the exampleDecimalOfIntReplicatedTable."
::= { exampleDecimalOfIntReplicatedEntry 1 }

exampleDecimalOfIntReplicatedValue OBJECT-TYPE
   SYNTAX     Unsigned32 (0..65535)
   ACCESS     read-write
   STATUS     mandatory
   DESCRIPTION
     "This variable represents an individual value for the
      exampleDecimalOfIntReplicatedTable."
::= { exampleDecimalOfIntReplicatedEntry 2 }

exampleDecimalOfIntReplicatedRowStatus OBJECT-TYPE
   SYNTAX     RowStatus 
   ACCESS     write-only
   STATUS     mandatory
   DESCRIPTION
     "This variable is used to control the addition and deletion 
      of individual values of the exampleDecimalOfIntReplicatedTable."
::= { exampleDecimalOfIntReplicatedEntry 3 }

exampleDecimalOfIntListTable OBJECT-TYPE
   SYNTAX     SEQUENCE OF ExampleDecimalOfIntListEntry
   ACCESS     not-accessible
   STATUS     mandatory
   DESCRIPTION
     ""
::= { exampleDecimal 1017 }

exampleDecimalOfIntListEntry OBJECT-TYPE
   SYNTAX     ExampleDecimalOfIntListEntry
   ACCESS     not-accessible
   STATUS     mandatory
   DESCRIPTION
     "An entry in the exampleDecimalOfIntListTable."
   INDEX {
      exampleIndex,
      exampleDecimalIndex,
      exampleDecimalOfIntListValue }
::= { exampleDecimalOfIntListTable 1 }

ExampleDecimalOfIntListEntry ::= SEQUENCE {
   exampleDecimalOfIntListValue
      Integer32,
   exampleDecimalOfIntListRowStatus
      RowStatus }

exampleDecimalOfIntListValue OBJECT-TYPE
   SYNTAX     Integer32 (0..10 | 1000..2000)
   ACCESS     read-write
   STATUS     mandatory
   DESCRIPTION
     "This variable represents both the value and the index for the
      exampleDecimalOfIntListTable."
::= { exampleDecimalOfIntListEntry 1 }

exampleDecimalOfIntListRowStatus OBJECT-TYPE
   SYNTAX     RowStatus 
   ACCESS     write-only
   STATUS     mandatory
   DESCRIPTION
     "This variable is used to control the addition and deletion 
      of individual values of the exampleDecimalOfIntListTable."
::= { exampleDecimalOfIntListEntry 2 }

exampleDecimalPsIntVectorTable OBJECT-TYPE
   SYNTAX     SEQUENCE OF ExampleDecimalPsIntVectorEntry
   ACCESS     not-accessible
   STATUS     mandatory
   DESCRIPTION
     ""
::= { exampleDecimal 1018 }

exampleDecimalPsIntVectorEntry OBJECT-TYPE
   SYNTAX     ExampleDecimalPsIntVectorEntry
   ACCESS     not-accessible
   STATUS     mandatory
   DESCRIPTION
     "An entry in the exampleDecimalPsIntVectorTable."
   INDEX {
      exampleIndex,
      exampleDecimalIndex,
      exampleDecimalPsIntVectorIndex }
::= { exampleDecimalPsIntVectorTable 1 }

ExampleDecimalPsIntVectorEntry ::= SEQUENCE {
   exampleDecimalPsIntVectorIndex
      Integer32,
   exampleDecimalPsIntVectorValue
      Unsigned32 }

exampleDecimalPsIntVectorIndex OBJECT-TYPE
   SYNTAX     Integer32 (0..9)
   ACCESS     not-accessible
   STATUS     mandatory
   DESCRIPTION
     "This variable represents the exampleDecimalPsIntVectorTable
      specific index for the exampleDecimalPsIntVectorTable."
::= { exampleDecimalPsIntVectorEntry 1 }

exampleDecimalPsIntVectorValue OBJECT-TYPE
   SYNTAX     Unsigned32 (0..100)
   ACCESS     read-write
   STATUS     mandatory
   DESCRIPTION
     "This variable represents an individual value for the
      exampleDecimalPsIntVectorTable."
::= { exampleDecimalPsIntVectorEntry 2 }

exampleDecimalPsIntArrayTable OBJECT-TYPE
   SYNTAX     SEQUENCE OF ExampleDecimalPsIntArrayEntry
   ACCESS     not-accessible
   STATUS     mandatory
   DESCRIPTION
     ""
::= { exampleDecimal 1019 }

exampleDecimalPsIntArrayEntry OBJECT-TYPE
   SYNTAX     ExampleDecimalPsIntArrayEntry
   ACCESS     not-accessible
   STATUS     mandatory
   DESCRIPTION
     "An entry in the exampleDecimalPsIntArrayTable."
   INDEX {
      exampleIndex,
      exampleDecimalIndex,
      exampleDecimalPsIntArrayRowIndex,
      exampleDecimalPsIntArrayColumnIndex }
::= { exampleDecimalPsIntArrayTable 1 }

ExampleDecimalPsIntArrayEntry ::= SEQUENCE {
   exampleDecimalPsIntArrayRowIndex
      Integer32,
   exampleDecimalPsIntArrayColumnIndex
      Integer32,
   exampleDecimalPsIntArrayValue
      Unsigned32 }

exampleDecimalPsIntArrayRowIndex OBJECT-TYPE
   SYNTAX     Integer32 (0..2)
   ACCESS     not-accessible
   STATUS     mandatory
   DESCRIPTION
     "This variable represents the next to last index for the 
      exampleDecimalPsIntArrayTable."
::= { exampleDecimalPsIntArrayEntry 1 }

exampleDecimalPsIntArrayColumnIndex OBJECT-TYPE
   SYNTAX     Integer32 (0..3)
   ACCESS     not-accessible
   STATUS     mandatory
   DESCRIPTION
     "This variable represents the final index for the 
      exampleDecimalPsIntArrayTable."
::= { exampleDecimalPsIntArrayEntry 2 }

exampleDecimalPsIntArrayValue OBJECT-TYPE
   SYNTAX     Unsigned32 (0..255)
   ACCESS     read-write
   STATUS     mandatory
   DESCRIPTION
     "This variable represents an individual value for the
      exampleDecimalPsIntArrayTable."
::= { exampleDecimalPsIntArrayEntry 3 }

exampleDecimalPfIntVectorTable OBJECT-TYPE
   SYNTAX     SEQUENCE OF ExampleDecimalPfIntVectorEntry
   ACCESS     not-accessible
   STATUS     mandatory
   DESCRIPTION
     ""
::= { exampleDecimal 1020 }

exampleDecimalPfIntVectorEntry OBJECT-TYPE
   SYNTAX     ExampleDecimalPfIntVectorEntry
   ACCESS     not-accessible
   STATUS     mandatory
   DESCRIPTION
     "An entry in the exampleDecimalPfIntVectorTable."
   INDEX {
      exampleIndex,
      exampleDecimalIndex,
      exampleDecimalPfIntVectorIndex }
::= { exampleDecimalPfIntVectorTable 1 }

ExampleDecimalPfIntVectorEntry ::= SEQUENCE {
   exampleDecimalPfIntVectorIndex
      Integer32,
   exampleDecimalPfIntVectorValue
      Unsigned32 }

exampleDecimalPfIntVectorIndex OBJECT-TYPE
   SYNTAX     Integer32 (0..9)
   ACCESS     not-accessible
   STATUS     mandatory
   DESCRIPTION
     "This variable represents the exampleDecimalPfIntVectorTable
      specific index for the exampleDecimalPfIntVectorTable."
::= { exampleDecimalPfIntVectorEntry 1 }

exampleDecimalPfIntVectorValue OBJECT-TYPE
   SYNTAX     Unsigned32 (0..100)
   ACCESS     read-write
   STATUS     mandatory
   DESCRIPTION
     "This variable represents an individual value for the
      exampleDecimalPfIntVectorTable."
::= { exampleDecimalPfIntVectorEntry 2 }

exampleDecimalPfIntVector1Table OBJECT-TYPE
   SYNTAX     SEQUENCE OF ExampleDecimalPfIntVector1Entry
   ACCESS     not-accessible
   STATUS     mandatory
   DESCRIPTION
     ""
::= { exampleDecimal 1021 }

exampleDecimalPfIntVector1Entry OBJECT-TYPE
   SYNTAX     ExampleDecimalPfIntVector1Entry
   ACCESS     not-accessible
   STATUS     mandatory
   DESCRIPTION
     "An entry in the exampleDecimalPfIntVector1Table."
   INDEX {
      exampleIndex,
      exampleDecimalIndex,
      exampleDecimalPfIntVector1Index }
::= { exampleDecimalPfIntVector1Table 1 }

ExampleDecimalPfIntVector1Entry ::= SEQUENCE {
   exampleDecimalPfIntVector1Index
      Integer32,
   exampleDecimalPfIntVector1Value
      Unsigned32 }

exampleDecimalPfIntVector1Index OBJECT-TYPE
   SYNTAX     Integer32 (0..15)
   ACCESS     not-accessible
   STATUS     mandatory
   DESCRIPTION
     "This variable represents the exampleDecimalPfIntVector1Table
      specific index for the exampleDecimalPfIntVector1Table."
::= { exampleDecimalPfIntVector1Entry 1 }

exampleDecimalPfIntVector1Value OBJECT-TYPE
   SYNTAX     Unsigned32 (0..50 | 100..150)
   ACCESS     read-write
   STATUS     mandatory
   DESCRIPTION
     "This variable represents an individual value for the
      exampleDecimalPfIntVector1Table."
::= { exampleDecimalPfIntVector1Entry 2 }

exampleDecimalPfIntArrayTable OBJECT-TYPE
   SYNTAX     SEQUENCE OF ExampleDecimalPfIntArrayEntry
   ACCESS     not-accessible
   STATUS     mandatory
   DESCRIPTION
     ""
::= { exampleDecimal 1022 }

exampleDecimalPfIntArrayEntry OBJECT-TYPE
   SYNTAX     ExampleDecimalPfIntArrayEntry
   ACCESS     not-accessible
   STATUS     mandatory
   DESCRIPTION
     "An entry in the exampleDecimalPfIntArrayTable."
   INDEX {
      exampleIndex,
      exampleDecimalIndex,
      exampleDecimalPfIntArrayRowIndex,
      exampleDecimalPfIntArrayColumnIndex }
::= { exampleDecimalPfIntArrayTable 1 }

ExampleDecimalPfIntArrayEntry ::= SEQUENCE {
   exampleDecimalPfIntArrayRowIndex
      Integer32,
   exampleDecimalPfIntArrayColumnIndex
      Integer32,
   exampleDecimalPfIntArrayValue
      Unsigned32 }

exampleDecimalPfIntArrayRowIndex OBJECT-TYPE
   SYNTAX     Integer32 (0..2)
   ACCESS     not-accessible
   STATUS     mandatory
   DESCRIPTION
     "This variable represents the next to last index for the 
      exampleDecimalPfIntArrayTable."
::= { exampleDecimalPfIntArrayEntry 1 }

exampleDecimalPfIntArrayColumnIndex OBJECT-TYPE
   SYNTAX     Integer32 (0..3)
   ACCESS     not-accessible
   STATUS     mandatory
   DESCRIPTION
     "This variable represents the final index for the 
      exampleDecimalPfIntArrayTable."
::= { exampleDecimalPfIntArrayEntry 2 }

exampleDecimalPfIntArrayValue OBJECT-TYPE
   SYNTAX     Unsigned32 (0..255)
   ACCESS     read-write
   STATUS     mandatory
   DESCRIPTION
     "This variable represents an individual value for the
      exampleDecimalPfIntArrayTable."
::= { exampleDecimalPfIntArrayEntry 3 }

exampleDecimalPfIntArray1Table OBJECT-TYPE
   SYNTAX     SEQUENCE OF ExampleDecimalPfIntArray1Entry
   ACCESS     not-accessible
   STATUS     mandatory
   DESCRIPTION
     ""
::= { exampleDecimal 1023 }

exampleDecimalPfIntArray1Entry OBJECT-TYPE
   SYNTAX     ExampleDecimalPfIntArray1Entry
   ACCESS     not-accessible
   STATUS     mandatory
   DESCRIPTION
     "An entry in the exampleDecimalPfIntArray1Table."
   INDEX {
      exampleIndex,
      exampleDecimalIndex,
      exampleDecimalPfIntArray1RowIndex,
      exampleDecimalPfIntArray1ColumnIndex }
::= { exampleDecimalPfIntArray1Table 1 }

ExampleDecimalPfIntArray1Entry ::= SEQUENCE {
   exampleDecimalPfIntArray1RowIndex
      Integer32,
   exampleDecimalPfIntArray1ColumnIndex
      Integer32,
   exampleDecimalPfIntArray1Value
      Unsigned32 }

exampleDecimalPfIntArray1RowIndex OBJECT-TYPE
   SYNTAX     Integer32 (0..2)
   ACCESS     not-accessible
   STATUS     mandatory
   DESCRIPTION
     "This variable represents the next to last index for the 
      exampleDecimalPfIntArray1Table."
::= { exampleDecimalPfIntArray1Entry 1 }

exampleDecimalPfIntArray1ColumnIndex OBJECT-TYPE
   SYNTAX     Integer32 (0..3)
   ACCESS     not-accessible
   STATUS     mandatory
   DESCRIPTION
     "This variable represents the final index for the 
      exampleDecimalPfIntArray1Table."
::= { exampleDecimalPfIntArray1Entry 2 }

exampleDecimalPfIntArray1Value OBJECT-TYPE
   SYNTAX     Unsigned32 (0..10 | 20..200)
   ACCESS     read-write
   STATUS     mandatory
   DESCRIPTION
     "This variable represents an individual value for the
      exampleDecimalPfIntArray1Table."
::= { exampleDecimalPfIntArray1Entry 3 }

exampleDecimalPfIntReplicatedTable OBJECT-TYPE
   SYNTAX     SEQUENCE OF ExampleDecimalPfIntReplicatedEntry
   ACCESS     not-accessible
   STATUS     mandatory
   DESCRIPTION
     ""
::= { exampleDecimal 1024 }

exampleDecimalPfIntReplicatedEntry OBJECT-TYPE
   SYNTAX     ExampleDecimalPfIntReplicatedEntry
   ACCESS     not-accessible
   STATUS     mandatory
   DESCRIPTION
     "An entry in the exampleDecimalPfIntReplicatedTable."
   INDEX {
      exampleIndex,
      exampleDecimalIndex,
      exampleDecimalPfIntReplicatedIndex }
::= { exampleDecimalPfIntReplicatedTable 1 }

ExampleDecimalPfIntReplicatedEntry ::= SEQUENCE {
   exampleDecimalPfIntReplicatedIndex
      Integer32,
   exampleDecimalPfIntReplicatedValue
      Unsigned32,
   exampleDecimalPfIntReplicatedRowStatus
      RowStatus }

exampleDecimalPfIntReplicatedIndex OBJECT-TYPE
   SYNTAX     Integer32 (0..9)
   ACCESS     not-accessible
   STATUS     mandatory
   DESCRIPTION
     "This variable represents the index for the exampleDecimalPfIntReplicatedTable."
::= { exampleDecimalPfIntReplicatedEntry 1 }

exampleDecimalPfIntReplicatedValue OBJECT-TYPE
   SYNTAX     Unsigned32 (0..65535)
   ACCESS     read-write
   STATUS     mandatory
   DESCRIPTION
     "This variable represents an individual value for the
      exampleDecimalPfIntReplicatedTable."
::= { exampleDecimalPfIntReplicatedEntry 2 }

exampleDecimalPfIntReplicatedRowStatus OBJECT-TYPE
   SYNTAX     RowStatus 
   ACCESS     write-only
   STATUS     mandatory
   DESCRIPTION
     "This variable is used to control the addition and deletion 
      of individual values of the exampleDecimalPfIntReplicatedTable."
::= { exampleDecimalPfIntReplicatedEntry 3 }

exampleDecimalPfIntReplicated1Table OBJECT-TYPE
   SYNTAX     SEQUENCE OF ExampleDecimalPfIntReplicated1Entry
   ACCESS     not-accessible
   STATUS     mandatory
   DESCRIPTION
     ""
::= { exampleDecimal 1025 }

exampleDecimalPfIntReplicated1Entry OBJECT-TYPE
   SYNTAX     ExampleDecimalPfIntReplicated1Entry
   ACCESS     not-accessible
   STATUS     mandatory
   DESCRIPTION
     "An entry in the exampleDecimalPfIntReplicated1Table."
   INDEX {
      exampleIndex,
      exampleDecimalIndex,
      exampleDecimalPfIntReplicated1Index }
::= { exampleDecimalPfIntReplicated1Table 1 }

ExampleDecimalPfIntReplicated1Entry ::= SEQUENCE {
   exampleDecimalPfIntReplicated1Index
      Integer32,
   exampleDecimalPfIntReplicated1Value
      Unsigned32,
   exampleDecimalPfIntReplicated1RowStatus
      RowStatus }

exampleDecimalPfIntReplicated1Index OBJECT-TYPE
   SYNTAX     Integer32 (0..9 | 11..19)
   ACCESS     not-accessible
   STATUS     mandatory
   DESCRIPTION
     "This variable represents the index for the exampleDecimalPfIntReplicated1Table."
::= { exampleDecimalPfIntReplicated1Entry 1 }

exampleDecimalPfIntReplicated1Value OBJECT-TYPE
   SYNTAX     Unsigned32 (0..3 | 30..300)
   ACCESS     read-write
   STATUS     mandatory
   DESCRIPTION
     "This variable represents an individual value for the
      exampleDecimalPfIntReplicated1Table."
::= { exampleDecimalPfIntReplicated1Entry 2 }

exampleDecimalPfIntReplicated1RowStatus OBJECT-TYPE
   SYNTAX     RowStatus 
   ACCESS     write-only
   STATUS     mandatory
   DESCRIPTION
     "This variable is used to control the addition and deletion 
      of individual values of the exampleDecimalPfIntReplicated1Table."
::= { exampleDecimalPfIntReplicated1Entry 3 }

exampleDecimalPfIntListTable OBJECT-TYPE
   SYNTAX     SEQUENCE OF ExampleDecimalPfIntListEntry
   ACCESS     not-accessible
   STATUS     mandatory
   DESCRIPTION
     ""
::= { exampleDecimal 1026 }

exampleDecimalPfIntListEntry OBJECT-TYPE
   SYNTAX     ExampleDecimalPfIntListEntry
   ACCESS     not-accessible
   STATUS     mandatory
   DESCRIPTION
     "An entry in the exampleDecimalPfIntListTable."
   INDEX {
      exampleIndex,
      exampleDecimalIndex,
      exampleDecimalPfIntListValue }
::= { exampleDecimalPfIntListTable 1 }

ExampleDecimalPfIntListEntry ::= SEQUENCE {
   exampleDecimalPfIntListValue
      Integer32,
   exampleDecimalPfIntListRowStatus
      RowStatus }

exampleDecimalPfIntListValue OBJECT-TYPE
   SYNTAX     Integer32 (1..1000)
   ACCESS     read-write
   STATUS     mandatory
   DESCRIPTION
     "This variable represents both the value and the index for the
      exampleDecimalPfIntListTable."
::= { exampleDecimalPfIntListEntry 1 }

exampleDecimalPfIntListRowStatus OBJECT-TYPE
   SYNTAX     RowStatus 
   ACCESS     write-only
   STATUS     mandatory
   DESCRIPTION
     "This variable is used to control the addition and deletion 
      of individual values of the exampleDecimalPfIntListTable."
::= { exampleDecimalPfIntListEntry 2 }

exampleDecimalPfIntList1Table OBJECT-TYPE
   SYNTAX     SEQUENCE OF ExampleDecimalPfIntList1Entry
   ACCESS     not-accessible
   STATUS     mandatory
   DESCRIPTION
     ""
::= { exampleDecimal 1027 }

exampleDecimalPfIntList1Entry OBJECT-TYPE
   SYNTAX     ExampleDecimalPfIntList1Entry
   ACCESS     not-accessible
   STATUS     mandatory
   DESCRIPTION
     "An entry in the exampleDecimalPfIntList1Table."
   INDEX {
      exampleIndex,
      exampleDecimalIndex,
      exampleDecimalPfIntList1Value }
::= { exampleDecimalPfIntList1Table 1 }

ExampleDecimalPfIntList1Entry ::= SEQUENCE {
   exampleDecimalPfIntList1Value
      Integer32,
   exampleDecimalPfIntList1RowStatus
      RowStatus }

exampleDecimalPfIntList1Value OBJECT-TYPE
   SYNTAX     Integer32 (1..10 | 15..50)
   ACCESS     read-write
   STATUS     mandatory
   DESCRIPTION
     "This variable represents both the value and the index for the
      exampleDecimalPfIntList1Table."
::= { exampleDecimalPfIntList1Entry 1 }

exampleDecimalPfIntList1RowStatus OBJECT-TYPE
   SYNTAX     RowStatus 
   ACCESS     write-only
   STATUS     mandatory
   DESCRIPTION
     "This variable is used to control the addition and deletion 
      of individual values of the exampleDecimalPfIntList1Table."
::= { exampleDecimalPfIntList1Entry 2 }



exampleHex OBJECT IDENTIFIER ::= { example 3 }



exampleHexRowStatusTable OBJECT-TYPE
   SYNTAX     SEQUENCE OF ExampleHexRowStatusEntry
   ACCESS     not-accessible
   STATUS     mandatory
   DESCRIPTION
     "This entry controls the addition and deletion of 
      exampleHex components."
::= { exampleHex 1 }

exampleHexRowStatusEntry OBJECT-TYPE
   SYNTAX     ExampleHexRowStatusEntry
   ACCESS     not-accessible
   STATUS     mandatory
   DESCRIPTION
     "A single entry in the table represents a single 
      exampleHex component."
   INDEX {
      exampleIndex,
      exampleHexIndex }
::= { exampleHexRowStatusTable 1 }

ExampleHexRowStatusEntry ::= SEQUENCE {
   exampleHexRowStatus
      RowStatus,
   exampleHexComponentName
      DisplayString,
   exampleHexStorageType
      StorageType,
   exampleHexIndex
      Integer32 }

exampleHexRowStatus OBJECT-TYPE
   SYNTAX     RowStatus 
   ACCESS     read-write
   STATUS     mandatory
   DESCRIPTION
     "This variable is used as the basis for SNMP naming of
      exampleHex components.
      These components can be added and deleted."
::= { exampleHexRowStatusEntry 1 }

exampleHexComponentName OBJECT-TYPE
   SYNTAX     DisplayString 
   ACCESS     read-only
   STATUS     mandatory
   DESCRIPTION
     "This variable provides the component's string name for
      use with the ASCII Console Interface"
::= { exampleHexRowStatusEntry 2 }

exampleHexStorageType OBJECT-TYPE
   SYNTAX     StorageType 
   ACCESS     read-only
   STATUS     mandatory
   DESCRIPTION
     "This variable represents the storage type value for the
      exampleHex tables."
::= { exampleHexRowStatusEntry 4 }

exampleHexIndex OBJECT-TYPE
   SYNTAX     Integer32 (0..255)
   ACCESS     not-accessible
   STATUS     mandatory
   DESCRIPTION
     "This variable represents the index for the exampleHex tables."
::= { exampleHexRowStatusEntry 10 }

exampleHexOperationalTable OBJECT-TYPE
   SYNTAX     SEQUENCE OF ExampleHexOperationalEntry
   ACCESS     not-accessible
   STATUS     mandatory
   DESCRIPTION
     ""
::= { exampleHex 10 }

exampleHexOperationalEntry OBJECT-TYPE
   SYNTAX     ExampleHexOperationalEntry
   ACCESS     not-accessible
   STATUS     mandatory
   DESCRIPTION
     "An entry in the exampleHexOperationalTable."
   INDEX {
      exampleIndex,
      exampleHexIndex }
::= { exampleHexOperationalTable 1 }

ExampleHexOperationalEntry ::= SEQUENCE {
   exampleHexOperStructHex
      Hex,
   exampleHexOperFreeHex
      Hex }

exampleHexOperStructHex OBJECT-TYPE
   SYNTAX     Hex (0..256)
   ACCESS     read-write
   STATUS     mandatory
   DESCRIPTION
     ""
::= { exampleHexOperationalEntry 1 }

exampleHexOperFreeHex OBJECT-TYPE
   SYNTAX     Hex (0..256)
   ACCESS     read-write
   STATUS     mandatory
   DESCRIPTION
     ""
::= { exampleHexOperationalEntry 2 }

exampleHexProvisionalTable OBJECT-TYPE
   SYNTAX     SEQUENCE OF ExampleHexProvisionalEntry
   ACCESS     not-accessible
   STATUS     mandatory
   DESCRIPTION
     ""
::= { exampleHex 11 }

exampleHexProvisionalEntry OBJECT-TYPE
   SYNTAX     ExampleHexProvisionalEntry
   ACCESS     not-accessible
   STATUS     mandatory
   DESCRIPTION
     "An entry in the exampleHexProvisionalTable."
   INDEX {
      exampleIndex,
      exampleHexIndex }
::= { exampleHexProvisionalTable 1 }

ExampleHexProvisionalEntry ::= SEQUENCE {
   exampleHexProvEnumSub
      Link,
   exampleHexProvStructHex
      Hex,
   exampleHexProvFreeHex
      Hex,
   exampleHexProvFreeHex1
      Hex }

exampleHexProvEnumSub OBJECT-TYPE
   SYNTAX     Link 
   ACCESS     read-write
   STATUS     mandatory
   DESCRIPTION
     ""
::= { exampleHexProvisionalEntry 1 }

exampleHexProvStructHex OBJECT-TYPE
   SYNTAX     Hex (0..256 | 512 | 513 | 514)
   ACCESS     read-write
   STATUS     mandatory
   DESCRIPTION
     "VALUES (

      512 = infinity

      513 = notApplicable

      514 = notMeasured

      )"
   DEFVAL     { 512 }
::= { exampleHexProvisionalEntry 2 }

exampleHexProvFreeHex OBJECT-TYPE
   SYNTAX     Hex (0..256)
   ACCESS     read-write
   STATUS     mandatory
   DESCRIPTION
     ""
   DEFVAL     { 18 }
::= { exampleHexProvisionalEntry 3 }

exampleHexProvFreeHex1 OBJECT-TYPE
   SYNTAX     Hex (0..16 | 256..4096)
   ACCESS     read-write
   STATUS     mandatory
   DESCRIPTION
     ""
::= { exampleHexProvisionalEntry 4 }

exampleHexOsHexVectorTable OBJECT-TYPE
   SYNTAX     SEQUENCE OF ExampleHexOsHexVectorEntry
   ACCESS     not-accessible
   STATUS     mandatory
   DESCRIPTION
     ""
::= { exampleHex 1040 }

exampleHexOsHexVectorEntry OBJECT-TYPE
   SYNTAX     ExampleHexOsHexVectorEntry
   ACCESS     not-accessible
   STATUS     mandatory
   DESCRIPTION
     "An entry in the exampleHexOsHexVectorTable."
   INDEX {
      exampleIndex,
      exampleHexIndex,
      exampleHexOsHexVectorIndex }
::= { exampleHexOsHexVectorTable 1 }

ExampleHexOsHexVectorEntry ::= SEQUENCE {
   exampleHexOsHexVectorIndex
      Integer32,
   exampleHexOsHexVectorValue
      Hex }

exampleHexOsHexVectorIndex OBJECT-TYPE
   SYNTAX     Integer32 (0..9)
   ACCESS     not-accessible
   STATUS     mandatory
   DESCRIPTION
     "This variable represents the exampleHexOsHexVectorTable
      specific index for the exampleHexOsHexVectorTable."
::= { exampleHexOsHexVectorEntry 1 }

exampleHexOsHexVectorValue OBJECT-TYPE
   SYNTAX     Hex (0..255)
   ACCESS     read-write
   STATUS     mandatory
   DESCRIPTION
     "This variable represents an individual value for the
      exampleHexOsHexVectorTable."
::= { exampleHexOsHexVectorEntry 2 }

exampleHexOsHexArrayTable OBJECT-TYPE
   SYNTAX     SEQUENCE OF ExampleHexOsHexArrayEntry
   ACCESS     not-accessible
   STATUS     mandatory
   DESCRIPTION
     ""
::= { exampleHex 1041 }

exampleHexOsHexArrayEntry OBJECT-TYPE
   SYNTAX     ExampleHexOsHexArrayEntry
   ACCESS     not-accessible
   STATUS     mandatory
   DESCRIPTION
     "An entry in the exampleHexOsHexArrayTable."
   INDEX {
      exampleIndex,
      exampleHexIndex,
      exampleHexOsHexArrayRowIndex,
      exampleHexOsHexArrayColumnIndex }
::= { exampleHexOsHexArrayTable 1 }

ExampleHexOsHexArrayEntry ::= SEQUENCE {
   exampleHexOsHexArrayRowIndex
      Integer32,
   exampleHexOsHexArrayColumnIndex
      Integer32,
   exampleHexOsHexArrayValue
      Hex }

exampleHexOsHexArrayRowIndex OBJECT-TYPE
   SYNTAX     Integer32 (0..2)
   ACCESS     not-accessible
   STATUS     mandatory
   DESCRIPTION
     "This variable represents the next to last index for the 
      exampleHexOsHexArrayTable."
::= { exampleHexOsHexArrayEntry 1 }

exampleHexOsHexArrayColumnIndex OBJECT-TYPE
   SYNTAX     Integer32 (0..3)
   ACCESS     not-accessible
   STATUS     mandatory
   DESCRIPTION
     "This variable represents the final index for the 
      exampleHexOsHexArrayTable."
::= { exampleHexOsHexArrayEntry 2 }

exampleHexOsHexArrayValue OBJECT-TYPE
   SYNTAX     Hex (0..255)
   ACCESS     read-write
   STATUS     mandatory
   DESCRIPTION
     "This variable represents an individual value for the
      exampleHexOsHexArrayTable."
::= { exampleHexOsHexArrayEntry 3 }

exampleHexOfHexVectorTable OBJECT-TYPE
   SYNTAX     SEQUENCE OF ExampleHexOfHexVectorEntry
   ACCESS     not-accessible
   STATUS     mandatory
   DESCRIPTION
     ""
::= { exampleHex 1042 }

exampleHexOfHexVectorEntry OBJECT-TYPE
   SYNTAX     ExampleHexOfHexVectorEntry
   ACCESS     not-accessible
   STATUS     mandatory
   DESCRIPTION
     "An entry in the exampleHexOfHexVectorTable."
   INDEX {
      exampleIndex,
      exampleHexIndex,
      exampleHexOfHexVectorIndex }
::= { exampleHexOfHexVectorTable 1 }

ExampleHexOfHexVectorEntry ::= SEQUENCE {
   exampleHexOfHexVectorIndex
      Integer32,
   exampleHexOfHexVectorValue
      Hex }

exampleHexOfHexVectorIndex OBJECT-TYPE
   SYNTAX     Integer32 (0..9)
   ACCESS     not-accessible
   STATUS     mandatory
   DESCRIPTION
     "This variable represents the exampleHexOfHexVectorTable
      specific index for the exampleHexOfHexVectorTable."
::= { exampleHexOfHexVectorEntry 1 }

exampleHexOfHexVectorValue OBJECT-TYPE
   SYNTAX     Hex (0..256)
   ACCESS     read-write
   STATUS     mandatory
   DESCRIPTION
     "This variable represents an individual value for the
      exampleHexOfHexVectorTable."
::= { exampleHexOfHexVectorEntry 2 }

exampleHexOfHexArrayTable OBJECT-TYPE
   SYNTAX     SEQUENCE OF ExampleHexOfHexArrayEntry
   ACCESS     not-accessible
   STATUS     mandatory
   DESCRIPTION
     ""
::= { exampleHex 1043 }

exampleHexOfHexArrayEntry OBJECT-TYPE
   SYNTAX     ExampleHexOfHexArrayEntry
   ACCESS     not-accessible
   STATUS     mandatory
   DESCRIPTION
     "An entry in the exampleHexOfHexArrayTable."
   INDEX {
      exampleIndex,
      exampleHexIndex,
      exampleHexOfHexArrayRowIndex,
      exampleHexOfHexArrayColumnIndex }
::= { exampleHexOfHexArrayTable 1 }

ExampleHexOfHexArrayEntry ::= SEQUENCE {
   exampleHexOfHexArrayRowIndex
      Integer32,
   exampleHexOfHexArrayColumnIndex
      Integer32,
   exampleHexOfHexArrayValue
      Hex }

exampleHexOfHexArrayRowIndex OBJECT-TYPE
   SYNTAX     Integer32 (0..2)
   ACCESS     not-accessible
   STATUS     mandatory
   DESCRIPTION
     "This variable represents the next to last index for the 
      exampleHexOfHexArrayTable."
::= { exampleHexOfHexArrayEntry 1 }

exampleHexOfHexArrayColumnIndex OBJECT-TYPE
   SYNTAX     Integer32 (0..3)
   ACCESS     not-accessible
   STATUS     mandatory
   DESCRIPTION
     "This variable represents the final index for the 
      exampleHexOfHexArrayTable."
::= { exampleHexOfHexArrayEntry 2 }

exampleHexOfHexArrayValue OBJECT-TYPE
   SYNTAX     Hex (0..255)
   ACCESS     read-write
   STATUS     mandatory
   DESCRIPTION
     "This variable represents an individual value for the
      exampleHexOfHexArrayTable."
::= { exampleHexOfHexArrayEntry 3 }

exampleHexOfHexReplicatedTable OBJECT-TYPE
   SYNTAX     SEQUENCE OF ExampleHexOfHexReplicatedEntry
   ACCESS     not-accessible
   STATUS     mandatory
   DESCRIPTION
     ""
::= { exampleHex 1044 }

exampleHexOfHexReplicatedEntry OBJECT-TYPE
   SYNTAX     ExampleHexOfHexReplicatedEntry
   ACCESS     not-accessible
   STATUS     mandatory
   DESCRIPTION
     "An entry in the exampleHexOfHexReplicatedTable."
   INDEX {
      exampleIndex,
      exampleHexIndex,
      exampleHexOfHexReplicatedIndex }
::= { exampleHexOfHexReplicatedTable 1 }

ExampleHexOfHexReplicatedEntry ::= SEQUENCE {
   exampleHexOfHexReplicatedIndex
      Integer32,
   exampleHexOfHexReplicatedValue
      Hex,
   exampleHexOfHexReplicatedRowStatus
      RowStatus }

exampleHexOfHexReplicatedIndex OBJECT-TYPE
   SYNTAX     Integer32 (0..9)
   ACCESS     not-accessible
   STATUS     mandatory
   DESCRIPTION
     "This variable represents the index for the exampleHexOfHexReplicatedTable."
::= { exampleHexOfHexReplicatedEntry 1 }

exampleHexOfHexReplicatedValue OBJECT-TYPE
   SYNTAX     Hex (0..256)
   ACCESS     read-write
   STATUS     mandatory
   DESCRIPTION
     "This variable represents an individual value for the
      exampleHexOfHexReplicatedTable."
::= { exampleHexOfHexReplicatedEntry 2 }

exampleHexOfHexReplicatedRowStatus OBJECT-TYPE
   SYNTAX     RowStatus 
   ACCESS     write-only
   STATUS     mandatory
   DESCRIPTION
     "This variable is used to control the addition and deletion 
      of individual values of the exampleHexOfHexReplicatedTable."
::= { exampleHexOfHexReplicatedEntry 3 }

exampleHexOfHexListTable OBJECT-TYPE
   SYNTAX     SEQUENCE OF ExampleHexOfHexListEntry
   ACCESS     not-accessible
   STATUS     mandatory
   DESCRIPTION
     ""
::= { exampleHex 1045 }

exampleHexOfHexListEntry OBJECT-TYPE
   SYNTAX     ExampleHexOfHexListEntry
   ACCESS     not-accessible
   STATUS     mandatory
   DESCRIPTION
     "An entry in the exampleHexOfHexListTable."
   INDEX {
      exampleIndex,
      exampleHexIndex,
      exampleHexOfHexListValue }
::= { exampleHexOfHexListTable 1 }

ExampleHexOfHexListEntry ::= SEQUENCE {
   exampleHexOfHexListValue
      Integer32,
   exampleHexOfHexListRowStatus
      RowStatus }

exampleHexOfHexListValue OBJECT-TYPE
   SYNTAX     Integer32 (1..4096)
   ACCESS     read-write
   STATUS     mandatory
   DESCRIPTION
     "This variable represents both the value and the index for the
      exampleHexOfHexListTable."
::= { exampleHexOfHexListEntry 1 }

exampleHexOfHexListRowStatus OBJECT-TYPE
   SYNTAX     RowStatus 
   ACCESS     write-only
   STATUS     mandatory
   DESCRIPTION
     "This variable is used to control the addition and deletion 
      of individual values of the exampleHexOfHexListTable."
::= { exampleHexOfHexListEntry 2 }

exampleHexProvStructHexVectorTable OBJECT-TYPE
   SYNTAX     SEQUENCE OF ExampleHexProvStructHexVectorEntry
   ACCESS     not-accessible
   STATUS     mandatory
   DESCRIPTION
     ""
::= { exampleHex 1046 }

exampleHexProvStructHexVectorEntry OBJECT-TYPE
   SYNTAX     ExampleHexProvStructHexVectorEntry
   ACCESS     not-accessible
   STATUS     mandatory
   DESCRIPTION
     "An entry in the exampleHexProvStructHexVectorTable."
   INDEX {
      exampleIndex,
      exampleHexIndex,
      exampleHexProvStructHexVectorIndex }
::= { exampleHexProvStructHexVectorTable 1 }

ExampleHexProvStructHexVectorEntry ::= SEQUENCE {
   exampleHexProvStructHexVectorIndex
      Integer32,
   exampleHexProvStructHexVectorValue
      Hex }

exampleHexProvStructHexVectorIndex OBJECT-TYPE
   SYNTAX     Integer32 (0..9)
   ACCESS     not-accessible
   STATUS     mandatory
   DESCRIPTION
     "This variable represents the exampleHexProvStructHexVectorTable
      specific index for the exampleHexProvStructHexVectorTable."
::= { exampleHexProvStructHexVectorEntry 1 }

exampleHexProvStructHexVectorValue OBJECT-TYPE
   SYNTAX     Hex (0..255)
   ACCESS     read-write
   STATUS     mandatory
   DESCRIPTION
     "This variable represents an individual value for the
      exampleHexProvStructHexVectorTable."
::= { exampleHexProvStructHexVectorEntry 2 }

exampleHexProvStructHexArrayTable OBJECT-TYPE
   SYNTAX     SEQUENCE OF ExampleHexProvStructHexArrayEntry
   ACCESS     not-accessible
   STATUS     mandatory
   DESCRIPTION
     ""
::= { exampleHex 1047 }

exampleHexProvStructHexArrayEntry OBJECT-TYPE
   SYNTAX     ExampleHexProvStructHexArrayEntry
   ACCESS     not-accessible
   STATUS     mandatory
   DESCRIPTION
     "An entry in the exampleHexProvStructHexArrayTable."
   INDEX {
      exampleIndex,
      exampleHexIndex,
      exampleHexProvStructHexArrayRowIndex,
      exampleHexProvStructHexArrayColumnIndex }
::= { exampleHexProvStructHexArrayTable 1 }

ExampleHexProvStructHexArrayEntry ::= SEQUENCE {
   exampleHexProvStructHexArrayRowIndex
      Integer32,
   exampleHexProvStructHexArrayColumnIndex
      Integer32,
   exampleHexProvStructHexArrayValue
      Hex }

exampleHexProvStructHexArrayRowIndex OBJECT-TYPE
   SYNTAX     Integer32 (0..2)
   ACCESS     not-accessible
   STATUS     mandatory
   DESCRIPTION
     "This variable represents the next to last index for the 
      exampleHexProvStructHexArrayTable."
::= { exampleHexProvStructHexArrayEntry 1 }

exampleHexProvStructHexArrayColumnIndex OBJECT-TYPE
   SYNTAX     Integer32 (0..3)
   ACCESS     not-accessible
   STATUS     mandatory
   DESCRIPTION
     "This variable represents the final index for the 
      exampleHexProvStructHexArrayTable."
::= { exampleHexProvStructHexArrayEntry 2 }

exampleHexProvStructHexArrayValue OBJECT-TYPE
   SYNTAX     Hex (0..255)
   ACCESS     read-write
   STATUS     mandatory
   DESCRIPTION
     "This variable represents an individual value for the
      exampleHexProvStructHexArrayTable."
::= { exampleHexProvStructHexArrayEntry 3 }

exampleHexProvFreeHexVectorTable OBJECT-TYPE
   SYNTAX     SEQUENCE OF ExampleHexProvFreeHexVectorEntry
   ACCESS     not-accessible
   STATUS     mandatory
   DESCRIPTION
     ""
::= { exampleHex 1048 }

exampleHexProvFreeHexVectorEntry OBJECT-TYPE
   SYNTAX     ExampleHexProvFreeHexVectorEntry
   ACCESS     not-accessible
   STATUS     mandatory
   DESCRIPTION
     "An entry in the exampleHexProvFreeHexVectorTable."
   INDEX {
      exampleIndex,
      exampleHexIndex,
      exampleHexProvFreeHexVectorIndex }
::= { exampleHexProvFreeHexVectorTable 1 }

ExampleHexProvFreeHexVectorEntry ::= SEQUENCE {
   exampleHexProvFreeHexVectorIndex
      Integer32,
   exampleHexProvFreeHexVectorValue
      Hex }

exampleHexProvFreeHexVectorIndex OBJECT-TYPE
   SYNTAX     Integer32 (0..9)
   ACCESS     not-accessible
   STATUS     mandatory
   DESCRIPTION
     "This variable represents the exampleHexProvFreeHexVectorTable
      specific index for the exampleHexProvFreeHexVectorTable."
::= { exampleHexProvFreeHexVectorEntry 1 }

exampleHexProvFreeHexVectorValue OBJECT-TYPE
   SYNTAX     Hex (0..256)
   ACCESS     read-write
   STATUS     mandatory
   DESCRIPTION
     "This variable represents an individual value for the
      exampleHexProvFreeHexVectorTable."
::= { exampleHexProvFreeHexVectorEntry 2 }

exampleHexProvFreeHexVector1Table OBJECT-TYPE
   SYNTAX     SEQUENCE OF ExampleHexProvFreeHexVector1Entry
   ACCESS     not-accessible
   STATUS     mandatory
   DESCRIPTION
     ""
::= { exampleHex 1049 }

exampleHexProvFreeHexVector1Entry OBJECT-TYPE
   SYNTAX     ExampleHexProvFreeHexVector1Entry
   ACCESS     not-accessible
   STATUS     mandatory
   DESCRIPTION
     "An entry in the exampleHexProvFreeHexVector1Table."
   INDEX {
      exampleIndex,
      exampleHexIndex,
      exampleHexProvFreeHexVector1Index }
::= { exampleHexProvFreeHexVector1Table 1 }

ExampleHexProvFreeHexVector1Entry ::= SEQUENCE {
   exampleHexProvFreeHexVector1Index
      Integer32,
   exampleHexProvFreeHexVector1Value
      Hex }

exampleHexProvFreeHexVector1Index OBJECT-TYPE
   SYNTAX     Integer32 (0..9)
   ACCESS     not-accessible
   STATUS     mandatory
   DESCRIPTION
     "This variable represents the exampleHexProvFreeHexVector1Table
      specific index for the exampleHexProvFreeHexVector1Table."
::= { exampleHexProvFreeHexVector1Entry 1 }

exampleHexProvFreeHexVector1Value OBJECT-TYPE
   SYNTAX     Hex (0..16 | 256..4096)
   ACCESS     read-write
   STATUS     mandatory
   DESCRIPTION
     "This variable represents an individual value for the
      exampleHexProvFreeHexVector1Table."
::= { exampleHexProvFreeHexVector1Entry 2 }

exampleHexProvFreeHexVector2Table OBJECT-TYPE
   SYNTAX     SEQUENCE OF ExampleHexProvFreeHexVector2Entry
   ACCESS     not-accessible
   STATUS     mandatory
   DESCRIPTION
     ""
::= { exampleHex 1050 }

exampleHexProvFreeHexVector2Entry OBJECT-TYPE
   SYNTAX     ExampleHexProvFreeHexVector2Entry
   ACCESS     not-accessible
   STATUS     mandatory
   DESCRIPTION
     "An entry in the exampleHexProvFreeHexVector2Table."
   INDEX {
      exampleIndex,
      exampleHexIndex,
      exampleHexProvFreeHexVector2Index }
::= { exampleHexProvFreeHexVector2Table 1 }

ExampleHexProvFreeHexVector2Entry ::= SEQUENCE {
   exampleHexProvFreeHexVector2Index
      Integer32,
   exampleHexProvFreeHexVector2Value
      Hex }

exampleHexProvFreeHexVector2Index OBJECT-TYPE
   SYNTAX     Integer32 (0..5)
   ACCESS     not-accessible
   STATUS     mandatory
   DESCRIPTION
     "This variable represents the exampleHexProvFreeHexVector2Table
      specific index for the exampleHexProvFreeHexVector2Table."
::= { exampleHexProvFreeHexVector2Entry 1 }

exampleHexProvFreeHexVector2Value OBJECT-TYPE
   SYNTAX     Hex (0..16 | 256..4096)
   ACCESS     read-write
   STATUS     mandatory
   DESCRIPTION
     "This variable represents an individual value for the
      exampleHexProvFreeHexVector2Table."
::= { exampleHexProvFreeHexVector2Entry 2 }

exampleHexProvFreeHexArrayTable OBJECT-TYPE
   SYNTAX     SEQUENCE OF ExampleHexProvFreeHexArrayEntry
   ACCESS     not-accessible
   STATUS     mandatory
   DESCRIPTION
     ""
::= { exampleHex 1051 }

exampleHexProvFreeHexArrayEntry OBJECT-TYPE
   SYNTAX     ExampleHexProvFreeHexArrayEntry
   ACCESS     not-accessible
   STATUS     mandatory
   DESCRIPTION
     "An entry in the exampleHexProvFreeHexArrayTable."
   INDEX {
      exampleIndex,
      exampleHexIndex,
      exampleHexProvFreeHexArrayRowIndex,
      exampleHexProvFreeHexArrayColumnIndex }
::= { exampleHexProvFreeHexArrayTable 1 }

ExampleHexProvFreeHexArrayEntry ::= SEQUENCE {
   exampleHexProvFreeHexArrayRowIndex
      Integer32,
   exampleHexProvFreeHexArrayColumnIndex
      Integer32,
   exampleHexProvFreeHexArrayValue
      Hex }

exampleHexProvFreeHexArrayRowIndex OBJECT-TYPE
   SYNTAX     Integer32 (0..2)
   ACCESS     not-accessible
   STATUS     mandatory
   DESCRIPTION
     "This variable represents the next to last index for the 
      exampleHexProvFreeHexArrayTable."
::= { exampleHexProvFreeHexArrayEntry 1 }

exampleHexProvFreeHexArrayColumnIndex OBJECT-TYPE
   SYNTAX     Integer32 (0..3)
   ACCESS     not-accessible
   STATUS     mandatory
   DESCRIPTION
     "This variable represents the final index for the 
      exampleHexProvFreeHexArrayTable."
::= { exampleHexProvFreeHexArrayEntry 2 }

exampleHexProvFreeHexArrayValue OBJECT-TYPE
   SYNTAX     Hex (0..255)
   ACCESS     read-write
   STATUS     mandatory
   DESCRIPTION
     "This variable represents an individual value for the
      exampleHexProvFreeHexArrayTable."
::= { exampleHexProvFreeHexArrayEntry 3 }

exampleHexProvFreeHexArray1Table OBJECT-TYPE
   SYNTAX     SEQUENCE OF ExampleHexProvFreeHexArray1Entry
   ACCESS     not-accessible
   STATUS     mandatory
   DESCRIPTION
     ""
::= { exampleHex 1052 }

exampleHexProvFreeHexArray1Entry OBJECT-TYPE
   SYNTAX     ExampleHexProvFreeHexArray1Entry
   ACCESS     not-accessible
   STATUS     mandatory
   DESCRIPTION
     "An entry in the exampleHexProvFreeHexArray1Table."
   INDEX {
      exampleIndex,
      exampleHexIndex,
      exampleHexProvFreeHexArray1RowIndex,
      exampleHexProvFreeHexArray1ColumnIndex }
::= { exampleHexProvFreeHexArray1Table 1 }

ExampleHexProvFreeHexArray1Entry ::= SEQUENCE {
   exampleHexProvFreeHexArray1RowIndex
      Integer32,
   exampleHexProvFreeHexArray1ColumnIndex
      Integer32,
   exampleHexProvFreeHexArray1Value
      Hex }

exampleHexProvFreeHexArray1RowIndex OBJECT-TYPE
   SYNTAX     Integer32 (0..1 | 3..4)
   ACCESS     not-accessible
   STATUS     mandatory
   DESCRIPTION
     "This variable represents the next to last index for the 
      exampleHexProvFreeHexArray1Table."
::= { exampleHexProvFreeHexArray1Entry 1 }

exampleHexProvFreeHexArray1ColumnIndex OBJECT-TYPE
   SYNTAX     Integer32 (0..3)
   ACCESS     not-accessible
   STATUS     mandatory
   DESCRIPTION
     "This variable represents the final index for the 
      exampleHexProvFreeHexArray1Table."
::= { exampleHexProvFreeHexArray1Entry 2 }

exampleHexProvFreeHexArray1Value OBJECT-TYPE
   SYNTAX     Hex (0..16 | 80..256)
   ACCESS     read-write
   STATUS     mandatory
   DESCRIPTION
     "This variable represents an individual value for the
      exampleHexProvFreeHexArray1Table."
::= { exampleHexProvFreeHexArray1Entry 3 }

exampleHexProvFreeHexArray2Table OBJECT-TYPE
   SYNTAX     SEQUENCE OF ExampleHexProvFreeHexArray2Entry
   ACCESS     not-accessible
   STATUS     mandatory
   DESCRIPTION
     ""
::= { exampleHex 1053 }

exampleHexProvFreeHexArray2Entry OBJECT-TYPE
   SYNTAX     ExampleHexProvFreeHexArray2Entry
   ACCESS     not-accessible
   STATUS     mandatory
   DESCRIPTION
     "An entry in the exampleHexProvFreeHexArray2Table."
   INDEX {
      exampleIndex,
      exampleHexIndex,
      exampleHexProvFreeHexArray2RowIndex,
      exampleHexProvFreeHexArray2ColumnIndex }
::= { exampleHexProvFreeHexArray2Table 1 }

ExampleHexProvFreeHexArray2Entry ::= SEQUENCE {
   exampleHexProvFreeHexArray2RowIndex
      Integer32,
   exampleHexProvFreeHexArray2ColumnIndex
      Integer32,
   exampleHexProvFreeHexArray2Value
      Hex }

exampleHexProvFreeHexArray2RowIndex OBJECT-TYPE
   SYNTAX     Integer32 (0..3)
   ACCESS     not-accessible
   STATUS     mandatory
   DESCRIPTION
     "This variable represents the next to last index for the 
      exampleHexProvFreeHexArray2Table."
::= { exampleHexProvFreeHexArray2Entry 1 }

exampleHexProvFreeHexArray2ColumnIndex OBJECT-TYPE
   SYNTAX     Integer32 (0..3)
   ACCESS     not-accessible
   STATUS     mandatory
   DESCRIPTION
     "This variable represents the final index for the 
      exampleHexProvFreeHexArray2Table."
::= { exampleHexProvFreeHexArray2Entry 2 }

exampleHexProvFreeHexArray2Value OBJECT-TYPE
   SYNTAX     Hex (0..16 | 80..256)
   ACCESS     read-write
   STATUS     mandatory
   DESCRIPTION
     "This variable represents an individual value for the
      exampleHexProvFreeHexArray2Table."
::= { exampleHexProvFreeHexArray2Entry 3 }

exampleHexProvFreeHexReplicatedTable OBJECT-TYPE
   SYNTAX     SEQUENCE OF ExampleHexProvFreeHexReplicatedEntry
   ACCESS     not-accessible
   STATUS     mandatory
   DESCRIPTION
     ""
::= { exampleHex 1054 }

exampleHexProvFreeHexReplicatedEntry OBJECT-TYPE
   SYNTAX     ExampleHexProvFreeHexReplicatedEntry
   ACCESS     not-accessible
   STATUS     mandatory
   DESCRIPTION
     "An entry in the exampleHexProvFreeHexReplicatedTable."
   INDEX {
      exampleIndex,
      exampleHexIndex,
      exampleHexProvFreeHexReplicatedIndex }
::= { exampleHexProvFreeHexReplicatedTable 1 }

ExampleHexProvFreeHexReplicatedEntry ::= SEQUENCE {
   exampleHexProvFreeHexReplicatedIndex
      Integer32,
   exampleHexProvFreeHexReplicatedValue
      Hex,
   exampleHexProvFreeHexReplicatedRowStatus
      RowStatus }

exampleHexProvFreeHexReplicatedIndex OBJECT-TYPE
   SYNTAX     Integer32 (0..9)
   ACCESS     not-accessible
   STATUS     mandatory
   DESCRIPTION
     "This variable represents the index for the exampleHexProvFreeHexReplicatedTable."
::= { exampleHexProvFreeHexReplicatedEntry 1 }

exampleHexProvFreeHexReplicatedValue OBJECT-TYPE
   SYNTAX     Hex (0..256)
   ACCESS     read-write
   STATUS     mandatory
   DESCRIPTION
     "This variable represents an individual value for the
      exampleHexProvFreeHexReplicatedTable."
::= { exampleHexProvFreeHexReplicatedEntry 2 }

exampleHexProvFreeHexReplicatedRowStatus OBJECT-TYPE
   SYNTAX     RowStatus 
   ACCESS     write-only
   STATUS     mandatory
   DESCRIPTION
     "This variable is used to control the addition and deletion 
      of individual values of the exampleHexProvFreeHexReplicatedTable."
::= { exampleHexProvFreeHexReplicatedEntry 3 }

exampleHexProvFreeHexReplicated1Table OBJECT-TYPE
   SYNTAX     SEQUENCE OF ExampleHexProvFreeHexReplicated1Entry
   ACCESS     not-accessible
   STATUS     mandatory
   DESCRIPTION
     ""
::= { exampleHex 1055 }

exampleHexProvFreeHexReplicated1Entry OBJECT-TYPE
   SYNTAX     ExampleHexProvFreeHexReplicated1Entry
   ACCESS     not-accessible
   STATUS     mandatory
   DESCRIPTION
     "An entry in the exampleHexProvFreeHexReplicated1Table."
   INDEX {
      exampleIndex,
      exampleHexIndex,
      exampleHexProvFreeHexReplicated1Index }
::= { exampleHexProvFreeHexReplicated1Table 1 }

ExampleHexProvFreeHexReplicated1Entry ::= SEQUENCE {
   exampleHexProvFreeHexReplicated1Index
      Integer32,
   exampleHexProvFreeHexReplicated1Value
      Hex,
   exampleHexProvFreeHexReplicated1RowStatus
      RowStatus }

exampleHexProvFreeHexReplicated1Index OBJECT-TYPE
   SYNTAX     Integer32 (0..3 | 5..9)
   ACCESS     not-accessible
   STATUS     mandatory
   DESCRIPTION
     "This variable represents the index for the exampleHexProvFreeHexReplicated1Table."
::= { exampleHexProvFreeHexReplicated1Entry 1 }

exampleHexProvFreeHexReplicated1Value OBJECT-TYPE
   SYNTAX     Hex (0..32 | 80..256)
   ACCESS     read-write
   STATUS     mandatory
   DESCRIPTION
     "This variable represents an individual value for the
      exampleHexProvFreeHexReplicated1Table."
::= { exampleHexProvFreeHexReplicated1Entry 2 }

exampleHexProvFreeHexReplicated1RowStatus OBJECT-TYPE
   SYNTAX     RowStatus 
   ACCESS     write-only
   STATUS     mandatory
   DESCRIPTION
     "This variable is used to control the addition and deletion 
      of individual values of the exampleHexProvFreeHexReplicated1Table."
::= { exampleHexProvFreeHexReplicated1Entry 3 }

exampleHexProvFreeHexListTable OBJECT-TYPE
   SYNTAX     SEQUENCE OF ExampleHexProvFreeHexListEntry
   ACCESS     not-accessible
   STATUS     mandatory
   DESCRIPTION
     ""
::= { exampleHex 1056 }

exampleHexProvFreeHexListEntry OBJECT-TYPE
   SYNTAX     ExampleHexProvFreeHexListEntry
   ACCESS     not-accessible
   STATUS     mandatory
   DESCRIPTION
     "An entry in the exampleHexProvFreeHexListTable."
   INDEX {
      exampleIndex,
      exampleHexIndex,
      exampleHexProvFreeHexListValue }
::= { exampleHexProvFreeHexListTable 1 }

ExampleHexProvFreeHexListEntry ::= SEQUENCE {
   exampleHexProvFreeHexListValue
      Integer32,
   exampleHexProvFreeHexListRowStatus
      RowStatus }

exampleHexProvFreeHexListValue OBJECT-TYPE
   SYNTAX     Integer32 (1..4096)
   ACCESS     read-write
   STATUS     mandatory
   DESCRIPTION
     "This variable represents both the value and the index for the
      exampleHexProvFreeHexListTable."
::= { exampleHexProvFreeHexListEntry 1 }

exampleHexProvFreeHexListRowStatus OBJECT-TYPE
   SYNTAX     RowStatus 
   ACCESS     write-only
   STATUS     mandatory
   DESCRIPTION
     "This variable is used to control the addition and deletion 
      of individual values of the exampleHexProvFreeHexListTable."
::= { exampleHexProvFreeHexListEntry 2 }

exampleHexProvFreeHexList1Table OBJECT-TYPE
   SYNTAX     SEQUENCE OF ExampleHexProvFreeHexList1Entry
   ACCESS     not-accessible
   STATUS     mandatory
   DESCRIPTION
     ""
::= { exampleHex 1057 }

exampleHexProvFreeHexList1Entry OBJECT-TYPE
   SYNTAX     ExampleHexProvFreeHexList1Entry
   ACCESS     not-accessible
   STATUS     mandatory
   DESCRIPTION
     "An entry in the exampleHexProvFreeHexList1Table."
   INDEX {
      exampleIndex,
      exampleHexIndex,
      exampleHexProvFreeHexList1Value }
::= { exampleHexProvFreeHexList1Table 1 }

ExampleHexProvFreeHexList1Entry ::= SEQUENCE {
   exampleHexProvFreeHexList1Value
      Integer32,
   exampleHexProvFreeHexList1RowStatus
      RowStatus }

exampleHexProvFreeHexList1Value OBJECT-TYPE
   SYNTAX     Integer32 (1..4096)
   ACCESS     read-write
   STATUS     mandatory
   DESCRIPTION
     "This variable represents both the value and the index for the
      exampleHexProvFreeHexList1Table."
::= { exampleHexProvFreeHexList1Entry 1 }

exampleHexProvFreeHexList1RowStatus OBJECT-TYPE
   SYNTAX     RowStatus 
   ACCESS     write-only
   STATUS     mandatory
   DESCRIPTION
     "This variable is used to control the addition and deletion 
      of individual values of the exampleHexProvFreeHexList1Table."
::= { exampleHexProvFreeHexList1Entry 2 }



exampleIpAddress OBJECT IDENTIFIER ::= { example 4 }



exampleIpAddressRowStatusTable OBJECT-TYPE
   SYNTAX     SEQUENCE OF ExampleIpAddressRowStatusEntry
   ACCESS     not-accessible
   STATUS     mandatory
   DESCRIPTION
     "This entry controls the addition and deletion of 
      exampleIpAddress components."
::= { exampleIpAddress 1 }

exampleIpAddressRowStatusEntry OBJECT-TYPE
   SYNTAX     ExampleIpAddressRowStatusEntry
   ACCESS     not-accessible
   STATUS     mandatory
   DESCRIPTION
     "A single entry in the table represents a single 
      exampleIpAddress component."
   INDEX {
      exampleIndex,
      exampleIpAddressIndex }
::= { exampleIpAddressRowStatusTable 1 }

ExampleIpAddressRowStatusEntry ::= SEQUENCE {
   exampleIpAddressRowStatus
      RowStatus,
   exampleIpAddressComponentName
      DisplayString,
   exampleIpAddressStorageType
      StorageType,
   exampleIpAddressIndex
      IpAddress }

exampleIpAddressRowStatus OBJECT-TYPE
   SYNTAX     RowStatus 
   ACCESS     read-write
   STATUS     mandatory
   DESCRIPTION
     "This variable is used as the basis for SNMP naming of
      exampleIpAddress components.
      These components can be added and deleted."
::= { exampleIpAddressRowStatusEntry 1 }

exampleIpAddressComponentName OBJECT-TYPE
   SYNTAX     DisplayString 
   ACCESS     read-only
   STATUS     mandatory
   DESCRIPTION
     "This variable provides the component's string name for
      use with the ASCII Console Interface"
::= { exampleIpAddressRowStatusEntry 2 }

exampleIpAddressStorageType OBJECT-TYPE
   SYNTAX     StorageType 
   ACCESS     read-only
   STATUS     mandatory
   DESCRIPTION
     "This variable represents the storage type value for the
      exampleIpAddress tables."
::= { exampleIpAddressRowStatusEntry 4 }

exampleIpAddressIndex OBJECT-TYPE
   SYNTAX     IpAddress 
   ACCESS     not-accessible
   STATUS     mandatory
   DESCRIPTION
     "This variable represents the index for the exampleIpAddress tables."
::= { exampleIpAddressRowStatusEntry 10 }

exampleIpAddressOperationalTable OBJECT-TYPE
   SYNTAX     SEQUENCE OF ExampleIpAddressOperationalEntry
   ACCESS     not-accessible
   STATUS     mandatory
   DESCRIPTION
     ""
::= { exampleIpAddress 10 }

exampleIpAddressOperationalEntry OBJECT-TYPE
   SYNTAX     ExampleIpAddressOperationalEntry
   ACCESS     not-accessible
   STATUS     mandatory
   DESCRIPTION
     "An entry in the exampleIpAddressOperationalTable."
   INDEX {
      exampleIndex,
      exampleIpAddressIndex }
::= { exampleIpAddressOperationalTable 1 }

ExampleIpAddressOperationalEntry ::= SEQUENCE {
   exampleIpAddressOperStructIpAddress
      IpAddress,
   exampleIpAddressOperFreeIpAddress
      IpAddress }

exampleIpAddressOperStructIpAddress OBJECT-TYPE
   SYNTAX     IpAddress 
   ACCESS     read-write
   STATUS     mandatory
   DESCRIPTION
     ""
::= { exampleIpAddressOperationalEntry 1 }

exampleIpAddressOperFreeIpAddress OBJECT-TYPE
   SYNTAX     IpAddress 
   ACCESS     read-write
   STATUS     mandatory
   DESCRIPTION
     ""
::= { exampleIpAddressOperationalEntry 2 }

exampleIpAddressProvisionalTable OBJECT-TYPE
   SYNTAX     SEQUENCE OF ExampleIpAddressProvisionalEntry
   ACCESS     not-accessible
   STATUS     mandatory
   DESCRIPTION
     ""
::= { exampleIpAddress 11 }

exampleIpAddressProvisionalEntry OBJECT-TYPE
   SYNTAX     ExampleIpAddressProvisionalEntry
   ACCESS     not-accessible
   STATUS     mandatory
   DESCRIPTION
     "An entry in the exampleIpAddressProvisionalTable."
   INDEX {
      exampleIndex,
      exampleIpAddressIndex }
::= { exampleIpAddressProvisionalTable 1 }

ExampleIpAddressProvisionalEntry ::= SEQUENCE {
   exampleIpAddressProvEnumSub
      Link,
   exampleIpAddressProvStructIpAddress
      IpAddress,
   exampleIpAddressProvFreeIpAddress
      IpAddress,
   exampleIpAddressProvFreeIpAddress1
      IpAddress }

exampleIpAddressProvEnumSub OBJECT-TYPE
   SYNTAX     Link 
   ACCESS     read-write
   STATUS     mandatory
   DESCRIPTION
     ""
::= { exampleIpAddressProvisionalEntry 1 }

exampleIpAddressProvStructIpAddress OBJECT-TYPE
   SYNTAX     IpAddress 
   ACCESS     read-write
   STATUS     mandatory
   DESCRIPTION
     ""
   DEFVAL     { '7f000100'H }  -- "127.0.1.0"
::= { exampleIpAddressProvisionalEntry 2 }

exampleIpAddressProvFreeIpAddress OBJECT-TYPE
   SYNTAX     IpAddress 
   ACCESS     read-write
   STATUS     mandatory
   DESCRIPTION
     ""
   DEFVAL     { '7f7f7f7f'H }  -- "127.127.127.127"
::= { exampleIpAddressProvisionalEntry 3 }

exampleIpAddressProvFreeIpAddress1 OBJECT-TYPE
   SYNTAX     IpAddress 
   ACCESS     read-write
   STATUS     mandatory
   DESCRIPTION
     ""
::= { exampleIpAddressProvisionalEntry 4 }

exampleIpAddressOperStructIpAddressVectorTable OBJECT-TYPE
   SYNTAX     SEQUENCE OF ExampleIpAddressOperStructIpAddressVectorEntry
   ACCESS     not-accessible
   STATUS     mandatory
   DESCRIPTION
     ""
::= { exampleIpAddress 1058 }

exampleIpAddressOperStructIpAddressVectorEntry OBJECT-TYPE
   SYNTAX     ExampleIpAddressOperStructIpAddressVectorEntry
   ACCESS     not-accessible
   STATUS     mandatory
   DESCRIPTION
     "An entry in the exampleIpAddressOperStructIpAddressVectorTable."
   INDEX {
      exampleIndex,
      exampleIpAddressIndex,
      exampleIpAddressOperStructIpAddressVectorIndex }
::= { exampleIpAddressOperStructIpAddressVectorTable 1 }

ExampleIpAddressOperStructIpAddressVectorEntry ::= SEQUENCE {
   exampleIpAddressOperStructIpAddressVectorIndex
      Integer32,
   exampleIpAddressOperStructIpAddressVectorValue
      IpAddress }

exampleIpAddressOperStructIpAddressVectorIndex OBJECT-TYPE
   SYNTAX     Integer32 (0..9)
   ACCESS     not-accessible
   STATUS     mandatory
   DESCRIPTION
     "This variable represents the exampleIpAddressOperStructIpAddressVectorTable
      specific index for the exampleIpAddressOperStructIpAddressVectorTable."
::= { exampleIpAddressOperStructIpAddressVectorEntry 1 }

exampleIpAddressOperStructIpAddressVectorValue OBJECT-TYPE
   SYNTAX     IpAddress 
   ACCESS     read-write
   STATUS     mandatory
   DESCRIPTION
     "This variable represents an individual value for the
      exampleIpAddressOperStructIpAddressVectorTable."
::= { exampleIpAddressOperStructIpAddressVectorEntry 2 }

exampleIpAddressOperStructIpAddressArrayTable OBJECT-TYPE
   SYNTAX     SEQUENCE OF ExampleIpAddressOperStructIpAddressArrayEntry
   ACCESS     not-accessible
   STATUS     mandatory
   DESCRIPTION
     ""
::= { exampleIpAddress 1059 }

exampleIpAddressOperStructIpAddressArrayEntry OBJECT-TYPE
   SYNTAX     ExampleIpAddressOperStructIpAddressArrayEntry
   ACCESS     not-accessible
   STATUS     mandatory
   DESCRIPTION
     "An entry in the exampleIpAddressOperStructIpAddressArrayTable."
   INDEX {
      exampleIndex,
      exampleIpAddressIndex,
      exampleIpAddressOperStructIpAddressArrayRowIndex,
      exampleIpAddressOperStructIpAddressArrayColumnIndex }
::= { exampleIpAddressOperStructIpAddressArrayTable 1 }

ExampleIpAddressOperStructIpAddressArrayEntry ::= SEQUENCE {
   exampleIpAddressOperStructIpAddressArrayRowIndex
      Integer32,
   exampleIpAddressOperStructIpAddressArrayColumnIndex
      Integer32,
   exampleIpAddressOperStructIpAddressArrayValue
      IpAddress }

exampleIpAddressOperStructIpAddressArrayRowIndex OBJECT-TYPE
   SYNTAX     Integer32 (0..2)
   ACCESS     not-accessible
   STATUS     mandatory
   DESCRIPTION
     "This variable represents the next to last index for the 
      exampleIpAddressOperStructIpAddressArrayTable."
::= { exampleIpAddressOperStructIpAddressArrayEntry 1 }

exampleIpAddressOperStructIpAddressArrayColumnIndex OBJECT-TYPE
   SYNTAX     Integer32 (0..3)
   ACCESS     not-accessible
   STATUS     mandatory
   DESCRIPTION
     "This variable represents the final index for the 
      exampleIpAddressOperStructIpAddressArrayTable."
::= { exampleIpAddressOperStructIpAddressArrayEntry 2 }

exampleIpAddressOperStructIpAddressArrayValue OBJECT-TYPE
   SYNTAX     IpAddress 
   ACCESS     read-write
   STATUS     mandatory
   DESCRIPTION
     "This variable represents an individual value for the
      exampleIpAddressOperStructIpAddressArrayTable."
::= { exampleIpAddressOperStructIpAddressArrayEntry 3 }

exampleIpAddressOperFreeIpAddressVectorTable OBJECT-TYPE
   SYNTAX     SEQUENCE OF ExampleIpAddressOperFreeIpAddressVectorEntry
   ACCESS     not-accessible
   STATUS     mandatory
   DESCRIPTION
     ""
::= { exampleIpAddress 1060 }

exampleIpAddressOperFreeIpAddressVectorEntry OBJECT-TYPE
   SYNTAX     ExampleIpAddressOperFreeIpAddressVectorEntry
   ACCESS     not-accessible
   STATUS     mandatory
   DESCRIPTION
     "An entry in the exampleIpAddressOperFreeIpAddressVectorTable."
   INDEX {
      exampleIndex,
      exampleIpAddressIndex,
      exampleIpAddressOperFreeIpAddressVectorIndex }
::= { exampleIpAddressOperFreeIpAddressVectorTable 1 }

ExampleIpAddressOperFreeIpAddressVectorEntry ::= SEQUENCE {
   exampleIpAddressOperFreeIpAddressVectorIndex
      Integer32,
   exampleIpAddressOperFreeIpAddressVectorValue
      IpAddress }

exampleIpAddressOperFreeIpAddressVectorIndex OBJECT-TYPE
   SYNTAX     Integer32 (0..9)
   ACCESS     not-accessible
   STATUS     mandatory
   DESCRIPTION
     "This variable represents the exampleIpAddressOperFreeIpAddressVectorTable
      specific index for the exampleIpAddressOperFreeIpAddressVectorTable."
::= { exampleIpAddressOperFreeIpAddressVectorEntry 1 }

exampleIpAddressOperFreeIpAddressVectorValue OBJECT-TYPE
   SYNTAX     IpAddress 
   ACCESS     read-write
   STATUS     mandatory
   DESCRIPTION
     "This variable represents an individual value for the
      exampleIpAddressOperFreeIpAddressVectorTable."
::= { exampleIpAddressOperFreeIpAddressVectorEntry 2 }

exampleIpAddressOperFreeIpAddressArrayTable OBJECT-TYPE
   SYNTAX     SEQUENCE OF ExampleIpAddressOperFreeIpAddressArrayEntry
   ACCESS     not-accessible
   STATUS     mandatory
   DESCRIPTION
     ""
::= { exampleIpAddress 1061 }

exampleIpAddressOperFreeIpAddressArrayEntry OBJECT-TYPE
   SYNTAX     ExampleIpAddressOperFreeIpAddressArrayEntry
   ACCESS     not-accessible
   STATUS     mandatory
   DESCRIPTION
     "An entry in the exampleIpAddressOperFreeIpAddressArrayTable."
   INDEX {
      exampleIndex,
      exampleIpAddressIndex,
      exampleIpAddressOperFreeIpAddressArrayRowIndex,
      exampleIpAddressOperFreeIpAddressArrayColumnIndex }
::= { exampleIpAddressOperFreeIpAddressArrayTable 1 }

ExampleIpAddressOperFreeIpAddressArrayEntry ::= SEQUENCE {
   exampleIpAddressOperFreeIpAddressArrayRowIndex
      Integer32,
   exampleIpAddressOperFreeIpAddressArrayColumnIndex
      Integer32,
   exampleIpAddressOperFreeIpAddressArrayValue
      IpAddress }

exampleIpAddressOperFreeIpAddressArrayRowIndex OBJECT-TYPE
   SYNTAX     Integer32 (0..2)
   ACCESS     not-accessible
   STATUS     mandatory
   DESCRIPTION
     "This variable represents the next to last index for the 
      exampleIpAddressOperFreeIpAddressArrayTable."
::= { exampleIpAddressOperFreeIpAddressArrayEntry 1 }

exampleIpAddressOperFreeIpAddressArrayColumnIndex OBJECT-TYPE
   SYNTAX     Integer32 (0..3)
   ACCESS     not-accessible
   STATUS     mandatory
   DESCRIPTION
     "This variable represents the final index for the 
      exampleIpAddressOperFreeIpAddressArrayTable."
::= { exampleIpAddressOperFreeIpAddressArrayEntry 2 }

exampleIpAddressOperFreeIpAddressArrayValue OBJECT-TYPE
   SYNTAX     IpAddress 
   ACCESS     read-write
   STATUS     mandatory
   DESCRIPTION
     "This variable represents an individual value for the
      exampleIpAddressOperFreeIpAddressArrayTable."
::= { exampleIpAddressOperFreeIpAddressArrayEntry 3 }

exampleIpAddressOperFreeIpAddressReplicatedTable OBJECT-TYPE
   SYNTAX     SEQUENCE OF ExampleIpAddressOperFreeIpAddressReplicatedEntry
   ACCESS     not-accessible
   STATUS     mandatory
   DESCRIPTION
     ""
::= { exampleIpAddress 1062 }

exampleIpAddressOperFreeIpAddressReplicatedEntry OBJECT-TYPE
   SYNTAX     ExampleIpAddressOperFreeIpAddressReplicatedEntry
   ACCESS     not-accessible
   STATUS     mandatory
   DESCRIPTION
     "An entry in the exampleIpAddressOperFreeIpAddressReplicatedTable."
   INDEX {
      exampleIndex,
      exampleIpAddressIndex,
      exampleIpAddressOperFreeIpAddressReplicatedIndex }
::= { exampleIpAddressOperFreeIpAddressReplicatedTable 1 }

ExampleIpAddressOperFreeIpAddressReplicatedEntry ::= SEQUENCE {
   exampleIpAddressOperFreeIpAddressReplicatedIndex
      IpAddress,
   exampleIpAddressOperFreeIpAddressReplicatedValue
      IpAddress,
   exampleIpAddressOperFreeIpAddressReplicatedRowStatus
      RowStatus }

exampleIpAddressOperFreeIpAddressReplicatedIndex OBJECT-TYPE
   SYNTAX     IpAddress 
   ACCESS     not-accessible
   STATUS     mandatory
   DESCRIPTION
     "This variable represents the index for the exampleIpAddressOperFreeIpAddressReplicatedTable."
::= { exampleIpAddressOperFreeIpAddressReplicatedEntry 1 }

exampleIpAddressOperFreeIpAddressReplicatedValue OBJECT-TYPE
   SYNTAX     IpAddress 
   ACCESS     read-write
   STATUS     mandatory
   DESCRIPTION
     "This variable represents an individual value for the
      exampleIpAddressOperFreeIpAddressReplicatedTable."
::= { exampleIpAddressOperFreeIpAddressReplicatedEntry 2 }

exampleIpAddressOperFreeIpAddressReplicatedRowStatus OBJECT-TYPE
   SYNTAX     RowStatus 
   ACCESS     write-only
   STATUS     mandatory
   DESCRIPTION
     "This variable is used to control the addition and deletion 
      of individual values of the exampleIpAddressOperFreeIpAddressReplicatedTable."
::= { exampleIpAddressOperFreeIpAddressReplicatedEntry 3 }

exampleIpAddressOperFreeIpAddressListTable OBJECT-TYPE
   SYNTAX     SEQUENCE OF ExampleIpAddressOperFreeIpAddressListEntry
   ACCESS     not-accessible
   STATUS     mandatory
   DESCRIPTION
     ""
::= { exampleIpAddress 1063 }

exampleIpAddressOperFreeIpAddressListEntry OBJECT-TYPE
   SYNTAX     ExampleIpAddressOperFreeIpAddressListEntry
   ACCESS     not-accessible
   STATUS     mandatory
   DESCRIPTION
     "An entry in the exampleIpAddressOperFreeIpAddressListTable."
   INDEX {
      exampleIndex,
      exampleIpAddressIndex,
      exampleIpAddressOperFreeIpAddressListValue }
::= { exampleIpAddressOperFreeIpAddressListTable 1 }

ExampleIpAddressOperFreeIpAddressListEntry ::= SEQUENCE {
   exampleIpAddressOperFreeIpAddressListValue
      IpAddress,
   exampleIpAddressOperFreeIpAddressListRowStatus
      RowStatus }

exampleIpAddressOperFreeIpAddressListValue OBJECT-TYPE
   SYNTAX     IpAddress 
   ACCESS     read-write
   STATUS     mandatory
   DESCRIPTION
     "This variable represents both the value and the index for the
      exampleIpAddressOperFreeIpAddressListTable."
::= { exampleIpAddressOperFreeIpAddressListEntry 1 }

exampleIpAddressOperFreeIpAddressListRowStatus OBJECT-TYPE
   SYNTAX     RowStatus 
   ACCESS     write-only
   STATUS     mandatory
   DESCRIPTION
     "This variable is used to control the addition and deletion 
      of individual values of the exampleIpAddressOperFreeIpAddressListTable."
::= { exampleIpAddressOperFreeIpAddressListEntry 2 }

exampleIpAddressProvStructIpAddressVectorTable OBJECT-TYPE
   SYNTAX     SEQUENCE OF ExampleIpAddressProvStructIpAddressVectorEntry
   ACCESS     not-accessible
   STATUS     mandatory
   DESCRIPTION
     ""
::= { exampleIpAddress 1064 }

exampleIpAddressProvStructIpAddressVectorEntry OBJECT-TYPE
   SYNTAX     ExampleIpAddressProvStructIpAddressVectorEntry
   ACCESS     not-accessible
   STATUS     mandatory
   DESCRIPTION
     "An entry in the exampleIpAddressProvStructIpAddressVectorTable."
   INDEX {
      exampleIndex,
      exampleIpAddressIndex,
      exampleIpAddressProvStructIpAddressVectorIndex }
::= { exampleIpAddressProvStructIpAddressVectorTable 1 }

ExampleIpAddressProvStructIpAddressVectorEntry ::= SEQUENCE {
   exampleIpAddressProvStructIpAddressVectorIndex
      Integer32,
   exampleIpAddressProvStructIpAddressVectorValue
      IpAddress }

exampleIpAddressProvStructIpAddressVectorIndex OBJECT-TYPE
   SYNTAX     Integer32 (0..9)
   ACCESS     not-accessible
   STATUS     mandatory
   DESCRIPTION
     "This variable represents the exampleIpAddressProvStructIpAddressVectorTable
      specific index for the exampleIpAddressProvStructIpAddressVectorTable."
::= { exampleIpAddressProvStructIpAddressVectorEntry 1 }

exampleIpAddressProvStructIpAddressVectorValue OBJECT-TYPE
   SYNTAX     IpAddress 
   ACCESS     read-write
   STATUS     mandatory
   DESCRIPTION
     "This variable represents an individual value for the
      exampleIpAddressProvStructIpAddressVectorTable."
::= { exampleIpAddressProvStructIpAddressVectorEntry 2 }

exampleIpAddressProvStructIpAddressArrayTable OBJECT-TYPE
   SYNTAX     SEQUENCE OF ExampleIpAddressProvStructIpAddressArrayEntry
   ACCESS     not-accessible
   STATUS     mandatory
   DESCRIPTION
     ""
::= { exampleIpAddress 1065 }

exampleIpAddressProvStructIpAddressArrayEntry OBJECT-TYPE
   SYNTAX     ExampleIpAddressProvStructIpAddressArrayEntry
   ACCESS     not-accessible
   STATUS     mandatory
   DESCRIPTION
     "An entry in the exampleIpAddressProvStructIpAddressArrayTable."
   INDEX {
      exampleIndex,
      exampleIpAddressIndex,
      exampleIpAddressProvStructIpAddressArrayRowIndex,
      exampleIpAddressProvStructIpAddressArrayColumnIndex }
::= { exampleIpAddressProvStructIpAddressArrayTable 1 }

ExampleIpAddressProvStructIpAddressArrayEntry ::= SEQUENCE {
   exampleIpAddressProvStructIpAddressArrayRowIndex
      Integer32,
   exampleIpAddressProvStructIpAddressArrayColumnIndex
      Integer32,
   exampleIpAddressProvStructIpAddressArrayValue
      IpAddress }

exampleIpAddressProvStructIpAddressArrayRowIndex OBJECT-TYPE
   SYNTAX     Integer32 (0..2)
   ACCESS     not-accessible
   STATUS     mandatory
   DESCRIPTION
     "This variable represents the next to last index for the 
      exampleIpAddressProvStructIpAddressArrayTable."
::= { exampleIpAddressProvStructIpAddressArrayEntry 1 }

exampleIpAddressProvStructIpAddressArrayColumnIndex OBJECT-TYPE
   SYNTAX     Integer32 (0..3)
   ACCESS     not-accessible
   STATUS     mandatory
   DESCRIPTION
     "This variable represents the final index for the 
      exampleIpAddressProvStructIpAddressArrayTable."
::= { exampleIpAddressProvStructIpAddressArrayEntry 2 }

exampleIpAddressProvStructIpAddressArrayValue OBJECT-TYPE
   SYNTAX     IpAddress 
   ACCESS     read-write
   STATUS     mandatory
   DESCRIPTION
     "This variable represents an individual value for the
      exampleIpAddressProvStructIpAddressArrayTable."
::= { exampleIpAddressProvStructIpAddressArrayEntry 3 }

exampleIpAddressProvFreeIpAddressVectorTable OBJECT-TYPE
   SYNTAX     SEQUENCE OF ExampleIpAddressProvFreeIpAddressVectorEntry
   ACCESS     not-accessible
   STATUS     mandatory
   DESCRIPTION
     ""
::= { exampleIpAddress 1066 }

exampleIpAddressProvFreeIpAddressVectorEntry OBJECT-TYPE
   SYNTAX     ExampleIpAddressProvFreeIpAddressVectorEntry
   ACCESS     not-accessible
   STATUS     mandatory
   DESCRIPTION
     "An entry in the exampleIpAddressProvFreeIpAddressVectorTable."
   INDEX {
      exampleIndex,
      exampleIpAddressIndex,
      exampleIpAddressProvFreeIpAddressVectorIndex }
::= { exampleIpAddressProvFreeIpAddressVectorTable 1 }

ExampleIpAddressProvFreeIpAddressVectorEntry ::= SEQUENCE {
   exampleIpAddressProvFreeIpAddressVectorIndex
      Integer32,
   exampleIpAddressProvFreeIpAddressVectorValue
      IpAddress }

exampleIpAddressProvFreeIpAddressVectorIndex OBJECT-TYPE
   SYNTAX     Integer32 (0..9)
   ACCESS     not-accessible
   STATUS     mandatory
   DESCRIPTION
     "This variable represents the exampleIpAddressProvFreeIpAddressVectorTable
      specific index for the exampleIpAddressProvFreeIpAddressVectorTable."
::= { exampleIpAddressProvFreeIpAddressVectorEntry 1 }

exampleIpAddressProvFreeIpAddressVectorValue OBJECT-TYPE
   SYNTAX     IpAddress 
   ACCESS     read-write
   STATUS     mandatory
   DESCRIPTION
     "This variable represents an individual value for the
      exampleIpAddressProvFreeIpAddressVectorTable."
::= { exampleIpAddressProvFreeIpAddressVectorEntry 2 }

exampleIpAddressProvFreeIpAddressVector1Table OBJECT-TYPE
   SYNTAX     SEQUENCE OF ExampleIpAddressProvFreeIpAddressVector1Entry
   ACCESS     not-accessible
   STATUS     mandatory
   DESCRIPTION
     ""
::= { exampleIpAddress 1067 }

exampleIpAddressProvFreeIpAddressVector1Entry OBJECT-TYPE
   SYNTAX     ExampleIpAddressProvFreeIpAddressVector1Entry
   ACCESS     not-accessible
   STATUS     mandatory
   DESCRIPTION
     "An entry in the exampleIpAddressProvFreeIpAddressVector1Table."
   INDEX {
      exampleIndex,
      exampleIpAddressIndex,
      exampleIpAddressProvFreeIpAddressVector1Index }
::= { exampleIpAddressProvFreeIpAddressVector1Table 1 }

ExampleIpAddressProvFreeIpAddressVector1Entry ::= SEQUENCE {
   exampleIpAddressProvFreeIpAddressVector1Index
      Integer32,
   exampleIpAddressProvFreeIpAddressVector1Value
      IpAddress }

exampleIpAddressProvFreeIpAddressVector1Index OBJECT-TYPE
   SYNTAX     Integer32 (0..3)
   ACCESS     not-accessible
   STATUS     mandatory
   DESCRIPTION
     "This variable represents the exampleIpAddressProvFreeIpAddressVector1Table
      specific index for the exampleIpAddressProvFreeIpAddressVector1Table."
::= { exampleIpAddressProvFreeIpAddressVector1Entry 1 }

exampleIpAddressProvFreeIpAddressVector1Value OBJECT-TYPE
   SYNTAX     IpAddress 
   ACCESS     read-write
   STATUS     mandatory
   DESCRIPTION
     "This variable represents an individual value for the
      exampleIpAddressProvFreeIpAddressVector1Table."
::= { exampleIpAddressProvFreeIpAddressVector1Entry 2 }

exampleIpAddressProvFreeIpAddressArrayTable OBJECT-TYPE
   SYNTAX     SEQUENCE OF ExampleIpAddressProvFreeIpAddressArrayEntry
   ACCESS     not-accessible
   STATUS     mandatory
   DESCRIPTION
     ""
::= { exampleIpAddress 1068 }

exampleIpAddressProvFreeIpAddressArrayEntry OBJECT-TYPE
   SYNTAX     ExampleIpAddressProvFreeIpAddressArrayEntry
   ACCESS     not-accessible
   STATUS     mandatory
   DESCRIPTION
     "An entry in the exampleIpAddressProvFreeIpAddressArrayTable."
   INDEX {
      exampleIndex,
      exampleIpAddressIndex,
      exampleIpAddressProvFreeIpAddressArrayRowIndex,
      exampleIpAddressProvFreeIpAddressArrayColumnIndex }
::= { exampleIpAddressProvFreeIpAddressArrayTable 1 }

ExampleIpAddressProvFreeIpAddressArrayEntry ::= SEQUENCE {
   exampleIpAddressProvFreeIpAddressArrayRowIndex
      Integer32,
   exampleIpAddressProvFreeIpAddressArrayColumnIndex
      Integer32,
   exampleIpAddressProvFreeIpAddressArrayValue
      IpAddress }

exampleIpAddressProvFreeIpAddressArrayRowIndex OBJECT-TYPE
   SYNTAX     Integer32 (0..2)
   ACCESS     not-accessible
   STATUS     mandatory
   DESCRIPTION
     "This variable represents the next to last index for the 
      exampleIpAddressProvFreeIpAddressArrayTable."
::= { exampleIpAddressProvFreeIpAddressArrayEntry 1 }

exampleIpAddressProvFreeIpAddressArrayColumnIndex OBJECT-TYPE
   SYNTAX     Integer32 (0..3)
   ACCESS     not-accessible
   STATUS     mandatory
   DESCRIPTION
     "This variable represents the final index for the 
      exampleIpAddressProvFreeIpAddressArrayTable."
::= { exampleIpAddressProvFreeIpAddressArrayEntry 2 }

exampleIpAddressProvFreeIpAddressArrayValue OBJECT-TYPE
   SYNTAX     IpAddress 
   ACCESS     read-write
   STATUS     mandatory
   DESCRIPTION
     "This variable represents an individual value for the
      exampleIpAddressProvFreeIpAddressArrayTable."
::= { exampleIpAddressProvFreeIpAddressArrayEntry 3 }

exampleIpAddressProvFreeIpAddressArray1Table OBJECT-TYPE
   SYNTAX     SEQUENCE OF ExampleIpAddressProvFreeIpAddressArray1Entry
   ACCESS     not-accessible
   STATUS     mandatory
   DESCRIPTION
     ""
::= { exampleIpAddress 1069 }

exampleIpAddressProvFreeIpAddressArray1Entry OBJECT-TYPE
   SYNTAX     ExampleIpAddressProvFreeIpAddressArray1Entry
   ACCESS     not-accessible
   STATUS     mandatory
   DESCRIPTION
     "An entry in the exampleIpAddressProvFreeIpAddressArray1Table."
   INDEX {
      exampleIndex,
      exampleIpAddressIndex,
      exampleIpAddressProvFreeIpAddressArray1RowIndex,
      exampleIpAddressProvFreeIpAddressArray1ColumnIndex }
::= { exampleIpAddressProvFreeIpAddressArray1Table 1 }

ExampleIpAddressProvFreeIpAddressArray1Entry ::= SEQUENCE {
   exampleIpAddressProvFreeIpAddressArray1RowIndex
      Integer32,
   exampleIpAddressProvFreeIpAddressArray1ColumnIndex
      Integer32,
   exampleIpAddressProvFreeIpAddressArray1Value
      IpAddress }

exampleIpAddressProvFreeIpAddressArray1RowIndex OBJECT-TYPE
   SYNTAX     Integer32 (0..3)
   ACCESS     not-accessible
   STATUS     mandatory
   DESCRIPTION
     "This variable represents the next to last index for the 
      exampleIpAddressProvFreeIpAddressArray1Table."
::= { exampleIpAddressProvFreeIpAddressArray1Entry 1 }

exampleIpAddressProvFreeIpAddressArray1ColumnIndex OBJECT-TYPE
   SYNTAX     Integer32 (0..3)
   ACCESS     not-accessible
   STATUS     mandatory
   DESCRIPTION
     "This variable represents the final index for the 
      exampleIpAddressProvFreeIpAddressArray1Table."
::= { exampleIpAddressProvFreeIpAddressArray1Entry 2 }

exampleIpAddressProvFreeIpAddressArray1Value OBJECT-TYPE
   SYNTAX     IpAddress 
   ACCESS     read-write
   STATUS     mandatory
   DESCRIPTION
     "This variable represents an individual value for the
      exampleIpAddressProvFreeIpAddressArray1Table."
::= { exampleIpAddressProvFreeIpAddressArray1Entry 3 }

exampleIpAddressProvFreeIpAddressReplicatedTable OBJECT-TYPE
   SYNTAX     SEQUENCE OF ExampleIpAddressProvFreeIpAddressReplicatedEntry
   ACCESS     not-accessible
   STATUS     mandatory
   DESCRIPTION
     ""
::= { exampleIpAddress 1070 }

exampleIpAddressProvFreeIpAddressReplicatedEntry OBJECT-TYPE
   SYNTAX     ExampleIpAddressProvFreeIpAddressReplicatedEntry
   ACCESS     not-accessible
   STATUS     mandatory
   DESCRIPTION
     "An entry in the exampleIpAddressProvFreeIpAddressReplicatedTable."
   INDEX {
      exampleIndex,
      exampleIpAddressIndex,
      exampleIpAddressProvFreeIpAddressReplicatedIndex }
::= { exampleIpAddressProvFreeIpAddressReplicatedTable 1 }

ExampleIpAddressProvFreeIpAddressReplicatedEntry ::= SEQUENCE {
   exampleIpAddressProvFreeIpAddressReplicatedIndex
      IpAddress,
   exampleIpAddressProvFreeIpAddressReplicatedValue
      IpAddress,
   exampleIpAddressProvFreeIpAddressReplicatedRowStatus
      RowStatus }

exampleIpAddressProvFreeIpAddressReplicatedIndex OBJECT-TYPE
   SYNTAX     IpAddress 
   ACCESS     not-accessible
   STATUS     mandatory
   DESCRIPTION
     "This variable represents the index for the exampleIpAddressProvFreeIpAddressReplicatedTable."
::= { exampleIpAddressProvFreeIpAddressReplicatedEntry 1 }

exampleIpAddressProvFreeIpAddressReplicatedValue OBJECT-TYPE
   SYNTAX     IpAddress 
   ACCESS     read-write
   STATUS     mandatory
   DESCRIPTION
     "This variable represents an individual value for the
      exampleIpAddressProvFreeIpAddressReplicatedTable."
::= { exampleIpAddressProvFreeIpAddressReplicatedEntry 2 }

exampleIpAddressProvFreeIpAddressReplicatedRowStatus OBJECT-TYPE
   SYNTAX     RowStatus 
   ACCESS     write-only
   STATUS     mandatory
   DESCRIPTION
     "This variable is used to control the addition and deletion 
      of individual values of the exampleIpAddressProvFreeIpAddressReplicatedTable."
::= { exampleIpAddressProvFreeIpAddressReplicatedEntry 3 }

exampleIpAddressProvFreeIpAddressListTable OBJECT-TYPE
   SYNTAX     SEQUENCE OF ExampleIpAddressProvFreeIpAddressListEntry
   ACCESS     not-accessible
   STATUS     mandatory
   DESCRIPTION
     ""
::= { exampleIpAddress 1071 }

exampleIpAddressProvFreeIpAddressListEntry OBJECT-TYPE
   SYNTAX     ExampleIpAddressProvFreeIpAddressListEntry
   ACCESS     not-accessible
   STATUS     mandatory
   DESCRIPTION
     "An entry in the exampleIpAddressProvFreeIpAddressListTable."
   INDEX {
      exampleIndex,
      exampleIpAddressIndex,
      exampleIpAddressProvFreeIpAddressListValue }
::= { exampleIpAddressProvFreeIpAddressListTable 1 }

ExampleIpAddressProvFreeIpAddressListEntry ::= SEQUENCE {
   exampleIpAddressProvFreeIpAddressListValue
      IpAddress,
   exampleIpAddressProvFreeIpAddressListRowStatus
      RowStatus }

exampleIpAddressProvFreeIpAddressListValue OBJECT-TYPE
   SYNTAX     IpAddress 
   ACCESS     read-write
   STATUS     mandatory
   DESCRIPTION
     "This variable represents both the value and the index for the
      exampleIpAddressProvFreeIpAddressListTable."
::= { exampleIpAddressProvFreeIpAddressListEntry 1 }

exampleIpAddressProvFreeIpAddressListRowStatus OBJECT-TYPE
   SYNTAX     RowStatus 
   ACCESS     write-only
   STATUS     mandatory
   DESCRIPTION
     "This variable is used to control the addition and deletion 
      of individual values of the exampleIpAddressProvFreeIpAddressListTable."
::= { exampleIpAddressProvFreeIpAddressListEntry 2 }

exampleIpAddressProvFreeIpAddressList1Table OBJECT-TYPE
   SYNTAX     SEQUENCE OF ExampleIpAddressProvFreeIpAddressList1Entry
   ACCESS     not-accessible
   STATUS     mandatory
   DESCRIPTION
     ""
::= { exampleIpAddress 1072 }

exampleIpAddressProvFreeIpAddressList1Entry OBJECT-TYPE
   SYNTAX     ExampleIpAddressProvFreeIpAddressList1Entry
   ACCESS     not-accessible
   STATUS     mandatory
   DESCRIPTION
     "An entry in the exampleIpAddressProvFreeIpAddressList1Table."
   INDEX {
      exampleIndex,
      exampleIpAddressIndex,
      exampleIpAddressProvFreeIpAddressList1Value }
::= { exampleIpAddressProvFreeIpAddressList1Table 1 }

ExampleIpAddressProvFreeIpAddressList1Entry ::= SEQUENCE {
   exampleIpAddressProvFreeIpAddressList1Value
      IpAddress,
   exampleIpAddressProvFreeIpAddressList1RowStatus
      RowStatus }

exampleIpAddressProvFreeIpAddressList1Value OBJECT-TYPE
   SYNTAX     IpAddress 
   ACCESS     read-write
   STATUS     mandatory
   DESCRIPTION
     "This variable represents both the value and the index for the
      exampleIpAddressProvFreeIpAddressList1Table."
::= { exampleIpAddressProvFreeIpAddressList1Entry 1 }

exampleIpAddressProvFreeIpAddressList1RowStatus OBJECT-TYPE
   SYNTAX     RowStatus 
   ACCESS     write-only
   STATUS     mandatory
   DESCRIPTION
     "This variable is used to control the addition and deletion 
      of individual values of the exampleIpAddressProvFreeIpAddressList1Table."
::= { exampleIpAddressProvFreeIpAddressList1Entry 2 }



exampleString OBJECT IDENTIFIER ::= { example 5 }



exampleStringRowStatusTable OBJECT-TYPE
   SYNTAX     SEQUENCE OF ExampleStringRowStatusEntry
   ACCESS     not-accessible
   STATUS     mandatory
   DESCRIPTION
     "This entry controls the addition and deletion of 
      exampleString components."
::= { exampleString 1 }

exampleStringRowStatusEntry OBJECT-TYPE
   SYNTAX     ExampleStringRowStatusEntry
   ACCESS     not-accessible
   STATUS     mandatory
   DESCRIPTION
     "A single entry in the table represents a single 
      exampleString component."
   INDEX {
      exampleIndex,
      exampleStringIndex }
::= { exampleStringRowStatusTable 1 }

ExampleStringRowStatusEntry ::= SEQUENCE {
   exampleStringRowStatus
      RowStatus,
   exampleStringComponentName
      DisplayString,
   exampleStringStorageType
      StorageType,
   exampleStringIndex
      AsciiStringIndex }

exampleStringRowStatus OBJECT-TYPE
   SYNTAX     RowStatus 
   ACCESS     read-write
   STATUS     mandatory
   DESCRIPTION
     "This variable is used as the basis for SNMP naming of
      exampleString components.
      These components can be added and deleted."
::= { exampleStringRowStatusEntry 1 }

exampleStringComponentName OBJECT-TYPE
   SYNTAX     DisplayString 
   ACCESS     read-only
   STATUS     mandatory
   DESCRIPTION
     "This variable provides the component's string name for
      use with the ASCII Console Interface"
::= { exampleStringRowStatusEntry 2 }

exampleStringStorageType OBJECT-TYPE
   SYNTAX     StorageType 
   ACCESS     read-only
   STATUS     mandatory
   DESCRIPTION
     "This variable represents the storage type value for the
      exampleString tables."
::= { exampleStringRowStatusEntry 4 }

exampleStringIndex OBJECT-TYPE
   SYNTAX     AsciiStringIndex (SIZE (1..10))
   ACCESS     not-accessible
   STATUS     mandatory
   DESCRIPTION
     "This variable represents the index for the exampleString tables."
::= { exampleStringRowStatusEntry 10 }

exampleStringOperationalTable OBJECT-TYPE
   SYNTAX     SEQUENCE OF ExampleStringOperationalEntry
   ACCESS     not-accessible
   STATUS     mandatory
   DESCRIPTION
     ""
::= { exampleString 10 }

exampleStringOperationalEntry OBJECT-TYPE
   SYNTAX     ExampleStringOperationalEntry
   ACCESS     not-accessible
   STATUS     mandatory
   DESCRIPTION
     "An entry in the exampleStringOperationalTable."
   INDEX {
      exampleIndex,
      exampleStringIndex }
::= { exampleStringOperationalTable 1 }

ExampleStringOperationalEntry ::= SEQUENCE {
   exampleStringOperStructAsciiOnly
      AsciiString,
   exampleStringOperStructHexOnly
      HexString,
   exampleStringOperFreeAsciiOnly
      AsciiString,
   exampleStringOperFreeHexOnly
      HexString }

exampleStringOperStructAsciiOnly OBJECT-TYPE
   SYNTAX     AsciiString (SIZE (0..5))
   ACCESS     read-write
   STATUS     mandatory
   DESCRIPTION
     ""
::= { exampleStringOperationalEntry 1 }

exampleStringOperStructHexOnly OBJECT-TYPE
   SYNTAX     HexString (SIZE (1..10))
   ACCESS     read-write
   STATUS     mandatory
   DESCRIPTION
     ""
::= { exampleStringOperationalEntry 2 }

exampleStringOperFreeAsciiOnly OBJECT-TYPE
   SYNTAX     AsciiString (SIZE (0..5))
   ACCESS     read-write
   STATUS     mandatory
   DESCRIPTION
     ""
::= { exampleStringOperationalEntry 3 }

exampleStringOperFreeHexOnly OBJECT-TYPE
   SYNTAX     HexString (SIZE (1..10))
   ACCESS     read-write
   STATUS     mandatory
   DESCRIPTION
     ""
::= { exampleStringOperationalEntry 4 }

exampleStringProvisionalTable OBJECT-TYPE
   SYNTAX     SEQUENCE OF ExampleStringProvisionalEntry
   ACCESS     not-accessible
   STATUS     mandatory
   DESCRIPTION
     ""
::= { exampleString 11 }

exampleStringProvisionalEntry OBJECT-TYPE
   SYNTAX     ExampleStringProvisionalEntry
   ACCESS     not-accessible
   STATUS     mandatory
   DESCRIPTION
     "An entry in the exampleStringProvisionalTable."
   INDEX {
      exampleIndex,
      exampleStringIndex }
::= { exampleStringProvisionalTable 1 }

ExampleStringProvisionalEntry ::= SEQUENCE {
   exampleStringProvStringSub
      Link,
   exampleStringProvStructAsciiOnly
      AsciiString,
   exampleStringProvStructHexOnly
      HexString,
   exampleStringProvFreeAsciiOnly
      AsciiString,
   exampleStringProvFreeAsciiOnly1
      AsciiString,
   exampleStringProvFreeHexOnly
      HexString,
   exampleStringProvFreeHexOnly1
      HexString }

exampleStringProvStringSub OBJECT-TYPE
   SYNTAX     Link 
   ACCESS     read-write
   STATUS     mandatory
   DESCRIPTION
     ""
::= { exampleStringProvisionalEntry 1 }

exampleStringProvStructAsciiOnly OBJECT-TYPE
   SYNTAX     AsciiString (SIZE (2..4))
   ACCESS     read-write
   STATUS     mandatory
   DESCRIPTION
     ""
   DEFVAL     { '596f2e'H }  -- "Yo."
::= { exampleStringProvisionalEntry 2 }

exampleStringProvStructHexOnly OBJECT-TYPE
   SYNTAX     HexString (SIZE (1..10))
   ACCESS     read-write
   STATUS     mandatory
   DESCRIPTION
     ""
::= { exampleStringProvisionalEntry 3 }

exampleStringProvFreeAsciiOnly OBJECT-TYPE
   SYNTAX     AsciiString (SIZE (0..59))
   ACCESS     read-write
   STATUS     mandatory
   DESCRIPTION
     ""
   DEFVAL     { '46726565205374616e64696e6720537472696e6720212121'H }  -- "Free Standing String !!!"
::= { exampleStringProvisionalEntry 4 }

exampleStringProvFreeAsciiOnly1 OBJECT-TYPE
   SYNTAX     AsciiString (SIZE (0..5))
   ACCESS     read-write
   STATUS     mandatory
   DESCRIPTION
     ""
::= { exampleStringProvisionalEntry 5 }

exampleStringProvFreeHexOnly OBJECT-TYPE
   SYNTAX     HexString (SIZE (1..10))
   ACCESS     read-write
   STATUS     mandatory
   DESCRIPTION
     ""
   DEFVAL     { '0102030405060708090A'H }  -- "0102030405060708090A"
::= { exampleStringProvisionalEntry 6 }

exampleStringProvFreeHexOnly1 OBJECT-TYPE
   SYNTAX     HexString (SIZE (0..10))
   ACCESS     read-write
   STATUS     mandatory
   DESCRIPTION
     ""
::= { exampleStringProvisionalEntry 7 }

exampleStringOperStructStrVectorTable OBJECT-TYPE
   SYNTAX     SEQUENCE OF ExampleStringOperStructStrVectorEntry
   ACCESS     not-accessible
   STATUS     mandatory
   DESCRIPTION
     ""
::= { exampleString 1073 }

exampleStringOperStructStrVectorEntry OBJECT-TYPE
   SYNTAX     ExampleStringOperStructStrVectorEntry
   ACCESS     not-accessible
   STATUS     mandatory
   DESCRIPTION
     "An entry in the exampleStringOperStructStrVectorTable."
   INDEX {
      exampleIndex,
      exampleStringIndex,
      exampleStringOperStructStrVectorIndex }
::= { exampleStringOperStructStrVectorTable 1 }

ExampleStringOperStructStrVectorEntry ::= SEQUENCE {
   exampleStringOperStructStrVectorIndex
      Integer32,
   exampleStringOperStructStrVectorValue
      AsciiString }

exampleStringOperStructStrVectorIndex OBJECT-TYPE
   SYNTAX     Integer32 (0..9)
   ACCESS     not-accessible
   STATUS     mandatory
   DESCRIPTION
     "This variable represents the exampleStringOperStructStrVectorTable
      specific index for the exampleStringOperStructStrVectorTable."
::= { exampleStringOperStructStrVectorEntry 1 }

exampleStringOperStructStrVectorValue OBJECT-TYPE
   SYNTAX     AsciiString (SIZE (0..5))
   ACCESS     read-write
   STATUS     mandatory
   DESCRIPTION
     "This variable represents an individual value for the
      exampleStringOperStructStrVectorTable."
::= { exampleStringOperStructStrVectorEntry 2 }

exampleStringOperStructStrArrayTable OBJECT-TYPE
   SYNTAX     SEQUENCE OF ExampleStringOperStructStrArrayEntry
   ACCESS     not-accessible
   STATUS     mandatory
   DESCRIPTION
     ""
::= { exampleString 1074 }

exampleStringOperStructStrArrayEntry OBJECT-TYPE
   SYNTAX     ExampleStringOperStructStrArrayEntry
   ACCESS     not-accessible
   STATUS     mandatory
   DESCRIPTION
     "An entry in the exampleStringOperStructStrArrayTable."
   INDEX {
      exampleIndex,
      exampleStringIndex,
      exampleStringOperStructStrArrayRowIndex,
      exampleStringOperStructStrArrayColumnIndex }
::= { exampleStringOperStructStrArrayTable 1 }

ExampleStringOperStructStrArrayEntry ::= SEQUENCE {
   exampleStringOperStructStrArrayRowIndex
      Integer32,
   exampleStringOperStructStrArrayColumnIndex
      Integer32,
   exampleStringOperStructStrArrayValue
      AsciiString }

exampleStringOperStructStrArrayRowIndex OBJECT-TYPE
   SYNTAX     Integer32 (0..2)
   ACCESS     not-accessible
   STATUS     mandatory
   DESCRIPTION
     "This variable represents the next to last index for the 
      exampleStringOperStructStrArrayTable."
::= { exampleStringOperStructStrArrayEntry 1 }

exampleStringOperStructStrArrayColumnIndex OBJECT-TYPE
   SYNTAX     Integer32 (0..3)
   ACCESS     not-accessible
   STATUS     mandatory
   DESCRIPTION
     "This variable represents the final index for the 
      exampleStringOperStructStrArrayTable."
::= { exampleStringOperStructStrArrayEntry 2 }

exampleStringOperStructStrArrayValue OBJECT-TYPE
   SYNTAX     AsciiString (SIZE (0..5))
   ACCESS     read-write
   STATUS     mandatory
   DESCRIPTION
     "This variable represents an individual value for the
      exampleStringOperStructStrArrayTable."
::= { exampleStringOperStructStrArrayEntry 3 }

exampleStringOperFreeStrVectorTable OBJECT-TYPE
   SYNTAX     SEQUENCE OF ExampleStringOperFreeStrVectorEntry
   ACCESS     not-accessible
   STATUS     mandatory
   DESCRIPTION
     ""
::= { exampleString 1075 }

exampleStringOperFreeStrVectorEntry OBJECT-TYPE
   SYNTAX     ExampleStringOperFreeStrVectorEntry
   ACCESS     not-accessible
   STATUS     mandatory
   DESCRIPTION
     "An entry in the exampleStringOperFreeStrVectorTable."
   INDEX {
      exampleIndex,
      exampleStringIndex,
      exampleStringOperFreeStrVectorIndex }
::= { exampleStringOperFreeStrVectorTable 1 }

ExampleStringOperFreeStrVectorEntry ::= SEQUENCE {
   exampleStringOperFreeStrVectorIndex
      Integer32,
   exampleStringOperFreeStrVectorValue
      AsciiString }

exampleStringOperFreeStrVectorIndex OBJECT-TYPE
   SYNTAX     Integer32 (0..9)
   ACCESS     not-accessible
   STATUS     mandatory
   DESCRIPTION
     "This variable represents the exampleStringOperFreeStrVectorTable
      specific index for the exampleStringOperFreeStrVectorTable."
::= { exampleStringOperFreeStrVectorEntry 1 }

exampleStringOperFreeStrVectorValue OBJECT-TYPE
   SYNTAX     AsciiString (SIZE (0..5))
   ACCESS     read-write
   STATUS     mandatory
   DESCRIPTION
     "This variable represents an individual value for the
      exampleStringOperFreeStrVectorTable."
::= { exampleStringOperFreeStrVectorEntry 2 }

exampleStringOperFreeStrArrayTable OBJECT-TYPE
   SYNTAX     SEQUENCE OF ExampleStringOperFreeStrArrayEntry
   ACCESS     not-accessible
   STATUS     mandatory
   DESCRIPTION
     ""
::= { exampleString 1076 }

exampleStringOperFreeStrArrayEntry OBJECT-TYPE
   SYNTAX     ExampleStringOperFreeStrArrayEntry
   ACCESS     not-accessible
   STATUS     mandatory
   DESCRIPTION
     "An entry in the exampleStringOperFreeStrArrayTable."
   INDEX {
      exampleIndex,
      exampleStringIndex,
      exampleStringOperFreeStrArrayRowIndex,
      exampleStringOperFreeStrArrayColumnIndex }
::= { exampleStringOperFreeStrArrayTable 1 }

ExampleStringOperFreeStrArrayEntry ::= SEQUENCE {
   exampleStringOperFreeStrArrayRowIndex
      Integer32,
   exampleStringOperFreeStrArrayColumnIndex
      Integer32,
   exampleStringOperFreeStrArrayValue
      AsciiString }

exampleStringOperFreeStrArrayRowIndex OBJECT-TYPE
   SYNTAX     Integer32 (0..2)
   ACCESS     not-accessible
   STATUS     mandatory
   DESCRIPTION
     "This variable represents the next to last index for the 
      exampleStringOperFreeStrArrayTable."
::= { exampleStringOperFreeStrArrayEntry 1 }

exampleStringOperFreeStrArrayColumnIndex OBJECT-TYPE
   SYNTAX     Integer32 (0..3)
   ACCESS     not-accessible
   STATUS     mandatory
   DESCRIPTION
     "This variable represents the final index for the 
      exampleStringOperFreeStrArrayTable."
::= { exampleStringOperFreeStrArrayEntry 2 }

exampleStringOperFreeStrArrayValue OBJECT-TYPE
   SYNTAX     AsciiString (SIZE (0..5))
   ACCESS     read-write
   STATUS     mandatory
   DESCRIPTION
     "This variable represents an individual value for the
      exampleStringOperFreeStrArrayTable."
::= { exampleStringOperFreeStrArrayEntry 3 }

exampleStringOperFreeStrReplicatedTable OBJECT-TYPE
   SYNTAX     SEQUENCE OF ExampleStringOperFreeStrReplicatedEntry
   ACCESS     not-accessible
   STATUS     mandatory
   DESCRIPTION
     ""
::= { exampleString 1077 }

exampleStringOperFreeStrReplicatedEntry OBJECT-TYPE
   SYNTAX     ExampleStringOperFreeStrReplicatedEntry
   ACCESS     not-accessible
   STATUS     mandatory
   DESCRIPTION
     "An entry in the exampleStringOperFreeStrReplicatedTable."
   INDEX {
      exampleIndex,
      exampleStringIndex,
      exampleStringOperFreeStrReplicatedIndex }
::= { exampleStringOperFreeStrReplicatedTable 1 }

ExampleStringOperFreeStrReplicatedEntry ::= SEQUENCE {
   exampleStringOperFreeStrReplicatedIndex
      AsciiString,
   exampleStringOperFreeStrReplicatedValue
      AsciiString,
   exampleStringOperFreeStrReplicatedRowStatus
      RowStatus }

exampleStringOperFreeStrReplicatedIndex OBJECT-TYPE
   SYNTAX     AsciiString (SIZE (0..5))
   ACCESS     not-accessible
   STATUS     mandatory
   DESCRIPTION
     "This variable represents the index for the exampleStringOperFreeStrReplicatedTable."
::= { exampleStringOperFreeStrReplicatedEntry 1 }

exampleStringOperFreeStrReplicatedValue OBJECT-TYPE
   SYNTAX     AsciiString (SIZE (0..5))
   ACCESS     read-write
   STATUS     mandatory
   DESCRIPTION
     "This variable represents an individual value for the
      exampleStringOperFreeStrReplicatedTable."
::= { exampleStringOperFreeStrReplicatedEntry 2 }

exampleStringOperFreeStrReplicatedRowStatus OBJECT-TYPE
   SYNTAX     RowStatus 
   ACCESS     write-only
   STATUS     mandatory
   DESCRIPTION
     "This variable is used to control the addition and deletion 
      of individual values of the exampleStringOperFreeStrReplicatedTable."
::= { exampleStringOperFreeStrReplicatedEntry 3 }

exampleStringOperFreeStrListTable OBJECT-TYPE
   SYNTAX     SEQUENCE OF ExampleStringOperFreeStrListEntry
   ACCESS     not-accessible
   STATUS     mandatory
   DESCRIPTION
     ""
::= { exampleString 1078 }

exampleStringOperFreeStrListEntry OBJECT-TYPE
   SYNTAX     ExampleStringOperFreeStrListEntry
   ACCESS     not-accessible
   STATUS     mandatory
   DESCRIPTION
     "An entry in the exampleStringOperFreeStrListTable."
   INDEX {
      exampleIndex,
      exampleStringIndex,
      exampleStringOperFreeStrListValue }
::= { exampleStringOperFreeStrListTable 1 }

ExampleStringOperFreeStrListEntry ::= SEQUENCE {
   exampleStringOperFreeStrListValue
      AsciiString,
   exampleStringOperFreeStrListRowStatus
      RowStatus }

exampleStringOperFreeStrListValue OBJECT-TYPE
   SYNTAX     AsciiString (SIZE (0..10))
   ACCESS     read-write
   STATUS     mandatory
   DESCRIPTION
     "This variable represents both the value and the index for the
      exampleStringOperFreeStrListTable."
::= { exampleStringOperFreeStrListEntry 1 }

exampleStringOperFreeStrListRowStatus OBJECT-TYPE
   SYNTAX     RowStatus 
   ACCESS     write-only
   STATUS     mandatory
   DESCRIPTION
     "This variable is used to control the addition and deletion 
      of individual values of the exampleStringOperFreeStrListTable."
::= { exampleStringOperFreeStrListEntry 2 }

exampleStringProvStructStrVectorTable OBJECT-TYPE
   SYNTAX     SEQUENCE OF ExampleStringProvStructStrVectorEntry
   ACCESS     not-accessible
   STATUS     mandatory
   DESCRIPTION
     ""
::= { exampleString 1079 }

exampleStringProvStructStrVectorEntry OBJECT-TYPE
   SYNTAX     ExampleStringProvStructStrVectorEntry
   ACCESS     not-accessible
   STATUS     mandatory
   DESCRIPTION
     "An entry in the exampleStringProvStructStrVectorTable."
   INDEX {
      exampleIndex,
      exampleStringIndex,
      exampleStringProvStructStrVectorIndex }
::= { exampleStringProvStructStrVectorTable 1 }

ExampleStringProvStructStrVectorEntry ::= SEQUENCE {
   exampleStringProvStructStrVectorIndex
      Integer32,
   exampleStringProvStructStrVectorValue
      AsciiString }

exampleStringProvStructStrVectorIndex OBJECT-TYPE
   SYNTAX     Integer32 (0..9)
   ACCESS     not-accessible
   STATUS     mandatory
   DESCRIPTION
     "This variable represents the exampleStringProvStructStrVectorTable
      specific index for the exampleStringProvStructStrVectorTable."
::= { exampleStringProvStructStrVectorEntry 1 }

exampleStringProvStructStrVectorValue OBJECT-TYPE
   SYNTAX     AsciiString (SIZE (0..5))
   ACCESS     read-write
   STATUS     mandatory
   DESCRIPTION
     "This variable represents an individual value for the
      exampleStringProvStructStrVectorTable."
::= { exampleStringProvStructStrVectorEntry 2 }

exampleStringProvStructStrArrayTable OBJECT-TYPE
   SYNTAX     SEQUENCE OF ExampleStringProvStructStrArrayEntry
   ACCESS     not-accessible
   STATUS     mandatory
   DESCRIPTION
     ""
::= { exampleString 1080 }

exampleStringProvStructStrArrayEntry OBJECT-TYPE
   SYNTAX     ExampleStringProvStructStrArrayEntry
   ACCESS     not-accessible
   STATUS     mandatory
   DESCRIPTION
     "An entry in the exampleStringProvStructStrArrayTable."
   INDEX {
      exampleIndex,
      exampleStringIndex,
      exampleStringProvStructStrArrayRowIndex,
      exampleStringProvStructStrArrayColumnIndex }
::= { exampleStringProvStructStrArrayTable 1 }

ExampleStringProvStructStrArrayEntry ::= SEQUENCE {
   exampleStringProvStructStrArrayRowIndex
      Integer32,
   exampleStringProvStructStrArrayColumnIndex
      Integer32,
   exampleStringProvStructStrArrayValue
      AsciiString }

exampleStringProvStructStrArrayRowIndex OBJECT-TYPE
   SYNTAX     Integer32 (0..2)
   ACCESS     not-accessible
   STATUS     mandatory
   DESCRIPTION
     "This variable represents the next to last index for the 
      exampleStringProvStructStrArrayTable."
::= { exampleStringProvStructStrArrayEntry 1 }

exampleStringProvStructStrArrayColumnIndex OBJECT-TYPE
   SYNTAX     Integer32 (0..3)
   ACCESS     not-accessible
   STATUS     mandatory
   DESCRIPTION
     "This variable represents the final index for the 
      exampleStringProvStructStrArrayTable."
::= { exampleStringProvStructStrArrayEntry 2 }

exampleStringProvStructStrArrayValue OBJECT-TYPE
   SYNTAX     AsciiString (SIZE (0..5))
   ACCESS     read-write
   STATUS     mandatory
   DESCRIPTION
     "This variable represents an individual value for the
      exampleStringProvStructStrArrayTable."
::= { exampleStringProvStructStrArrayEntry 3 }

exampleStringProvFreeStrVectorTable OBJECT-TYPE
   SYNTAX     SEQUENCE OF ExampleStringProvFreeStrVectorEntry
   ACCESS     not-accessible
   STATUS     mandatory
   DESCRIPTION
     ""
::= { exampleString 1081 }

exampleStringProvFreeStrVectorEntry OBJECT-TYPE
   SYNTAX     ExampleStringProvFreeStrVectorEntry
   ACCESS     not-accessible
   STATUS     mandatory
   DESCRIPTION
     "An entry in the exampleStringProvFreeStrVectorTable."
   INDEX {
      exampleIndex,
      exampleStringIndex,
      exampleStringProvFreeStrVectorIndex }
::= { exampleStringProvFreeStrVectorTable 1 }

ExampleStringProvFreeStrVectorEntry ::= SEQUENCE {
   exampleStringProvFreeStrVectorIndex
      Integer32,
   exampleStringProvFreeStrVectorValue
      AsciiString }

exampleStringProvFreeStrVectorIndex OBJECT-TYPE
   SYNTAX     Integer32 (0..9)
   ACCESS     not-accessible
   STATUS     mandatory
   DESCRIPTION
     "This variable represents the exampleStringProvFreeStrVectorTable
      specific index for the exampleStringProvFreeStrVectorTable."
::= { exampleStringProvFreeStrVectorEntry 1 }

exampleStringProvFreeStrVectorValue OBJECT-TYPE
   SYNTAX     AsciiString (SIZE (0..5))
   ACCESS     read-write
   STATUS     mandatory
   DESCRIPTION
     "This variable represents an individual value for the
      exampleStringProvFreeStrVectorTable."
::= { exampleStringProvFreeStrVectorEntry 2 }

exampleStringProvFreeStrVector1Table OBJECT-TYPE
   SYNTAX     SEQUENCE OF ExampleStringProvFreeStrVector1Entry
   ACCESS     not-accessible
   STATUS     mandatory
   DESCRIPTION
     ""
::= { exampleString 1082 }

exampleStringProvFreeStrVector1Entry OBJECT-TYPE
   SYNTAX     ExampleStringProvFreeStrVector1Entry
   ACCESS     not-accessible
   STATUS     mandatory
   DESCRIPTION
     "An entry in the exampleStringProvFreeStrVector1Table."
   INDEX {
      exampleIndex,
      exampleStringIndex,
      exampleStringProvFreeStrVector1Index }
::= { exampleStringProvFreeStrVector1Table 1 }

ExampleStringProvFreeStrVector1Entry ::= SEQUENCE {
   exampleStringProvFreeStrVector1Index
      Integer32,
   exampleStringProvFreeStrVector1Value
      AsciiString }

exampleStringProvFreeStrVector1Index OBJECT-TYPE
   SYNTAX     Integer32 (0..5)
   ACCESS     not-accessible
   STATUS     mandatory
   DESCRIPTION
     "This variable represents the exampleStringProvFreeStrVector1Table
      specific index for the exampleStringProvFreeStrVector1Table."
::= { exampleStringProvFreeStrVector1Entry 1 }

exampleStringProvFreeStrVector1Value OBJECT-TYPE
   SYNTAX     AsciiString (SIZE (0..5))
   ACCESS     read-write
   STATUS     mandatory
   DESCRIPTION
     "This variable represents an individual value for the
      exampleStringProvFreeStrVector1Table."
::= { exampleStringProvFreeStrVector1Entry 2 }

exampleStringProvFreeStrArrayTable OBJECT-TYPE
   SYNTAX     SEQUENCE OF ExampleStringProvFreeStrArrayEntry
   ACCESS     not-accessible
   STATUS     mandatory
   DESCRIPTION
     ""
::= { exampleString 1083 }

exampleStringProvFreeStrArrayEntry OBJECT-TYPE
   SYNTAX     ExampleStringProvFreeStrArrayEntry
   ACCESS     not-accessible
   STATUS     mandatory
   DESCRIPTION
     "An entry in the exampleStringProvFreeStrArrayTable."
   INDEX {
      exampleIndex,
      exampleStringIndex,
      exampleStringProvFreeStrArrayRowIndex,
      exampleStringProvFreeStrArrayColumnIndex }
::= { exampleStringProvFreeStrArrayTable 1 }

ExampleStringProvFreeStrArrayEntry ::= SEQUENCE {
   exampleStringProvFreeStrArrayRowIndex
      Integer32,
   exampleStringProvFreeStrArrayColumnIndex
      Integer32,
   exampleStringProvFreeStrArrayValue
      AsciiString }

exampleStringProvFreeStrArrayRowIndex OBJECT-TYPE
   SYNTAX     Integer32 (0..2)
   ACCESS     not-accessible
   STATUS     mandatory
   DESCRIPTION
     "This variable represents the next to last index for the 
      exampleStringProvFreeStrArrayTable."
::= { exampleStringProvFreeStrArrayEntry 1 }

exampleStringProvFreeStrArrayColumnIndex OBJECT-TYPE
   SYNTAX     Integer32 (0..3)
   ACCESS     not-accessible
   STATUS     mandatory
   DESCRIPTION
     "This variable represents the final index for the 
      exampleStringProvFreeStrArrayTable."
::= { exampleStringProvFreeStrArrayEntry 2 }

exampleStringProvFreeStrArrayValue OBJECT-TYPE
   SYNTAX     AsciiString (SIZE (0..5))
   ACCESS     read-write
   STATUS     mandatory
   DESCRIPTION
     "This variable represents an individual value for the
      exampleStringProvFreeStrArrayTable."
::= { exampleStringProvFreeStrArrayEntry 3 }

exampleStringProvFreeStrArray1Table OBJECT-TYPE
   SYNTAX     SEQUENCE OF ExampleStringProvFreeStrArray1Entry
   ACCESS     not-accessible
   STATUS     mandatory
   DESCRIPTION
     ""
::= { exampleString 1084 }

exampleStringProvFreeStrArray1Entry OBJECT-TYPE
   SYNTAX     ExampleStringProvFreeStrArray1Entry
   ACCESS     not-accessible
   STATUS     mandatory
   DESCRIPTION
     "An entry in the exampleStringProvFreeStrArray1Table."
   INDEX {
      exampleIndex,
      exampleStringIndex,
      exampleStringProvFreeStrArray1RowIndex,
      exampleStringProvFreeStrArray1ColumnIndex }
::= { exampleStringProvFreeStrArray1Table 1 }

ExampleStringProvFreeStrArray1Entry ::= SEQUENCE {
   exampleStringProvFreeStrArray1RowIndex
      Integer32,
   exampleStringProvFreeStrArray1ColumnIndex
      Integer32,
   exampleStringProvFreeStrArray1Value
      AsciiString }

exampleStringProvFreeStrArray1RowIndex OBJECT-TYPE
   SYNTAX     Integer32 (0..4)
   ACCESS     not-accessible
   STATUS     mandatory
   DESCRIPTION
     "This variable represents the next to last index for the 
      exampleStringProvFreeStrArray1Table."
::= { exampleStringProvFreeStrArray1Entry 1 }

exampleStringProvFreeStrArray1ColumnIndex OBJECT-TYPE
   SYNTAX     Integer32 (0..3)
   ACCESS     not-accessible
   STATUS     mandatory
   DESCRIPTION
     "This variable represents the final index for the 
      exampleStringProvFreeStrArray1Table."
::= { exampleStringProvFreeStrArray1Entry 2 }

exampleStringProvFreeStrArray1Value OBJECT-TYPE
   SYNTAX     AsciiString (SIZE (0..5))
   ACCESS     read-write
   STATUS     mandatory
   DESCRIPTION
     "This variable represents an individual value for the
      exampleStringProvFreeStrArray1Table."
::= { exampleStringProvFreeStrArray1Entry 3 }

exampleStringProvFreeStrReplicatedTable OBJECT-TYPE
   SYNTAX     SEQUENCE OF ExampleStringProvFreeStrReplicatedEntry
   ACCESS     not-accessible
   STATUS     mandatory
   DESCRIPTION
     ""
::= { exampleString 1085 }

exampleStringProvFreeStrReplicatedEntry OBJECT-TYPE
   SYNTAX     ExampleStringProvFreeStrReplicatedEntry
   ACCESS     not-accessible
   STATUS     mandatory
   DESCRIPTION
     "An entry in the exampleStringProvFreeStrReplicatedTable."
   INDEX {
      exampleIndex,
      exampleStringIndex,
      exampleStringProvFreeStrReplicatedIndex }
::= { exampleStringProvFreeStrReplicatedTable 1 }

ExampleStringProvFreeStrReplicatedEntry ::= SEQUENCE {
   exampleStringProvFreeStrReplicatedIndex
      AsciiString,
   exampleStringProvFreeStrReplicatedValue
      AsciiString,
   exampleStringProvFreeStrReplicatedRowStatus
      RowStatus }

exampleStringProvFreeStrReplicatedIndex OBJECT-TYPE
   SYNTAX     AsciiString (SIZE (0..5))
   ACCESS     not-accessible
   STATUS     mandatory
   DESCRIPTION
     "This variable represents the index for the exampleStringProvFreeStrReplicatedTable."
::= { exampleStringProvFreeStrReplicatedEntry 1 }

exampleStringProvFreeStrReplicatedValue OBJECT-TYPE
   SYNTAX     AsciiString (SIZE (0..5))
   ACCESS     read-write
   STATUS     mandatory
   DESCRIPTION
     "This variable represents an individual value for the
      exampleStringProvFreeStrReplicatedTable."
::= { exampleStringProvFreeStrReplicatedEntry 2 }

exampleStringProvFreeStrReplicatedRowStatus OBJECT-TYPE
   SYNTAX     RowStatus 
   ACCESS     write-only
   STATUS     mandatory
   DESCRIPTION
     "This variable is used to control the addition and deletion 
      of individual values of the exampleStringProvFreeStrReplicatedTable."
::= { exampleStringProvFreeStrReplicatedEntry 3 }

exampleStringProvFreeStrListTable OBJECT-TYPE
   SYNTAX     SEQUENCE OF ExampleStringProvFreeStrListEntry
   ACCESS     not-accessible
   STATUS     mandatory
   DESCRIPTION
     ""
::= { exampleString 1086 }

exampleStringProvFreeStrListEntry OBJECT-TYPE
   SYNTAX     ExampleStringProvFreeStrListEntry
   ACCESS     not-accessible
   STATUS     mandatory
   DESCRIPTION
     "An entry in the exampleStringProvFreeStrListTable."
   INDEX {
      exampleIndex,
      exampleStringIndex,
      exampleStringProvFreeStrListValue }
::= { exampleStringProvFreeStrListTable 1 }

ExampleStringProvFreeStrListEntry ::= SEQUENCE {
   exampleStringProvFreeStrListValue
      AsciiString,
   exampleStringProvFreeStrListRowStatus
      RowStatus }

exampleStringProvFreeStrListValue OBJECT-TYPE
   SYNTAX     AsciiString (SIZE (0..10))
   ACCESS     read-write
   STATUS     mandatory
   DESCRIPTION
     "This variable represents both the value and the index for the
      exampleStringProvFreeStrListTable."
::= { exampleStringProvFreeStrListEntry 1 }

exampleStringProvFreeStrListRowStatus OBJECT-TYPE
   SYNTAX     RowStatus 
   ACCESS     write-only
   STATUS     mandatory
   DESCRIPTION
     "This variable is used to control the addition and deletion 
      of individual values of the exampleStringProvFreeStrListTable."
::= { exampleStringProvFreeStrListEntry 2 }

exampleStringProvFreeStrList1Table OBJECT-TYPE
   SYNTAX     SEQUENCE OF ExampleStringProvFreeStrList1Entry
   ACCESS     not-accessible
   STATUS     mandatory
   DESCRIPTION
     ""
::= { exampleString 1087 }

exampleStringProvFreeStrList1Entry OBJECT-TYPE
   SYNTAX     ExampleStringProvFreeStrList1Entry
   ACCESS     not-accessible
   STATUS     mandatory
   DESCRIPTION
     "An entry in the exampleStringProvFreeStrList1Table."
   INDEX {
      exampleIndex,
      exampleStringIndex,
      exampleStringProvFreeStrList1Value }
::= { exampleStringProvFreeStrList1Table 1 }

ExampleStringProvFreeStrList1Entry ::= SEQUENCE {
   exampleStringProvFreeStrList1Value
      AsciiString,
   exampleStringProvFreeStrList1RowStatus
      RowStatus }

exampleStringProvFreeStrList1Value OBJECT-TYPE
   SYNTAX     AsciiString (SIZE (0..10))
   ACCESS     read-write
   STATUS     mandatory
   DESCRIPTION
     "This variable represents both the value and the index for the
      exampleStringProvFreeStrList1Table."
::= { exampleStringProvFreeStrList1Entry 1 }

exampleStringProvFreeStrList1RowStatus OBJECT-TYPE
   SYNTAX     RowStatus 
   ACCESS     write-only
   STATUS     mandatory
   DESCRIPTION
     "This variable is used to control the addition and deletion 
      of individual values of the exampleStringProvFreeStrList1Table."
::= { exampleStringProvFreeStrList1Entry 2 }



exampleFixedPt OBJECT IDENTIFIER ::= { example 6 }



exampleFixedPtRowStatusTable OBJECT-TYPE
   SYNTAX     SEQUENCE OF ExampleFixedPtRowStatusEntry
   ACCESS     not-accessible
   STATUS     mandatory
   DESCRIPTION
     "This entry controls the addition and deletion of 
      exampleFixedPt components."
::= { exampleFixedPt 1 }

exampleFixedPtRowStatusEntry OBJECT-TYPE
   SYNTAX     ExampleFixedPtRowStatusEntry
   ACCESS     not-accessible
   STATUS     mandatory
   DESCRIPTION
     "A single entry in the table represents a single 
      exampleFixedPt component."
   INDEX {
      exampleIndex,
      exampleFixedPtIndex }
::= { exampleFixedPtRowStatusTable 1 }

ExampleFixedPtRowStatusEntry ::= SEQUENCE {
   exampleFixedPtRowStatus
      RowStatus,
   exampleFixedPtComponentName
      DisplayString,
   exampleFixedPtStorageType
      StorageType,
   exampleFixedPtIndex
      NonReplicated }

exampleFixedPtRowStatus OBJECT-TYPE
   SYNTAX     RowStatus 
   ACCESS     read-write
   STATUS     mandatory
   DESCRIPTION
     "This variable is used as the basis for SNMP naming of
      exampleFixedPt components.
      These components can be added and deleted."
::= { exampleFixedPtRowStatusEntry 1 }

exampleFixedPtComponentName OBJECT-TYPE
   SYNTAX     DisplayString 
   ACCESS     read-only
   STATUS     mandatory
   DESCRIPTION
     "This variable provides the component's string name for
      use with the ASCII Console Interface"
::= { exampleFixedPtRowStatusEntry 2 }

exampleFixedPtStorageType OBJECT-TYPE
   SYNTAX     StorageType 
   ACCESS     read-only
   STATUS     mandatory
   DESCRIPTION
     "This variable represents the storage type value for the
      exampleFixedPt tables."
::= { exampleFixedPtRowStatusEntry 4 }

exampleFixedPtIndex OBJECT-TYPE
   SYNTAX     NonReplicated 
   ACCESS     not-accessible
   STATUS     mandatory
   DESCRIPTION
     "This variable represents the index for the exampleFixedPt tables."
::= { exampleFixedPtRowStatusEntry 10 }

exampleFixedPtOperationalTable OBJECT-TYPE
   SYNTAX     SEQUENCE OF ExampleFixedPtOperationalEntry
   ACCESS     not-accessible
   STATUS     mandatory
   DESCRIPTION
     ""
::= { exampleFixedPt 10 }

exampleFixedPtOperationalEntry OBJECT-TYPE
   SYNTAX     ExampleFixedPtOperationalEntry
   ACCESS     not-accessible
   STATUS     mandatory
   DESCRIPTION
     "An entry in the exampleFixedPtOperationalTable."
   INDEX {
      exampleIndex,
      exampleFixedPtIndex }
::= { exampleFixedPtOperationalTable 1 }

ExampleFixedPtOperationalEntry ::= SEQUENCE {
   exampleFixedPtOperStructFixedPt
      FixedPoint4,
   exampleFixedPtOperFreeFixedPt
      FixedPoint2,
   exampleFixedPtOperFreeFixedPtSet
      OCTET STRING }

exampleFixedPtOperStructFixedPt OBJECT-TYPE
   SYNTAX     FixedPoint4 (100..2553300)
   ACCESS     read-write
   STATUS     mandatory
   DESCRIPTION
     ""
::= { exampleFixedPtOperationalEntry 1 }

exampleFixedPtOperFreeFixedPt OBJECT-TYPE
   SYNTAX     FixedPoint2 (0..1099 | 10001..20000)
   ACCESS     read-write
   STATUS     mandatory
   DESCRIPTION
     ""
::= { exampleFixedPtOperationalEntry 2 }

exampleFixedPtOperFreeFixedPtSet OBJECT-TYPE
   SYNTAX     OCTET STRING (SIZE (4))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)"
::= { exampleFixedPtOperationalEntry 3 }

exampleFixedPtProvisionalTable OBJECT-TYPE
   SYNTAX     SEQUENCE OF ExampleFixedPtProvisionalEntry
   ACCESS     not-accessible
   STATUS     mandatory
   DESCRIPTION
     ""
::= { exampleFixedPt 11 }

exampleFixedPtProvisionalEntry OBJECT-TYPE
   SYNTAX     ExampleFixedPtProvisionalEntry
   ACCESS     not-accessible
   STATUS     mandatory
   DESCRIPTION
     "An entry in the exampleFixedPtProvisionalTable."
   INDEX {
      exampleIndex,
      exampleFixedPtIndex }
::= { exampleFixedPtProvisionalTable 1 }

ExampleFixedPtProvisionalEntry ::= SEQUENCE {
   exampleFixedPtProvFixedPtSubcomponent
      Link,
   exampleFixedPtProvStructFixedPt
      FixedPoint3,
   exampleFixedPtProvStructFixedPtSet
      OCTET STRING,
   exampleFixedPtProvFreeFixedPt
      FixedPoint2,
   exampleFixedPtProvFreeFixedPtSet
      OCTET STRING }

exampleFixedPtProvFixedPtSubcomponent OBJECT-TYPE
   SYNTAX     Link 
   ACCESS     read-write
   STATUS     mandatory
   DESCRIPTION
     ""
::= { exampleFixedPtProvisionalEntry 1 }

exampleFixedPtProvStructFixedPt OBJECT-TYPE
   SYNTAX     FixedPoint3 (0..252000 | 253000 | 254000 | 255000)
   ACCESS     read-write
   STATUS     mandatory
   DESCRIPTION
     "VALUES (

      253000 = infinity

      254000 = notApplicable

      255000 = notMeasured

      )"
   DEFVAL     { 253000 }
::= { exampleFixedPtProvisionalEntry 2 }

exampleFixedPtProvStructFixedPtSet OBJECT-TYPE
   SYNTAX     OCTET STRING (SIZE (1))
   ACCESS     read-write
   STATUS     mandatory
   DESCRIPTION
     "Description of bits:
      n0(0)
      n1(1)
      n2(2)
      n3(3)
      n4(4)
      n5(5)"
   DEFVAL     { 'c8'H }
::= { exampleFixedPtProvisionalEntry 3 }

exampleFixedPtProvFreeFixedPt OBJECT-TYPE
   SYNTAX     FixedPoint2 (0..1099 | 10001..20099)
   ACCESS     read-write
   STATUS     mandatory
   DESCRIPTION
     ""
   DEFVAL     { 10101 }
::= { exampleFixedPtProvisionalEntry 4 }

exampleFixedPtProvFreeFixedPtSet OBJECT-TYPE
   SYNTAX     OCTET STRING (SIZE (4))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)"
   DEFVAL     { '05500002'H }
::= { exampleFixedPtProvisionalEntry 5 }

exampleFixedPtOperStructFixedPtVectorTable OBJECT-TYPE
   SYNTAX     SEQUENCE OF ExampleFixedPtOperStructFixedPtVectorEntry
   ACCESS     not-accessible
   STATUS     mandatory
   DESCRIPTION
     ""
::= { exampleFixedPt 1028 }

exampleFixedPtOperStructFixedPtVectorEntry OBJECT-TYPE
   SYNTAX     ExampleFixedPtOperStructFixedPtVectorEntry
   ACCESS     not-accessible
   STATUS     mandatory
   DESCRIPTION
     "An entry in the exampleFixedPtOperStructFixedPtVectorTable."
   INDEX {
      exampleIndex,
      exampleFixedPtIndex,
      exampleFixedPtOperStructFixedPtVectorIndex }
::= { exampleFixedPtOperStructFixedPtVectorTable 1 }

ExampleFixedPtOperStructFixedPtVectorEntry ::= SEQUENCE {
   exampleFixedPtOperStructFixedPtVectorIndex
      Integer32,
   exampleFixedPtOperStructFixedPtVectorValue
      FixedPoint3 }

exampleFixedPtOperStructFixedPtVectorIndex OBJECT-TYPE
   SYNTAX     Integer32 (0..9)
   ACCESS     not-accessible
   STATUS     mandatory
   DESCRIPTION
     "This variable represents the exampleFixedPtOperStructFixedPtVectorTable
      specific index for the exampleFixedPtOperStructFixedPtVectorTable."
::= { exampleFixedPtOperStructFixedPtVectorEntry 1 }

exampleFixedPtOperStructFixedPtVectorValue OBJECT-TYPE
   SYNTAX     FixedPoint3 (0..100100)
   ACCESS     read-write
   STATUS     mandatory
   DESCRIPTION
     "This variable represents an individual value for the
      exampleFixedPtOperStructFixedPtVectorTable."
::= { exampleFixedPtOperStructFixedPtVectorEntry 2 }

exampleFixedPtOperStructFixedPtArrayTable OBJECT-TYPE
   SYNTAX     SEQUENCE OF ExampleFixedPtOperStructFixedPtArrayEntry
   ACCESS     not-accessible
   STATUS     mandatory
   DESCRIPTION
     ""
::= { exampleFixedPt 1029 }

exampleFixedPtOperStructFixedPtArrayEntry OBJECT-TYPE
   SYNTAX     ExampleFixedPtOperStructFixedPtArrayEntry
   ACCESS     not-accessible
   STATUS     mandatory
   DESCRIPTION
     "An entry in the exampleFixedPtOperStructFixedPtArrayTable."
   INDEX {
      exampleIndex,
      exampleFixedPtIndex,
      exampleFixedPtOperStructFixedPtArrayRowIndex,
      exampleFixedPtOperStructFixedPtArrayColumnIndex }
::= { exampleFixedPtOperStructFixedPtArrayTable 1 }

ExampleFixedPtOperStructFixedPtArrayEntry ::= SEQUENCE {
   exampleFixedPtOperStructFixedPtArrayRowIndex
      Integer32,
   exampleFixedPtOperStructFixedPtArrayColumnIndex
      Integer32,
   exampleFixedPtOperStructFixedPtArrayValue
      FixedPoint3 }

exampleFixedPtOperStructFixedPtArrayRowIndex OBJECT-TYPE
   SYNTAX     Integer32 (0..2)
   ACCESS     not-accessible
   STATUS     mandatory
   DESCRIPTION
     "This variable represents the next to last index for the 
      exampleFixedPtOperStructFixedPtArrayTable."
::= { exampleFixedPtOperStructFixedPtArrayEntry 1 }

exampleFixedPtOperStructFixedPtArrayColumnIndex OBJECT-TYPE
   SYNTAX     Integer32 (0..3)
   ACCESS     not-accessible
   STATUS     mandatory
   DESCRIPTION
     "This variable represents the final index for the 
      exampleFixedPtOperStructFixedPtArrayTable."
::= { exampleFixedPtOperStructFixedPtArrayEntry 2 }

exampleFixedPtOperStructFixedPtArrayValue OBJECT-TYPE
   SYNTAX     FixedPoint3 (80..255880)
   ACCESS     read-write
   STATUS     mandatory
   DESCRIPTION
     "This variable represents an individual value for the
      exampleFixedPtOperStructFixedPtArrayTable."
::= { exampleFixedPtOperStructFixedPtArrayEntry 3 }

exampleFixedPtOperFreeFixedPtVectorTable OBJECT-TYPE
   SYNTAX     SEQUENCE OF ExampleFixedPtOperFreeFixedPtVectorEntry
   ACCESS     not-accessible
   STATUS     mandatory
   DESCRIPTION
     ""
::= { exampleFixedPt 1030 }

exampleFixedPtOperFreeFixedPtVectorEntry OBJECT-TYPE
   SYNTAX     ExampleFixedPtOperFreeFixedPtVectorEntry
   ACCESS     not-accessible
   STATUS     mandatory
   DESCRIPTION
     "An entry in the exampleFixedPtOperFreeFixedPtVectorTable."
   INDEX {
      exampleIndex,
      exampleFixedPtIndex,
      exampleFixedPtOperFreeFixedPtVectorIndex }
::= { exampleFixedPtOperFreeFixedPtVectorTable 1 }

ExampleFixedPtOperFreeFixedPtVectorEntry ::= SEQUENCE {
   exampleFixedPtOperFreeFixedPtVectorIndex
      Integer32,
   exampleFixedPtOperFreeFixedPtVectorValue
      FixedPoint2 }

exampleFixedPtOperFreeFixedPtVectorIndex OBJECT-TYPE
   SYNTAX     Integer32 (0..9)
   ACCESS     not-accessible
   STATUS     mandatory
   DESCRIPTION
     "This variable represents the exampleFixedPtOperFreeFixedPtVectorTable
      specific index for the exampleFixedPtOperFreeFixedPtVectorTable."
::= { exampleFixedPtOperFreeFixedPtVectorEntry 1 }

exampleFixedPtOperFreeFixedPtVectorValue OBJECT-TYPE
   SYNTAX     FixedPoint2 (0..10000)
   ACCESS     read-write
   STATUS     mandatory
   DESCRIPTION
     "This variable represents an individual value for the
      exampleFixedPtOperFreeFixedPtVectorTable."
::= { exampleFixedPtOperFreeFixedPtVectorEntry 2 }

exampleFixedPtOperFreeFixedPtArrayTable OBJECT-TYPE
   SYNTAX     SEQUENCE OF ExampleFixedPtOperFreeFixedPtArrayEntry
   ACCESS     not-accessible
   STATUS     mandatory
   DESCRIPTION
     ""
::= { exampleFixedPt 1031 }

exampleFixedPtOperFreeFixedPtArrayEntry OBJECT-TYPE
   SYNTAX     ExampleFixedPtOperFreeFixedPtArrayEntry
   ACCESS     not-accessible
   STATUS     mandatory
   DESCRIPTION
     "An entry in the exampleFixedPtOperFreeFixedPtArrayTable."
   INDEX {
      exampleIndex,
      exampleFixedPtIndex,
      exampleFixedPtOperFreeFixedPtArrayRowIndex,
      exampleFixedPtOperFreeFixedPtArrayColumnIndex }
::= { exampleFixedPtOperFreeFixedPtArrayTable 1 }

ExampleFixedPtOperFreeFixedPtArrayEntry ::= SEQUENCE {
   exampleFixedPtOperFreeFixedPtArrayRowIndex
      Integer32,
   exampleFixedPtOperFreeFixedPtArrayColumnIndex
      Integer32,
   exampleFixedPtOperFreeFixedPtArrayValue
      FixedPoint3 }

exampleFixedPtOperFreeFixedPtArrayRowIndex OBJECT-TYPE
   SYNTAX     Integer32 (0..2)
   ACCESS     not-accessible
   STATUS     mandatory
   DESCRIPTION
     "This variable represents the next to last index for the 
      exampleFixedPtOperFreeFixedPtArrayTable."
::= { exampleFixedPtOperFreeFixedPtArrayEntry 1 }

exampleFixedPtOperFreeFixedPtArrayColumnIndex OBJECT-TYPE
   SYNTAX     Integer32 (0..3)
   ACCESS     not-accessible
   STATUS     mandatory
   DESCRIPTION
     "This variable represents the final index for the 
      exampleFixedPtOperFreeFixedPtArrayTable."
::= { exampleFixedPtOperFreeFixedPtArrayEntry 2 }

exampleFixedPtOperFreeFixedPtArrayValue OBJECT-TYPE
   SYNTAX     FixedPoint3 (255)
   ACCESS     read-write
   STATUS     mandatory
   DESCRIPTION
     "This variable represents an individual value for the
      exampleFixedPtOperFreeFixedPtArrayTable."
::= { exampleFixedPtOperFreeFixedPtArrayEntry 3 }

exampleFixedPtOperFreeFixedPtReplicatedTable OBJECT-TYPE
   SYNTAX     SEQUENCE OF ExampleFixedPtOperFreeFixedPtReplicatedEntry
   ACCESS     not-accessible
   STATUS     mandatory
   DESCRIPTION
     ""
::= { exampleFixedPt 1032 }

exampleFixedPtOperFreeFixedPtReplicatedEntry OBJECT-TYPE
   SYNTAX     ExampleFixedPtOperFreeFixedPtReplicatedEntry
   ACCESS     not-accessible
   STATUS     mandatory
   DESCRIPTION
     "An entry in the exampleFixedPtOperFreeFixedPtReplicatedTable."
   INDEX {
      exampleIndex,
      exampleFixedPtIndex,
      exampleFixedPtOperFreeFixedPtReplicatedIndex }
::= { exampleFixedPtOperFreeFixedPtReplicatedTable 1 }

ExampleFixedPtOperFreeFixedPtReplicatedEntry ::= SEQUENCE {
   exampleFixedPtOperFreeFixedPtReplicatedIndex
      Integer32,
   exampleFixedPtOperFreeFixedPtReplicatedValue
      FixedPoint1,
   exampleFixedPtOperFreeFixedPtReplicatedRowStatus
      RowStatus }

exampleFixedPtOperFreeFixedPtReplicatedIndex OBJECT-TYPE
   SYNTAX     Integer32 (0..9)
   ACCESS     not-accessible
   STATUS     mandatory
   DESCRIPTION
     "This variable represents the index for the exampleFixedPtOperFreeFixedPtReplicatedTable."
::= { exampleFixedPtOperFreeFixedPtReplicatedEntry 1 }

exampleFixedPtOperFreeFixedPtReplicatedValue OBJECT-TYPE
   SYNTAX     FixedPoint1 (0..655350)
   ACCESS     read-write
   STATUS     mandatory
   DESCRIPTION
     "This variable represents an individual value for the
      exampleFixedPtOperFreeFixedPtReplicatedTable."
::= { exampleFixedPtOperFreeFixedPtReplicatedEntry 2 }

exampleFixedPtOperFreeFixedPtReplicatedRowStatus OBJECT-TYPE
   SYNTAX     RowStatus 
   ACCESS     write-only
   STATUS     mandatory
   DESCRIPTION
     "This variable is used to control the addition and deletion 
      of individual values of the exampleFixedPtOperFreeFixedPtReplicatedTable."
::= { exampleFixedPtOperFreeFixedPtReplicatedEntry 3 }

exampleFixedPtOperFreeFixedPtListTable OBJECT-TYPE
   SYNTAX     SEQUENCE OF ExampleFixedPtOperFreeFixedPtListEntry
   ACCESS     not-accessible
   STATUS     mandatory
   DESCRIPTION
     ""
::= { exampleFixedPt 1033 }

exampleFixedPtOperFreeFixedPtListEntry OBJECT-TYPE
   SYNTAX     ExampleFixedPtOperFreeFixedPtListEntry
   ACCESS     not-accessible
   STATUS     mandatory
   DESCRIPTION
     "An entry in the exampleFixedPtOperFreeFixedPtListTable."
   INDEX {
      exampleIndex,
      exampleFixedPtIndex,
      exampleFixedPtOperFreeFixedPtListValue }
::= { exampleFixedPtOperFreeFixedPtListTable 1 }

ExampleFixedPtOperFreeFixedPtListEntry ::= SEQUENCE {
   exampleFixedPtOperFreeFixedPtListValue
      Integer32,
   exampleFixedPtOperFreeFixedPtListRowStatus
      RowStatus }

exampleFixedPtOperFreeFixedPtListValue OBJECT-TYPE
   SYNTAX     Integer32 (0..100 | 10000..20000)
   ACCESS     read-write
   STATUS     mandatory
   DESCRIPTION
     "This variable represents both the value and the index for the
      exampleFixedPtOperFreeFixedPtListTable."
::= { exampleFixedPtOperFreeFixedPtListEntry 1 }

exampleFixedPtOperFreeFixedPtListRowStatus OBJECT-TYPE
   SYNTAX     RowStatus 
   ACCESS     write-only
   STATUS     mandatory
   DESCRIPTION
     "This variable is used to control the addition and deletion 
      of individual values of the exampleFixedPtOperFreeFixedPtListTable."
::= { exampleFixedPtOperFreeFixedPtListEntry 2 }

exampleFixedPtProvStructFixedPtVectorTable OBJECT-TYPE
   SYNTAX     SEQUENCE OF ExampleFixedPtProvStructFixedPtVectorEntry
   ACCESS     not-accessible
   STATUS     mandatory
   DESCRIPTION
     ""
::= { exampleFixedPt 1034 }

exampleFixedPtProvStructFixedPtVectorEntry OBJECT-TYPE
   SYNTAX     ExampleFixedPtProvStructFixedPtVectorEntry
   ACCESS     not-accessible
   STATUS     mandatory
   DESCRIPTION
     "An entry in the exampleFixedPtProvStructFixedPtVectorTable."
   INDEX {
      exampleIndex,
      exampleFixedPtIndex,
      exampleFixedPtProvStructFixedPtVectorIndex }
::= { exampleFixedPtProvStructFixedPtVectorTable 1 }

ExampleFixedPtProvStructFixedPtVectorEntry ::= SEQUENCE {
   exampleFixedPtProvStructFixedPtVectorIndex
      Integer32,
   exampleFixedPtProvStructFixedPtVectorValue
      FixedPoint3 }

exampleFixedPtProvStructFixedPtVectorIndex OBJECT-TYPE
   SYNTAX     Integer32 (0..9)
   ACCESS     not-accessible
   STATUS     mandatory
   DESCRIPTION
     "This variable represents the exampleFixedPtProvStructFixedPtVectorTable
      specific index for the exampleFixedPtProvStructFixedPtVectorTable."
::= { exampleFixedPtProvStructFixedPtVectorEntry 1 }

exampleFixedPtProvStructFixedPtVectorValue OBJECT-TYPE
   SYNTAX     FixedPoint3 (0..100100)
   ACCESS     read-write
   STATUS     mandatory
   DESCRIPTION
     "This variable represents an individual value for the
      exampleFixedPtProvStructFixedPtVectorTable."
::= { exampleFixedPtProvStructFixedPtVectorEntry 2 }

exampleFixedPtProvStructFixedPtArrayTable OBJECT-TYPE
   SYNTAX     SEQUENCE OF ExampleFixedPtProvStructFixedPtArrayEntry
   ACCESS     not-accessible
   STATUS     mandatory
   DESCRIPTION
     ""
::= { exampleFixedPt 1035 }

exampleFixedPtProvStructFixedPtArrayEntry OBJECT-TYPE
   SYNTAX     ExampleFixedPtProvStructFixedPtArrayEntry
   ACCESS     not-accessible
   STATUS     mandatory
   DESCRIPTION
     "An entry in the exampleFixedPtProvStructFixedPtArrayTable."
   INDEX {
      exampleIndex,
      exampleFixedPtIndex,
      exampleFixedPtProvStructFixedPtArrayRowIndex,
      exampleFixedPtProvStructFixedPtArrayColumnIndex }
::= { exampleFixedPtProvStructFixedPtArrayTable 1 }

ExampleFixedPtProvStructFixedPtArrayEntry ::= SEQUENCE {
   exampleFixedPtProvStructFixedPtArrayRowIndex
      Integer32,
   exampleFixedPtProvStructFixedPtArrayColumnIndex
      Integer32,
   exampleFixedPtProvStructFixedPtArrayValue
      FixedPoint1 }

exampleFixedPtProvStructFixedPtArrayRowIndex OBJECT-TYPE
   SYNTAX     Integer32 (0..2)
   ACCESS     not-accessible
   STATUS     mandatory
   DESCRIPTION
     "This variable represents the next to last index for the 
      exampleFixedPtProvStructFixedPtArrayTable."
::= { exampleFixedPtProvStructFixedPtArrayEntry 1 }

exampleFixedPtProvStructFixedPtArrayColumnIndex OBJECT-TYPE
   SYNTAX     Integer32 (0..3)
   ACCESS     not-accessible
   STATUS     mandatory
   DESCRIPTION
     "This variable represents the final index for the 
      exampleFixedPtProvStructFixedPtArrayTable."
::= { exampleFixedPtProvStructFixedPtArrayEntry 2 }

exampleFixedPtProvStructFixedPtArrayValue OBJECT-TYPE
   SYNTAX     FixedPoint1 (255..300)
   ACCESS     read-write
   STATUS     mandatory
   DESCRIPTION
     "This variable represents an individual value for the
      exampleFixedPtProvStructFixedPtArrayTable."
::= { exampleFixedPtProvStructFixedPtArrayEntry 3 }

exampleFixedPtProvFreeFixedPtVectorTable OBJECT-TYPE
   SYNTAX     SEQUENCE OF ExampleFixedPtProvFreeFixedPtVectorEntry
   ACCESS     not-accessible
   STATUS     mandatory
   DESCRIPTION
     ""
::= { exampleFixedPt 1036 }

exampleFixedPtProvFreeFixedPtVectorEntry OBJECT-TYPE
   SYNTAX     ExampleFixedPtProvFreeFixedPtVectorEntry
   ACCESS     not-accessible
   STATUS     mandatory
   DESCRIPTION
     "An entry in the exampleFixedPtProvFreeFixedPtVectorTable."
   INDEX {
      exampleIndex,
      exampleFixedPtIndex,
      exampleFixedPtProvFreeFixedPtVectorIndex }
::= { exampleFixedPtProvFreeFixedPtVectorTable 1 }

ExampleFixedPtProvFreeFixedPtVectorEntry ::= SEQUENCE {
   exampleFixedPtProvFreeFixedPtVectorIndex
      Integer32,
   exampleFixedPtProvFreeFixedPtVectorValue
      FixedPoint1 }

exampleFixedPtProvFreeFixedPtVectorIndex OBJECT-TYPE
   SYNTAX     Integer32 (0..9)
   ACCESS     not-accessible
   STATUS     mandatory
   DESCRIPTION
     "This variable represents the exampleFixedPtProvFreeFixedPtVectorTable
      specific index for the exampleFixedPtProvFreeFixedPtVectorTable."
::= { exampleFixedPtProvFreeFixedPtVectorEntry 1 }

exampleFixedPtProvFreeFixedPtVectorValue OBJECT-TYPE
   SYNTAX     FixedPoint1 (0..1000)
   ACCESS     read-write
   STATUS     mandatory
   DESCRIPTION
     "This variable represents an individual value for the
      exampleFixedPtProvFreeFixedPtVectorTable."
::= { exampleFixedPtProvFreeFixedPtVectorEntry 2 }

exampleFixedPtProvFreeFixedPtArrayTable OBJECT-TYPE
   SYNTAX     SEQUENCE OF ExampleFixedPtProvFreeFixedPtArrayEntry
   ACCESS     not-accessible
   STATUS     mandatory
   DESCRIPTION
     ""
::= { exampleFixedPt 1037 }

exampleFixedPtProvFreeFixedPtArrayEntry OBJECT-TYPE
   SYNTAX     ExampleFixedPtProvFreeFixedPtArrayEntry
   ACCESS     not-accessible
   STATUS     mandatory
   DESCRIPTION
     "An entry in the exampleFixedPtProvFreeFixedPtArrayTable."
   INDEX {
      exampleIndex,
      exampleFixedPtIndex,
      exampleFixedPtProvFreeFixedPtArrayRowIndex,
      exampleFixedPtProvFreeFixedPtArrayColumnIndex }
::= { exampleFixedPtProvFreeFixedPtArrayTable 1 }

ExampleFixedPtProvFreeFixedPtArrayEntry ::= SEQUENCE {
   exampleFixedPtProvFreeFixedPtArrayRowIndex
      Integer32,
   exampleFixedPtProvFreeFixedPtArrayColumnIndex
      Integer32,
   exampleFixedPtProvFreeFixedPtArrayValue
      FixedPoint2 }

exampleFixedPtProvFreeFixedPtArrayRowIndex OBJECT-TYPE
   SYNTAX     Integer32 (0..2)
   ACCESS     not-accessible
   STATUS     mandatory
   DESCRIPTION
     "This variable represents the next to last index for the 
      exampleFixedPtProvFreeFixedPtArrayTable."
::= { exampleFixedPtProvFreeFixedPtArrayEntry 1 }

exampleFixedPtProvFreeFixedPtArrayColumnIndex OBJECT-TYPE
   SYNTAX     Integer32 (0..3)
   ACCESS     not-accessible
   STATUS     mandatory
   DESCRIPTION
     "This variable represents the final index for the 
      exampleFixedPtProvFreeFixedPtArrayTable."
::= { exampleFixedPtProvFreeFixedPtArrayEntry 2 }

exampleFixedPtProvFreeFixedPtArrayValue OBJECT-TYPE
   SYNTAX     FixedPoint2 (0..25555)
   ACCESS     read-write
   STATUS     mandatory
   DESCRIPTION
     "This variable represents an individual value for the
      exampleFixedPtProvFreeFixedPtArrayTable."
::= { exampleFixedPtProvFreeFixedPtArrayEntry 3 }

exampleFixedPtProvFreeFixedPtReplicatedTable OBJECT-TYPE
   SYNTAX     SEQUENCE OF ExampleFixedPtProvFreeFixedPtReplicatedEntry
   ACCESS     not-accessible
   STATUS     mandatory
   DESCRIPTION
     ""
::= { exampleFixedPt 1038 }

exampleFixedPtProvFreeFixedPtReplicatedEntry OBJECT-TYPE
   SYNTAX     ExampleFixedPtProvFreeFixedPtReplicatedEntry
   ACCESS     not-accessible
   STATUS     mandatory
   DESCRIPTION
     "An entry in the exampleFixedPtProvFreeFixedPtReplicatedTable."
   INDEX {
      exampleIndex,
      exampleFixedPtIndex,
      exampleFixedPtProvFreeFixedPtReplicatedIndex }
::= { exampleFixedPtProvFreeFixedPtReplicatedTable 1 }

ExampleFixedPtProvFreeFixedPtReplicatedEntry ::= SEQUENCE {
   exampleFixedPtProvFreeFixedPtReplicatedIndex
      Integer32,
   exampleFixedPtProvFreeFixedPtReplicatedValue
      FixedPoint2,
   exampleFixedPtProvFreeFixedPtReplicatedRowStatus
      RowStatus }

exampleFixedPtProvFreeFixedPtReplicatedIndex OBJECT-TYPE
   SYNTAX     Integer32 (0..9)
   ACCESS     not-accessible
   STATUS     mandatory
   DESCRIPTION
     "This variable represents the index for the exampleFixedPtProvFreeFixedPtReplicatedTable."
::= { exampleFixedPtProvFreeFixedPtReplicatedEntry 1 }

exampleFixedPtProvFreeFixedPtReplicatedValue OBJECT-TYPE
   SYNTAX     FixedPoint2 (0..65535)
   ACCESS     read-write
   STATUS     mandatory
   DESCRIPTION
     "This variable represents an individual value for the
      exampleFixedPtProvFreeFixedPtReplicatedTable."
::= { exampleFixedPtProvFreeFixedPtReplicatedEntry 2 }

exampleFixedPtProvFreeFixedPtReplicatedRowStatus OBJECT-TYPE
   SYNTAX     RowStatus 
   ACCESS     write-only
   STATUS     mandatory
   DESCRIPTION
     "This variable is used to control the addition and deletion 
      of individual values of the exampleFixedPtProvFreeFixedPtReplicatedTable."
::= { exampleFixedPtProvFreeFixedPtReplicatedEntry 3 }

exampleFixedPtProvFreeFixedPtListTable OBJECT-TYPE
   SYNTAX     SEQUENCE OF ExampleFixedPtProvFreeFixedPtListEntry
   ACCESS     not-accessible
   STATUS     mandatory
   DESCRIPTION
     ""
::= { exampleFixedPt 1039 }

exampleFixedPtProvFreeFixedPtListEntry OBJECT-TYPE
   SYNTAX     ExampleFixedPtProvFreeFixedPtListEntry
   ACCESS     not-accessible
   STATUS     mandatory
   DESCRIPTION
     "An entry in the exampleFixedPtProvFreeFixedPtListTable."
   INDEX {
      exampleIndex,
      exampleFixedPtIndex,
      exampleFixedPtProvFreeFixedPtListValue }
::= { exampleFixedPtProvFreeFixedPtListTable 1 }

ExampleFixedPtProvFreeFixedPtListEntry ::= SEQUENCE {
   exampleFixedPtProvFreeFixedPtListValue
      Integer32,
   exampleFixedPtProvFreeFixedPtListRowStatus
      RowStatus }

exampleFixedPtProvFreeFixedPtListValue OBJECT-TYPE
   SYNTAX     Integer32 (100..100000)
   ACCESS     read-write
   STATUS     mandatory
   DESCRIPTION
     "This variable represents both the value and the index for the
      exampleFixedPtProvFreeFixedPtListTable."
::= { exampleFixedPtProvFreeFixedPtListEntry 1 }

exampleFixedPtProvFreeFixedPtListRowStatus OBJECT-TYPE
   SYNTAX     RowStatus 
   ACCESS     write-only
   STATUS     mandatory
   DESCRIPTION
     "This variable is used to control the addition and deletion 
      of individual values of the exampleFixedPtProvFreeFixedPtListTable."
::= { exampleFixedPtProvFreeFixedPtListEntry 2 }



exampleDashed OBJECT IDENTIFIER ::= { example 7 }



exampleDashedRowStatusTable OBJECT-TYPE
   SYNTAX     SEQUENCE OF ExampleDashedRowStatusEntry
   ACCESS     not-accessible
   STATUS     mandatory
   DESCRIPTION
     "This entry controls the addition and deletion of 
      exampleDashed components."
::= { exampleDashed 1 }

exampleDashedRowStatusEntry OBJECT-TYPE
   SYNTAX     ExampleDashedRowStatusEntry
   ACCESS     not-accessible
   STATUS     mandatory
   DESCRIPTION
     "A single entry in the table represents a single 
      exampleDashed component."
   INDEX {
      exampleIndex,
      exampleDashedIndex }
::= { exampleDashedRowStatusTable 1 }

ExampleDashedRowStatusEntry ::= SEQUENCE {
   exampleDashedRowStatus
      RowStatus,
   exampleDashedComponentName
      DisplayString,
   exampleDashedStorageType
      StorageType,
   exampleDashedIndex
      DashedHexString }

exampleDashedRowStatus OBJECT-TYPE
   SYNTAX     RowStatus 
   ACCESS     read-write
   STATUS     mandatory
   DESCRIPTION
     "This variable is used as the basis for SNMP naming of
      exampleDashed components.
      These components can be added and deleted."
::= { exampleDashedRowStatusEntry 1 }

exampleDashedComponentName OBJECT-TYPE
   SYNTAX     DisplayString 
   ACCESS     read-only
   STATUS     mandatory
   DESCRIPTION
     "This variable provides the component's string name for
      use with the ASCII Console Interface"
::= { exampleDashedRowStatusEntry 2 }

exampleDashedStorageType OBJECT-TYPE
   SYNTAX     StorageType 
   ACCESS     read-only
   STATUS     mandatory
   DESCRIPTION
     "This variable represents the storage type value for the
      exampleDashed tables."
::= { exampleDashedRowStatusEntry 4 }

exampleDashedIndex OBJECT-TYPE
   SYNTAX     DashedHexString (SIZE (1..10))
   ACCESS     not-accessible
   STATUS     mandatory
   DESCRIPTION
     "This variable represents the index for the exampleDashed tables."
::= { exampleDashedRowStatusEntry 10 }

exampleDashedOperationalTable OBJECT-TYPE
   SYNTAX     SEQUENCE OF ExampleDashedOperationalEntry
   ACCESS     not-accessible
   STATUS     mandatory
   DESCRIPTION
     ""
::= { exampleDashed 10 }

exampleDashedOperationalEntry OBJECT-TYPE
   SYNTAX     ExampleDashedOperationalEntry
   ACCESS     not-accessible
   STATUS     mandatory
   DESCRIPTION
     "An entry in the exampleDashedOperationalTable."
   INDEX {
      exampleIndex,
      exampleDashedIndex }
::= { exampleDashedOperationalTable 1 }

ExampleDashedOperationalEntry ::= SEQUENCE {
   exampleDashedOperStructDashed
      DashedHexString,
   exampleDashedOperFreeDashed
      DashedHexString }

exampleDashedOperStructDashed OBJECT-TYPE
   SYNTAX     DashedHexString (SIZE (1..10))
   ACCESS     read-write
   STATUS     mandatory
   DESCRIPTION
     ""
::= { exampleDashedOperationalEntry 1 }

exampleDashedOperFreeDashed OBJECT-TYPE
   SYNTAX     DashedHexString (SIZE (1..10))
   ACCESS     read-write
   STATUS     mandatory
   DESCRIPTION
     ""
   DEFVAL     { '123456'H }
::= { exampleDashedOperationalEntry 2 }

exampleDashedProvisionalTable OBJECT-TYPE
   SYNTAX     SEQUENCE OF ExampleDashedProvisionalEntry
   ACCESS     not-accessible
   STATUS     mandatory
   DESCRIPTION
     ""
::= { exampleDashed 11 }

exampleDashedProvisionalEntry OBJECT-TYPE
   SYNTAX     ExampleDashedProvisionalEntry
   ACCESS     not-accessible
   STATUS     mandatory
   DESCRIPTION
     "An entry in the exampleDashedProvisionalTable."
   INDEX {
      exampleIndex,
      exampleDashedIndex }
::= { exampleDashedProvisionalTable 1 }

ExampleDashedProvisionalEntry ::= SEQUENCE {
   exampleDashedProvStructDashed
      DashedHexString,
   exampleDashedProvFreeDashed
      DashedHexString }

exampleDashedProvStructDashed OBJECT-TYPE
   SYNTAX     DashedHexString (SIZE (1..10))
   ACCESS     read-write
   STATUS     mandatory
   DESCRIPTION
     ""
::= { exampleDashedProvisionalEntry 1 }

exampleDashedProvFreeDashed OBJECT-TYPE
   SYNTAX     DashedHexString (SIZE (1..10))
   ACCESS     read-write
   STATUS     mandatory
   DESCRIPTION
     ""
   DEFVAL     { '123456'H }
::= { exampleDashedProvisionalEntry 2 }

exampleDashedOsDashedArrayTable OBJECT-TYPE
   SYNTAX     SEQUENCE OF ExampleDashedOsDashedArrayEntry
   ACCESS     not-accessible
   STATUS     mandatory
   DESCRIPTION
     ""
::= { exampleDashed 1088 }

exampleDashedOsDashedArrayEntry OBJECT-TYPE
   SYNTAX     ExampleDashedOsDashedArrayEntry
   ACCESS     not-accessible
   STATUS     mandatory
   DESCRIPTION
     "An entry in the exampleDashedOsDashedArrayTable."
   INDEX {
      exampleIndex,
      exampleDashedIndex,
      exampleDashedOsDashedArrayRowIndex,
      exampleDashedOsDashedArrayColumnIndex }
::= { exampleDashedOsDashedArrayTable 1 }

ExampleDashedOsDashedArrayEntry ::= SEQUENCE {
   exampleDashedOsDashedArrayRowIndex
      Integer32,
   exampleDashedOsDashedArrayColumnIndex
      Integer32,
   exampleDashedOsDashedArrayValue
      DashedHexString }

exampleDashedOsDashedArrayRowIndex OBJECT-TYPE
   SYNTAX     Integer32 (0..2)
   ACCESS     not-accessible
   STATUS     mandatory
   DESCRIPTION
     "This variable represents the next to last index for the 
      exampleDashedOsDashedArrayTable."
::= { exampleDashedOsDashedArrayEntry 1 }

exampleDashedOsDashedArrayColumnIndex OBJECT-TYPE
   SYNTAX     Integer32 (0..3)
   ACCESS     not-accessible
   STATUS     mandatory
   DESCRIPTION
     "This variable represents the final index for the 
      exampleDashedOsDashedArrayTable."
::= { exampleDashedOsDashedArrayEntry 2 }

exampleDashedOsDashedArrayValue OBJECT-TYPE
   SYNTAX     DashedHexString (SIZE (1..5))
   ACCESS     read-write
   STATUS     mandatory
   DESCRIPTION
     "This variable represents an individual value for the
      exampleDashedOsDashedArrayTable."
::= { exampleDashedOsDashedArrayEntry 3 }

exampleDashedOsDashedVectorTable OBJECT-TYPE
   SYNTAX     SEQUENCE OF ExampleDashedOsDashedVectorEntry
   ACCESS     not-accessible
   STATUS     mandatory
   DESCRIPTION
     ""
::= { exampleDashed 1089 }

exampleDashedOsDashedVectorEntry OBJECT-TYPE
   SYNTAX     ExampleDashedOsDashedVectorEntry
   ACCESS     not-accessible
   STATUS     mandatory
   DESCRIPTION
     "An entry in the exampleDashedOsDashedVectorTable."
   INDEX {
      exampleIndex,
      exampleDashedIndex,
      exampleDashedOsDashedVectorIndex }
::= { exampleDashedOsDashedVectorTable 1 }

ExampleDashedOsDashedVectorEntry ::= SEQUENCE {
   exampleDashedOsDashedVectorIndex
      Integer32,
   exampleDashedOsDashedVectorValue
      DashedHexString }

exampleDashedOsDashedVectorIndex OBJECT-TYPE
   SYNTAX     Integer32 (0..9)
   ACCESS     not-accessible
   STATUS     mandatory
   DESCRIPTION
     "This variable represents the exampleDashedOsDashedVectorTable
      specific index for the exampleDashedOsDashedVectorTable."
::= { exampleDashedOsDashedVectorEntry 1 }

exampleDashedOsDashedVectorValue OBJECT-TYPE
   SYNTAX     DashedHexString (SIZE (1..5))
   ACCESS     read-write
   STATUS     mandatory
   DESCRIPTION
     "This variable represents an individual value for the
      exampleDashedOsDashedVectorTable."
::= { exampleDashedOsDashedVectorEntry 2 }

exampleDashedOfDashedListTable OBJECT-TYPE
   SYNTAX     SEQUENCE OF ExampleDashedOfDashedListEntry
   ACCESS     not-accessible
   STATUS     mandatory
   DESCRIPTION
     ""
::= { exampleDashed 1090 }

exampleDashedOfDashedListEntry OBJECT-TYPE
   SYNTAX     ExampleDashedOfDashedListEntry
   ACCESS     not-accessible
   STATUS     mandatory
   DESCRIPTION
     "An entry in the exampleDashedOfDashedListTable."
   INDEX {
      exampleIndex,
      exampleDashedIndex,
      exampleDashedOfDashedListValue }
::= { exampleDashedOfDashedListTable 1 }

ExampleDashedOfDashedListEntry ::= SEQUENCE {
   exampleDashedOfDashedListValue
      DashedHexString,
   exampleDashedOfDashedListRowStatus
      RowStatus }

exampleDashedOfDashedListValue OBJECT-TYPE
   SYNTAX     DashedHexString (SIZE (1..5))
   ACCESS     read-write
   STATUS     mandatory
   DESCRIPTION
     "This variable represents both the value and the index for the
      exampleDashedOfDashedListTable."
::= { exampleDashedOfDashedListEntry 1 }

exampleDashedOfDashedListRowStatus OBJECT-TYPE
   SYNTAX     RowStatus 
   ACCESS     write-only
   STATUS     mandatory
   DESCRIPTION
     "This variable is used to control the addition and deletion 
      of individual values of the exampleDashedOfDashedListTable."
::= { exampleDashedOfDashedListEntry 2 }

exampleDashedOfDashedReplicatedTable OBJECT-TYPE
   SYNTAX     SEQUENCE OF ExampleDashedOfDashedReplicatedEntry
   ACCESS     not-accessible
   STATUS     mandatory
   DESCRIPTION
     ""
::= { exampleDashed 1091 }

exampleDashedOfDashedReplicatedEntry OBJECT-TYPE
   SYNTAX     ExampleDashedOfDashedReplicatedEntry
   ACCESS     not-accessible
   STATUS     mandatory
   DESCRIPTION
     "An entry in the exampleDashedOfDashedReplicatedTable."
   INDEX {
      exampleIndex,
      exampleDashedIndex,
      exampleDashedOfDashedReplicatedIndex }
::= { exampleDashedOfDashedReplicatedTable 1 }

ExampleDashedOfDashedReplicatedEntry ::= SEQUENCE {
   exampleDashedOfDashedReplicatedIndex
      DashedHexString,
   exampleDashedOfDashedReplicatedValue
      DashedHexString,
   exampleDashedOfDashedReplicatedRowStatus
      RowStatus }

exampleDashedOfDashedReplicatedIndex OBJECT-TYPE
   SYNTAX     DashedHexString (SIZE (1..5))
   ACCESS     not-accessible
   STATUS     mandatory
   DESCRIPTION
     "This variable represents the index for the exampleDashedOfDashedReplicatedTable."
::= { exampleDashedOfDashedReplicatedEntry 1 }

exampleDashedOfDashedReplicatedValue OBJECT-TYPE
   SYNTAX     DashedHexString (SIZE (1..10))
   ACCESS     read-write
   STATUS     mandatory
   DESCRIPTION
     "This variable represents an individual value for the
      exampleDashedOfDashedReplicatedTable."
::= { exampleDashedOfDashedReplicatedEntry 2 }

exampleDashedOfDashedReplicatedRowStatus OBJECT-TYPE
   SYNTAX     RowStatus 
   ACCESS     write-only
   STATUS     mandatory
   DESCRIPTION
     "This variable is used to control the addition and deletion 
      of individual values of the exampleDashedOfDashedReplicatedTable."
::= { exampleDashedOfDashedReplicatedEntry 3 }

exampleDashedOfDashedArrayTable OBJECT-TYPE
   SYNTAX     SEQUENCE OF ExampleDashedOfDashedArrayEntry
   ACCESS     not-accessible
   STATUS     mandatory
   DESCRIPTION
     ""
::= { exampleDashed 1092 }

exampleDashedOfDashedArrayEntry OBJECT-TYPE
   SYNTAX     ExampleDashedOfDashedArrayEntry
   ACCESS     not-accessible
   STATUS     mandatory
   DESCRIPTION
     "An entry in the exampleDashedOfDashedArrayTable."
   INDEX {
      exampleIndex,
      exampleDashedIndex,
      exampleDashedOfDashedArrayRowIndex,
      exampleDashedOfDashedArrayColumnIndex }
::= { exampleDashedOfDashedArrayTable 1 }

ExampleDashedOfDashedArrayEntry ::= SEQUENCE {
   exampleDashedOfDashedArrayRowIndex
      Integer32,
   exampleDashedOfDashedArrayColumnIndex
      Integer32,
   exampleDashedOfDashedArrayValue
      DashedHexString }

exampleDashedOfDashedArrayRowIndex OBJECT-TYPE
   SYNTAX     Integer32 (0..2)
   ACCESS     not-accessible
   STATUS     mandatory
   DESCRIPTION
     "This variable represents the next to last index for the 
      exampleDashedOfDashedArrayTable."
::= { exampleDashedOfDashedArrayEntry 1 }

exampleDashedOfDashedArrayColumnIndex OBJECT-TYPE
   SYNTAX     Integer32 (0..3)
   ACCESS     not-accessible
   STATUS     mandatory
   DESCRIPTION
     "This variable represents the final index for the 
      exampleDashedOfDashedArrayTable."
::= { exampleDashedOfDashedArrayEntry 2 }

exampleDashedOfDashedArrayValue OBJECT-TYPE
   SYNTAX     DashedHexString (SIZE (1..5))
   ACCESS     read-write
   STATUS     mandatory
   DESCRIPTION
     "This variable represents an individual value for the
      exampleDashedOfDashedArrayTable."
::= { exampleDashedOfDashedArrayEntry 3 }

exampleDashedOfDashedVectorTable OBJECT-TYPE
   SYNTAX     SEQUENCE OF ExampleDashedOfDashedVectorEntry
   ACCESS     not-accessible
   STATUS     mandatory
   DESCRIPTION
     ""
::= { exampleDashed 1093 }

exampleDashedOfDashedVectorEntry OBJECT-TYPE
   SYNTAX     ExampleDashedOfDashedVectorEntry
   ACCESS     not-accessible
   STATUS     mandatory
   DESCRIPTION
     "An entry in the exampleDashedOfDashedVectorTable."
   INDEX {
      exampleIndex,
      exampleDashedIndex,
      exampleDashedOfDashedVectorIndex }
::= { exampleDashedOfDashedVectorTable 1 }

ExampleDashedOfDashedVectorEntry ::= SEQUENCE {
   exampleDashedOfDashedVectorIndex
      Integer32,
   exampleDashedOfDashedVectorValue
      DashedHexString }

exampleDashedOfDashedVectorIndex OBJECT-TYPE
   SYNTAX     Integer32 (0..9)
   ACCESS     not-accessible
   STATUS     mandatory
   DESCRIPTION
     "This variable represents the exampleDashedOfDashedVectorTable
      specific index for the exampleDashedOfDashedVectorTable."
::= { exampleDashedOfDashedVectorEntry 1 }

exampleDashedOfDashedVectorValue OBJECT-TYPE
   SYNTAX     DashedHexString (SIZE (1..5))
   ACCESS     read-write
   STATUS     mandatory
   DESCRIPTION
     "This variable represents an individual value for the
      exampleDashedOfDashedVectorTable."
::= { exampleDashedOfDashedVectorEntry 2 }

exampleDashedProvStructDashedArrayTable OBJECT-TYPE
   SYNTAX     SEQUENCE OF ExampleDashedProvStructDashedArrayEntry
   ACCESS     not-accessible
   STATUS     mandatory
   DESCRIPTION
     ""
::= { exampleDashed 1094 }

exampleDashedProvStructDashedArrayEntry OBJECT-TYPE
   SYNTAX     ExampleDashedProvStructDashedArrayEntry
   ACCESS     not-accessible
   STATUS     mandatory
   DESCRIPTION
     "An entry in the exampleDashedProvStructDashedArrayTable."
   INDEX {
      exampleIndex,
      exampleDashedIndex,
      exampleDashedProvStructDashedArrayRowIndex,
      exampleDashedProvStructDashedArrayColumnIndex }
::= { exampleDashedProvStructDashedArrayTable 1 }

ExampleDashedProvStructDashedArrayEntry ::= SEQUENCE {
   exampleDashedProvStructDashedArrayRowIndex
      Integer32,
   exampleDashedProvStructDashedArrayColumnIndex
      Integer32,
   exampleDashedProvStructDashedArrayValue
      DashedHexString }

exampleDashedProvStructDashedArrayRowIndex OBJECT-TYPE
   SYNTAX     Integer32 (0..2)
   ACCESS     not-accessible
   STATUS     mandatory
   DESCRIPTION
     "This variable represents the next to last index for the 
      exampleDashedProvStructDashedArrayTable."
::= { exampleDashedProvStructDashedArrayEntry 1 }

exampleDashedProvStructDashedArrayColumnIndex OBJECT-TYPE
   SYNTAX     Integer32 (0..3)
   ACCESS     not-accessible
   STATUS     mandatory
   DESCRIPTION
     "This variable represents the final index for the 
      exampleDashedProvStructDashedArrayTable."
::= { exampleDashedProvStructDashedArrayEntry 2 }

exampleDashedProvStructDashedArrayValue OBJECT-TYPE
   SYNTAX     DashedHexString (SIZE (0..5))
   ACCESS     read-write
   STATUS     mandatory
   DESCRIPTION
     "This variable represents an individual value for the
      exampleDashedProvStructDashedArrayTable."
::= { exampleDashedProvStructDashedArrayEntry 3 }

exampleDashedProvStructDashedVectorTable OBJECT-TYPE
   SYNTAX     SEQUENCE OF ExampleDashedProvStructDashedVectorEntry
   ACCESS     not-accessible
   STATUS     mandatory
   DESCRIPTION
     ""
::= { exampleDashed 1095 }

exampleDashedProvStructDashedVectorEntry OBJECT-TYPE
   SYNTAX     ExampleDashedProvStructDashedVectorEntry
   ACCESS     not-accessible
   STATUS     mandatory
   DESCRIPTION
     "An entry in the exampleDashedProvStructDashedVectorTable."
   INDEX {
      exampleIndex,
      exampleDashedIndex,
      exampleDashedProvStructDashedVectorIndex }
::= { exampleDashedProvStructDashedVectorTable 1 }

ExampleDashedProvStructDashedVectorEntry ::= SEQUENCE {
   exampleDashedProvStructDashedVectorIndex
      Integer32,
   exampleDashedProvStructDashedVectorValue
      DashedHexString }

exampleDashedProvStructDashedVectorIndex OBJECT-TYPE
   SYNTAX     Integer32 (0..9)
   ACCESS     not-accessible
   STATUS     mandatory
   DESCRIPTION
     "This variable represents the exampleDashedProvStructDashedVectorTable
      specific index for the exampleDashedProvStructDashedVectorTable."
::= { exampleDashedProvStructDashedVectorEntry 1 }

exampleDashedProvStructDashedVectorValue OBJECT-TYPE
   SYNTAX     DashedHexString (SIZE (0..5))
   ACCESS     read-write
   STATUS     mandatory
   DESCRIPTION
     "This variable represents an individual value for the
      exampleDashedProvStructDashedVectorTable."
::= { exampleDashedProvStructDashedVectorEntry 2 }

exampleDashedProvFreeDashedListTable OBJECT-TYPE
   SYNTAX     SEQUENCE OF ExampleDashedProvFreeDashedListEntry
   ACCESS     not-accessible
   STATUS     mandatory
   DESCRIPTION
     ""
::= { exampleDashed 1096 }

exampleDashedProvFreeDashedListEntry OBJECT-TYPE
   SYNTAX     ExampleDashedProvFreeDashedListEntry
   ACCESS     not-accessible
   STATUS     mandatory
   DESCRIPTION
     "An entry in the exampleDashedProvFreeDashedListTable."
   INDEX {
      exampleIndex,
      exampleDashedIndex,
      exampleDashedProvFreeDashedListValue }
::= { exampleDashedProvFreeDashedListTable 1 }

ExampleDashedProvFreeDashedListEntry ::= SEQUENCE {
   exampleDashedProvFreeDashedListValue
      DashedHexString,
   exampleDashedProvFreeDashedListRowStatus
      RowStatus }

exampleDashedProvFreeDashedListValue OBJECT-TYPE
   SYNTAX     DashedHexString (SIZE (1..5))
   ACCESS     read-write
   STATUS     mandatory
   DESCRIPTION
     "This variable represents both the value and the index for the
      exampleDashedProvFreeDashedListTable."
::= { exampleDashedProvFreeDashedListEntry 1 }

exampleDashedProvFreeDashedListRowStatus OBJECT-TYPE
   SYNTAX     RowStatus 
   ACCESS     write-only
   STATUS     mandatory
   DESCRIPTION
     "This variable is used to control the addition and deletion 
      of individual values of the exampleDashedProvFreeDashedListTable."
::= { exampleDashedProvFreeDashedListEntry 2 }

exampleDashedProvFreeDashedReplicatedTable OBJECT-TYPE
   SYNTAX     SEQUENCE OF ExampleDashedProvFreeDashedReplicatedEntry
   ACCESS     not-accessible
   STATUS     mandatory
   DESCRIPTION
     ""
::= { exampleDashed 1097 }

exampleDashedProvFreeDashedReplicatedEntry OBJECT-TYPE
   SYNTAX     ExampleDashedProvFreeDashedReplicatedEntry
   ACCESS     not-accessible
   STATUS     mandatory
   DESCRIPTION
     "An entry in the exampleDashedProvFreeDashedReplicatedTable."
   INDEX {
      exampleIndex,
      exampleDashedIndex,
      exampleDashedProvFreeDashedReplicatedIndex }
::= { exampleDashedProvFreeDashedReplicatedTable 1 }

ExampleDashedProvFreeDashedReplicatedEntry ::= SEQUENCE {
   exampleDashedProvFreeDashedReplicatedIndex
      DashedHexString,
   exampleDashedProvFreeDashedReplicatedValue
      DashedHexString,
   exampleDashedProvFreeDashedReplicatedRowStatus
      RowStatus }

exampleDashedProvFreeDashedReplicatedIndex OBJECT-TYPE
   SYNTAX     DashedHexString (SIZE (1..5))
   ACCESS     not-accessible
   STATUS     mandatory
   DESCRIPTION
     "This variable represents the index for the exampleDashedProvFreeDashedReplicatedTable."
::= { exampleDashedProvFreeDashedReplicatedEntry 1 }

exampleDashedProvFreeDashedReplicatedValue OBJECT-TYPE
   SYNTAX     DashedHexString (SIZE (1..10))
   ACCESS     read-write
   STATUS     mandatory
   DESCRIPTION
     "This variable represents an individual value for the
      exampleDashedProvFreeDashedReplicatedTable."
::= { exampleDashedProvFreeDashedReplicatedEntry 2 }

exampleDashedProvFreeDashedReplicatedRowStatus OBJECT-TYPE
   SYNTAX     RowStatus 
   ACCESS     write-only
   STATUS     mandatory
   DESCRIPTION
     "This variable is used to control the addition and deletion 
      of individual values of the exampleDashedProvFreeDashedReplicatedTable."
::= { exampleDashedProvFreeDashedReplicatedEntry 3 }

exampleDashedProvFreeDashedArrayTable OBJECT-TYPE
   SYNTAX     SEQUENCE OF ExampleDashedProvFreeDashedArrayEntry
   ACCESS     not-accessible
   STATUS     mandatory
   DESCRIPTION
     ""
::= { exampleDashed 1098 }

exampleDashedProvFreeDashedArrayEntry OBJECT-TYPE
   SYNTAX     ExampleDashedProvFreeDashedArrayEntry
   ACCESS     not-accessible
   STATUS     mandatory
   DESCRIPTION
     "An entry in the exampleDashedProvFreeDashedArrayTable."
   INDEX {
      exampleIndex,
      exampleDashedIndex,
      exampleDashedProvFreeDashedArrayRowIndex,
      exampleDashedProvFreeDashedArrayColumnIndex }
::= { exampleDashedProvFreeDashedArrayTable 1 }

ExampleDashedProvFreeDashedArrayEntry ::= SEQUENCE {
   exampleDashedProvFreeDashedArrayRowIndex
      Integer32,
   exampleDashedProvFreeDashedArrayColumnIndex
      Integer32,
   exampleDashedProvFreeDashedArrayValue
      DashedHexString }

exampleDashedProvFreeDashedArrayRowIndex OBJECT-TYPE
   SYNTAX     Integer32 (0..2)
   ACCESS     not-accessible
   STATUS     mandatory
   DESCRIPTION
     "This variable represents the next to last index for the 
      exampleDashedProvFreeDashedArrayTable."
::= { exampleDashedProvFreeDashedArrayEntry 1 }

exampleDashedProvFreeDashedArrayColumnIndex OBJECT-TYPE
   SYNTAX     Integer32 (0..3)
   ACCESS     not-accessible
   STATUS     mandatory
   DESCRIPTION
     "This variable represents the final index for the 
      exampleDashedProvFreeDashedArrayTable."
::= { exampleDashedProvFreeDashedArrayEntry 2 }

exampleDashedProvFreeDashedArrayValue OBJECT-TYPE
   SYNTAX     DashedHexString (SIZE (0..5))
   ACCESS     read-write
   STATUS     mandatory
   DESCRIPTION
     "This variable represents an individual value for the
      exampleDashedProvFreeDashedArrayTable."
::= { exampleDashedProvFreeDashedArrayEntry 3 }

exampleDashedProvFreeDashedVectorTable OBJECT-TYPE
   SYNTAX     SEQUENCE OF ExampleDashedProvFreeDashedVectorEntry
   ACCESS     not-accessible
   STATUS     mandatory
   DESCRIPTION
     ""
::= { exampleDashed 1099 }

exampleDashedProvFreeDashedVectorEntry OBJECT-TYPE
   SYNTAX     ExampleDashedProvFreeDashedVectorEntry
   ACCESS     not-accessible
   STATUS     mandatory
   DESCRIPTION
     "An entry in the exampleDashedProvFreeDashedVectorTable."
   INDEX {
      exampleIndex,
      exampleDashedIndex,
      exampleDashedProvFreeDashedVectorIndex }
::= { exampleDashedProvFreeDashedVectorTable 1 }

ExampleDashedProvFreeDashedVectorEntry ::= SEQUENCE {
   exampleDashedProvFreeDashedVectorIndex
      Integer32,
   exampleDashedProvFreeDashedVectorValue
      DashedHexString }

exampleDashedProvFreeDashedVectorIndex OBJECT-TYPE
   SYNTAX     Integer32 (0..9)
   ACCESS     not-accessible
   STATUS     mandatory
   DESCRIPTION
     "This variable represents the exampleDashedProvFreeDashedVectorTable
      specific index for the exampleDashedProvFreeDashedVectorTable."
::= { exampleDashedProvFreeDashedVectorEntry 1 }

exampleDashedProvFreeDashedVectorValue OBJECT-TYPE
   SYNTAX     DashedHexString (SIZE (0..5))
   ACCESS     read-write
   STATUS     mandatory
   DESCRIPTION
     "This variable represents an individual value for the
      exampleDashedProvFreeDashedVectorTable."
::= { exampleDashedProvFreeDashedVectorEntry 2 }



exampleExtended OBJECT IDENTIFIER ::= { example 8 }



exampleExtendedRowStatusTable OBJECT-TYPE
   SYNTAX     SEQUENCE OF ExampleExtendedRowStatusEntry
   ACCESS     not-accessible
   STATUS     mandatory
   DESCRIPTION
     "This entry controls the addition and deletion of 
      exampleExtended components."
::= { exampleExtended 1 }

exampleExtendedRowStatusEntry OBJECT-TYPE
   SYNTAX     ExampleExtendedRowStatusEntry
   ACCESS     not-accessible
   STATUS     mandatory
   DESCRIPTION
     "A single entry in the table represents a single 
      exampleExtended component."
   INDEX {
      exampleIndex,
      exampleExtendedIndex }
::= { exampleExtendedRowStatusTable 1 }

ExampleExtendedRowStatusEntry ::= SEQUENCE {
   exampleExtendedRowStatus
      RowStatus,
   exampleExtendedComponentName
      DisplayString,
   exampleExtendedStorageType
      StorageType,
   exampleExtendedIndex
      NonReplicated }

exampleExtendedRowStatus OBJECT-TYPE
   SYNTAX     RowStatus 
   ACCESS     read-write
   STATUS     mandatory
   DESCRIPTION
     "This variable is used as the basis for SNMP naming of
      exampleExtended components.
      These components can be added and deleted."
::= { exampleExtendedRowStatusEntry 1 }

exampleExtendedComponentName OBJECT-TYPE
   SYNTAX     DisplayString 
   ACCESS     read-only
   STATUS     mandatory
   DESCRIPTION
     "This variable provides the component's string name for
      use with the ASCII Console Interface"
::= { exampleExtendedRowStatusEntry 2 }

exampleExtendedStorageType OBJECT-TYPE
   SYNTAX     StorageType 
   ACCESS     read-only
   STATUS     mandatory
   DESCRIPTION
     "This variable represents the storage type value for the
      exampleExtended tables."
::= { exampleExtendedRowStatusEntry 4 }

exampleExtendedIndex OBJECT-TYPE
   SYNTAX     NonReplicated 
   ACCESS     not-accessible
   STATUS     mandatory
   DESCRIPTION
     "This variable represents the index for the exampleExtended tables."
::= { exampleExtendedRowStatusEntry 10 }

exampleExtendedOperationalTable OBJECT-TYPE
   SYNTAX     SEQUENCE OF ExampleExtendedOperationalEntry
   ACCESS     not-accessible
   STATUS     mandatory
   DESCRIPTION
     ""
::= { exampleExtended 10 }

exampleExtendedOperationalEntry OBJECT-TYPE
   SYNTAX     ExampleExtendedOperationalEntry
   ACCESS     not-accessible
   STATUS     mandatory
   DESCRIPTION
     "An entry in the exampleExtendedOperationalTable."
   INDEX {
      exampleIndex,
      exampleExtendedIndex }
::= { exampleExtendedOperationalTable 1 }

ExampleExtendedOperationalEntry ::= SEQUENCE {
   exampleExtendedOperStructExtended
      ExtendedAsciiString,
   exampleExtendedOperFreeExtended
      ExtendedAsciiString }

exampleExtendedOperStructExtended OBJECT-TYPE
   SYNTAX     ExtendedAsciiString (SIZE (1..10))
   ACCESS     read-write
   STATUS     mandatory
   DESCRIPTION
     ""
::= { exampleExtendedOperationalEntry 1 }

exampleExtendedOperFreeExtended OBJECT-TYPE
   SYNTAX     ExtendedAsciiString (SIZE (1..10))
   ACCESS     read-write
   STATUS     mandatory
   DESCRIPTION
     ""
   DEFVAL     { '68656c6c6f5c6162'H }  -- "hello\\ab"
::= { exampleExtendedOperationalEntry 2 }

exampleExtendedProvisionalTable OBJECT-TYPE
   SYNTAX     SEQUENCE OF ExampleExtendedProvisionalEntry
   ACCESS     not-accessible
   STATUS     mandatory
   DESCRIPTION
     ""
::= { exampleExtended 11 }

exampleExtendedProvisionalEntry OBJECT-TYPE
   SYNTAX     ExampleExtendedProvisionalEntry
   ACCESS     not-accessible
   STATUS     mandatory
   DESCRIPTION
     "An entry in the exampleExtendedProvisionalTable."
   INDEX {
      exampleIndex,
      exampleExtendedIndex }
::= { exampleExtendedProvisionalTable 1 }

ExampleExtendedProvisionalEntry ::= SEQUENCE {
   exampleExtendedProvEnumSub
      Link,
   exampleExtendedProvStructExtended
      ExtendedAsciiString,
   exampleExtendedProvFreeExtended
      ExtendedAsciiString }

exampleExtendedProvEnumSub OBJECT-TYPE
   SYNTAX     Link 
   ACCESS     read-write
   STATUS     mandatory
   DESCRIPTION
     ""
::= { exampleExtendedProvisionalEntry 1 }

exampleExtendedProvStructExtended OBJECT-TYPE
   SYNTAX     ExtendedAsciiString (SIZE (1..10))
   ACCESS     read-write
   STATUS     mandatory
   DESCRIPTION
     ""
::= { exampleExtendedProvisionalEntry 2 }

exampleExtendedProvFreeExtended OBJECT-TYPE
   SYNTAX     ExtendedAsciiString (SIZE (1..10))
   ACCESS     read-write
   STATUS     mandatory
   DESCRIPTION
     ""
   DEFVAL     { '48656c6c6f5c61626364'H }  -- "Hello\\abcd"
::= { exampleExtendedProvisionalEntry 3 }

exampleExtendedOperStructExtendedArrayTable OBJECT-TYPE
   SYNTAX     SEQUENCE OF ExampleExtendedOperStructExtendedArrayEntry
   ACCESS     not-accessible
   STATUS     mandatory
   DESCRIPTION
     ""
::= { exampleExtended 1100 }

exampleExtendedOperStructExtendedArrayEntry OBJECT-TYPE
   SYNTAX     ExampleExtendedOperStructExtendedArrayEntry
   ACCESS     not-accessible
   STATUS     mandatory
   DESCRIPTION
     "An entry in the exampleExtendedOperStructExtendedArrayTable."
   INDEX {
      exampleIndex,
      exampleExtendedIndex,
      exampleExtendedOperStructExtendedArrayRowIndex,
      exampleExtendedOperStructExtendedArrayColumnIndex }
::= { exampleExtendedOperStructExtendedArrayTable 1 }

ExampleExtendedOperStructExtendedArrayEntry ::= SEQUENCE {
   exampleExtendedOperStructExtendedArrayRowIndex
      Integer32,
   exampleExtendedOperStructExtendedArrayColumnIndex
      Integer32,
   exampleExtendedOperStructExtendedArrayValue
      ExtendedAsciiString }

exampleExtendedOperStructExtendedArrayRowIndex OBJECT-TYPE
   SYNTAX     Integer32 (0..2)
   ACCESS     not-accessible
   STATUS     mandatory
   DESCRIPTION
     "This variable represents the next to last index for the 
      exampleExtendedOperStructExtendedArrayTable."
::= { exampleExtendedOperStructExtendedArrayEntry 1 }

exampleExtendedOperStructExtendedArrayColumnIndex OBJECT-TYPE
   SYNTAX     Integer32 (0..3)
   ACCESS     not-accessible
   STATUS     mandatory
   DESCRIPTION
     "This variable represents the final index for the 
      exampleExtendedOperStructExtendedArrayTable."
::= { exampleExtendedOperStructExtendedArrayEntry 2 }

exampleExtendedOperStructExtendedArrayValue OBJECT-TYPE
   SYNTAX     ExtendedAsciiString (SIZE (1..5))
   ACCESS     read-write
   STATUS     mandatory
   DESCRIPTION
     "This variable represents an individual value for the
      exampleExtendedOperStructExtendedArrayTable."
::= { exampleExtendedOperStructExtendedArrayEntry 3 }

exampleExtendedOperStructExtendedVectorTable OBJECT-TYPE
   SYNTAX     SEQUENCE OF ExampleExtendedOperStructExtendedVectorEntry
   ACCESS     not-accessible
   STATUS     mandatory
   DESCRIPTION
     ""
::= { exampleExtended 1101 }

exampleExtendedOperStructExtendedVectorEntry OBJECT-TYPE
   SYNTAX     ExampleExtendedOperStructExtendedVectorEntry
   ACCESS     not-accessible
   STATUS     mandatory
   DESCRIPTION
     "An entry in the exampleExtendedOperStructExtendedVectorTable."
   INDEX {
      exampleIndex,
      exampleExtendedIndex,
      exampleExtendedOperStructExtendedVectorIndex }
::= { exampleExtendedOperStructExtendedVectorTable 1 }

ExampleExtendedOperStructExtendedVectorEntry ::= SEQUENCE {
   exampleExtendedOperStructExtendedVectorIndex
      Integer32,
   exampleExtendedOperStructExtendedVectorValue
      ExtendedAsciiString }

exampleExtendedOperStructExtendedVectorIndex OBJECT-TYPE
   SYNTAX     Integer32 (0..9)
   ACCESS     not-accessible
   STATUS     mandatory
   DESCRIPTION
     "This variable represents the exampleExtendedOperStructExtendedVectorTable
      specific index for the exampleExtendedOperStructExtendedVectorTable."
::= { exampleExtendedOperStructExtendedVectorEntry 1 }

exampleExtendedOperStructExtendedVectorValue OBJECT-TYPE
   SYNTAX     ExtendedAsciiString (SIZE (1..5))
   ACCESS     read-write
   STATUS     mandatory
   DESCRIPTION
     "This variable represents an individual value for the
      exampleExtendedOperStructExtendedVectorTable."
::= { exampleExtendedOperStructExtendedVectorEntry 2 }

exampleExtendedOperFreeExtendedListTable OBJECT-TYPE
   SYNTAX     SEQUENCE OF ExampleExtendedOperFreeExtendedListEntry
   ACCESS     not-accessible
   STATUS     mandatory
   DESCRIPTION
     ""
::= { exampleExtended 1102 }

exampleExtendedOperFreeExtendedListEntry OBJECT-TYPE
   SYNTAX     ExampleExtendedOperFreeExtendedListEntry
   ACCESS     not-accessible
   STATUS     mandatory
   DESCRIPTION
     "An entry in the exampleExtendedOperFreeExtendedListTable."
   INDEX {
      exampleIndex,
      exampleExtendedIndex,
      exampleExtendedOperFreeExtendedListValue }
::= { exampleExtendedOperFreeExtendedListTable 1 }

ExampleExtendedOperFreeExtendedListEntry ::= SEQUENCE {
   exampleExtendedOperFreeExtendedListValue
      ExtendedAsciiString,
   exampleExtendedOperFreeExtendedListRowStatus
      RowStatus }

exampleExtendedOperFreeExtendedListValue OBJECT-TYPE
   SYNTAX     ExtendedAsciiString (SIZE (1..5))
   ACCESS     read-write
   STATUS     mandatory
   DESCRIPTION
     "This variable represents both the value and the index for the
      exampleExtendedOperFreeExtendedListTable."
::= { exampleExtendedOperFreeExtendedListEntry 1 }

exampleExtendedOperFreeExtendedListRowStatus OBJECT-TYPE
   SYNTAX     RowStatus 
   ACCESS     write-only
   STATUS     mandatory
   DESCRIPTION
     "This variable is used to control the addition and deletion 
      of individual values of the exampleExtendedOperFreeExtendedListTable."
::= { exampleExtendedOperFreeExtendedListEntry 2 }

exampleExtendedOperFreeExtendedReplicatedTable OBJECT-TYPE
   SYNTAX     SEQUENCE OF ExampleExtendedOperFreeExtendedReplicatedEntry
   ACCESS     not-accessible
   STATUS     mandatory
   DESCRIPTION
     ""
::= { exampleExtended 1103 }

exampleExtendedOperFreeExtendedReplicatedEntry OBJECT-TYPE
   SYNTAX     ExampleExtendedOperFreeExtendedReplicatedEntry
   ACCESS     not-accessible
   STATUS     mandatory
   DESCRIPTION
     "An entry in the exampleExtendedOperFreeExtendedReplicatedTable."
   INDEX {
      exampleIndex,
      exampleExtendedIndex,
      exampleExtendedOperFreeExtendedReplicatedIndex }
::= { exampleExtendedOperFreeExtendedReplicatedTable 1 }

ExampleExtendedOperFreeExtendedReplicatedEntry ::= SEQUENCE {
   exampleExtendedOperFreeExtendedReplicatedIndex
      ExtendedAsciiString,
   exampleExtendedOperFreeExtendedReplicatedValue
      ExtendedAsciiString,
   exampleExtendedOperFreeExtendedReplicatedRowStatus
      RowStatus }

exampleExtendedOperFreeExtendedReplicatedIndex OBJECT-TYPE
   SYNTAX     ExtendedAsciiString (SIZE (1..5))
   ACCESS     not-accessible
   STATUS     mandatory
   DESCRIPTION
     "This variable represents the index for the exampleExtendedOperFreeExtendedReplicatedTable."
::= { exampleExtendedOperFreeExtendedReplicatedEntry 1 }

exampleExtendedOperFreeExtendedReplicatedValue OBJECT-TYPE
   SYNTAX     ExtendedAsciiString (SIZE (1..10))
   ACCESS     read-write
   STATUS     mandatory
   DESCRIPTION
     "This variable represents an individual value for the
      exampleExtendedOperFreeExtendedReplicatedTable."
::= { exampleExtendedOperFreeExtendedReplicatedEntry 2 }

exampleExtendedOperFreeExtendedReplicatedRowStatus OBJECT-TYPE
   SYNTAX     RowStatus 
   ACCESS     write-only
   STATUS     mandatory
   DESCRIPTION
     "This variable is used to control the addition and deletion 
      of individual values of the exampleExtendedOperFreeExtendedReplicatedTable."
::= { exampleExtendedOperFreeExtendedReplicatedEntry 3 }

exampleExtendedOperFreeExtendedArrayTable OBJECT-TYPE
   SYNTAX     SEQUENCE OF ExampleExtendedOperFreeExtendedArrayEntry
   ACCESS     not-accessible
   STATUS     mandatory
   DESCRIPTION
     ""
::= { exampleExtended 1104 }

exampleExtendedOperFreeExtendedArrayEntry OBJECT-TYPE
   SYNTAX     ExampleExtendedOperFreeExtendedArrayEntry
   ACCESS     not-accessible
   STATUS     mandatory
   DESCRIPTION
     "An entry in the exampleExtendedOperFreeExtendedArrayTable."
   INDEX {
      exampleIndex,
      exampleExtendedIndex,
      exampleExtendedOperFreeExtendedArrayRowIndex,
      exampleExtendedOperFreeExtendedArrayColumnIndex }
::= { exampleExtendedOperFreeExtendedArrayTable 1 }

ExampleExtendedOperFreeExtendedArrayEntry ::= SEQUENCE {
   exampleExtendedOperFreeExtendedArrayRowIndex
      Integer32,
   exampleExtendedOperFreeExtendedArrayColumnIndex
      Integer32,
   exampleExtendedOperFreeExtendedArrayValue
      ExtendedAsciiString }

exampleExtendedOperFreeExtendedArrayRowIndex OBJECT-TYPE
   SYNTAX     Integer32 (0..2)
   ACCESS     not-accessible
   STATUS     mandatory
   DESCRIPTION
     "This variable represents the next to last index for the 
      exampleExtendedOperFreeExtendedArrayTable."
::= { exampleExtendedOperFreeExtendedArrayEntry 1 }

exampleExtendedOperFreeExtendedArrayColumnIndex OBJECT-TYPE
   SYNTAX     Integer32 (0..3)
   ACCESS     not-accessible
   STATUS     mandatory
   DESCRIPTION
     "This variable represents the final index for the 
      exampleExtendedOperFreeExtendedArrayTable."
::= { exampleExtendedOperFreeExtendedArrayEntry 2 }

exampleExtendedOperFreeExtendedArrayValue OBJECT-TYPE
   SYNTAX     ExtendedAsciiString (SIZE (1..5))
   ACCESS     read-write
   STATUS     mandatory
   DESCRIPTION
     "This variable represents an individual value for the
      exampleExtendedOperFreeExtendedArrayTable."
::= { exampleExtendedOperFreeExtendedArrayEntry 3 }

exampleExtendedOperFreeExtendedVectorTable OBJECT-TYPE
   SYNTAX     SEQUENCE OF ExampleExtendedOperFreeExtendedVectorEntry
   ACCESS     not-accessible
   STATUS     mandatory
   DESCRIPTION
     ""
::= { exampleExtended 1105 }

exampleExtendedOperFreeExtendedVectorEntry OBJECT-TYPE
   SYNTAX     ExampleExtendedOperFreeExtendedVectorEntry
   ACCESS     not-accessible
   STATUS     mandatory
   DESCRIPTION
     "An entry in the exampleExtendedOperFreeExtendedVectorTable."
   INDEX {
      exampleIndex,
      exampleExtendedIndex,
      exampleExtendedOperFreeExtendedVectorIndex }
::= { exampleExtendedOperFreeExtendedVectorTable 1 }

ExampleExtendedOperFreeExtendedVectorEntry ::= SEQUENCE {
   exampleExtendedOperFreeExtendedVectorIndex
      Integer32,
   exampleExtendedOperFreeExtendedVectorValue
      ExtendedAsciiString }

exampleExtendedOperFreeExtendedVectorIndex OBJECT-TYPE
   SYNTAX     Integer32 (0..9)
   ACCESS     not-accessible
   STATUS     mandatory
   DESCRIPTION
     "This variable represents the exampleExtendedOperFreeExtendedVectorTable
      specific index for the exampleExtendedOperFreeExtendedVectorTable."
::= { exampleExtendedOperFreeExtendedVectorEntry 1 }

exampleExtendedOperFreeExtendedVectorValue OBJECT-TYPE
   SYNTAX     ExtendedAsciiString (SIZE (1..5))
   ACCESS     read-write
   STATUS     mandatory
   DESCRIPTION
     "This variable represents an individual value for the
      exampleExtendedOperFreeExtendedVectorTable."
::= { exampleExtendedOperFreeExtendedVectorEntry 2 }

exampleExtendedProvStructExtendedArrayTable OBJECT-TYPE
   SYNTAX     SEQUENCE OF ExampleExtendedProvStructExtendedArrayEntry
   ACCESS     not-accessible
   STATUS     mandatory
   DESCRIPTION
     ""
::= { exampleExtended 1106 }

exampleExtendedProvStructExtendedArrayEntry OBJECT-TYPE
   SYNTAX     ExampleExtendedProvStructExtendedArrayEntry
   ACCESS     not-accessible
   STATUS     mandatory
   DESCRIPTION
     "An entry in the exampleExtendedProvStructExtendedArrayTable."
   INDEX {
      exampleIndex,
      exampleExtendedIndex,
      exampleExtendedProvStructExtendedArrayRowIndex,
      exampleExtendedProvStructExtendedArrayColumnIndex }
::= { exampleExtendedProvStructExtendedArrayTable 1 }

ExampleExtendedProvStructExtendedArrayEntry ::= SEQUENCE {
   exampleExtendedProvStructExtendedArrayRowIndex
      Integer32,
   exampleExtendedProvStructExtendedArrayColumnIndex
      Integer32,
   exampleExtendedProvStructExtendedArrayValue
      ExtendedAsciiString }

exampleExtendedProvStructExtendedArrayRowIndex OBJECT-TYPE
   SYNTAX     Integer32 (0..2)
   ACCESS     not-accessible
   STATUS     mandatory
   DESCRIPTION
     "This variable represents the next to last index for the 
      exampleExtendedProvStructExtendedArrayTable."
::= { exampleExtendedProvStructExtendedArrayEntry 1 }

exampleExtendedProvStructExtendedArrayColumnIndex OBJECT-TYPE
   SYNTAX     Integer32 (0..3)
   ACCESS     not-accessible
   STATUS     mandatory
   DESCRIPTION
     "This variable represents the final index for the 
      exampleExtendedProvStructExtendedArrayTable."
::= { exampleExtendedProvStructExtendedArrayEntry 2 }

exampleExtendedProvStructExtendedArrayValue OBJECT-TYPE
   SYNTAX     ExtendedAsciiString (SIZE (0..5))
   ACCESS     read-write
   STATUS     mandatory
   DESCRIPTION
     "This variable represents an individual value for the
      exampleExtendedProvStructExtendedArrayTable."
::= { exampleExtendedProvStructExtendedArrayEntry 3 }

exampleExtendedProvStructExtendedVectorTable OBJECT-TYPE
   SYNTAX     SEQUENCE OF ExampleExtendedProvStructExtendedVectorEntry
   ACCESS     not-accessible
   STATUS     mandatory
   DESCRIPTION
     ""
::= { exampleExtended 1107 }

exampleExtendedProvStructExtendedVectorEntry OBJECT-TYPE
   SYNTAX     ExampleExtendedProvStructExtendedVectorEntry
   ACCESS     not-accessible
   STATUS     mandatory
   DESCRIPTION
     "An entry in the exampleExtendedProvStructExtendedVectorTable."
   INDEX {
      exampleIndex,
      exampleExtendedIndex,
      exampleExtendedProvStructExtendedVectorIndex }
::= { exampleExtendedProvStructExtendedVectorTable 1 }

ExampleExtendedProvStructExtendedVectorEntry ::= SEQUENCE {
   exampleExtendedProvStructExtendedVectorIndex
      Integer32,
   exampleExtendedProvStructExtendedVectorValue
      ExtendedAsciiString }

exampleExtendedProvStructExtendedVectorIndex OBJECT-TYPE
   SYNTAX     Integer32 (0..9)
   ACCESS     not-accessible
   STATUS     mandatory
   DESCRIPTION
     "This variable represents the exampleExtendedProvStructExtendedVectorTable
      specific index for the exampleExtendedProvStructExtendedVectorTable."
::= { exampleExtendedProvStructExtendedVectorEntry 1 }

exampleExtendedProvStructExtendedVectorValue OBJECT-TYPE
   SYNTAX     ExtendedAsciiString (SIZE (0..5))
   ACCESS     read-write
   STATUS     mandatory
   DESCRIPTION
     "This variable represents an individual value for the
      exampleExtendedProvStructExtendedVectorTable."
::= { exampleExtendedProvStructExtendedVectorEntry 2 }

exampleExtendedProvFreeExtendedListTable OBJECT-TYPE
   SYNTAX     SEQUENCE OF ExampleExtendedProvFreeExtendedListEntry
   ACCESS     not-accessible
   STATUS     mandatory
   DESCRIPTION
     ""
::= { exampleExtended 1108 }

exampleExtendedProvFreeExtendedListEntry OBJECT-TYPE
   SYNTAX     ExampleExtendedProvFreeExtendedListEntry
   ACCESS     not-accessible
   STATUS     mandatory
   DESCRIPTION
     "An entry in the exampleExtendedProvFreeExtendedListTable."
   INDEX {
      exampleIndex,
      exampleExtendedIndex,
      exampleExtendedProvFreeExtendedListValue }
::= { exampleExtendedProvFreeExtendedListTable 1 }

ExampleExtendedProvFreeExtendedListEntry ::= SEQUENCE {
   exampleExtendedProvFreeExtendedListValue
      ExtendedAsciiString,
   exampleExtendedProvFreeExtendedListRowStatus
      RowStatus }

exampleExtendedProvFreeExtendedListValue OBJECT-TYPE
   SYNTAX     ExtendedAsciiString (SIZE (1..5))
   ACCESS     read-write
   STATUS     mandatory
   DESCRIPTION
     "This variable represents both the value and the index for the
      exampleExtendedProvFreeExtendedListTable."
::= { exampleExtendedProvFreeExtendedListEntry 1 }

exampleExtendedProvFreeExtendedListRowStatus OBJECT-TYPE
   SYNTAX     RowStatus 
   ACCESS     write-only
   STATUS     mandatory
   DESCRIPTION
     "This variable is used to control the addition and deletion 
      of individual values of the exampleExtendedProvFreeExtendedListTable."
::= { exampleExtendedProvFreeExtendedListEntry 2 }

exampleExtendedProvFreeExtendedReplicatedTable OBJECT-TYPE
   SYNTAX     SEQUENCE OF ExampleExtendedProvFreeExtendedReplicatedEntry
   ACCESS     not-accessible
   STATUS     mandatory
   DESCRIPTION
     ""
::= { exampleExtended 1109 }

exampleExtendedProvFreeExtendedReplicatedEntry OBJECT-TYPE
   SYNTAX     ExampleExtendedProvFreeExtendedReplicatedEntry
   ACCESS     not-accessible
   STATUS     mandatory
   DESCRIPTION
     "An entry in the exampleExtendedProvFreeExtendedReplicatedTable."
   INDEX {
      exampleIndex,
      exampleExtendedIndex,
      exampleExtendedProvFreeExtendedReplicatedIndex }
::= { exampleExtendedProvFreeExtendedReplicatedTable 1 }

ExampleExtendedProvFreeExtendedReplicatedEntry ::= SEQUENCE {
   exampleExtendedProvFreeExtendedReplicatedIndex
      ExtendedAsciiString,
   exampleExtendedProvFreeExtendedReplicatedValue
      ExtendedAsciiString,
   exampleExtendedProvFreeExtendedReplicatedRowStatus
      RowStatus }

exampleExtendedProvFreeExtendedReplicatedIndex OBJECT-TYPE
   SYNTAX     ExtendedAsciiString (SIZE (1..5))
   ACCESS     not-accessible
   STATUS     mandatory
   DESCRIPTION
     "This variable represents the index for the exampleExtendedProvFreeExtendedReplicatedTable."
::= { exampleExtendedProvFreeExtendedReplicatedEntry 1 }

exampleExtendedProvFreeExtendedReplicatedValue OBJECT-TYPE
   SYNTAX     ExtendedAsciiString (SIZE (1..10))
   ACCESS     read-write
   STATUS     mandatory
   DESCRIPTION
     "This variable represents an individual value for the
      exampleExtendedProvFreeExtendedReplicatedTable."
::= { exampleExtendedProvFreeExtendedReplicatedEntry 2 }

exampleExtendedProvFreeExtendedReplicatedRowStatus OBJECT-TYPE
   SYNTAX     RowStatus 
   ACCESS     write-only
   STATUS     mandatory
   DESCRIPTION
     "This variable is used to control the addition and deletion 
      of individual values of the exampleExtendedProvFreeExtendedReplicatedTable."
::= { exampleExtendedProvFreeExtendedReplicatedEntry 3 }

exampleExtendedProvFreeExtendedArrayTable OBJECT-TYPE
   SYNTAX     SEQUENCE OF ExampleExtendedProvFreeExtendedArrayEntry
   ACCESS     not-accessible
   STATUS     mandatory
   DESCRIPTION
     ""
::= { exampleExtended 1110 }

exampleExtendedProvFreeExtendedArrayEntry OBJECT-TYPE
   SYNTAX     ExampleExtendedProvFreeExtendedArrayEntry
   ACCESS     not-accessible
   STATUS     mandatory
   DESCRIPTION
     "An entry in the exampleExtendedProvFreeExtendedArrayTable."
   INDEX {
      exampleIndex,
      exampleExtendedIndex,
      exampleExtendedProvFreeExtendedArrayRowIndex,
      exampleExtendedProvFreeExtendedArrayColumnIndex }
::= { exampleExtendedProvFreeExtendedArrayTable 1 }

ExampleExtendedProvFreeExtendedArrayEntry ::= SEQUENCE {
   exampleExtendedProvFreeExtendedArrayRowIndex
      Integer32,
   exampleExtendedProvFreeExtendedArrayColumnIndex
      Integer32,
   exampleExtendedProvFreeExtendedArrayValue
      ExtendedAsciiString }

exampleExtendedProvFreeExtendedArrayRowIndex OBJECT-TYPE
   SYNTAX     Integer32 (0..2)
   ACCESS     not-accessible
   STATUS     mandatory
   DESCRIPTION
     "This variable represents the next to last index for the 
      exampleExtendedProvFreeExtendedArrayTable."
::= { exampleExtendedProvFreeExtendedArrayEntry 1 }

exampleExtendedProvFreeExtendedArrayColumnIndex OBJECT-TYPE
   SYNTAX     Integer32 (0..3)
   ACCESS     not-accessible
   STATUS     mandatory
   DESCRIPTION
     "This variable represents the final index for the 
      exampleExtendedProvFreeExtendedArrayTable."
::= { exampleExtendedProvFreeExtendedArrayEntry 2 }

exampleExtendedProvFreeExtendedArrayValue OBJECT-TYPE
   SYNTAX     ExtendedAsciiString (SIZE (0..5))
   ACCESS     read-write
   STATUS     mandatory
   DESCRIPTION
     "This variable represents an individual value for the
      exampleExtendedProvFreeExtendedArrayTable."
::= { exampleExtendedProvFreeExtendedArrayEntry 3 }

exampleExtendedProvFreeExtendedVectorTable OBJECT-TYPE
   SYNTAX     SEQUENCE OF ExampleExtendedProvFreeExtendedVectorEntry
   ACCESS     not-accessible
   STATUS     mandatory
   DESCRIPTION
     ""
::= { exampleExtended 1111 }

exampleExtendedProvFreeExtendedVectorEntry OBJECT-TYPE
   SYNTAX     ExampleExtendedProvFreeExtendedVectorEntry
   ACCESS     not-accessible
   STATUS     mandatory
   DESCRIPTION
     "An entry in the exampleExtendedProvFreeExtendedVectorTable."
   INDEX {
      exampleIndex,
      exampleExtendedIndex,
      exampleExtendedProvFreeExtendedVectorIndex }
::= { exampleExtendedProvFreeExtendedVectorTable 1 }

ExampleExtendedProvFreeExtendedVectorEntry ::= SEQUENCE {
   exampleExtendedProvFreeExtendedVectorIndex
      Integer32,
   exampleExtendedProvFreeExtendedVectorValue
      ExtendedAsciiString }

exampleExtendedProvFreeExtendedVectorIndex OBJECT-TYPE
   SYNTAX     Integer32 (0..9)
   ACCESS     not-accessible
   STATUS     mandatory
   DESCRIPTION
     "This variable represents the exampleExtendedProvFreeExtendedVectorTable
      specific index for the exampleExtendedProvFreeExtendedVectorTable."
::= { exampleExtendedProvFreeExtendedVectorEntry 1 }

exampleExtendedProvFreeExtendedVectorValue OBJECT-TYPE
   SYNTAX     ExtendedAsciiString (SIZE (0..5))
   ACCESS     read-write
   STATUS     mandatory
   DESCRIPTION
     "This variable represents an individual value for the
      exampleExtendedProvFreeExtendedVectorTable."
::= { exampleExtendedProvFreeExtendedVectorEntry 2 }



exampleBcd OBJECT IDENTIFIER ::= { example 9 }



exampleBcdRowStatusTable OBJECT-TYPE
   SYNTAX     SEQUENCE OF ExampleBcdRowStatusEntry
   ACCESS     not-accessible
   STATUS     mandatory
   DESCRIPTION
     "This entry controls the addition and deletion of 
      exampleBcd components."
::= { exampleBcd 1 }

exampleBcdRowStatusEntry OBJECT-TYPE
   SYNTAX     ExampleBcdRowStatusEntry
   ACCESS     not-accessible
   STATUS     mandatory
   DESCRIPTION
     "A single entry in the table represents a single 
      exampleBcd component."
   INDEX {
      exampleIndex,
      exampleBcdIndex }
::= { exampleBcdRowStatusTable 1 }

ExampleBcdRowStatusEntry ::= SEQUENCE {
   exampleBcdRowStatus
      RowStatus,
   exampleBcdComponentName
      DisplayString,
   exampleBcdStorageType
      StorageType,
   exampleBcdIndex
      DigitString }

exampleBcdRowStatus OBJECT-TYPE
   SYNTAX     RowStatus 
   ACCESS     read-write
   STATUS     mandatory
   DESCRIPTION
     "This variable is used as the basis for SNMP naming of
      exampleBcd components.
      These components can be added and deleted."
::= { exampleBcdRowStatusEntry 1 }

exampleBcdComponentName OBJECT-TYPE
   SYNTAX     DisplayString 
   ACCESS     read-only
   STATUS     mandatory
   DESCRIPTION
     "This variable provides the component's string name for
      use with the ASCII Console Interface"
::= { exampleBcdRowStatusEntry 2 }

exampleBcdStorageType OBJECT-TYPE
   SYNTAX     StorageType 
   ACCESS     read-only
   STATUS     mandatory
   DESCRIPTION
     "This variable represents the storage type value for the
      exampleBcd tables."
::= { exampleBcdRowStatusEntry 4 }

exampleBcdIndex OBJECT-TYPE
   SYNTAX     DigitString (SIZE (1..10))
   ACCESS     not-accessible
   STATUS     mandatory
   DESCRIPTION
     "This variable represents the index for the exampleBcd tables."
::= { exampleBcdRowStatusEntry 10 }

exampleBcdOperationalTable OBJECT-TYPE
   SYNTAX     SEQUENCE OF ExampleBcdOperationalEntry
   ACCESS     not-accessible
   STATUS     mandatory
   DESCRIPTION
     ""
::= { exampleBcd 10 }

exampleBcdOperationalEntry OBJECT-TYPE
   SYNTAX     ExampleBcdOperationalEntry
   ACCESS     not-accessible
   STATUS     mandatory
   DESCRIPTION
     "An entry in the exampleBcdOperationalTable."
   INDEX {
      exampleIndex,
      exampleBcdIndex }
::= { exampleBcdOperationalTable 1 }

ExampleBcdOperationalEntry ::= SEQUENCE {
   exampleBcdOperStructBcd
      DigitString,
   exampleBcdOperFreeBcd
      DigitString }

exampleBcdOperStructBcd OBJECT-TYPE
   SYNTAX     DigitString (SIZE (0..16))
   ACCESS     read-write
   STATUS     mandatory
   DESCRIPTION
     ""
::= { exampleBcdOperationalEntry 1 }

exampleBcdOperFreeBcd OBJECT-TYPE
   SYNTAX     DigitString (SIZE (0..16))
   ACCESS     read-write
   STATUS     mandatory
   DESCRIPTION
     ""
::= { exampleBcdOperationalEntry 2 }

exampleBcdProvisionalTable OBJECT-TYPE
   SYNTAX     SEQUENCE OF ExampleBcdProvisionalEntry
   ACCESS     not-accessible
   STATUS     mandatory
   DESCRIPTION
     ""
::= { exampleBcd 11 }

exampleBcdProvisionalEntry OBJECT-TYPE
   SYNTAX     ExampleBcdProvisionalEntry
   ACCESS     not-accessible
   STATUS     mandatory
   DESCRIPTION
     "An entry in the exampleBcdProvisionalTable."
   INDEX {
      exampleIndex,
      exampleBcdIndex }
::= { exampleBcdProvisionalTable 1 }

ExampleBcdProvisionalEntry ::= SEQUENCE {
   exampleBcdProvEnumSub
      Link,
   exampleBcdProvStructBcd
      DigitString,
   exampleBcdProvFreeBcd
      DigitString,
   exampleBcdProvFreeBcd1
      DigitString }

exampleBcdProvEnumSub OBJECT-TYPE
   SYNTAX     Link 
   ACCESS     read-write
   STATUS     mandatory
   DESCRIPTION
     ""
::= { exampleBcdProvisionalEntry 1 }

exampleBcdProvStructBcd OBJECT-TYPE
   SYNTAX     DigitString (SIZE (0..16))
   ACCESS     read-write
   STATUS     mandatory
   DESCRIPTION
     ""
   DEFVAL     { '30313233343536373839'H }  -- "0123456789"
::= { exampleBcdProvisionalEntry 2 }

exampleBcdProvFreeBcd OBJECT-TYPE
   SYNTAX     DigitString (SIZE (4..16))
   ACCESS     read-write
   STATUS     mandatory
   DESCRIPTION
     ""
   DEFVAL     { '31323334353637383930'H }  -- "1234567890"
::= { exampleBcdProvisionalEntry 3 }

exampleBcdProvFreeBcd1 OBJECT-TYPE
   SYNTAX     DigitString (SIZE (4..8))
   ACCESS     read-write
   STATUS     mandatory
   DESCRIPTION
     ""
::= { exampleBcdProvisionalEntry 4 }

exampleBcdOperStructBcdVectorTable OBJECT-TYPE
   SYNTAX     SEQUENCE OF ExampleBcdOperStructBcdVectorEntry
   ACCESS     not-accessible
   STATUS     mandatory
   DESCRIPTION
     ""
::= { exampleBcd 1120 }

exampleBcdOperStructBcdVectorEntry OBJECT-TYPE
   SYNTAX     ExampleBcdOperStructBcdVectorEntry
   ACCESS     not-accessible
   STATUS     mandatory
   DESCRIPTION
     "An entry in the exampleBcdOperStructBcdVectorTable."
   INDEX {
      exampleIndex,
      exampleBcdIndex,
      exampleBcdOperStructBcdVectorIndex }
::= { exampleBcdOperStructBcdVectorTable 1 }

ExampleBcdOperStructBcdVectorEntry ::= SEQUENCE {
   exampleBcdOperStructBcdVectorIndex
      Integer32,
   exampleBcdOperStructBcdVectorValue
      DigitString }

exampleBcdOperStructBcdVectorIndex OBJECT-TYPE
   SYNTAX     Integer32 (0..9)
   ACCESS     not-accessible
   STATUS     mandatory
   DESCRIPTION
     "This variable represents the exampleBcdOperStructBcdVectorTable
      specific index for the exampleBcdOperStructBcdVectorTable."
::= { exampleBcdOperStructBcdVectorEntry 1 }

exampleBcdOperStructBcdVectorValue OBJECT-TYPE
   SYNTAX     DigitString (SIZE (0..5))
   ACCESS     read-write
   STATUS     mandatory
   DESCRIPTION
     "This variable represents an individual value for the
      exampleBcdOperStructBcdVectorTable."
::= { exampleBcdOperStructBcdVectorEntry 2 }

exampleBcdOperStructBcdArrayTable OBJECT-TYPE
   SYNTAX     SEQUENCE OF ExampleBcdOperStructBcdArrayEntry
   ACCESS     not-accessible
   STATUS     mandatory
   DESCRIPTION
     ""
::= { exampleBcd 1121 }

exampleBcdOperStructBcdArrayEntry OBJECT-TYPE
   SYNTAX     ExampleBcdOperStructBcdArrayEntry
   ACCESS     not-accessible
   STATUS     mandatory
   DESCRIPTION
     "An entry in the exampleBcdOperStructBcdArrayTable."
   INDEX {
      exampleIndex,
      exampleBcdIndex,
      exampleBcdOperStructBcdArrayRowIndex,
      exampleBcdOperStructBcdArrayColumnIndex }
::= { exampleBcdOperStructBcdArrayTable 1 }

ExampleBcdOperStructBcdArrayEntry ::= SEQUENCE {
   exampleBcdOperStructBcdArrayRowIndex
      Integer32,
   exampleBcdOperStructBcdArrayColumnIndex
      Integer32,
   exampleBcdOperStructBcdArrayValue
      DigitString }

exampleBcdOperStructBcdArrayRowIndex OBJECT-TYPE
   SYNTAX     Integer32 (0..2)
   ACCESS     not-accessible
   STATUS     mandatory
   DESCRIPTION
     "This variable represents the next to last index for the 
      exampleBcdOperStructBcdArrayTable."
::= { exampleBcdOperStructBcdArrayEntry 1 }

exampleBcdOperStructBcdArrayColumnIndex OBJECT-TYPE
   SYNTAX     Integer32 (0..3)
   ACCESS     not-accessible
   STATUS     mandatory
   DESCRIPTION
     "This variable represents the final index for the 
      exampleBcdOperStructBcdArrayTable."
::= { exampleBcdOperStructBcdArrayEntry 2 }

exampleBcdOperStructBcdArrayValue OBJECT-TYPE
   SYNTAX     DigitString (SIZE (0..5))
   ACCESS     read-write
   STATUS     mandatory
   DESCRIPTION
     "This variable represents an individual value for the
      exampleBcdOperStructBcdArrayTable."
::= { exampleBcdOperStructBcdArrayEntry 3 }

exampleBcdOperFreeBcdVectorTable OBJECT-TYPE
   SYNTAX     SEQUENCE OF ExampleBcdOperFreeBcdVectorEntry
   ACCESS     not-accessible
   STATUS     mandatory
   DESCRIPTION
     ""
::= { exampleBcd 1122 }

exampleBcdOperFreeBcdVectorEntry OBJECT-TYPE
   SYNTAX     ExampleBcdOperFreeBcdVectorEntry
   ACCESS     not-accessible
   STATUS     mandatory
   DESCRIPTION
     "An entry in the exampleBcdOperFreeBcdVectorTable."
   INDEX {
      exampleIndex,
      exampleBcdIndex,
      exampleBcdOperFreeBcdVectorIndex }
::= { exampleBcdOperFreeBcdVectorTable 1 }

ExampleBcdOperFreeBcdVectorEntry ::= SEQUENCE {
   exampleBcdOperFreeBcdVectorIndex
      Integer32,
   exampleBcdOperFreeBcdVectorValue
      DigitString }

exampleBcdOperFreeBcdVectorIndex OBJECT-TYPE
   SYNTAX     Integer32 (0..9)
   ACCESS     not-accessible
   STATUS     mandatory
   DESCRIPTION
     "This variable represents the exampleBcdOperFreeBcdVectorTable
      specific index for the exampleBcdOperFreeBcdVectorTable."
::= { exampleBcdOperFreeBcdVectorEntry 1 }

exampleBcdOperFreeBcdVectorValue OBJECT-TYPE
   SYNTAX     DigitString (SIZE (0..5))
   ACCESS     read-write
   STATUS     mandatory
   DESCRIPTION
     "This variable represents an individual value for the
      exampleBcdOperFreeBcdVectorTable."
::= { exampleBcdOperFreeBcdVectorEntry 2 }

exampleBcdOperFreeBcdArrayTable OBJECT-TYPE
   SYNTAX     SEQUENCE OF ExampleBcdOperFreeBcdArrayEntry
   ACCESS     not-accessible
   STATUS     mandatory
   DESCRIPTION
     ""
::= { exampleBcd 1123 }

exampleBcdOperFreeBcdArrayEntry OBJECT-TYPE
   SYNTAX     ExampleBcdOperFreeBcdArrayEntry
   ACCESS     not-accessible
   STATUS     mandatory
   DESCRIPTION
     "An entry in the exampleBcdOperFreeBcdArrayTable."
   INDEX {
      exampleIndex,
      exampleBcdIndex,
      exampleBcdOperFreeBcdArrayRowIndex,
      exampleBcdOperFreeBcdArrayColumnIndex }
::= { exampleBcdOperFreeBcdArrayTable 1 }

ExampleBcdOperFreeBcdArrayEntry ::= SEQUENCE {
   exampleBcdOperFreeBcdArrayRowIndex
      Integer32,
   exampleBcdOperFreeBcdArrayColumnIndex
      Integer32,
   exampleBcdOperFreeBcdArrayValue
      DigitString }

exampleBcdOperFreeBcdArrayRowIndex OBJECT-TYPE
   SYNTAX     Integer32 (0..2)
   ACCESS     not-accessible
   STATUS     mandatory
   DESCRIPTION
     "This variable represents the next to last index for the 
      exampleBcdOperFreeBcdArrayTable."
::= { exampleBcdOperFreeBcdArrayEntry 1 }

exampleBcdOperFreeBcdArrayColumnIndex OBJECT-TYPE
   SYNTAX     Integer32 (0..3)
   ACCESS     not-accessible
   STATUS     mandatory
   DESCRIPTION
     "This variable represents the final index for the 
      exampleBcdOperFreeBcdArrayTable."
::= { exampleBcdOperFreeBcdArrayEntry 2 }

exampleBcdOperFreeBcdArrayValue OBJECT-TYPE
   SYNTAX     DigitString (SIZE (0..5))
   ACCESS     read-write
   STATUS     mandatory
   DESCRIPTION
     "This variable represents an individual value for the
      exampleBcdOperFreeBcdArrayTable."
::= { exampleBcdOperFreeBcdArrayEntry 3 }

exampleBcdOperFreeBcdReplicatedTable OBJECT-TYPE
   SYNTAX     SEQUENCE OF ExampleBcdOperFreeBcdReplicatedEntry
   ACCESS     not-accessible
   STATUS     mandatory
   DESCRIPTION
     ""
::= { exampleBcd 1124 }

exampleBcdOperFreeBcdReplicatedEntry OBJECT-TYPE
   SYNTAX     ExampleBcdOperFreeBcdReplicatedEntry
   ACCESS     not-accessible
   STATUS     mandatory
   DESCRIPTION
     "An entry in the exampleBcdOperFreeBcdReplicatedTable."
   INDEX {
      exampleIndex,
      exampleBcdIndex,
      exampleBcdOperFreeBcdReplicatedIndex }
::= { exampleBcdOperFreeBcdReplicatedTable 1 }

ExampleBcdOperFreeBcdReplicatedEntry ::= SEQUENCE {
   exampleBcdOperFreeBcdReplicatedIndex
      DigitString,
   exampleBcdOperFreeBcdReplicatedValue
      DigitString,
   exampleBcdOperFreeBcdReplicatedRowStatus
      RowStatus }

exampleBcdOperFreeBcdReplicatedIndex OBJECT-TYPE
   SYNTAX     DigitString (SIZE (0..5))
   ACCESS     not-accessible
   STATUS     mandatory
   DESCRIPTION
     "This variable represents the index for the exampleBcdOperFreeBcdReplicatedTable."
::= { exampleBcdOperFreeBcdReplicatedEntry 1 }

exampleBcdOperFreeBcdReplicatedValue OBJECT-TYPE
   SYNTAX     DigitString (SIZE (0..16))
   ACCESS     read-write
   STATUS     mandatory
   DESCRIPTION
     "This variable represents an individual value for the
      exampleBcdOperFreeBcdReplicatedTable."
::= { exampleBcdOperFreeBcdReplicatedEntry 2 }

exampleBcdOperFreeBcdReplicatedRowStatus OBJECT-TYPE
   SYNTAX     RowStatus 
   ACCESS     write-only
   STATUS     mandatory
   DESCRIPTION
     "This variable is used to control the addition and deletion 
      of individual values of the exampleBcdOperFreeBcdReplicatedTable."
::= { exampleBcdOperFreeBcdReplicatedEntry 3 }

exampleBcdOperFreeBcdListTable OBJECT-TYPE
   SYNTAX     SEQUENCE OF ExampleBcdOperFreeBcdListEntry
   ACCESS     not-accessible
   STATUS     mandatory
   DESCRIPTION
     ""
::= { exampleBcd 1125 }

exampleBcdOperFreeBcdListEntry OBJECT-TYPE
   SYNTAX     ExampleBcdOperFreeBcdListEntry
   ACCESS     not-accessible
   STATUS     mandatory
   DESCRIPTION
     "An entry in the exampleBcdOperFreeBcdListTable."
   INDEX {
      exampleIndex,
      exampleBcdIndex,
      exampleBcdOperFreeBcdListValue }
::= { exampleBcdOperFreeBcdListTable 1 }

ExampleBcdOperFreeBcdListEntry ::= SEQUENCE {
   exampleBcdOperFreeBcdListValue
      DigitString,
   exampleBcdOperFreeBcdListRowStatus
      RowStatus }

exampleBcdOperFreeBcdListValue OBJECT-TYPE
   SYNTAX     DigitString (SIZE (0..16))
   ACCESS     read-write
   STATUS     mandatory
   DESCRIPTION
     "This variable represents both the value and the index for the
      exampleBcdOperFreeBcdListTable."
::= { exampleBcdOperFreeBcdListEntry 1 }

exampleBcdOperFreeBcdListRowStatus OBJECT-TYPE
   SYNTAX     RowStatus 
   ACCESS     write-only
   STATUS     mandatory
   DESCRIPTION
     "This variable is used to control the addition and deletion 
      of individual values of the exampleBcdOperFreeBcdListTable."
::= { exampleBcdOperFreeBcdListEntry 2 }

exampleBcdProvStructBcdVectorTable OBJECT-TYPE
   SYNTAX     SEQUENCE OF ExampleBcdProvStructBcdVectorEntry
   ACCESS     not-accessible
   STATUS     mandatory
   DESCRIPTION
     ""
::= { exampleBcd 1126 }

exampleBcdProvStructBcdVectorEntry OBJECT-TYPE
   SYNTAX     ExampleBcdProvStructBcdVectorEntry
   ACCESS     not-accessible
   STATUS     mandatory
   DESCRIPTION
     "An entry in the exampleBcdProvStructBcdVectorTable."
   INDEX {
      exampleIndex,
      exampleBcdIndex,
      exampleBcdProvStructBcdVectorIndex }
::= { exampleBcdProvStructBcdVectorTable 1 }

ExampleBcdProvStructBcdVectorEntry ::= SEQUENCE {
   exampleBcdProvStructBcdVectorIndex
      Integer32,
   exampleBcdProvStructBcdVectorValue
      DigitString }

exampleBcdProvStructBcdVectorIndex OBJECT-TYPE
   SYNTAX     Integer32 (0..9)
   ACCESS     not-accessible
   STATUS     mandatory
   DESCRIPTION
     "This variable represents the exampleBcdProvStructBcdVectorTable
      specific index for the exampleBcdProvStructBcdVectorTable."
::= { exampleBcdProvStructBcdVectorEntry 1 }

exampleBcdProvStructBcdVectorValue OBJECT-TYPE
   SYNTAX     DigitString (SIZE (0..5))
   ACCESS     read-write
   STATUS     mandatory
   DESCRIPTION
     "This variable represents an individual value for the
      exampleBcdProvStructBcdVectorTable."
::= { exampleBcdProvStructBcdVectorEntry 2 }

exampleBcdProvStructBcdArrayTable OBJECT-TYPE
   SYNTAX     SEQUENCE OF ExampleBcdProvStructBcdArrayEntry
   ACCESS     not-accessible
   STATUS     mandatory
   DESCRIPTION
     ""
::= { exampleBcd 1127 }

exampleBcdProvStructBcdArrayEntry OBJECT-TYPE
   SYNTAX     ExampleBcdProvStructBcdArrayEntry
   ACCESS     not-accessible
   STATUS     mandatory
   DESCRIPTION
     "An entry in the exampleBcdProvStructBcdArrayTable."
   INDEX {
      exampleIndex,
      exampleBcdIndex,
      exampleBcdProvStructBcdArrayRowIndex,
      exampleBcdProvStructBcdArrayColumnIndex }
::= { exampleBcdProvStructBcdArrayTable 1 }

ExampleBcdProvStructBcdArrayEntry ::= SEQUENCE {
   exampleBcdProvStructBcdArrayRowIndex
      Integer32,
   exampleBcdProvStructBcdArrayColumnIndex
      Integer32,
   exampleBcdProvStructBcdArrayValue
      DigitString }

exampleBcdProvStructBcdArrayRowIndex OBJECT-TYPE
   SYNTAX     Integer32 (0..2)
   ACCESS     not-accessible
   STATUS     mandatory
   DESCRIPTION
     "This variable represents the next to last index for the 
      exampleBcdProvStructBcdArrayTable."
::= { exampleBcdProvStructBcdArrayEntry 1 }

exampleBcdProvStructBcdArrayColumnIndex OBJECT-TYPE
   SYNTAX     Integer32 (0..3)
   ACCESS     not-accessible
   STATUS     mandatory
   DESCRIPTION
     "This variable represents the final index for the 
      exampleBcdProvStructBcdArrayTable."
::= { exampleBcdProvStructBcdArrayEntry 2 }

exampleBcdProvStructBcdArrayValue OBJECT-TYPE
   SYNTAX     DigitString (SIZE (0..5))
   ACCESS     read-write
   STATUS     mandatory
   DESCRIPTION
     "This variable represents an individual value for the
      exampleBcdProvStructBcdArrayTable."
::= { exampleBcdProvStructBcdArrayEntry 3 }

exampleBcdProvFreeBcdVectorTable OBJECT-TYPE
   SYNTAX     SEQUENCE OF ExampleBcdProvFreeBcdVectorEntry
   ACCESS     not-accessible
   STATUS     mandatory
   DESCRIPTION
     ""
::= { exampleBcd 1128 }

exampleBcdProvFreeBcdVectorEntry OBJECT-TYPE
   SYNTAX     ExampleBcdProvFreeBcdVectorEntry
   ACCESS     not-accessible
   STATUS     mandatory
   DESCRIPTION
     "An entry in the exampleBcdProvFreeBcdVectorTable."
   INDEX {
      exampleIndex,
      exampleBcdIndex,
      exampleBcdProvFreeBcdVectorIndex }
::= { exampleBcdProvFreeBcdVectorTable 1 }

ExampleBcdProvFreeBcdVectorEntry ::= SEQUENCE {
   exampleBcdProvFreeBcdVectorIndex
      Integer32,
   exampleBcdProvFreeBcdVectorValue
      DigitString }

exampleBcdProvFreeBcdVectorIndex OBJECT-TYPE
   SYNTAX     Integer32 (0..9)
   ACCESS     not-accessible
   STATUS     mandatory
   DESCRIPTION
     "This variable represents the exampleBcdProvFreeBcdVectorTable
      specific index for the exampleBcdProvFreeBcdVectorTable."
::= { exampleBcdProvFreeBcdVectorEntry 1 }

exampleBcdProvFreeBcdVectorValue OBJECT-TYPE
   SYNTAX     DigitString (SIZE (0..5))
   ACCESS     read-write
   STATUS     mandatory
   DESCRIPTION
     "This variable represents an individual value for the
      exampleBcdProvFreeBcdVectorTable."
::= { exampleBcdProvFreeBcdVectorEntry 2 }

exampleBcdProvFreeBcdVector1Table OBJECT-TYPE
   SYNTAX     SEQUENCE OF ExampleBcdProvFreeBcdVector1Entry
   ACCESS     not-accessible
   STATUS     mandatory
   DESCRIPTION
     ""
::= { exampleBcd 1129 }

exampleBcdProvFreeBcdVector1Entry OBJECT-TYPE
   SYNTAX     ExampleBcdProvFreeBcdVector1Entry
   ACCESS     not-accessible
   STATUS     mandatory
   DESCRIPTION
     "An entry in the exampleBcdProvFreeBcdVector1Table."
   INDEX {
      exampleIndex,
      exampleBcdIndex,
      exampleBcdProvFreeBcdVector1Index }
::= { exampleBcdProvFreeBcdVector1Table 1 }

ExampleBcdProvFreeBcdVector1Entry ::= SEQUENCE {
   exampleBcdProvFreeBcdVector1Index
      Integer32,
   exampleBcdProvFreeBcdVector1Value
      DigitString }

exampleBcdProvFreeBcdVector1Index OBJECT-TYPE
   SYNTAX     Integer32 (1..15)
   ACCESS     not-accessible
   STATUS     mandatory
   DESCRIPTION
     "This variable represents the exampleBcdProvFreeBcdVector1Table
      specific index for the exampleBcdProvFreeBcdVector1Table."
::= { exampleBcdProvFreeBcdVector1Entry 1 }

exampleBcdProvFreeBcdVector1Value OBJECT-TYPE
   SYNTAX     DigitString (SIZE (0..5))
   ACCESS     read-write
   STATUS     mandatory
   DESCRIPTION
     "This variable represents an individual value for the
      exampleBcdProvFreeBcdVector1Table."
::= { exampleBcdProvFreeBcdVector1Entry 2 }

exampleBcdProvFreeBcdArrayTable OBJECT-TYPE
   SYNTAX     SEQUENCE OF ExampleBcdProvFreeBcdArrayEntry
   ACCESS     not-accessible
   STATUS     mandatory
   DESCRIPTION
     ""
::= { exampleBcd 1130 }

exampleBcdProvFreeBcdArrayEntry OBJECT-TYPE
   SYNTAX     ExampleBcdProvFreeBcdArrayEntry
   ACCESS     not-accessible
   STATUS     mandatory
   DESCRIPTION
     "An entry in the exampleBcdProvFreeBcdArrayTable."
   INDEX {
      exampleIndex,
      exampleBcdIndex,
      exampleBcdProvFreeBcdArrayRowIndex,
      exampleBcdProvFreeBcdArrayColumnIndex }
::= { exampleBcdProvFreeBcdArrayTable 1 }

ExampleBcdProvFreeBcdArrayEntry ::= SEQUENCE {
   exampleBcdProvFreeBcdArrayRowIndex
      Integer32,
   exampleBcdProvFreeBcdArrayColumnIndex
      Integer32,
   exampleBcdProvFreeBcdArrayValue
      DigitString }

exampleBcdProvFreeBcdArrayRowIndex OBJECT-TYPE
   SYNTAX     Integer32 (0..2)
   ACCESS     not-accessible
   STATUS     mandatory
   DESCRIPTION
     "This variable represents the next to last index for the 
      exampleBcdProvFreeBcdArrayTable."
::= { exampleBcdProvFreeBcdArrayEntry 1 }

exampleBcdProvFreeBcdArrayColumnIndex OBJECT-TYPE
   SYNTAX     Integer32 (0..3)
   ACCESS     not-accessible
   STATUS     mandatory
   DESCRIPTION
     "This variable represents the final index for the 
      exampleBcdProvFreeBcdArrayTable."
::= { exampleBcdProvFreeBcdArrayEntry 2 }

exampleBcdProvFreeBcdArrayValue OBJECT-TYPE
   SYNTAX     DigitString (SIZE (0..5))
   ACCESS     read-write
   STATUS     mandatory
   DESCRIPTION
     "This variable represents an individual value for the
      exampleBcdProvFreeBcdArrayTable."
::= { exampleBcdProvFreeBcdArrayEntry 3 }

exampleBcdProvFreeBcdArray1Table OBJECT-TYPE
   SYNTAX     SEQUENCE OF ExampleBcdProvFreeBcdArray1Entry
   ACCESS     not-accessible
   STATUS     mandatory
   DESCRIPTION
     ""
::= { exampleBcd 1131 }

exampleBcdProvFreeBcdArray1Entry OBJECT-TYPE
   SYNTAX     ExampleBcdProvFreeBcdArray1Entry
   ACCESS     not-accessible
   STATUS     mandatory
   DESCRIPTION
     "An entry in the exampleBcdProvFreeBcdArray1Table."
   INDEX {
      exampleIndex,
      exampleBcdIndex,
      exampleBcdProvFreeBcdArray1RowIndex,
      exampleBcdProvFreeBcdArray1ColumnIndex }
::= { exampleBcdProvFreeBcdArray1Table 1 }

ExampleBcdProvFreeBcdArray1Entry ::= SEQUENCE {
   exampleBcdProvFreeBcdArray1RowIndex
      Integer32,
   exampleBcdProvFreeBcdArray1ColumnIndex
      Integer32,
   exampleBcdProvFreeBcdArray1Value
      DigitString }

exampleBcdProvFreeBcdArray1RowIndex OBJECT-TYPE
   SYNTAX     Integer32 (0..3)
   ACCESS     not-accessible
   STATUS     mandatory
   DESCRIPTION
     "This variable represents the next to last index for the 
      exampleBcdProvFreeBcdArray1Table."
::= { exampleBcdProvFreeBcdArray1Entry 1 }

exampleBcdProvFreeBcdArray1ColumnIndex OBJECT-TYPE
   SYNTAX     Integer32 (0..3)
   ACCESS     not-accessible
   STATUS     mandatory
   DESCRIPTION
     "This variable represents the final index for the 
      exampleBcdProvFreeBcdArray1Table."
::= { exampleBcdProvFreeBcdArray1Entry 2 }

exampleBcdProvFreeBcdArray1Value OBJECT-TYPE
   SYNTAX     DigitString (SIZE (0..5))
   ACCESS     read-write
   STATUS     mandatory
   DESCRIPTION
     "This variable represents an individual value for the
      exampleBcdProvFreeBcdArray1Table."
::= { exampleBcdProvFreeBcdArray1Entry 3 }

exampleBcdProvFreeBcdReplicatedTable OBJECT-TYPE
   SYNTAX     SEQUENCE OF ExampleBcdProvFreeBcdReplicatedEntry
   ACCESS     not-accessible
   STATUS     mandatory
   DESCRIPTION
     ""
::= { exampleBcd 1132 }

exampleBcdProvFreeBcdReplicatedEntry OBJECT-TYPE
   SYNTAX     ExampleBcdProvFreeBcdReplicatedEntry
   ACCESS     not-accessible
   STATUS     mandatory
   DESCRIPTION
     "An entry in the exampleBcdProvFreeBcdReplicatedTable."
   INDEX {
      exampleIndex,
      exampleBcdIndex,
      exampleBcdProvFreeBcdReplicatedIndex }
::= { exampleBcdProvFreeBcdReplicatedTable 1 }

ExampleBcdProvFreeBcdReplicatedEntry ::= SEQUENCE {
   exampleBcdProvFreeBcdReplicatedIndex
      DigitString,
   exampleBcdProvFreeBcdReplicatedValue
      DigitString,
   exampleBcdProvFreeBcdReplicatedRowStatus
      RowStatus }

exampleBcdProvFreeBcdReplicatedIndex OBJECT-TYPE
   SYNTAX     DigitString (SIZE (0..5))
   ACCESS     not-accessible
   STATUS     mandatory
   DESCRIPTION
     "This variable represents the index for the exampleBcdProvFreeBcdReplicatedTable."
::= { exampleBcdProvFreeBcdReplicatedEntry 1 }

exampleBcdProvFreeBcdReplicatedValue OBJECT-TYPE
   SYNTAX     DigitString (SIZE (0..16))
   ACCESS     read-write
   STATUS     mandatory
   DESCRIPTION
     "This variable represents an individual value for the
      exampleBcdProvFreeBcdReplicatedTable."
::= { exampleBcdProvFreeBcdReplicatedEntry 2 }

exampleBcdProvFreeBcdReplicatedRowStatus OBJECT-TYPE
   SYNTAX     RowStatus 
   ACCESS     write-only
   STATUS     mandatory
   DESCRIPTION
     "This variable is used to control the addition and deletion 
      of individual values of the exampleBcdProvFreeBcdReplicatedTable."
::= { exampleBcdProvFreeBcdReplicatedEntry 3 }

exampleBcdProvFreeBcdReplicated1Table OBJECT-TYPE
   SYNTAX     SEQUENCE OF ExampleBcdProvFreeBcdReplicated1Entry
   ACCESS     not-accessible
   STATUS     mandatory
   DESCRIPTION
     ""
::= { exampleBcd 1133 }

exampleBcdProvFreeBcdReplicated1Entry OBJECT-TYPE
   SYNTAX     ExampleBcdProvFreeBcdReplicated1Entry
   ACCESS     not-accessible
   STATUS     mandatory
   DESCRIPTION
     "An entry in the exampleBcdProvFreeBcdReplicated1Table."
   INDEX {
      exampleIndex,
      exampleBcdIndex,
      exampleBcdProvFreeBcdReplicated1Index }
::= { exampleBcdProvFreeBcdReplicated1Table 1 }

ExampleBcdProvFreeBcdReplicated1Entry ::= SEQUENCE {
   exampleBcdProvFreeBcdReplicated1Index
      DigitString,
   exampleBcdProvFreeBcdReplicated1Value
      DigitString,
   exampleBcdProvFreeBcdReplicated1RowStatus
      RowStatus }

exampleBcdProvFreeBcdReplicated1Index OBJECT-TYPE
   SYNTAX     DigitString (SIZE (1..7))
   ACCESS     not-accessible
   STATUS     mandatory
   DESCRIPTION
     "This variable represents the index for the exampleBcdProvFreeBcdReplicated1Table."
::= { exampleBcdProvFreeBcdReplicated1Entry 1 }

exampleBcdProvFreeBcdReplicated1Value OBJECT-TYPE
   SYNTAX     DigitString (SIZE (0..5))
   ACCESS     read-write
   STATUS     mandatory
   DESCRIPTION
     "This variable represents an individual value for the
      exampleBcdProvFreeBcdReplicated1Table."
::= { exampleBcdProvFreeBcdReplicated1Entry 2 }

exampleBcdProvFreeBcdReplicated1RowStatus OBJECT-TYPE
   SYNTAX     RowStatus 
   ACCESS     write-only
   STATUS     mandatory
   DESCRIPTION
     "This variable is used to control the addition and deletion 
      of individual values of the exampleBcdProvFreeBcdReplicated1Table."
::= { exampleBcdProvFreeBcdReplicated1Entry 3 }

exampleBcdProvFreeBcdListTable OBJECT-TYPE
   SYNTAX     SEQUENCE OF ExampleBcdProvFreeBcdListEntry
   ACCESS     not-accessible
   STATUS     mandatory
   DESCRIPTION
     ""
::= { exampleBcd 1134 }

exampleBcdProvFreeBcdListEntry OBJECT-TYPE
   SYNTAX     ExampleBcdProvFreeBcdListEntry
   ACCESS     not-accessible
   STATUS     mandatory
   DESCRIPTION
     "An entry in the exampleBcdProvFreeBcdListTable."
   INDEX {
      exampleIndex,
      exampleBcdIndex,
      exampleBcdProvFreeBcdListValue }
::= { exampleBcdProvFreeBcdListTable 1 }

ExampleBcdProvFreeBcdListEntry ::= SEQUENCE {
   exampleBcdProvFreeBcdListValue
      DigitString,
   exampleBcdProvFreeBcdListRowStatus
      RowStatus }

exampleBcdProvFreeBcdListValue OBJECT-TYPE
   SYNTAX     DigitString (SIZE (0..16))
   ACCESS     read-write
   STATUS     mandatory
   DESCRIPTION
     "This variable represents both the value and the index for the
      exampleBcdProvFreeBcdListTable."
::= { exampleBcdProvFreeBcdListEntry 1 }

exampleBcdProvFreeBcdListRowStatus OBJECT-TYPE
   SYNTAX     RowStatus 
   ACCESS     write-only
   STATUS     mandatory
   DESCRIPTION
     "This variable is used to control the addition and deletion 
      of individual values of the exampleBcdProvFreeBcdListTable."
::= { exampleBcdProvFreeBcdListEntry 2 }

exampleBcdProvFreeBcdList1Table OBJECT-TYPE
   SYNTAX     SEQUENCE OF ExampleBcdProvFreeBcdList1Entry
   ACCESS     not-accessible
   STATUS     mandatory
   DESCRIPTION
     ""
::= { exampleBcd 1135 }

exampleBcdProvFreeBcdList1Entry OBJECT-TYPE
   SYNTAX     ExampleBcdProvFreeBcdList1Entry
   ACCESS     not-accessible
   STATUS     mandatory
   DESCRIPTION
     "An entry in the exampleBcdProvFreeBcdList1Table."
   INDEX {
      exampleIndex,
      exampleBcdIndex,
      exampleBcdProvFreeBcdList1Value }
::= { exampleBcdProvFreeBcdList1Table 1 }

ExampleBcdProvFreeBcdList1Entry ::= SEQUENCE {
   exampleBcdProvFreeBcdList1Value
      DigitString,
   exampleBcdProvFreeBcdList1RowStatus
      RowStatus }

exampleBcdProvFreeBcdList1Value OBJECT-TYPE
   SYNTAX     DigitString (SIZE (0..16))
   ACCESS     read-write
   STATUS     mandatory
   DESCRIPTION
     "This variable represents both the value and the index for the
      exampleBcdProvFreeBcdList1Table."
::= { exampleBcdProvFreeBcdList1Entry 1 }

exampleBcdProvFreeBcdList1RowStatus OBJECT-TYPE
   SYNTAX     RowStatus 
   ACCESS     write-only
   STATUS     mandatory
   DESCRIPTION
     "This variable is used to control the addition and deletion 
      of individual values of the exampleBcdProvFreeBcdList1Table."
::= { exampleBcdProvFreeBcdList1Entry 2 }



exampleWildBcd OBJECT IDENTIFIER ::= { example 10 }



exampleWildBcdRowStatusTable OBJECT-TYPE
   SYNTAX     SEQUENCE OF ExampleWildBcdRowStatusEntry
   ACCESS     not-accessible
   STATUS     mandatory
   DESCRIPTION
     "This entry controls the addition and deletion of 
      exampleWildBcd components."
::= { exampleWildBcd 1 }

exampleWildBcdRowStatusEntry OBJECT-TYPE
   SYNTAX     ExampleWildBcdRowStatusEntry
   ACCESS     not-accessible
   STATUS     mandatory
   DESCRIPTION
     "A single entry in the table represents a single 
      exampleWildBcd component."
   INDEX {
      exampleIndex,
      exampleWildBcdIndex }
::= { exampleWildBcdRowStatusTable 1 }

ExampleWildBcdRowStatusEntry ::= SEQUENCE {
   exampleWildBcdRowStatus
      RowStatus,
   exampleWildBcdComponentName
      DisplayString,
   exampleWildBcdStorageType
      StorageType,
   exampleWildBcdIndex
      WildcardedDigitString }

exampleWildBcdRowStatus OBJECT-TYPE
   SYNTAX     RowStatus 
   ACCESS     read-write
   STATUS     mandatory
   DESCRIPTION
     "This variable is used as the basis for SNMP naming of
      exampleWildBcd components.
      These components can be added and deleted."
::= { exampleWildBcdRowStatusEntry 1 }

exampleWildBcdComponentName OBJECT-TYPE
   SYNTAX     DisplayString 
   ACCESS     read-only
   STATUS     mandatory
   DESCRIPTION
     "This variable provides the component's string name for
      use with the ASCII Console Interface"
::= { exampleWildBcdRowStatusEntry 2 }

exampleWildBcdStorageType OBJECT-TYPE
   SYNTAX     StorageType 
   ACCESS     read-only
   STATUS     mandatory
   DESCRIPTION
     "This variable represents the storage type value for the
      exampleWildBcd tables."
::= { exampleWildBcdRowStatusEntry 4 }

exampleWildBcdIndex OBJECT-TYPE
   SYNTAX     WildcardedDigitString (SIZE (1..10))
   ACCESS     not-accessible
   STATUS     mandatory
   DESCRIPTION
     "This variable represents the index for the exampleWildBcd tables."
::= { exampleWildBcdRowStatusEntry 10 }

exampleWildBcdOperationalTable OBJECT-TYPE
   SYNTAX     SEQUENCE OF ExampleWildBcdOperationalEntry
   ACCESS     not-accessible
   STATUS     mandatory
   DESCRIPTION
     ""
::= { exampleWildBcd 10 }

exampleWildBcdOperationalEntry OBJECT-TYPE
   SYNTAX     ExampleWildBcdOperationalEntry
   ACCESS     not-accessible
   STATUS     mandatory
   DESCRIPTION
     "An entry in the exampleWildBcdOperationalTable."
   INDEX {
      exampleIndex,
      exampleWildBcdIndex }
::= { exampleWildBcdOperationalTable 1 }

ExampleWildBcdOperationalEntry ::= SEQUENCE {
   exampleWildBcdOperStructWildBcd
      WildcardedDigitString,
   exampleWildBcdOperFreeWildBcd
      WildcardedDigitString }

exampleWildBcdOperStructWildBcd OBJECT-TYPE
   SYNTAX     WildcardedDigitString (SIZE (0..16))
   ACCESS     read-write
   STATUS     mandatory
   DESCRIPTION
     ""
::= { exampleWildBcdOperationalEntry 1 }

exampleWildBcdOperFreeWildBcd OBJECT-TYPE
   SYNTAX     WildcardedDigitString (SIZE (0..16))
   ACCESS     read-write
   STATUS     mandatory
   DESCRIPTION
     ""
::= { exampleWildBcdOperationalEntry 2 }

exampleWildBcdProvisionalTable OBJECT-TYPE
   SYNTAX     SEQUENCE OF ExampleWildBcdProvisionalEntry
   ACCESS     not-accessible
   STATUS     mandatory
   DESCRIPTION
     ""
::= { exampleWildBcd 11 }

exampleWildBcdProvisionalEntry OBJECT-TYPE
   SYNTAX     ExampleWildBcdProvisionalEntry
   ACCESS     not-accessible
   STATUS     mandatory
   DESCRIPTION
     "An entry in the exampleWildBcdProvisionalTable."
   INDEX {
      exampleIndex,
      exampleWildBcdIndex }
::= { exampleWildBcdProvisionalTable 1 }

ExampleWildBcdProvisionalEntry ::= SEQUENCE {
   exampleWildBcdProvStructWildBcd
      WildcardedDigitString,
   exampleWildBcdProvFreeWildBcd
      WildcardedDigitString }

exampleWildBcdProvStructWildBcd OBJECT-TYPE
   SYNTAX     WildcardedDigitString (SIZE (0..16))
   ACCESS     read-write
   STATUS     mandatory
   DESCRIPTION
     ""
   DEFVAL     { '30313233343536373839'H }  -- "0123456789"
::= { exampleWildBcdProvisionalEntry 1 }

exampleWildBcdProvFreeWildBcd OBJECT-TYPE
   SYNTAX     WildcardedDigitString (SIZE (4..16))
   ACCESS     read-write
   STATUS     mandatory
   DESCRIPTION
     ""
   DEFVAL     { '31323334353637383930'H }  -- "1234567890"
::= { exampleWildBcdProvisionalEntry 2 }

exampleWildBcdOperStructWildBcdVectorTable OBJECT-TYPE
   SYNTAX     SEQUENCE OF ExampleWildBcdOperStructWildBcdVectorEntry
   ACCESS     not-accessible
   STATUS     mandatory
   DESCRIPTION
     ""
::= { exampleWildBcd 1136 }

exampleWildBcdOperStructWildBcdVectorEntry OBJECT-TYPE
   SYNTAX     ExampleWildBcdOperStructWildBcdVectorEntry
   ACCESS     not-accessible
   STATUS     mandatory
   DESCRIPTION
     "An entry in the exampleWildBcdOperStructWildBcdVectorTable."
   INDEX {
      exampleIndex,
      exampleWildBcdIndex,
      exampleWildBcdOperStructWildBcdVectorIndex }
::= { exampleWildBcdOperStructWildBcdVectorTable 1 }

ExampleWildBcdOperStructWildBcdVectorEntry ::= SEQUENCE {
   exampleWildBcdOperStructWildBcdVectorIndex
      Integer32,
   exampleWildBcdOperStructWildBcdVectorValue
      WildcardedDigitString }

exampleWildBcdOperStructWildBcdVectorIndex OBJECT-TYPE
   SYNTAX     Integer32 (0..9)
   ACCESS     not-accessible
   STATUS     mandatory
   DESCRIPTION
     "This variable represents the exampleWildBcdOperStructWildBcdVectorTable
      specific index for the exampleWildBcdOperStructWildBcdVectorTable."
::= { exampleWildBcdOperStructWildBcdVectorEntry 1 }

exampleWildBcdOperStructWildBcdVectorValue OBJECT-TYPE
   SYNTAX     WildcardedDigitString (SIZE (0..5))
   ACCESS     read-write
   STATUS     mandatory
   DESCRIPTION
     "This variable represents an individual value for the
      exampleWildBcdOperStructWildBcdVectorTable."
::= { exampleWildBcdOperStructWildBcdVectorEntry 2 }

exampleWildBcdOperStructWildBcdArrayTable OBJECT-TYPE
   SYNTAX     SEQUENCE OF ExampleWildBcdOperStructWildBcdArrayEntry
   ACCESS     not-accessible
   STATUS     mandatory
   DESCRIPTION
     ""
::= { exampleWildBcd 1137 }

exampleWildBcdOperStructWildBcdArrayEntry OBJECT-TYPE
   SYNTAX     ExampleWildBcdOperStructWildBcdArrayEntry
   ACCESS     not-accessible
   STATUS     mandatory
   DESCRIPTION
     "An entry in the exampleWildBcdOperStructWildBcdArrayTable."
   INDEX {
      exampleIndex,
      exampleWildBcdIndex,
      exampleWildBcdOperStructWildBcdArrayRowIndex,
      exampleWildBcdOperStructWildBcdArrayColumnIndex }
::= { exampleWildBcdOperStructWildBcdArrayTable 1 }

ExampleWildBcdOperStructWildBcdArrayEntry ::= SEQUENCE {
   exampleWildBcdOperStructWildBcdArrayRowIndex
      Integer32,
   exampleWildBcdOperStructWildBcdArrayColumnIndex
      Integer32,
   exampleWildBcdOperStructWildBcdArrayValue
      WildcardedDigitString }

exampleWildBcdOperStructWildBcdArrayRowIndex OBJECT-TYPE
   SYNTAX     Integer32 (0..2)
   ACCESS     not-accessible
   STATUS     mandatory
   DESCRIPTION
     "This variable represents the next to last index for the 
      exampleWildBcdOperStructWildBcdArrayTable."
::= { exampleWildBcdOperStructWildBcdArrayEntry 1 }

exampleWildBcdOperStructWildBcdArrayColumnIndex OBJECT-TYPE
   SYNTAX     Integer32 (0..3)
   ACCESS     not-accessible
   STATUS     mandatory
   DESCRIPTION
     "This variable represents the final index for the 
      exampleWildBcdOperStructWildBcdArrayTable."
::= { exampleWildBcdOperStructWildBcdArrayEntry 2 }

exampleWildBcdOperStructWildBcdArrayValue OBJECT-TYPE
   SYNTAX     WildcardedDigitString (SIZE (0..5))
   ACCESS     read-write
   STATUS     mandatory
   DESCRIPTION
     "This variable represents an individual value for the
      exampleWildBcdOperStructWildBcdArrayTable."
::= { exampleWildBcdOperStructWildBcdArrayEntry 3 }

exampleWildBcdOperFreeWildBcdVectorTable OBJECT-TYPE
   SYNTAX     SEQUENCE OF ExampleWildBcdOperFreeWildBcdVectorEntry
   ACCESS     not-accessible
   STATUS     mandatory
   DESCRIPTION
     ""
::= { exampleWildBcd 1138 }

exampleWildBcdOperFreeWildBcdVectorEntry OBJECT-TYPE
   SYNTAX     ExampleWildBcdOperFreeWildBcdVectorEntry
   ACCESS     not-accessible
   STATUS     mandatory
   DESCRIPTION
     "An entry in the exampleWildBcdOperFreeWildBcdVectorTable."
   INDEX {
      exampleIndex,
      exampleWildBcdIndex,
      exampleWildBcdOperFreeWildBcdVectorIndex }
::= { exampleWildBcdOperFreeWildBcdVectorTable 1 }

ExampleWildBcdOperFreeWildBcdVectorEntry ::= SEQUENCE {
   exampleWildBcdOperFreeWildBcdVectorIndex
      Integer32,
   exampleWildBcdOperFreeWildBcdVectorValue
      WildcardedDigitString }

exampleWildBcdOperFreeWildBcdVectorIndex OBJECT-TYPE
   SYNTAX     Integer32 (0..9)
   ACCESS     not-accessible
   STATUS     mandatory
   DESCRIPTION
     "This variable represents the exampleWildBcdOperFreeWildBcdVectorTable
      specific index for the exampleWildBcdOperFreeWildBcdVectorTable."
::= { exampleWildBcdOperFreeWildBcdVectorEntry 1 }

exampleWildBcdOperFreeWildBcdVectorValue OBJECT-TYPE
   SYNTAX     WildcardedDigitString (SIZE (0..5))
   ACCESS     read-write
   STATUS     mandatory
   DESCRIPTION
     "This variable represents an individual value for the
      exampleWildBcdOperFreeWildBcdVectorTable."
::= { exampleWildBcdOperFreeWildBcdVectorEntry 2 }

exampleWildBcdOperFreeWildBcdArrayTable OBJECT-TYPE
   SYNTAX     SEQUENCE OF ExampleWildBcdOperFreeWildBcdArrayEntry
   ACCESS     not-accessible
   STATUS     mandatory
   DESCRIPTION
     ""
::= { exampleWildBcd 1139 }

exampleWildBcdOperFreeWildBcdArrayEntry OBJECT-TYPE
   SYNTAX     ExampleWildBcdOperFreeWildBcdArrayEntry
   ACCESS     not-accessible
   STATUS     mandatory
   DESCRIPTION
     "An entry in the exampleWildBcdOperFreeWildBcdArrayTable."
   INDEX {
      exampleIndex,
      exampleWildBcdIndex,
      exampleWildBcdOperFreeWildBcdArrayRowIndex,
      exampleWildBcdOperFreeWildBcdArrayColumnIndex }
::= { exampleWildBcdOperFreeWildBcdArrayTable 1 }

ExampleWildBcdOperFreeWildBcdArrayEntry ::= SEQUENCE {
   exampleWildBcdOperFreeWildBcdArrayRowIndex
      Integer32,
   exampleWildBcdOperFreeWildBcdArrayColumnIndex
      Integer32,
   exampleWildBcdOperFreeWildBcdArrayValue
      WildcardedDigitString }

exampleWildBcdOperFreeWildBcdArrayRowIndex OBJECT-TYPE
   SYNTAX     Integer32 (0..2)
   ACCESS     not-accessible
   STATUS     mandatory
   DESCRIPTION
     "This variable represents the next to last index for the 
      exampleWildBcdOperFreeWildBcdArrayTable."
::= { exampleWildBcdOperFreeWildBcdArrayEntry 1 }

exampleWildBcdOperFreeWildBcdArrayColumnIndex OBJECT-TYPE
   SYNTAX     Integer32 (0..3)
   ACCESS     not-accessible
   STATUS     mandatory
   DESCRIPTION
     "This variable represents the final index for the 
      exampleWildBcdOperFreeWildBcdArrayTable."
::= { exampleWildBcdOperFreeWildBcdArrayEntry 2 }

exampleWildBcdOperFreeWildBcdArrayValue OBJECT-TYPE
   SYNTAX     WildcardedDigitString (SIZE (0..5))
   ACCESS     read-write
   STATUS     mandatory
   DESCRIPTION
     "This variable represents an individual value for the
      exampleWildBcdOperFreeWildBcdArrayTable."
::= { exampleWildBcdOperFreeWildBcdArrayEntry 3 }

exampleWildBcdOperFreeWildBcdReplicatedTable OBJECT-TYPE
   SYNTAX     SEQUENCE OF ExampleWildBcdOperFreeWildBcdReplicatedEntry
   ACCESS     not-accessible
   STATUS     mandatory
   DESCRIPTION
     ""
::= { exampleWildBcd 1140 }

exampleWildBcdOperFreeWildBcdReplicatedEntry OBJECT-TYPE
   SYNTAX     ExampleWildBcdOperFreeWildBcdReplicatedEntry
   ACCESS     not-accessible
   STATUS     mandatory
   DESCRIPTION
     "An entry in the exampleWildBcdOperFreeWildBcdReplicatedTable."
   INDEX {
      exampleIndex,
      exampleWildBcdIndex,
      exampleWildBcdOperFreeWildBcdReplicatedIndex }
::= { exampleWildBcdOperFreeWildBcdReplicatedTable 1 }

ExampleWildBcdOperFreeWildBcdReplicatedEntry ::= SEQUENCE {
   exampleWildBcdOperFreeWildBcdReplicatedIndex
      WildcardedDigitString,
   exampleWildBcdOperFreeWildBcdReplicatedValue
      WildcardedDigitString,
   exampleWildBcdOperFreeWildBcdReplicatedRowStatus
      RowStatus }

exampleWildBcdOperFreeWildBcdReplicatedIndex OBJECT-TYPE
   SYNTAX     WildcardedDigitString (SIZE (0..5))
   ACCESS     not-accessible
   STATUS     mandatory
   DESCRIPTION
     "This variable represents the index for the exampleWildBcdOperFreeWildBcdReplicatedTable."
::= { exampleWildBcdOperFreeWildBcdReplicatedEntry 1 }

exampleWildBcdOperFreeWildBcdReplicatedValue OBJECT-TYPE
   SYNTAX     WildcardedDigitString (SIZE (0..16))
   ACCESS     read-write
   STATUS     mandatory
   DESCRIPTION
     "This variable represents an individual value for the
      exampleWildBcdOperFreeWildBcdReplicatedTable."
::= { exampleWildBcdOperFreeWildBcdReplicatedEntry 2 }

exampleWildBcdOperFreeWildBcdReplicatedRowStatus OBJECT-TYPE
   SYNTAX     RowStatus 
   ACCESS     write-only
   STATUS     mandatory
   DESCRIPTION
     "This variable is used to control the addition and deletion 
      of individual values of the exampleWildBcdOperFreeWildBcdReplicatedTable."
::= { exampleWildBcdOperFreeWildBcdReplicatedEntry 3 }

exampleWildBcdOperFreeWildBcdListTable OBJECT-TYPE
   SYNTAX     SEQUENCE OF ExampleWildBcdOperFreeWildBcdListEntry
   ACCESS     not-accessible
   STATUS     mandatory
   DESCRIPTION
     ""
::= { exampleWildBcd 1141 }

exampleWildBcdOperFreeWildBcdListEntry OBJECT-TYPE
   SYNTAX     ExampleWildBcdOperFreeWildBcdListEntry
   ACCESS     not-accessible
   STATUS     mandatory
   DESCRIPTION
     "An entry in the exampleWildBcdOperFreeWildBcdListTable."
   INDEX {
      exampleIndex,
      exampleWildBcdIndex,
      exampleWildBcdOperFreeWildBcdListValue }
::= { exampleWildBcdOperFreeWildBcdListTable 1 }

ExampleWildBcdOperFreeWildBcdListEntry ::= SEQUENCE {
   exampleWildBcdOperFreeWildBcdListValue
      WildcardedDigitString,
   exampleWildBcdOperFreeWildBcdListRowStatus
      RowStatus }

exampleWildBcdOperFreeWildBcdListValue OBJECT-TYPE
   SYNTAX     WildcardedDigitString (SIZE (0..16))
   ACCESS     read-write
   STATUS     mandatory
   DESCRIPTION
     "This variable represents both the value and the index for the
      exampleWildBcdOperFreeWildBcdListTable."
::= { exampleWildBcdOperFreeWildBcdListEntry 1 }

exampleWildBcdOperFreeWildBcdListRowStatus OBJECT-TYPE
   SYNTAX     RowStatus 
   ACCESS     write-only
   STATUS     mandatory
   DESCRIPTION
     "This variable is used to control the addition and deletion 
      of individual values of the exampleWildBcdOperFreeWildBcdListTable."
::= { exampleWildBcdOperFreeWildBcdListEntry 2 }

exampleWildBcdProvStructWildBcdVectorTable OBJECT-TYPE
   SYNTAX     SEQUENCE OF ExampleWildBcdProvStructWildBcdVectorEntry
   ACCESS     not-accessible
   STATUS     mandatory
   DESCRIPTION
     ""
::= { exampleWildBcd 1142 }

exampleWildBcdProvStructWildBcdVectorEntry OBJECT-TYPE
   SYNTAX     ExampleWildBcdProvStructWildBcdVectorEntry
   ACCESS     not-accessible
   STATUS     mandatory
   DESCRIPTION
     "An entry in the exampleWildBcdProvStructWildBcdVectorTable."
   INDEX {
      exampleIndex,
      exampleWildBcdIndex,
      exampleWildBcdProvStructWildBcdVectorIndex }
::= { exampleWildBcdProvStructWildBcdVectorTable 1 }

ExampleWildBcdProvStructWildBcdVectorEntry ::= SEQUENCE {
   exampleWildBcdProvStructWildBcdVectorIndex
      Integer32,
   exampleWildBcdProvStructWildBcdVectorValue
      WildcardedDigitString }

exampleWildBcdProvStructWildBcdVectorIndex OBJECT-TYPE
   SYNTAX     Integer32 (0..9)
   ACCESS     not-accessible
   STATUS     mandatory
   DESCRIPTION
     "This variable represents the exampleWildBcdProvStructWildBcdVectorTable
      specific index for the exampleWildBcdProvStructWildBcdVectorTable."
::= { exampleWildBcdProvStructWildBcdVectorEntry 1 }

exampleWildBcdProvStructWildBcdVectorValue OBJECT-TYPE
   SYNTAX     WildcardedDigitString (SIZE (0..5))
   ACCESS     read-write
   STATUS     mandatory
   DESCRIPTION
     "This variable represents an individual value for the
      exampleWildBcdProvStructWildBcdVectorTable."
::= { exampleWildBcdProvStructWildBcdVectorEntry 2 }

exampleWildBcdProvStructWildBcdArrayTable OBJECT-TYPE
   SYNTAX     SEQUENCE OF ExampleWildBcdProvStructWildBcdArrayEntry
   ACCESS     not-accessible
   STATUS     mandatory
   DESCRIPTION
     ""
::= { exampleWildBcd 1143 }

exampleWildBcdProvStructWildBcdArrayEntry OBJECT-TYPE
   SYNTAX     ExampleWildBcdProvStructWildBcdArrayEntry
   ACCESS     not-accessible
   STATUS     mandatory
   DESCRIPTION
     "An entry in the exampleWildBcdProvStructWildBcdArrayTable."
   INDEX {
      exampleIndex,
      exampleWildBcdIndex,
      exampleWildBcdProvStructWildBcdArrayRowIndex,
      exampleWildBcdProvStructWildBcdArrayColumnIndex }
::= { exampleWildBcdProvStructWildBcdArrayTable 1 }

ExampleWildBcdProvStructWildBcdArrayEntry ::= SEQUENCE {
   exampleWildBcdProvStructWildBcdArrayRowIndex
      Integer32,
   exampleWildBcdProvStructWildBcdArrayColumnIndex
      Integer32,
   exampleWildBcdProvStructWildBcdArrayValue
      WildcardedDigitString }

exampleWildBcdProvStructWildBcdArrayRowIndex OBJECT-TYPE
   SYNTAX     Integer32 (0..2)
   ACCESS     not-accessible
   STATUS     mandatory
   DESCRIPTION
     "This variable represents the next to last index for the 
      exampleWildBcdProvStructWildBcdArrayTable."
::= { exampleWildBcdProvStructWildBcdArrayEntry 1 }

exampleWildBcdProvStructWildBcdArrayColumnIndex OBJECT-TYPE
   SYNTAX     Integer32 (0..3)
   ACCESS     not-accessible
   STATUS     mandatory
   DESCRIPTION
     "This variable represents the final index for the 
      exampleWildBcdProvStructWildBcdArrayTable."
::= { exampleWildBcdProvStructWildBcdArrayEntry 2 }

exampleWildBcdProvStructWildBcdArrayValue OBJECT-TYPE
   SYNTAX     WildcardedDigitString (SIZE (0..5))
   ACCESS     read-write
   STATUS     mandatory
   DESCRIPTION
     "This variable represents an individual value for the
      exampleWildBcdProvStructWildBcdArrayTable."
::= { exampleWildBcdProvStructWildBcdArrayEntry 3 }

exampleWildBcdProvFreeWildBcdVectorTable OBJECT-TYPE
   SYNTAX     SEQUENCE OF ExampleWildBcdProvFreeWildBcdVectorEntry
   ACCESS     not-accessible
   STATUS     mandatory
   DESCRIPTION
     ""
::= { exampleWildBcd 1144 }

exampleWildBcdProvFreeWildBcdVectorEntry OBJECT-TYPE
   SYNTAX     ExampleWildBcdProvFreeWildBcdVectorEntry
   ACCESS     not-accessible
   STATUS     mandatory
   DESCRIPTION
     "An entry in the exampleWildBcdProvFreeWildBcdVectorTable."
   INDEX {
      exampleIndex,
      exampleWildBcdIndex,
      exampleWildBcdProvFreeWildBcdVectorIndex }
::= { exampleWildBcdProvFreeWildBcdVectorTable 1 }

ExampleWildBcdProvFreeWildBcdVectorEntry ::= SEQUENCE {
   exampleWildBcdProvFreeWildBcdVectorIndex
      Integer32,
   exampleWildBcdProvFreeWildBcdVectorValue
      WildcardedDigitString }

exampleWildBcdProvFreeWildBcdVectorIndex OBJECT-TYPE
   SYNTAX     Integer32 (0..9)
   ACCESS     not-accessible
   STATUS     mandatory
   DESCRIPTION
     "This variable represents the exampleWildBcdProvFreeWildBcdVectorTable
      specific index for the exampleWildBcdProvFreeWildBcdVectorTable."
::= { exampleWildBcdProvFreeWildBcdVectorEntry 1 }

exampleWildBcdProvFreeWildBcdVectorValue OBJECT-TYPE
   SYNTAX     WildcardedDigitString (SIZE (0..5))
   ACCESS     read-write
   STATUS     mandatory
   DESCRIPTION
     "This variable represents an individual value for the
      exampleWildBcdProvFreeWildBcdVectorTable."
::= { exampleWildBcdProvFreeWildBcdVectorEntry 2 }

exampleWildBcdProvFreeWildBcdArrayTable OBJECT-TYPE
   SYNTAX     SEQUENCE OF ExampleWildBcdProvFreeWildBcdArrayEntry
   ACCESS     not-accessible
   STATUS     mandatory
   DESCRIPTION
     ""
::= { exampleWildBcd 1145 }

exampleWildBcdProvFreeWildBcdArrayEntry OBJECT-TYPE
   SYNTAX     ExampleWildBcdProvFreeWildBcdArrayEntry
   ACCESS     not-accessible
   STATUS     mandatory
   DESCRIPTION
     "An entry in the exampleWildBcdProvFreeWildBcdArrayTable."
   INDEX {
      exampleIndex,
      exampleWildBcdIndex,
      exampleWildBcdProvFreeWildBcdArrayRowIndex,
      exampleWildBcdProvFreeWildBcdArrayColumnIndex }
::= { exampleWildBcdProvFreeWildBcdArrayTable 1 }

ExampleWildBcdProvFreeWildBcdArrayEntry ::= SEQUENCE {
   exampleWildBcdProvFreeWildBcdArrayRowIndex
      Integer32,
   exampleWildBcdProvFreeWildBcdArrayColumnIndex
      Integer32,
   exampleWildBcdProvFreeWildBcdArrayValue
      WildcardedDigitString }

exampleWildBcdProvFreeWildBcdArrayRowIndex OBJECT-TYPE
   SYNTAX     Integer32 (0..2)
   ACCESS     not-accessible
   STATUS     mandatory
   DESCRIPTION
     "This variable represents the next to last index for the 
      exampleWildBcdProvFreeWildBcdArrayTable."
::= { exampleWildBcdProvFreeWildBcdArrayEntry 1 }

exampleWildBcdProvFreeWildBcdArrayColumnIndex OBJECT-TYPE
   SYNTAX     Integer32 (0..3)
   ACCESS     not-accessible
   STATUS     mandatory
   DESCRIPTION
     "This variable represents the final index for the 
      exampleWildBcdProvFreeWildBcdArrayTable."
::= { exampleWildBcdProvFreeWildBcdArrayEntry 2 }

exampleWildBcdProvFreeWildBcdArrayValue OBJECT-TYPE
   SYNTAX     WildcardedDigitString (SIZE (0..5))
   ACCESS     read-write
   STATUS     mandatory
   DESCRIPTION
     "This variable represents an individual value for the
      exampleWildBcdProvFreeWildBcdArrayTable."
::= { exampleWildBcdProvFreeWildBcdArrayEntry 3 }

exampleWildBcdProvFreeWildBcdReplicatedTable OBJECT-TYPE
   SYNTAX     SEQUENCE OF ExampleWildBcdProvFreeWildBcdReplicatedEntry
   ACCESS     not-accessible
   STATUS     mandatory
   DESCRIPTION
     ""
::= { exampleWildBcd 1146 }

exampleWildBcdProvFreeWildBcdReplicatedEntry OBJECT-TYPE
   SYNTAX     ExampleWildBcdProvFreeWildBcdReplicatedEntry
   ACCESS     not-accessible
   STATUS     mandatory
   DESCRIPTION
     "An entry in the exampleWildBcdProvFreeWildBcdReplicatedTable."
   INDEX {
      exampleIndex,
      exampleWildBcdIndex,
      exampleWildBcdProvFreeWildBcdReplicatedIndex }
::= { exampleWildBcdProvFreeWildBcdReplicatedTable 1 }

ExampleWildBcdProvFreeWildBcdReplicatedEntry ::= SEQUENCE {
   exampleWildBcdProvFreeWildBcdReplicatedIndex
      WildcardedDigitString,
   exampleWildBcdProvFreeWildBcdReplicatedValue
      WildcardedDigitString,
   exampleWildBcdProvFreeWildBcdReplicatedRowStatus
      RowStatus }

exampleWildBcdProvFreeWildBcdReplicatedIndex OBJECT-TYPE
   SYNTAX     WildcardedDigitString (SIZE (0..5))
   ACCESS     not-accessible
   STATUS     mandatory
   DESCRIPTION
     "This variable represents the index for the exampleWildBcdProvFreeWildBcdReplicatedTable."
::= { exampleWildBcdProvFreeWildBcdReplicatedEntry 1 }

exampleWildBcdProvFreeWildBcdReplicatedValue OBJECT-TYPE
   SYNTAX     WildcardedDigitString (SIZE (0..16))
   ACCESS     read-write
   STATUS     mandatory
   DESCRIPTION
     "This variable represents an individual value for the
      exampleWildBcdProvFreeWildBcdReplicatedTable."
::= { exampleWildBcdProvFreeWildBcdReplicatedEntry 2 }

exampleWildBcdProvFreeWildBcdReplicatedRowStatus OBJECT-TYPE
   SYNTAX     RowStatus 
   ACCESS     write-only
   STATUS     mandatory
   DESCRIPTION
     "This variable is used to control the addition and deletion 
      of individual values of the exampleWildBcdProvFreeWildBcdReplicatedTable."
::= { exampleWildBcdProvFreeWildBcdReplicatedEntry 3 }

exampleWildBcdProvFreeWildBcdListTable OBJECT-TYPE
   SYNTAX     SEQUENCE OF ExampleWildBcdProvFreeWildBcdListEntry
   ACCESS     not-accessible
   STATUS     mandatory
   DESCRIPTION
     ""
::= { exampleWildBcd 1147 }

exampleWildBcdProvFreeWildBcdListEntry OBJECT-TYPE
   SYNTAX     ExampleWildBcdProvFreeWildBcdListEntry
   ACCESS     not-accessible
   STATUS     mandatory
   DESCRIPTION
     "An entry in the exampleWildBcdProvFreeWildBcdListTable."
   INDEX {
      exampleIndex,
      exampleWildBcdIndex,
      exampleWildBcdProvFreeWildBcdListValue }
::= { exampleWildBcdProvFreeWildBcdListTable 1 }

ExampleWildBcdProvFreeWildBcdListEntry ::= SEQUENCE {
   exampleWildBcdProvFreeWildBcdListValue
      WildcardedDigitString,
   exampleWildBcdProvFreeWildBcdListRowStatus
      RowStatus }

exampleWildBcdProvFreeWildBcdListValue OBJECT-TYPE
   SYNTAX     WildcardedDigitString (SIZE (0..16))
   ACCESS     read-write
   STATUS     mandatory
   DESCRIPTION
     "This variable represents both the value and the index for the
      exampleWildBcdProvFreeWildBcdListTable."
::= { exampleWildBcdProvFreeWildBcdListEntry 1 }

exampleWildBcdProvFreeWildBcdListRowStatus OBJECT-TYPE
   SYNTAX     RowStatus 
   ACCESS     write-only
   STATUS     mandatory
   DESCRIPTION
     "This variable is used to control the addition and deletion 
      of individual values of the exampleWildBcdProvFreeWildBcdListTable."
::= { exampleWildBcdProvFreeWildBcdListEntry 2 }



exampleEnum OBJECT IDENTIFIER ::= { example 11 }



exampleEnumRowStatusTable OBJECT-TYPE
   SYNTAX     SEQUENCE OF ExampleEnumRowStatusEntry
   ACCESS     not-accessible
   STATUS     mandatory
   DESCRIPTION
     "This entry controls the addition and deletion of 
      exampleEnum components."
::= { exampleEnum 1 }

exampleEnumRowStatusEntry OBJECT-TYPE
   SYNTAX     ExampleEnumRowStatusEntry
   ACCESS     not-accessible
   STATUS     mandatory
   DESCRIPTION
     "A single entry in the table represents a single 
      exampleEnum component."
   INDEX {
      exampleIndex,
      exampleEnumIndex }
::= { exampleEnumRowStatusTable 1 }

ExampleEnumRowStatusEntry ::= SEQUENCE {
   exampleEnumRowStatus
      RowStatus,
   exampleEnumComponentName
      DisplayString,
   exampleEnumStorageType
      StorageType,
   exampleEnumIndex
      INTEGER }

exampleEnumRowStatus OBJECT-TYPE
   SYNTAX     RowStatus 
   ACCESS     read-write
   STATUS     mandatory
   DESCRIPTION
     "This variable is used as the basis for SNMP naming of
      exampleEnum components.
      These components can be added and deleted."
::= { exampleEnumRowStatusEntry 1 }

exampleEnumComponentName OBJECT-TYPE
   SYNTAX     DisplayString 
   ACCESS     read-only
   STATUS     mandatory
   DESCRIPTION
     "This variable provides the component's string name for
      use with the ASCII Console Interface"
::= { exampleEnumRowStatusEntry 2 }

exampleEnumStorageType OBJECT-TYPE
   SYNTAX     StorageType 
   ACCESS     read-only
   STATUS     mandatory
   DESCRIPTION
     "This variable represents the storage type value for the
      exampleEnum tables."
::= { exampleEnumRowStatusEntry 4 }

exampleEnumIndex OBJECT-TYPE
   SYNTAX     INTEGER  {
                 first(1),
                 second(2),
                 third(3) }
   ACCESS     not-accessible
   STATUS     mandatory
   DESCRIPTION
     "This variable represents the index for the exampleEnum tables."
::= { exampleEnumRowStatusEntry 10 }

exampleEnumOperationalTable OBJECT-TYPE
   SYNTAX     SEQUENCE OF ExampleEnumOperationalEntry
   ACCESS     not-accessible
   STATUS     mandatory
   DESCRIPTION
     ""
::= { exampleEnum 10 }

exampleEnumOperationalEntry OBJECT-TYPE
   SYNTAX     ExampleEnumOperationalEntry
   ACCESS     not-accessible
   STATUS     mandatory
   DESCRIPTION
     "An entry in the exampleEnumOperationalTable."
   INDEX {
      exampleIndex,
      exampleEnumIndex }
::= { exampleEnumOperationalTable 1 }

ExampleEnumOperationalEntry ::= SEQUENCE {
   exampleEnumOperStructEnum
      INTEGER,
   exampleEnumOperStructEnumSet
      OCTET STRING,
   exampleEnumOperFreeEnum
      INTEGER,
   exampleEnumOperFreeEnumSet
      OCTET STRING }

exampleEnumOperStructEnum OBJECT-TYPE
   SYNTAX     INTEGER  {
                 monday(0),
                 tuesday(1),
                 wednesday(2),
                 thursday(3),
                 friday(4) }
   ACCESS     read-write
   STATUS     mandatory
   DESCRIPTION
     ""
::= { exampleEnumOperationalEntry 1 }

exampleEnumOperStructEnumSet OBJECT-TYPE
   SYNTAX     OCTET STRING (SIZE (1))
   ACCESS     read-write
   STATUS     mandatory
   DESCRIPTION
     "Description of bits:
      monday(0)
      tuesday(1)
      wednesday(2)
      thursday(3)
      friday(4)
      saturday(5)
      sunday(6)"
::= { exampleEnumOperationalEntry 2 }

exampleEnumOperFreeEnum OBJECT-TYPE
   SYNTAX     INTEGER  {
                 january(0),
                 february(1),
                 march(2),
                 april(3),
                 may(4),
                 june(5) }
   ACCESS     read-write
   STATUS     mandatory
   DESCRIPTION
     ""
::= { exampleEnumOperationalEntry 3 }

exampleEnumOperFreeEnumSet OBJECT-TYPE
   SYNTAX     OCTET STRING (SIZE (2))
   ACCESS     read-write
   STATUS     mandatory
   DESCRIPTION
     "Description of bits:
      notused0(0)
      notused1(1)
      notused2(2)
      notused3(3)
      notused4(4)
      notused5(5)
      july(6)
      august(7)
      september(8)
      october(9)
      november(10)
      december(11)"
::= { exampleEnumOperationalEntry 4 }

exampleEnumProvisionalTable OBJECT-TYPE
   SYNTAX     SEQUENCE OF ExampleEnumProvisionalEntry
   ACCESS     not-accessible
   STATUS     mandatory
   DESCRIPTION
     ""
::= { exampleEnum 11 }

exampleEnumProvisionalEntry OBJECT-TYPE
   SYNTAX     ExampleEnumProvisionalEntry
   ACCESS     not-accessible
   STATUS     mandatory
   DESCRIPTION
     "An entry in the exampleEnumProvisionalTable."
   INDEX {
      exampleIndex,
      exampleEnumIndex }
::= { exampleEnumProvisionalTable 1 }

ExampleEnumProvisionalEntry ::= SEQUENCE {
   exampleEnumProvEnumSub
      Link,
   exampleEnumProvStructEnum
      INTEGER,
   exampleEnumProvStructEnumSet
      OCTET STRING,
   exampleEnumProvFreeEnum
      INTEGER,
   exampleEnumProvFreeEnum1
      INTEGER,
   exampleEnumProvFreeEnumSet
      OCTET STRING,
   exampleEnumProvFreeEnumSet1
      OCTET STRING }

exampleEnumProvEnumSub OBJECT-TYPE
   SYNTAX     Link 
   ACCESS     read-write
   STATUS     mandatory
   DESCRIPTION
     ""
::= { exampleEnumProvisionalEntry 1 }

exampleEnumProvStructEnum OBJECT-TYPE
   SYNTAX     INTEGER  {
                 monday(0),
                 tuesday(1),
                 wednesday(2),
                 thursday(3),
                 friday(4) }
   ACCESS     read-write
   STATUS     mandatory
   DESCRIPTION
     ""
   DEFVAL     { friday }
::= { exampleEnumProvisionalEntry 2 }

exampleEnumProvStructEnumSet OBJECT-TYPE
   SYNTAX     OCTET STRING (SIZE (1))
   ACCESS     read-write
   STATUS     mandatory
   DESCRIPTION
     "Description of bits:
      monday(0)
      tuesday(1)
      wednesday(2)
      thursday(3)
      friday(4)
      saturday(5)
      sunday(6)"
   DEFVAL     { 'aa'H }
::= { exampleEnumProvisionalEntry 3 }

exampleEnumProvFreeEnum OBJECT-TYPE
   SYNTAX     INTEGER  {
                 january(0),
                 february(1),
                 march(2),
                 april(3),
                 may(4),
                 june(5) }
   ACCESS     read-write
   STATUS     mandatory
   DESCRIPTION
     ""
   DEFVAL     { may }
::= { exampleEnumProvisionalEntry 4 }

exampleEnumProvFreeEnum1 OBJECT-TYPE
   SYNTAX     INTEGER  {
                 apple(1),
                 orange(2),
                 banana(3),
                 pear(11),
                 grapes(12),
                 pineapple(13),
                 watermelon(14) }
   ACCESS     read-write
   STATUS     mandatory
   DESCRIPTION
     ""
::= { exampleEnumProvisionalEntry 5 }

exampleEnumProvFreeEnumSet OBJECT-TYPE
   SYNTAX     OCTET STRING (SIZE (2))
   ACCESS     read-write
   STATUS     mandatory
   DESCRIPTION
     "Description of bits:
      notused0(0)
      notused1(1)
      notused2(2)
      notused3(3)
      notused4(4)
      notused5(5)
      july(6)
      august(7)
      september(8)
      october(9)
      november(10)
      december(11)"
   DEFVAL     { '0070'H }
::= { exampleEnumProvisionalEntry 6 }

exampleEnumProvFreeEnumSet1 OBJECT-TYPE
   SYNTAX     OCTET STRING (SIZE (2))
   ACCESS     read-write
   STATUS     mandatory
   DESCRIPTION
     "Description of bits:
      notused0(0)
      apple(1)
      orange(2)
      banana(3)
      notused4(4)
      notused5(5)
      notused6(6)
      notused7(7)
      notused8(8)
      notused9(9)
      notused10(10)
      pear(11)
      grapes(12)
      pineapple(13)
      watermelon(14)"
::= { exampleEnumProvisionalEntry 7 }

exampleEnumOperStructEnumVectorTable OBJECT-TYPE
   SYNTAX     SEQUENCE OF ExampleEnumOperStructEnumVectorEntry
   ACCESS     not-accessible
   STATUS     mandatory
   DESCRIPTION
     ""
::= { exampleEnum 1162 }

exampleEnumOperStructEnumVectorEntry OBJECT-TYPE
   SYNTAX     ExampleEnumOperStructEnumVectorEntry
   ACCESS     not-accessible
   STATUS     mandatory
   DESCRIPTION
     "An entry in the exampleEnumOperStructEnumVectorTable."
   INDEX {
      exampleIndex,
      exampleEnumIndex,
      exampleEnumOperStructEnumVectorIndex }
::= { exampleEnumOperStructEnumVectorTable 1 }

ExampleEnumOperStructEnumVectorEntry ::= SEQUENCE {
   exampleEnumOperStructEnumVectorIndex
      INTEGER,
   exampleEnumOperStructEnumVectorValue
      INTEGER }

exampleEnumOperStructEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the exampleEnumOperStructEnumVectorTable
      specific index for the exampleEnumOperStructEnumVectorTable."
::= { exampleEnumOperStructEnumVectorEntry 1 }

exampleEnumOperStructEnumVectorValue OBJECT-TYPE
   SYNTAX     INTEGER  {
                 monday(0),
                 tuesday(1),
                 wednesday(2),
                 thursday(3),
                 friday(4),
                 saturday(5),
                 sunday(6) }
   ACCESS     read-write
   STATUS     mandatory
   DESCRIPTION
     "This variable represents an individual value for the
      exampleEnumOperStructEnumVectorTable."
::= { exampleEnumOperStructEnumVectorEntry 2 }

exampleEnumOperStructEnumArrayTable OBJECT-TYPE
   SYNTAX     SEQUENCE OF ExampleEnumOperStructEnumArrayEntry
   ACCESS     not-accessible
   STATUS     mandatory
   DESCRIPTION
     ""
::= { exampleEnum 1163 }

exampleEnumOperStructEnumArrayEntry OBJECT-TYPE
   SYNTAX     ExampleEnumOperStructEnumArrayEntry
   ACCESS     not-accessible
   STATUS     mandatory
   DESCRIPTION
     "An entry in the exampleEnumOperStructEnumArrayTable."
   INDEX {
      exampleIndex,
      exampleEnumIndex,
      exampleEnumOperStructEnumArrayMonthIndex,
      exampleEnumOperStructEnumArrayDayIndex }
::= { exampleEnumOperStructEnumArrayTable 1 }

ExampleEnumOperStructEnumArrayEntry ::= SEQUENCE {
   exampleEnumOperStructEnumArrayMonthIndex
      INTEGER,
   exampleEnumOperStructEnumArrayDayIndex
      INTEGER,
   exampleEnumOperStructEnumArrayValue
      INTEGER }

exampleEnumOperStructEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      exampleEnumOperStructEnumArrayTable."
::= { exampleEnumOperStructEnumArrayEntry 1 }

exampleEnumOperStructEnumArrayDayIndex OBJECT-TYPE
   SYNTAX     INTEGER  {
                 mondayaaaa(0),
                 tuesdayaaaa(1),
                 wednesdayaaaa(2),
                 thursdayaaaa(3),
                 fridayaaaa(4),
                 saturdayaaaa(5),
                 sundayaaaa(6) }
   ACCESS     not-accessible
   STATUS     mandatory
   DESCRIPTION
     "This variable represents the final index for the 
      exampleEnumOperStructEnumArrayTable."
::= { exampleEnumOperStructEnumArrayEntry 2 }

exampleEnumOperStructEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      exampleEnumOperStructEnumArrayTable."
::= { exampleEnumOperStructEnumArrayEntry 3 }

exampleEnumOperFreeEnumVectorTable OBJECT-TYPE
   SYNTAX     SEQUENCE OF ExampleEnumOperFreeEnumVectorEntry
   ACCESS     not-accessible
   STATUS     mandatory
   DESCRIPTION
     ""
::= { exampleEnum 1164 }

exampleEnumOperFreeEnumVectorEntry OBJECT-TYPE
   SYNTAX     ExampleEnumOperFreeEnumVectorEntry
   ACCESS     not-accessible
   STATUS     mandatory
   DESCRIPTION
     "An entry in the exampleEnumOperFreeEnumVectorTable."
   INDEX {
      exampleIndex,
      exampleEnumIndex,
      exampleEnumOperFreeEnumVectorIndex }
::= { exampleEnumOperFreeEnumVectorTable 1 }

ExampleEnumOperFreeEnumVectorEntry ::= SEQUENCE {
   exampleEnumOperFreeEnumVectorIndex
      INTEGER,
   exampleEnumOperFreeEnumVectorValue
      INTEGER }

exampleEnumOperFreeEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the exampleEnumOperFreeEnumVectorTable
      specific index for the exampleEnumOperFreeEnumVectorTable."
::= { exampleEnumOperFreeEnumVectorEntry 1 }

exampleEnumOperFreeEnumVectorValue OBJECT-TYPE
   SYNTAX     INTEGER  {
                 monday(0),
                 tuesday(1),
                 wednesday(2),
                 thursday(3),
                 friday(4) }
   ACCESS     read-write
   STATUS     mandatory
   DESCRIPTION
     "This variable represents an individual value for the
      exampleEnumOperFreeEnumVectorTable."
::= { exampleEnumOperFreeEnumVectorEntry 2 }

exampleEnumOperFreeEnumArrayTable OBJECT-TYPE
   SYNTAX     SEQUENCE OF ExampleEnumOperFreeEnumArrayEntry
   ACCESS     not-accessible
   STATUS     mandatory
   DESCRIPTION
     ""
::= { exampleEnum 1165 }

exampleEnumOperFreeEnumArrayEntry OBJECT-TYPE
   SYNTAX     ExampleEnumOperFreeEnumArrayEntry
   ACCESS     not-accessible
   STATUS     mandatory
   DESCRIPTION
     "An entry in the exampleEnumOperFreeEnumArrayTable."
   INDEX {
      exampleIndex,
      exampleEnumIndex,
      exampleEnumOperFreeEnumArrayMonthIndex,
      exampleEnumOperFreeEnumArrayDayIndex }
::= { exampleEnumOperFreeEnumArrayTable 1 }

ExampleEnumOperFreeEnumArrayEntry ::= SEQUENCE {
   exampleEnumOperFreeEnumArrayMonthIndex
      INTEGER,
   exampleEnumOperFreeEnumArrayDayIndex
      INTEGER,
   exampleEnumOperFreeEnumArrayValue
      INTEGER }

exampleEnumOperFreeEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      exampleEnumOperFreeEnumArrayTable."
::= { exampleEnumOperFreeEnumArrayEntry 1 }

exampleEnumOperFreeEnumArrayDayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      exampleEnumOperFreeEnumArrayTable."
::= { exampleEnumOperFreeEnumArrayEntry 2 }

exampleEnumOperFreeEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      exampleEnumOperFreeEnumArrayTable."
::= { exampleEnumOperFreeEnumArrayEntry 3 }

exampleEnumOperFreeEnumReplicatedTable OBJECT-TYPE
   SYNTAX     SEQUENCE OF ExampleEnumOperFreeEnumReplicatedEntry
   ACCESS     not-accessible
   STATUS     mandatory
   DESCRIPTION
     ""
::= { exampleEnum 1166 }

exampleEnumOperFreeEnumReplicatedEntry OBJECT-TYPE
   SYNTAX     ExampleEnumOperFreeEnumReplicatedEntry
   ACCESS     not-accessible
   STATUS     mandatory
   DESCRIPTION
     "An entry in the exampleEnumOperFreeEnumReplicatedTable."
   INDEX {
      exampleIndex,
      exampleEnumIndex,
      exampleEnumOperFreeEnumReplicatedIndex }
::= { exampleEnumOperFreeEnumReplicatedTable 1 }

ExampleEnumOperFreeEnumReplicatedEntry ::= SEQUENCE {
   exampleEnumOperFreeEnumReplicatedIndex
      INTEGER,
   exampleEnumOperFreeEnumReplicatedValue
      INTEGER,
   exampleEnumOperFreeEnumReplicatedRowStatus
      RowStatus }

exampleEnumOperFreeEnumReplicatedIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the index for the exampleEnumOperFreeEnumReplicatedTable."
::= { exampleEnumOperFreeEnumReplicatedEntry 1 }

exampleEnumOperFreeEnumReplicatedValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      exampleEnumOperFreeEnumReplicatedTable."
::= { exampleEnumOperFreeEnumReplicatedEntry 2 }

exampleEnumOperFreeEnumReplicatedRowStatus OBJECT-TYPE
   SYNTAX     RowStatus 
   ACCESS     write-only
   STATUS     mandatory
   DESCRIPTION
     "This variable is used to control the addition and deletion 
      of individual values of the exampleEnumOperFreeEnumReplicatedTable."
::= { exampleEnumOperFreeEnumReplicatedEntry 3 }

exampleEnumOperFreeEnumListTable OBJECT-TYPE
   SYNTAX     SEQUENCE OF ExampleEnumOperFreeEnumListEntry
   ACCESS     not-accessible
   STATUS     mandatory
   DESCRIPTION
     ""
::= { exampleEnum 1167 }

exampleEnumOperFreeEnumListEntry OBJECT-TYPE
   SYNTAX     ExampleEnumOperFreeEnumListEntry
   ACCESS     not-accessible
   STATUS     mandatory
   DESCRIPTION
     "An entry in the exampleEnumOperFreeEnumListTable."
   INDEX {
      exampleIndex,
      exampleEnumIndex,
      exampleEnumOperFreeEnumListValue }
::= { exampleEnumOperFreeEnumListTable 1 }

ExampleEnumOperFreeEnumListEntry ::= SEQUENCE {
   exampleEnumOperFreeEnumListValue
      INTEGER,
   exampleEnumOperFreeEnumListRowStatus
      RowStatus }

exampleEnumOperFreeEnumListValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      exampleEnumOperFreeEnumListTable."
::= { exampleEnumOperFreeEnumListEntry 1 }

exampleEnumOperFreeEnumListRowStatus OBJECT-TYPE
   SYNTAX     RowStatus 
   ACCESS     write-only
   STATUS     mandatory
   DESCRIPTION
     "This variable is used to control the addition and deletion 
      of individual values of the exampleEnumOperFreeEnumListTable."
::= { exampleEnumOperFreeEnumListEntry 2 }

exampleEnumProvStructEnumVectorTable OBJECT-TYPE
   SYNTAX     SEQUENCE OF ExampleEnumProvStructEnumVectorEntry
   ACCESS     not-accessible
   STATUS     mandatory
   DESCRIPTION
     ""
::= { exampleEnum 1168 }

exampleEnumProvStructEnumVectorEntry OBJECT-TYPE
   SYNTAX     ExampleEnumProvStructEnumVectorEntry
   ACCESS     not-accessible
   STATUS     mandatory
   DESCRIPTION
     "An entry in the exampleEnumProvStructEnumVectorTable."
   INDEX {
      exampleIndex,
      exampleEnumIndex,
      exampleEnumProvStructEnumVectorIndex }
::= { exampleEnumProvStructEnumVectorTable 1 }

ExampleEnumProvStructEnumVectorEntry ::= SEQUENCE {
   exampleEnumProvStructEnumVectorIndex
      INTEGER,
   exampleEnumProvStructEnumVectorValue
      INTEGER }

exampleEnumProvStructEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the exampleEnumProvStructEnumVectorTable
      specific index for the exampleEnumProvStructEnumVectorTable."
::= { exampleEnumProvStructEnumVectorEntry 1 }

exampleEnumProvStructEnumVectorValue OBJECT-TYPE
   SYNTAX     INTEGER  {
                 monday(0),
                 tuesday(1),
                 wednesday(2),
                 thursday(3),
                 friday(4) }
   ACCESS     read-write
   STATUS     mandatory
   DESCRIPTION
     "This variable represents an individual value for the
      exampleEnumProvStructEnumVectorTable."
::= { exampleEnumProvStructEnumVectorEntry 2 }

exampleEnumProvStructEnumArrayTable OBJECT-TYPE
   SYNTAX     SEQUENCE OF ExampleEnumProvStructEnumArrayEntry
   ACCESS     not-accessible
   STATUS     mandatory
   DESCRIPTION
     ""
::= { exampleEnum 1169 }

exampleEnumProvStructEnumArrayEntry OBJECT-TYPE
   SYNTAX     ExampleEnumProvStructEnumArrayEntry
   ACCESS     not-accessible
   STATUS     mandatory
   DESCRIPTION
     "An entry in the exampleEnumProvStructEnumArrayTable."
   INDEX {
      exampleIndex,
      exampleEnumIndex,
      exampleEnumProvStructEnumArrayMonthIndex,
      exampleEnumProvStructEnumArrayDayIndex }
::= { exampleEnumProvStructEnumArrayTable 1 }

ExampleEnumProvStructEnumArrayEntry ::= SEQUENCE {
   exampleEnumProvStructEnumArrayMonthIndex
      INTEGER,
   exampleEnumProvStructEnumArrayDayIndex
      INTEGER,
   exampleEnumProvStructEnumArrayValue
      INTEGER }

exampleEnumProvStructEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      exampleEnumProvStructEnumArrayTable."
::= { exampleEnumProvStructEnumArrayEntry 1 }

exampleEnumProvStructEnumArrayDayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      exampleEnumProvStructEnumArrayTable."
::= { exampleEnumProvStructEnumArrayEntry 2 }

exampleEnumProvStructEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      exampleEnumProvStructEnumArrayTable."
::= { exampleEnumProvStructEnumArrayEntry 3 }

exampleEnumProvFreeEnumVectorTable OBJECT-TYPE
   SYNTAX     SEQUENCE OF ExampleEnumProvFreeEnumVectorEntry
   ACCESS     not-accessible
   STATUS     mandatory
   DESCRIPTION
     ""
::= { exampleEnum 1170 }

exampleEnumProvFreeEnumVectorEntry OBJECT-TYPE
   SYNTAX     ExampleEnumProvFreeEnumVectorEntry
   ACCESS     not-accessible
   STATUS     mandatory
   DESCRIPTION
     "An entry in the exampleEnumProvFreeEnumVectorTable."
   INDEX {
      exampleIndex,
      exampleEnumIndex,
      exampleEnumProvFreeEnumVectorIndex }
::= { exampleEnumProvFreeEnumVectorTable 1 }

ExampleEnumProvFreeEnumVectorEntry ::= SEQUENCE {
   exampleEnumProvFreeEnumVectorIndex
      INTEGER,
   exampleEnumProvFreeEnumVectorValue
      INTEGER }

exampleEnumProvFreeEnumVectorIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the exampleEnumProvFreeEnumVectorTable
      specific index for the exampleEnumProvFreeEnumVectorTable."
::= { exampleEnumProvFreeEnumVectorEntry 1 }

exampleEnumProvFreeEnumVectorValue OBJECT-TYPE
   SYNTAX     INTEGER  {
                 monday(0),
                 tuesday(1),
                 wednesday(2),
                 thursday(3),
                 friday(4) }
   ACCESS     read-write
   STATUS     mandatory
   DESCRIPTION
     "This variable represents an individual value for the
      exampleEnumProvFreeEnumVectorTable."
::= { exampleEnumProvFreeEnumVectorEntry 2 }

exampleEnumProvFreeEnumVector1Table OBJECT-TYPE
   SYNTAX     SEQUENCE OF ExampleEnumProvFreeEnumVector1Entry
   ACCESS     not-accessible
   STATUS     mandatory
   DESCRIPTION
     ""
::= { exampleEnum 1171 }

exampleEnumProvFreeEnumVector1Entry OBJECT-TYPE
   SYNTAX     ExampleEnumProvFreeEnumVector1Entry
   ACCESS     not-accessible
   STATUS     mandatory
   DESCRIPTION
     "An entry in the exampleEnumProvFreeEnumVector1Table."
   INDEX {
      exampleIndex,
      exampleEnumIndex,
      exampleEnumProvFreeEnumVector1Index }
::= { exampleEnumProvFreeEnumVector1Table 1 }

ExampleEnumProvFreeEnumVector1Entry ::= SEQUENCE {
   exampleEnumProvFreeEnumVector1Index
      INTEGER,
   exampleEnumProvFreeEnumVector1Value
      INTEGER }

exampleEnumProvFreeEnumVector1Index OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the exampleEnumProvFreeEnumVector1Table
      specific index for the exampleEnumProvFreeEnumVector1Table."
::= { exampleEnumProvFreeEnumVector1Entry 1 }

exampleEnumProvFreeEnumVector1Value OBJECT-TYPE
   SYNTAX     INTEGER  {
                 january(0),
                 february(1),
                 march(2),
                 april(3),
                 may(4) }
   ACCESS     read-write
   STATUS     mandatory
   DESCRIPTION
     "This variable represents an individual value for the
      exampleEnumProvFreeEnumVector1Table."
::= { exampleEnumProvFreeEnumVector1Entry 2 }

exampleEnumProvFreeEnumArrayTable OBJECT-TYPE
   SYNTAX     SEQUENCE OF ExampleEnumProvFreeEnumArrayEntry
   ACCESS     not-accessible
   STATUS     mandatory
   DESCRIPTION
     ""
::= { exampleEnum 1172 }

exampleEnumProvFreeEnumArrayEntry OBJECT-TYPE
   SYNTAX     ExampleEnumProvFreeEnumArrayEntry
   ACCESS     not-accessible
   STATUS     mandatory
   DESCRIPTION
     "An entry in the exampleEnumProvFreeEnumArrayTable."
   INDEX {
      exampleIndex,
      exampleEnumIndex,
      exampleEnumProvFreeEnumArrayMonthIndex,
      exampleEnumProvFreeEnumArrayDayIndex }
::= { exampleEnumProvFreeEnumArrayTable 1 }

ExampleEnumProvFreeEnumArrayEntry ::= SEQUENCE {
   exampleEnumProvFreeEnumArrayMonthIndex
      INTEGER,
   exampleEnumProvFreeEnumArrayDayIndex
      INTEGER,
   exampleEnumProvFreeEnumArrayValue
      INTEGER }

exampleEnumProvFreeEnumArrayMonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      exampleEnumProvFreeEnumArrayTable."
::= { exampleEnumProvFreeEnumArrayEntry 1 }

exampleEnumProvFreeEnumArrayDayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      exampleEnumProvFreeEnumArrayTable."
::= { exampleEnumProvFreeEnumArrayEntry 2 }

exampleEnumProvFreeEnumArrayValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      exampleEnumProvFreeEnumArrayTable."
::= { exampleEnumProvFreeEnumArrayEntry 3 }

exampleEnumProvFreeEnumArray1Table OBJECT-TYPE
   SYNTAX     SEQUENCE OF ExampleEnumProvFreeEnumArray1Entry
   ACCESS     not-accessible
   STATUS     mandatory
   DESCRIPTION
     ""
::= { exampleEnum 1173 }

exampleEnumProvFreeEnumArray1Entry OBJECT-TYPE
   SYNTAX     ExampleEnumProvFreeEnumArray1Entry
   ACCESS     not-accessible
   STATUS     mandatory
   DESCRIPTION
     "An entry in the exampleEnumProvFreeEnumArray1Table."
   INDEX {
      exampleIndex,
      exampleEnumIndex,
      exampleEnumProvFreeEnumArray1MonthIndex,
      exampleEnumProvFreeEnumArray1DayIndex }
::= { exampleEnumProvFreeEnumArray1Table 1 }

ExampleEnumProvFreeEnumArray1Entry ::= SEQUENCE {
   exampleEnumProvFreeEnumArray1MonthIndex
      INTEGER,
   exampleEnumProvFreeEnumArray1DayIndex
      INTEGER,
   exampleEnumProvFreeEnumArray1Value
      INTEGER }

exampleEnumProvFreeEnumArray1MonthIndex OBJECT-TYPE
   SYNTAX     INTEGER  {
                 january(0),
                 february(1),
                 march(2),
                 april(3),
                 may(4),
                 june(5),
                 july(6),
                 august(7),
                 september(8),
                 october(9),
                 november(10),
                 december(11) }
   ACCESS     not-accessible
   STATUS     mandatory
   DESCRIPTION
     "This variable represents the next to last index for the 
      exampleEnumProvFreeEnumArray1Table."
::= { exampleEnumProvFreeEnumArray1Entry 1 }

exampleEnumProvFreeEnumArray1DayIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the final index for the 
      exampleEnumProvFreeEnumArray1Table."
::= { exampleEnumProvFreeEnumArray1Entry 2 }

exampleEnumProvFreeEnumArray1Value OBJECT-TYPE
   SYNTAX     INTEGER  {
                 apple(1),
                 orange(2),
                 banana(3),
                 pear(11),
                 grapes(12),
                 pineapple(13),
                 watermelon(14) }
   ACCESS     read-write
   STATUS     mandatory
   DESCRIPTION
     "This variable represents an individual value for the
      exampleEnumProvFreeEnumArray1Table."
::= { exampleEnumProvFreeEnumArray1Entry 3 }

exampleEnumProvFreeEnumReplicatedTable OBJECT-TYPE
   SYNTAX     SEQUENCE OF ExampleEnumProvFreeEnumReplicatedEntry
   ACCESS     not-accessible
   STATUS     mandatory
   DESCRIPTION
     ""
::= { exampleEnum 1174 }

exampleEnumProvFreeEnumReplicatedEntry OBJECT-TYPE
   SYNTAX     ExampleEnumProvFreeEnumReplicatedEntry
   ACCESS     not-accessible
   STATUS     mandatory
   DESCRIPTION
     "An entry in the exampleEnumProvFreeEnumReplicatedTable."
   INDEX {
      exampleIndex,
      exampleEnumIndex,
      exampleEnumProvFreeEnumReplicatedIndex }
::= { exampleEnumProvFreeEnumReplicatedTable 1 }

ExampleEnumProvFreeEnumReplicatedEntry ::= SEQUENCE {
   exampleEnumProvFreeEnumReplicatedIndex
      INTEGER,
   exampleEnumProvFreeEnumReplicatedValue
      INTEGER,
   exampleEnumProvFreeEnumReplicatedRowStatus
      RowStatus }

exampleEnumProvFreeEnumReplicatedIndex OBJECT-TYPE
   SYNTAX     INTEGER  {
                 monday(0),
                 tuesday(1),
                 wednesday(2),
                 thursday(3),
                 friday(4),
                 saturday(5),
                 sunday(6) }
   ACCESS     not-accessible
   STATUS     mandatory
   DESCRIPTION
     "This variable represents the index for the exampleEnumProvFreeEnumReplicatedTable."
::= { exampleEnumProvFreeEnumReplicatedEntry 1 }

exampleEnumProvFreeEnumReplicatedValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents an individual value for the
      exampleEnumProvFreeEnumReplicatedTable."
::= { exampleEnumProvFreeEnumReplicatedEntry 2 }

exampleEnumProvFreeEnumReplicatedRowStatus OBJECT-TYPE
   SYNTAX     RowStatus 
   ACCESS     write-only
   STATUS     mandatory
   DESCRIPTION
     "This variable is used to control the addition and deletion 
      of individual values of the exampleEnumProvFreeEnumReplicatedTable."
::= { exampleEnumProvFreeEnumReplicatedEntry 3 }

exampleEnumProvFreeEnumListTable OBJECT-TYPE
   SYNTAX     SEQUENCE OF ExampleEnumProvFreeEnumListEntry
   ACCESS     not-accessible
   STATUS     mandatory
   DESCRIPTION
     ""
::= { exampleEnum 1175 }

exampleEnumProvFreeEnumListEntry OBJECT-TYPE
   SYNTAX     ExampleEnumProvFreeEnumListEntry
   ACCESS     not-accessible
   STATUS     mandatory
   DESCRIPTION
     "An entry in the exampleEnumProvFreeEnumListTable."
   INDEX {
      exampleIndex,
      exampleEnumIndex,
      exampleEnumProvFreeEnumListValue }
::= { exampleEnumProvFreeEnumListTable 1 }

ExampleEnumProvFreeEnumListEntry ::= SEQUENCE {
   exampleEnumProvFreeEnumListValue
      INTEGER,
   exampleEnumProvFreeEnumListRowStatus
      RowStatus }

exampleEnumProvFreeEnumListValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      exampleEnumProvFreeEnumListTable."
::= { exampleEnumProvFreeEnumListEntry 1 }

exampleEnumProvFreeEnumListRowStatus OBJECT-TYPE
   SYNTAX     RowStatus 
   ACCESS     write-only
   STATUS     mandatory
   DESCRIPTION
     "This variable is used to control the addition and deletion 
      of individual values of the exampleEnumProvFreeEnumListTable."
::= { exampleEnumProvFreeEnumListEntry 2 }

exampleEnumProvFreeEnumList1Table OBJECT-TYPE
   SYNTAX     SEQUENCE OF ExampleEnumProvFreeEnumList1Entry
   ACCESS     not-accessible
   STATUS     mandatory
   DESCRIPTION
     ""
::= { exampleEnum 1176 }

exampleEnumProvFreeEnumList1Entry OBJECT-TYPE
   SYNTAX     ExampleEnumProvFreeEnumList1Entry
   ACCESS     not-accessible
   STATUS     mandatory
   DESCRIPTION
     "An entry in the exampleEnumProvFreeEnumList1Table."
   INDEX {
      exampleIndex,
      exampleEnumIndex,
      exampleEnumProvFreeEnumList1Value }
::= { exampleEnumProvFreeEnumList1Table 1 }

ExampleEnumProvFreeEnumList1Entry ::= SEQUENCE {
   exampleEnumProvFreeEnumList1Value
      INTEGER,
   exampleEnumProvFreeEnumList1RowStatus
      RowStatus }

exampleEnumProvFreeEnumList1Value OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      exampleEnumProvFreeEnumList1Table."
::= { exampleEnumProvFreeEnumList1Entry 1 }

exampleEnumProvFreeEnumList1RowStatus OBJECT-TYPE
   SYNTAX     RowStatus 
   ACCESS     write-only
   STATUS     mandatory
   DESCRIPTION
     "This variable is used to control the addition and deletion 
      of individual values of the exampleEnumProvFreeEnumList1Table."
::= { exampleEnumProvFreeEnumList1Entry 2 }



exampleObjectId OBJECT IDENTIFIER ::= { example 12 }



exampleObjectIdRowStatusTable OBJECT-TYPE
   SYNTAX     SEQUENCE OF ExampleObjectIdRowStatusEntry
   ACCESS     not-accessible
   STATUS     mandatory
   DESCRIPTION
     "This entry controls the addition and deletion of 
      exampleObjectId components."
::= { exampleObjectId 1 }

exampleObjectIdRowStatusEntry OBJECT-TYPE
   SYNTAX     ExampleObjectIdRowStatusEntry
   ACCESS     not-accessible
   STATUS     mandatory
   DESCRIPTION
     "A single entry in the table represents a single 
      exampleObjectId component."
   INDEX {
      exampleIndex,
      exampleObjectIdIndex }
::= { exampleObjectIdRowStatusTable 1 }

ExampleObjectIdRowStatusEntry ::= SEQUENCE {
   exampleObjectIdRowStatus
      RowStatus,
   exampleObjectIdComponentName
      DisplayString,
   exampleObjectIdStorageType
      StorageType,
   exampleObjectIdIndex
      OBJECT IDENTIFIER }

exampleObjectIdRowStatus OBJECT-TYPE
   SYNTAX     RowStatus 
   ACCESS     read-write
   STATUS     mandatory
   DESCRIPTION
     "This variable is used as the basis for SNMP naming of
      exampleObjectId components.
      These components can be added and deleted."
::= { exampleObjectIdRowStatusEntry 1 }

exampleObjectIdComponentName OBJECT-TYPE
   SYNTAX     DisplayString 
   ACCESS     read-only
   STATUS     mandatory
   DESCRIPTION
     "This variable provides the component's string name for
      use with the ASCII Console Interface"
::= { exampleObjectIdRowStatusEntry 2 }

exampleObjectIdStorageType OBJECT-TYPE
   SYNTAX     StorageType 
   ACCESS     read-only
   STATUS     mandatory
   DESCRIPTION
     "This variable represents the storage type value for the
      exampleObjectId tables."
::= { exampleObjectIdRowStatusEntry 4 }

exampleObjectIdIndex OBJECT-TYPE
   SYNTAX     OBJECT IDENTIFIER 
   ACCESS     not-accessible
   STATUS     mandatory
   DESCRIPTION
     "This variable represents the index for the exampleObjectId tables."
::= { exampleObjectIdRowStatusEntry 10 }

exampleObjectIdOperationalTable OBJECT-TYPE
   SYNTAX     SEQUENCE OF ExampleObjectIdOperationalEntry
   ACCESS     not-accessible
   STATUS     mandatory
   DESCRIPTION
     ""
::= { exampleObjectId 10 }

exampleObjectIdOperationalEntry OBJECT-TYPE
   SYNTAX     ExampleObjectIdOperationalEntry
   ACCESS     not-accessible
   STATUS     mandatory
   DESCRIPTION
     "An entry in the exampleObjectIdOperationalTable."
   INDEX {
      exampleIndex,
      exampleObjectIdIndex }
::= { exampleObjectIdOperationalTable 1 }

ExampleObjectIdOperationalEntry ::= SEQUENCE {
   exampleObjectIdOperFreeObjId
      OBJECT IDENTIFIER }

exampleObjectIdOperFreeObjId OBJECT-TYPE
   SYNTAX     OBJECT IDENTIFIER 
   ACCESS     read-write
   STATUS     mandatory
   DESCRIPTION
     ""
::= { exampleObjectIdOperationalEntry 1 }

exampleObjectIdProvisionalTable OBJECT-TYPE
   SYNTAX     SEQUENCE OF ExampleObjectIdProvisionalEntry
   ACCESS     not-accessible
   STATUS     mandatory
   DESCRIPTION
     ""
::= { exampleObjectId 11 }

exampleObjectIdProvisionalEntry OBJECT-TYPE
   SYNTAX     ExampleObjectIdProvisionalEntry
   ACCESS     not-accessible
   STATUS     mandatory
   DESCRIPTION
     "An entry in the exampleObjectIdProvisionalTable."
   INDEX {
      exampleIndex,
      exampleObjectIdIndex }
::= { exampleObjectIdProvisionalTable 1 }

ExampleObjectIdProvisionalEntry ::= SEQUENCE {
   exampleObjectIdProvEnumSub
      Link,
   exampleObjectIdProvFreeObjId
      OBJECT IDENTIFIER }

exampleObjectIdProvEnumSub OBJECT-TYPE
   SYNTAX     Link 
   ACCESS     read-write
   STATUS     mandatory
   DESCRIPTION
     ""
::= { exampleObjectIdProvisionalEntry 1 }

exampleObjectIdProvFreeObjId OBJECT-TYPE
   SYNTAX     OBJECT IDENTIFIER 
   ACCESS     read-write
   STATUS     mandatory
   DESCRIPTION
     ""
::= { exampleObjectIdProvisionalEntry 2 }

exampleObjectIdOperFreeObjIdReplicatedTable OBJECT-TYPE
   SYNTAX     SEQUENCE OF ExampleObjectIdOperFreeObjIdReplicatedEntry
   ACCESS     not-accessible
   STATUS     mandatory
   DESCRIPTION
     ""
::= { exampleObjectId 1116 }

exampleObjectIdOperFreeObjIdReplicatedEntry OBJECT-TYPE
   SYNTAX     ExampleObjectIdOperFreeObjIdReplicatedEntry
   ACCESS     not-accessible
   STATUS     mandatory
   DESCRIPTION
     "An entry in the exampleObjectIdOperFreeObjIdReplicatedTable."
   INDEX {
      exampleIndex,
      exampleObjectIdIndex,
      exampleObjectIdOperFreeObjIdReplicatedIndex }
::= { exampleObjectIdOperFreeObjIdReplicatedTable 1 }

ExampleObjectIdOperFreeObjIdReplicatedEntry ::= SEQUENCE {
   exampleObjectIdOperFreeObjIdReplicatedIndex
      OBJECT IDENTIFIER,
   exampleObjectIdOperFreeObjIdReplicatedValue
      OBJECT IDENTIFIER,
   exampleObjectIdOperFreeObjIdReplicatedRowStatus
      RowStatus }

exampleObjectIdOperFreeObjIdReplicatedIndex OBJECT-TYPE
   SYNTAX     OBJECT IDENTIFIER 
   ACCESS     not-accessible
   STATUS     mandatory
   DESCRIPTION
     "This variable represents the index for the exampleObjectIdOperFreeObjIdReplicatedTable."
::= { exampleObjectIdOperFreeObjIdReplicatedEntry 1 }

exampleObjectIdOperFreeObjIdReplicatedValue OBJECT-TYPE
   SYNTAX     OBJECT IDENTIFIER 
   ACCESS     read-write
   STATUS     mandatory
   DESCRIPTION
     "This variable represents an individual value for the
      exampleObjectIdOperFreeObjIdReplicatedTable."
::= { exampleObjectIdOperFreeObjIdReplicatedEntry 2 }

exampleObjectIdOperFreeObjIdReplicatedRowStatus OBJECT-TYPE
   SYNTAX     RowStatus 
   ACCESS     write-only
   STATUS     mandatory
   DESCRIPTION
     "This variable is used to control the addition and deletion 
      of individual values of the exampleObjectIdOperFreeObjIdReplicatedTable."
::= { exampleObjectIdOperFreeObjIdReplicatedEntry 3 }

exampleObjectIdOperFreeObjIdListTable OBJECT-TYPE
   SYNTAX     SEQUENCE OF ExampleObjectIdOperFreeObjIdListEntry
   ACCESS     not-accessible
   STATUS     mandatory
   DESCRIPTION
     ""
::= { exampleObjectId 1117 }

exampleObjectIdOperFreeObjIdListEntry OBJECT-TYPE
   SYNTAX     ExampleObjectIdOperFreeObjIdListEntry
   ACCESS     not-accessible
   STATUS     mandatory
   DESCRIPTION
     "An entry in the exampleObjectIdOperFreeObjIdListTable."
   INDEX {
      exampleIndex,
      exampleObjectIdIndex,
      exampleObjectIdOperFreeObjIdListValue }
::= { exampleObjectIdOperFreeObjIdListTable 1 }

ExampleObjectIdOperFreeObjIdListEntry ::= SEQUENCE {
   exampleObjectIdOperFreeObjIdListValue
      IntegerSequence,
   exampleObjectIdOperFreeObjIdListRowStatus
      RowStatus }

exampleObjectIdOperFreeObjIdListValue OBJECT-TYPE
   SYNTAX     IntegerSequence 
   ACCESS     read-write
   STATUS     mandatory
   DESCRIPTION
     "This variable represents both the value and the index for the
      exampleObjectIdOperFreeObjIdListTable."
::= { exampleObjectIdOperFreeObjIdListEntry 1 }

exampleObjectIdOperFreeObjIdListRowStatus OBJECT-TYPE
   SYNTAX     RowStatus 
   ACCESS     write-only
   STATUS     mandatory
   DESCRIPTION
     "This variable is used to control the addition and deletion 
      of individual values of the exampleObjectIdOperFreeObjIdListTable."
::= { exampleObjectIdOperFreeObjIdListEntry 2 }

exampleObjectIdProvFreeObjIdReplicatedTable OBJECT-TYPE
   SYNTAX     SEQUENCE OF ExampleObjectIdProvFreeObjIdReplicatedEntry
   ACCESS     not-accessible
   STATUS     mandatory
   DESCRIPTION
     ""
::= { exampleObjectId 1118 }

exampleObjectIdProvFreeObjIdReplicatedEntry OBJECT-TYPE
   SYNTAX     ExampleObjectIdProvFreeObjIdReplicatedEntry
   ACCESS     not-accessible
   STATUS     mandatory
   DESCRIPTION
     "An entry in the exampleObjectIdProvFreeObjIdReplicatedTable."
   INDEX {
      exampleIndex,
      exampleObjectIdIndex,
      exampleObjectIdProvFreeObjIdReplicatedIndex }
::= { exampleObjectIdProvFreeObjIdReplicatedTable 1 }

ExampleObjectIdProvFreeObjIdReplicatedEntry ::= SEQUENCE {
   exampleObjectIdProvFreeObjIdReplicatedIndex
      OBJECT IDENTIFIER,
   exampleObjectIdProvFreeObjIdReplicatedValue
      OBJECT IDENTIFIER,
   exampleObjectIdProvFreeObjIdReplicatedRowStatus
      RowStatus }

exampleObjectIdProvFreeObjIdReplicatedIndex OBJECT-TYPE
   SYNTAX     OBJECT IDENTIFIER 
   ACCESS     not-accessible
   STATUS     mandatory
   DESCRIPTION
     "This variable represents the index for the exampleObjectIdProvFreeObjIdReplicatedTable."
::= { exampleObjectIdProvFreeObjIdReplicatedEntry 1 }

exampleObjectIdProvFreeObjIdReplicatedValue OBJECT-TYPE
   SYNTAX     OBJECT IDENTIFIER 
   ACCESS     read-write
   STATUS     mandatory
   DESCRIPTION
     "This variable represents an individual value for the
      exampleObjectIdProvFreeObjIdReplicatedTable."
::= { exampleObjectIdProvFreeObjIdReplicatedEntry 2 }

exampleObjectIdProvFreeObjIdReplicatedRowStatus OBJECT-TYPE
   SYNTAX     RowStatus 
   ACCESS     write-only
   STATUS     mandatory
   DESCRIPTION
     "This variable is used to control the addition and deletion 
      of individual values of the exampleObjectIdProvFreeObjIdReplicatedTable."
::= { exampleObjectIdProvFreeObjIdReplicatedEntry 3 }

exampleObjectIdProvFreeObjIdListTable OBJECT-TYPE
   SYNTAX     SEQUENCE OF ExampleObjectIdProvFreeObjIdListEntry
   ACCESS     not-accessible
   STATUS     mandatory
   DESCRIPTION
     ""
::= { exampleObjectId 1119 }

exampleObjectIdProvFreeObjIdListEntry OBJECT-TYPE
   SYNTAX     ExampleObjectIdProvFreeObjIdListEntry
   ACCESS     not-accessible
   STATUS     mandatory
   DESCRIPTION
     "An entry in the exampleObjectIdProvFreeObjIdListTable."
   INDEX {
      exampleIndex,
      exampleObjectIdIndex,
      exampleObjectIdProvFreeObjIdListValue }
::= { exampleObjectIdProvFreeObjIdListTable 1 }

ExampleObjectIdProvFreeObjIdListEntry ::= SEQUENCE {
   exampleObjectIdProvFreeObjIdListValue
      IntegerSequence,
   exampleObjectIdProvFreeObjIdListRowStatus
      RowStatus }

exampleObjectIdProvFreeObjIdListValue OBJECT-TYPE
   SYNTAX     IntegerSequence 
   ACCESS     read-write
   STATUS     mandatory
   DESCRIPTION
     "This variable represents both the value and the index for the
      exampleObjectIdProvFreeObjIdListTable."
::= { exampleObjectIdProvFreeObjIdListEntry 1 }

exampleObjectIdProvFreeObjIdListRowStatus OBJECT-TYPE
   SYNTAX     RowStatus 
   ACCESS     write-only
   STATUS     mandatory
   DESCRIPTION
     "This variable is used to control the addition and deletion 
      of individual values of the exampleObjectIdProvFreeObjIdListTable."
::= { exampleObjectIdProvFreeObjIdListEntry 2 }



exampleSequence OBJECT IDENTIFIER ::= { example 13 }



exampleSequenceRowStatusTable OBJECT-TYPE
   SYNTAX     SEQUENCE OF ExampleSequenceRowStatusEntry
   ACCESS     not-accessible
   STATUS     mandatory
   DESCRIPTION
     "This entry controls the addition and deletion of 
      exampleSequence components."
::= { exampleSequence 1 }

exampleSequenceRowStatusEntry OBJECT-TYPE
   SYNTAX     ExampleSequenceRowStatusEntry
   ACCESS     not-accessible
   STATUS     mandatory
   DESCRIPTION
     "A single entry in the table represents a single 
      exampleSequence component."
   INDEX {
      exampleIndex,
      exampleSequenceIndex }
::= { exampleSequenceRowStatusTable 1 }

ExampleSequenceRowStatusEntry ::= SEQUENCE {
   exampleSequenceRowStatus
      RowStatus,
   exampleSequenceComponentName
      DisplayString,
   exampleSequenceStorageType
      StorageType,
   exampleSequenceIndex
      OBJECT IDENTIFIER }

exampleSequenceRowStatus OBJECT-TYPE
   SYNTAX     RowStatus 
   ACCESS     read-write
   STATUS     mandatory
   DESCRIPTION
     "This variable is used as the basis for SNMP naming of
      exampleSequence components.
      These components can be added and deleted."
::= { exampleSequenceRowStatusEntry 1 }

exampleSequenceComponentName OBJECT-TYPE
   SYNTAX     DisplayString 
   ACCESS     read-only
   STATUS     mandatory
   DESCRIPTION
     "This variable provides the component's string name for
      use with the ASCII Console Interface"
::= { exampleSequenceRowStatusEntry 2 }

exampleSequenceStorageType OBJECT-TYPE
   SYNTAX     StorageType 
   ACCESS     read-only
   STATUS     mandatory
   DESCRIPTION
     "This variable represents the storage type value for the
      exampleSequence tables."
::= { exampleSequenceRowStatusEntry 4 }

exampleSequenceIndex OBJECT-TYPE
   SYNTAX     OBJECT IDENTIFIER 
   ACCESS     not-accessible
   STATUS     mandatory
   DESCRIPTION
     "This variable represents the index for the exampleSequence tables."
::= { exampleSequenceRowStatusEntry 10 }

exampleSequenceOperationalTable OBJECT-TYPE
   SYNTAX     SEQUENCE OF ExampleSequenceOperationalEntry
   ACCESS     not-accessible
   STATUS     mandatory
   DESCRIPTION
     ""
::= { exampleSequence 10 }

exampleSequenceOperationalEntry OBJECT-TYPE
   SYNTAX     ExampleSequenceOperationalEntry
   ACCESS     not-accessible
   STATUS     mandatory
   DESCRIPTION
     "An entry in the exampleSequenceOperationalTable."
   INDEX {
      exampleIndex,
      exampleSequenceIndex }
::= { exampleSequenceOperationalTable 1 }

ExampleSequenceOperationalEntry ::= SEQUENCE {
   exampleSequenceOperStructSequence
      IntegerSequence,
   exampleSequenceOperFreeSequence
      IntegerSequence }

exampleSequenceOperStructSequence OBJECT-TYPE
   SYNTAX     IntegerSequence (SIZE (7..9))
   ACCESS     read-write
   STATUS     mandatory
   DESCRIPTION
     ""
::= { exampleSequenceOperationalEntry 1 }

exampleSequenceOperFreeSequence OBJECT-TYPE
   SYNTAX     IntegerSequence (SIZE (7..9))
   ACCESS     read-write
   STATUS     mandatory
   DESCRIPTION
     ""
::= { exampleSequenceOperationalEntry 2 }

exampleSequenceProvisionalTable OBJECT-TYPE
   SYNTAX     SEQUENCE OF ExampleSequenceProvisionalEntry
   ACCESS     not-accessible
   STATUS     mandatory
   DESCRIPTION
     ""
::= { exampleSequence 11 }

exampleSequenceProvisionalEntry OBJECT-TYPE
   SYNTAX     ExampleSequenceProvisionalEntry
   ACCESS     not-accessible
   STATUS     mandatory
   DESCRIPTION
     "An entry in the exampleSequenceProvisionalTable."
   INDEX {
      exampleIndex,
      exampleSequenceIndex }
::= { exampleSequenceProvisionalTable 1 }

ExampleSequenceProvisionalEntry ::= SEQUENCE {
   exampleSequenceProvStructSequence
      IntegerSequence,
   exampleSequenceProvFreeSequence
      IntegerSequence }

exampleSequenceProvStructSequence OBJECT-TYPE
   SYNTAX     IntegerSequence (SIZE (7..9))
   ACCESS     read-write
   STATUS     mandatory
   DESCRIPTION
     ""
::= { exampleSequenceProvisionalEntry 1 }

exampleSequenceProvFreeSequence OBJECT-TYPE
   SYNTAX     IntegerSequence (SIZE (1))
   ACCESS     read-write
   STATUS     mandatory
   DESCRIPTION
     ""
::= { exampleSequenceProvisionalEntry 2 }

exampleSequenceOperFreeSequenceReplicatedTable OBJECT-TYPE
   SYNTAX     SEQUENCE OF ExampleSequenceOperFreeSequenceReplicatedEntry
   ACCESS     not-accessible
   STATUS     mandatory
   DESCRIPTION
     ""
::= { exampleSequence 1112 }

exampleSequenceOperFreeSequenceReplicatedEntry OBJECT-TYPE
   SYNTAX     ExampleSequenceOperFreeSequenceReplicatedEntry
   ACCESS     not-accessible
   STATUS     mandatory
   DESCRIPTION
     "An entry in the exampleSequenceOperFreeSequenceReplicatedTable."
   INDEX {
      exampleIndex,
      exampleSequenceIndex,
      exampleSequenceOperFreeSequenceReplicatedIndex }
::= { exampleSequenceOperFreeSequenceReplicatedTable 1 }

ExampleSequenceOperFreeSequenceReplicatedEntry ::= SEQUENCE {
   exampleSequenceOperFreeSequenceReplicatedIndex
      OBJECT IDENTIFIER,
   exampleSequenceOperFreeSequenceReplicatedValue
      IntegerSequence,
   exampleSequenceOperFreeSequenceReplicatedRowStatus
      RowStatus }

exampleSequenceOperFreeSequenceReplicatedIndex OBJECT-TYPE
   SYNTAX     OBJECT IDENTIFIER 
   ACCESS     not-accessible
   STATUS     mandatory
   DESCRIPTION
     "This variable represents the index for the exampleSequenceOperFreeSequenceReplicatedTable."
::= { exampleSequenceOperFreeSequenceReplicatedEntry 1 }

exampleSequenceOperFreeSequenceReplicatedValue OBJECT-TYPE
   SYNTAX     IntegerSequence (SIZE (7..9))
   ACCESS     read-write
   STATUS     mandatory
   DESCRIPTION
     "This variable represents an individual value for the
      exampleSequenceOperFreeSequenceReplicatedTable."
::= { exampleSequenceOperFreeSequenceReplicatedEntry 2 }

exampleSequenceOperFreeSequenceReplicatedRowStatus OBJECT-TYPE
   SYNTAX     RowStatus 
   ACCESS     write-only
   STATUS     mandatory
   DESCRIPTION
     "This variable is used to control the addition and deletion 
      of individual values of the exampleSequenceOperFreeSequenceReplicatedTable."
::= { exampleSequenceOperFreeSequenceReplicatedEntry 3 }

exampleSequenceOperFreeSequenceListTable OBJECT-TYPE
   SYNTAX     SEQUENCE OF ExampleSequenceOperFreeSequenceListEntry
   ACCESS     not-accessible
   STATUS     mandatory
   DESCRIPTION
     ""
::= { exampleSequence 1113 }

exampleSequenceOperFreeSequenceListEntry OBJECT-TYPE
   SYNTAX     ExampleSequenceOperFreeSequenceListEntry
   ACCESS     not-accessible
   STATUS     mandatory
   DESCRIPTION
     "An entry in the exampleSequenceOperFreeSequenceListTable."
   INDEX {
      exampleIndex,
      exampleSequenceIndex,
      exampleSequenceOperFreeSequenceListValue }
::= { exampleSequenceOperFreeSequenceListTable 1 }

ExampleSequenceOperFreeSequenceListEntry ::= SEQUENCE {
   exampleSequenceOperFreeSequenceListValue
      IntegerSequence,
   exampleSequenceOperFreeSequenceListRowStatus
      RowStatus }

exampleSequenceOperFreeSequenceListValue OBJECT-TYPE
   SYNTAX     IntegerSequence (SIZE (7..9))
   ACCESS     read-write
   STATUS     mandatory
   DESCRIPTION
     "This variable represents both the value and the index for the
      exampleSequenceOperFreeSequenceListTable."
::= { exampleSequenceOperFreeSequenceListEntry 1 }

exampleSequenceOperFreeSequenceListRowStatus OBJECT-TYPE
   SYNTAX     RowStatus 
   ACCESS     write-only
   STATUS     mandatory
   DESCRIPTION
     "This variable is used to control the addition and deletion 
      of individual values of the exampleSequenceOperFreeSequenceListTable."
::= { exampleSequenceOperFreeSequenceListEntry 2 }

exampleSequenceProvFreeSequenceReplicatedTable OBJECT-TYPE
   SYNTAX     SEQUENCE OF ExampleSequenceProvFreeSequenceReplicatedEntry
   ACCESS     not-accessible
   STATUS     mandatory
   DESCRIPTION
     ""
::= { exampleSequence 1114 }

exampleSequenceProvFreeSequenceReplicatedEntry OBJECT-TYPE
   SYNTAX     ExampleSequenceProvFreeSequenceReplicatedEntry
   ACCESS     not-accessible
   STATUS     mandatory
   DESCRIPTION
     "An entry in the exampleSequenceProvFreeSequenceReplicatedTable."
   INDEX {
      exampleIndex,
      exampleSequenceIndex,
      exampleSequenceProvFreeSequenceReplicatedIndex }
::= { exampleSequenceProvFreeSequenceReplicatedTable 1 }

ExampleSequenceProvFreeSequenceReplicatedEntry ::= SEQUENCE {
   exampleSequenceProvFreeSequenceReplicatedIndex
      OBJECT IDENTIFIER,
   exampleSequenceProvFreeSequenceReplicatedValue
      IntegerSequence,
   exampleSequenceProvFreeSequenceReplicatedRowStatus
      RowStatus }

exampleSequenceProvFreeSequenceReplicatedIndex OBJECT-TYPE
   SYNTAX     OBJECT IDENTIFIER 
   ACCESS     not-accessible
   STATUS     mandatory
   DESCRIPTION
     "This variable represents the index for the exampleSequenceProvFreeSequenceReplicatedTable."
::= { exampleSequenceProvFreeSequenceReplicatedEntry 1 }

exampleSequenceProvFreeSequenceReplicatedValue OBJECT-TYPE
   SYNTAX     IntegerSequence (SIZE (7))
   ACCESS     read-write
   STATUS     mandatory
   DESCRIPTION
     "This variable represents an individual value for the
      exampleSequenceProvFreeSequenceReplicatedTable."
::= { exampleSequenceProvFreeSequenceReplicatedEntry 2 }

exampleSequenceProvFreeSequenceReplicatedRowStatus OBJECT-TYPE
   SYNTAX     RowStatus 
   ACCESS     write-only
   STATUS     mandatory
   DESCRIPTION
     "This variable is used to control the addition and deletion 
      of individual values of the exampleSequenceProvFreeSequenceReplicatedTable."
::= { exampleSequenceProvFreeSequenceReplicatedEntry 3 }

exampleSequenceProvFreeSequenceListTable OBJECT-TYPE
   SYNTAX     SEQUENCE OF ExampleSequenceProvFreeSequenceListEntry
   ACCESS     not-accessible
   STATUS     mandatory
   DESCRIPTION
     ""
::= { exampleSequence 1115 }

exampleSequenceProvFreeSequenceListEntry OBJECT-TYPE
   SYNTAX     ExampleSequenceProvFreeSequenceListEntry
   ACCESS     not-accessible
   STATUS     mandatory
   DESCRIPTION
     "An entry in the exampleSequenceProvFreeSequenceListTable."
   INDEX {
      exampleIndex,
      exampleSequenceIndex,
      exampleSequenceProvFreeSequenceListValue }
::= { exampleSequenceProvFreeSequenceListTable 1 }

ExampleSequenceProvFreeSequenceListEntry ::= SEQUENCE {
   exampleSequenceProvFreeSequenceListValue
      IntegerSequence,
   exampleSequenceProvFreeSequenceListRowStatus
      RowStatus }

exampleSequenceProvFreeSequenceListValue OBJECT-TYPE
   SYNTAX     IntegerSequence (SIZE (7..9))
   ACCESS     read-write
   STATUS     mandatory
   DESCRIPTION
     "This variable represents both the value and the index for the
      exampleSequenceProvFreeSequenceListTable."
::= { exampleSequenceProvFreeSequenceListEntry 1 }

exampleSequenceProvFreeSequenceListRowStatus OBJECT-TYPE
   SYNTAX     RowStatus 
   ACCESS     write-only
   STATUS     mandatory
   DESCRIPTION
     "This variable is used to control the addition and deletion 
      of individual values of the exampleSequenceProvFreeSequenceListTable."
::= { exampleSequenceProvFreeSequenceListEntry 2 }



exampleSigned OBJECT IDENTIFIER ::= { example 14 }



exampleSignedRowStatusTable OBJECT-TYPE
   SYNTAX     SEQUENCE OF ExampleSignedRowStatusEntry
   ACCESS     not-accessible
   STATUS     mandatory
   DESCRIPTION
     "This entry controls the addition and deletion of 
      exampleSigned components."
::= { exampleSigned 1 }

exampleSignedRowStatusEntry OBJECT-TYPE
   SYNTAX     ExampleSignedRowStatusEntry
   ACCESS     not-accessible
   STATUS     mandatory
   DESCRIPTION
     "A single entry in the table represents a single 
      exampleSigned component."
   INDEX {
      exampleIndex,
      exampleSignedIndex }
::= { exampleSignedRowStatusTable 1 }

ExampleSignedRowStatusEntry ::= SEQUENCE {
   exampleSignedRowStatus
      RowStatus,
   exampleSignedComponentName
      DisplayString,
   exampleSignedStorageType
      StorageType,
   exampleSignedIndex
      NonReplicated }

exampleSignedRowStatus OBJECT-TYPE
   SYNTAX     RowStatus 
   ACCESS     read-write
   STATUS     mandatory
   DESCRIPTION
     "This variable is used as the basis for SNMP naming of
      exampleSigned components.
      These components can be added and deleted."
::= { exampleSignedRowStatusEntry 1 }

exampleSignedComponentName OBJECT-TYPE
   SYNTAX     DisplayString 
   ACCESS     read-only
   STATUS     mandatory
   DESCRIPTION
     "This variable provides the component's string name for
      use with the ASCII Console Interface"
::= { exampleSignedRowStatusEntry 2 }

exampleSignedStorageType OBJECT-TYPE
   SYNTAX     StorageType 
   ACCESS     read-only
   STATUS     mandatory
   DESCRIPTION
     "This variable represents the storage type value for the
      exampleSigned tables."
::= { exampleSignedRowStatusEntry 4 }

exampleSignedIndex OBJECT-TYPE
   SYNTAX     NonReplicated 
   ACCESS     not-accessible
   STATUS     mandatory
   DESCRIPTION
     "This variable represents the index for the exampleSigned tables."
::= { exampleSignedRowStatusEntry 10 }

exampleSignedOperationalTable OBJECT-TYPE
   SYNTAX     SEQUENCE OF ExampleSignedOperationalEntry
   ACCESS     not-accessible
   STATUS     mandatory
   DESCRIPTION
     ""
::= { exampleSigned 10 }

exampleSignedOperationalEntry OBJECT-TYPE
   SYNTAX     ExampleSignedOperationalEntry
   ACCESS     not-accessible
   STATUS     mandatory
   DESCRIPTION
     "An entry in the exampleSignedOperationalTable."
   INDEX {
      exampleIndex,
      exampleSignedIndex }
::= { exampleSignedOperationalTable 1 }

ExampleSignedOperationalEntry ::= SEQUENCE {
   exampleSignedOperStructSigned
      INTEGER,
   exampleSignedOperFreeSigned
      INTEGER }

exampleSignedOperStructSigned OBJECT-TYPE
   SYNTAX     INTEGER (-16..16)
   ACCESS     read-write
   STATUS     mandatory
   DESCRIPTION
     ""
::= { exampleSignedOperationalEntry 1 }

exampleSignedOperFreeSigned OBJECT-TYPE
   SYNTAX     INTEGER (-16..16)
   ACCESS     read-write
   STATUS     mandatory
   DESCRIPTION
     ""
::= { exampleSignedOperationalEntry 2 }

exampleSignedProvisionalTable OBJECT-TYPE
   SYNTAX     SEQUENCE OF ExampleSignedProvisionalEntry
   ACCESS     not-accessible
   STATUS     mandatory
   DESCRIPTION
     ""
::= { exampleSigned 11 }

exampleSignedProvisionalEntry OBJECT-TYPE
   SYNTAX     ExampleSignedProvisionalEntry
   ACCESS     not-accessible
   STATUS     mandatory
   DESCRIPTION
     "An entry in the exampleSignedProvisionalTable."
   INDEX {
      exampleIndex,
      exampleSignedIndex }
::= { exampleSignedProvisionalTable 1 }

ExampleSignedProvisionalEntry ::= SEQUENCE {
   exampleSignedProvSignedSub
      Link,
   exampleSignedProvStructSigned
      INTEGER,
   exampleSignedProvFreeSigned
      INTEGER,
   exampleSignedProvFreeSigned1
      INTEGER }

exampleSignedProvSignedSub OBJECT-TYPE
   SYNTAX     Link 
   ACCESS     read-write
   STATUS     mandatory
   DESCRIPTION
     ""
::= { exampleSignedProvisionalEntry 1 }

exampleSignedProvStructSigned OBJECT-TYPE
   SYNTAX     INTEGER (-17 | -16..16 | 17 | 18)
   ACCESS     read-write
   STATUS     mandatory
   DESCRIPTION
     "VALUES (

      -17 = infinity

      17 = notApplicable

      18 = notMeasured

      )"
   DEFVAL     { -17 }
::= { exampleSignedProvisionalEntry 2 }

exampleSignedProvFreeSigned OBJECT-TYPE
   SYNTAX     INTEGER (-4..8)
   ACCESS     read-write
   STATUS     mandatory
   DESCRIPTION
     ""
   DEFVAL     { -2 }
::= { exampleSignedProvisionalEntry 3 }

exampleSignedProvFreeSigned1 OBJECT-TYPE
   SYNTAX     INTEGER (-4..8)
   ACCESS     read-write
   STATUS     mandatory
   DESCRIPTION
     ""
::= { exampleSignedProvisionalEntry 4 }

exampleSignedOperStructSignedVectorTable OBJECT-TYPE
   SYNTAX     SEQUENCE OF ExampleSignedOperStructSignedVectorEntry
   ACCESS     not-accessible
   STATUS     mandatory
   DESCRIPTION
     ""
::= { exampleSigned 1148 }

exampleSignedOperStructSignedVectorEntry OBJECT-TYPE
   SYNTAX     ExampleSignedOperStructSignedVectorEntry
   ACCESS     not-accessible
   STATUS     mandatory
   DESCRIPTION
     "An entry in the exampleSignedOperStructSignedVectorTable."
   INDEX {
      exampleIndex,
      exampleSignedIndex,
      exampleSignedOperStructSignedVectorIndex }
::= { exampleSignedOperStructSignedVectorTable 1 }

ExampleSignedOperStructSignedVectorEntry ::= SEQUENCE {
   exampleSignedOperStructSignedVectorIndex
      Integer32,
   exampleSignedOperStructSignedVectorValue
      INTEGER }

exampleSignedOperStructSignedVectorIndex OBJECT-TYPE
   SYNTAX     Integer32 (0..9)
   ACCESS     not-accessible
   STATUS     mandatory
   DESCRIPTION
     "This variable represents the exampleSignedOperStructSignedVectorTable
      specific index for the exampleSignedOperStructSignedVectorTable."
::= { exampleSignedOperStructSignedVectorEntry 1 }

exampleSignedOperStructSignedVectorValue OBJECT-TYPE
   SYNTAX     INTEGER (-5..5)
   ACCESS     read-write
   STATUS     mandatory
   DESCRIPTION
     "This variable represents an individual value for the
      exampleSignedOperStructSignedVectorTable."
::= { exampleSignedOperStructSignedVectorEntry 2 }

exampleSignedOperStructSignedArrayTable OBJECT-TYPE
   SYNTAX     SEQUENCE OF ExampleSignedOperStructSignedArrayEntry
   ACCESS     not-accessible
   STATUS     mandatory
   DESCRIPTION
     ""
::= { exampleSigned 1149 }

exampleSignedOperStructSignedArrayEntry OBJECT-TYPE
   SYNTAX     ExampleSignedOperStructSignedArrayEntry
   ACCESS     not-accessible
   STATUS     mandatory
   DESCRIPTION
     "An entry in the exampleSignedOperStructSignedArrayTable."
   INDEX {
      exampleIndex,
      exampleSignedIndex,
      exampleSignedOperStructSignedArrayRowIndex,
      exampleSignedOperStructSignedArrayColumnIndex }
::= { exampleSignedOperStructSignedArrayTable 1 }

ExampleSignedOperStructSignedArrayEntry ::= SEQUENCE {
   exampleSignedOperStructSignedArrayRowIndex
      Integer32,
   exampleSignedOperStructSignedArrayColumnIndex
      Integer32,
   exampleSignedOperStructSignedArrayValue
      INTEGER }

exampleSignedOperStructSignedArrayRowIndex OBJECT-TYPE
   SYNTAX     Integer32 (0..2)
   ACCESS     not-accessible
   STATUS     mandatory
   DESCRIPTION
     "This variable represents the next to last index for the 
      exampleSignedOperStructSignedArrayTable."
::= { exampleSignedOperStructSignedArrayEntry 1 }

exampleSignedOperStructSignedArrayColumnIndex OBJECT-TYPE
   SYNTAX     Integer32 (0..3)
   ACCESS     not-accessible
   STATUS     mandatory
   DESCRIPTION
     "This variable represents the final index for the 
      exampleSignedOperStructSignedArrayTable."
::= { exampleSignedOperStructSignedArrayEntry 2 }

exampleSignedOperStructSignedArrayValue OBJECT-TYPE
   SYNTAX     INTEGER (-5..5)
   ACCESS     read-write
   STATUS     mandatory
   DESCRIPTION
     "This variable represents an individual value for the
      exampleSignedOperStructSignedArrayTable."
::= { exampleSignedOperStructSignedArrayEntry 3 }

exampleSignedOperFreeSignedVectorTable OBJECT-TYPE
   SYNTAX     SEQUENCE OF ExampleSignedOperFreeSignedVectorEntry
   ACCESS     not-accessible
   STATUS     mandatory
   DESCRIPTION
     ""
::= { exampleSigned 1150 }

exampleSignedOperFreeSignedVectorEntry OBJECT-TYPE
   SYNTAX     ExampleSignedOperFreeSignedVectorEntry
   ACCESS     not-accessible
   STATUS     mandatory
   DESCRIPTION
     "An entry in the exampleSignedOperFreeSignedVectorTable."
   INDEX {
      exampleIndex,
      exampleSignedIndex,
      exampleSignedOperFreeSignedVectorIndex }
::= { exampleSignedOperFreeSignedVectorTable 1 }

ExampleSignedOperFreeSignedVectorEntry ::= SEQUENCE {
   exampleSignedOperFreeSignedVectorIndex
      Integer32,
   exampleSignedOperFreeSignedVectorValue
      INTEGER }

exampleSignedOperFreeSignedVectorIndex OBJECT-TYPE
   SYNTAX     Integer32 (0..3)
   ACCESS     not-accessible
   STATUS     mandatory
   DESCRIPTION
     "This variable represents the exampleSignedOperFreeSignedVectorTable
      specific index for the exampleSignedOperFreeSignedVectorTable."
::= { exampleSignedOperFreeSignedVectorEntry 1 }

exampleSignedOperFreeSignedVectorValue OBJECT-TYPE
   SYNTAX     INTEGER (-5..5)
   ACCESS     read-write
   STATUS     mandatory
   DESCRIPTION
     "This variable represents an individual value for the
      exampleSignedOperFreeSignedVectorTable."
::= { exampleSignedOperFreeSignedVectorEntry 2 }

exampleSignedOperFreeSignedArrayTable OBJECT-TYPE
   SYNTAX     SEQUENCE OF ExampleSignedOperFreeSignedArrayEntry
   ACCESS     not-accessible
   STATUS     mandatory
   DESCRIPTION
     ""
::= { exampleSigned 1151 }

exampleSignedOperFreeSignedArrayEntry OBJECT-TYPE
   SYNTAX     ExampleSignedOperFreeSignedArrayEntry
   ACCESS     not-accessible
   STATUS     mandatory
   DESCRIPTION
     "An entry in the exampleSignedOperFreeSignedArrayTable."
   INDEX {
      exampleIndex,
      exampleSignedIndex,
      exampleSignedOperFreeSignedArrayRowIndex,
      exampleSignedOperFreeSignedArrayColumnIndex }
::= { exampleSignedOperFreeSignedArrayTable 1 }

ExampleSignedOperFreeSignedArrayEntry ::= SEQUENCE {
   exampleSignedOperFreeSignedArrayRowIndex
      Integer32,
   exampleSignedOperFreeSignedArrayColumnIndex
      Integer32,
   exampleSignedOperFreeSignedArrayValue
      INTEGER }

exampleSignedOperFreeSignedArrayRowIndex OBJECT-TYPE
   SYNTAX     Integer32 (0..2)
   ACCESS     not-accessible
   STATUS     mandatory
   DESCRIPTION
     "This variable represents the next to last index for the 
      exampleSignedOperFreeSignedArrayTable."
::= { exampleSignedOperFreeSignedArrayEntry 1 }

exampleSignedOperFreeSignedArrayColumnIndex OBJECT-TYPE
   SYNTAX     Integer32 (0..3)
   ACCESS     not-accessible
   STATUS     mandatory
   DESCRIPTION
     "This variable represents the final index for the 
      exampleSignedOperFreeSignedArrayTable."
::= { exampleSignedOperFreeSignedArrayEntry 2 }

exampleSignedOperFreeSignedArrayValue OBJECT-TYPE
   SYNTAX     INTEGER (-5..5)
   ACCESS     read-write
   STATUS     mandatory
   DESCRIPTION
     "This variable represents an individual value for the
      exampleSignedOperFreeSignedArrayTable."
::= { exampleSignedOperFreeSignedArrayEntry 3 }

exampleSignedOperFreeSignedReplicatedTable OBJECT-TYPE
   SYNTAX     SEQUENCE OF ExampleSignedOperFreeSignedReplicatedEntry
   ACCESS     not-accessible
   STATUS     mandatory
   DESCRIPTION
     ""
::= { exampleSigned 1152 }

exampleSignedOperFreeSignedReplicatedEntry OBJECT-TYPE
   SYNTAX     ExampleSignedOperFreeSignedReplicatedEntry
   ACCESS     not-accessible
   STATUS     mandatory
   DESCRIPTION
     "An entry in the exampleSignedOperFreeSignedReplicatedTable."
   INDEX {
      exampleIndex,
      exampleSignedIndex,
      exampleSignedOperFreeSignedReplicatedIndex }
::= { exampleSignedOperFreeSignedReplicatedTable 1 }

ExampleSignedOperFreeSignedReplicatedEntry ::= SEQUENCE {
   exampleSignedOperFreeSignedReplicatedIndex
      INTEGER,
   exampleSignedOperFreeSignedReplicatedValue
      INTEGER,
   exampleSignedOperFreeSignedReplicatedRowStatus
      RowStatus }

exampleSignedOperFreeSignedReplicatedIndex OBJECT-TYPE
   SYNTAX     INTEGER (-5..5)
   ACCESS     not-accessible
   STATUS     mandatory
   DESCRIPTION
     "This variable represents the index for the exampleSignedOperFreeSignedReplicatedTable."
::= { exampleSignedOperFreeSignedReplicatedEntry 1 }

exampleSignedOperFreeSignedReplicatedValue OBJECT-TYPE
   SYNTAX     INTEGER (-16..16)
   ACCESS     read-write
   STATUS     mandatory
   DESCRIPTION
     "This variable represents an individual value for the
      exampleSignedOperFreeSignedReplicatedTable."
::= { exampleSignedOperFreeSignedReplicatedEntry 2 }

exampleSignedOperFreeSignedReplicatedRowStatus OBJECT-TYPE
   SYNTAX     RowStatus 
   ACCESS     write-only
   STATUS     mandatory
   DESCRIPTION
     "This variable is used to control the addition and deletion 
      of individual values of the exampleSignedOperFreeSignedReplicatedTable."
::= { exampleSignedOperFreeSignedReplicatedEntry 3 }

exampleSignedOperFreeSignedListTable OBJECT-TYPE
   SYNTAX     SEQUENCE OF ExampleSignedOperFreeSignedListEntry
   ACCESS     not-accessible
   STATUS     mandatory
   DESCRIPTION
     ""
::= { exampleSigned 1153 }

exampleSignedOperFreeSignedListEntry OBJECT-TYPE
   SYNTAX     ExampleSignedOperFreeSignedListEntry
   ACCESS     not-accessible
   STATUS     mandatory
   DESCRIPTION
     "An entry in the exampleSignedOperFreeSignedListTable."
   INDEX {
      exampleIndex,
      exampleSignedIndex,
      exampleSignedOperFreeSignedListValue }
::= { exampleSignedOperFreeSignedListTable 1 }

ExampleSignedOperFreeSignedListEntry ::= SEQUENCE {
   exampleSignedOperFreeSignedListValue
      INTEGER,
   exampleSignedOperFreeSignedListRowStatus
      RowStatus }

exampleSignedOperFreeSignedListValue OBJECT-TYPE
   SYNTAX     INTEGER (-16..16)
   ACCESS     read-write
   STATUS     mandatory
   DESCRIPTION
     "This variable represents both the value and the index for the
      exampleSignedOperFreeSignedListTable."
::= { exampleSignedOperFreeSignedListEntry 1 }

exampleSignedOperFreeSignedListRowStatus OBJECT-TYPE
   SYNTAX     RowStatus 
   ACCESS     write-only
   STATUS     mandatory
   DESCRIPTION
     "This variable is used to control the addition and deletion 
      of individual values of the exampleSignedOperFreeSignedListTable."
::= { exampleSignedOperFreeSignedListEntry 2 }

exampleSignedProvStructSignedVectorTable OBJECT-TYPE
   SYNTAX     SEQUENCE OF ExampleSignedProvStructSignedVectorEntry
   ACCESS     not-accessible
   STATUS     mandatory
   DESCRIPTION
     ""
::= { exampleSigned 1154 }

exampleSignedProvStructSignedVectorEntry OBJECT-TYPE
   SYNTAX     ExampleSignedProvStructSignedVectorEntry
   ACCESS     not-accessible
   STATUS     mandatory
   DESCRIPTION
     "An entry in the exampleSignedProvStructSignedVectorTable."
   INDEX {
      exampleIndex,
      exampleSignedIndex,
      exampleSignedProvStructSignedVectorIndex }
::= { exampleSignedProvStructSignedVectorTable 1 }

ExampleSignedProvStructSignedVectorEntry ::= SEQUENCE {
   exampleSignedProvStructSignedVectorIndex
      Integer32,
   exampleSignedProvStructSignedVectorValue
      INTEGER }

exampleSignedProvStructSignedVectorIndex OBJECT-TYPE
   SYNTAX     Integer32 (0..9)
   ACCESS     not-accessible
   STATUS     mandatory
   DESCRIPTION
     "This variable represents the exampleSignedProvStructSignedVectorTable
      specific index for the exampleSignedProvStructSignedVectorTable."
::= { exampleSignedProvStructSignedVectorEntry 1 }

exampleSignedProvStructSignedVectorValue OBJECT-TYPE
   SYNTAX     INTEGER (-5..5)
   ACCESS     read-write
   STATUS     mandatory
   DESCRIPTION
     "This variable represents an individual value for the
      exampleSignedProvStructSignedVectorTable."
::= { exampleSignedProvStructSignedVectorEntry 2 }

exampleSignedProvStructSignedArrayTable OBJECT-TYPE
   SYNTAX     SEQUENCE OF ExampleSignedProvStructSignedArrayEntry
   ACCESS     not-accessible
   STATUS     mandatory
   DESCRIPTION
     ""
::= { exampleSigned 1155 }

exampleSignedProvStructSignedArrayEntry OBJECT-TYPE
   SYNTAX     ExampleSignedProvStructSignedArrayEntry
   ACCESS     not-accessible
   STATUS     mandatory
   DESCRIPTION
     "An entry in the exampleSignedProvStructSignedArrayTable."
   INDEX {
      exampleIndex,
      exampleSignedIndex,
      exampleSignedProvStructSignedArrayRowIndex,
      exampleSignedProvStructSignedArrayColumnIndex }
::= { exampleSignedProvStructSignedArrayTable 1 }

ExampleSignedProvStructSignedArrayEntry ::= SEQUENCE {
   exampleSignedProvStructSignedArrayRowIndex
      Integer32,
   exampleSignedProvStructSignedArrayColumnIndex
      Integer32,
   exampleSignedProvStructSignedArrayValue
      INTEGER }

exampleSignedProvStructSignedArrayRowIndex OBJECT-TYPE
   SYNTAX     Integer32 (0..2)
   ACCESS     not-accessible
   STATUS     mandatory
   DESCRIPTION
     "This variable represents the next to last index for the 
      exampleSignedProvStructSignedArrayTable."
::= { exampleSignedProvStructSignedArrayEntry 1 }

exampleSignedProvStructSignedArrayColumnIndex OBJECT-TYPE
   SYNTAX     Integer32 (0..3)
   ACCESS     not-accessible
   STATUS     mandatory
   DESCRIPTION
     "This variable represents the final index for the 
      exampleSignedProvStructSignedArrayTable."
::= { exampleSignedProvStructSignedArrayEntry 2 }

exampleSignedProvStructSignedArrayValue OBJECT-TYPE
   SYNTAX     INTEGER (-5..5)
   ACCESS     read-write
   STATUS     mandatory
   DESCRIPTION
     "This variable represents an individual value for the
      exampleSignedProvStructSignedArrayTable."
::= { exampleSignedProvStructSignedArrayEntry 3 }

exampleSignedProvFreeSignedVectorTable OBJECT-TYPE
   SYNTAX     SEQUENCE OF ExampleSignedProvFreeSignedVectorEntry
   ACCESS     not-accessible
   STATUS     mandatory
   DESCRIPTION
     ""
::= { exampleSigned 1156 }

exampleSignedProvFreeSignedVectorEntry OBJECT-TYPE
   SYNTAX     ExampleSignedProvFreeSignedVectorEntry
   ACCESS     not-accessible
   STATUS     mandatory
   DESCRIPTION
     "An entry in the exampleSignedProvFreeSignedVectorTable."
   INDEX {
      exampleIndex,
      exampleSignedIndex,
      exampleSignedProvFreeSignedVectorIndex }
::= { exampleSignedProvFreeSignedVectorTable 1 }

ExampleSignedProvFreeSignedVectorEntry ::= SEQUENCE {
   exampleSignedProvFreeSignedVectorIndex
      Integer32,
   exampleSignedProvFreeSignedVectorValue
      INTEGER }

exampleSignedProvFreeSignedVectorIndex OBJECT-TYPE
   SYNTAX     Integer32 (0..9)
   ACCESS     not-accessible
   STATUS     mandatory
   DESCRIPTION
     "This variable represents the exampleSignedProvFreeSignedVectorTable
      specific index for the exampleSignedProvFreeSignedVectorTable."
::= { exampleSignedProvFreeSignedVectorEntry 1 }

exampleSignedProvFreeSignedVectorValue OBJECT-TYPE
   SYNTAX     INTEGER (-5..5)
   ACCESS     read-write
   STATUS     mandatory
   DESCRIPTION
     "This variable represents an individual value for the
      exampleSignedProvFreeSignedVectorTable."
::= { exampleSignedProvFreeSignedVectorEntry 2 }

exampleSignedProvFreeSignedVector1Table OBJECT-TYPE
   SYNTAX     SEQUENCE OF ExampleSignedProvFreeSignedVector1Entry
   ACCESS     not-accessible
   STATUS     mandatory
   DESCRIPTION
     ""
::= { exampleSigned 1157 }

exampleSignedProvFreeSignedVector1Entry OBJECT-TYPE
   SYNTAX     ExampleSignedProvFreeSignedVector1Entry
   ACCESS     not-accessible
   STATUS     mandatory
   DESCRIPTION
     "An entry in the exampleSignedProvFreeSignedVector1Table."
   INDEX {
      exampleIndex,
      exampleSignedIndex,
      exampleSignedProvFreeSignedVector1Index }
::= { exampleSignedProvFreeSignedVector1Table 1 }

ExampleSignedProvFreeSignedVector1Entry ::= SEQUENCE {
   exampleSignedProvFreeSignedVector1Index
      Integer32,
   exampleSignedProvFreeSignedVector1Value
      INTEGER }

exampleSignedProvFreeSignedVector1Index OBJECT-TYPE
   SYNTAX     Integer32 (0..9)
   ACCESS     not-accessible
   STATUS     mandatory
   DESCRIPTION
     "This variable represents the exampleSignedProvFreeSignedVector1Table
      specific index for the exampleSignedProvFreeSignedVector1Table."
::= { exampleSignedProvFreeSignedVector1Entry 1 }

exampleSignedProvFreeSignedVector1Value OBJECT-TYPE
   SYNTAX     INTEGER (-5..5)
   ACCESS     read-write
   STATUS     mandatory
   DESCRIPTION
     "This variable represents an individual value for the
      exampleSignedProvFreeSignedVector1Table."
::= { exampleSignedProvFreeSignedVector1Entry 2 }

exampleSignedProvFreeSignedArrayTable OBJECT-TYPE
   SYNTAX     SEQUENCE OF ExampleSignedProvFreeSignedArrayEntry
   ACCESS     not-accessible
   STATUS     mandatory
   DESCRIPTION
     ""
::= { exampleSigned 1158 }

exampleSignedProvFreeSignedArrayEntry OBJECT-TYPE
   SYNTAX     ExampleSignedProvFreeSignedArrayEntry
   ACCESS     not-accessible
   STATUS     mandatory
   DESCRIPTION
     "An entry in the exampleSignedProvFreeSignedArrayTable."
   INDEX {
      exampleIndex,
      exampleSignedIndex,
      exampleSignedProvFreeSignedArrayRowIndex,
      exampleSignedProvFreeSignedArrayColumnIndex }
::= { exampleSignedProvFreeSignedArrayTable 1 }

ExampleSignedProvFreeSignedArrayEntry ::= SEQUENCE {
   exampleSignedProvFreeSignedArrayRowIndex
      Integer32,
   exampleSignedProvFreeSignedArrayColumnIndex
      Integer32,
   exampleSignedProvFreeSignedArrayValue
      INTEGER }

exampleSignedProvFreeSignedArrayRowIndex OBJECT-TYPE
   SYNTAX     Integer32 (0..2)
   ACCESS     not-accessible
   STATUS     mandatory
   DESCRIPTION
     "This variable represents the next to last index for the 
      exampleSignedProvFreeSignedArrayTable."
::= { exampleSignedProvFreeSignedArrayEntry 1 }

exampleSignedProvFreeSignedArrayColumnIndex OBJECT-TYPE
   SYNTAX     Integer32 (0..3)
   ACCESS     not-accessible
   STATUS     mandatory
   DESCRIPTION
     "This variable represents the final index for the 
      exampleSignedProvFreeSignedArrayTable."
::= { exampleSignedProvFreeSignedArrayEntry 2 }

exampleSignedProvFreeSignedArrayValue OBJECT-TYPE
   SYNTAX     INTEGER (-1000..4000)
   ACCESS     read-write
   STATUS     mandatory
   DESCRIPTION
     "This variable represents an individual value for the
      exampleSignedProvFreeSignedArrayTable."
::= { exampleSignedProvFreeSignedArrayEntry 3 }

exampleSignedProvFreeSignedArray1Table OBJECT-TYPE
   SYNTAX     SEQUENCE OF ExampleSignedProvFreeSignedArray1Entry
   ACCESS     not-accessible
   STATUS     mandatory
   DESCRIPTION
     ""
::= { exampleSigned 1159 }

exampleSignedProvFreeSignedArray1Entry OBJECT-TYPE
   SYNTAX     ExampleSignedProvFreeSignedArray1Entry
   ACCESS     not-accessible
   STATUS     mandatory
   DESCRIPTION
     "An entry in the exampleSignedProvFreeSignedArray1Table."
   INDEX {
      exampleIndex,
      exampleSignedIndex,
      exampleSignedProvFreeSignedArray1RowIndex,
      exampleSignedProvFreeSignedArray1ColumnIndex }
::= { exampleSignedProvFreeSignedArray1Table 1 }

ExampleSignedProvFreeSignedArray1Entry ::= SEQUENCE {
   exampleSignedProvFreeSignedArray1RowIndex
      Integer32,
   exampleSignedProvFreeSignedArray1ColumnIndex
      Integer32,
   exampleSignedProvFreeSignedArray1Value
      INTEGER }

exampleSignedProvFreeSignedArray1RowIndex OBJECT-TYPE
   SYNTAX     Integer32 (0..2)
   ACCESS     not-accessible
   STATUS     mandatory
   DESCRIPTION
     "This variable represents the next to last index for the 
      exampleSignedProvFreeSignedArray1Table."
::= { exampleSignedProvFreeSignedArray1Entry 1 }

exampleSignedProvFreeSignedArray1ColumnIndex OBJECT-TYPE
   SYNTAX     Integer32 (0..3)
   ACCESS     not-accessible
   STATUS     mandatory
   DESCRIPTION
     "This variable represents the final index for the 
      exampleSignedProvFreeSignedArray1Table."
::= { exampleSignedProvFreeSignedArray1Entry 2 }

exampleSignedProvFreeSignedArray1Value OBJECT-TYPE
   SYNTAX     INTEGER (-1000..4000)
   ACCESS     read-write
   STATUS     mandatory
   DESCRIPTION
     "This variable represents an individual value for the
      exampleSignedProvFreeSignedArray1Table."
::= { exampleSignedProvFreeSignedArray1Entry 3 }

exampleSignedProvFreeSignedReplicatedTable OBJECT-TYPE
   SYNTAX     SEQUENCE OF ExampleSignedProvFreeSignedReplicatedEntry
   ACCESS     not-accessible
   STATUS     mandatory
   DESCRIPTION
     ""
::= { exampleSigned 1160 }

exampleSignedProvFreeSignedReplicatedEntry OBJECT-TYPE
   SYNTAX     ExampleSignedProvFreeSignedReplicatedEntry
   ACCESS     not-accessible
   STATUS     mandatory
   DESCRIPTION
     "An entry in the exampleSignedProvFreeSignedReplicatedTable."
   INDEX {
      exampleIndex,
      exampleSignedIndex,
      exampleSignedProvFreeSignedReplicatedIndex }
::= { exampleSignedProvFreeSignedReplicatedTable 1 }

ExampleSignedProvFreeSignedReplicatedEntry ::= SEQUENCE {
   exampleSignedProvFreeSignedReplicatedIndex
      INTEGER,
   exampleSignedProvFreeSignedReplicatedValue
      INTEGER,
   exampleSignedProvFreeSignedReplicatedRowStatus
      RowStatus }

exampleSignedProvFreeSignedReplicatedIndex OBJECT-TYPE
   SYNTAX     INTEGER (0..5)
   ACCESS     not-accessible
   STATUS     mandatory
   DESCRIPTION
     "This variable represents the index for the exampleSignedProvFreeSignedReplicatedTable."
::= { exampleSignedProvFreeSignedReplicatedEntry 1 }

exampleSignedProvFreeSignedReplicatedValue OBJECT-TYPE
   SYNTAX     INTEGER (-1..13)
   ACCESS     read-write
   STATUS     mandatory
   DESCRIPTION
     "This variable represents an individual value for the
      exampleSignedProvFreeSignedReplicatedTable."
::= { exampleSignedProvFreeSignedReplicatedEntry 2 }

exampleSignedProvFreeSignedReplicatedRowStatus OBJECT-TYPE
   SYNTAX     RowStatus 
   ACCESS     write-only
   STATUS     mandatory
   DESCRIPTION
     "This variable is used to control the addition and deletion 
      of individual values of the exampleSignedProvFreeSignedReplicatedTable."
::= { exampleSignedProvFreeSignedReplicatedEntry 3 }

exampleSignedProvFreeSignedListTable OBJECT-TYPE
   SYNTAX     SEQUENCE OF ExampleSignedProvFreeSignedListEntry
   ACCESS     not-accessible
   STATUS     mandatory
   DESCRIPTION
     ""
::= { exampleSigned 1161 }

exampleSignedProvFreeSignedListEntry OBJECT-TYPE
   SYNTAX     ExampleSignedProvFreeSignedListEntry
   ACCESS     not-accessible
   STATUS     mandatory
   DESCRIPTION
     "An entry in the exampleSignedProvFreeSignedListTable."
   INDEX {
      exampleIndex,
      exampleSignedIndex,
      exampleSignedProvFreeSignedListValue }
::= { exampleSignedProvFreeSignedListTable 1 }

ExampleSignedProvFreeSignedListEntry ::= SEQUENCE {
   exampleSignedProvFreeSignedListValue
      INTEGER,
   exampleSignedProvFreeSignedListRowStatus
      RowStatus }

exampleSignedProvFreeSignedListValue OBJECT-TYPE
   SYNTAX     INTEGER (-3000..160)
   ACCESS     read-write
   STATUS     mandatory
   DESCRIPTION
     "This variable represents both the value and the index for the
      exampleSignedProvFreeSignedListTable."
::= { exampleSignedProvFreeSignedListEntry 1 }

exampleSignedProvFreeSignedListRowStatus OBJECT-TYPE
   SYNTAX     RowStatus 
   ACCESS     write-only
   STATUS     mandatory
   DESCRIPTION
     "This variable is used to control the addition and deletion 
      of individual values of the exampleSignedProvFreeSignedListTable."
::= { exampleSignedProvFreeSignedListEntry 2 }



exampleMiscellaneous OBJECT IDENTIFIER ::= { example 15 }



exampleMiscellaneousRowStatusTable OBJECT-TYPE
   SYNTAX     SEQUENCE OF ExampleMiscellaneousRowStatusEntry
   ACCESS     not-accessible
   STATUS     mandatory
   DESCRIPTION
     "This entry controls the addition and deletion of 
      exampleMiscellaneous components."
::= { exampleMiscellaneous 1 }

exampleMiscellaneousRowStatusEntry OBJECT-TYPE
   SYNTAX     ExampleMiscellaneousRowStatusEntry
   ACCESS     not-accessible
   STATUS     mandatory
   DESCRIPTION
     "A single entry in the table represents a single 
      exampleMiscellaneous component."
   INDEX {
      exampleIndex,
      exampleMiscellaneousIndex }
::= { exampleMiscellaneousRowStatusTable 1 }

ExampleMiscellaneousRowStatusEntry ::= SEQUENCE {
   exampleMiscellaneousRowStatus
      RowStatus,
   exampleMiscellaneousComponentName
      DisplayString,
   exampleMiscellaneousStorageType
      StorageType,
   exampleMiscellaneousIndex
      NonReplicated }

exampleMiscellaneousRowStatus OBJECT-TYPE
   SYNTAX     RowStatus 
   ACCESS     read-write
   STATUS     mandatory
   DESCRIPTION
     "This variable is used as the basis for SNMP naming of
      exampleMiscellaneous components.
      These components can be added and deleted."
::= { exampleMiscellaneousRowStatusEntry 1 }

exampleMiscellaneousComponentName OBJECT-TYPE
   SYNTAX     DisplayString 
   ACCESS     read-only
   STATUS     mandatory
   DESCRIPTION
     "This variable provides the component's string name for
      use with the ASCII Console Interface"
::= { exampleMiscellaneousRowStatusEntry 2 }

exampleMiscellaneousStorageType OBJECT-TYPE
   SYNTAX     StorageType 
   ACCESS     read-only
   STATUS     mandatory
   DESCRIPTION
     "This variable represents the storage type value for the
      exampleMiscellaneous tables."
::= { exampleMiscellaneousRowStatusEntry 4 }

exampleMiscellaneousIndex OBJECT-TYPE
   SYNTAX     NonReplicated 
   ACCESS     not-accessible
   STATUS     mandatory
   DESCRIPTION
     "This variable represents the index for the exampleMiscellaneous tables."
::= { exampleMiscellaneousRowStatusEntry 10 }

exampleMiscellaneousOperationalTable OBJECT-TYPE
   SYNTAX     SEQUENCE OF ExampleMiscellaneousOperationalEntry
   ACCESS     not-accessible
   STATUS     mandatory
   DESCRIPTION
     ""
::= { exampleMiscellaneous 10 }

exampleMiscellaneousOperationalEntry OBJECT-TYPE
   SYNTAX     ExampleMiscellaneousOperationalEntry
   ACCESS     not-accessible
   STATUS     mandatory
   DESCRIPTION
     "An entry in the exampleMiscellaneousOperationalTable."
   INDEX {
      exampleIndex,
      exampleMiscellaneousIndex }
::= { exampleMiscellaneousOperationalTable 1 }

ExampleMiscellaneousOperationalEntry ::= SEQUENCE {
   exampleMiscellaneousOperStructLong
      Unsigned64,
   exampleMiscellaneousOperFreeLong
      Unsigned64,
   exampleMiscellaneousOperFreeTime
      EnterpriseDateAndTime,
   exampleMiscellaneousOperFreeTimeDateOnly
      EnterpriseDateAndTime,
   exampleMiscellaneousOperFreeTimeTimeOnly
      EnterpriseDateAndTime,
   exampleMiscellaneousOperFreeTimeDateTimeMinute
      EnterpriseDateAndTime,
   exampleMiscellaneousOperFreeCounter64
      PassportCounter64,
   exampleMiscellaneousOperFreeGauge64
      Gauge64,
   exampleMiscellaneousOperStructCounter64
      PassportCounter64 }

exampleMiscellaneousOperStructLong OBJECT-TYPE
   SYNTAX     Unsigned64 (SIZE (8))
   ACCESS     read-write
   STATUS     mandatory
   DESCRIPTION
     ""
::= { exampleMiscellaneousOperationalEntry 1 }

exampleMiscellaneousOperFreeLong OBJECT-TYPE
   SYNTAX     Unsigned64 (SIZE (8))
   ACCESS     read-write
   STATUS     mandatory
   DESCRIPTION
     ""
::= { exampleMiscellaneousOperationalEntry 2 }

exampleMiscellaneousOperFreeTime OBJECT-TYPE
   SYNTAX     EnterpriseDateAndTime (SIZE (0 | 19))
   ACCESS     read-write
   STATUS     mandatory
   DESCRIPTION
     ""
::= { exampleMiscellaneousOperationalEntry 3 }

exampleMiscellaneousOperFreeTimeDateOnly OBJECT-TYPE
   SYNTAX     EnterpriseDateAndTime (SIZE (0 | 10))
   ACCESS     read-write
   STATUS     mandatory
   DESCRIPTION
     ""
::= { exampleMiscellaneousOperationalEntry 4 }

exampleMiscellaneousOperFreeTimeTimeOnly OBJECT-TYPE
   SYNTAX     EnterpriseDateAndTime (SIZE (0 | 5))
   ACCESS     read-write
   STATUS     mandatory
   DESCRIPTION
     ""
::= { exampleMiscellaneousOperationalEntry 5 }

exampleMiscellaneousOperFreeTimeDateTimeMinute OBJECT-TYPE
   SYNTAX     EnterpriseDateAndTime (SIZE (0 | 16))
   ACCESS     read-write
   STATUS     mandatory
   DESCRIPTION
     ""
::= { exampleMiscellaneousOperationalEntry 6 }

exampleMiscellaneousOperFreeCounter64 OBJECT-TYPE
   SYNTAX     PassportCounter64 
   ACCESS     read-only
   STATUS     mandatory
   DESCRIPTION
     ""
::= { exampleMiscellaneousOperationalEntry 7 }

exampleMiscellaneousOperFreeGauge64 OBJECT-TYPE
   SYNTAX     Gauge64 (SIZE (8))
   ACCESS     read-write
   STATUS     mandatory
   DESCRIPTION
     ""
::= { exampleMiscellaneousOperationalEntry 8 }

exampleMiscellaneousOperStructCounter64 OBJECT-TYPE
   SYNTAX     PassportCounter64 
   ACCESS     read-only
   STATUS     mandatory
   DESCRIPTION
     ""
::= { exampleMiscellaneousOperationalEntry 9 }

exampleMiscellaneousProvisionalTable OBJECT-TYPE
   SYNTAX     SEQUENCE OF ExampleMiscellaneousProvisionalEntry
   ACCESS     not-accessible
   STATUS     mandatory
   DESCRIPTION
     ""
::= { exampleMiscellaneous 11 }

exampleMiscellaneousProvisionalEntry OBJECT-TYPE
   SYNTAX     ExampleMiscellaneousProvisionalEntry
   ACCESS     not-accessible
   STATUS     mandatory
   DESCRIPTION
     "An entry in the exampleMiscellaneousProvisionalTable."
   INDEX {
      exampleIndex,
      exampleMiscellaneousIndex }
::= { exampleMiscellaneousProvisionalTable 1 }

ExampleMiscellaneousProvisionalEntry ::= SEQUENCE {
   exampleMiscellaneousProvEnumSub
      Link,
   exampleMiscellaneousProvStructLong
      Unsigned64,
   exampleMiscellaneousProvFreeLong
      Unsigned64,
   exampleMiscellaneousProvFreeTime
      EnterpriseDateAndTime,
   exampleMiscellaneousProvFreeTimeDateOnly
      EnterpriseDateAndTime,
   exampleMiscellaneousProvFreeTimeTimeOnly
      EnterpriseDateAndTime,
   exampleMiscellaneousProvFreeTimeDateTimeMinute
      EnterpriseDateAndTime,
   exampleMiscellaneousProvFreeTime1
      EnterpriseDateAndTime,
   exampleMiscellaneousProvFreeTimeDateOnly1
      EnterpriseDateAndTime,
   exampleMiscellaneousProvFreeTimeTimeOnly1
      EnterpriseDateAndTime,
   exampleMiscellaneousProvFreeTimeDateTimeMinute1
      EnterpriseDateAndTime }

exampleMiscellaneousProvEnumSub OBJECT-TYPE
   SYNTAX     Link 
   ACCESS     read-write
   STATUS     mandatory
   DESCRIPTION
     ""
::= { exampleMiscellaneousProvisionalEntry 1 }

exampleMiscellaneousProvStructLong OBJECT-TYPE
   SYNTAX     Unsigned64 (SIZE (8))
   ACCESS     read-write
   STATUS     mandatory
   DESCRIPTION
     ""
::= { exampleMiscellaneousProvisionalEntry 2 }

exampleMiscellaneousProvFreeLong OBJECT-TYPE
   SYNTAX     Unsigned64 (SIZE (8))
   ACCESS     read-write
   STATUS     mandatory
   DESCRIPTION
     ""
::= { exampleMiscellaneousProvisionalEntry 3 }

exampleMiscellaneousProvFreeTime OBJECT-TYPE
   SYNTAX     EnterpriseDateAndTime (SIZE (0 | 19))
   ACCESS     read-write
   STATUS     mandatory
   DESCRIPTION
     ""
   DEFVAL     { '313939322d31302d31352031303a33393a3030'H }  -- "1992-10-15 10:39:00"
::= { exampleMiscellaneousProvisionalEntry 4 }

exampleMiscellaneousProvFreeTimeDateOnly OBJECT-TYPE
   SYNTAX     EnterpriseDateAndTime (SIZE (0 | 10))
   ACCESS     read-write
   STATUS     mandatory
   DESCRIPTION
     ""
   DEFVAL     { '313939322d31302d3135'H }  -- "1992-10-15"
::= { exampleMiscellaneousProvisionalEntry 5 }

exampleMiscellaneousProvFreeTimeTimeOnly OBJECT-TYPE
   SYNTAX     EnterpriseDateAndTime (SIZE (0 | 5))
   ACCESS     read-write
   STATUS     mandatory
   DESCRIPTION
     ""
   DEFVAL     { '31303a3339'H }  -- "10:39"
::= { exampleMiscellaneousProvisionalEntry 6 }

exampleMiscellaneousProvFreeTimeDateTimeMinute OBJECT-TYPE
   SYNTAX     EnterpriseDateAndTime (SIZE (0 | 16))
   ACCESS     read-write
   STATUS     mandatory
   DESCRIPTION
     ""
   DEFVAL     { '313939322d31302d31352031303a3330'H }  -- "1992-10-15 10:30"
::= { exampleMiscellaneousProvisionalEntry 7 }

exampleMiscellaneousProvFreeTime1 OBJECT-TYPE
   SYNTAX     EnterpriseDateAndTime (SIZE (0 | 19))
   ACCESS     read-write
   STATUS     mandatory
   DESCRIPTION
     ""
::= { exampleMiscellaneousProvisionalEntry 8 }

exampleMiscellaneousProvFreeTimeDateOnly1 OBJECT-TYPE
   SYNTAX     EnterpriseDateAndTime (SIZE (0 | 10))
   ACCESS     read-write
   STATUS     mandatory
   DESCRIPTION
     ""
::= { exampleMiscellaneousProvisionalEntry 9 }

exampleMiscellaneousProvFreeTimeTimeOnly1 OBJECT-TYPE
   SYNTAX     EnterpriseDateAndTime (SIZE (0 | 8))
   ACCESS     read-write
   STATUS     mandatory
   DESCRIPTION
     ""
::= { exampleMiscellaneousProvisionalEntry 10 }

exampleMiscellaneousProvFreeTimeDateTimeMinute1 OBJECT-TYPE
   SYNTAX     EnterpriseDateAndTime (SIZE (0 | 16))
   ACCESS     read-write
   STATUS     mandatory
   DESCRIPTION
     ""
::= { exampleMiscellaneousProvisionalEntry 11 }

exampleMiscellaneousOperFreeLongReplicatedTable OBJECT-TYPE
   SYNTAX     SEQUENCE OF ExampleMiscellaneousOperFreeLongReplicatedEntry
   ACCESS     not-accessible
   STATUS     mandatory
   DESCRIPTION
     ""
::= { exampleMiscellaneous 1177 }

exampleMiscellaneousOperFreeLongReplicatedEntry OBJECT-TYPE
   SYNTAX     ExampleMiscellaneousOperFreeLongReplicatedEntry
   ACCESS     not-accessible
   STATUS     mandatory
   DESCRIPTION
     "An entry in the exampleMiscellaneousOperFreeLongReplicatedTable."
   INDEX {
      exampleIndex,
      exampleMiscellaneousIndex,
      exampleMiscellaneousOperFreeLongReplicatedIndex }
::= { exampleMiscellaneousOperFreeLongReplicatedTable 1 }

ExampleMiscellaneousOperFreeLongReplicatedEntry ::= SEQUENCE {
   exampleMiscellaneousOperFreeLongReplicatedIndex
      Unsigned64,
   exampleMiscellaneousOperFreeLongReplicatedValue
      Unsigned64,
   exampleMiscellaneousOperFreeLongReplicatedRowStatus
      RowStatus }

exampleMiscellaneousOperFreeLongReplicatedIndex OBJECT-TYPE
   SYNTAX     Unsigned64 
   ACCESS     not-accessible
   STATUS     mandatory
   DESCRIPTION
     "This variable represents the index for the exampleMiscellaneousOperFreeLongReplicatedTable."
::= { exampleMiscellaneousOperFreeLongReplicatedEntry 1 }

exampleMiscellaneousOperFreeLongReplicatedValue OBJECT-TYPE
   SYNTAX     Unsigned64 (SIZE (8))
   ACCESS     read-write
   STATUS     mandatory
   DESCRIPTION
     "This variable represents an individual value for the
      exampleMiscellaneousOperFreeLongReplicatedTable."
::= { exampleMiscellaneousOperFreeLongReplicatedEntry 2 }

exampleMiscellaneousOperFreeLongReplicatedRowStatus OBJECT-TYPE
   SYNTAX     RowStatus 
   ACCESS     write-only
   STATUS     mandatory
   DESCRIPTION
     "This variable is used to control the addition and deletion 
      of individual values of the exampleMiscellaneousOperFreeLongReplicatedTable."
::= { exampleMiscellaneousOperFreeLongReplicatedEntry 3 }

exampleMiscellaneousOperFreeLongListTable OBJECT-TYPE
   SYNTAX     SEQUENCE OF ExampleMiscellaneousOperFreeLongListEntry
   ACCESS     not-accessible
   STATUS     mandatory
   DESCRIPTION
     ""
::= { exampleMiscellaneous 1178 }

exampleMiscellaneousOperFreeLongListEntry OBJECT-TYPE
   SYNTAX     ExampleMiscellaneousOperFreeLongListEntry
   ACCESS     not-accessible
   STATUS     mandatory
   DESCRIPTION
     "An entry in the exampleMiscellaneousOperFreeLongListTable."
   INDEX {
      exampleIndex,
      exampleMiscellaneousIndex,
      exampleMiscellaneousOperFreeLongListValue }
::= { exampleMiscellaneousOperFreeLongListTable 1 }

ExampleMiscellaneousOperFreeLongListEntry ::= SEQUENCE {
   exampleMiscellaneousOperFreeLongListValue
      Unsigned64,
   exampleMiscellaneousOperFreeLongListRowStatus
      RowStatus }

exampleMiscellaneousOperFreeLongListValue OBJECT-TYPE
   SYNTAX     Unsigned64 (SIZE (8))
   ACCESS     read-write
   STATUS     mandatory
   DESCRIPTION
     "This variable represents both the value and the index for the
      exampleMiscellaneousOperFreeLongListTable."
::= { exampleMiscellaneousOperFreeLongListEntry 1 }

exampleMiscellaneousOperFreeLongListRowStatus OBJECT-TYPE
   SYNTAX     RowStatus 
   ACCESS     write-only
   STATUS     mandatory
   DESCRIPTION
     "This variable is used to control the addition and deletion 
      of individual values of the exampleMiscellaneousOperFreeLongListTable."
::= { exampleMiscellaneousOperFreeLongListEntry 2 }

exampleMiscellaneousOperFreeTimeListTable OBJECT-TYPE
   SYNTAX     SEQUENCE OF ExampleMiscellaneousOperFreeTimeListEntry
   ACCESS     not-accessible
   STATUS     mandatory
   DESCRIPTION
     ""
::= { exampleMiscellaneous 1179 }

exampleMiscellaneousOperFreeTimeListEntry OBJECT-TYPE
   SYNTAX     ExampleMiscellaneousOperFreeTimeListEntry
   ACCESS     not-accessible
   STATUS     mandatory
   DESCRIPTION
     "An entry in the exampleMiscellaneousOperFreeTimeListTable."
   INDEX {
      exampleIndex,
      exampleMiscellaneousIndex,
      exampleMiscellaneousOperFreeTimeListValue }
::= { exampleMiscellaneousOperFreeTimeListTable 1 }

ExampleMiscellaneousOperFreeTimeListEntry ::= SEQUENCE {
   exampleMiscellaneousOperFreeTimeListValue
      EnterpriseDateAndTime,
   exampleMiscellaneousOperFreeTimeListRowStatus
      RowStatus }

exampleMiscellaneousOperFreeTimeListValue OBJECT-TYPE
   SYNTAX     EnterpriseDateAndTime (SIZE (16))
   ACCESS     read-write
   STATUS     mandatory
   DESCRIPTION
     "This variable represents both the value and the index for the
      exampleMiscellaneousOperFreeTimeListTable."
::= { exampleMiscellaneousOperFreeTimeListEntry 1 }

exampleMiscellaneousOperFreeTimeListRowStatus OBJECT-TYPE
   SYNTAX     RowStatus 
   ACCESS     write-only
   STATUS     mandatory
   DESCRIPTION
     "This variable is used to control the addition and deletion 
      of individual values of the exampleMiscellaneousOperFreeTimeListTable."
::= { exampleMiscellaneousOperFreeTimeListEntry 2 }

exampleMiscellaneousProvFreeLongReplicatedTable OBJECT-TYPE
   SYNTAX     SEQUENCE OF ExampleMiscellaneousProvFreeLongReplicatedEntry
   ACCESS     not-accessible
   STATUS     mandatory
   DESCRIPTION
     ""
::= { exampleMiscellaneous 1180 }

exampleMiscellaneousProvFreeLongReplicatedEntry OBJECT-TYPE
   SYNTAX     ExampleMiscellaneousProvFreeLongReplicatedEntry
   ACCESS     not-accessible
   STATUS     mandatory
   DESCRIPTION
     "An entry in the exampleMiscellaneousProvFreeLongReplicatedTable."
   INDEX {
      exampleIndex,
      exampleMiscellaneousIndex,
      exampleMiscellaneousProvFreeLongReplicatedIndex }
::= { exampleMiscellaneousProvFreeLongReplicatedTable 1 }

ExampleMiscellaneousProvFreeLongReplicatedEntry ::= SEQUENCE {
   exampleMiscellaneousProvFreeLongReplicatedIndex
      Unsigned64,
   exampleMiscellaneousProvFreeLongReplicatedValue
      Unsigned64,
   exampleMiscellaneousProvFreeLongReplicatedRowStatus
      RowStatus }

exampleMiscellaneousProvFreeLongReplicatedIndex OBJECT-TYPE
   SYNTAX     Unsigned64 
   ACCESS     not-accessible
   STATUS     mandatory
   DESCRIPTION
     "This variable represents the index for the exampleMiscellaneousProvFreeLongReplicatedTable."
::= { exampleMiscellaneousProvFreeLongReplicatedEntry 1 }

exampleMiscellaneousProvFreeLongReplicatedValue OBJECT-TYPE
   SYNTAX     Unsigned64 (SIZE (8))
   ACCESS     read-write
   STATUS     mandatory
   DESCRIPTION
     "This variable represents an individual value for the
      exampleMiscellaneousProvFreeLongReplicatedTable."
::= { exampleMiscellaneousProvFreeLongReplicatedEntry 2 }

exampleMiscellaneousProvFreeLongReplicatedRowStatus OBJECT-TYPE
   SYNTAX     RowStatus 
   ACCESS     write-only
   STATUS     mandatory
   DESCRIPTION
     "This variable is used to control the addition and deletion 
      of individual values of the exampleMiscellaneousProvFreeLongReplicatedTable."
::= { exampleMiscellaneousProvFreeLongReplicatedEntry 3 }

exampleMiscellaneousProvFreeLongListTable OBJECT-TYPE
   SYNTAX     SEQUENCE OF ExampleMiscellaneousProvFreeLongListEntry
   ACCESS     not-accessible
   STATUS     mandatory
   DESCRIPTION
     ""
::= { exampleMiscellaneous 1181 }

exampleMiscellaneousProvFreeLongListEntry OBJECT-TYPE
   SYNTAX     ExampleMiscellaneousProvFreeLongListEntry
   ACCESS     not-accessible
   STATUS     mandatory
   DESCRIPTION
     "An entry in the exampleMiscellaneousProvFreeLongListTable."
   INDEX {
      exampleIndex,
      exampleMiscellaneousIndex,
      exampleMiscellaneousProvFreeLongListValue }
::= { exampleMiscellaneousProvFreeLongListTable 1 }

ExampleMiscellaneousProvFreeLongListEntry ::= SEQUENCE {
   exampleMiscellaneousProvFreeLongListValue
      Unsigned64,
   exampleMiscellaneousProvFreeLongListRowStatus
      RowStatus }

exampleMiscellaneousProvFreeLongListValue OBJECT-TYPE
   SYNTAX     Unsigned64 (SIZE (8))
   ACCESS     read-write
   STATUS     mandatory
   DESCRIPTION
     "This variable represents both the value and the index for the
      exampleMiscellaneousProvFreeLongListTable."
::= { exampleMiscellaneousProvFreeLongListEntry 1 }

exampleMiscellaneousProvFreeLongListRowStatus OBJECT-TYPE
   SYNTAX     RowStatus 
   ACCESS     write-only
   STATUS     mandatory
   DESCRIPTION
     "This variable is used to control the addition and deletion 
      of individual values of the exampleMiscellaneousProvFreeLongListTable."
::= { exampleMiscellaneousProvFreeLongListEntry 2 }

exampleMiscellaneousProvFreeTimeReplicatedTable OBJECT-TYPE
   SYNTAX     SEQUENCE OF ExampleMiscellaneousProvFreeTimeReplicatedEntry
   ACCESS     not-accessible
   STATUS     mandatory
   DESCRIPTION
     ""
::= { exampleMiscellaneous 1182 }

exampleMiscellaneousProvFreeTimeReplicatedEntry OBJECT-TYPE
   SYNTAX     ExampleMiscellaneousProvFreeTimeReplicatedEntry
   ACCESS     not-accessible
   STATUS     mandatory
   DESCRIPTION
     "An entry in the exampleMiscellaneousProvFreeTimeReplicatedTable."
   INDEX {
      exampleIndex,
      exampleMiscellaneousIndex,
      exampleMiscellaneousProvFreeTimeReplicatedIndex }
::= { exampleMiscellaneousProvFreeTimeReplicatedTable 1 }

ExampleMiscellaneousProvFreeTimeReplicatedEntry ::= SEQUENCE {
   exampleMiscellaneousProvFreeTimeReplicatedIndex
      EnterpriseDateAndTime,
   exampleMiscellaneousProvFreeTimeReplicatedValue
      EnterpriseDateAndTime,
   exampleMiscellaneousProvFreeTimeReplicatedRowStatus
      RowStatus }

exampleMiscellaneousProvFreeTimeReplicatedIndex OBJECT-TYPE
   SYNTAX     EnterpriseDateAndTime (SIZE (10))
   ACCESS     not-accessible
   STATUS     mandatory
   DESCRIPTION
     "This variable represents the index for the exampleMiscellaneousProvFreeTimeReplicatedTable."
::= { exampleMiscellaneousProvFreeTimeReplicatedEntry 1 }

exampleMiscellaneousProvFreeTimeReplicatedValue OBJECT-TYPE
   SYNTAX     EnterpriseDateAndTime (SIZE (0 | 8))
   ACCESS     read-write
   STATUS     mandatory
   DESCRIPTION
     "This variable represents an individual value for the
      exampleMiscellaneousProvFreeTimeReplicatedTable."
::= { exampleMiscellaneousProvFreeTimeReplicatedEntry 2 }

exampleMiscellaneousProvFreeTimeReplicatedRowStatus OBJECT-TYPE
   SYNTAX     RowStatus 
   ACCESS     write-only
   STATUS     mandatory
   DESCRIPTION
     "This variable is used to control the addition and deletion 
      of individual values of the exampleMiscellaneousProvFreeTimeReplicatedTable."
::= { exampleMiscellaneousProvFreeTimeReplicatedEntry 3 }

exampleMiscellaneousProvFreeTimeListTable OBJECT-TYPE
   SYNTAX     SEQUENCE OF ExampleMiscellaneousProvFreeTimeListEntry
   ACCESS     not-accessible
   STATUS     mandatory
   DESCRIPTION
     ""
::= { exampleMiscellaneous 1183 }

exampleMiscellaneousProvFreeTimeListEntry OBJECT-TYPE
   SYNTAX     ExampleMiscellaneousProvFreeTimeListEntry
   ACCESS     not-accessible
   STATUS     mandatory
   DESCRIPTION
     "An entry in the exampleMiscellaneousProvFreeTimeListTable."
   INDEX {
      exampleIndex,
      exampleMiscellaneousIndex,
      exampleMiscellaneousProvFreeTimeListValue }
::= { exampleMiscellaneousProvFreeTimeListTable 1 }

ExampleMiscellaneousProvFreeTimeListEntry ::= SEQUENCE {
   exampleMiscellaneousProvFreeTimeListValue
      EnterpriseDateAndTime,
   exampleMiscellaneousProvFreeTimeListRowStatus
      RowStatus }

exampleMiscellaneousProvFreeTimeListValue OBJECT-TYPE
   SYNTAX     EnterpriseDateAndTime (SIZE (19))
   ACCESS     read-write
   STATUS     mandatory
   DESCRIPTION
     "This variable represents both the value and the index for the
      exampleMiscellaneousProvFreeTimeListTable."
::= { exampleMiscellaneousProvFreeTimeListEntry 1 }

exampleMiscellaneousProvFreeTimeListRowStatus OBJECT-TYPE
   SYNTAX     RowStatus 
   ACCESS     write-only
   STATUS     mandatory
   DESCRIPTION
     "This variable is used to control the addition and deletion 
      of individual values of the exampleMiscellaneousProvFreeTimeListTable."
::= { exampleMiscellaneousProvFreeTimeListEntry 2 }

exampleMiscellaneousProvFreeTimeList1Table OBJECT-TYPE
   SYNTAX     SEQUENCE OF ExampleMiscellaneousProvFreeTimeList1Entry
   ACCESS     not-accessible
   STATUS     mandatory
   DESCRIPTION
     ""
::= { exampleMiscellaneous 1184 }

exampleMiscellaneousProvFreeTimeList1Entry OBJECT-TYPE
   SYNTAX     ExampleMiscellaneousProvFreeTimeList1Entry
   ACCESS     not-accessible
   STATUS     mandatory
   DESCRIPTION
     "An entry in the exampleMiscellaneousProvFreeTimeList1Table."
   INDEX {
      exampleIndex,
      exampleMiscellaneousIndex,
      exampleMiscellaneousProvFreeTimeList1Value }
::= { exampleMiscellaneousProvFreeTimeList1Table 1 }

ExampleMiscellaneousProvFreeTimeList1Entry ::= SEQUENCE {
   exampleMiscellaneousProvFreeTimeList1Value
      EnterpriseDateAndTime,
   exampleMiscellaneousProvFreeTimeList1RowStatus
      RowStatus }

exampleMiscellaneousProvFreeTimeList1Value OBJECT-TYPE
   SYNTAX     EnterpriseDateAndTime (SIZE (10))
   ACCESS     read-write
   STATUS     mandatory
   DESCRIPTION
     "This variable represents both the value and the index for the
      exampleMiscellaneousProvFreeTimeList1Table."
::= { exampleMiscellaneousProvFreeTimeList1Entry 1 }

exampleMiscellaneousProvFreeTimeList1RowStatus OBJECT-TYPE
   SYNTAX     RowStatus 
   ACCESS     write-only
   STATUS     mandatory
   DESCRIPTION
     "This variable is used to control the addition and deletion 
      of individual values of the exampleMiscellaneousProvFreeTimeList1Table."
::= { exampleMiscellaneousProvFreeTimeList1Entry 2 }

exampleMiscellaneousProvFreeTimeList2Table OBJECT-TYPE
   SYNTAX     SEQUENCE OF ExampleMiscellaneousProvFreeTimeList2Entry
   ACCESS     not-accessible
   STATUS     mandatory
   DESCRIPTION
     ""
::= { exampleMiscellaneous 1185 }

exampleMiscellaneousProvFreeTimeList2Entry OBJECT-TYPE
   SYNTAX     ExampleMiscellaneousProvFreeTimeList2Entry
   ACCESS     not-accessible
   STATUS     mandatory
   DESCRIPTION
     "An entry in the exampleMiscellaneousProvFreeTimeList2Table."
   INDEX {
      exampleIndex,
      exampleMiscellaneousIndex,
      exampleMiscellaneousProvFreeTimeList2Value }
::= { exampleMiscellaneousProvFreeTimeList2Table 1 }

ExampleMiscellaneousProvFreeTimeList2Entry ::= SEQUENCE {
   exampleMiscellaneousProvFreeTimeList2Value
      EnterpriseDateAndTime,
   exampleMiscellaneousProvFreeTimeList2RowStatus
      RowStatus }

exampleMiscellaneousProvFreeTimeList2Value OBJECT-TYPE
   SYNTAX     EnterpriseDateAndTime (SIZE (8))
   ACCESS     read-write
   STATUS     mandatory
   DESCRIPTION
     "This variable represents both the value and the index for the
      exampleMiscellaneousProvFreeTimeList2Table."
::= { exampleMiscellaneousProvFreeTimeList2Entry 1 }

exampleMiscellaneousProvFreeTimeList2RowStatus OBJECT-TYPE
   SYNTAX     RowStatus 
   ACCESS     write-only
   STATUS     mandatory
   DESCRIPTION
     "This variable is used to control the addition and deletion 
      of individual values of the exampleMiscellaneousProvFreeTimeList2Table."
::= { exampleMiscellaneousProvFreeTimeList2Entry 2 }

exampleMiscellaneousProvFreeTimeList3Table OBJECT-TYPE
   SYNTAX     SEQUENCE OF ExampleMiscellaneousProvFreeTimeList3Entry
   ACCESS     not-accessible
   STATUS     mandatory
   DESCRIPTION
     ""
::= { exampleMiscellaneous 1186 }

exampleMiscellaneousProvFreeTimeList3Entry OBJECT-TYPE
   SYNTAX     ExampleMiscellaneousProvFreeTimeList3Entry
   ACCESS     not-accessible
   STATUS     mandatory
   DESCRIPTION
     "An entry in the exampleMiscellaneousProvFreeTimeList3Table."
   INDEX {
      exampleIndex,
      exampleMiscellaneousIndex,
      exampleMiscellaneousProvFreeTimeList3Value }
::= { exampleMiscellaneousProvFreeTimeList3Table 1 }

ExampleMiscellaneousProvFreeTimeList3Entry ::= SEQUENCE {
   exampleMiscellaneousProvFreeTimeList3Value
      EnterpriseDateAndTime,
   exampleMiscellaneousProvFreeTimeList3RowStatus
      RowStatus }

exampleMiscellaneousProvFreeTimeList3Value OBJECT-TYPE
   SYNTAX     EnterpriseDateAndTime (SIZE (16))
   ACCESS     read-write
   STATUS     mandatory
   DESCRIPTION
     "This variable represents both the value and the index for the
      exampleMiscellaneousProvFreeTimeList3Table."
::= { exampleMiscellaneousProvFreeTimeList3Entry 1 }

exampleMiscellaneousProvFreeTimeList3RowStatus OBJECT-TYPE
   SYNTAX     RowStatus 
   ACCESS     write-only
   STATUS     mandatory
   DESCRIPTION
     "This variable is used to control the addition and deletion 
      of individual values of the exampleMiscellaneousProvFreeTimeList3Table."
::= { exampleMiscellaneousProvFreeTimeList3Entry 2 }



exampleOneIndex OBJECT IDENTIFIER ::= { example 16 }



exampleOneIndexRowStatusTable OBJECT-TYPE
   SYNTAX     SEQUENCE OF ExampleOneIndexRowStatusEntry
   ACCESS     not-accessible
   STATUS     mandatory
   DESCRIPTION
     "This entry controls the addition and deletion of 
      exampleOneIndex components."
::= { exampleOneIndex 1 }

exampleOneIndexRowStatusEntry OBJECT-TYPE
   SYNTAX     ExampleOneIndexRowStatusEntry
   ACCESS     not-accessible
   STATUS     mandatory
   DESCRIPTION
     "A single entry in the table represents a single 
      exampleOneIndex component."
   INDEX {
      exampleIndex,
      exampleOneIndexOneIndex }
::= { exampleOneIndexRowStatusTable 1 }

ExampleOneIndexRowStatusEntry ::= SEQUENCE {
   exampleOneIndexRowStatus
      RowStatus,
   exampleOneIndexComponentName
      DisplayString,
   exampleOneIndexStorageType
      StorageType,
   exampleOneIndexOneIndex
      Integer32 }

exampleOneIndexRowStatus OBJECT-TYPE
   SYNTAX     RowStatus 
   ACCESS     read-write
   STATUS     mandatory
   DESCRIPTION
     "This variable is used as the basis for SNMP naming of
      exampleOneIndex components.
      These components can be added and deleted."
::= { exampleOneIndexRowStatusEntry 1 }

exampleOneIndexComponentName OBJECT-TYPE
   SYNTAX     DisplayString 
   ACCESS     read-only
   STATUS     mandatory
   DESCRIPTION
     "This variable provides the component's string name for
      use with the ASCII Console Interface"
::= { exampleOneIndexRowStatusEntry 2 }

exampleOneIndexStorageType OBJECT-TYPE
   SYNTAX     StorageType 
   ACCESS     read-only
   STATUS     mandatory
   DESCRIPTION
     "This variable represents the storage type value for the
      exampleOneIndex tables."
::= { exampleOneIndexRowStatusEntry 4 }

exampleOneIndexOneIndex OBJECT-TYPE
   SYNTAX     Integer32 (0..268435455)
   ACCESS     not-accessible
   STATUS     mandatory
   DESCRIPTION
     "This variable represents the index for the exampleOneIndex tables."
::= { exampleOneIndexRowStatusEntry 10 }

exampleOneIndexProvisionedTable OBJECT-TYPE
   SYNTAX     SEQUENCE OF ExampleOneIndexProvisionedEntry
   ACCESS     not-accessible
   STATUS     mandatory
   DESCRIPTION
     ""
::= { exampleOneIndex 10 }

exampleOneIndexProvisionedEntry OBJECT-TYPE
   SYNTAX     ExampleOneIndexProvisionedEntry
   ACCESS     not-accessible
   STATUS     mandatory
   DESCRIPTION
     "An entry in the exampleOneIndexProvisionedTable."
   INDEX {
      exampleIndex,
      exampleOneIndexOneIndex }
::= { exampleOneIndexProvisionedTable 1 }

ExampleOneIndexProvisionedEntry ::= SEQUENCE {
   exampleOneIndexProvAttribute
      Unsigned32 }

exampleOneIndexProvAttribute OBJECT-TYPE
   SYNTAX     Unsigned32 (0..255)
   ACCESS     read-write
   STATUS     mandatory
   DESCRIPTION
     ""
   DEFVAL     { 1 }
::= { exampleOneIndexProvisionedEntry 1 }



exampleTwoIndices OBJECT IDENTIFIER ::= { example 17 }



exampleTwoIndicesRowStatusTable OBJECT-TYPE
   SYNTAX     SEQUENCE OF ExampleTwoIndicesRowStatusEntry
   ACCESS     not-accessible
   STATUS     mandatory
   DESCRIPTION
     "This entry controls the addition and deletion of 
      exampleTwoIndices components."
::= { exampleTwoIndices 1 }

exampleTwoIndicesRowStatusEntry OBJECT-TYPE
   SYNTAX     ExampleTwoIndicesRowStatusEntry
   ACCESS     not-accessible
   STATUS     mandatory
   DESCRIPTION
     "A single entry in the table represents a single 
      exampleTwoIndices component."
   INDEX {
      exampleIndex,
      exampleTwoIndicesOneIndex,
      exampleTwoIndicesTwoIndex }
::= { exampleTwoIndicesRowStatusTable 1 }

ExampleTwoIndicesRowStatusEntry ::= SEQUENCE {
   exampleTwoIndicesRowStatus
      RowStatus,
   exampleTwoIndicesComponentName
      DisplayString,
   exampleTwoIndicesStorageType
      StorageType,
   exampleTwoIndicesOneIndex
      Integer32,
   exampleTwoIndicesTwoIndex
      Integer32 }

exampleTwoIndicesRowStatus OBJECT-TYPE
   SYNTAX     RowStatus 
   ACCESS     read-write
   STATUS     mandatory
   DESCRIPTION
     "This variable is used as the basis for SNMP naming of
      exampleTwoIndices components.
      These components can be added and deleted."
::= { exampleTwoIndicesRowStatusEntry 1 }

exampleTwoIndicesComponentName OBJECT-TYPE
   SYNTAX     DisplayString 
   ACCESS     read-only
   STATUS     mandatory
   DESCRIPTION
     "This variable provides the component's string name for
      use with the ASCII Console Interface"
::= { exampleTwoIndicesRowStatusEntry 2 }

exampleTwoIndicesStorageType OBJECT-TYPE
   SYNTAX     StorageType 
   ACCESS     read-only
   STATUS     mandatory
   DESCRIPTION
     "This variable represents the storage type value for the
      exampleTwoIndices tables."
::= { exampleTwoIndicesRowStatusEntry 4 }

exampleTwoIndicesOneIndex OBJECT-TYPE
   SYNTAX     Integer32 (0..268435455)
   ACCESS     not-accessible
   STATUS     mandatory
   DESCRIPTION
     "This variable represents an index for the exampleTwoIndices tables."
::= { exampleTwoIndicesRowStatusEntry 10 }

exampleTwoIndicesTwoIndex OBJECT-TYPE
   SYNTAX     Integer32 (0..268435455)
   ACCESS     not-accessible
   STATUS     mandatory
   DESCRIPTION
     "This variable represents an index for the exampleTwoIndices tables."
::= { exampleTwoIndicesRowStatusEntry 11 }

exampleTwoIndicesProvisionedTable OBJECT-TYPE
   SYNTAX     SEQUENCE OF ExampleTwoIndicesProvisionedEntry
   ACCESS     not-accessible
   STATUS     mandatory
   DESCRIPTION
     ""
::= { exampleTwoIndices 10 }

exampleTwoIndicesProvisionedEntry OBJECT-TYPE
   SYNTAX     ExampleTwoIndicesProvisionedEntry
   ACCESS     not-accessible
   STATUS     mandatory
   DESCRIPTION
     "An entry in the exampleTwoIndicesProvisionedTable."
   INDEX {
      exampleIndex,
      exampleTwoIndicesOneIndex,
      exampleTwoIndicesTwoIndex }
::= { exampleTwoIndicesProvisionedTable 1 }

ExampleTwoIndicesProvisionedEntry ::= SEQUENCE {
   exampleTwoIndicesProvAttribute
      Unsigned32 }

exampleTwoIndicesProvAttribute OBJECT-TYPE
   SYNTAX     Unsigned32 (0..255)
   ACCESS     read-write
   STATUS     mandatory
   DESCRIPTION
     ""
   DEFVAL     { 1 }
::= { exampleTwoIndicesProvisionedEntry 1 }



exampleThreeIndices OBJECT IDENTIFIER ::= { example 18 }



exampleThreeIndicesRowStatusTable OBJECT-TYPE
   SYNTAX     SEQUENCE OF ExampleThreeIndicesRowStatusEntry
   ACCESS     not-accessible
   STATUS     mandatory
   DESCRIPTION
     "This entry controls the addition and deletion of 
      exampleThreeIndices components."
::= { exampleThreeIndices 1 }

exampleThreeIndicesRowStatusEntry OBJECT-TYPE
   SYNTAX     ExampleThreeIndicesRowStatusEntry
   ACCESS     not-accessible
   STATUS     mandatory
   DESCRIPTION
     "A single entry in the table represents a single 
      exampleThreeIndices component."
   INDEX {
      exampleIndex,
      exampleThreeIndicesOneIndex,
      exampleThreeIndicesTwoIndex,
      exampleThreeIndicesThreeIndex }
::= { exampleThreeIndicesRowStatusTable 1 }

ExampleThreeIndicesRowStatusEntry ::= SEQUENCE {
   exampleThreeIndicesRowStatus
      RowStatus,
   exampleThreeIndicesComponentName
      DisplayString,
   exampleThreeIndicesStorageType
      StorageType,
   exampleThreeIndicesOneIndex
      Integer32,
   exampleThreeIndicesTwoIndex
      Integer32,
   exampleThreeIndicesThreeIndex
      Integer32 }

exampleThreeIndicesRowStatus OBJECT-TYPE
   SYNTAX     RowStatus 
   ACCESS     read-write
   STATUS     mandatory
   DESCRIPTION
     "This variable is used as the basis for SNMP naming of
      exampleThreeIndices components.
      These components can be added and deleted."
::= { exampleThreeIndicesRowStatusEntry 1 }

exampleThreeIndicesComponentName OBJECT-TYPE
   SYNTAX     DisplayString 
   ACCESS     read-only
   STATUS     mandatory
   DESCRIPTION
     "This variable provides the component's string name for
      use with the ASCII Console Interface"
::= { exampleThreeIndicesRowStatusEntry 2 }

exampleThreeIndicesStorageType OBJECT-TYPE
   SYNTAX     StorageType 
   ACCESS     read-only
   STATUS     mandatory
   DESCRIPTION
     "This variable represents the storage type value for the
      exampleThreeIndices tables."
::= { exampleThreeIndicesRowStatusEntry 4 }

exampleThreeIndicesOneIndex OBJECT-TYPE
   SYNTAX     Integer32 (0..268435455)
   ACCESS     not-accessible
   STATUS     mandatory
   DESCRIPTION
     "This variable represents an index for the exampleThreeIndices tables."
::= { exampleThreeIndicesRowStatusEntry 10 }

exampleThreeIndicesTwoIndex OBJECT-TYPE
   SYNTAX     Integer32 (0..268435455)
   ACCESS     not-accessible
   STATUS     mandatory
   DESCRIPTION
     "This variable represents an index for the exampleThreeIndices tables."
::= { exampleThreeIndicesRowStatusEntry 11 }

exampleThreeIndicesThreeIndex OBJECT-TYPE
   SYNTAX     Integer32 (0..268435455)
   ACCESS     not-accessible
   STATUS     mandatory
   DESCRIPTION
     "This variable represents an index for the exampleThreeIndices tables."
::= { exampleThreeIndicesRowStatusEntry 12 }

exampleThreeIndicesProvisionedTable OBJECT-TYPE
   SYNTAX     SEQUENCE OF ExampleThreeIndicesProvisionedEntry
   ACCESS     not-accessible
   STATUS     mandatory
   DESCRIPTION
     ""
::= { exampleThreeIndices 10 }

exampleThreeIndicesProvisionedEntry OBJECT-TYPE
   SYNTAX     ExampleThreeIndicesProvisionedEntry
   ACCESS     not-accessible
   STATUS     mandatory
   DESCRIPTION
     "An entry in the exampleThreeIndicesProvisionedTable."
   INDEX {
      exampleIndex,
      exampleThreeIndicesOneIndex,
      exampleThreeIndicesTwoIndex,
      exampleThreeIndicesThreeIndex }
::= { exampleThreeIndicesProvisionedTable 1 }

ExampleThreeIndicesProvisionedEntry ::= SEQUENCE {
   exampleThreeIndicesProvAttribute
      Unsigned32 }

exampleThreeIndicesProvAttribute OBJECT-TYPE
   SYNTAX     Unsigned32 (0..255)
   ACCESS     read-write
   STATUS     mandatory
   DESCRIPTION
     ""
   DEFVAL     { 1 }
::= { exampleThreeIndicesProvisionedEntry 1 }



exampleFourIndices OBJECT IDENTIFIER ::= { example 19 }



exampleFourIndicesRowStatusTable OBJECT-TYPE
   SYNTAX     SEQUENCE OF ExampleFourIndicesRowStatusEntry
   ACCESS     not-accessible
   STATUS     mandatory
   DESCRIPTION
     "This entry controls the addition and deletion of 
      exampleFourIndices components."
::= { exampleFourIndices 1 }

exampleFourIndicesRowStatusEntry OBJECT-TYPE
   SYNTAX     ExampleFourIndicesRowStatusEntry
   ACCESS     not-accessible
   STATUS     mandatory
   DESCRIPTION
     "A single entry in the table represents a single 
      exampleFourIndices component."
   INDEX {
      exampleIndex,
      exampleFourIndicesOneIndex,
      exampleFourIndicesTwoIndex,
      exampleFourIndicesThreeIndex,
      exampleFourIndicesFourIndex }
::= { exampleFourIndicesRowStatusTable 1 }

ExampleFourIndicesRowStatusEntry ::= SEQUENCE {
   exampleFourIndicesRowStatus
      RowStatus,
   exampleFourIndicesComponentName
      DisplayString,
   exampleFourIndicesStorageType
      StorageType,
   exampleFourIndicesOneIndex
      Integer32,
   exampleFourIndicesTwoIndex
      Integer32,
   exampleFourIndicesThreeIndex
      Integer32,
   exampleFourIndicesFourIndex
      Integer32 }

exampleFourIndicesRowStatus OBJECT-TYPE
   SYNTAX     RowStatus 
   ACCESS     read-write
   STATUS     mandatory
   DESCRIPTION
     "This variable is used as the basis for SNMP naming of
      exampleFourIndices components.
      These components can be added and deleted."
::= { exampleFourIndicesRowStatusEntry 1 }

exampleFourIndicesComponentName OBJECT-TYPE
   SYNTAX     DisplayString 
   ACCESS     read-only
   STATUS     mandatory
   DESCRIPTION
     "This variable provides the component's string name for
      use with the ASCII Console Interface"
::= { exampleFourIndicesRowStatusEntry 2 }

exampleFourIndicesStorageType OBJECT-TYPE
   SYNTAX     StorageType 
   ACCESS     read-only
   STATUS     mandatory
   DESCRIPTION
     "This variable represents the storage type value for the
      exampleFourIndices tables."
::= { exampleFourIndicesRowStatusEntry 4 }

exampleFourIndicesOneIndex OBJECT-TYPE
   SYNTAX     Integer32 (0..268435455)
   ACCESS     not-accessible
   STATUS     mandatory
   DESCRIPTION
     "This variable represents an index for the exampleFourIndices tables."
::= { exampleFourIndicesRowStatusEntry 10 }

exampleFourIndicesTwoIndex OBJECT-TYPE
   SYNTAX     Integer32 (0..268435455)
   ACCESS     not-accessible
   STATUS     mandatory
   DESCRIPTION
     "This variable represents an index for the exampleFourIndices tables."
::= { exampleFourIndicesRowStatusEntry 11 }

exampleFourIndicesThreeIndex OBJECT-TYPE
   SYNTAX     Integer32 (0..268435455)
   ACCESS     not-accessible
   STATUS     mandatory
   DESCRIPTION
     "This variable represents an index for the exampleFourIndices tables."
::= { exampleFourIndicesRowStatusEntry 12 }

exampleFourIndicesFourIndex OBJECT-TYPE
   SYNTAX     Integer32 (0..268435455)
   ACCESS     not-accessible
   STATUS     mandatory
   DESCRIPTION
     "This variable represents an index for the exampleFourIndices tables."
::= { exampleFourIndicesRowStatusEntry 13 }

exampleFourIndicesProvisionedTable OBJECT-TYPE
   SYNTAX     SEQUENCE OF ExampleFourIndicesProvisionedEntry
   ACCESS     not-accessible
   STATUS     mandatory
   DESCRIPTION
     ""
::= { exampleFourIndices 10 }

exampleFourIndicesProvisionedEntry OBJECT-TYPE
   SYNTAX     ExampleFourIndicesProvisionedEntry
   ACCESS     not-accessible
   STATUS     mandatory
   DESCRIPTION
     "An entry in the exampleFourIndicesProvisionedTable."
   INDEX {
      exampleIndex,
      exampleFourIndicesOneIndex,
      exampleFourIndicesTwoIndex,
      exampleFourIndicesThreeIndex,
      exampleFourIndicesFourIndex }
::= { exampleFourIndicesProvisionedTable 1 }

ExampleFourIndicesProvisionedEntry ::= SEQUENCE {
   exampleFourIndicesProvAttribute
      Unsigned32 }

exampleFourIndicesProvAttribute OBJECT-TYPE
   SYNTAX     Unsigned32 (0..255)
   ACCESS     read-write
   STATUS     mandatory
   DESCRIPTION
     ""
   DEFVAL     { 1 }
::= { exampleFourIndicesProvisionedEntry 1 }



exampleDecimalIndices OBJECT IDENTIFIER ::= { example 20 }



exampleDecimalIndicesRowStatusTable OBJECT-TYPE
   SYNTAX     SEQUENCE OF ExampleDecimalIndicesRowStatusEntry
   ACCESS     not-accessible
   STATUS     mandatory
   DESCRIPTION
     "This entry controls the addition and deletion of 
      exampleDecimalIndices components."
::= { exampleDecimalIndices 1 }

exampleDecimalIndicesRowStatusEntry OBJECT-TYPE
   SYNTAX     ExampleDecimalIndicesRowStatusEntry
   ACCESS     not-accessible
   STATUS     mandatory
   DESCRIPTION
     "A single entry in the table represents a single 
      exampleDecimalIndices component."
   INDEX {
      exampleIndex,
      exampleDecimalIndicesOneIndex,
      exampleDecimalIndicesTwoIndex,
      exampleDecimalIndicesThreeIndex }
::= { exampleDecimalIndicesRowStatusTable 1 }

ExampleDecimalIndicesRowStatusEntry ::= SEQUENCE {
   exampleDecimalIndicesRowStatus
      RowStatus,
   exampleDecimalIndicesComponentName
      DisplayString,
   exampleDecimalIndicesStorageType
      StorageType,
   exampleDecimalIndicesOneIndex
      Integer32,
   exampleDecimalIndicesTwoIndex
      Integer32,
   exampleDecimalIndicesThreeIndex
      Integer32 }

exampleDecimalIndicesRowStatus OBJECT-TYPE
   SYNTAX     RowStatus 
   ACCESS     read-write
   STATUS     mandatory
   DESCRIPTION
     "This variable is used as the basis for SNMP naming of
      exampleDecimalIndices components.
      These components can be added and deleted."
::= { exampleDecimalIndicesRowStatusEntry 1 }

exampleDecimalIndicesComponentName OBJECT-TYPE
   SYNTAX     DisplayString 
   ACCESS     read-only
   STATUS     mandatory
   DESCRIPTION
     "This variable provides the component's string name for
      use with the ASCII Console Interface"
::= { exampleDecimalIndicesRowStatusEntry 2 }

exampleDecimalIndicesStorageType OBJECT-TYPE
   SYNTAX     StorageType 
   ACCESS     read-only
   STATUS     mandatory
   DESCRIPTION
     "This variable represents the storage type value for the
      exampleDecimalIndices tables."
::= { exampleDecimalIndicesRowStatusEntry 4 }

exampleDecimalIndicesOneIndex OBJECT-TYPE
   SYNTAX     Integer32 (1..10 | 100)
   ACCESS     not-accessible
   STATUS     mandatory
   DESCRIPTION
     "This variable represents an index for the exampleDecimalIndices tables."
::= { exampleDecimalIndicesRowStatusEntry 10 }

exampleDecimalIndicesTwoIndex OBJECT-TYPE
   SYNTAX     Integer32 (1..10 | 100)
   ACCESS     not-accessible
   STATUS     mandatory
   DESCRIPTION
     "This variable represents an index for the exampleDecimalIndices tables."
::= { exampleDecimalIndicesRowStatusEntry 11 }

exampleDecimalIndicesThreeIndex OBJECT-TYPE
   SYNTAX     Integer32 (1..10 | 100)
   ACCESS     not-accessible
   STATUS     mandatory
   DESCRIPTION
     "This variable represents an index for the exampleDecimalIndices tables."
::= { exampleDecimalIndicesRowStatusEntry 12 }

exampleDecimalIndicesProvisionedTable OBJECT-TYPE
   SYNTAX     SEQUENCE OF ExampleDecimalIndicesProvisionedEntry
   ACCESS     not-accessible
   STATUS     mandatory
   DESCRIPTION
     ""
::= { exampleDecimalIndices 10 }

exampleDecimalIndicesProvisionedEntry OBJECT-TYPE
   SYNTAX     ExampleDecimalIndicesProvisionedEntry
   ACCESS     not-accessible
   STATUS     mandatory
   DESCRIPTION
     "An entry in the exampleDecimalIndicesProvisionedTable."
   INDEX {
      exampleIndex,
      exampleDecimalIndicesOneIndex,
      exampleDecimalIndicesTwoIndex,
      exampleDecimalIndicesThreeIndex }
::= { exampleDecimalIndicesProvisionedTable 1 }

ExampleDecimalIndicesProvisionedEntry ::= SEQUENCE {
   exampleDecimalIndicesProvAttribute
      Unsigned32 }

exampleDecimalIndicesProvAttribute OBJECT-TYPE
   SYNTAX     Unsigned32 (0..255)
   ACCESS     read-write
   STATUS     mandatory
   DESCRIPTION
     ""
   DEFVAL     { 1 }
::= { exampleDecimalIndicesProvisionedEntry 1 }



exampleHexIndices OBJECT IDENTIFIER ::= { example 21 }



exampleHexIndicesRowStatusTable OBJECT-TYPE
   SYNTAX     SEQUENCE OF ExampleHexIndicesRowStatusEntry
   ACCESS     not-accessible
   STATUS     mandatory
   DESCRIPTION
     "This entry controls the addition and deletion of 
      exampleHexIndices components."
::= { exampleHexIndices 1 }

exampleHexIndicesRowStatusEntry OBJECT-TYPE
   SYNTAX     ExampleHexIndicesRowStatusEntry
   ACCESS     not-accessible
   STATUS     mandatory
   DESCRIPTION
     "A single entry in the table represents a single 
      exampleHexIndices component."
   INDEX {
      exampleIndex,
      exampleHexIndicesOneIndex,
      exampleHexIndicesTwoIndex,
      exampleHexIndicesThreeIndex }
::= { exampleHexIndicesRowStatusTable 1 }

ExampleHexIndicesRowStatusEntry ::= SEQUENCE {
   exampleHexIndicesRowStatus
      RowStatus,
   exampleHexIndicesComponentName
      DisplayString,
   exampleHexIndicesStorageType
      StorageType,
   exampleHexIndicesOneIndex
      Integer32,
   exampleHexIndicesTwoIndex
      Integer32,
   exampleHexIndicesThreeIndex
      Integer32 }

exampleHexIndicesRowStatus OBJECT-TYPE
   SYNTAX     RowStatus 
   ACCESS     read-write
   STATUS     mandatory
   DESCRIPTION
     "This variable is used as the basis for SNMP naming of
      exampleHexIndices components.
      These components can be added and deleted."
::= { exampleHexIndicesRowStatusEntry 1 }

exampleHexIndicesComponentName OBJECT-TYPE
   SYNTAX     DisplayString 
   ACCESS     read-only
   STATUS     mandatory
   DESCRIPTION
     "This variable provides the component's string name for
      use with the ASCII Console Interface"
::= { exampleHexIndicesRowStatusEntry 2 }

exampleHexIndicesStorageType OBJECT-TYPE
   SYNTAX     StorageType 
   ACCESS     read-only
   STATUS     mandatory
   DESCRIPTION
     "This variable represents the storage type value for the
      exampleHexIndices tables."
::= { exampleHexIndicesRowStatusEntry 4 }

exampleHexIndicesOneIndex OBJECT-TYPE
   SYNTAX     Integer32 (1..16 | 256)
   ACCESS     not-accessible
   STATUS     mandatory
   DESCRIPTION
     "This variable represents an index for the exampleHexIndices tables."
::= { exampleHexIndicesRowStatusEntry 10 }

exampleHexIndicesTwoIndex OBJECT-TYPE
   SYNTAX     Integer32 (1..16 | 256)
   ACCESS     not-accessible
   STATUS     mandatory
   DESCRIPTION
     "This variable represents an index for the exampleHexIndices tables."
::= { exampleHexIndicesRowStatusEntry 11 }

exampleHexIndicesThreeIndex OBJECT-TYPE
   SYNTAX     Integer32 (1..16 | 256)
   ACCESS     not-accessible
   STATUS     mandatory
   DESCRIPTION
     "This variable represents an index for the exampleHexIndices tables."
::= { exampleHexIndicesRowStatusEntry 12 }

exampleHexIndicesProvisionedTable OBJECT-TYPE
   SYNTAX     SEQUENCE OF ExampleHexIndicesProvisionedEntry
   ACCESS     not-accessible
   STATUS     mandatory
   DESCRIPTION
     ""
::= { exampleHexIndices 10 }

exampleHexIndicesProvisionedEntry OBJECT-TYPE
   SYNTAX     ExampleHexIndicesProvisionedEntry
   ACCESS     not-accessible
   STATUS     mandatory
   DESCRIPTION
     "An entry in the exampleHexIndicesProvisionedTable."
   INDEX {
      exampleIndex,
      exampleHexIndicesOneIndex,
      exampleHexIndicesTwoIndex,
      exampleHexIndicesThreeIndex }
::= { exampleHexIndicesProvisionedTable 1 }

ExampleHexIndicesProvisionedEntry ::= SEQUENCE {
   exampleHexIndicesProvAttribute
      Unsigned32 }

exampleHexIndicesProvAttribute OBJECT-TYPE
   SYNTAX     Unsigned32 (0..255)
   ACCESS     read-write
   STATUS     mandatory
   DESCRIPTION
     ""
   DEFVAL     { 1 }
::= { exampleHexIndicesProvisionedEntry 1 }



exampleIpAddrIndices OBJECT IDENTIFIER ::= { example 22 }



exampleIpAddrIndicesRowStatusTable OBJECT-TYPE
   SYNTAX     SEQUENCE OF ExampleIpAddrIndicesRowStatusEntry
   ACCESS     not-accessible
   STATUS     mandatory
   DESCRIPTION
     "This entry controls the addition and deletion of 
      exampleIpAddrIndices components."
::= { exampleIpAddrIndices 1 }

exampleIpAddrIndicesRowStatusEntry OBJECT-TYPE
   SYNTAX     ExampleIpAddrIndicesRowStatusEntry
   ACCESS     not-accessible
   STATUS     mandatory
   DESCRIPTION
     "A single entry in the table represents a single 
      exampleIpAddrIndices component."
   INDEX {
      exampleIndex,
      exampleIpAddrIndicesOneIndex,
      exampleIpAddrIndicesTwoIndex,
      exampleIpAddrIndicesThreeIndex }
::= { exampleIpAddrIndicesRowStatusTable 1 }

ExampleIpAddrIndicesRowStatusEntry ::= SEQUENCE {
   exampleIpAddrIndicesRowStatus
      RowStatus,
   exampleIpAddrIndicesComponentName
      DisplayString,
   exampleIpAddrIndicesStorageType
      StorageType,
   exampleIpAddrIndicesOneIndex
      IpAddress,
   exampleIpAddrIndicesTwoIndex
      IpAddress,
   exampleIpAddrIndicesThreeIndex
      IpAddress }

exampleIpAddrIndicesRowStatus OBJECT-TYPE
   SYNTAX     RowStatus 
   ACCESS     read-write
   STATUS     mandatory
   DESCRIPTION
     "This variable is used as the basis for SNMP naming of
      exampleIpAddrIndices components.
      These components can be added and deleted."
::= { exampleIpAddrIndicesRowStatusEntry 1 }

exampleIpAddrIndicesComponentName OBJECT-TYPE
   SYNTAX     DisplayString 
   ACCESS     read-only
   STATUS     mandatory
   DESCRIPTION
     "This variable provides the component's string name for
      use with the ASCII Console Interface"
::= { exampleIpAddrIndicesRowStatusEntry 2 }

exampleIpAddrIndicesStorageType OBJECT-TYPE
   SYNTAX     StorageType 
   ACCESS     read-only
   STATUS     mandatory
   DESCRIPTION
     "This variable represents the storage type value for the
      exampleIpAddrIndices tables."
::= { exampleIpAddrIndicesRowStatusEntry 4 }

exampleIpAddrIndicesOneIndex OBJECT-TYPE
   SYNTAX     IpAddress 
   ACCESS     not-accessible
   STATUS     mandatory
   DESCRIPTION
     "This variable represents an index for the exampleIpAddrIndices tables."
::= { exampleIpAddrIndicesRowStatusEntry 10 }

exampleIpAddrIndicesTwoIndex OBJECT-TYPE
   SYNTAX     IpAddress 
   ACCESS     not-accessible
   STATUS     mandatory
   DESCRIPTION
     "This variable represents an index for the exampleIpAddrIndices tables."
::= { exampleIpAddrIndicesRowStatusEntry 11 }

exampleIpAddrIndicesThreeIndex OBJECT-TYPE
   SYNTAX     IpAddress 
   ACCESS     not-accessible
   STATUS     mandatory
   DESCRIPTION
     "This variable represents an index for the exampleIpAddrIndices tables."
::= { exampleIpAddrIndicesRowStatusEntry 12 }

exampleIpAddrIndicesProvisionedTable OBJECT-TYPE
   SYNTAX     SEQUENCE OF ExampleIpAddrIndicesProvisionedEntry
   ACCESS     not-accessible
   STATUS     mandatory
   DESCRIPTION
     ""
::= { exampleIpAddrIndices 10 }

exampleIpAddrIndicesProvisionedEntry OBJECT-TYPE
   SYNTAX     ExampleIpAddrIndicesProvisionedEntry
   ACCESS     not-accessible
   STATUS     mandatory
   DESCRIPTION
     "An entry in the exampleIpAddrIndicesProvisionedTable."
   INDEX {
      exampleIndex,
      exampleIpAddrIndicesOneIndex,
      exampleIpAddrIndicesTwoIndex,
      exampleIpAddrIndicesThreeIndex }
::= { exampleIpAddrIndicesProvisionedTable 1 }

ExampleIpAddrIndicesProvisionedEntry ::= SEQUENCE {
   exampleIpAddrIndicesProvAttribute
      Unsigned32 }

exampleIpAddrIndicesProvAttribute OBJECT-TYPE
   SYNTAX     Unsigned32 (0..255)
   ACCESS     read-write
   STATUS     mandatory
   DESCRIPTION
     ""
   DEFVAL     { 1 }
::= { exampleIpAddrIndicesProvisionedEntry 1 }



exampleAsciiIndices OBJECT IDENTIFIER ::= { example 23 }



exampleAsciiIndicesRowStatusTable OBJECT-TYPE
   SYNTAX     SEQUENCE OF ExampleAsciiIndicesRowStatusEntry
   ACCESS     not-accessible
   STATUS     mandatory
   DESCRIPTION
     "This entry controls the addition and deletion of 
      exampleAsciiIndices components."
::= { exampleAsciiIndices 1 }

exampleAsciiIndicesRowStatusEntry OBJECT-TYPE
   SYNTAX     ExampleAsciiIndicesRowStatusEntry
   ACCESS     not-accessible
   STATUS     mandatory
   DESCRIPTION
     "A single entry in the table represents a single 
      exampleAsciiIndices component."
   INDEX {
      exampleIndex,
      exampleAsciiIndicesOneIndex,
      exampleAsciiIndicesTwoIndex,
      exampleAsciiIndicesThreeIndex }
::= { exampleAsciiIndicesRowStatusTable 1 }

ExampleAsciiIndicesRowStatusEntry ::= SEQUENCE {
   exampleAsciiIndicesRowStatus
      RowStatus,
   exampleAsciiIndicesComponentName
      DisplayString,
   exampleAsciiIndicesStorageType
      StorageType,
   exampleAsciiIndicesOneIndex
      AsciiStringIndex,
   exampleAsciiIndicesTwoIndex
      AsciiStringIndex,
   exampleAsciiIndicesThreeIndex
      AsciiStringIndex }

exampleAsciiIndicesRowStatus OBJECT-TYPE
   SYNTAX     RowStatus 
   ACCESS     read-write
   STATUS     mandatory
   DESCRIPTION
     "This variable is used as the basis for SNMP naming of
      exampleAsciiIndices components.
      These components can be added and deleted."
::= { exampleAsciiIndicesRowStatusEntry 1 }

exampleAsciiIndicesComponentName OBJECT-TYPE
   SYNTAX     DisplayString 
   ACCESS     read-only
   STATUS     mandatory
   DESCRIPTION
     "This variable provides the component's string name for
      use with the ASCII Console Interface"
::= { exampleAsciiIndicesRowStatusEntry 2 }

exampleAsciiIndicesStorageType OBJECT-TYPE
   SYNTAX     StorageType 
   ACCESS     read-only
   STATUS     mandatory
   DESCRIPTION
     "This variable represents the storage type value for the
      exampleAsciiIndices tables."
::= { exampleAsciiIndicesRowStatusEntry 4 }

exampleAsciiIndicesOneIndex OBJECT-TYPE
   SYNTAX     AsciiStringIndex (SIZE (1..10))
   ACCESS     not-accessible
   STATUS     mandatory
   DESCRIPTION
     "This variable represents an index for the exampleAsciiIndices tables."
::= { exampleAsciiIndicesRowStatusEntry 10 }

exampleAsciiIndicesTwoIndex OBJECT-TYPE
   SYNTAX     AsciiStringIndex (SIZE (1..10))
   ACCESS     not-accessible
   STATUS     mandatory
   DESCRIPTION
     "This variable represents an index for the exampleAsciiIndices tables."
::= { exampleAsciiIndicesRowStatusEntry 11 }

exampleAsciiIndicesThreeIndex OBJECT-TYPE
   SYNTAX     AsciiStringIndex (SIZE (1..10))
   ACCESS     not-accessible
   STATUS     mandatory
   DESCRIPTION
     "This variable represents an index for the exampleAsciiIndices tables."
::= { exampleAsciiIndicesRowStatusEntry 12 }

exampleAsciiIndicesProvisionedTable OBJECT-TYPE
   SYNTAX     SEQUENCE OF ExampleAsciiIndicesProvisionedEntry
   ACCESS     not-accessible
   STATUS     mandatory
   DESCRIPTION
     ""
::= { exampleAsciiIndices 10 }

exampleAsciiIndicesProvisionedEntry OBJECT-TYPE
   SYNTAX     ExampleAsciiIndicesProvisionedEntry
   ACCESS     not-accessible
   STATUS     mandatory
   DESCRIPTION
     "An entry in the exampleAsciiIndicesProvisionedTable."
   INDEX {
      exampleIndex,
      exampleAsciiIndicesOneIndex,
      exampleAsciiIndicesTwoIndex,
      exampleAsciiIndicesThreeIndex }
::= { exampleAsciiIndicesProvisionedTable 1 }

ExampleAsciiIndicesProvisionedEntry ::= SEQUENCE {
   exampleAsciiIndicesProvAttribute
      Unsigned32 }

exampleAsciiIndicesProvAttribute OBJECT-TYPE
   SYNTAX     Unsigned32 (0..255)
   ACCESS     read-write
   STATUS     mandatory
   DESCRIPTION
     ""
   DEFVAL     { 1 }
::= { exampleAsciiIndicesProvisionedEntry 1 }



exampleHexStrIndices OBJECT IDENTIFIER ::= { example 24 }



exampleHexStrIndicesRowStatusTable OBJECT-TYPE
   SYNTAX     SEQUENCE OF ExampleHexStrIndicesRowStatusEntry
   ACCESS     not-accessible
   STATUS     mandatory
   DESCRIPTION
     "This entry controls the addition and deletion of 
      exampleHexStrIndices components."
::= { exampleHexStrIndices 1 }

exampleHexStrIndicesRowStatusEntry OBJECT-TYPE
   SYNTAX     ExampleHexStrIndicesRowStatusEntry
   ACCESS     not-accessible
   STATUS     mandatory
   DESCRIPTION
     "A single entry in the table represents a single 
      exampleHexStrIndices component."
   INDEX {
      exampleIndex,
      exampleHexStrIndicesOneIndex,
      exampleHexStrIndicesTwoIndex,
      exampleHexStrIndicesThreeIndex }
::= { exampleHexStrIndicesRowStatusTable 1 }

ExampleHexStrIndicesRowStatusEntry ::= SEQUENCE {
   exampleHexStrIndicesRowStatus
      RowStatus,
   exampleHexStrIndicesComponentName
      DisplayString,
   exampleHexStrIndicesStorageType
      StorageType,
   exampleHexStrIndicesOneIndex
      HexString,
   exampleHexStrIndicesTwoIndex
      HexString,
   exampleHexStrIndicesThreeIndex
      HexString }

exampleHexStrIndicesRowStatus OBJECT-TYPE
   SYNTAX     RowStatus 
   ACCESS     read-write
   STATUS     mandatory
   DESCRIPTION
     "This variable is used as the basis for SNMP naming of
      exampleHexStrIndices components.
      These components can be added and deleted."
::= { exampleHexStrIndicesRowStatusEntry 1 }

exampleHexStrIndicesComponentName OBJECT-TYPE
   SYNTAX     DisplayString 
   ACCESS     read-only
   STATUS     mandatory
   DESCRIPTION
     "This variable provides the component's string name for
      use with the ASCII Console Interface"
::= { exampleHexStrIndicesRowStatusEntry 2 }

exampleHexStrIndicesStorageType OBJECT-TYPE
   SYNTAX     StorageType 
   ACCESS     read-only
   STATUS     mandatory
   DESCRIPTION
     "This variable represents the storage type value for the
      exampleHexStrIndices tables."
::= { exampleHexStrIndicesRowStatusEntry 4 }

exampleHexStrIndicesOneIndex OBJECT-TYPE
   SYNTAX     HexString (SIZE (1..10))
   ACCESS     not-accessible
   STATUS     mandatory
   DESCRIPTION
     "This variable represents an index for the exampleHexStrIndices tables."
::= { exampleHexStrIndicesRowStatusEntry 10 }

exampleHexStrIndicesTwoIndex OBJECT-TYPE
   SYNTAX     HexString (SIZE (1..10))
   ACCESS     not-accessible
   STATUS     mandatory
   DESCRIPTION
     "This variable represents an index for the exampleHexStrIndices tables."
::= { exampleHexStrIndicesRowStatusEntry 11 }

exampleHexStrIndicesThreeIndex OBJECT-TYPE
   SYNTAX     HexString (SIZE (1..10))
   ACCESS     not-accessible
   STATUS     mandatory
   DESCRIPTION
     "This variable represents an index for the exampleHexStrIndices tables."
::= { exampleHexStrIndicesRowStatusEntry 12 }

exampleHexStrIndicesProvisionedTable OBJECT-TYPE
   SYNTAX     SEQUENCE OF ExampleHexStrIndicesProvisionedEntry
   ACCESS     not-accessible
   STATUS     mandatory
   DESCRIPTION
     ""
::= { exampleHexStrIndices 10 }

exampleHexStrIndicesProvisionedEntry OBJECT-TYPE
   SYNTAX     ExampleHexStrIndicesProvisionedEntry
   ACCESS     not-accessible
   STATUS     mandatory
   DESCRIPTION
     "An entry in the exampleHexStrIndicesProvisionedTable."
   INDEX {
      exampleIndex,
      exampleHexStrIndicesOneIndex,
      exampleHexStrIndicesTwoIndex,
      exampleHexStrIndicesThreeIndex }
::= { exampleHexStrIndicesProvisionedTable 1 }

ExampleHexStrIndicesProvisionedEntry ::= SEQUENCE {
   exampleHexStrIndicesProvAttribute
      Unsigned32 }

exampleHexStrIndicesProvAttribute OBJECT-TYPE
   SYNTAX     Unsigned32 (0..255)
   ACCESS     read-write
   STATUS     mandatory
   DESCRIPTION
     ""
   DEFVAL     { 1 }
::= { exampleHexStrIndicesProvisionedEntry 1 }



exampleBcdIndices OBJECT IDENTIFIER ::= { example 25 }



exampleBcdIndicesRowStatusTable OBJECT-TYPE
   SYNTAX     SEQUENCE OF ExampleBcdIndicesRowStatusEntry
   ACCESS     not-accessible
   STATUS     mandatory
   DESCRIPTION
     "This entry controls the addition and deletion of 
      exampleBcdIndices components."
::= { exampleBcdIndices 1 }

exampleBcdIndicesRowStatusEntry OBJECT-TYPE
   SYNTAX     ExampleBcdIndicesRowStatusEntry
   ACCESS     not-accessible
   STATUS     mandatory
   DESCRIPTION
     "A single entry in the table represents a single 
      exampleBcdIndices component."
   INDEX {
      exampleIndex,
      exampleBcdIndicesOneIndex,
      exampleBcdIndicesTwoIndex,
      exampleBcdIndicesThreeIndex }
::= { exampleBcdIndicesRowStatusTable 1 }

ExampleBcdIndicesRowStatusEntry ::= SEQUENCE {
   exampleBcdIndicesRowStatus
      RowStatus,
   exampleBcdIndicesComponentName
      DisplayString,
   exampleBcdIndicesStorageType
      StorageType,
   exampleBcdIndicesOneIndex
      DigitString,
   exampleBcdIndicesTwoIndex
      DigitString,
   exampleBcdIndicesThreeIndex
      DigitString }

exampleBcdIndicesRowStatus OBJECT-TYPE
   SYNTAX     RowStatus 
   ACCESS     read-write
   STATUS     mandatory
   DESCRIPTION
     "This variable is used as the basis for SNMP naming of
      exampleBcdIndices components.
      These components can be added and deleted."
::= { exampleBcdIndicesRowStatusEntry 1 }

exampleBcdIndicesComponentName OBJECT-TYPE
   SYNTAX     DisplayString 
   ACCESS     read-only
   STATUS     mandatory
   DESCRIPTION
     "This variable provides the component's string name for
      use with the ASCII Console Interface"
::= { exampleBcdIndicesRowStatusEntry 2 }

exampleBcdIndicesStorageType OBJECT-TYPE
   SYNTAX     StorageType 
   ACCESS     read-only
   STATUS     mandatory
   DESCRIPTION
     "This variable represents the storage type value for the
      exampleBcdIndices tables."
::= { exampleBcdIndicesRowStatusEntry 4 }

exampleBcdIndicesOneIndex OBJECT-TYPE
   SYNTAX     DigitString (SIZE (1..10))
   ACCESS     not-accessible
   STATUS     mandatory
   DESCRIPTION
     "This variable represents an index for the exampleBcdIndices tables."
::= { exampleBcdIndicesRowStatusEntry 10 }

exampleBcdIndicesTwoIndex OBJECT-TYPE
   SYNTAX     DigitString (SIZE (1..10))
   ACCESS     not-accessible
   STATUS     mandatory
   DESCRIPTION
     "This variable represents an index for the exampleBcdIndices tables."
::= { exampleBcdIndicesRowStatusEntry 11 }

exampleBcdIndicesThreeIndex OBJECT-TYPE
   SYNTAX     DigitString (SIZE (1..10))
   ACCESS     not-accessible
   STATUS     mandatory
   DESCRIPTION
     "This variable represents an index for the exampleBcdIndices tables."
::= { exampleBcdIndicesRowStatusEntry 12 }

exampleBcdIndicesProvisionedTable OBJECT-TYPE
   SYNTAX     SEQUENCE OF ExampleBcdIndicesProvisionedEntry
   ACCESS     not-accessible
   STATUS     mandatory
   DESCRIPTION
     ""
::= { exampleBcdIndices 10 }

exampleBcdIndicesProvisionedEntry OBJECT-TYPE
   SYNTAX     ExampleBcdIndicesProvisionedEntry
   ACCESS     not-accessible
   STATUS     mandatory
   DESCRIPTION
     "An entry in the exampleBcdIndicesProvisionedTable."
   INDEX {
      exampleIndex,
      exampleBcdIndicesOneIndex,
      exampleBcdIndicesTwoIndex,
      exampleBcdIndicesThreeIndex }
::= { exampleBcdIndicesProvisionedTable 1 }

ExampleBcdIndicesProvisionedEntry ::= SEQUENCE {
   exampleBcdIndicesProvAttribute
      Unsigned32 }

exampleBcdIndicesProvAttribute OBJECT-TYPE
   SYNTAX     Unsigned32 (0..255)
   ACCESS     read-write
   STATUS     mandatory
   DESCRIPTION
     ""
   DEFVAL     { 1 }
::= { exampleBcdIndicesProvisionedEntry 1 }



exampleEnumIndices OBJECT IDENTIFIER ::= { example 26 }



exampleEnumIndicesRowStatusTable OBJECT-TYPE
   SYNTAX     SEQUENCE OF ExampleEnumIndicesRowStatusEntry
   ACCESS     not-accessible
   STATUS     mandatory
   DESCRIPTION
     "This entry controls the addition and deletion of 
      exampleEnumIndices components."
::= { exampleEnumIndices 1 }

exampleEnumIndicesRowStatusEntry OBJECT-TYPE
   SYNTAX     ExampleEnumIndicesRowStatusEntry
   ACCESS     not-accessible
   STATUS     mandatory
   DESCRIPTION
     "A single entry in the table represents a single 
      exampleEnumIndices component."
   INDEX {
      exampleIndex,
      exampleEnumIndicesOneIndex,
      exampleEnumIndicesTwoIndex,
      exampleEnumIndicesThreeIndex }
::= { exampleEnumIndicesRowStatusTable 1 }

ExampleEnumIndicesRowStatusEntry ::= SEQUENCE {
   exampleEnumIndicesRowStatus
      RowStatus,
   exampleEnumIndicesComponentName
      DisplayString,
   exampleEnumIndicesStorageType
      StorageType,
   exampleEnumIndicesOneIndex
      INTEGER,
   exampleEnumIndicesTwoIndex
      INTEGER,
   exampleEnumIndicesThreeIndex
      INTEGER }

exampleEnumIndicesRowStatus OBJECT-TYPE
   SYNTAX     RowStatus 
   ACCESS     read-write
   STATUS     mandatory
   DESCRIPTION
     "This variable is used as the basis for SNMP naming of
      exampleEnumIndices components.
      These components can be added and deleted."
::= { exampleEnumIndicesRowStatusEntry 1 }

exampleEnumIndicesComponentName OBJECT-TYPE
   SYNTAX     DisplayString 
   ACCESS     read-only
   STATUS     mandatory
   DESCRIPTION
     "This variable provides the component's string name for
      use with the ASCII Console Interface"
::= { exampleEnumIndicesRowStatusEntry 2 }

exampleEnumIndicesStorageType OBJECT-TYPE
   SYNTAX     StorageType 
   ACCESS     read-only
   STATUS     mandatory
   DESCRIPTION
     "This variable represents the storage type value for the
      exampleEnumIndices tables."
::= { exampleEnumIndicesRowStatusEntry 4 }

exampleEnumIndicesOneIndex OBJECT-TYPE
   SYNTAX     INTEGER  {
                 first(1),
                 second(2),
                 third(3) }
   ACCESS     not-accessible
   STATUS     mandatory
   DESCRIPTION
     "This variable represents an index for the exampleEnumIndices tables."
::= { exampleEnumIndicesRowStatusEntry 10 }

exampleEnumIndicesTwoIndex OBJECT-TYPE
   SYNTAX     INTEGER  {
                 first(1),
                 second(2),
                 third(3) }
   ACCESS     not-accessible
   STATUS     mandatory
   DESCRIPTION
     "This variable represents an index for the exampleEnumIndices tables."
::= { exampleEnumIndicesRowStatusEntry 11 }

exampleEnumIndicesThreeIndex OBJECT-TYPE
   SYNTAX     INTEGER  {
                 first(1),
                 second(2),
                 third(3) }
   ACCESS     not-accessible
   STATUS     mandatory
   DESCRIPTION
     "This variable represents an index for the exampleEnumIndices tables."
::= { exampleEnumIndicesRowStatusEntry 12 }

exampleEnumIndicesProvisionedTable OBJECT-TYPE
   SYNTAX     SEQUENCE OF ExampleEnumIndicesProvisionedEntry
   ACCESS     not-accessible
   STATUS     mandatory
   DESCRIPTION
     ""
::= { exampleEnumIndices 10 }

exampleEnumIndicesProvisionedEntry OBJECT-TYPE
   SYNTAX     ExampleEnumIndicesProvisionedEntry
   ACCESS     not-accessible
   STATUS     mandatory
   DESCRIPTION
     "An entry in the exampleEnumIndicesProvisionedTable."
   INDEX {
      exampleIndex,
      exampleEnumIndicesOneIndex,
      exampleEnumIndicesTwoIndex,
      exampleEnumIndicesThreeIndex }
::= { exampleEnumIndicesProvisionedTable 1 }

ExampleEnumIndicesProvisionedEntry ::= SEQUENCE {
   exampleEnumIndicesProvAttribute
      Unsigned32 }

exampleEnumIndicesProvAttribute OBJECT-TYPE
   SYNTAX     Unsigned32 (0..255)
   ACCESS     read-write
   STATUS     mandatory
   DESCRIPTION
     ""
   DEFVAL     { 1 }
::= { exampleEnumIndicesProvisionedEntry 1 }



exampleSequenceIndices OBJECT IDENTIFIER ::= { example 27 }



exampleSequenceIndicesRowStatusTable OBJECT-TYPE
   SYNTAX     SEQUENCE OF ExampleSequenceIndicesRowStatusEntry
   ACCESS     not-accessible
   STATUS     mandatory
   DESCRIPTION
     "This entry controls the addition and deletion of 
      exampleSequenceIndices components."
::= { exampleSequenceIndices 1 }

exampleSequenceIndicesRowStatusEntry OBJECT-TYPE
   SYNTAX     ExampleSequenceIndicesRowStatusEntry
   ACCESS     not-accessible
   STATUS     mandatory
   DESCRIPTION
     "A single entry in the table represents a single 
      exampleSequenceIndices component."
   INDEX {
      exampleIndex,
      exampleSequenceIndicesOneIndex,
      exampleSequenceIndicesTwoIndex,
      exampleSequenceIndicesThreeIndex }
::= { exampleSequenceIndicesRowStatusTable 1 }

ExampleSequenceIndicesRowStatusEntry ::= SEQUENCE {
   exampleSequenceIndicesRowStatus
      RowStatus,
   exampleSequenceIndicesComponentName
      DisplayString,
   exampleSequenceIndicesStorageType
      StorageType,
   exampleSequenceIndicesOneIndex
      OBJECT IDENTIFIER,
   exampleSequenceIndicesTwoIndex
      OBJECT IDENTIFIER,
   exampleSequenceIndicesThreeIndex
      OBJECT IDENTIFIER }

exampleSequenceIndicesRowStatus OBJECT-TYPE
   SYNTAX     RowStatus 
   ACCESS     read-write
   STATUS     mandatory
   DESCRIPTION
     "This variable is used as the basis for SNMP naming of
      exampleSequenceIndices components.
      These components can be added and deleted."
::= { exampleSequenceIndicesRowStatusEntry 1 }

exampleSequenceIndicesComponentName OBJECT-TYPE
   SYNTAX     DisplayString 
   ACCESS     read-only
   STATUS     mandatory
   DESCRIPTION
     "This variable provides the component's string name for
      use with the ASCII Console Interface"
::= { exampleSequenceIndicesRowStatusEntry 2 }

exampleSequenceIndicesStorageType OBJECT-TYPE
   SYNTAX     StorageType 
   ACCESS     read-only
   STATUS     mandatory
   DESCRIPTION
     "This variable represents the storage type value for the
      exampleSequenceIndices tables."
::= { exampleSequenceIndicesRowStatusEntry 4 }

exampleSequenceIndicesOneIndex OBJECT-TYPE
   SYNTAX     OBJECT IDENTIFIER 
   ACCESS     not-accessible
   STATUS     mandatory
   DESCRIPTION
     "This variable represents an index for the exampleSequenceIndices tables."
::= { exampleSequenceIndicesRowStatusEntry 10 }

exampleSequenceIndicesTwoIndex OBJECT-TYPE
   SYNTAX     OBJECT IDENTIFIER 
   ACCESS     not-accessible
   STATUS     mandatory
   DESCRIPTION
     "This variable represents an index for the exampleSequenceIndices tables."
::= { exampleSequenceIndicesRowStatusEntry 11 }

exampleSequenceIndicesThreeIndex OBJECT-TYPE
   SYNTAX     OBJECT IDENTIFIER 
   ACCESS     not-accessible
   STATUS     mandatory
   DESCRIPTION
     "This variable represents an index for the exampleSequenceIndices tables."
::= { exampleSequenceIndicesRowStatusEntry 12 }

exampleSequenceIndicesProvisionedTable OBJECT-TYPE
   SYNTAX     SEQUENCE OF ExampleSequenceIndicesProvisionedEntry
   ACCESS     not-accessible
   STATUS     mandatory
   DESCRIPTION
     ""
::= { exampleSequenceIndices 10 }

exampleSequenceIndicesProvisionedEntry OBJECT-TYPE
   SYNTAX     ExampleSequenceIndicesProvisionedEntry
   ACCESS     not-accessible
   STATUS     mandatory
   DESCRIPTION
     "An entry in the exampleSequenceIndicesProvisionedTable."
   INDEX {
      exampleIndex,
      exampleSequenceIndicesOneIndex,
      exampleSequenceIndicesTwoIndex,
      exampleSequenceIndicesThreeIndex }
::= { exampleSequenceIndicesProvisionedTable 1 }

ExampleSequenceIndicesProvisionedEntry ::= SEQUENCE {
   exampleSequenceIndicesProvAttribute
      Unsigned32 }

exampleSequenceIndicesProvAttribute OBJECT-TYPE
   SYNTAX     Unsigned32 (0..255)
   ACCESS     read-write
   STATUS     mandatory
   DESCRIPTION
     ""
   DEFVAL     { 1 }
::= { exampleSequenceIndicesProvisionedEntry 1 }



exampleObjIdIndices OBJECT IDENTIFIER ::= { example 28 }



exampleObjIdIndicesRowStatusTable OBJECT-TYPE
   SYNTAX     SEQUENCE OF ExampleObjIdIndicesRowStatusEntry
   ACCESS     not-accessible
   STATUS     mandatory
   DESCRIPTION
     "This entry controls the addition and deletion of 
      exampleObjIdIndices components."
::= { exampleObjIdIndices 1 }

exampleObjIdIndicesRowStatusEntry OBJECT-TYPE
   SYNTAX     ExampleObjIdIndicesRowStatusEntry
   ACCESS     not-accessible
   STATUS     mandatory
   DESCRIPTION
     "A single entry in the table represents a single 
      exampleObjIdIndices component."
   INDEX {
      exampleIndex,
      exampleObjIdIndicesOneIndex,
      exampleObjIdIndicesTwoIndex,
      exampleObjIdIndicesThreeIndex }
::= { exampleObjIdIndicesRowStatusTable 1 }

ExampleObjIdIndicesRowStatusEntry ::= SEQUENCE {
   exampleObjIdIndicesRowStatus
      RowStatus,
   exampleObjIdIndicesComponentName
      DisplayString,
   exampleObjIdIndicesStorageType
      StorageType,
   exampleObjIdIndicesOneIndex
      OBJECT IDENTIFIER,
   exampleObjIdIndicesTwoIndex
      OBJECT IDENTIFIER,
   exampleObjIdIndicesThreeIndex
      OBJECT IDENTIFIER }

exampleObjIdIndicesRowStatus OBJECT-TYPE
   SYNTAX     RowStatus 
   ACCESS     read-write
   STATUS     mandatory
   DESCRIPTION
     "This variable is used as the basis for SNMP naming of
      exampleObjIdIndices components.
      These components can be added and deleted."
::= { exampleObjIdIndicesRowStatusEntry 1 }

exampleObjIdIndicesComponentName OBJECT-TYPE
   SYNTAX     DisplayString 
   ACCESS     read-only
   STATUS     mandatory
   DESCRIPTION
     "This variable provides the component's string name for
      use with the ASCII Console Interface"
::= { exampleObjIdIndicesRowStatusEntry 2 }

exampleObjIdIndicesStorageType OBJECT-TYPE
   SYNTAX     StorageType 
   ACCESS     read-only
   STATUS     mandatory
   DESCRIPTION
     "This variable represents the storage type value for the
      exampleObjIdIndices tables."
::= { exampleObjIdIndicesRowStatusEntry 4 }

exampleObjIdIndicesOneIndex OBJECT-TYPE
   SYNTAX     OBJECT IDENTIFIER 
   ACCESS     not-accessible
   STATUS     mandatory
   DESCRIPTION
     "This variable represents an index for the exampleObjIdIndices tables."
::= { exampleObjIdIndicesRowStatusEntry 10 }

exampleObjIdIndicesTwoIndex OBJECT-TYPE
   SYNTAX     OBJECT IDENTIFIER 
   ACCESS     not-accessible
   STATUS     mandatory
   DESCRIPTION
     "This variable represents an index for the exampleObjIdIndices tables."
::= { exampleObjIdIndicesRowStatusEntry 11 }

exampleObjIdIndicesThreeIndex OBJECT-TYPE
   SYNTAX     OBJECT IDENTIFIER 
   ACCESS     not-accessible
   STATUS     mandatory
   DESCRIPTION
     "This variable represents an index for the exampleObjIdIndices tables."
::= { exampleObjIdIndicesRowStatusEntry 12 }

exampleObjIdIndicesProvisionedTable OBJECT-TYPE
   SYNTAX     SEQUENCE OF ExampleObjIdIndicesProvisionedEntry
   ACCESS     not-accessible
   STATUS     mandatory
   DESCRIPTION
     ""
::= { exampleObjIdIndices 10 }

exampleObjIdIndicesProvisionedEntry OBJECT-TYPE
   SYNTAX     ExampleObjIdIndicesProvisionedEntry
   ACCESS     not-accessible
   STATUS     mandatory
   DESCRIPTION
     "An entry in the exampleObjIdIndicesProvisionedTable."
   INDEX {
      exampleIndex,
      exampleObjIdIndicesOneIndex,
      exampleObjIdIndicesTwoIndex,
      exampleObjIdIndicesThreeIndex }
::= { exampleObjIdIndicesProvisionedTable 1 }

ExampleObjIdIndicesProvisionedEntry ::= SEQUENCE {
   exampleObjIdIndicesProvAttribute
      Unsigned32 }

exampleObjIdIndicesProvAttribute OBJECT-TYPE
   SYNTAX     Unsigned32 (0..255)
   ACCESS     read-write
   STATUS     mandatory
   DESCRIPTION
     ""
   DEFVAL     { 1 }
::= { exampleObjIdIndicesProvisionedEntry 1 }



exampleDashedIndices OBJECT IDENTIFIER ::= { example 30 }



exampleDashedIndicesRowStatusTable OBJECT-TYPE
   SYNTAX     SEQUENCE OF ExampleDashedIndicesRowStatusEntry
   ACCESS     not-accessible
   STATUS     mandatory
   DESCRIPTION
     "This entry controls the addition and deletion of 
      exampleDashedIndices components."
::= { exampleDashedIndices 1 }

exampleDashedIndicesRowStatusEntry OBJECT-TYPE
   SYNTAX     ExampleDashedIndicesRowStatusEntry
   ACCESS     not-accessible
   STATUS     mandatory
   DESCRIPTION
     "A single entry in the table represents a single 
      exampleDashedIndices component."
   INDEX {
      exampleIndex,
      exampleDashedIndicesOneIndex,
      exampleDashedIndicesTwoIndex,
      exampleDashedIndicesThreeIndex }
::= { exampleDashedIndicesRowStatusTable 1 }

ExampleDashedIndicesRowStatusEntry ::= SEQUENCE {
   exampleDashedIndicesRowStatus
      RowStatus,
   exampleDashedIndicesComponentName
      DisplayString,
   exampleDashedIndicesStorageType
      StorageType,
   exampleDashedIndicesOneIndex
      DashedHexString,
   exampleDashedIndicesTwoIndex
      DashedHexString,
   exampleDashedIndicesThreeIndex
      DashedHexString }

exampleDashedIndicesRowStatus OBJECT-TYPE
   SYNTAX     RowStatus 
   ACCESS     read-write
   STATUS     mandatory
   DESCRIPTION
     "This variable is used as the basis for SNMP naming of
      exampleDashedIndices components.
      These components can be added and deleted."
::= { exampleDashedIndicesRowStatusEntry 1 }

exampleDashedIndicesComponentName OBJECT-TYPE
   SYNTAX     DisplayString 
   ACCESS     read-only
   STATUS     mandatory
   DESCRIPTION
     "This variable provides the component's string name for
      use with the ASCII Console Interface"
::= { exampleDashedIndicesRowStatusEntry 2 }

exampleDashedIndicesStorageType OBJECT-TYPE
   SYNTAX     StorageType 
   ACCESS     read-only
   STATUS     mandatory
   DESCRIPTION
     "This variable represents the storage type value for the
      exampleDashedIndices tables."
::= { exampleDashedIndicesRowStatusEntry 4 }

exampleDashedIndicesOneIndex OBJECT-TYPE
   SYNTAX     DashedHexString (SIZE (1..10))
   ACCESS     not-accessible
   STATUS     mandatory
   DESCRIPTION
     "This variable represents an index for the exampleDashedIndices tables."
::= { exampleDashedIndicesRowStatusEntry 10 }

exampleDashedIndicesTwoIndex OBJECT-TYPE
   SYNTAX     DashedHexString (SIZE (1..10))
   ACCESS     not-accessible
   STATUS     mandatory
   DESCRIPTION
     "This variable represents an index for the exampleDashedIndices tables."
::= { exampleDashedIndicesRowStatusEntry 11 }

exampleDashedIndicesThreeIndex OBJECT-TYPE
   SYNTAX     DashedHexString (SIZE (1..10))
   ACCESS     not-accessible
   STATUS     mandatory
   DESCRIPTION
     "This variable represents an index for the exampleDashedIndices tables."
::= { exampleDashedIndicesRowStatusEntry 12 }

exampleDashedIndicesProvisionedTable OBJECT-TYPE
   SYNTAX     SEQUENCE OF ExampleDashedIndicesProvisionedEntry
   ACCESS     not-accessible
   STATUS     mandatory
   DESCRIPTION
     ""
::= { exampleDashedIndices 10 }

exampleDashedIndicesProvisionedEntry OBJECT-TYPE
   SYNTAX     ExampleDashedIndicesProvisionedEntry
   ACCESS     not-accessible
   STATUS     mandatory
   DESCRIPTION
     "An entry in the exampleDashedIndicesProvisionedTable."
   INDEX {
      exampleIndex,
      exampleDashedIndicesOneIndex,
      exampleDashedIndicesTwoIndex,
      exampleDashedIndicesThreeIndex }
::= { exampleDashedIndicesProvisionedTable 1 }

ExampleDashedIndicesProvisionedEntry ::= SEQUENCE {
   exampleDashedIndicesProvAttribute
      Unsigned32 }

exampleDashedIndicesProvAttribute OBJECT-TYPE
   SYNTAX     Unsigned32 (0..255)
   ACCESS     read-write
   STATUS     mandatory
   DESCRIPTION
     ""
   DEFVAL     { 1 }
::= { exampleDashedIndicesProvisionedEntry 1 }



exampleRequiredIndices OBJECT IDENTIFIER ::= { example 31 }



exampleRequiredIndicesRowStatusTable OBJECT-TYPE
   SYNTAX     SEQUENCE OF ExampleRequiredIndicesRowStatusEntry
   ACCESS     not-accessible
   STATUS     mandatory
   DESCRIPTION
     "This entry controls the addition and deletion of 
      exampleRequiredIndices components."
::= { exampleRequiredIndices 1 }

exampleRequiredIndicesRowStatusEntry OBJECT-TYPE
   SYNTAX     ExampleRequiredIndicesRowStatusEntry
   ACCESS     not-accessible
   STATUS     mandatory
   DESCRIPTION
     "A single entry in the table represents a single 
      exampleRequiredIndices component."
   INDEX {
      exampleIndex,
      exampleRequiredIndicesDecimalIndex,
      exampleRequiredIndicesEnumerationIndex }
::= { exampleRequiredIndicesRowStatusTable 1 }

ExampleRequiredIndicesRowStatusEntry ::= SEQUENCE {
   exampleRequiredIndicesRowStatus
      RowStatus,
   exampleRequiredIndicesComponentName
      DisplayString,
   exampleRequiredIndicesStorageType
      StorageType,
   exampleRequiredIndicesDecimalIndex
      Integer32,
   exampleRequiredIndicesEnumerationIndex
      INTEGER }

exampleRequiredIndicesRowStatus OBJECT-TYPE
   SYNTAX     RowStatus 
   ACCESS     read-write
   STATUS     mandatory
   DESCRIPTION
     "This variable is used as the basis for SNMP naming of
      exampleRequiredIndices components.
      These components can be added and deleted."
::= { exampleRequiredIndicesRowStatusEntry 1 }

exampleRequiredIndicesComponentName OBJECT-TYPE
   SYNTAX     DisplayString 
   ACCESS     read-only
   STATUS     mandatory
   DESCRIPTION
     "This variable provides the component's string name for
      use with the ASCII Console Interface"
::= { exampleRequiredIndicesRowStatusEntry 2 }

exampleRequiredIndicesStorageType OBJECT-TYPE
   SYNTAX     StorageType 
   ACCESS     read-only
   STATUS     mandatory
   DESCRIPTION
     "This variable represents the storage type value for the
      exampleRequiredIndices tables."
::= { exampleRequiredIndicesRowStatusEntry 4 }

exampleRequiredIndicesDecimalIndex OBJECT-TYPE
   SYNTAX     Integer32 (0..268435455)
   ACCESS     not-accessible
   STATUS     mandatory
   DESCRIPTION
     "This variable represents an index for the exampleRequiredIndices tables."
::= { exampleRequiredIndicesRowStatusEntry 10 }

exampleRequiredIndicesEnumerationIndex OBJECT-TYPE
   SYNTAX     INTEGER  {
                 first(1),
                 second(2),
                 third(3) }
   ACCESS     not-accessible
   STATUS     mandatory
   DESCRIPTION
     "This variable represents an index for the exampleRequiredIndices tables."
::= { exampleRequiredIndicesRowStatusEntry 11 }

exampleRequiredIndicesProvisionedTable OBJECT-TYPE
   SYNTAX     SEQUENCE OF ExampleRequiredIndicesProvisionedEntry
   ACCESS     not-accessible
   STATUS     mandatory
   DESCRIPTION
     ""
::= { exampleRequiredIndices 10 }

exampleRequiredIndicesProvisionedEntry OBJECT-TYPE
   SYNTAX     ExampleRequiredIndicesProvisionedEntry
   ACCESS     not-accessible
   STATUS     mandatory
   DESCRIPTION
     "An entry in the exampleRequiredIndicesProvisionedTable."
   INDEX {
      exampleIndex,
      exampleRequiredIndicesDecimalIndex,
      exampleRequiredIndicesEnumerationIndex }
::= { exampleRequiredIndicesProvisionedTable 1 }

ExampleRequiredIndicesProvisionedEntry ::= SEQUENCE {
   exampleRequiredIndicesProvAttribute
      Unsigned32 }

exampleRequiredIndicesProvAttribute OBJECT-TYPE
   SYNTAX     Unsigned32 (0..255)
   ACCESS     read-write
   STATUS     mandatory
   DESCRIPTION
     ""
   DEFVAL     { 1 }
::= { exampleRequiredIndicesProvisionedEntry 1 }



exampleNsap OBJECT IDENTIFIER ::= { example 32 }



exampleNsapRowStatusTable OBJECT-TYPE
   SYNTAX     SEQUENCE OF ExampleNsapRowStatusEntry
   ACCESS     not-accessible
   STATUS     mandatory
   DESCRIPTION
     "This entry controls the addition and deletion of 
      exampleNsap components."
::= { exampleNsap 1 }

exampleNsapRowStatusEntry OBJECT-TYPE
   SYNTAX     ExampleNsapRowStatusEntry
   ACCESS     not-accessible
   STATUS     mandatory
   DESCRIPTION
     "A single entry in the table represents a single 
      exampleNsap component."
   INDEX {
      exampleIndex,
      exampleNsapIndex }
::= { exampleNsapRowStatusTable 1 }

ExampleNsapRowStatusEntry ::= SEQUENCE {
   exampleNsapRowStatus
      RowStatus,
   exampleNsapComponentName
      DisplayString,
   exampleNsapStorageType
      StorageType,
   exampleNsapIndex
      AsciiStringIndex }

exampleNsapRowStatus OBJECT-TYPE
   SYNTAX     RowStatus 
   ACCESS     read-write
   STATUS     mandatory
   DESCRIPTION
     "This variable is used as the basis for SNMP naming of
      exampleNsap components.
      These components can be added and deleted."
::= { exampleNsapRowStatusEntry 1 }

exampleNsapComponentName OBJECT-TYPE
   SYNTAX     DisplayString 
   ACCESS     read-only
   STATUS     mandatory
   DESCRIPTION
     "This variable provides the component's string name for
      use with the ASCII Console Interface"
::= { exampleNsapRowStatusEntry 2 }

exampleNsapStorageType OBJECT-TYPE
   SYNTAX     StorageType 
   ACCESS     read-only
   STATUS     mandatory
   DESCRIPTION
     "This variable represents the storage type value for the
      exampleNsap tables."
::= { exampleNsapRowStatusEntry 4 }

exampleNsapIndex OBJECT-TYPE
   SYNTAX     AsciiStringIndex (SIZE (0..44))
   ACCESS     not-accessible
   STATUS     mandatory
   DESCRIPTION
     "This variable represents the index for the exampleNsap tables."
::= { exampleNsapRowStatusEntry 10 }

exampleNsapAtmAddrTable OBJECT-TYPE
   SYNTAX     SEQUENCE OF ExampleNsapAtmAddrEntry
   ACCESS     not-accessible
   STATUS     mandatory
   DESCRIPTION
     ""
::= { exampleNsap 102 }

exampleNsapAtmAddrEntry OBJECT-TYPE
   SYNTAX     ExampleNsapAtmAddrEntry
   ACCESS     not-accessible
   STATUS     mandatory
   DESCRIPTION
     "An entry in the exampleNsapAtmAddrTable."
   INDEX {
      exampleIndex,
      exampleNsapIndex }
::= { exampleNsapAtmAddrTable 1 }

ExampleNsapAtmAddrEntry ::= SEQUENCE {
   exampleNsapNsapNativeAddress
      AsciiString }

exampleNsapNsapNativeAddress OBJECT-TYPE
   SYNTAX     AsciiString (SIZE (1..44))
   ACCESS     read-write
   STATUS     mandatory
   DESCRIPTION
     ""
::= { exampleNsapAtmAddrEntry 1246 }

exampleNsapNativeTable OBJECT-TYPE
   SYNTAX     SEQUENCE OF ExampleNsapNativeEntry
   ACCESS     not-accessible
   STATUS     mandatory
   DESCRIPTION
     ""
::= { exampleNsap 1247 }

exampleNsapNativeEntry OBJECT-TYPE
   SYNTAX     ExampleNsapNativeEntry
   ACCESS     not-accessible
   STATUS     mandatory
   DESCRIPTION
     "An entry in the exampleNsapNativeTable."
   INDEX {
      exampleIndex,
      exampleNsapIndex,
      exampleNsapNativeIndex }
::= { exampleNsapNativeTable 1 }

ExampleNsapNativeEntry ::= SEQUENCE {
   exampleNsapNativeIndex
      Integer32,
   exampleNsapNativeValue
      AsciiString }

exampleNsapNativeIndex OBJECT-TYPE
   SYNTAX     Integer32 (0..9)
   ACCESS     not-accessible
   STATUS     mandatory
   DESCRIPTION
     "This variable represents the exampleNsapNativeTable
      specific index for the exampleNsapNativeTable."
::= { exampleNsapNativeEntry 1 }

exampleNsapNativeValue OBJECT-TYPE
   SYNTAX     AsciiString (SIZE (1..44))
   ACCESS     read-write
   STATUS     mandatory
   DESCRIPTION
     "This variable represents an individual value for the
      exampleNsapNativeTable."
::= { exampleNsapNativeEntry 2 }


-- This is an example process component.

fri OBJECT IDENTIFIER ::= { components 5001 }



friRowStatusTable OBJECT-TYPE
   SYNTAX     SEQUENCE OF FriRowStatusEntry
   ACCESS     not-accessible
   STATUS     mandatory
   DESCRIPTION
     "This entry controls the addition and deletion of 
      fri components."
::= { fri 1 }

friRowStatusEntry OBJECT-TYPE
   SYNTAX     FriRowStatusEntry
   ACCESS     not-accessible
   STATUS     mandatory
   DESCRIPTION
     "A single entry in the table represents a single 
      fri component."
   INDEX {
      friIndex }
::= { friRowStatusTable 1 }

FriRowStatusEntry ::= SEQUENCE {
   friRowStatus
      RowStatus,
   friComponentName
      DisplayString,
   friStorageType
      StorageType,
   friIndex
      Integer32 }

friRowStatus OBJECT-TYPE
   SYNTAX     RowStatus 
   ACCESS     read-write
   STATUS     mandatory
   DESCRIPTION
     "This variable is used as the basis for SNMP naming of
      fri components.
      These components can be added and deleted."
::= { friRowStatusEntry 1 }

friComponentName OBJECT-TYPE
   SYNTAX     DisplayString 
   ACCESS     read-only
   STATUS     mandatory
   DESCRIPTION
     "This variable provides the component's string name for
      use with the ASCII Console Interface"
::= { friRowStatusEntry 2 }

friStorageType OBJECT-TYPE
   SYNTAX     StorageType 
   ACCESS     read-only
   STATUS     mandatory
   DESCRIPTION
     "This variable represents the storage type value for the
      fri tables."
::= { friRowStatusEntry 4 }

friIndex OBJECT-TYPE
   SYNTAX     Integer32 (0..99)
   ACCESS     not-accessible
   STATUS     mandatory
   DESCRIPTION
     "This variable represents the index for the fri tables."
::= { friRowStatusEntry 10 }

friOperationalTable OBJECT-TYPE
   SYNTAX     SEQUENCE OF FriOperationalEntry
   ACCESS     not-accessible
   STATUS     mandatory
   DESCRIPTION
     ""
::= { fri 100 }

friOperationalEntry OBJECT-TYPE
   SYNTAX     FriOperationalEntry
   ACCESS     not-accessible
   STATUS     mandatory
   DESCRIPTION
     "An entry in the friOperationalTable."
   INDEX {
      friIndex }
::= { friOperationalTable 1 }

FriOperationalEntry ::= SEQUENCE {
   friOperationalFreeSimpleAscii
      AsciiString,
   friOperationalFreeSimpleDashed
      DashedHexString,
   friOperationalFreeSimpleExtended
      ExtendedAsciiString,
   friOperationalFreeSimpleBcd
      DigitString,
   friOperationalFreeSimpleSigned
      INTEGER,
   friOperationalFreeSimpleFixed
      FixedPoint1,
   friOperationalFreeSimpleSequence
      IntegerSequence,
   friOperationalFreeSimpleObjId
      IntegerSequence,
   friOperationalFreeSimpleComponent
      RowPointer,
   friOperationalFreeSimpleHex
      HexString,
   friOperationalStructSetEnumeration
      OCTET STRING,
   friOperationalStructSetUnsigned
      OCTET STRING,
   friOperationalStructSimpleAscii
      AsciiString,
   friOperationalStructSimpleDashed
      DashedHexString,
   friOperationalStructSimpleExtended
      ExtendedAsciiString,
   friOperationalStructSimpleBcd
      DigitString,
   friOperationalStructSimpleSigned
      INTEGER,
   friOperationalStructSimpleFixed
      FixedPoint1,
   friOperationalStructSimpleSequence
      IntegerSequence,
   friOperationalStructSimpleEnum
      INTEGER,
   friOperationalStructSimpleHex
      HexString,
   friOperationalStructSimpleUnsigned
      Unsigned32 }

friOperationalFreeSimpleAscii OBJECT-TYPE
   SYNTAX     AsciiString (SIZE (10..100))
   ACCESS     read-write
   STATUS     mandatory
   DESCRIPTION
     ""
::= { friOperationalEntry 1 }

friOperationalFreeSimpleDashed OBJECT-TYPE
   SYNTAX     DashedHexString (SIZE (10..100))
   ACCESS     read-write
   STATUS     mandatory
   DESCRIPTION
     ""
::= { friOperationalEntry 2 }

friOperationalFreeSimpleExtended OBJECT-TYPE
   SYNTAX     ExtendedAsciiString (SIZE (10..100))
   ACCESS     read-write
   STATUS     mandatory
   DESCRIPTION
     ""
::= { friOperationalEntry 3 }

friOperationalFreeSimpleBcd OBJECT-TYPE
   SYNTAX     DigitString (SIZE (2..10))
   ACCESS     read-write
   STATUS     mandatory
   DESCRIPTION
     ""
::= { friOperationalEntry 4 }

friOperationalFreeSimpleSigned OBJECT-TYPE
   SYNTAX     INTEGER (-2..10)
   ACCESS     read-write
   STATUS     mandatory
   DESCRIPTION
     ""
::= { friOperationalEntry 5 }

friOperationalFreeSimpleFixed OBJECT-TYPE
   SYNTAX     FixedPoint1 (55..66)
   ACCESS     read-write
   STATUS     mandatory
   DESCRIPTION
     ""
::= { friOperationalEntry 6 }

friOperationalFreeSimpleSequence OBJECT-TYPE
   SYNTAX     IntegerSequence (SIZE (5..11))
   ACCESS     read-write
   STATUS     mandatory
   DESCRIPTION
     ""
::= { friOperationalEntry 7 }

friOperationalFreeSimpleObjId OBJECT-TYPE
   SYNTAX     IntegerSequence 
   ACCESS     read-write
   STATUS     mandatory
   DESCRIPTION
     ""
::= { friOperationalEntry 8 }

friOperationalFreeSimpleComponent OBJECT-TYPE
   SYNTAX     RowPointer 
   ACCESS     read-write
   STATUS     mandatory
   DESCRIPTION
     ""
::= { friOperationalEntry 9 }

friOperationalFreeSimpleHex OBJECT-TYPE
   SYNTAX     HexString (SIZE (20))
   ACCESS     read-write
   STATUS     mandatory
   DESCRIPTION
     ""
::= { friOperationalEntry 10 }

friOperationalStructSetEnumeration OBJECT-TYPE
   SYNTAX     OCTET STRING (SIZE (2))
   ACCESS     read-write
   STATUS     mandatory
   DESCRIPTION
     "Description of bits:
      january(0)
      february(1)
      march(2)
      april(3)
      may(4)
      june(5)
      july(6)
      august(7)
      september(8)
      october(9)
      november(10)
      december(11)"
   DEFVAL     { '9100'H }
::= { friOperationalEntry 11 }

friOperationalStructSetUnsigned OBJECT-TYPE
   SYNTAX     OCTET STRING (SIZE (1))
   ACCESS     read-write
   STATUS     mandatory
   DESCRIPTION
     "Description of bits:
      n0(0)
      n1(1)
      n2(2)
      n3(3)
      n4(4)
      n5(5)"
   DEFVAL     { '54'H }
::= { friOperationalEntry 12 }

friOperationalStructSimpleAscii OBJECT-TYPE
   SYNTAX     AsciiString (SIZE (10..100))
   ACCESS     read-write
   STATUS     mandatory
   DESCRIPTION
     ""
   DEFVAL     { '61313063686172737472696e67'H }  -- "a10charstring"
::= { friOperationalEntry 13 }

friOperationalStructSimpleDashed OBJECT-TYPE
   SYNTAX     DashedHexString (SIZE (10..100))
   ACCESS     read-write
   STATUS     mandatory
   DESCRIPTION
     ""
::= { friOperationalEntry 14 }

friOperationalStructSimpleExtended OBJECT-TYPE
   SYNTAX     ExtendedAsciiString (SIZE (10..100))
   ACCESS     read-write
   STATUS     mandatory
   DESCRIPTION
     ""
::= { friOperationalEntry 15 }

friOperationalStructSimpleBcd OBJECT-TYPE
   SYNTAX     DigitString (SIZE (2..10))
   ACCESS     read-write
   STATUS     mandatory
   DESCRIPTION
     ""
::= { friOperationalEntry 16 }

friOperationalStructSimpleSigned OBJECT-TYPE
   SYNTAX     INTEGER (-2..10)
   ACCESS     read-write
   STATUS     mandatory
   DESCRIPTION
     ""
::= { friOperationalEntry 17 }

friOperationalStructSimpleFixed OBJECT-TYPE
   SYNTAX     FixedPoint1 (23..29)
   ACCESS     read-write
   STATUS     mandatory
   DESCRIPTION
     ""
::= { friOperationalEntry 18 }

friOperationalStructSimpleSequence OBJECT-TYPE
   SYNTAX     IntegerSequence (SIZE (3..6))
   ACCESS     read-write
   STATUS     mandatory
   DESCRIPTION
     ""
::= { friOperationalEntry 19 }

friOperationalStructSimpleEnum OBJECT-TYPE
   SYNTAX     INTEGER  {
                 monday(0),
                 tuesday(1),
                 wednesday(2),
                 thursday(3),
                 friday(4),
                 saterday(5),
                 sunday(6) }
   ACCESS     read-write
   STATUS     mandatory
   DESCRIPTION
     ""
   DEFVAL     { monday }
::= { friOperationalEntry 20 }

friOperationalStructSimpleHex OBJECT-TYPE
   SYNTAX     HexString (SIZE (10..100))
   ACCESS     read-write
   STATUS     mandatory
   DESCRIPTION
     ""
::= { friOperationalEntry 21 }

friOperationalStructSimpleUnsigned OBJECT-TYPE
   SYNTAX     Unsigned32 (0..31)
   ACCESS     read-write
   STATUS     mandatory
   DESCRIPTION
     ""
   DEFVAL     { 3 }
::= { friOperationalEntry 22 }

friProvisionalTable OBJECT-TYPE
   SYNTAX     SEQUENCE OF FriProvisionalEntry
   ACCESS     not-accessible
   STATUS     mandatory
   DESCRIPTION
     ""
::= { fri 101 }

friProvisionalEntry OBJECT-TYPE
   SYNTAX     FriProvisionalEntry
   ACCESS     not-accessible
   STATUS     mandatory
   DESCRIPTION
     "An entry in the friProvisionalTable."
   INDEX {
      friIndex }
::= { friProvisionalTable 1 }

FriProvisionalEntry ::= SEQUENCE {
   friProvisionalStructSetEnumeration
      OCTET STRING,
   friProvisionalStructSetUnsigned
      OCTET STRING,
   friProvisionalStructSimpleAscii
      AsciiString,
   friProvisionalStructSimpleDashed
      DashedHexString,
   friProvisionalStructSimpleExtended
      ExtendedAsciiString,
   friProvisionalStructSimpleBcd
      DigitString,
   friProvisionalStructSimpleSequence
      IntegerSequence,
   friProvisionalStructSimpleEnum
      INTEGER,
   friProvisionalStructSimpleHex
      HexString,
   friProvisionalStructSimpleUnsigned
      Unsigned32,
   friProvisionalStructSimpleSigned
      INTEGER,
   friProvisionalStructSimpleFixed
      FixedPoint2,
   friProvisionalFreeSimpleAscii
      AsciiString,
   friProvisionalFreeSimpleDashed
      DashedHexString,
   friProvisionalFreeSimpleExtended
      ExtendedAsciiString,
   friProvisionalFreeSimpleBcd
      DigitString,
   friProvisionalFreeSimpleSequence
      IntegerSequence,
   friProvisionalFreeSimpleSigned
      INTEGER,
   friProvisionalFreeSimpleFixed
      FixedPoint2,
   friProvisionalFreeSimpleObjId
      IntegerSequence,
   friProvisionalFreeSimpleComponent
      RowPointer,
   friProvisionalFreeSimpleHex
      HexString,
   friEscapeCheckAttribute
      Unsigned32,
   friEscapeDefaultsComponent
      Unsigned32,
   friEscapeDefaultsGroup
      Unsigned32,
   friEscapeSet
      AsciiString,
   friEscapeCopyComponent
      Unsigned32,
   friEscapeCopyGroup
      Unsigned32,
   friEscapeCopyAttribute
      Unsigned32 }

friProvisionalStructSetEnumeration OBJECT-TYPE
   SYNTAX     OCTET STRING (SIZE (1))
   ACCESS     read-write
   STATUS     mandatory
   DESCRIPTION
     "Description of bits:
      monday(0)
      tuesday(1)
      wednesday(2)
      thursday(3)
      friday(4)
      saterday(5)
      sunday(6)"
   DEFVAL     { 'a8'H }
::= { friProvisionalEntry 1 }

friProvisionalStructSetUnsigned OBJECT-TYPE
   SYNTAX     OCTET STRING (SIZE (2))
   ACCESS     read-write
   STATUS     mandatory
   DESCRIPTION
     "Description of bits:
      n0(0)
      n1(1)
      n2(2)
      n3(3)
      n4(4)
      n5(5)
      n6(6)
      n7(7)
      n8(8)
      n9(9)
      n10(10)
      n11(11)
      n12(12)"
   DEFVAL     { 'aaa8'H }
::= { friProvisionalEntry 2 }

friProvisionalStructSimpleAscii OBJECT-TYPE
   SYNTAX     AsciiString (SIZE (10..100))
   ACCESS     read-write
   STATUS     mandatory
   DESCRIPTION
     ""
   DEFVAL     { '61737472696e676f663131'H }  -- "astringof11"
::= { friProvisionalEntry 3 }

friProvisionalStructSimpleDashed OBJECT-TYPE
   SYNTAX     DashedHexString (SIZE (10..100))
   ACCESS     read-write
   STATUS     mandatory
   DESCRIPTION
     ""
   DEFVAL     { '01234556789abCDef0ee'H }
::= { friProvisionalEntry 4 }

friProvisionalStructSimpleExtended OBJECT-TYPE
   SYNTAX     ExtendedAsciiString (SIZE (10..100))
   ACCESS     read-write
   STATUS     mandatory
   DESCRIPTION
     ""
   DEFVAL     { '61006211632264336544'H }  -- "a\00b\11c\22d\33e\44"
::= { friProvisionalEntry 5 }

friProvisionalStructSimpleBcd OBJECT-TYPE
   SYNTAX     DigitString (SIZE (2..10))
   ACCESS     read-write
   STATUS     mandatory
   DESCRIPTION
     ""
   DEFVAL     { '31323334'H }  -- "1234"
::= { friProvisionalEntry 6 }

friProvisionalStructSimpleSequence OBJECT-TYPE
   SYNTAX     IntegerSequence (SIZE (1..2))
   ACCESS     read-write
   STATUS     mandatory
   DESCRIPTION
     ""
::= { friProvisionalEntry 7 }

friProvisionalStructSimpleEnum OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     ""
   DEFVAL     { february }
::= { friProvisionalEntry 8 }

friProvisionalStructSimpleHex OBJECT-TYPE
   SYNTAX     HexString (SIZE (10..100))
   ACCESS     read-write
   STATUS     mandatory
   DESCRIPTION
     ""
   DEFVAL     { '3039303930393039303930393039303930393039303930393039'H }  -- "\x09090909090909090909090909"
::= { friProvisionalEntry 9 }

friProvisionalStructSimpleUnsigned OBJECT-TYPE
   SYNTAX     Unsigned32 (0..255)
   ACCESS     read-write
   STATUS     mandatory
   DESCRIPTION
     ""
   DEFVAL     { 10 }
::= { friProvisionalEntry 10 }

friProvisionalStructSimpleSigned OBJECT-TYPE
   SYNTAX     INTEGER (-255..255)
   ACCESS     read-write
   STATUS     mandatory
   DESCRIPTION
     ""
   DEFVAL     { -5 }
::= { friProvisionalEntry 11 }

friProvisionalStructSimpleFixed OBJECT-TYPE
   SYNTAX     FixedPoint2 (254..355)
   ACCESS     read-write
   STATUS     mandatory
   DESCRIPTION
     ""
   DEFVAL     { 350 }
::= { friProvisionalEntry 12 }

friProvisionalFreeSimpleAscii OBJECT-TYPE
   SYNTAX     AsciiString (SIZE (10..100))
   ACCESS     read-write
   STATUS     mandatory
   DESCRIPTION
     ""
   DEFVAL     { '61737472696e676f663131'H }  -- "astringof11"
::= { friProvisionalEntry 13 }

friProvisionalFreeSimpleDashed OBJECT-TYPE
   SYNTAX     DashedHexString (SIZE (10..100))
   ACCESS     read-write
   STATUS     mandatory
   DESCRIPTION
     ""
   DEFVAL     { '00112233445566778899aabbccddeeff'H }
::= { friProvisionalEntry 14 }

friProvisionalFreeSimpleExtended OBJECT-TYPE
   SYNTAX     ExtendedAsciiString (SIZE (10..100))
   ACCESS     read-write
   STATUS     mandatory
   DESCRIPTION
     ""
   DEFVAL     { '61626300006465665555676869'H }  -- "abc\00\00def\55\55ghi"
::= { friProvisionalEntry 15 }

friProvisionalFreeSimpleBcd OBJECT-TYPE
   SYNTAX     DigitString (SIZE (2..10))
   ACCESS     read-write
   STATUS     mandatory
   DESCRIPTION
     ""
   DEFVAL     { '31323334'H }  -- "1234"
::= { friProvisionalEntry 16 }

friProvisionalFreeSimpleSequence OBJECT-TYPE
   SYNTAX     IntegerSequence (SIZE (8..11))
   ACCESS     read-write
   STATUS     mandatory
   DESCRIPTION
     ""
::= { friProvisionalEntry 17 }

friProvisionalFreeSimpleSigned OBJECT-TYPE
   SYNTAX     INTEGER (-2147483648..2147483647)
   ACCESS     read-write
   STATUS     mandatory
   DESCRIPTION
     ""
   DEFVAL     { -11 }
::= { friProvisionalEntry 18 }

friProvisionalFreeSimpleFixed OBJECT-TYPE
   SYNTAX     FixedPoint2 (22..233)
   ACCESS     read-write
   STATUS     mandatory
   DESCRIPTION
     ""
   DEFVAL     { 122 }
::= { friProvisionalEntry 19 }

friProvisionalFreeSimpleObjId OBJECT-TYPE
   SYNTAX     IntegerSequence 
   ACCESS     read-write
   STATUS     mandatory
   DESCRIPTION
     ""
::= { friProvisionalEntry 20 }

friProvisionalFreeSimpleComponent OBJECT-TYPE
   SYNTAX     RowPointer 
   ACCESS     read-write
   STATUS     mandatory
   DESCRIPTION
     ""
::= { friProvisionalEntry 21 }

friProvisionalFreeSimpleHex OBJECT-TYPE
   SYNTAX     HexString (SIZE (10..100))
   ACCESS     read-write
   STATUS     mandatory
   DESCRIPTION
     ""
   DEFVAL     { '00112233445566778899aaBBcCDdeeFF313233'H }  -- "00112233445566778899aaBBcCDdeeFF\x123"
::= { friProvisionalEntry 22 }

friEscapeCheckAttribute OBJECT-TYPE
   SYNTAX     Unsigned32 (0..255)
   ACCESS     read-write
   STATUS     mandatory
   DESCRIPTION
     ""
   DEFVAL     { 4 }
::= { friProvisionalEntry 23 }

friEscapeDefaultsComponent OBJECT-TYPE
   SYNTAX     Unsigned32 (0..255)
   ACCESS     read-write
   STATUS     mandatory
   DESCRIPTION
     ""
::= { friProvisionalEntry 24 }

friEscapeDefaultsGroup OBJECT-TYPE
   SYNTAX     Unsigned32 (0..255)
   ACCESS     read-write
   STATUS     mandatory
   DESCRIPTION
     ""
::= { friProvisionalEntry 25 }

friEscapeSet OBJECT-TYPE
   SYNTAX     AsciiString (SIZE (4..8))
   ACCESS     write-only
   STATUS     mandatory
   DESCRIPTION
     "This attribute is used for testing the immediate
      value manipulation offered by the set escape.
      This is ONLY VALID IF the read access is DEBUG or
      NONE. This is to prevent the NMS and Passport from
      becoming out of sync. If the value has an odd number
      of characters, we issue the exampleEscapeSetResponse
      error response."
   DEFVAL     { '70617373776f7264'H }  -- "password"
::= { friProvisionalEntry 26 }

friEscapeCopyComponent OBJECT-TYPE
   SYNTAX     Unsigned32 (0..65535)
   ACCESS     read-write
   STATUS     mandatory
   DESCRIPTION
     ""
::= { friProvisionalEntry 27 }

friEscapeCopyGroup OBJECT-TYPE
   SYNTAX     Unsigned32 (0..65535)
   ACCESS     read-write
   STATUS     mandatory
   DESCRIPTION
     ""
::= { friProvisionalEntry 28 }

friEscapeCopyAttribute OBJECT-TYPE
   SYNTAX     Unsigned32 (0..65535)
   ACCESS     read-write
   STATUS     mandatory
   DESCRIPTION
     ""
::= { friProvisionalEntry 29 }

friStateTable OBJECT-TYPE
   SYNTAX     SEQUENCE OF FriStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { fri 102 }

friStateEntry OBJECT-TYPE
   SYNTAX     FriStateEntry
   ACCESS     not-accessible
   STATUS     mandatory
   DESCRIPTION
     "An entry in the friStateTable."
   INDEX {
      friIndex }
::= { friStateTable 1 }

FriStateEntry ::= SEQUENCE {
   friAdminState
      INTEGER,
   friOperationalState
      INTEGER,
   friUsageState
      INTEGER,
   friAvailabilityStatus
      OCTET STRING,
   friProceduralStatus
      OCTET STRING,
   friControlStatus
      OCTET STRING,
   friAlarmStatus
      OCTET STRING,
   friStandbyStatus
      INTEGER,
   friUnknownStatus
      INTEGER }

friAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { friStateEntry 1 }

friOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { friStateEntry 2 }

friUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { friStateEntry 3 }

friAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { friStateEntry 4 }

friProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { friStateEntry 5 }

friControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { friStateEntry 6 }

friAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { friStateEntry 7 }

friStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { friStateEntry 8 }

friUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { friStateEntry 9 }

friPfListAsciiTable OBJECT-TYPE
   SYNTAX     SEQUENCE OF FriPfListAsciiEntry
   ACCESS     not-accessible
   STATUS     mandatory
   DESCRIPTION
     ""
::= { fri 1187 }

friPfListAsciiEntry OBJECT-TYPE
   SYNTAX     FriPfListAsciiEntry
   ACCESS     not-accessible
   STATUS     mandatory
   DESCRIPTION
     "An entry in the friPfListAsciiTable."
   INDEX {
      friIndex,
      friPfListAsciiValue }
::= { friPfListAsciiTable 1 }

FriPfListAsciiEntry ::= SEQUENCE {
   friPfListAsciiValue
      AsciiString,
   friPfListAsciiRowStatus
      RowStatus }

friPfListAsciiValue OBJECT-TYPE
   SYNTAX     AsciiString (SIZE (0..100))
   ACCESS     read-write
   STATUS     mandatory
   DESCRIPTION
     "This variable represents both the value and the index for the
      friPfListAsciiTable."
::= { friPfListAsciiEntry 1 }

friPfListAsciiRowStatus OBJECT-TYPE
   SYNTAX     RowStatus 
   ACCESS     write-only
   STATUS     mandatory
   DESCRIPTION
     "This variable is used to control the addition and deletion 
      of individual values of the friPfListAsciiTable."
::= { friPfListAsciiEntry 2 }

friPfListUnsignedTable OBJECT-TYPE
   SYNTAX     SEQUENCE OF FriPfListUnsignedEntry
   ACCESS     not-accessible
   STATUS     mandatory
   DESCRIPTION
     ""
::= { fri 1188 }

friPfListUnsignedEntry OBJECT-TYPE
   SYNTAX     FriPfListUnsignedEntry
   ACCESS     not-accessible
   STATUS     mandatory
   DESCRIPTION
     "An entry in the friPfListUnsignedTable."
   INDEX {
      friIndex,
      friPfListUnsignedValue }
::= { friPfListUnsignedTable 1 }

FriPfListUnsignedEntry ::= SEQUENCE {
   friPfListUnsignedValue
      Integer32,
   friPfListUnsignedRowStatus
      RowStatus }

friPfListUnsignedValue OBJECT-TYPE
   SYNTAX     Integer32 (0..255)
   ACCESS     read-write
   STATUS     mandatory
   DESCRIPTION
     "This variable represents both the value and the index for the
      friPfListUnsignedTable."
::= { friPfListUnsignedEntry 1 }

friPfListUnsignedRowStatus OBJECT-TYPE
   SYNTAX     RowStatus 
   ACCESS     write-only
   STATUS     mandatory
   DESCRIPTION
     "This variable is used to control the addition and deletion 
      of individual values of the friPfListUnsignedTable."
::= { friPfListUnsignedEntry 2 }

friPfListFixedTable OBJECT-TYPE
   SYNTAX     SEQUENCE OF FriPfListFixedEntry
   ACCESS     not-accessible
   STATUS     mandatory
   DESCRIPTION
     ""
::= { fri 1189 }

friPfListFixedEntry OBJECT-TYPE
   SYNTAX     FriPfListFixedEntry
   ACCESS     not-accessible
   STATUS     mandatory
   DESCRIPTION
     "An entry in the friPfListFixedTable."
   INDEX {
      friIndex,
      friPfListFixedValue }
::= { friPfListFixedTable 1 }

FriPfListFixedEntry ::= SEQUENCE {
   friPfListFixedValue
      Integer32,
   friPfListFixedRowStatus
      RowStatus }

friPfListFixedValue OBJECT-TYPE
   SYNTAX     Integer32 (1..2559)
   ACCESS     read-write
   STATUS     mandatory
   DESCRIPTION
     "This variable represents both the value and the index for the
      friPfListFixedTable."
::= { friPfListFixedEntry 1 }

friPfListFixedRowStatus OBJECT-TYPE
   SYNTAX     RowStatus 
   ACCESS     write-only
   STATUS     mandatory
   DESCRIPTION
     "This variable is used to control the addition and deletion 
      of individual values of the friPfListFixedTable."
::= { friPfListFixedEntry 2 }

friPfListSignedTable OBJECT-TYPE
   SYNTAX     SEQUENCE OF FriPfListSignedEntry
   ACCESS     not-accessible
   STATUS     mandatory
   DESCRIPTION
     ""
::= { fri 1190 }

friPfListSignedEntry OBJECT-TYPE
   SYNTAX     FriPfListSignedEntry
   ACCESS     not-accessible
   STATUS     mandatory
   DESCRIPTION
     "An entry in the friPfListSignedTable."
   INDEX {
      friIndex,
      friPfListSignedValue }
::= { friPfListSignedTable 1 }

FriPfListSignedEntry ::= SEQUENCE {
   friPfListSignedValue
      INTEGER,
   friPfListSignedRowStatus
      RowStatus }

friPfListSignedValue OBJECT-TYPE
   SYNTAX     INTEGER (-200..255)
   ACCESS     read-write
   STATUS     mandatory
   DESCRIPTION
     "This variable represents both the value and the index for the
      friPfListSignedTable."
::= { friPfListSignedEntry 1 }

friPfListSignedRowStatus OBJECT-TYPE
   SYNTAX     RowStatus 
   ACCESS     write-only
   STATUS     mandatory
   DESCRIPTION
     "This variable is used to control the addition and deletion 
      of individual values of the friPfListSignedTable."
::= { friPfListSignedEntry 2 }

friOfListComponentTable OBJECT-TYPE
   SYNTAX     SEQUENCE OF FriOfListComponentEntry
   ACCESS     not-accessible
   STATUS     mandatory
   DESCRIPTION
     ""
::= { fri 1191 }

friOfListComponentEntry OBJECT-TYPE
   SYNTAX     FriOfListComponentEntry
   ACCESS     not-accessible
   STATUS     mandatory
   DESCRIPTION
     "An entry in the friOfListComponentTable."
   INDEX {
      friIndex,
      friOfListComponentValue }
::= { friOfListComponentTable 1 }

FriOfListComponentEntry ::= SEQUENCE {
   friOfListComponentValue
      RowPointer,
   friOfListComponentRowStatus
      RowStatus }

friOfListComponentValue OBJECT-TYPE
   SYNTAX     RowPointer 
   ACCESS     read-write
   STATUS     mandatory
   DESCRIPTION
     "This variable represents both the value and the index for the
      friOfListComponentTable."
::= { friOfListComponentEntry 1 }

friOfListComponentRowStatus OBJECT-TYPE
   SYNTAX     RowStatus 
   ACCESS     write-only
   STATUS     mandatory
   DESCRIPTION
     "This variable is used to control the addition and deletion 
      of individual values of the friOfListComponentTable."
::= { friOfListComponentEntry 2 }

friOfListEnumerationTable OBJECT-TYPE
   SYNTAX     SEQUENCE OF FriOfListEnumerationEntry
   ACCESS     not-accessible
   STATUS     mandatory
   DESCRIPTION
     ""
::= { fri 1192 }

friOfListEnumerationEntry OBJECT-TYPE
   SYNTAX     FriOfListEnumerationEntry
   ACCESS     not-accessible
   STATUS     mandatory
   DESCRIPTION
     "An entry in the friOfListEnumerationTable."
   INDEX {
      friIndex,
      friOfListEnumerationValue }
::= { friOfListEnumerationTable 1 }

FriOfListEnumerationEntry ::= SEQUENCE {
   friOfListEnumerationValue
      INTEGER,
   friOfListEnumerationRowStatus
      RowStatus }

friOfListEnumerationValue OBJECT-TYPE
   SYNTAX     INTEGER  {
                 january(0),
                 february(1),
                 march(2),
                 april(3),
                 may(4),
                 june(5),
                 july(6),
                 august(7),
                 september(8),
                 october(9),
                 november(10),
                 december(11) }
   ACCESS     read-write
   STATUS     mandatory
   DESCRIPTION
     "This variable represents both the value and the index for the
      friOfListEnumerationTable."
::= { friOfListEnumerationEntry 1 }

friOfListEnumerationRowStatus OBJECT-TYPE
   SYNTAX     RowStatus 
   ACCESS     write-only
   STATUS     mandatory
   DESCRIPTION
     "This variable is used to control the addition and deletion 
      of individual values of the friOfListEnumerationTable."
::= { friOfListEnumerationEntry 2 }



friDna OBJECT IDENTIFIER ::= { fri 4 }



friDnaRowStatusTable OBJECT-TYPE
   SYNTAX     SEQUENCE OF FriDnaRowStatusEntry
   ACCESS     not-accessible
   STATUS     mandatory
   DESCRIPTION
     "This entry controls the addition and deletion of 
      friDna components."
::= { friDna 1 }

friDnaRowStatusEntry OBJECT-TYPE
   SYNTAX     FriDnaRowStatusEntry
   ACCESS     not-accessible
   STATUS     mandatory
   DESCRIPTION
     "A single entry in the table represents a single 
      friDna component."
   INDEX {
      friIndex,
      friDnaIndex }
::= { friDnaRowStatusTable 1 }

FriDnaRowStatusEntry ::= SEQUENCE {
   friDnaRowStatus
      RowStatus,
   friDnaComponentName
      DisplayString,
   friDnaStorageType
      StorageType,
   friDnaIndex
      Integer32 }

friDnaRowStatus OBJECT-TYPE
   SYNTAX     RowStatus 
   ACCESS     read-write
   STATUS     mandatory
   DESCRIPTION
     "This variable is used as the basis for SNMP naming of
      friDna components.
      These components can be added and deleted."
::= { friDnaRowStatusEntry 1 }

friDnaComponentName OBJECT-TYPE
   SYNTAX     DisplayString 
   ACCESS     read-only
   STATUS     mandatory
   DESCRIPTION
     "This variable provides the component's string name for
      use with the ASCII Console Interface"
::= { friDnaRowStatusEntry 2 }

friDnaStorageType OBJECT-TYPE
   SYNTAX     StorageType 
   ACCESS     read-only
   STATUS     mandatory
   DESCRIPTION
     "This variable represents the storage type value for the
      friDna tables."
::= { friDnaRowStatusEntry 4 }

friDnaIndex OBJECT-TYPE
   SYNTAX     Integer32 (0..15)
   ACCESS     not-accessible
   STATUS     mandatory
   DESCRIPTION
     "This variable represents the index for the friDna tables."
::= { friDnaRowStatusEntry 10 }

friDnaOperationalTable OBJECT-TYPE
   SYNTAX     SEQUENCE OF FriDnaOperationalEntry
   ACCESS     not-accessible
   STATUS     mandatory
   DESCRIPTION
     ""
::= { friDna 10 }

friDnaOperationalEntry OBJECT-TYPE
   SYNTAX     FriDnaOperationalEntry
   ACCESS     not-accessible
   STATUS     mandatory
   DESCRIPTION
     "An entry in the friDnaOperationalTable."
   INDEX {
      friIndex,
      friDnaIndex }
::= { friDnaOperationalTable 1 }

FriDnaOperationalEntry ::= SEQUENCE {
   friDnaAttribute
      Unsigned32 }

friDnaAttribute OBJECT-TYPE
   SYNTAX     Unsigned32 (0..65535)
   ACCESS     read-write
   STATUS     mandatory
   DESCRIPTION
     ""
   DEFVAL     { 1 }
::= { friDnaOperationalEntry 1 }

friDnaProvisionalTable OBJECT-TYPE
   SYNTAX     SEQUENCE OF FriDnaProvisionalEntry
   ACCESS     not-accessible
   STATUS     mandatory
   DESCRIPTION
     ""
::= { friDna 11 }

friDnaProvisionalEntry OBJECT-TYPE
   SYNTAX     FriDnaProvisionalEntry
   ACCESS     not-accessible
   STATUS     mandatory
   DESCRIPTION
     "An entry in the friDnaProvisionalTable."
   INDEX {
      friIndex,
      friDnaIndex }
::= { friDnaProvisionalTable 1 }

FriDnaProvisionalEntry ::= SEQUENCE {
   friDnaTypeOfAddress
      INTEGER,
   friDnaNumberPlanIndicator
      INTEGER,
   friDnaDataNetworkAddress
      DigitString }

friDnaTypeOfAddress OBJECT-TYPE
   SYNTAX     INTEGER  {
                 networkDepend(0),
                 international(1),
                 national(2) }
   ACCESS     read-only
   STATUS     mandatory
   DESCRIPTION
     ""
   DEFVAL     { international }
::= { friDnaProvisionalEntry 1 }

friDnaNumberPlanIndicator OBJECT-TYPE
   SYNTAX     INTEGER  {
                 x121(0),
                 e164(1) }
   ACCESS     read-write
   STATUS     mandatory
   DESCRIPTION
     ""
   DEFVAL     { x121 }
::= { friDnaProvisionalEntry 2 }

friDnaDataNetworkAddress OBJECT-TYPE
   SYNTAX     DigitString (SIZE (1..15))
   ACCESS     read-write
   STATUS     mandatory
   DESCRIPTION
     ""
::= { friDnaProvisionalEntry 3 }

-- 
-- *** THIS SUBTREE CURRENTLY NOT IMPLEMENTED ***
-- 


friDynamic OBJECT IDENTIFIER ::= { fri 7 }



friDynamicRowStatusTable OBJECT-TYPE
   SYNTAX     SEQUENCE OF FriDynamicRowStatusEntry
   ACCESS     not-accessible
   STATUS     mandatory
   DESCRIPTION
     "*** THIS TABLE CURRENTLY NOT IMPLEMENTED ***

      This entry controls the addition and deletion of 
      friDynamic components."
::= { friDynamic 1 }

friDynamicRowStatusEntry OBJECT-TYPE
   SYNTAX     FriDynamicRowStatusEntry
   ACCESS     not-accessible
   STATUS     mandatory
   DESCRIPTION
     "A single entry in the table represents a single 
      friDynamic component."
   INDEX {
      friIndex,
      friDynamicIndex }
::= { friDynamicRowStatusTable 1 }

FriDynamicRowStatusEntry ::= SEQUENCE {
   friDynamicRowStatus
      RowStatus,
   friDynamicComponentName
      DisplayString,
   friDynamicStorageType
      StorageType,
   friDynamicIndex
      Integer32 }

friDynamicRowStatus OBJECT-TYPE
   SYNTAX     RowStatus 
   ACCESS     read-only
   STATUS     mandatory
   DESCRIPTION
     "This variable is used as the basis for SNMP naming of
      friDynamic components.
      These components cannot be added nor deleted."
::= { friDynamicRowStatusEntry 1 }

friDynamicComponentName OBJECT-TYPE
   SYNTAX     DisplayString 
   ACCESS     read-only
   STATUS     mandatory
   DESCRIPTION
     "This variable provides the component's string name for
      use with the ASCII Console Interface"
::= { friDynamicRowStatusEntry 2 }

friDynamicStorageType OBJECT-TYPE
   SYNTAX     StorageType 
   ACCESS     read-only
   STATUS     mandatory
   DESCRIPTION
     "This variable represents the storage type value for the
      friDynamic tables."
::= { friDynamicRowStatusEntry 4 }

friDynamicIndex OBJECT-TYPE
   SYNTAX     Integer32 (0..1023)
   ACCESS     not-accessible
   STATUS     mandatory
   DESCRIPTION
     "This variable represents the index for the friDynamic tables."
::= { friDynamicRowStatusEntry 10 }

friDynamicOperationalTable OBJECT-TYPE
   SYNTAX     SEQUENCE OF FriDynamicOperationalEntry
   ACCESS     not-accessible
   STATUS     mandatory
   DESCRIPTION
     "*** THIS TABLE CURRENTLY NOT IMPLEMENTED ***"
::= { friDynamic 10 }

friDynamicOperationalEntry OBJECT-TYPE
   SYNTAX     FriDynamicOperationalEntry
   ACCESS     not-accessible
   STATUS     mandatory
   DESCRIPTION
     "An entry in the friDynamicOperationalTable."
   INDEX {
      friIndex,
      friDynamicIndex }
::= { friDynamicOperationalTable 1 }

FriDynamicOperationalEntry ::= SEQUENCE {
   friDynamicAttribute
      Unsigned32 }

friDynamicAttribute OBJECT-TYPE
   SYNTAX     Unsigned32 (0..255)
   ACCESS     read-write
   STATUS     mandatory
   DESCRIPTION
     ""
   DEFVAL     { 1 }
::= { friDynamicOperationalEntry 1 }



friDynOp OBJECT IDENTIFIER ::= { fri 8 }



friDynOpRowStatusTable OBJECT-TYPE
   SYNTAX     SEQUENCE OF FriDynOpRowStatusEntry
   ACCESS     not-accessible
   STATUS     mandatory
   DESCRIPTION
     "This entry controls the addition and deletion of 
      friDynOp components."
::= { friDynOp 1 }

friDynOpRowStatusEntry OBJECT-TYPE
   SYNTAX     FriDynOpRowStatusEntry
   ACCESS     not-accessible
   STATUS     mandatory
   DESCRIPTION
     "A single entry in the table represents a single 
      friDynOp component."
   INDEX {
      friIndex,
      friDynOpIndex }
::= { friDynOpRowStatusTable 1 }

FriDynOpRowStatusEntry ::= SEQUENCE {
   friDynOpRowStatus
      RowStatus,
   friDynOpComponentName
      DisplayString,
   friDynOpStorageType
      StorageType,
   friDynOpIndex
      Integer32 }

friDynOpRowStatus OBJECT-TYPE
   SYNTAX     RowStatus 
   ACCESS     read-write
   STATUS     mandatory
   DESCRIPTION
     "This variable is used as the basis for SNMP naming of
      friDynOp components.
      These components can be added and deleted."
::= { friDynOpRowStatusEntry 1 }

friDynOpComponentName OBJECT-TYPE
   SYNTAX     DisplayString 
   ACCESS     read-only
   STATUS     mandatory
   DESCRIPTION
     "This variable provides the component's string name for
      use with the ASCII Console Interface"
::= { friDynOpRowStatusEntry 2 }

friDynOpStorageType OBJECT-TYPE
   SYNTAX     StorageType 
   ACCESS     read-only
   STATUS     mandatory
   DESCRIPTION
     "This variable represents the storage type value for the
      friDynOp tables."
::= { friDynOpRowStatusEntry 4 }

friDynOpIndex OBJECT-TYPE
   SYNTAX     Integer32 (0..1023)
   ACCESS     not-accessible
   STATUS     mandatory
   DESCRIPTION
     "This variable represents the index for the friDynOp tables."
::= { friDynOpRowStatusEntry 10 }

friDynOpOperationalTable OBJECT-TYPE
   SYNTAX     SEQUENCE OF FriDynOpOperationalEntry
   ACCESS     not-accessible
   STATUS     mandatory
   DESCRIPTION
     ""
::= { friDynOp 10 }

friDynOpOperationalEntry OBJECT-TYPE
   SYNTAX     FriDynOpOperationalEntry
   ACCESS     not-accessible
   STATUS     mandatory
   DESCRIPTION
     "An entry in the friDynOpOperationalTable."
   INDEX {
      friIndex,
      friDynOpIndex }
::= { friDynOpOperationalTable 1 }

FriDynOpOperationalEntry ::= SEQUENCE {
   friDynOpAttribute
      Unsigned32 }

friDynOpAttribute OBJECT-TYPE
   SYNTAX     Unsigned32 (0..255)
   ACCESS     read-write
   STATUS     mandatory
   DESCRIPTION
     ""
   DEFVAL     { 1 }
::= { friDynOpOperationalEntry 1 }



friDynOpInitial OBJECT IDENTIFIER ::= { friDynOp 2 }



friDynOpInitialRowStatusTable OBJECT-TYPE
   SYNTAX     SEQUENCE OF FriDynOpInitialRowStatusEntry
   ACCESS     not-accessible
   STATUS     mandatory
   DESCRIPTION
     "This entry controls the addition and deletion of 
      friDynOpInitial components."
::= { friDynOpInitial 1 }

friDynOpInitialRowStatusEntry OBJECT-TYPE
   SYNTAX     FriDynOpInitialRowStatusEntry
   ACCESS     not-accessible
   STATUS     mandatory
   DESCRIPTION
     "A single entry in the table represents a single 
      friDynOpInitial component."
   INDEX {
      friIndex,
      friDynOpIndex,
      friDynOpInitialIndex }
::= { friDynOpInitialRowStatusTable 1 }

FriDynOpInitialRowStatusEntry ::= SEQUENCE {
   friDynOpInitialRowStatus
      RowStatus,
   friDynOpInitialComponentName
      DisplayString,
   friDynOpInitialStorageType
      StorageType,
   friDynOpInitialIndex
      NonReplicated }

friDynOpInitialRowStatus OBJECT-TYPE
   SYNTAX     RowStatus 
   ACCESS     read-only
   STATUS     mandatory
   DESCRIPTION
     "This variable is used as the basis for SNMP naming of
      friDynOpInitial components.
      These components cannot be added nor deleted."
::= { friDynOpInitialRowStatusEntry 1 }

friDynOpInitialComponentName OBJECT-TYPE
   SYNTAX     DisplayString 
   ACCESS     read-only
   STATUS     mandatory
   DESCRIPTION
     "This variable provides the component's string name for
      use with the ASCII Console Interface"
::= { friDynOpInitialRowStatusEntry 2 }

friDynOpInitialStorageType OBJECT-TYPE
   SYNTAX     StorageType 
   ACCESS     read-only
   STATUS     mandatory
   DESCRIPTION
     "This variable represents the storage type value for the
      friDynOpInitial tables."
::= { friDynOpInitialRowStatusEntry 4 }

friDynOpInitialIndex OBJECT-TYPE
   SYNTAX     NonReplicated 
   ACCESS     not-accessible
   STATUS     mandatory
   DESCRIPTION
     "This variable represents the index for the friDynOpInitial tables."
::= { friDynOpInitialRowStatusEntry 10 }

friDynOpInitialOperationalTable OBJECT-TYPE
   SYNTAX     SEQUENCE OF FriDynOpInitialOperationalEntry
   ACCESS     not-accessible
   STATUS     mandatory
   DESCRIPTION
     ""
::= { friDynOpInitial 10 }

friDynOpInitialOperationalEntry OBJECT-TYPE
   SYNTAX     FriDynOpInitialOperationalEntry
   ACCESS     not-accessible
   STATUS     mandatory
   DESCRIPTION
     "An entry in the friDynOpInitialOperationalTable."
   INDEX {
      friIndex,
      friDynOpIndex,
      friDynOpInitialIndex }
::= { friDynOpInitialOperationalTable 1 }

FriDynOpInitialOperationalEntry ::= SEQUENCE {
   friDynOpInitialAttribute
      Unsigned32 }

friDynOpInitialAttribute OBJECT-TYPE
   SYNTAX     Unsigned32 (0..255)
   ACCESS     read-write
   STATUS     mandatory
   DESCRIPTION
     ""
   DEFVAL     { 1 }
::= { friDynOpInitialOperationalEntry 1 }

friDynOpInitialProvisionedTable OBJECT-TYPE
   SYNTAX     SEQUENCE OF FriDynOpInitialProvisionedEntry
   ACCESS     not-accessible
   STATUS     mandatory
   DESCRIPTION
     ""
::= { friDynOpInitial 11 }

friDynOpInitialProvisionedEntry OBJECT-TYPE
   SYNTAX     FriDynOpInitialProvisionedEntry
   ACCESS     not-accessible
   STATUS     mandatory
   DESCRIPTION
     "An entry in the friDynOpInitialProvisionedTable."
   INDEX {
      friIndex,
      friDynOpIndex,
      friDynOpInitialIndex }
::= { friDynOpInitialProvisionedTable 1 }

FriDynOpInitialProvisionedEntry ::= SEQUENCE {
   friDynOpInitialProvAttribute
      Unsigned32 }

friDynOpInitialProvAttribute OBJECT-TYPE
   SYNTAX     Unsigned32 (0..255)
   ACCESS     read-write
   STATUS     mandatory
   DESCRIPTION
     ""
   DEFVAL     { 1 }
::= { friDynOpInitialProvisionedEntry 1 }



friDynOpOptional OBJECT IDENTIFIER ::= { friDynOp 3 }



friDynOpOptionalRowStatusTable OBJECT-TYPE
   SYNTAX     SEQUENCE OF FriDynOpOptionalRowStatusEntry
   ACCESS     not-accessible
   STATUS     mandatory
   DESCRIPTION
     "This entry controls the addition and deletion of 
      friDynOpOptional components."
::= { friDynOpOptional 1 }

friDynOpOptionalRowStatusEntry OBJECT-TYPE
   SYNTAX     FriDynOpOptionalRowStatusEntry
   ACCESS     not-accessible
   STATUS     mandatory
   DESCRIPTION
     "A single entry in the table represents a single 
      friDynOpOptional component."
   INDEX {
      friIndex,
      friDynOpIndex,
      friDynOpOptionalIndex }
::= { friDynOpOptionalRowStatusTable 1 }

FriDynOpOptionalRowStatusEntry ::= SEQUENCE {
   friDynOpOptionalRowStatus
      RowStatus,
   friDynOpOptionalComponentName
      DisplayString,
   friDynOpOptionalStorageType
      StorageType,
   friDynOpOptionalIndex
      NonReplicated }

friDynOpOptionalRowStatus OBJECT-TYPE
   SYNTAX     RowStatus 
   ACCESS     read-write
   STATUS     mandatory
   DESCRIPTION
     "This variable is used as the basis for SNMP naming of
      friDynOpOptional components.
      These components can be added and deleted."
::= { friDynOpOptionalRowStatusEntry 1 }

friDynOpOptionalComponentName OBJECT-TYPE
   SYNTAX     DisplayString 
   ACCESS     read-only
   STATUS     mandatory
   DESCRIPTION
     "This variable provides the component's string name for
      use with the ASCII Console Interface"
::= { friDynOpOptionalRowStatusEntry 2 }

friDynOpOptionalStorageType OBJECT-TYPE
   SYNTAX     StorageType 
   ACCESS     read-only
   STATUS     mandatory
   DESCRIPTION
     "This variable represents the storage type value for the
      friDynOpOptional tables."
::= { friDynOpOptionalRowStatusEntry 4 }

friDynOpOptionalIndex OBJECT-TYPE
   SYNTAX     NonReplicated 
   ACCESS     not-accessible
   STATUS     mandatory
   DESCRIPTION
     "This variable represents the index for the friDynOpOptional tables."
::= { friDynOpOptionalRowStatusEntry 10 }

friDynOpOptionalOperationalTable OBJECT-TYPE
   SYNTAX     SEQUENCE OF FriDynOpOptionalOperationalEntry
   ACCESS     not-accessible
   STATUS     mandatory
   DESCRIPTION
     ""
::= { friDynOpOptional 10 }

friDynOpOptionalOperationalEntry OBJECT-TYPE
   SYNTAX     FriDynOpOptionalOperationalEntry
   ACCESS     not-accessible
   STATUS     mandatory
   DESCRIPTION
     "An entry in the friDynOpOptionalOperationalTable."
   INDEX {
      friIndex,
      friDynOpIndex,
      friDynOpOptionalIndex }
::= { friDynOpOptionalOperationalTable 1 }

FriDynOpOptionalOperationalEntry ::= SEQUENCE {
   friDynOpOptionalAttribute
      Unsigned32 }

friDynOpOptionalAttribute OBJECT-TYPE
   SYNTAX     Unsigned32 (0..255)
   ACCESS     read-write
   STATUS     mandatory
   DESCRIPTION
     ""
   DEFVAL     { 1 }
::= { friDynOpOptionalOperationalEntry 1 }

friDynOpOptionalProvisionedTable OBJECT-TYPE
   SYNTAX     SEQUENCE OF FriDynOpOptionalProvisionedEntry
   ACCESS     not-accessible
   STATUS     mandatory
   DESCRIPTION
     ""
::= { friDynOpOptional 11 }

friDynOpOptionalProvisionedEntry OBJECT-TYPE
   SYNTAX     FriDynOpOptionalProvisionedEntry
   ACCESS     not-accessible
   STATUS     mandatory
   DESCRIPTION
     "An entry in the friDynOpOptionalProvisionedTable."
   INDEX {
      friIndex,
      friDynOpIndex,
      friDynOpOptionalIndex }
::= { friDynOpOptionalProvisionedTable 1 }

FriDynOpOptionalProvisionedEntry ::= SEQUENCE {
   friDynOpOptionalProvAttribute
      Unsigned32 }

friDynOpOptionalProvAttribute OBJECT-TYPE
   SYNTAX     Unsigned32 (0..255)
   ACCESS     read-write
   STATUS     mandatory
   DESCRIPTION
     ""
   DEFVAL     { 1 }
::= { friDynOpOptionalProvisionedEntry 1 }



friDynOpDynamic OBJECT IDENTIFIER ::= { friDynOp 4 }



friDynOpDynamicRowStatusTable OBJECT-TYPE
   SYNTAX     SEQUENCE OF FriDynOpDynamicRowStatusEntry
   ACCESS     not-accessible
   STATUS     mandatory
   DESCRIPTION
     "This entry controls the addition and deletion of 
      friDynOpDynamic components."
::= { friDynOpDynamic 1 }

friDynOpDynamicRowStatusEntry OBJECT-TYPE
   SYNTAX     FriDynOpDynamicRowStatusEntry
   ACCESS     not-accessible
   STATUS     mandatory
   DESCRIPTION
     "A single entry in the table represents a single 
      friDynOpDynamic component."
   INDEX {
      friIndex,
      friDynOpIndex,
      friDynOpDynamicIndex }
::= { friDynOpDynamicRowStatusTable 1 }

FriDynOpDynamicRowStatusEntry ::= SEQUENCE {
   friDynOpDynamicRowStatus
      RowStatus,
   friDynOpDynamicComponentName
      DisplayString,
   friDynOpDynamicStorageType
      StorageType,
   friDynOpDynamicIndex
      NonReplicated }

friDynOpDynamicRowStatus OBJECT-TYPE
   SYNTAX     RowStatus 
   ACCESS     read-only
   STATUS     mandatory
   DESCRIPTION
     "This variable is used as the basis for SNMP naming of
      friDynOpDynamic components.
      These components cannot be added nor deleted."
::= { friDynOpDynamicRowStatusEntry 1 }

friDynOpDynamicComponentName OBJECT-TYPE
   SYNTAX     DisplayString 
   ACCESS     read-only
   STATUS     mandatory
   DESCRIPTION
     "This variable provides the component's string name for
      use with the ASCII Console Interface"
::= { friDynOpDynamicRowStatusEntry 2 }

friDynOpDynamicStorageType OBJECT-TYPE
   SYNTAX     StorageType 
   ACCESS     read-only
   STATUS     mandatory
   DESCRIPTION
     "This variable represents the storage type value for the
      friDynOpDynamic tables."
::= { friDynOpDynamicRowStatusEntry 4 }

friDynOpDynamicIndex OBJECT-TYPE
   SYNTAX     NonReplicated 
   ACCESS     not-accessible
   STATUS     mandatory
   DESCRIPTION
     "This variable represents the index for the friDynOpDynamic tables."
::= { friDynOpDynamicRowStatusEntry 10 }

friDynOpDynamicOperationalTable OBJECT-TYPE
   SYNTAX     SEQUENCE OF FriDynOpDynamicOperationalEntry
   ACCESS     not-accessible
   STATUS     mandatory
   DESCRIPTION
     ""
::= { friDynOpDynamic 10 }

friDynOpDynamicOperationalEntry OBJECT-TYPE
   SYNTAX     FriDynOpDynamicOperationalEntry
   ACCESS     not-accessible
   STATUS     mandatory
   DESCRIPTION
     "An entry in the friDynOpDynamicOperationalTable."
   INDEX {
      friIndex,
      friDynOpIndex,
      friDynOpDynamicIndex }
::= { friDynOpDynamicOperationalTable 1 }

FriDynOpDynamicOperationalEntry ::= SEQUENCE {
   friDynOpDynamicAttribute
      Unsigned32 }

friDynOpDynamicAttribute OBJECT-TYPE
   SYNTAX     Unsigned32 (0..255)
   ACCESS     read-write
   STATUS     mandatory
   DESCRIPTION
     ""
   DEFVAL     { 1 }
::= { friDynOpDynamicOperationalEntry 1 }



friDynOpDynOpJr OBJECT IDENTIFIER ::= { friDynOp 5 }



friDynOpDynOpJrRowStatusTable OBJECT-TYPE
   SYNTAX     SEQUENCE OF FriDynOpDynOpJrRowStatusEntry
   ACCESS     not-accessible
   STATUS     mandatory
   DESCRIPTION
     "This entry controls the addition and deletion of 
      friDynOpDynOpJr components."
::= { friDynOpDynOpJr 1 }

friDynOpDynOpJrRowStatusEntry OBJECT-TYPE
   SYNTAX     FriDynOpDynOpJrRowStatusEntry
   ACCESS     not-accessible
   STATUS     mandatory
   DESCRIPTION
     "A single entry in the table represents a single 
      friDynOpDynOpJr component."
   INDEX {
      friIndex,
      friDynOpIndex,
      friDynOpDynOpJrIndex }
::= { friDynOpDynOpJrRowStatusTable 1 }

FriDynOpDynOpJrRowStatusEntry ::= SEQUENCE {
   friDynOpDynOpJrRowStatus
      RowStatus,
   friDynOpDynOpJrComponentName
      DisplayString,
   friDynOpDynOpJrStorageType
      StorageType,
   friDynOpDynOpJrIndex
      NonReplicated }

friDynOpDynOpJrRowStatus OBJECT-TYPE
   SYNTAX     RowStatus 
   ACCESS     read-write
   STATUS     mandatory
   DESCRIPTION
     "This variable is used as the basis for SNMP naming of
      friDynOpDynOpJr components.
      These components can be added and deleted."
::= { friDynOpDynOpJrRowStatusEntry 1 }

friDynOpDynOpJrComponentName OBJECT-TYPE
   SYNTAX     DisplayString 
   ACCESS     read-only
   STATUS     mandatory
   DESCRIPTION
     "This variable provides the component's string name for
      use with the ASCII Console Interface"
::= { friDynOpDynOpJrRowStatusEntry 2 }

friDynOpDynOpJrStorageType OBJECT-TYPE
   SYNTAX     StorageType 
   ACCESS     read-only
   STATUS     mandatory
   DESCRIPTION
     "This variable represents the storage type value for the
      friDynOpDynOpJr tables."
::= { friDynOpDynOpJrRowStatusEntry 4 }

friDynOpDynOpJrIndex OBJECT-TYPE
   SYNTAX     NonReplicated 
   ACCESS     not-accessible
   STATUS     mandatory
   DESCRIPTION
     "This variable represents the index for the friDynOpDynOpJr tables."
::= { friDynOpDynOpJrRowStatusEntry 10 }

friDynOpDynOpJrOperationalTable OBJECT-TYPE
   SYNTAX     SEQUENCE OF FriDynOpDynOpJrOperationalEntry
   ACCESS     not-accessible
   STATUS     mandatory
   DESCRIPTION
     ""
::= { friDynOpDynOpJr 10 }

friDynOpDynOpJrOperationalEntry OBJECT-TYPE
   SYNTAX     FriDynOpDynOpJrOperationalEntry
   ACCESS     not-accessible
   STATUS     mandatory
   DESCRIPTION
     "An entry in the friDynOpDynOpJrOperationalTable."
   INDEX {
      friIndex,
      friDynOpIndex,
      friDynOpDynOpJrIndex }
::= { friDynOpDynOpJrOperationalTable 1 }

FriDynOpDynOpJrOperationalEntry ::= SEQUENCE {
   friDynOpDynOpJrAttribute
      Unsigned32 }

friDynOpDynOpJrAttribute OBJECT-TYPE
   SYNTAX     Unsigned32 (0..255)
   ACCESS     read-write
   STATUS     mandatory
   DESCRIPTION
     ""
   DEFVAL     { 1 }
::= { friDynOpDynOpJrOperationalEntry 1 }



friEvent OBJECT IDENTIFIER ::= { fri 9 }



friEventRowStatusTable OBJECT-TYPE
   SYNTAX     SEQUENCE OF FriEventRowStatusEntry
   ACCESS     not-accessible
   STATUS     mandatory
   DESCRIPTION
     "This entry controls the addition and deletion of 
      friEvent components."
::= { friEvent 1 }

friEventRowStatusEntry OBJECT-TYPE
   SYNTAX     FriEventRowStatusEntry
   ACCESS     not-accessible
   STATUS     mandatory
   DESCRIPTION
     "A single entry in the table represents a single 
      friEvent component."
   INDEX {
      friIndex,
      friEventIndex }
::= { friEventRowStatusTable 1 }

FriEventRowStatusEntry ::= SEQUENCE {
   friEventRowStatus
      RowStatus,
   friEventComponentName
      DisplayString,
   friEventStorageType
      StorageType,
   friEventIndex
      NonReplicated }

friEventRowStatus OBJECT-TYPE
   SYNTAX     RowStatus 
   ACCESS     read-only
   STATUS     mandatory
   DESCRIPTION
     "This variable is used as the basis for SNMP naming of
      friEvent components.
      These components cannot be added nor deleted."
::= { friEventRowStatusEntry 1 }

friEventComponentName OBJECT-TYPE
   SYNTAX     DisplayString 
   ACCESS     read-only
   STATUS     mandatory
   DESCRIPTION
     "This variable provides the component's string name for
      use with the ASCII Console Interface"
::= { friEventRowStatusEntry 2 }

friEventStorageType OBJECT-TYPE
   SYNTAX     StorageType 
   ACCESS     read-only
   STATUS     mandatory
   DESCRIPTION
     "This variable represents the storage type value for the
      friEvent tables."
::= { friEventRowStatusEntry 4 }

friEventIndex OBJECT-TYPE
   SYNTAX     NonReplicated 
   ACCESS     not-accessible
   STATUS     mandatory
   DESCRIPTION
     "This variable represents the index for the friEvent tables."
::= { friEventRowStatusEntry 10 }



friRegistered OBJECT IDENTIFIER ::= { fri 18 }



friRegisteredRowStatusTable OBJECT-TYPE
   SYNTAX     SEQUENCE OF FriRegisteredRowStatusEntry
   ACCESS     not-accessible
   STATUS     mandatory
   DESCRIPTION
     "This entry controls the addition and deletion of 
      friRegistered components."
::= { friRegistered 1 }

friRegisteredRowStatusEntry OBJECT-TYPE
   SYNTAX     FriRegisteredRowStatusEntry
   ACCESS     not-accessible
   STATUS     mandatory
   DESCRIPTION
     "A single entry in the table represents a single 
      friRegistered component."
   INDEX {
      friIndex,
      friRegisteredIndex }
::= { friRegisteredRowStatusTable 1 }

FriRegisteredRowStatusEntry ::= SEQUENCE {
   friRegisteredRowStatus
      RowStatus,
   friRegisteredComponentName
      DisplayString,
   friRegisteredStorageType
      StorageType,
   friRegisteredIndex
      Integer32 }

friRegisteredRowStatus OBJECT-TYPE
   SYNTAX     RowStatus 
   ACCESS     read-only
   STATUS     mandatory
   DESCRIPTION
     "This variable is used as the basis for SNMP naming of
      friRegistered components.
      These components cannot be added nor deleted."
::= { friRegisteredRowStatusEntry 1 }

friRegisteredComponentName OBJECT-TYPE
   SYNTAX     DisplayString 
   ACCESS     read-only
   STATUS     mandatory
   DESCRIPTION
     "This variable provides the component's string name for
      use with the ASCII Console Interface"
::= { friRegisteredRowStatusEntry 2 }

friRegisteredStorageType OBJECT-TYPE
   SYNTAX     StorageType 
   ACCESS     read-only
   STATUS     mandatory
   DESCRIPTION
     "This variable represents the storage type value for the
      friRegistered tables."
::= { friRegisteredRowStatusEntry 4 }

friRegisteredIndex OBJECT-TYPE
   SYNTAX     Integer32 (0..15)
   ACCESS     not-accessible
   STATUS     mandatory
   DESCRIPTION
     "This variable represents the index for the friRegistered tables."
::= { friRegisteredRowStatusEntry 10 }

friRegisteredDataTable OBJECT-TYPE
   SYNTAX     SEQUENCE OF FriRegisteredDataEntry
   ACCESS     not-accessible
   STATUS     mandatory
   DESCRIPTION
     ""
::= { friRegistered 10 }

friRegisteredDataEntry OBJECT-TYPE
   SYNTAX     FriRegisteredDataEntry
   ACCESS     not-accessible
   STATUS     mandatory
   DESCRIPTION
     "An entry in the friRegisteredDataTable."
   INDEX {
      friIndex,
      friRegisteredIndex }
::= { friRegisteredDataTable 1 }

FriRegisteredDataEntry ::= SEQUENCE {
   friRegisteredAttribute
      Unsigned32 }

friRegisteredAttribute OBJECT-TYPE
   SYNTAX     Unsigned32 (0..255)
   ACCESS     read-write
   STATUS     mandatory
   DESCRIPTION
     ""
   DEFVAL     { 1 }
::= { friRegisteredDataEntry 1 }



registered OBJECT IDENTIFIER ::= { components 5004 }



registeredRowStatusTable OBJECT-TYPE
   SYNTAX     SEQUENCE OF RegisteredRowStatusEntry
   ACCESS     not-accessible
   STATUS     mandatory
   DESCRIPTION
     "This entry controls the addition and deletion of 
      registered components."
::= { registered 1 }

registeredRowStatusEntry OBJECT-TYPE
   SYNTAX     RegisteredRowStatusEntry
   ACCESS     not-accessible
   STATUS     mandatory
   DESCRIPTION
     "A single entry in the table represents a single 
      registered component."
   INDEX {
      registeredIndex }
::= { registeredRowStatusTable 1 }

RegisteredRowStatusEntry ::= SEQUENCE {
   registeredRowStatus
      RowStatus,
   registeredComponentName
      DisplayString,
   registeredStorageType
      StorageType,
   registeredIndex
      Integer32 }

registeredRowStatus OBJECT-TYPE
   SYNTAX     RowStatus 
   ACCESS     read-only
   STATUS     mandatory
   DESCRIPTION
     "This variable is used as the basis for SNMP naming of
      registered components.
      These components cannot be added nor deleted."
::= { registeredRowStatusEntry 1 }

registeredComponentName OBJECT-TYPE
   SYNTAX     DisplayString 
   ACCESS     read-only
   STATUS     mandatory
   DESCRIPTION
     "This variable provides the component's string name for
      use with the ASCII Console Interface"
::= { registeredRowStatusEntry 2 }

registeredStorageType OBJECT-TYPE
   SYNTAX     StorageType 
   ACCESS     read-only
   STATUS     mandatory
   DESCRIPTION
     "This variable represents the storage type value for the
      registered tables."
::= { registeredRowStatusEntry 4 }

registeredIndex OBJECT-TYPE
   SYNTAX     Integer32 (0..15)
   ACCESS     not-accessible
   STATUS     mandatory
   DESCRIPTION
     "This variable represents the index for the registered tables."
::= { registeredRowStatusEntry 10 }

registeredDataTable OBJECT-TYPE
   SYNTAX     SEQUENCE OF RegisteredDataEntry
   ACCESS     not-accessible
   STATUS     mandatory
   DESCRIPTION
     ""
::= { registered 10 }

registeredDataEntry OBJECT-TYPE
   SYNTAX     RegisteredDataEntry
   ACCESS     not-accessible
   STATUS     mandatory
   DESCRIPTION
     "An entry in the registeredDataTable."
   INDEX {
      registeredIndex }
::= { registeredDataTable 1 }

RegisteredDataEntry ::= SEQUENCE {
   registeredAttribute
      Unsigned32 }

registeredAttribute OBJECT-TYPE
   SYNTAX     Unsigned32 (0..255)
   ACCESS     read-write
   STATUS     mandatory
   DESCRIPTION
     ""
   DEFVAL     { 1 }
::= { registeredDataEntry 1 }




-- 
-- Version and Compliance statements
-- 



-- Object-Group Statement:
-- A list of all current accessible leaf objects.

-- OBJECTS { exampleNsapNsapNativeAddress,
--           friDynOpInitialAttribute,
--           exampleDashedIndicesProvAttribute,
--           friOperationalStructSimpleExtended,
--           exampleMiscellaneousProvFreeLong,
--           exampleDashedOfDashedVectorValue,
--           exampleEnumOperFreeEnumReplicatedValue,
--           exampleEnumProvStructEnumVectorValue,
--           friEventStorageType,
--           friRegisteredRowStatus,
--           exampleHexProvFreeHex1,
--           exampleDecimalPfIntListValue,
--           exampleOperFixedPtSubcomponentsCreatedRowStatus,
--           friProvisionalStructSimpleHex,
--           exampleStringRowStatus,
--           exampleBcdIndicesRowStatus,
--           exampleOperStringSubCreatedValue,
--           exampleStringProvFreeStrListRowStatus,
--           exampleFourIndicesProvAttribute,
--           exampleHexOperStructHex,
--           exampleOperEnumSubCreatedValue,
--           exampleIpAddrIndicesProvAttribute,
--           exampleObjectIdOperFreeObjIdReplicatedValue,
--           friProvisionalStructSetEnumeration,
--           exampleDecimalOfIntListValue,
--           friProvisionalStructSimpleBcd,
--           exampleHexOsHexVectorValue,
--           friOperationalStructSimpleDashed,
--           exampleWildBcdStorageType,
--           friRegisteredStorageType,
--           exampleDashedIndicesStorageType,
--           exampleEnumProvFreeEnum1,
--           exampleMiscellaneousProvFreeTimeDateOnly,
--           exampleOperSignedSubCreatedRowStatus,
--           exampleFixedPtOperStructFixedPtVectorValue,
--           exampleStringOperFreeStrVectorValue,
--           exampleWildBcdOperStructWildBcdVectorValue,
--           exampleAsciiIndicesRowStatus,
--           exampleBcdProvFreeBcd1,
--           exampleNsapNativeValue,
--           exampleDashedProvFreeDashed,
--           exampleMiscellaneousProvFreeLongListValue,
--           exampleEnumOperStructEnum,
--           exampleIpAddressOperFreeIpAddressReplicatedRowStatus,
--           exampleHexStrIndicesStorageType,
--           exampleProvFixedPtSubCreatedRowStatus,
--           exampleOperDecimalSubCreatedRowStatus,
--           exampleBcdOperStructBcd,
--           exampleIpAddressOperFreeIpAddressArrayValue,
--           friRegisteredAttribute,
--           friDnaAttribute,
--           exampleDashedOfDashedReplicatedValue,
--           exampleSignedOperFreeSignedReplicatedValue,
--           exampleSignedProvStructSignedVectorValue,
--           exampleSequenceProvFreeSequenceListRowStatus,
--           exampleHexOfHexListValue,
--           exampleHexProvFreeHexList1Value,
--           exampleFixedPtProvFreeFixedPt,
--           exampleMiscellaneousOperFreeCounter64,
--           exampleExtendedProvFreeExtendedVectorValue,
--           exampleFixedPtProvStructFixedPtSet,
--           exampleExtendedComponentName,
--           exampleMiscellaneousProvFreeLongListRowStatus,
--           exampleComponentName,
--           friProvisionalFreeSimpleExtended,
--           friOperationalStructSimpleFixed,
--           exampleStringProvFreeAsciiOnly1,
--           friDynOpDynOpJrAttribute,
--           exampleSequenceIndicesRowStatus,
--           exampleIpAddrIndicesRowStatus,
--           friEscapeCopyAttribute,
--           friOperationalStructSimpleSigned,
--           exampleNsapStorageType,
--           friOperationalFreeSimpleFixed,
--           exampleMiscellaneousProvFreeTimeTimeOnly1,
--           exampleHexOfHexReplicatedValue,
--           exampleStringOperStructAsciiOnly,
--           exampleStringOperFreeStrReplicatedValue,
--           exampleSignedComponentName,
--           exampleStringProvStructStrVectorValue,
--           friProvisionalFreeSimpleSequence,
--           exampleBcdProvFreeBcdList1Value,
--           exampleSignedOperStructSigned,
--           exampleDashedProvFreeDashedListValue,
--           friDynOpDynOpJrComponentName,
--           exampleBcdProvFreeBcdArray1Value,
--           exampleExtendedProvEnumSub,
--           exampleMiscellaneousProvFreeTimeDateTimeMinute1,
--           exampleIpAddressProvStructIpAddressArrayValue,
--           registeredAttribute,
--           friEventRowStatus,
--           exampleMiscellaneousOperFreeLongReplicatedRowStatus,
--           exampleExtendedOperFreeExtended,
--           exampleMiscellaneousProvFreeTimeListRowStatus,
--           exampleBcdProvFreeBcdArrayValue,
--           exampleExtendedOperFreeExtendedVectorValue,
--           exampleHexProvFreeHexReplicatedRowStatus,
--           exampleExtendedProvFreeExtendedReplicatedValue,
--           exampleFixedPtProvFreeFixedPtListValue,
--           exampleHexProvFreeHexArrayValue,
--           exampleWildBcdProvFreeWildBcdListValue,
--           exampleBcdProvFreeBcdList1RowStatus,
--           exampleBcdIndicesProvAttribute,
--           friDnaComponentName,
--           exampleHexStorageType,
--           friStandbyStatus,
--           exampleIpAddressProvFreeIpAddressList1RowStatus,
--           exampleFourIndicesStorageType,
--           exampleSequenceOperFreeSequenceReplicatedValue,
--           exampleDecimalOperFreeCounter32,
--           exampleStringOperFreeHexOnly,
--           friEscapeCopyComponent,
--           exampleEnumProvFreeEnumArrayValue,
--           exampleBcdProvFreeBcdReplicatedRowStatus,
--           exampleDecimalPfIntList1RowStatus,
--           exampleAsciiIndicesProvAttribute,
--           exampleIpAddressProvFreeIpAddressVectorValue,
--           exampleProvStringSubCreatedRowStatus,
--           exampleIpAddrIndicesStorageType,
--           exampleHexProvEnumSub,
--           exampleEnumIndicesStorageType,
--           exampleSequenceComponentName,
--           exampleDecimalOperFreeInteger,
--           exampleProvEnumSubCreatedRowStatus,
--           exampleBcdIndicesStorageType,
--           exampleIpAddressProvFreeIpAddressListRowStatus,
--           exampleExtendedProvStructExtended,
--           exampleExtendedOperFreeExtendedListValue,
--           exampleBcdOperFreeBcdReplicatedValue,
--           exampleDashedComponentName,
--           exampleObjIdIndicesProvAttribute,
--           friDynOpOptionalProvAttribute,
--           friProvisionalStructSimpleUnsigned,
--           exampleSignedStorageType,
--           exampleEnumProvEnumSub,
--           exampleOneIndexProvAttribute,
--           exampleDecimalPfIntVectorValue,
--           friEscapeCopyGroup,
--           exampleFixedPtOperFreeFixedPtReplicatedRowStatus,
--           exampleDecimalOperFreeIntSet,
--           exampleStringProvFreeStrList1Value,
--           exampleFixedPtComponentName,
--           exampleSequenceOperStructSequence,
--           exampleMiscellaneousProvFreeTimeList3RowStatus,
--           exampleFixedPtOperFreeFixedPtArrayValue,
--           exampleWildBcdOperFreeWildBcdArrayValue,
--           exampleMiscellaneousStorageType,
--           friStorageType,
--           exampleEnumOperFreeEnumListRowStatus,
--           exampleDecimalOfIntVectorValue,
--           exampleTwoIndicesComponentName,
--           exampleThreeIndicesRowStatus,
--           exampleDecimalOperStructIntSet,
--           exampleBcdOperFreeBcdListRowStatus,
--           exampleOneIndexStorageType,
--           exampleIpAddressOperFreeIpAddress,
--           exampleIpAddressRowStatus,
--           exampleSignedProvFreeSignedReplicatedRowStatus,
--           exampleMiscellaneousProvFreeTimeList2RowStatus,
--           exampleStringProvStructHexOnly,
--           exampleTwoIndicesProvAttribute,
--           exampleSignedProvFreeSignedArrayValue,
--           exampleObjIdIndicesStorageType,
--           friDynOpInitialRowStatus,
--           exampleSequenceOperFreeSequenceListValue,
--           exampleObjectIdOperFreeObjIdListRowStatus,
--           exampleIpAddressProvFreeIpAddressReplicatedValue,
--           exampleSequenceStorageType,
--           exampleProvDecimalSubCreatedValue,
--           exampleDashedProvStructDashedArrayValue,
--           exampleAsciiIndicesComponentName,
--           exampleDecimalProvStructInteger,
--           friEscapeCheckAttribute,
--           friDynOpInitialStorageType,
--           friProvisionalFreeSimpleFixed,
--           exampleHexProvFreeHexVector2Value,
--           friOfListComponentValue,
--           exampleDecimalPfIntReplicatedValue,
--           exampleHexOfHexVectorValue,
--           exampleHexProvFreeHexVector1Value,
--           friDynOpOptionalAttribute,
--           exampleStringProvFreeStrReplicatedRowStatus,
--           friEscapeDefaultsGroup,
--           exampleFixedPtProvStructFixedPtArrayValue,
--           exampleStringProvFreeStrArrayValue,
--           exampleWildBcdProvStructWildBcdArrayValue,
--           exampleFixedPtRowStatus,
--           exampleSignedOperFreeSignedListRowStatus,
--           exampleDecimalOfIntReplicatedValue,
--           exampleEnumOperFreeEnumSet,
--           exampleIpAddressOperFreeIpAddressListRowStatus,
--           exampleObjectIdOperFreeObjIdReplicatedRowStatus,
--           exampleFixedPtProvFixedPtSubcomponent,
--           friProvisionalFreeSimpleSigned,
--           exampleWildBcdOperStructWildBcd,
--           exampleIpAddressProvStructIpAddress,
--           exampleIpAddressOperFreeIpAddressListValue,
--           exampleEnumProvFreeEnumVector1Value,
--           friOperationalFreeSimpleSequence,
--           exampleSignedOperFreeSigned,
--           exampleFixedPtOperFreeFixedPtSet,
--           exampleBcdProvFreeBcdVector1Value,
--           exampleAsciiIndicesStorageType,
--           exampleDashedProvFreeDashedVectorValue,
--           exampleDashedOsDashedArrayValue,
--           exampleEnumOperStructEnumVectorValue,
--           exampleWildBcdRowStatus,
--           exampleMiscellaneousProvFreeTimeList1RowStatus,
--           exampleSignedOperFreeSignedListValue,
--           exampleHexProvFreeHex,
--           exampleObjectIdComponentName,
--           exampleBcdOperStructBcdVectorValue,
--           friOperationalState,
--           exampleSignedProvFreeSigned1,
--           exampleMiscellaneousOperFreeTime,
--           exampleStringOperFreeStrListRowStatus,
--           friAvailabilityStatus,
--           exampleSequenceProvFreeSequenceReplicatedRowStatus,
--           exampleExtendedOperStructExtendedArrayValue,
--           exampleHexProvFreeHexReplicated1Value,
--           friDnaNumberPlanIndicator,
--           friDynOpRowStatus,
--           exampleFourIndicesRowStatus,
--           exampleFixedPtProvFreeFixedPtVectorValue,
--           exampleMiscellaneousProvFreeTimeReplicatedValue,
--           exampleWildBcdProvFreeWildBcdVectorValue,
--           friDynOpOptionalComponentName,
--           friProvisionalStructSimpleAscii,
--           exampleEnumComponentName,
--           exampleEnumProvFreeEnum,
--           exampleHexIndicesComponentName,
--           exampleBcdComponentName,
--           exampleFixedPtOperFreeFixedPtListValue,
--           friDynamicStorageType,
--           friOperationalFreeSimpleHex,
--           exampleBcdProvFreeBcd,
--           friProvisionalFreeSimpleBcd,
--           exampleObjectIdProvEnumSub,
--           friComponentName,
--           exampleSequenceProvStructSequence,
--           friProvisionalStructSetUnsigned,
--           exampleSignedProvFreeSignedVector1Value,
--           exampleExtendedProvFreeExtendedListRowStatus,
--           exampleStringProvFreeHexOnly1,
--           exampleDecimalIndicesRowStatus,
--           exampleBcdProvFreeBcdReplicated1Value,
--           exampleMiscellaneousProvStructLong,
--           exampleDashedProvFreeDashedReplicatedValue,
--           exampleSignedOperStructSignedVectorValue,
--           friDynOpComponentName,
--           exampleDecimalProvStructIntSet,
--           friDynamicAttribute,
--           exampleObjectIdProvFreeObjId,
--           friPfListSignedRowStatus,
--           exampleSequenceOperFreeSequenceListRowStatus,
--           friProvisionalFreeSimpleAscii,
--           exampleHexProvFreeHexListValue,
--           exampleExtendedProvStructExtendedArrayValue,
--           exampleFixedPtOperFreeFixedPt,
--           friDnaStorageType,
--           exampleWildBcdOperFreeWildBcd,
--           exampleBcdProvEnumSub,
--           exampleMiscellaneousOperFreeTimeListValue,
--           exampleRequiredIndicesComponentName,
--           exampleExtendedStorageType,
--           friPfListAsciiValue,
--           exampleMiscellaneousOperFreeLongListValue,
--           exampleStorageType,
--           exampleNsapComponentName,
--           exampleStringProvFreeAsciiOnly,
--           exampleWildBcdProvFreeWildBcdReplicatedValue,
--           exampleStringProvFreeStrVector1Value,
--           friProvisionalFreeSimpleObjId,
--           exampleOperMyComponentName,
--           exampleMiscellaneousProvFreeTimeTimeOnly,
--           exampleDecimalIndicesComponentName,
--           exampleEnumProvFreeEnumListValue,
--           friOfListEnumerationRowStatus,
--           exampleStringOperStructStrVectorValue,
--           exampleProvFixedPtSubCreatedValue,
--           exampleBcdProvFreeBcdListValue,
--           exampleDashedProvStructDashed,
--           exampleRequiredIndicesRowStatus,
--           friDynOpDynOpJrStorageType,
--           exampleHexRowStatus,
--           exampleMiscellaneousProvFreeTimeDateTimeMinute,
--           exampleNsapRowStatus,
--           exampleIpAddressOperStructIpAddressArrayValue,
--           exampleDecimalPfIntReplicated1RowStatus,
--           exampleIpAddressProvStructIpAddressVectorValue,
--           friUnknownStatus,
--           exampleObjectIdProvFreeObjIdListValue,
--           exampleObjectIdProvFreeObjIdReplicatedRowStatus,
--           friProvisionalStructSimpleSigned,
--           exampleDecimalPfIntArray1Value,
--           friOperationalStructSetUnsigned,
--           exampleSequenceIndicesComponentName,
--           exampleSignedRowStatus,
--           exampleStringProvFreeStrArray1Value,
--           exampleDecimalOsIntArrayValue,
--           exampleStringProvStringSub,
--           exampleExtendedOperFreeExtendedReplicatedValue,
--           exampleMiscellaneousOperStructCounter64,
--           exampleFixedPtProvFreeFixedPtSet,
--           exampleWildBcdOperFreeWildBcdListValue,
--           exampleDashedOfDashedListValue,
--           friOperationalStructSetEnumeration,
--           exampleEnumIndicesRowStatus,
--           exampleMiscellaneousOperFreeGauge64,
--           exampleBcdProvStructBcdVectorValue,
--           exampleEnumProvFreeEnumReplicatedRowStatus,
--           friProvisionalStructSimpleSequence,
--           friEscapeSet,
--           friPfListFixedValue,
--           exampleSignedProvFreeSignedListValue,
--           exampleEnumOperFreeEnumReplicatedRowStatus,
--           exampleMiscellaneousOperFreeLong,
--           exampleIpAddressProvFreeIpAddressArray1Value,
--           exampleDecimalProvDecimalSub,
--           exampleEnumOperFreeEnumArrayValue,
--           exampleBcdOperFreeBcdReplicatedRowStatus,
--           exampleDecimalPfIntListRowStatus,
--           friDynOpStorageType,
--           friPfListUnsignedValue,
--           exampleIpAddressOperFreeIpAddressVectorValue,
--           exampleOperStringSubCreatedRowStatus,
--           exampleMiscellaneousRowStatus,
--           exampleFixedPtProvStructFixedPt,
--           exampleDecimalProvFreeInteger1,
--           exampleOperEnumSubCreatedRowStatus,
--           friOperationalStructSimpleUnsigned,
--           friOperationalStructSimpleBcd,
--           exampleExtendedOperStructExtended,
--           exampleDecimalOfIntListRowStatus,
--           exampleOneIndexRowStatus,
--           exampleSequenceProvFreeSequence,
--           exampleDashedStorageType,
--           friAlarmStatus,
--           exampleOperFixedPtSubcomponentsCreatedValue,
--           friOperationalFreeSimpleSigned,
--           exampleDecimalPsIntArrayValue,
--           exampleObjIdIndicesRowStatus,
--           exampleHexProvStructHexArrayValue,
--           friDynOpOptionalRowStatus,
--           exampleFixedPtStorageType,
--           friOperationalFreeSimpleExtended,
--           exampleSequenceRowStatus,
--           friProvisionalFreeSimpleDashed,
--           exampleEnumIndicesComponentName,
--           friDnaTypeOfAddress,
--           exampleDecimalProvFreeInteger2,
--           exampleEnumIndicesProvAttribute,
--           friOperationalStructSimpleAscii,
--           exampleDashedOfDashedReplicatedRowStatus,
--           exampleSignedOperFreeSignedReplicatedRowStatus,
--           friOfListEnumerationValue,
--           exampleOperSignedSubCreatedValue,
--           exampleStringOperStructHexOnly,
--           friDynOpDynamicComponentName,
--           exampleDashedOfDashedArrayValue,
--           exampleSignedOperFreeSignedArrayValue,
--           friControlStatus,
--           exampleEnumProvStructEnumArrayValue,
--           exampleHexOfHexListRowStatus,
--           exampleHexProvFreeHexList1RowStatus,
--           friOperationalStructSimpleHex,
--           exampleIpAddressOperFreeIpAddressReplicatedValue,
--           exampleDecimalOperFreeGauge32,
--           exampleBcdProvStructBcdArrayValue,
--           exampleOperDecimalSubCreatedValue,
--           exampleTwoIndicesRowStatus,
--           exampleDecimalOperStructInteger,
--           exampleRequiredIndicesProvAttribute,
--           exampleDecimalProvFreeIntSet1,
--           exampleSequenceProvFreeSequenceListValue,
--           exampleHexProvFreeHexVectorValue,
--           exampleHexOsHexArrayValue,
--           exampleEnumProvFreeEnumList1RowStatus,
--           exampleStringOperFreeStrReplicatedRowStatus,
--           exampleFixedPtOperFreeFixedPtReplicatedValue,
--           exampleFixedPtOperStructFixedPtArrayValue,
--           exampleStringOperFreeStrArrayValue,
--           exampleWildBcdOperStructWildBcdArrayValue,
--           exampleMiscellaneousProvFreeTime,
--           exampleDashedProvFreeDashedListRowStatus,
--           exampleIpAddressProvFreeIpAddress1,
--           friDynamicRowStatus,
--           exampleMiscellaneousProvFreeTimeListValue,
--           exampleTwoIndicesStorageType,
--           exampleSignedOperFreeSignedVectorValue,
--           friPfListSignedValue,
--           exampleIpAddressOperStructIpAddress,
--           exampleEnumProvFreeEnumVectorValue,
--           exampleRequiredIndicesStorageType,
--           exampleSignedProvStructSignedArrayValue,
--           exampleBcdProvFreeBcdVectorValue,
--           friProvisionalFreeSimpleComponent,
--           exampleHexIndicesProvAttribute,
--           exampleExtendedProvFreeExtendedReplicatedRowStatus,
--           exampleFixedPtProvFreeFixedPtListRowStatus,
--           exampleIpAddressComponentName,
--           exampleStringProvFreeStrListValue,
--           exampleHexOperFreeHex,
--           exampleExtendedProvFreeExtendedArrayValue,
--           exampleMiscellaneousOperFreeLongReplicatedValue,
--           exampleObjectIdStorageType,
--           friProvisionalStructSimpleFixed,
--           friAdminState,
--           exampleSequenceOperFreeSequenceReplicatedRowStatus,
--           friOperationalFreeSimpleDashed,
--           exampleHexProvFreeHexReplicatedValue,
--           exampleFixedPtOperFreeFixedPtVectorValue,
--           exampleWildBcdOperFreeWildBcdVectorValue,
--           exampleStringComponentName,
--           exampleStringStorageType,
--           friDynOpAttribute,
--           exampleStringProvStructStrArrayValue,
--           friPfListUnsignedRowStatus,
--           exampleEnumOperFreeEnum,
--           exampleIpAddressProvFreeIpAddressListValue,
--           exampleEnumStorageType,
--           exampleIpAddressProvFreeIpAddressList1Value,
--           exampleHexIndicesStorageType,
--           exampleBcdStorageType,
--           exampleIpAddressProvEnumSub,
--           exampleBcdOperFreeBcd,
--           exampleExtendedRowStatus,
--           exampleExtendedOperFreeExtendedListRowStatus,
--           exampleRowStatus,
--           exampleDecimalStorageType,
--           exampleDecimalPfIntList1Value,
--           exampleMiscellaneousOperStructLong,
--           exampleObjectIdOperFreeObjId,
--           exampleDecimalIndicesProvAttribute,
--           exampleDashedProvStructDashedVectorValue,
--           exampleIpAddressOperStructIpAddressVectorValue,
--           exampleProvStringSubCreatedValue,
--           exampleStringProvFreeStrList1RowStatus,
--           exampleHexProvStructHex,
--           exampleProvEnumSubCreatedValue,
--           exampleBcdProvFreeBcdReplicatedValue,
--           exampleObjectIdProvFreeObjIdReplicatedValue,
--           exampleMiscellaneousProvFreeTimeList2Value,
--           exampleDashedOperFreeDashed,
--           exampleWildBcdComponentName,
--           friOperationalFreeSimpleComponent,
--           friRegisteredComponentName,
--           exampleDashedIndicesComponentName,
--           friDynOpDynOpJrRowStatus,
--           exampleStringOperFreeAsciiOnly,
--           exampleProvSignedSubCreatedRowStatus,
--           exampleWildBcdOperFreeWildBcdReplicatedValue,
--           exampleStringProvFreeStrVectorValue,
--           exampleWildBcdProvStructWildBcdVectorValue,
--           exampleSequenceIndicesProvAttribute,
--           exampleMiscellaneousProvFreeTimeList3Value,
--           exampleMiscellaneousOperFreeTimeTimeOnly,
--           exampleHexStrIndicesComponentName,
--           exampleEnumProvStructEnum,
--           exampleEnumOperFreeEnumListValue,
--           exampleIpAddressProvFreeIpAddressReplicatedRowStatus,
--           exampleDecimalIndicesStorageType,
--           exampleFourIndicesComponentName,
--           exampleProvDecimalSubCreatedRowStatus,
--           exampleBcdProvStructBcd,
--           exampleIpAddressProvFreeIpAddressArrayValue,
--           exampleDashedOperStructDashed,
--           exampleSignedProvFreeSignedReplicatedValue,
--           exampleFixedPtProvFreeFixedPtReplicatedValue,
--           friOperationalFreeSimpleObjId,
--           friUsageState,
--           exampleMiscellaneousOperFreeTimeDateTimeMinute,
--           exampleDashedOsDashedVectorValue,
--           exampleDecimalPfIntReplicatedRowStatus,
--           friPfListFixedRowStatus,
--           exampleObjectIdOperFreeObjIdListValue,
--           exampleDecimalPfIntArrayValue,
--           exampleSignedProvFreeSignedVectorValue,
--           exampleMiscellaneousProvFreeTimeList1Value,
--           friOperationalStructSimpleSequence,
--           friDynOpDynamicStorageType,
--           exampleSequenceIndicesStorageType,
--           exampleFixedPtOperStructFixedPt,
--           exampleDecimalOfIntReplicatedRowStatus,
--           exampleExtendedOperStructExtendedVectorValue,
--           friDnaDataNetworkAddress,
--           friEventComponentName,
--           exampleDecimalOperFreeTimeInterval,
--           exampleDecimalOfIntArrayValue,
--           friOfListComponentRowStatus,
--           friRowStatus,
--           friProvisionalStructSimpleExtended,
--           exampleStringProvStructAsciiOnly,
--           exampleStringProvFreeStrReplicatedValue,
--           exampleMiscellaneousProvFreeLongReplicatedValue,
--           exampleMiscellaneousProvEnumSub,
--           exampleSignedProvStructSigned,
--           exampleDashedRowStatus,
--           exampleEnumOperStructEnumSet,
--           friOperationalFreeSimpleBcd,
--           exampleWildBcdOperFreeWildBcdReplicatedRowStatus,
--           exampleHexProvFreeHexArray2Value,
--           exampleMiscellaneousProvFreeLongReplicatedRowStatus,
--           exampleExtendedProvFreeExtended,
--           exampleDecimalRowStatus,
--           exampleEnumProvFreeEnumSet1,
--           exampleHexOfHexReplicatedRowStatus,
--           exampleHexProvFreeHexReplicated1RowStatus,
--           friDynOpOptionalStorageType,
--           registeredStorageType,
--           friEscapeDefaultsComponent,
--           exampleHexOfHexArrayValue,
--           exampleHexProvFreeHexArray1Value,
--           exampleMiscellaneousProvFreeTimeReplicatedRowStatus,
--           exampleSequenceOperFreeSequence,
--           exampleHexComponentName,
--           friOperationalFreeSimpleAscii,
--           friDnaRowStatus,
--           friProvisionalFreeSimpleHex,
--           exampleStringOperFreeStrListValue,
--           exampleFixedPtProvStructFixedPtVectorValue,
--           exampleSequenceProvFreeSequenceReplicatedValue,
--           exampleStringProvFreeHexOnly,
--           exampleDashedIndicesRowStatus,
--           exampleEnumProvFreeEnumArray1Value,
--           exampleBcdProvFreeBcdReplicated1RowStatus,
--           friProceduralStatus,
--           exampleMiscellaneousOperFreeLongListRowStatus,
--           exampleEnumProvFreeEnumList1Value,
--           exampleIpAddressProvFreeIpAddressVector1Value,
--           exampleHexStrIndicesRowStatus,
--           exampleDashedProvFreeDashedArrayValue,
--           exampleBcdIndicesComponentName,
--           exampleEnumOperStructEnumArrayValue,
--           exampleDecimalProvFreeInteger,
--           exampleHexProvFreeHexListRowStatus,
--           exampleExtendedProvFreeExtendedListValue,
--           exampleBcdOperStructBcdArrayValue,
--           exampleMiscellaneousOperFreeTimeDateOnly,
--           exampleMiscellaneousOperFreeTimeListRowStatus,
--           exampleBcdOperFreeBcdListValue,
--           friDynOpDynamicAttribute,
--           friProvisionalStructSimpleDashed,
--           friPfListAsciiRowStatus,
--           exampleDecimalPfIntVector1Value,
--           registeredComponentName,
--           exampleFixedPtProvFreeFixedPtReplicatedRowStatus,
--           exampleDecimalProvFreeIntSet,
--           exampleWildBcdProvFreeWildBcdReplicatedRowStatus,
--           exampleWildBcdProvFreeWildBcd,
--           exampleDecimalComponentName,
--           exampleMiscellaneousComponentName,
--           exampleFixedPtProvFreeFixedPtArrayValue,
--           exampleThreeIndicesProvAttribute,
--           exampleWildBcdProvFreeWildBcdArrayValue,
--           exampleIpAddressStorageType,
--           exampleProvSignedSubCreatedValue,
--           friDynOpInitialComponentName,
--           exampleEnumProvFreeEnumListRowStatus,
--           friDynamicComponentName,
--           friDynOpInitialProvAttribute,
--           exampleOneIndexComponentName,
--           exampleBcdProvFreeBcdListRowStatus,
--           registeredRowStatus,
--           exampleIpAddressProvFreeIpAddress,
--           exampleWildBcdProvStructWildBcd,
--           exampleObjIdIndicesComponentName,
--           exampleObjectIdRowStatus,
--           exampleSignedProvFreeSignedArray1Value,
--           exampleSignedProvFreeSigned,
--           exampleDashedProvFreeDashedReplicatedRowStatus,
--           exampleHexStrIndicesProvAttribute,
--           exampleObjectIdProvFreeObjIdListRowStatus,
--           exampleEnumOperFreeEnumVectorValue,
--           exampleProvMyComponentName,
--           friProvisionalStructSimpleEnum,
--           exampleSignedOperStructSignedArrayValue,
--           exampleExtendedOperFreeExtendedArrayValue,
--           exampleBcdOperFreeBcdVectorValue,
--           exampleThreeIndicesStorageType,
--           exampleExtendedOperFreeExtendedReplicatedRowStatus,
--           exampleFixedPtOperFreeFixedPtListRowStatus,
--           exampleWildBcdOperFreeWildBcdListRowStatus,
--           exampleThreeIndicesComponentName,
--           exampleEnumRowStatus,
--           exampleEnumProvFreeEnumReplicatedValue,
--           exampleDecimalPfIntReplicated1Value,
--           exampleHexIndicesRowStatus,
--           exampleBcdRowStatus,
--           exampleEnumProvStructEnumSet,
--           exampleExtendedProvStructExtendedVectorValue,
--           exampleSignedProvSignedSub,
--           exampleIpAddrIndicesComponentName,
--           exampleDecimalPsIntVectorValue,
--           exampleMiscellaneousProvFreeTimeDateOnly1,
--           friDynOpDynamicRowStatus,
--           exampleHexProvStructHexVectorValue,
--           exampleSignedProvFreeSignedListRowStatus,
--           exampleEnumProvFreeEnumSet,
--           friOperationalStructSimpleEnum,
--           exampleBcdOperFreeBcdArrayValue,
--           exampleStringOperStructStrArrayValue,
--           exampleDecimalOsIntVectorValue,
--           exampleMiscellaneousProvFreeTime1,
--           exampleDashedOfDashedListRowStatus,
--           exampleWildBcdProvFreeWildBcdListRowStatus }
-- STATUS  mandatory
-- DESCRIPTION
--   "A list of all current accessible leaf objects."

casTestGroup OBJECT IDENTIFIER ::= { casTestMIB 1 }
casTestGroupBE OBJECT IDENTIFIER ::= { casTestGroup 5 }
casTestGroupBE01 OBJECT IDENTIFIER ::= { casTestGroupBE 2 }
casTestGroupBE01A OBJECT IDENTIFIER ::= { casTestGroupBE01 2 }



-- Agent-Capabilities Statement:

-- PRODUCT-RELEASE "Passport Release 7.0 CasTest."
-- STATUS          mandatory
-- DESCRIPTION     "CasTest MIB: MIB Version BE01A,
--                  Software Version BG00S4C."
-- SUPPORTS        Nortel-Magellan-Passport-CasTestMIB
--    INCLUDES     { casTestGroupBE01A }

casTestCapabilities OBJECT IDENTIFIER ::= { casTestMIB 3 }
casTestCapabilitiesBE OBJECT IDENTIFIER ::= { casTestCapabilities 5 }
casTestCapabilitiesBE01 OBJECT IDENTIFIER ::= { casTestCapabilitiesBE 2 }
casTestCapabilitiesBE01A OBJECT IDENTIFIER ::= { casTestCapabilitiesBE01 2 }





END
