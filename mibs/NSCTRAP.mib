-- *****************************************
    -- Network System Corporation Enterprise MIB
    -- *****************************************
    --
    -- Title:           NSCTRAP
    -- Purpose:         This MIB defines traps which are common to more 
    --                  than one NSC product.
    -- Required MIBs:   None.
    --
    -- Version:         1.1
    -- 1st revision:    July  9, 1994      luray@network.com
    -- last changed:    June 28, 1995      luray@network.com


    NSCTRAP DEFINITIONS ::= BEGIN


    IMPORTS
        enterprises               FROM RFC1155-SMI
        OBJECT-TYPE               FROM RFC-1212
        TRAP-TYPE                 FROM RFC-1215
        ifIndex, ifDescr, ifType  FROM RFC1213-MIB
        DisplayString             FROM RFC1213-MIB;


    nsc            OBJECT IDENTIFIER ::= { enterprises 10 }
    nscMib         OBJECT IDENTIFIER ::= { nsc 2 }
    nscManagement  OBJECT IDENTIFIER ::= { nscMib 2 }
    nscTraps       OBJECT IDENTIFIER ::= { nscManagement 4 }


    --
    -- Textual Conventions
    --

    nscTrapsProtBindIndex  OBJECT-TYPE
	SYNTAX		INTEGER {
                            ip                (1),
                            decnet            (2),
                            appleTalk         (3),
                            ipx               (4),
                            xns               (5),
                            bridging          (9),  -- Unencapsulated Bridging
                            bridgingEc       (10)   -- Encapsulated Bridging
                        }
	ACCESS		not-accessible
	STATUS		mandatory
	DESCRIPTION	"The communication protocols whose bind state changes
                         would cause traps to be generated. "
	::= {nscTraps 1}

    nscTrapsFddiSMTCFState  OBJECT-TYPE
	SYNTAX		INTEGER {
                            cf0 (1),  -- Isolated
                            cf1 (2),  -- Wrap_S
                            cf2 (3),  -- Wrap_A
                            cf3 (4),  -- Wrap_B
                            cf4 (5),  -- Wrap_AB
                            cf5 (6)   -- Thru
                        }
	ACCESS		not-accessible
	STATUS		mandatory
	DESCRIPTION	"The attachment configuration for the station or
			 concentrator. The values are the same as those 
                         defined in the SMT group in RFC-1285."
	::= {nscTraps 2}


    --
    -- The following objects are defined for DECnet traps. 
    --

    nscTrapsDecNetAreaNbr OBJECT-TYPE
        SYNTAX OCTET STRING (SIZE (1))
        ACCESS not-accessible
        STATUS mandatory
        DESCRIPTION
            ""
    ::= { nscTraps 3 }
 

    nscTrapsDecNetNodeNbr OBJECT-TYPE
        SYNTAX OCTET STRING (SIZE (1))
        ACCESS not-accessible
        STATUS mandatory
        DESCRIPTION
            ""
    ::= { nscTraps 4 }


    nscTrapsDecNetCircuitName OBJECT-TYPE
        SYNTAX DisplayString (SIZE (0..6))
        ACCESS not-accessible
        STATUS mandatory
        DESCRIPTION
            "The name of a DECnet circuit. "
    ::= { nscTraps 5 }
 
    nscTrapsDecNetEventReason OBJECT-TYPE
        SYNTAX DisplayString (SIZE (1..256))
        ACCESS not-accessible
        STATUS mandatory
        DESCRIPTION
            "The reason that causes the routing event to
             happen. Possible reasons are:
               SYNC_LOST                            (0),                      
               DATA_ERRORS                          (1),                      
               UNEXPECTED_PKT_TYPE                  (2),                      
               ROUTING_UPDATE_CHECKSUM_ERROR        (3),                      
               ADJ_ADDR_CHANGE                      (4),                      
               VERIF_RECV_TIMEOUT                   (5),                      
               VERSION_SKEW                         (6),                      
               ADJ_ADDR_OUT_OF_RANGE                (7),                      
               ADJ_BLOCK_SIZE_TOO_SMALL             (8),                      
               INVALID_VERIF_SEED_VALUE             (9),                      
               ADJ_LIST_RECV_TIMEOUT               (10),                      
               ADJ_LIST_RECV_INVALID_DATA          (11),                      
               CALL_FAILED                         (12),                      
               VERIF_PASSWORD_REQ_FROM_PIII_NODE   (13),                      
               DROPPED_BY_ADJ_NODE                 (14)."
    ::= { nscTraps 6 }

    nscTrapsDecNetReachStatus OBJECT-TYPE
        SYNTAX INTEGER {
                 reachable      (1),
                 unreachable    (2)
        }
        ACCESS not-accessible
        STATUS mandatory
        DESCRIPTION
            "The reachable status of a node or area."
    ::= { nscTraps 7 }

    nscTrapsVcpPortName OBJECT-TYPE
        SYNTAX DisplayString (SIZE (0..12))   
        ACCESS not-accessible
        STATUS mandatory
        DESCRIPTION
            "The name of the VCP port."         
    ::= { nscTraps 8 }

    nscTrapsVcpLogicalState OBJECT-TYPE
        SYNTAX DisplayString (SIZE (0..30))    
        ACCESS not-accessible
        STATUS mandatory
        DESCRIPTION
            "The logical state of a VCP port. The possible states 
             are ACTIVE, DOWN, DISABLED."  
    ::= { nscTraps 9 }

    nscTrapsVcpPhysicalState OBJECT-TYPE
        SYNTAX DisplayString (SIZE (0..30))
        ACCESS not-accessible
        STATUS mandatory
        DESCRIPTION
            "The physical state of a VCP port.  The possible states
             are Off, On, Broken_Cannot_IO, Broken_Purge, 
             Broken_Reconfigure, Broken_Misconfigure."  
    ::= { nscTraps 10 }


    -- *****************************************************************
    --                    NSC Enterprise Traps
    --
    --  The following traps are defined to be used accross the NSC 
    --  hardware platforms. Traps that are specific to certain platforms
    --  are defined in separated files.
    -- *****************************************************************

    protocolBound TRAP-TYPE
        ENTERPRISE  nscTraps
        VARIABLES   { ifIndex, ifDescr, ifType, nscTrapsProtBindIndex }
        DESCRIPTION
            "A protocolBound trap is sent when a protocol is bound
             to an interface."
    ::= 1

    protocolUnbound TRAP-TYPE
        ENTERPRISE  nscTraps
        VARIABLES   { ifIndex, ifDescr, ifType, nscTrapsProtBindIndex }
        DESCRIPTION
            "A protocolBound trap is sent when a protocol is unbound
             from an interface."
    ::= 2

    physicalLinkUp TRAP-TYPE
        ENTERPRISE  nscTraps
        VARIABLES   { ifIndex, ifDescr, ifType  }
        DESCRIPTION
            "A physicalLinkUp trap is sent for devices that
             represent both a logical and physical device.  The
             physicalLinkUp trap is sent when the physical device
             becomes active.  The SNMP linkUp is sent when the
             logical device becomes active."
    ::= 3

    physicalLinkDown TRAP-TYPE
        ENTERPRISE  nscTraps
        VARIABLES   { ifIndex, ifDescr, ifType  }
        DESCRIPTION
            "A physicalLinkDown trap is sent for devices that
             represent both a logical and physical device.  The
             physicalLinkDown trap is sent when the physical device
             becomes not active.  The SNMP linkDown is sent when
             the logical device becomes not active."
    ::= 4

    fddiWrap TRAP-TYPE
        ENTERPRISE  nscTraps
        VARIABLES   { ifIndex, nscTrapsFddiSMTCFState }
        DESCRIPTION
            "A FDDI wrap trap indicates that a FDDI ring is broken
             and the signal path wraps through a device and out the 
             parallel fiber. The trap also occures when the wrapped 
             condition is relieved."
    ::= 5


    -- *****************************************************************
    --
    -- Trap IDs from 6 to 10 are reserved for VCP physical link traps.
    --
    -- *****************************************************************


    vcpActive TRAP-TYPE
        ENTERPRISE  nscTraps
        VARIABLES   { nscTrapsVcpPortName,
                      nscTrapsVcpLogicalState,
                      nscTrapsVcpPhysicalState }
        DESCRIPTION
            "This trap indicates that a VCP physical link just came up."
    ::= 6

    vcpInactive TRAP-TYPE
        ENTERPRISE  nscTraps
        VARIABLES   { nscTrapsVcpPortName,
                      nscTrapsVcpLogicalState,
                      nscTrapsVcpPhysicalState }
        DESCRIPTION
            "This trap indicates that a VCP physical link just went down."
    ::= 7

    vcpReconfig TRAP-TYPE
        ENTERPRISE  nscTraps
        VARIABLES   { nscTrapsVcpPortName,
                      nscTrapsVcpLogicalState,
                      nscTrapsVcpPhysicalState }
        DESCRIPTION
            "This trap indicates that a VCP physical link is reconfiguring."
    ::= 8

    vcpBroken TRAP-TYPE
        ENTERPRISE  nscTraps
        VARIABLES   { nscTrapsVcpPortName,
                      nscTrapsVcpLogicalState,
                      nscTrapsVcpPhysicalState }
        DESCRIPTION
            "This trap indicates that a VCP physical link lost connection 
             with its remote end."
    ::= 9

    vcpMisconfigured TRAP-TYPE
        ENTERPRISE  nscTraps
        VARIABLES   { nscTrapsVcpPortName }
        DESCRIPTION
            "This trap indicates that a VCP physical link has detected 
             different configuration on the remote end."
    ::= 10


    -- *****************************************************************
    --
    -- Trap IDs from 400 to 450 are reserved for DECnet traps.
    -- The trap IDs are assigned to reflect the internal 
    -- DECnet message numbers for the DECnet events; 
    --         407  -  4.7, 
    --         408  -  4.8,
    --         410  -  4.10, 
    --         414  -  4.14,
    --         415  -  4.15,
    --         416  -  4.16,
    --         417  -  4.17,
    --         418  -  4.18,
    --         422.
    --
    -- *****************************************************************


    decNetCircDownFault TRAP-TYPE
        ENTERPRISE  nscTraps
        VARIABLES { nscTrapsDecNetAreaNbr, 
                    nscTrapsDecNetNodeNbr,
                    nscTrapsDecNetCircuitName, 
                    nscTrapsDecNetEventReason }
        DESCRIPTION
             "This trap shows that a fault has brought down 
              the indicated DECnet circuit."
    ::= 407


    decNetCircDown TRAP-TYPE
        ENTERPRISE  nscTraps
        VARIABLES { nscTrapsDecNetAreaNbr, 
                    nscTrapsDecNetNodeNbr,
                    nscTrapsDecNetCircuitName, 
                    nscTrapsDecNetEventReason }
        DESCRIPTION
             "This trap indicates that the named DECnet circuit
              is down. (This trap is not supported.)"
    ::= 408


    decNetCircUp TRAP-TYPE
        ENTERPRISE  nscTraps
        VARIABLES { nscTrapsDecNetAreaNbr, 
                    nscTrapsDecNetNodeNbr,
                    nscTrapsDecNetCircuitName }
        DESCRIPTION
             "This trap indicates that a DECnet circuit has
               become enabled."
    ::= 410


    decNetNodeReachChg TRAP-TYPE
        ENTERPRISE  nscTraps
        VARIABLES { nscTrapsDecNetNodeNbr,
                    nscTrapsDecNetReachStatus }
        DESCRIPTION
             "This trap reports a change in the nodes that can be 
              reached. (This trap is not supported.)"
    ::= 414


    decNetAdjUp TRAP-TYPE
        ENTERPRISE  nscTraps
        VARIABLES { nscTrapsDecNetAreaNbr, 
                    nscTrapsDecNetNodeNbr,
                    nscTrapsDecNetCircuitName  }
        DESCRIPTION
	     "This trap indicates that a DECnet adjacent node 
              just has come up."
    ::= 415


    decNetAdjRejected TRAP-TYPE
        ENTERPRISE  nscTraps
        VARIABLES { nscTrapsDecNetAreaNbr, 
                    nscTrapsDecNetNodeNbr,
                    nscTrapsDecNetCircuitName, 
                    nscTrapsDecNetEventReason }
        DESCRIPTION
             "This trap indicates that an adjacent node has 
              been rejected of communication, or become inactive. 
              The reason could be either the numbers of broadcast 
              (non)routers or the address of a node exceeds the 
              ones in the router's configuartion. "
    ::= 416


    decNetAreaReachChg TRAP-TYPE
        ENTERPRISE  nscTraps
        VARIABLES { nscTrapsDecNetAreaNbr,
                    nscTrapsDecNetReachStatus }
        DESCRIPTION
             "This trap reports a change in the areas that can be 
              reached. (This trap is not supported.)"
    ::= 417


    decNetAdjDown TRAP-TYPE
        ENTERPRISE  nscTraps
        VARIABLES { nscTrapsDecNetAreaNbr, 
                    nscTrapsDecNetNodeNbr,
                    nscTrapsDecNetCircuitName, 
                    nscTrapsDecNetEventReason }
        DESCRIPTION
             "This trap indicates that a adjacent node has
              come down or lost."
    ::= 418


    decNetDesignatedRouter TRAP-TYPE
        ENTERPRISE  nscTraps
        VARIABLES { nscTrapsDecNetAreaNbr,
                    nscTrapsDecNetNodeNbr,
                    nscTrapsDecNetCircuitName }
        DESCRIPTION
             "This trap reports a change in the designated router."
    ::= 422


    -- End of DECnet traps.


   END
