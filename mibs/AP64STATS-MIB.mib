AP64STATS-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Counter64, TimeTicks
			FROM SNMPv2-SMI
        Gauge
            FROM RFC1155-SMI
		DisplayString
			FROM SNMPv2-TC
		ap64Stats
			FROM APENT-MIB;

--AP64STATS MIB

    ap64StatsMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "This MIB module contains 64 bit statistical aggregation of the 
       RMON (RFC1757), MIBII (RFC1213) and EtherErrors (RFC1398)"
      ::= { ap64Stats 1}

    PhysAddress ::=
           OCTET STRING

    OwnerString ::= DisplayString

     EntryStatus ::= INTEGER
                         { valid(1),
                           createRequest(2),
                           underCreation(3),
                           invalid(4)
                         }

ap64dot3StatsTable   OBJECT-TYPE
	SYNTAX     SEQUENCE OF AP64Dot3StatsEntry
	MAX-ACCESS not-accessible
	STATUS     current
	DESCRIPTION
		"Statistics for a collection of ethernet-like
		interfaces attached to a particular system."
	::= { ap64Stats 2 }

ap64dot3StatsEntry   OBJECT-TYPE
	SYNTAX     AP64Dot3StatsEntry
	MAX-ACCESS not-accessible
	STATUS     current
	DESCRIPTION
		"Statistics for a particular interface to an
		ethernet-like medium."
	INDEX     { ap64dot3StatsIndex }
	::= { ap64dot3StatsTable 1 }

AP64Dot3StatsEntry ::= SEQUENCE {
	ap64dot3StatsIndex 	                    INTEGER,
	ap64dot3StatsAlignmentErrors            Counter64,
	ap64dot3StatsFCSErrors                  Counter64,
	ap64dot3StatsSingleCollisionFrames      Counter64,
	ap64dot3StatsMultipleCollisionFrames    Counter64,
	ap64dot3StatsSQETestErrors              Counter64,
	ap64dot3StatsDeferredTransmissions      Counter64,
	ap64dot3StatsLateCollisions             Counter64,
	ap64dot3StatsExcessiveCollisions        Counter64,
	ap64dot3StatsInternalMacTransmitErrors  Counter64,
	ap64dot3StatsCarrierSenseErrors         Counter64,
	ap64dot3StatsFrameTooLongs              Counter64,
	ap64dot3StatsInternalMacReceiveErrors   Counter64
	}

ap64dot3StatsIndex   OBJECT-TYPE
	SYNTAX     INTEGER
	MAX-ACCESS read-only
	STATUS     current
	DESCRIPTION
	          "An index value that uniquely identifies an
	          interface to an ethernet-like medium.  The
	          interface identified by a particular value of
	          this index is the same interface as identified
	          by the same value of ifIndex."
	::= { ap64dot3StatsEntry 1 }

ap64dot3StatsAlignmentErrors   OBJECT-TYPE
	SYNTAX     Counter64
	MAX-ACCESS read-only
	STATUS     current
	DESCRIPTION
	          "A count of frames received on a particular
	          interface that are not an integral number of
	          octets in length and do not pass the FCS check.
	           The count represented by an instance of this
	          object is incremented when the alignmentError
	          status is returned by the MAC service to the
	          LLC (or other MAC user). Received frames for
	          which multiple error conditions obtain are,
	          according to the conventions of IEEE 802.3
	          Layer Management, counted exclusively according
	          to the error status presented to the LLC."
	REFERENCE
	          "IEEE 802.3 Layer Management"
	::= { ap64dot3StatsEntry 2 }

ap64dot3StatsFCSErrors   OBJECT-TYPE
	SYNTAX     Counter64
	MAX-ACCESS read-only
	STATUS     current
	DESCRIPTION
	          "A count of frames received on a particular
	          interface that are an integral number of octets
	          in length but do not pass the FCS check.
	           The count represented by an instance of this
	          object is incremented when the frameCheckError
	          status is returned by the MAC service to the
	          LLC (or other MAC user). Received frames for
	          which multiple error conditions obtain are,
	          according to the conventions of IEEE 802.3
	          Layer Management, counted exclusively according
	          to the error status presented to the LLC."
	REFERENCE
	          "IEEE 802.3 Layer Management"
	::= { ap64dot3StatsEntry 3 }

ap64dot3StatsSingleCollisionFrames   OBJECT-TYPE
	SYNTAX     Counter64
	MAX-ACCESS read-only
	STATUS     current
	DESCRIPTION
	          "A count of successfully transmitted frames on
	          a particular interface for which transmission
	          is inhibited by exactly one collision.
	           A frame that is counted by an instance of this
	          object is also counted by the corresponding
	          instance of either the ifOutUcastPkts or
	          ifOutNUcastPkts object and is not counted by
	          the corresponding instance of the
	          ap64dot3StatsMultipleCollisionFrames object."
	REFERENCE
	          "IEEE 802.3 Layer Management"
	::= { ap64dot3StatsEntry 4 }

ap64dot3StatsMultipleCollisionFrames   OBJECT-TYPE
	SYNTAX     Counter64
	MAX-ACCESS read-only
	STATUS     current
	DESCRIPTION
	          "A count of successfully transmitted frames on
	          a particular interface for which transmission
	          is inhibited by more than one collision.
	           A frame that is counted by an instance of this
	          object is also counted by the corresponding
	          instance of either the ifOutUcastPkts or
	          ifOutNUcastPkts object and is not counted by
	          the corresponding instance of the
	          ap64dot3StatsSingleCollisionFrames object."
	REFERENCE
	          "IEEE 802.3 Layer Management"
	::= { ap64dot3StatsEntry 5 }

ap64dot3StatsSQETestErrors   OBJECT-TYPE
	SYNTAX     Counter64
	MAX-ACCESS read-only
	STATUS     current
	DESCRIPTION
	          "A count of times that the SQE TEST ERROR
	          message is generated by the PLS sublayer for a
	          particular interface. The SQE TEST ERROR
	          message is defined in section 7.2.2.2.4 of
	          ANSI/IEEE 802.3-1985 and its generation is
	          described in section 7.2.4.6 of the same
	          document."
	REFERENCE
	          "ANSI/IEEE Std 802.3-1985 Carrier Sense
	          Multiple Access with Collision Detection Access
	          Method and Physical Layer Specifications"
	::= { ap64dot3StatsEntry 6 }

ap64dot3StatsDeferredTransmissions   OBJECT-TYPE
	SYNTAX     Counter64
	MAX-ACCESS read-only
	STATUS     current
	DESCRIPTION
	          "A count of frames for which the first
	          transmission attempt on a particular interface
	          is delayed because the medium is busy.
	           The count represented by an instance of this
	          object does not include frames involved in
	          collisions."
	REFERENCE
	          "IEEE 802.3 Layer Management"
	::= { ap64dot3StatsEntry 7 }

ap64dot3StatsLateCollisions   OBJECT-TYPE
	SYNTAX     Counter64
	MAX-ACCESS read-only
	STATUS     current
	DESCRIPTION
	          "The number of times that a collision is
	          detected on a particular interface later than
	          512 bit-times into the transmission of a
	          packet.
	           Five hundred and twelve bit-times corresponds
	          to 51.2 microseconds on a 10 Mbit/s system. A
	          (late) collision included in a count
	          represented by an instance of this object is
	          also considered as a (generic) collision for
	          purposes of other collision-related
	          statistics."
	REFERENCE
	          "IEEE 802.3 Layer Management"
	::= { ap64dot3StatsEntry 8 }

ap64dot3StatsExcessiveCollisions   OBJECT-TYPE
	SYNTAX     Counter64
	MAX-ACCESS read-only
	STATUS     current
	DESCRIPTION
	          "A count of frames for which transmission on a
	          particular interface fails due to excessive
	          collisions."
	 REFERENCE
	          "IEEE 802.3 Layer Management"
	::= { ap64dot3StatsEntry 9 }

ap64dot3StatsInternalMacTransmitErrors   OBJECT-TYPE
	SYNTAX     Counter64
	MAX-ACCESS read-only
	STATUS     current
	DESCRIPTION
	          "A count of frames for which transmission on a
	          particular interface fails due to an internal
	          MAC sublayer transmit error. A frame is only
	          counted by an instance of this object if it is
	          not counted by the corresponding instance of
	          either the ap64dot3StatsLateCollisions object, the
	          ap64dot3StatsExcessiveCollisions object, or the
	          ap64dot3StatsCarrierSenseErrors object.
	           The precise meaning of the count represented by
	          an instance of this object is implementation-
	          specific.  In particular, an instance of this
	          object may represent a count of transmission
	          errors on a particular interface that are not
	          otherwise counted."
	REFERENCE
	          "IEEE 802.3 Layer Management"
	::= { ap64dot3StatsEntry 10 }

ap64dot3StatsCarrierSenseErrors   OBJECT-TYPE
	SYNTAX     Counter64
	MAX-ACCESS read-only
	STATUS     current
	DESCRIPTION
	          "The number of times that the carrier sense
	          condition was lost or never asserted when
	          attempting to transmit a frame on a particular
	          interface.
	           The count represented by an instance of this
	          object is incremented at most once per
	          transmission attempt, even if the carrier sense
	          condition fluctuates during a transmission
	          attempt."
	REFERENCE
	          "IEEE 802.3 Layer Management"
	::= { ap64dot3StatsEntry 11 }

ap64dot3StatsFrameTooLongs   OBJECT-TYPE
	SYNTAX     Counter64
	MAX-ACCESS read-only
	STATUS     current
	DESCRIPTION
	          "A count of frames received on a particular
	          interface that exceed the maximum permitted
	          frame size.
	           The count represented by an instance of this
	          object is incremented when the frameTooLong
	          status is returned by the MAC service to the
	          LLC (or other MAC user). Received frames for
	          which multiple error conditions obtain are,
	          according to the conventions of IEEE 802.3
	          Layer Management, counted exclusively according
	          to the error status presented to the LLC."
	REFERENCE
	          "IEEE 802.3 Layer Management"
	::= { ap64dot3StatsEntry 13 }

ap64dot3StatsInternalMacReceiveErrors   OBJECT-TYPE
	SYNTAX     Counter64
	MAX-ACCESS read-only
	STATUS     current
	DESCRIPTION
	          "A count of frames for which reception on a
	          particular interface fails due to an internal
	          MAC sublayer receive error. A frame is only
	          counted by an instance of this object if it is
	          not counted by the corresponding instance of
	          either the ap64dot3StatsFrameTooLongs object, the
	          ap64dot3StatsAlignmentErrors object, or the
	          ap64dot3StatsFCSErrors object.
	           The precise meaning of the count represented by
	          an instance of this object is implementation-
	          specific.  In particular, an instance of this
	          object may represent a count of receive errors
	          on a particular interface that are not
	          otherwise counted."
	REFERENCE
	          "IEEE 802.3 Layer Management"
	::= { ap64dot3StatsEntry 16 }


ap64ifTable OBJECT-TYPE
		SYNTAX  SEQUENCE OF AP64IfEntry
		MAX-ACCESS  not-accessible
		STATUS  current
		DESCRIPTION
			"A list of interface entries.  The number of
			entries is given by the value of ifNumber."
		::= { ap64Stats 3 }

ap64ifEntry OBJECT-TYPE
		SYNTAX  AP64IfEntry
		MAX-ACCESS  not-accessible
		STATUS  current
		DESCRIPTION
			"An interface entry containing objects at the
			subnetwork layer and below for a particular
			interface."
		INDEX   { ap64ifIndex }
		::= { ap64ifTable 1 }

AP64IfEntry ::=	SEQUENCE {
	ap64ifIndex                      INTEGER,
	ap64ifDescr                      DisplayString,
	ap64ifType                       INTEGER,
	ap64ifMtu                        INTEGER,
	ap64ifSpeed                      Gauge,
	ap64ifPhysAddress                PhysAddress,
	ap64ifAdminStatus                INTEGER,
	ap64ifOperStatus                 INTEGER,
	ap64ifLastChange                 TimeTicks,
	ap64ifInOctets                   Counter64,
	ap64ifInUcastPkts                Counter64,
	ap64ifInNUcastPkts               Counter64,
	ap64ifInDiscards                 Counter64,
	ap64ifInErrors                   Counter64,
	ap64ifInUnknownProtos            Counter64,
	ap64ifOutOctets                  Counter64,
	ap64ifOutUcastPkts               Counter64,
	ap64ifOutNUcastPkts              Counter64,
	ap64ifOutDiscards                Counter64,
	ap64ifOutErrors                  Counter64,
	ap64ifOutQLen                    Gauge,
	ap64ifSpecific                   OBJECT IDENTIFIER
	}

ap64ifIndex OBJECT-TYPE
	SYNTAX  INTEGER
	MAX-ACCESS  read-only
	STATUS  current
	DESCRIPTION
		"A unique value for each interface.  Its value
		ranges between 1 and the value of ifNumber.  The
		value for each interface must remain constant at
		least from one re-initialization of the entity's
		network management system to the next re-
		initialization."
	::= { ap64ifEntry 1 }

ap64ifDescr OBJECT-TYPE
	SYNTAX  DisplayString (SIZE (0..255))
	MAX-ACCESS  read-only
	STATUS  current
	DESCRIPTION
		"A textual string containing information about the
		interface.  This string should include the name of
		the manufacturer, the product name and the version
		of the hardware interface."
	::= { ap64ifEntry 2 }

ap64ifType OBJECT-TYPE
	SYNTAX  INTEGER {
		other(1),          -- none of the following
		regular1822(2),
		hdh1822(3),
		ddn-x25(4),
		rfc877-x25(5),
		ethernet-csmacd(6),
		iso88023-csmacd(7),
		iso88024-tokenBus(8),
		iso88025-tokenRing(9),
		iso88026-man(10),
		starLan(11),
		proteon-10Mbit(12),
		proteon-80Mbit(13),
		hyperchannel(14),
		fddi(15),
		lapb(16),
		sdlc(17),
		ds1(18),           -- T-1
		e1(19),            -- european equiv. of T-1
		basicISDN(20),
		primaryISDN(21),   -- proprietary serial
		propPointToPointSerial(22),
		ppp(23),
		softwareLoopback(24),
		eon(25),            -- CLNP over IP [11]
		ethernet-3Mbit(26),
		nsip(27),           -- XNS over IP
		slip(28),           -- generic SLIP
		ultra(29),          -- ULTRA technologies
		ds3(30),            -- T-3
		sip(31),            -- SMDS
		frame-relay(32)
	}
	MAX-ACCESS  read-only
	STATUS  current
	DESCRIPTION
		"The type of interface, distinguished according to
		the physical/link protocol(s) immediately `below'
		the network layer in the protocol stack."
		::= { ap64ifEntry 3 }

ap64ifMtu OBJECT-TYPE
	SYNTAX  INTEGER
	MAX-ACCESS  read-only
	STATUS  current
	DESCRIPTION
		"The size of the largest datagram which can be
		sent/received on the interface, specified in
		octets.  For interfaces that are used for
		transmitting network datagrams, this is the size
		of the largest network datagram that can be sent
		on the interface."
	::= { ap64ifEntry 4 }

ap64ifSpeed OBJECT-TYPE
	SYNTAX  Gauge
	MAX-ACCESS  read-only
	STATUS  current
	DESCRIPTION
	        "An estimate of the interface's current bandwidth
	        in bits per second.  For interfaces which do not
	        vary in bandwidth or for those where no accurate
	        estimation can be made, this object should contain
	        the nominal bandwidth."
	::= { ap64ifEntry 5 }

ap64ifPhysAddress OBJECT-TYPE
	SYNTAX  PhysAddress
	MAX-ACCESS  read-only
	STATUS  current
	DESCRIPTION
	        "The interface's address at the protocol layer
	        immediately `below' the network layer in the
	        protocol stack.  For interfaces which do not have
	        such an address (e.g., a serial line), this object
	        should contain an octet string of zero length."
	::= { ap64ifEntry 6 }

ap64ifAdminStatus OBJECT-TYPE
	SYNTAX  INTEGER {
	            up(1),       -- ready to pass packets
	            down(2),
	            testing(3)   -- in some test mode
	        }
	MAX-ACCESS  read-only
	STATUS  current
	DESCRIPTION
	        "The desired state of the interface.  The
	        testing(3) state indicates that no operational
	        packets can be passed."
	::= { ap64ifEntry 7 }

ap64ifOperStatus OBJECT-TYPE
	SYNTAX  INTEGER {
	            up(1),       -- ready to pass packets
	            down(2),
	            testing(3)   -- in some test mode
	        }
	MAX-ACCESS  read-only
	STATUS  current
	DESCRIPTION
	        "The current operational state of the interface.
	        The testing(3) state indicates that no operational
	        packets can be passed."
	::= { ap64ifEntry 8 }

ap64ifLastChange OBJECT-TYPE
	SYNTAX  TimeTicks
	MAX-ACCESS  read-only
	STATUS  current
	DESCRIPTION
	        "The value of sysUpTime at the time the interface
	        entered its current operational state.  If the
	        current state was entered prior to the last re-
	        initialization of the local network management
	        subsystem, then this object contains a zero
	        value."
	::= { ap64ifEntry 9 }

ap64ifInOctets OBJECT-TYPE
	SYNTAX  Counter64
	MAX-ACCESS  read-only
	STATUS  current
	DESCRIPTION
	        "The total number of octets received on the
	        interface, including framing characters."
	::= { ap64ifEntry 10 }

ap64ifInUcastPkts OBJECT-TYPE
	SYNTAX  Counter64
	MAX-ACCESS  read-only
	STATUS  current
	DESCRIPTION
	        "The number of subnetwork-unicast packets
	        delivered to a higher-layer protocol."
	::= { ap64ifEntry 11 }

ap64ifInNUcastPkts OBJECT-TYPE
	SYNTAX  Counter64
	MAX-ACCESS  read-only
	STATUS  current
	DESCRIPTION
	        "The number of non-unicast (i.e., subnetwork-
	        broadcast or subnetwork-multicast) packets
	        delivered to a higher-layer protocol."
	::= { ap64ifEntry 12 }

ap64ifInDiscards OBJECT-TYPE
	SYNTAX  Counter64
	MAX-ACCESS  read-only
	STATUS  current
	DESCRIPTION
	        "The number of inbound packets which were chosen
	        to be discarded even though no errors had been
	        detected to prevent their being deliverable to a
	        higher-layer protocol.  One possible reason for
	        discarding such a packet could be to free up
	        buffer space."
	::= { ap64ifEntry 13 }

ap64ifInErrors OBJECT-TYPE
	SYNTAX  Counter64
	MAX-ACCESS  read-only
	STATUS  current
	DESCRIPTION
	        "The number of inbound packets that contained
	        errors preventing them from being deliverable to a
	        higher-layer protocol."
	::= { ap64ifEntry 14 }


ap64ifInUnknownProtos OBJECT-TYPE
	SYNTAX  Counter64
	MAX-ACCESS  read-only
	STATUS  current
	DESCRIPTION
	        "The number of packets received via the interface
	        which were discarded because of an unknown or
	        unsupported protocol."
	::= { ap64ifEntry 15 }

ap64ifOutOctets OBJECT-TYPE
	SYNTAX  Counter64
	MAX-ACCESS  read-only
	STATUS  current
	DESCRIPTION
	        "The total number of octets transmitted out of the
	        interface, including framing characters."
	::= { ap64ifEntry 16 }

ap64ifOutUcastPkts OBJECT-TYPE
	SYNTAX  Counter64
	MAX-ACCESS  read-only
	STATUS  current
	DESCRIPTION
	        "The total number of packets that higher-level
	        protocols requested be transmitted to a
	        subnetwork-unicast address, including those that
	        were discarded or not sent."
	::= { ap64ifEntry 17 }

ap64ifOutNUcastPkts OBJECT-TYPE
	SYNTAX  Counter64
	MAX-ACCESS  read-only
	STATUS  current
	DESCRIPTION
	        "The total number of packets that higher-level
	        protocols requested be transmitted to a non-
	        unicast (i.e., a subnetwork-broadcast or
	        subnetwork-multicast) address, including those
	        that were discarded or not sent."
	::= { ap64ifEntry 18 }

ap64ifOutDiscards OBJECT-TYPE
	SYNTAX  Counter64
	MAX-ACCESS  read-only
	STATUS  current
	DESCRIPTION
	        "The number of outbound packets which were chosen
	        to be discarded even though no errors had been
	        detected to prevent their being transmitted.  One
	        possible reason for discarding such a packet could
	        be to free up buffer space."
	::= { ap64ifEntry 19 }

ap64ifOutErrors OBJECT-TYPE
	SYNTAX  Counter64
	MAX-ACCESS  read-only
	STATUS  current
	DESCRIPTION
	        "The number of outbound packets that could not be
	        transmitted because of errors."
	::= { ap64ifEntry 20 }

ap64ifOutQLen OBJECT-TYPE
	SYNTAX  Gauge
	MAX-ACCESS  read-only
	STATUS  current
	DESCRIPTION
	        "The length of the output packet queue (in
	        packets)."
	::= { ap64ifEntry 21 }

ap64ifSpecific OBJECT-TYPE
	SYNTAX  OBJECT IDENTIFIER
	MAX-ACCESS  read-only
	STATUS  current
	DESCRIPTION
	        "A reference to MIB definitions specific to the
	        particular media being used to realize the
	        interface.  For example, if the interface is
	        realized by an ethernet, then the value of this
	        object refers to a document defining objects
	        specific to ethernet.  If this information is not
	        present, its value should be set to the OBJECT
	        IDENTIFIER { 0 0 }, which is a syntatically valid
	        object identifier, and any conformant
	        implementation of ASN.1 and BER must be able to
	        generate and recognize this value."
	::= { ap64ifEntry 22 }

ap64etherStatsTable OBJECT-TYPE
	SYNTAX SEQUENCE OF AP64EtherStatsEntry
	MAX-ACCESS not-accessible
	STATUS current
	DESCRIPTION
	    "A list of Ethernet statistics entries."
	::= { ap64Stats 4 }

ap64etherStatsEntry OBJECT-TYPE
	SYNTAX AP64EtherStatsEntry
	MAX-ACCESS not-accessible
	STATUS current
	DESCRIPTION
	    "A collection of statistics kept for a particular
	    Ethernet interface.  As an example, an instance of the
	    etherStatsPkts object might be named etherStatsPkts.1"
	INDEX { ap64etherStatsIndex }
	::= { ap64etherStatsTable 1 }

AP64EtherStatsEntry ::= SEQUENCE {
	ap64etherStatsIndex                    INTEGER (1..65535),
	ap64etherStatsDataSource               OBJECT IDENTIFIER,
	ap64etherStatsDropEvents               Counter64,
	ap64etherStatsOctets                   Counter64,
	ap64etherStatsPkts                     Counter64,
	ap64etherStatsBroadcastPkts            Counter64,
	ap64etherStatsMulticastPkts            Counter64,
	ap64etherStatsCRCAlignErrors           Counter64,
	ap64etherStatsUndersizePkts            Counter64,
	ap64etherStatsOversizePkts             Counter64,
	ap64etherStatsFragments                Counter64,
	ap64etherStatsJabbers                  Counter64,
	ap64etherStatsCollisions               Counter64,
	ap64etherStatsPkts64Octets             Counter64,
	ap64etherStatsPkts65to127Octets        Counter64,
	ap64etherStatsPkts128to255Octets       Counter64,
	ap64etherStatsPkts256to511Octets       Counter64,
	ap64etherStatsPkts512to1023Octets      Counter64,
	ap64etherStatsPkts1024to1518Octets     Counter64,
	ap64etherStatsOwner                    OwnerString,
	ap64etherStatsStatus                   EntryStatus
    }

ap64etherStatsIndex OBJECT-TYPE
	SYNTAX INTEGER (1..65535)
	MAX-ACCESS read-only
	STATUS current
	DESCRIPTION
	    "The value of this object uniquely identifies this
	    etherStats entry."
	::= { ap64etherStatsEntry 1 }

ap64etherStatsDataSource OBJECT-TYPE
	SYNTAX OBJECT IDENTIFIER
	MAX-ACCESS read-only
	STATUS current
	DESCRIPTION
	    "This object identifies the source of the data that
	    this etherStats entry is configured to analyze.  This
	    source can be any ethernet interface on this device.
	    In order to identify a particular interface, this
	    object shall identify the instance of the ifIndex
	    object, defined in RFC 1213 and RFC 1573 [4,6], for
	    the desired interface.  For example, if an entry
	    were to receive data from interface #1, this object
	    would be set to ifIndex.1.
	     The statistics in this group reflect all packets
	    on the local network segment attached to the
	    identified interface.
	     An agent may or may not be able to tell if
	    fundamental changes to the media of the interface
	    have occurred and necessitate an invalidation of
	    this entry.  For example, a hot-pluggable ethernet
	    card could be pulled out and replaced by a
	    token-ring card.  In such a case, if the agent has
	    such knowledge of the change, it is recommended that
	    it invalidate this entry.

	    This object may not be modified if the associated
	    etherStatsStatus object is equal to valid(1)."
	::= { ap64etherStatsEntry 2 }

ap64etherStatsDropEvents OBJECT-TYPE
	SYNTAX Counter64
	MAX-ACCESS read-only
	STATUS current
	DESCRIPTION
	    "The total number of events in which packets
	    were dropped by the probe due to lack of resources.
	    Note that this number is not necessarily the number of
	    packets dropped; it is just the number of times this
	    condition has been detected."
	::= { ap64etherStatsEntry 3 }

ap64etherStatsOctets OBJECT-TYPE
	SYNTAX Counter64
	MAX-ACCESS read-only
	STATUS current
	DESCRIPTION
	    "The total number of octets of data (including
	    those in bad packets) received on the
	    network (excluding framing bits but including
        FCS octets).

	    This object can be used as a reasonable estimate of
	    ethernet utilization.  If greater precision is
	    desired, the etherStatsPkts and etherStatsOctets
	    objects should be sampled before and after a common
	    interval.  The differences in the sampled values are
	    Pkts and Octets, respectively, and the number of
	    seconds in the interval is Interval.  These values
	    are used to calculate the Utilization as follows:

	                     Pkts * (9.6 + 6.4) + (Octets * .8)
                   Utilization = -------------------------------------
	                Interval * 10,000
	     The result of this equation is the value Utilization
	    which is the percent utilization of the ethernet
	    segment on a scale of 0 to 100 percent."
	::= { ap64etherStatsEntry 4 }

ap64etherStatsPkts OBJECT-TYPE
	SYNTAX Counter64
	MAX-ACCESS read-only
	STATUS current
	DESCRIPTION
	    "The total number of packets (including bad packets,
	    broadcast packets, and multicast packets) received."
	::= { ap64etherStatsEntry 5 }

ap64etherStatsBroadcastPkts OBJECT-TYPE
	SYNTAX Counter64
	MAX-ACCESS read-only
	STATUS current
	DESCRIPTION
	    "The total number of good packets received that were
	    directed to the broadcast address.  Note that this
	    does not include multicast packets."
	::= { ap64etherStatsEntry 6 }

ap64etherStatsMulticastPkts OBJECT-TYPE
	SYNTAX Counter64
	MAX-ACCESS read-only
	STATUS current
	DESCRIPTION
	    "The total number of good packets received that were
	    directed to a multicast address.  Note that this
	    number does not include packets directed to the
	    broadcast address."
	::= { ap64etherStatsEntry 7 }

ap64etherStatsCRCAlignErrors OBJECT-TYPE
	SYNTAX Counter64
	MAX-ACCESS read-only
	STATUS current
	DESCRIPTION
	    "The total number of packets received that
	    had a length (excluding framing bits, but
	    including FCS octets) of between 64 and 1518
	    octets, inclusive, but but had either a bad
	    Frame Check Sequence (FCS) with an integral
	    number of octets (FCS Error) or a bad FCS with
	    a non-integral number of octets (Alignment Error)."
	::= { ap64etherStatsEntry 8 }

ap64etherStatsUndersizePkts OBJECT-TYPE
	SYNTAX Counter64
	MAX-ACCESS read-only
	STATUS current
	DESCRIPTION
	    "The total number of packets received that were
	    less than 64 octets long (excluding framing bits,
	    but including FCS octets) and were otherwise well
	    formed."
	::= { ap64etherStatsEntry 9 }

ap64etherStatsOversizePkts OBJECT-TYPE
	SYNTAX Counter64
	MAX-ACCESS read-only
	STATUS current
	DESCRIPTION
	    "The total number of packets received that were
	    longer than 1518 octets (excluding framing bits,
	    but including FCS octets) and were otherwise
	    well formed."
	::= { ap64etherStatsEntry 10 }

ap64etherStatsFragments OBJECT-TYPE
	SYNTAX Counter64
	MAX-ACCESS read-only
	STATUS current
	DESCRIPTION
	    "The total number of packets received that were less
	    than 64 octets in length (excluding framing bits but
	    including FCS octets) and had either a bad Frame
	    Check Sequence (FCS) with an integral number of
	    octets (FCS Error) or a bad FCS with a non-integral
	    number of octets (Alignment Error).

	    Note that it is entirely normal for
	    ap64etherStatsFragments to increment.  This is because
	    it counts both runts (which are normal occurrences
	    due to collisions) and noise hits."
	::= { ap64etherStatsEntry 11 }

ap64etherStatsJabbers OBJECT-TYPE
	SYNTAX Counter64
	MAX-ACCESS read-only
	STATUS current
	DESCRIPTION
	    "The total number of packets received that were
	    longer than 1518 octets (excluding framing bits,
	    but including FCS octets), and had either a bad
	    Frame Check Sequence (FCS) with an integral number
	    of octets (FCS Error) or a bad FCS with a
	    non-integral number of octets (Alignment Error).

	    Note that this definition of jabber is different
	    than the definition in IEEE-802.3 section 8.2.1.5
	    (10BASE5) and section 10.3.1.4 (10BASE2).  These
	    documents define jabber as the condition where any
	    packet exceeds 20 ms.  The allowed range to detect
	    jabber is between 20 ms and 150 ms."
	::= { ap64etherStatsEntry 12 }

ap64etherStatsCollisions OBJECT-TYPE
	SYNTAX Counter64
	MAX-ACCESS read-only
	STATUS current
	DESCRIPTION
	    "The best estimate of the total number of collisions
	    on this Ap64ethernet segment.

	    The value returned will depend on the location of
	    the RMON probe. Section 8.2.1.3 (10BASE-5) and
	    section 10.3.1.3 (10BASE-2) of IEEE standard 802.3
	    states that a station must detect a collision, in
	    the receive mode, if three or more stations are
	    transmitting simultaneously.  A repeater port must
	    detect a collision when two or more stations are
	    transmitting simultaneously.  Thus a probe placed on
	    a repeater port could record more collisions than a
	    probe connected to a station on the same segment
	    would.

	    Probe location plays a much smaller role when
	    considering 10BASE-T.  14.2.1.4 (10BASE-T) of IEEE
	    standard 802.3 defines a collision as the
	    simultaneous presence of signals on the DO and RD
	    circuits (transmitting and receiving at the same
	    time).  A 10BASE-T station can only detect
	    collisions when it is transmitting.  Thus probes
	    placed on a station and a repeater, should report
	    the same number of collisions.

	    Note also that an RMON probe inside a repeater
	    should ideally report collisions between the
	    repeater and one or more other hosts (transmit
	    collisions as defined by IEEE 802.3k) plus receiver
	    collisions observed on any coax segments to which
	    the repeater is connected."
	::= { ap64etherStatsEntry 13 }

ap64etherStatsPkts64Octets OBJECT-TYPE
	SYNTAX Counter64
	MAX-ACCESS read-only
	STATUS current
	DESCRIPTION
	    "The total number of packets (including bad
	    packets) received that were 64 octets in length
	    (excluding framing bits but including FCS octets)."
	::= { ap64etherStatsEntry 14 }

ap64etherStatsPkts65to127Octets OBJECT-TYPE
	SYNTAX Counter64
	MAX-ACCESS read-only
	STATUS current
	DESCRIPTION
	    "The total number of packets (including bad
	    packets) received that were between
	    65 and 127 octets in length inclusive
	    (excluding framing bits but including FCS octets)."
	::= { ap64etherStatsEntry 15 }

ap64etherStatsPkts128to255Octets OBJECT-TYPE
	SYNTAX Counter64
	MAX-ACCESS read-only
	STATUS current
	DESCRIPTION
	    "The total number of packets (including bad
	    packets) received that were between
	    128 and 255 octets in length inclusive
	    (excluding framing bits but including FCS octets)."
	::= { ap64etherStatsEntry 16 }

ap64etherStatsPkts256to511Octets OBJECT-TYPE
	SYNTAX Counter64
	MAX-ACCESS read-only
	STATUS current
	DESCRIPTION
	    "The total number of packets (including bad
	    packets) received that were between
	    256 and 511 octets in length inclusive
	    (excluding framing bits but including FCS octets)."
	::= { ap64etherStatsEntry 17 }

ap64etherStatsPkts512to1023Octets OBJECT-TYPE
	SYNTAX Counter64
	MAX-ACCESS read-only
	STATUS current
	DESCRIPTION
	    "The total number of packets (including bad
	    packets) received that were between
	    512 and 1023 octets in length inclusive
	    (excluding framing bits but including FCS octets)."
	::= { ap64etherStatsEntry 18 }

ap64etherStatsPkts1024to1518Octets OBJECT-TYPE
	SYNTAX Counter64
	MAX-ACCESS read-only
	STATUS current
	DESCRIPTION
	    "The total number of packets (including bad
	    packets) received that were between
	    1024 and 1518 octets in length inclusive
	    (excluding framing bits but including FCS octets)."
	::= { ap64etherStatsEntry 19 }

ap64etherStatsOwner OBJECT-TYPE
	SYNTAX OwnerString
	MAX-ACCESS read-only
	STATUS current
	DESCRIPTION
	    "The entity that configured this entry and is
	    therefore using the resources assigned to it."
	::= { ap64etherStatsEntry 20 }

ap64etherStatsStatus OBJECT-TYPE
	SYNTAX EntryStatus
	MAX-ACCESS read-only
	STATUS current
	DESCRIPTION
	    "The status of this ap64etherStats entry."
	::= { ap64etherStatsEntry 21 }


END
