-- *****************************************************************
--
-- stn-bgp.mib:  
--      Spring Tide Networks BGP-4 MIB File
--
--
--      Copyright (c) 2000 by Spring Tide Networks, Inc.
--                      ALL RIGHTS RESERVED       
--
-- *****************************************************************

-- MIB Object definitions for Spring Tide BGP-4

STN-BGP-MIB DEFINITIONS ::= BEGIN

    IMPORTS
        MODULE-IDENTITY,
        OBJECT-TYPE,
        IpAddress,
        Counter32,
        Integer32
                FROM SNMPv2-SMI

        MODULE-COMPLIANCE
                FROM SNMPv2-CONF

		bgp4PathAttrEntry
				FROM BGP4-MIB

        stnIpRouting
                FROM STN-IPROUTING-MIB
                
        stnNotification
                FROM SPRING-TIDE-NETWORKS-SMI;


    stnBgp MODULE-IDENTITY
        LAST-UPDATED    "0004060000Z"
        ORGANIZATION    "Spring Tide Networks"
        CONTACT-INFO
                "
                Spring Tide Networks, Inc.
                Customer Service

                Postal: 3 Clock Tower Place
                        Suite 200
                        Maynard, MA 01754 USA
                Tel:    +1 978 298 2000
                Email:  custserv@springtidenet.com
                "
        DESCRIPTION     "This MIB module describes managed objects of
                         Spring Tide Networks BGP-4."
        ::= { stnIpRouting 5 }

--
-- Top Level STN BGP MIB Objects
--

    stnBgpObjects       OBJECT IDENTIFIER ::= {stnBgp 1}
    

-- STN BGP-4 Route Attribute Table.
-- This table contains one entry per BGP route attribute set.

    stnBgpRouteAttrTable OBJECT-TYPE
        SYNTAX        SEQUENCE OF StnBgpRouteAttrEntry
        MAX-ACCESS    not-accessible
        STATUS        current
        DESCRIPTION   "A table of BGP route attribute sets."
        ::= { stnBgpObjects 1 }

    stnBgpRouteAttrEntry OBJECT-TYPE
        SYNTAX        StnBgpRouteAttrEntry
        MAX-ACCESS    not-accessible
        STATUS        current
        DESCRIPTION   "Information about a particular set of BGP attributes."
        INDEX         { stnBgpRouteAttrId }
        ::= { stnBgpRouteAttrTable 1 }

    StnBgpRouteAttrEntry ::= SEQUENCE {
        stnBgpRouteAttrId                Integer32,
        stnBgpRouteAttrASPathSegment     OCTET STRING,
        stnBgpRouteAttrRefCount          INTEGER,
        stnBgpRouteAttrLocPref           INTEGER,
        stnBgpRouteAttrMultiExitDisc     INTEGER,
        stnBgpRouteAttrOrigin            INTEGER,
        stnBgpRouteAttrNextHop           IpAddress,
        stnBgpRouteAttrAtomicAggregate   INTEGER,
        stnBgpRouteAttrAggregatorAS      INTEGER,
        stnBgpRouteAttrAggregatorAddr    IpAddress
    }

    stnBgpRouteAttrId OBJECT-TYPE
        SYNTAX          Integer32
        MAX-ACCESS      read-only
        STATUS          current
        DESCRIPTION     "A unique integer identifing this row in the table."
        ::= { stnBgpRouteAttrEntry 1 }

    stnBgpRouteAttrASPathSegment OBJECT-TYPE
        SYNTAX          OCTET STRING (SIZE (2..255))
        MAX-ACCESS      read-only
        STATUS          current
        DESCRIPTION
            "The sequence of AS path segments.  Each AS
            path segment is represented by a triple
            <type, length, value>.

            The type is a 1-octet field which has two
            possible values:
                 1      AS_SET: unordered set of ASs a
                             route in the UPDATE
                             message has traversed
                 2      AS_SEQUENCE: ordered set of ASs
                             a route in the UPDATE
                             message has traversed.

            The length is a 1-octet field containing the
            number of ASs in the value field.

            The value field contains one or more AS
            numbers, each AS is represented in the octet
            string as a pair of octets according to the
            following algorithm:
                first-byte-of-pair = ASNumber / 256;
                second-byte-of-pair = ASNumber & 255;"
        ::= { stnBgpRouteAttrEntry 2 }

    stnBgpRouteAttrRefCount OBJECT-TYPE
        SYNTAX          INTEGER
        MAX-ACCESS      read-only
        STATUS          current
        DESCRIPTION     "A number of BGP routes using this attibute set."
        ::= { stnBgpRouteAttrEntry 3 }

    stnBgpRouteAttrLocPref OBJECT-TYPE
        SYNTAX          INTEGER
        MAX-ACCESS      read-only
        STATUS          current
        DESCRIPTION     "The originating BGP4 speaker's degree of
                         preference for an advertised route.
                         A value of -1 indicates the absence of this
                         attribute."
        ::= { stnBgpRouteAttrEntry 4 }

    stnBgpRouteAttrMultiExitDisc OBJECT-TYPE
        SYNTAX          INTEGER
        MAX-ACCESS      read-only
        STATUS          current
        DESCRIPTION     "This metric is used to discriminate
                         between multiple exit points to an
                         adjacent autonomous system.  A value of -1
                         indicates the absence of this attribute."
        ::= { stnBgpRouteAttrEntry 5 }

    stnBgpRouteAttrOrigin OBJECT-TYPE
        SYNTAX          INTEGER {
                            igp(1),-- networks are interior
                            egp(2),-- networks learned via EGP
                            incomplete(3) -- undetermined
                        }
        MAX-ACCESS      read-only
        STATUS          current
        DESCRIPTION     "The ultimate origin of the path information."
        ::= { stnBgpRouteAttrEntry 6 }

    stnBgpRouteAttrNextHop OBJECT-TYPE
        SYNTAX          IpAddress
        MAX-ACCESS      read-only
        STATUS          current
        DESCRIPTION     "The address of the border router that
                         should be used for the destination
                         network."
        ::= { stnBgpRouteAttrEntry 7 }

    stnBgpRouteAttrAtomicAggregate OBJECT-TYPE
        SYNTAX          INTEGER {
                            lessSpecificRouteNotSelected(1),
                            lessSpecificRouteSelected(2)
                        }
        MAX-ACCESS      read-only
        STATUS          current
        DESCRIPTION     "Whether or not the local system has
                         selected a less specific route without
                         selecting a more specific route."
        ::= { stnBgpRouteAttrEntry 8 }

    stnBgpRouteAttrAggregatorAS OBJECT-TYPE
        SYNTAX          INTEGER (0..65535)
        MAX-ACCESS      read-only
        STATUS          current
        DESCRIPTION     "The AS number of the last BGP4 speaker that
                         performed route aggregation.  A value of
                         zero (0) indicates the absence of this
                         attribute."
        ::= { stnBgpRouteAttrEntry 9 }

    stnBgpRouteAttrAggregatorAddr OBJECT-TYPE
        SYNTAX          IpAddress
        MAX-ACCESS      read-only
        STATUS          current
        DESCRIPTION     "The IP address of the last BGP4 speaker
                         that performed route aggregation.  A value
                         of 0.0.0.0 indicates the absence of this
                         attribute."
        ::= { stnBgpRouteAttrEntry 10 }


-- STN BGP Router Statistics

    stnBgpPrefixCount                  OBJECT-TYPE
        SYNTAX          Counter32
        MAX-ACCESS      read-only
        STATUS          current
        DESCRIPTION     "Number of distinct prefixes in the local RIB."
        ::= { stnBgpObjects 2 }

    stnBgpPathCount                    OBJECT-TYPE
        SYNTAX          Counter32
        MAX-ACCESS      read-only
        STATUS          current
        DESCRIPTION     "Number of paths in the local RIB."
        ::= { stnBgpObjects 3 }

    stnBgpSelectedPathCount            OBJECT-TYPE
        SYNTAX          Counter32
        MAX-ACCESS      read-only
        STATUS          current
        DESCRIPTION     "Number of paths selected for route table installation."
        ::= { stnBgpObjects 4 }

    stnBgpPathAttributeCount           OBJECT-TYPE
        SYNTAX          Counter32
        MAX-ACCESS      read-only
        STATUS          current
        DESCRIPTION     "Number of entries in the path attribute database."
        ::= { stnBgpObjects 5 }

    stnBgpPathAttributeTlvLength       OBJECT-TYPE
        SYNTAX          Counter32
        MAX-ACCESS      read-only
        STATUS          current
        DESCRIPTION     "Total length of all TLVs in the path attribute database."
        ::= { stnBgpObjects 6 }


-- STN BGP-4 Received Path Attribute Table.
-- This table contains one entry per path to a network.
-- This table augments bgp4PathAttrTable from BGP4-MIB (rfc1657).

    stnBgp4PathAttrTable OBJECT-TYPE
        SYNTAX        SEQUENCE OF StnBgp4PathAttrEntry
        MAX-ACCESS    not-accessible
        STATUS        current
        DESCRIPTION   "A table of BGP path attributes."
        ::= { stnBgpObjects 7 }

    stnBgp4PathAttrEntry                OBJECT-TYPE
        SYNTAX        StnBgp4PathAttrEntry
        MAX-ACCESS    not-accessible
        STATUS        current
        DESCRIPTION
            "Additional information about a bgp path to a network."
        AUGMENTS { bgp4PathAttrEntry }
    ::= { stnBgp4PathAttrTable 1 }

    StnBgp4PathAttrEntry ::= SEQUENCE {
        stnBgp4PathAttrCommunities      OCTET STRING,
        stnBgp4PathAttrWeight           Integer32,
        stnBgp4PathAttrImported         INTEGER
    }

    stnBgp4PathAttrCommunities          OBJECT-TYPE
        SYNTAX          OCTET STRING (SIZE (0..256))
        MAX-ACCESS      read-only
        STATUS          current
        DESCRIPTION     "The sequence of community numbers.
                         Each AS community number is a 4-octet long unsigned integer" 
        ::= { stnBgp4PathAttrEntry 1 }

    stnBgp4PathAttrWeight               OBJECT-TYPE
        SYNTAX          Integer32
        MAX-ACCESS      read-only
        STATUS          current
        DESCRIPTION     "The weight of this path." 
        ::= { stnBgp4PathAttrEntry 2 }

    stnBgp4PathAttrImported             OBJECT-TYPE
        SYNTAX          INTEGER {
                                 true(1),
                                 false(2)
                        }
        MAX-ACCESS      read-only
        STATUS          current
        DESCRIPTION     "Variable indicates whether this path has been imported
                         from the other portocol on this router."
        ::= { stnBgp4PathAttrEntry 3 }

END
