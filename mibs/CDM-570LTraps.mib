--
-- CDM-570LTraps.my
-- MIB generated by MG-SOFT Visual MIB Builder Version 2.1 Build 199
-- Wednesday, January 26, 2005 at 15:41:30
--

	CDM-570LTraps DEFINITIONS ::= BEGIN

		IMPORTS 
			cdm570LODUAlarms, cdm570			
				FROM CDM-570L			
			TRAP-TYPE			
				FROM RFC-1215;
	
	
	
--
-- Trap definitions
--
	
		cdm570LODUAlarm TRAP-TYPE
			ENTERPRISE cdm570
			VARIABLES { cdm570LODUAlarms }
			DESCRIPTION
				"CDM-570L BUC and LNB Alarm Trap"
			::=  6247244
			
	
	END

--
-- CDM-570LTraps.my
--
