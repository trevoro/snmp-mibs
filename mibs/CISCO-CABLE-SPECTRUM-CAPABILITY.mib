-- *****************************************************************
-- CISCO-CABLE-SPECTRUM-CAPABILITY.my: CISCO-CABLE-SPECTRUM-MIB 
--                                     AGENT-CAPABILITIES
--
-- June 2000  Lynn Tran   
--
-- Copyright (c) 2000 by cisco Systems, Inc.
-- All rights reserved.
-- *****************************************************************

CISCO-CABLE-SPECTRUM-CAPABILITY DEFINITIONS ::= BEGIN

IMPORTS
    MODULE-IDENTITY, Integer32
        FROM SNMPv2-SMI
    AGENT-CAPABILITIES
        FROM SNMPv2-CONF
    ciscoAgentCapability
        FROM CISCO-SMI;


ciscoCableSpectrumCapability MODULE-IDENTITY
        LAST-UPDATED    "200212180000Z"
        ORGANIZATION    "Cisco Systems, Inc."
        CONTACT-INFO
                "       Cisco Systems
                        Customer Service

                Postal: 170 W. Tasman Drive
                        San Jose, CA  95134
                        USA

                Tel: +1 800 553-NETS

                E-mail: cs-ubr@cisco.com"
        DESCRIPTION
                "Agent capabilities for CISCO-CABLE-SPECTRUM-MIB"

        REVISION    "200212180000Z"
        DESCRIPTION
                "Initial version of this MIB module."

        ::= { ciscoAgentCapability 999 }


ciscoCableSpectrumCapabilityV12R00 AGENT-CAPABILITIES

PRODUCT-RELEASE "Cisco IOS 12.0"
STATUS      current 
DESCRIPTION "Cisco Cable Spectrum Management MIB capabilities."

SUPPORTS    CISCO-CABLE-SPECTRUM-MIB
INCLUDES    { ccsFlapGroup 
            }

    ::= { ciscoCableSpectrumCapability 1 }


ciscoCableSpectrumCapabilityV12R01Rev1 AGENT-CAPABILITIES

PRODUCT-RELEASE "Cisco IOS 12.1(05)EC and 12.2 BC"
STATUS      current 
DESCRIPTION "Cisco Cable Spectrum Management MIB capabilities."

SUPPORTS    CISCO-CABLE-SPECTRUM-MIB
INCLUDES    { ccsFlapGroup, ccsSpectrumGroup,
              ccsUpSpecMgmtGroup 
            }

VARIATION       ccsFlapListMaxSize
SYNTAX          Integer32 (1..8191)
DESCRIPTION     "The maximum number of modems that a flap list 
                 can support is presently restricted to 8191."

    ::= { ciscoCableSpectrumCapability 2 }

END
