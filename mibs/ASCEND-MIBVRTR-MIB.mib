--			Ascend mibvrtr MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBVRTR-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibvRouterProfile  OBJECT IDENTIFIER ::= { configuration 139}

	-- The mibvRouterProfile table
	--
	-- This table contains parameters for the mibvRouterProfile profile
	--

    mibvRouterProfileTable	OBJECT-TYPE
	SYNTAX		SEQUENCE OF MibvRouterProfileEntry
	ACCESS		not-accessible
	STATUS		mandatory
	DESCRIPTION	"A list of mibvRouterProfile profile entries."
	::= { mibvRouterProfile 1 }

    mibvRouterProfileEntry	OBJECT-TYPE
	SYNTAX		MibvRouterProfileEntry
	ACCESS		not-accessible
	STATUS		mandatory
	DESCRIPTION	"A mibvRouterProfile entry containing objects that
			 maps to the parameters of mibvRouterProfile profile."
	INDEX		{ vRouterProfile-Name }
	::= { mibvRouterProfileTable 1 }

    MibvRouterProfileEntry ::=
	SEQUENCE {
	    vRouterProfile-Name
		DisplayString,
	    vRouterProfile-Active
		INTEGER,
	    vRouterProfile-VrouterIpAddr
		IpAddress,
	    vRouterProfile-PoolSummary
		INTEGER,
	    vRouterProfile-ShareGlobalPool
		INTEGER,
	    vRouterProfile-RipPolicy
		INTEGER,
	    vRouterProfile-SummarizeRipRoutes
		INTEGER,
	    vRouterProfile-RipTrigger
		INTEGER,
	    vRouterProfile-DomainName
		DisplayString,
	    vRouterProfile-SecDomainName
		DisplayString,
	    vRouterProfile-DnsPrimaryServer
		IpAddress,
	    vRouterProfile-DnsSecondaryServer
		IpAddress,
	    vRouterProfile-ClientPrimaryDnsServer
		IpAddress,
	    vRouterProfile-ClientSecondaryDnsServer
		IpAddress,
	    vRouterProfile-AllowAsClientDnsInfo
		INTEGER,
	    vRouterProfile-IpxRoutingEnabled
		INTEGER,
	    vRouterProfile-IpxDialinPool
		DisplayString,
	    vRouterProfile-Action-o
		INTEGER
	}

    vRouterProfile-Name	OBJECT-TYPE
	SYNTAX	DisplayString
	ACCESS	read-only
	STATUS	mandatory
	DESCRIPTION	"The name of a VRouter."
	::= { mibvRouterProfileEntry 1 }

    vRouterProfile-Active	OBJECT-TYPE
	SYNTAX	INTEGER {
		    no (1),
		    yes (2)
		}
	ACCESS	read-write
	STATUS	mandatory
	DESCRIPTION	"Whether the VROUTER is active or not"
	::= { mibvRouterProfileEntry 2 }

    vRouterProfile-VrouterIpAddr	OBJECT-TYPE
	SYNTAX	IpAddress
	ACCESS	read-write
	STATUS	mandatory
	DESCRIPTION	"System ip address for a VRouter."
	::= { mibvRouterProfileEntry 3 }

    vRouterProfile-PoolSummary	OBJECT-TYPE
	SYNTAX	INTEGER {
		    no (1),
		    yes (2)
		}
	ACCESS	read-write
	STATUS	mandatory
	DESCRIPTION	"Flag, when set indicates that host addresses assigned from the pool should be marked as PRIVATE in the routing table and summarized to the world at large via a (constant) network advertisement for the whole pool."
	::= { mibvRouterProfileEntry 4 }

    vRouterProfile-ShareGlobalPool	OBJECT-TYPE
	SYNTAX	INTEGER {
		    no (1),
		    yes (2)
		}
	ACCESS	read-write
	STATUS	mandatory
	DESCRIPTION	"Flag, when set indicates that vrouter can share the address pools defined for in IP-GLOBAL profile."
	::= { mibvRouterProfileEntry 18 }

    vRouterProfile-RipPolicy	OBJECT-TYPE
	SYNTAX	INTEGER {
		    splitHorzn (1),
		    poisonRvrs (2)
		}
	ACCESS	read-write
	STATUS	mandatory
	DESCRIPTION	"Describes whether to use Poison reverse or Split Horizon policy. Global for the vrouter."
	::= { mibvRouterProfileEntry 5 }

    vRouterProfile-SummarizeRipRoutes	OBJECT-TYPE
	SYNTAX	INTEGER {
		    no (1),
		    yes (2)
		}
	ACCESS	read-write
	STATUS	mandatory
	DESCRIPTION	"Summarize subnets in RIP broadcasts per RFC 1058/RFC 1009."
	::= { mibvRouterProfileEntry 6 }

    vRouterProfile-RipTrigger	OBJECT-TYPE
	SYNTAX	INTEGER {
		    no (1),
		    yes (2)
		}
	ACCESS	read-write
	STATUS	mandatory
	DESCRIPTION	"When set to TRUE (its default value) it causes RIP to send triggered (incremental) updates. Otherwise full table updates are sent when a change in the routing table is noticed."
	::= { mibvRouterProfileEntry 7 }

    vRouterProfile-DomainName	OBJECT-TYPE
	SYNTAX	DisplayString
	ACCESS	read-write
	STATUS	mandatory
	DESCRIPTION	"The DNS domain name assigned to this vrouter."
	::= { mibvRouterProfileEntry 8 }

    vRouterProfile-SecDomainName	OBJECT-TYPE
	SYNTAX	DisplayString
	ACCESS	read-write
	STATUS	mandatory
	DESCRIPTION	"The secondary DNS domain name assigned to this vrouter."
	::= { mibvRouterProfileEntry 9 }

    vRouterProfile-DnsPrimaryServer	OBJECT-TYPE
	SYNTAX	IpAddress
	ACCESS	read-write
	STATUS	mandatory
	DESCRIPTION	"The IP address of the primary DNS server for this vRouter."
	::= { mibvRouterProfileEntry 10 }

    vRouterProfile-DnsSecondaryServer	OBJECT-TYPE
	SYNTAX	IpAddress
	ACCESS	read-write
	STATUS	mandatory
	DESCRIPTION	"The IP address of the secondary DNS server for this vRouter. This server is used when the primary is not available."
	::= { mibvRouterProfileEntry 11 }

    vRouterProfile-ClientPrimaryDnsServer	OBJECT-TYPE
	SYNTAX	IpAddress
	ACCESS	read-write
	STATUS	mandatory
	DESCRIPTION	"Default user IP address of the primary DNS server."
	::= { mibvRouterProfileEntry 12 }

    vRouterProfile-ClientSecondaryDnsServer	OBJECT-TYPE
	SYNTAX	IpAddress
	ACCESS	read-write
	STATUS	mandatory
	DESCRIPTION	"Default user IP address of the secondary DNS server. This server is used when the primary is not available."
	::= { mibvRouterProfileEntry 13 }

    vRouterProfile-AllowAsClientDnsInfo	OBJECT-TYPE
	SYNTAX	INTEGER {
		    false (1),
		    true (2)
		}
	ACCESS	read-write
	STATUS	mandatory
	DESCRIPTION	"This flag controls if main DNS info should be allowed as Client DNS info."
	::= { mibvRouterProfileEntry 14 }

    vRouterProfile-IpxRoutingEnabled	OBJECT-TYPE
	SYNTAX	INTEGER {
		    no (1),
		    yes (2)
		}
	ACCESS	read-write
	STATUS	mandatory
	DESCRIPTION	"TRUE if this vRouter is currently routing IPX. We don't do IPX routing protocols or packet forwarding if FALSE."
	::= { mibvRouterProfileEntry 15 }

    vRouterProfile-IpxDialinPool	OBJECT-TYPE
	SYNTAX	DisplayString
	ACCESS	read-write
	STATUS	mandatory
	DESCRIPTION	"Dialin Pool Numbers to be shared by the ipx wan interfaces"
	::= { mibvRouterProfileEntry 16 }

    vRouterProfile-Action-o	OBJECT-TYPE
	SYNTAX	INTEGER {
		    noAction (1),
		    createProfile (2),
		    deleteProfile (3)
		}
	ACCESS	read-write
	STATUS	mandatory
	DESCRIPTION	""
	::= { mibvRouterProfileEntry 17 }


	-- The mibvRouterProfile__pool_name table
	--
	-- This table contains parameters for the mibvRouterProfile__pool_name profile
	--

    mibvRouterProfile-PoolNameTable	OBJECT-TYPE
	SYNTAX		SEQUENCE OF MibvRouterProfile-PoolNameEntry
	ACCESS		not-accessible
	STATUS		mandatory
	DESCRIPTION	"A list of mibvRouterProfile__pool_name profile entries."
	::= { mibvRouterProfile 2 }

    mibvRouterProfile-PoolNameEntry	OBJECT-TYPE
	SYNTAX		MibvRouterProfile-PoolNameEntry
	ACCESS		not-accessible
	STATUS		mandatory
	DESCRIPTION	"A mibvRouterProfile__pool_name entry containing objects that
			 maps to the parameters of mibvRouterProfile__pool_name profile."
	INDEX		{ vRouterProfile-PoolName-Name, vRouterProfile-PoolName-Index-o }
	::= { mibvRouterProfile-PoolNameTable 1 }

    MibvRouterProfile-PoolNameEntry ::=
	SEQUENCE {
	    vRouterProfile-PoolName-Name
		DisplayString,
	    vRouterProfile-PoolName-Index-o
		INTEGER,
	    vRouterProfile-PoolName
		DisplayString
	}

    vRouterProfile-PoolName-Name	OBJECT-TYPE
	SYNTAX	DisplayString
	ACCESS	read-only
	STATUS	mandatory
	DESCRIPTION	""
	::= { mibvRouterProfile-PoolNameEntry 1 }

    vRouterProfile-PoolName-Index-o	OBJECT-TYPE
	SYNTAX	INTEGER
	ACCESS	read-only
	STATUS	mandatory
	DESCRIPTION	""
	::= { mibvRouterProfile-PoolNameEntry 2 }

    vRouterProfile-PoolName	OBJECT-TYPE
	SYNTAX	DisplayString
	ACCESS	read-write
	STATUS	mandatory
	DESCRIPTION	"The name of this pool"
	::= { mibvRouterProfile-PoolNameEntry 3 }


	-- The mibvRouterProfile__assign_count table
	--
	-- This table contains parameters for the mibvRouterProfile__assign_count profile
	--

    mibvRouterProfile-AssignCountTable	OBJECT-TYPE
	SYNTAX		SEQUENCE OF MibvRouterProfile-AssignCountEntry
	ACCESS		not-accessible
	STATUS		mandatory
	DESCRIPTION	"A list of mibvRouterProfile__assign_count profile entries."
	::= { mibvRouterProfile 3 }

    mibvRouterProfile-AssignCountEntry	OBJECT-TYPE
	SYNTAX		MibvRouterProfile-AssignCountEntry
	ACCESS		not-accessible
	STATUS		mandatory
	DESCRIPTION	"A mibvRouterProfile__assign_count entry containing objects that
			 maps to the parameters of mibvRouterProfile__assign_count profile."
	INDEX		{ vRouterProfile-AssignCount-Name, vRouterProfile-AssignCount-Index-o }
	::= { mibvRouterProfile-AssignCountTable 1 }

    MibvRouterProfile-AssignCountEntry ::=
	SEQUENCE {
	    vRouterProfile-AssignCount-Name
		DisplayString,
	    vRouterProfile-AssignCount-Index-o
		INTEGER,
	    vRouterProfile-AssignCount
		INTEGER
	}

    vRouterProfile-AssignCount-Name	OBJECT-TYPE
	SYNTAX	DisplayString
	ACCESS	read-only
	STATUS	mandatory
	DESCRIPTION	""
	::= { mibvRouterProfile-AssignCountEntry 1 }

    vRouterProfile-AssignCount-Index-o	OBJECT-TYPE
	SYNTAX	INTEGER
	ACCESS	read-only
	STATUS	mandatory
	DESCRIPTION	""
	::= { mibvRouterProfile-AssignCountEntry 2 }

    vRouterProfile-AssignCount	OBJECT-TYPE
	SYNTAX	INTEGER
	ACCESS	read-write
	STATUS	mandatory
	DESCRIPTION	"The number of host addresses in the above pool. The addresses are contiguous."
	::= { mibvRouterProfile-AssignCountEntry 3 }


	-- The mibvRouterProfile__pool_base_address table
	--
	-- This table contains parameters for the mibvRouterProfile__pool_base_address profile
	--

    mibvRouterProfile-PoolBaseAddressTable	OBJECT-TYPE
	SYNTAX		SEQUENCE OF MibvRouterProfile-PoolBaseAddressEntry
	ACCESS		not-accessible
	STATUS		mandatory
	DESCRIPTION	"A list of mibvRouterProfile__pool_base_address profile entries."
	::= { mibvRouterProfile 4 }

    mibvRouterProfile-PoolBaseAddressEntry	OBJECT-TYPE
	SYNTAX		MibvRouterProfile-PoolBaseAddressEntry
	ACCESS		not-accessible
	STATUS		mandatory
	DESCRIPTION	"A mibvRouterProfile__pool_base_address entry containing objects that
			 maps to the parameters of mibvRouterProfile__pool_base_address profile."
	INDEX		{ vRouterProfile-PoolBaseAddress-Name, vRouterProfile-PoolBaseAddress-Index-o }
	::= { mibvRouterProfile-PoolBaseAddressTable 1 }

    MibvRouterProfile-PoolBaseAddressEntry ::=
	SEQUENCE {
	    vRouterProfile-PoolBaseAddress-Name
		DisplayString,
	    vRouterProfile-PoolBaseAddress-Index-o
		INTEGER,
	    vRouterProfile-PoolBaseAddress
		IpAddress
	}

    vRouterProfile-PoolBaseAddress-Name	OBJECT-TYPE
	SYNTAX	DisplayString
	ACCESS	read-only
	STATUS	mandatory
	DESCRIPTION	""
	::= { mibvRouterProfile-PoolBaseAddressEntry 1 }

    vRouterProfile-PoolBaseAddress-Index-o	OBJECT-TYPE
	SYNTAX	INTEGER
	ACCESS	read-only
	STATUS	mandatory
	DESCRIPTION	""
	::= { mibvRouterProfile-PoolBaseAddressEntry 2 }

    vRouterProfile-PoolBaseAddress	OBJECT-TYPE
	SYNTAX	IpAddress
	ACCESS	read-write
	STATUS	mandatory
	DESCRIPTION	"The base address of a pool of addresses we can use to assign to clients."
	::= { mibvRouterProfile-PoolBaseAddressEntry 3 }

END
