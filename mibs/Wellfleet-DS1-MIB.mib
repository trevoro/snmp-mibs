Wellfleet-DS1-MIB DEFINITIONS ::= BEGIN

-- Created by mdl2asn version 3.1
-- Creation date: Wed Aug 30 16:39:57 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfDs1Group
        FROM Wellfleet-COMMON-MIB;


    wfDs1Config OBJECT-TYPE
        SYNTAX	SEQUENCE OF WfDs1ConfigEntry
        ACCESS	not-accessible
        STATUS	mandatory
        DESCRIPTION
                "The DS1 Configuration table"
        ::= { wfDs1Group 1 }

    wfDs1ConfigEntry OBJECT-TYPE
        SYNTAX	WfDs1ConfigEntry
        ACCESS	not-accessible
        STATUS	mandatory
        DESCRIPTION
                "per circuit DS1 configuration objects; wfDs1LineIndex
                corresponds to Wellfleet circuit number"
        INDEX	{ wfDs1LineIndex }
        ::= { wfDs1Config 1 }

    WfDs1ConfigEntry ::= SEQUENCE {
    	    wfDs1LineIndex
    		INTEGER,
    	    wfDs1TimeElapsed
    		INTEGER,
    	    wfDs1ValidIntervals
    		INTEGER,
    	    wfDs1LineType
    		INTEGER,
    	    wfDs1ZeroCoding
    		INTEGER,
    	    wfDs1SendCode
    		INTEGER,
    	    wfDs1CircuitIdentifier
    		DisplayString,
    	    wfDs1LoopbackConfig
    		INTEGER,
    	    wfDs1LineStatus
    		INTEGER
        }

    wfDs1LineIndex OBJECT-TYPE
        SYNTAX	INTEGER(1..1024)
        ACCESS	read-only
        STATUS	mandatory
        DESCRIPTION
                "this corresponds to the Wellfleet circuit number"
        ::= { wfDs1ConfigEntry 1 }

    wfDs1TimeElapsed OBJECT-TYPE
        SYNTAX	INTEGER
        ACCESS	read-only
        STATUS	mandatory
        DESCRIPTION
                "1..900 seconds within the current 15-minute interval"
        ::= { wfDs1ConfigEntry 2 }

    wfDs1ValidIntervals OBJECT-TYPE
        SYNTAX	INTEGER
        ACCESS	read-only
        STATUS	mandatory
        DESCRIPTION
                "0..96 previous intervals that valid data
                were collected. This is 96 unless the CSU
                device was brought on line within the last 24
                hours."
        ::= { wfDs1ConfigEntry 3 }

    wfDs1LineType OBJECT-TYPE
        SYNTAX	INTEGER {
    		    ds1ansi-esf(4)
    		}
        ACCESS	read-only
        STATUS	mandatory
        DESCRIPTION
                "the variety of DS1 implementing this circuit"
        ::= { wfDs1ConfigEntry 4 }

    wfDs1ZeroCoding OBJECT-TYPE
        SYNTAX	INTEGER {
    		    ds1b8zs(2),
    		    ds1zbtsi(5)
    		}
        ACCESS	read-only
        STATUS	mandatory
        DESCRIPTION
                "the variety of Zero Code Suppression used on the link"
        ::= { wfDs1ConfigEntry 5 }

    wfDs1SendCode OBJECT-TYPE
        SYNTAX	INTEGER {
    		    ds1sendnocode(2)
    		}
        ACCESS	read-only
        STATUS	mandatory
        DESCRIPTION
                "the type of code being sent across the DS1 circuit by
                the CSU"
        ::= { wfDs1ConfigEntry 6 }

    wfDs1CircuitIdentifier OBJECT-TYPE
        SYNTAX	DisplayString
        ACCESS	read-only
        STATUS	mandatory
        DESCRIPTION
                "the transmission vendor's circuit identifier"
        ::= { wfDs1ConfigEntry 7 }

    wfDs1LoopbackConfig OBJECT-TYPE
        SYNTAX	INTEGER {
    		    ds1noloop(1),
    		    ds1mgrpayloadloop(2),
    		    ds1mgrlineloop(3),
    		    ds1netreqpayloadloop(4),
    		    ds1netreqlineloop(5),
    		    ds1otherloop(6)
    		}
        ACCESS	read-only
        STATUS	mandatory
        DESCRIPTION
                "the loopback state of the CSU"
        ::= { wfDs1ConfigEntry 8 }

    wfDs1LineStatus OBJECT-TYPE
        SYNTAX	INTEGER {
    		    ds1noalarm(1),
    		    ds1farendalarm(2),
    		    ds1alarmindicationsignal(4),
    		    ds1lossofframe(8),
    		    ds1lossofsignal(16),
    		    ds1loopbackstate(32)
    		}
        ACCESS	read-only
        STATUS	mandatory
        DESCRIPTION
                "the state of the DS1 line"
        ::= { wfDs1ConfigEntry 9 }

    wfDs1Current OBJECT-TYPE
        SYNTAX	SEQUENCE OF WfDs1CurrentEntry
        ACCESS	not-accessible
        STATUS	mandatory
        DESCRIPTION
                "The DS1 Current table"
        ::= { wfDs1Group 2 }

    wfDs1CurrentEntry OBJECT-TYPE
        SYNTAX	WfDs1CurrentEntry
        ACCESS	not-accessible
        STATUS	mandatory
        DESCRIPTION
                "per circuit DS1 current objects - wfDs1CurrentIndex
                corresponds to Wellfleet circuit number"
        INDEX	{ wfDs1CurrentIndex }
        ::= { wfDs1Current 1 }

    WfDs1CurrentEntry ::= SEQUENCE {
    	    wfDs1CurrentIndex
    		INTEGER,
    	    wfDs1CurrentESs
    		Counter,
    	    wfDs1CurrentSESs
    		Counter,
    	    wfDs1CurrentSEFs
    		Counter,
    	    wfDs1CurrentUASs
    		Counter,
    	    wfDs1CurrentBPVs
    		Counter,
    	    wfDs1CurrentCVs
    		Counter
        }

    wfDs1CurrentIndex OBJECT-TYPE
        SYNTAX	INTEGER(1..1024)
        ACCESS	read-only
        STATUS	mandatory
        DESCRIPTION
                "this corresponds to the Wellfleet circuit number"
        ::= { wfDs1CurrentEntry 1 }

    wfDs1CurrentESs OBJECT-TYPE
        SYNTAX	Counter
        ACCESS	read-only
        STATUS	mandatory
        DESCRIPTION
                "the count of errored seconds in the current interval"
        ::= { wfDs1CurrentEntry 2 }

    wfDs1CurrentSESs OBJECT-TYPE
        SYNTAX	Counter
        ACCESS	read-only
        STATUS	mandatory
        DESCRIPTION
                "the count of severely errored seconds in the
                current interval"
        ::= { wfDs1CurrentEntry 3 }

    wfDs1CurrentSEFs OBJECT-TYPE
        SYNTAX	Counter
        ACCESS	read-only
        STATUS	mandatory
        DESCRIPTION
                "the count of severely errored framing seconds in the current
                interval"
        ::= { wfDs1CurrentEntry 4 }

    wfDs1CurrentUASs OBJECT-TYPE
        SYNTAX	Counter
        ACCESS	read-only
        STATUS	mandatory
        DESCRIPTION
                "the number of unavailable seconds in the current interval"
        ::= { wfDs1CurrentEntry 5 }

    wfDs1CurrentBPVs OBJECT-TYPE
        SYNTAX	Counter
        ACCESS	read-only
        STATUS	mandatory
        DESCRIPTION
                "the count of bipolar violations in the current interval"
        ::= { wfDs1CurrentEntry 6 }

    wfDs1CurrentCVs OBJECT-TYPE
        SYNTAX	Counter
        ACCESS	read-only
        STATUS	mandatory
        DESCRIPTION
                "the count of code violation error events in the
                current interval"
        ::= { wfDs1CurrentEntry 7 }

    wfDs1Interval OBJECT-TYPE
        SYNTAX	SEQUENCE OF WfDs1IntervalEntry
        ACCESS	not-accessible
        STATUS	mandatory
        DESCRIPTION
                "The DS1 Interval table"
        ::= { wfDs1Group 3 }

    wfDs1IntervalEntry OBJECT-TYPE
        SYNTAX	WfDs1IntervalEntry
        ACCESS	not-accessible
        STATUS	mandatory
        DESCRIPTION
                "per circuit DS1 interval objects - wfDs1IntervalIndex
                corresponds to Wellfleet circuit number,
                wfDs1IntervalNumber is the numbered previous
                15-minute interval"
        INDEX	{ wfDs1IntervalIndex,
    		  wfDs1IntervalNumber }
        ::= { wfDs1Interval 1 }

    WfDs1IntervalEntry ::= SEQUENCE {
    	    wfDs1IntervalIndex
    		INTEGER,
    	    wfDs1IntervalNumber
    		INTEGER,
    	    wfDs1IntervalESs
    		Gauge,
    	    wfDs1IntervalSESs
    		Gauge,
    	    wfDs1IntervalSEFs
    		Gauge,
    	    wfDs1IntervalUASs
    		Gauge,
    	    wfDs1IntervalBPVs
    		Gauge,
    	    wfDs1IntervalCVs
    		Gauge
        }

    wfDs1IntervalIndex OBJECT-TYPE
        SYNTAX	INTEGER(1..1024)
        ACCESS	read-only
        STATUS	mandatory
        DESCRIPTION
                "this corresponds to the Wellfleet circuit number"
        ::= { wfDs1IntervalEntry 1 }

    wfDs1IntervalNumber OBJECT-TYPE
        SYNTAX	INTEGER(1..96)
        ACCESS	read-only
        STATUS	mandatory
        DESCRIPTION
                "1..96 where 1 is the most recent 15-minute interval and 96 is
                the least"
        ::= { wfDs1IntervalEntry 2 }

    wfDs1IntervalESs OBJECT-TYPE
        SYNTAX	Gauge
        ACCESS	read-only
        STATUS	mandatory
        DESCRIPTION
                "the count of errored seconds in the specified interval"
        ::= { wfDs1IntervalEntry 3 }

    wfDs1IntervalSESs OBJECT-TYPE
        SYNTAX	Gauge
        ACCESS	read-only
        STATUS	mandatory
        DESCRIPTION
                "the count of severely errored seconds in the specified
                interval"
        ::= { wfDs1IntervalEntry 4 }

    wfDs1IntervalSEFs OBJECT-TYPE
        SYNTAX	Gauge
        ACCESS	read-only
        STATUS	mandatory
        DESCRIPTION
                "the count of severely errored framing seconds in the specified
                interval"
        ::= { wfDs1IntervalEntry 5 }

    wfDs1IntervalUASs OBJECT-TYPE
        SYNTAX	Gauge
        ACCESS	read-only
        STATUS	mandatory
        DESCRIPTION
                "the number of unavailable seconds in the specified interval"
        ::= { wfDs1IntervalEntry 6 }

    wfDs1IntervalBPVs OBJECT-TYPE
        SYNTAX	Gauge
        ACCESS	read-only
        STATUS	mandatory
        DESCRIPTION
                "the count of bipolar violations in the specified interval"
        ::= { wfDs1IntervalEntry 7 }

    wfDs1IntervalCVs OBJECT-TYPE
        SYNTAX	Gauge
        ACCESS	read-only
        STATUS	mandatory
        DESCRIPTION
                "the count of code violation error events in the
                specified interval"
        ::= { wfDs1IntervalEntry 8 }

    wfDs1Total OBJECT-TYPE
        SYNTAX	SEQUENCE OF WfDs1TotalEntry
        ACCESS	not-accessible
        STATUS	mandatory
        DESCRIPTION
                "The DS1 Total table"
        ::= { wfDs1Group 4 }

    wfDs1TotalEntry OBJECT-TYPE
        SYNTAX	WfDs1TotalEntry
        ACCESS	not-accessible
        STATUS	mandatory
        DESCRIPTION
                "per circuit DS1 total objects - wfDs1TotalIndex
                corresponds to Wellfleet circuit number"
        INDEX	{ wfDs1TotalIndex }
        ::= { wfDs1Total 1 }

    WfDs1TotalEntry ::= SEQUENCE {
    	    wfDs1TotalIndex
    		INTEGER,
    	    wfDs1TotalESs
    		Gauge,
    	    wfDs1TotalSESs
    		Gauge,
    	    wfDs1TotalSEFs
    		Gauge,
    	    wfDs1TotalUASs
    		Gauge,
    	    wfDs1TotalBPVs
    		Gauge,
    	    wfDs1TotalCVs
    		Gauge
        }

    wfDs1TotalIndex OBJECT-TYPE
        SYNTAX	INTEGER(1..1024)
        ACCESS	read-only
        STATUS	mandatory
        DESCRIPTION
                "this corresponds to the Wellfleet circuit number"
        ::= { wfDs1TotalEntry 1 }

    wfDs1TotalESs OBJECT-TYPE
        SYNTAX	Gauge
        ACCESS	read-only
        STATUS	mandatory
        DESCRIPTION
                "total count of errored seconds"
        ::= { wfDs1TotalEntry 2 }

    wfDs1TotalSESs OBJECT-TYPE
        SYNTAX	Gauge
        ACCESS	read-only
        STATUS	mandatory
        DESCRIPTION
                "total count of severely errored seconds"
        ::= { wfDs1TotalEntry 3 }

    wfDs1TotalSEFs OBJECT-TYPE
        SYNTAX	Gauge
        ACCESS	read-only
        STATUS	mandatory
        DESCRIPTION
                "total count of severely errored framing seconds"
        ::= { wfDs1TotalEntry 4 }

    wfDs1TotalUASs OBJECT-TYPE
        SYNTAX	Gauge
        ACCESS	read-only
        STATUS	mandatory
        DESCRIPTION
                "total number of unavailable seconds"
        ::= { wfDs1TotalEntry 5 }

    wfDs1TotalBPVs OBJECT-TYPE
        SYNTAX	Gauge
        ACCESS	read-only
        STATUS	mandatory
        DESCRIPTION
                "total count of bipolar violations"
        ::= { wfDs1TotalEntry 6 }

    wfDs1TotalCVs OBJECT-TYPE
        SYNTAX	Gauge
        ACCESS	read-only
        STATUS	mandatory
        DESCRIPTION
                "total count of code violation error events"
        ::= { wfDs1TotalEntry 7 }

    wfDs1FeCurrent OBJECT-TYPE
        SYNTAX	SEQUENCE OF WfDs1FeCurrentEntry
        ACCESS	not-accessible
        STATUS	mandatory
        DESCRIPTION
                "The DS1 Far End Current table"
        ::= { wfDs1Group 5 }

    wfDs1FeCurrentEntry OBJECT-TYPE
        SYNTAX	WfDs1FeCurrentEntry
        ACCESS	not-accessible
        STATUS	mandatory
        DESCRIPTION
                "per circuit DS1 far end current objects
                wfDs1CurrentIndex corresponds to Wellfleet circuit
                number"
        INDEX	{ wfDs1FeCurrentIndex }
        ::= { wfDs1FeCurrent 1 }

    WfDs1FeCurrentEntry ::= SEQUENCE {
    	    wfDs1FeCurrentIndex
    		INTEGER,
    	    wfDs1FeCurrentESs
    		Counter,
    	    wfDs1FeCurrentSESs
    		Counter,
    	    wfDs1FeCurrentSEFs
    		Counter,
    	    wfDs1FeCurrentBPVs
    		Counter,
    	    wfDs1FeCurrentCVs
    		Counter
        }

    wfDs1FeCurrentIndex OBJECT-TYPE
        SYNTAX	INTEGER(1..1024)
        ACCESS	read-only
        STATUS	mandatory
        DESCRIPTION
                "this corresponds to the Wellfleet circuit number"
        ::= { wfDs1FeCurrentEntry 1 }

    wfDs1FeCurrentESs OBJECT-TYPE
        SYNTAX	Counter
        ACCESS	read-only
        STATUS	mandatory
        DESCRIPTION
                "the count of errored seconds in the current interval"
        ::= { wfDs1FeCurrentEntry 2 }

    wfDs1FeCurrentSESs OBJECT-TYPE
        SYNTAX	Counter
        ACCESS	read-only
        STATUS	mandatory
        DESCRIPTION
                "the count of severely errored seconds in the
                current interval"
        ::= { wfDs1FeCurrentEntry 3 }

    wfDs1FeCurrentSEFs OBJECT-TYPE
        SYNTAX	Counter
        ACCESS	read-only
        STATUS	mandatory
        DESCRIPTION
                "the count of severely errored framing seconds in the current
                interval"
        ::= { wfDs1FeCurrentEntry 4 }

    wfDs1FeCurrentBPVs OBJECT-TYPE
        SYNTAX	Counter
        ACCESS	read-only
        STATUS	mandatory
        DESCRIPTION
                "the count of bipolar violations in the current interval"
        ::= { wfDs1FeCurrentEntry 5 }

    wfDs1FeCurrentCVs OBJECT-TYPE
        SYNTAX	Counter
        ACCESS	read-only
        STATUS	mandatory
        DESCRIPTION
                "the count of code violation error events in the
                current interval"
        ::= { wfDs1FeCurrentEntry 6 }

    wfDs1FeInterval OBJECT-TYPE
        SYNTAX	SEQUENCE OF WfDs1FeIntervalEntry
        ACCESS	not-accessible
        STATUS	mandatory
        DESCRIPTION
                "The DS1 Far End Interval table"
        ::= { wfDs1Group 6 }

    wfDs1FeIntervalEntry OBJECT-TYPE
        SYNTAX	WfDs1FeIntervalEntry
        ACCESS	not-accessible
        STATUS	mandatory
        DESCRIPTION
                "per circuit DS1 far end interval objects -
                wfDs1FeIntervalIndex corresponds to Wellfleet circuit
                number, wfDs1FeIntervalNumber is the numbered
                previous 15-minute interval"
        INDEX	{ wfDs1FeIntervalIndex,
    		  wfDs1FeIntervalNumber }
        ::= { wfDs1FeInterval 1 }

    WfDs1FeIntervalEntry ::= SEQUENCE {
    	    wfDs1FeIntervalIndex
    		INTEGER,
    	    wfDs1FeIntervalNumber
    		INTEGER,
    	    wfDs1FeIntervalESs
    		Gauge,
    	    wfDs1FeIntervalSESs
    		Gauge,
    	    wfDs1FeIntervalSEFs
    		Gauge,
    	    wfDs1FeIntervalBPVs
    		Gauge,
    	    wfDs1FeIntervalCVs
    		Gauge
        }

    wfDs1FeIntervalIndex OBJECT-TYPE
        SYNTAX	INTEGER(1..1024)
        ACCESS	read-only
        STATUS	mandatory
        DESCRIPTION
                "this corresponds to the Wellfleet circuit number"
        ::= { wfDs1FeIntervalEntry 1 }

    wfDs1FeIntervalNumber OBJECT-TYPE
        SYNTAX	INTEGER(1..96)
        ACCESS	read-only
        STATUS	mandatory
        DESCRIPTION
                "1..96 where 1 is the most recent 15-minute interval and 96 is
                the least"
        ::= { wfDs1FeIntervalEntry 2 }

    wfDs1FeIntervalESs OBJECT-TYPE
        SYNTAX	Gauge
        ACCESS	read-only
        STATUS	mandatory
        DESCRIPTION
                "the count of errored seconds in the specified interval"
        ::= { wfDs1FeIntervalEntry 3 }

    wfDs1FeIntervalSESs OBJECT-TYPE
        SYNTAX	Gauge
        ACCESS	read-only
        STATUS	mandatory
        DESCRIPTION
                "the count of severely errored seconds in the specified
                interval"
        ::= { wfDs1FeIntervalEntry 4 }

    wfDs1FeIntervalSEFs OBJECT-TYPE
        SYNTAX	Gauge
        ACCESS	read-only
        STATUS	mandatory
        DESCRIPTION
                "the count of severely errored framing seconds in the specified
                interval"
        ::= { wfDs1FeIntervalEntry 5 }

    wfDs1FeIntervalBPVs OBJECT-TYPE
        SYNTAX	Gauge
        ACCESS	read-only
        STATUS	mandatory
        DESCRIPTION
                "the count of bipolar violations in the specified interval"
        ::= { wfDs1FeIntervalEntry 6 }

    wfDs1FeIntervalCVs OBJECT-TYPE
        SYNTAX	Gauge
        ACCESS	read-only
        STATUS	mandatory
        DESCRIPTION
                "the count of code violation error events in the
                specified interval"
        ::= { wfDs1FeIntervalEntry 7 }

    wfDs1FeTotal OBJECT-TYPE
        SYNTAX	SEQUENCE OF WfDs1FeTotalEntry
        ACCESS	not-accessible
        STATUS	mandatory
        DESCRIPTION
                "The DS1 Far End Total table"
        ::= { wfDs1Group 7 }

    wfDs1FeTotalEntry OBJECT-TYPE
        SYNTAX	WfDs1FeTotalEntry
        ACCESS	not-accessible
        STATUS	mandatory
        DESCRIPTION
                "per circuit DS1 far end total objects - wfDs1FeTotalIndex
                corresponds to Wellfleet circuit number"
        INDEX	{ wfDs1FeTotalIndex }
        ::= { wfDs1FeTotal 1 }

    WfDs1FeTotalEntry ::= SEQUENCE {
    	    wfDs1FeTotalIndex
    		INTEGER,
    	    wfDs1FeTotalESs
    		Gauge,
    	    wfDs1FeTotalSESs
    		Gauge,
    	    wfDs1FeTotalSEFs
    		Gauge,
    	    wfDs1FeTotalBPVs
    		Gauge,
    	    wfDs1FeTotalCVs
    		Gauge
        }

    wfDs1FeTotalIndex OBJECT-TYPE
        SYNTAX	INTEGER(1..1024)
        ACCESS	read-only
        STATUS	mandatory
        DESCRIPTION
                "this corresponds to the Wellfleet circuit number"
        ::= { wfDs1FeTotalEntry 1 }

    wfDs1FeTotalESs OBJECT-TYPE
        SYNTAX	Gauge
        ACCESS	read-only
        STATUS	mandatory
        DESCRIPTION
                "total count of errored seconds"
        ::= { wfDs1FeTotalEntry 2 }

    wfDs1FeTotalSESs OBJECT-TYPE
        SYNTAX	Gauge
        ACCESS	read-only
        STATUS	mandatory
        DESCRIPTION
                "total count of severely errored seconds"
        ::= { wfDs1FeTotalEntry 3 }

    wfDs1FeTotalSEFs OBJECT-TYPE
        SYNTAX	Gauge
        ACCESS	read-only
        STATUS	mandatory
        DESCRIPTION
                "total count of severely errored framing seconds"
        ::= { wfDs1FeTotalEntry 4 }

    wfDs1FeTotalBPVs OBJECT-TYPE
        SYNTAX	Gauge
        ACCESS	read-only
        STATUS	mandatory
        DESCRIPTION
                "total count of bipolar violations"
        ::= { wfDs1FeTotalEntry 5 }

    wfDs1FeTotalCVs OBJECT-TYPE
        SYNTAX	Gauge
        ACCESS	read-only
        STATUS	mandatory
        DESCRIPTION
                "total count of code violation error events"
        ::= { wfDs1FeTotalEntry 6 }

    END  -- Wellfleet-DS1-MIB
