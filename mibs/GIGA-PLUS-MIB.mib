GIGA-PLUS-MIB DEFINITIONS ::= BEGIN

IMPORTS
	MODULE-IDENTITY,
	OBJECT-TYPE,
	Counter32, Opaque, OBJECT-IDENTITY,
        IpAddress,
        Unsigned32,
        Counter64,
	NOTIFICATION-TYPE,
	enterprises
		FROM SNMPv2-SMI
	MODULE-COMPLIANCE
		FROM SNMPv2-CONF
        DisplayString
                FROM SNMPv2-TC;
	
-- *******************************************************************
-- * Trango module
-- *******************************************************************
trango		OBJECT IDENTIFIER ::= { enterprises 5454 }
tbw 		OBJECT IDENTIFIER ::= { trango 1 }
ptp		OBJECT IDENTIFIER ::= { tbw 80 }

sys		OBJECT IDENTIFIER ::= { ptp 1 }
modem		OBJECT IDENTIFIER ::= { ptp 2 }
rf		OBJECT IDENTIFIER ::= { ptp 3 }
gige		OBJECT IDENTIFIER ::= { ptp 4 }
tdm		OBJECT IDENTIFIER ::= { ptp 5 }
trangotrap	OBJECT IDENTIFIER ::= { ptp 6 }

-- *******************************************************************
-- ** System Information ** trango.tbw.ptp.sys
-- *******************************************************************

ver             OBJECT IDENTIFIER ::= { sys 1  }

sysFPGAVer      		OBJECT-TYPE
    	SYNTAX      		DisplayString (SIZE(0..80))
    	MAX-ACCESS  		read-only
	STATUS      		current
    	DESCRIPTION 		"FPGA 1 Version"
    	::= { ver 1 }

sysOSVer      			OBJECT-TYPE
    	SYNTAX      		DisplayString (SIZE(0..80))
    	MAX-ACCESS  		read-only
    	STATUS      		current
    	DESCRIPTION 		"IDU OS Version"
    	::= { ver 2 }

sysFWVer      			OBJECT-TYPE
    	SYNTAX      		DisplayString (SIZE(0..80))
    	MAX-ACCESS  		read-only
    	STATUS      		current
    	DESCRIPTION 		"IDU FW Version"
    	::= { ver 3 }

sysPICVer      			OBJECT-TYPE
    	SYNTAX      		DisplayString (SIZE(0..80))
    	MAX-ACCESS  		read-only
    	STATUS      		current
    	DESCRIPTION 		"IDU PIC Version"
    	::= { ver 4 }

sysModemVer      		OBJECT-TYPE
    	SYNTAX      		DisplayString (SIZE(0..80))
    	MAX-ACCESS  		read-only
    	STATUS      		current
    	DESCRIPTION 		"IDU Modem Version"
    	::= { ver 5 }

sysODUFWVer      		OBJECT-TYPE
    	SYNTAX      		DisplayString (SIZE(0..80))
    	MAX-ACCESS  		read-only
    	STATUS      		current
    	DESCRIPTION 		"ODU 1 FW Version"
    	::= { ver 6 }

prever             OBJECT IDENTIFIER ::= { sys 2  }

sysFPGAPreVer      		OBJECT-TYPE
    	SYNTAX      		DisplayString (SIZE(0..80))
    	MAX-ACCESS  		read-only
    	STATUS      		current
    	DESCRIPTION 		"FPGA 1 PreVersion"
    	::= { prever 1 }

sysOSPreVer      		OBJECT-TYPE
    	SYNTAX      		DisplayString (SIZE(0..80))
    	MAX-ACCESS  		read-only
    	STATUS      		current
    	DESCRIPTION 		"IDU OS PreVersion"
    	::= { prever 2 }

sysFWPreVer      		OBJECT-TYPE
    	SYNTAX      		DisplayString (SIZE(0..80))
    	MAX-ACCESS  		read-only
    	STATUS      		current
    	DESCRIPTION 		"IDU FW PreVersion"
    	::= { prever 3 }

sysPICPreVer      		OBJECT-TYPE
    	SYNTAX      		DisplayString (SIZE(0..80))
    	MAX-ACCESS  		read-only
    	STATUS      		current
    	DESCRIPTION 		"IDU PIC PreVersion"
    	::= { prever 4 }

sysModemPreVer      		OBJECT-TYPE
    	SYNTAX      		DisplayString (SIZE(0..80))
    	MAX-ACCESS  		read-only
    	STATUS      		current
    	DESCRIPTION 		"IDU Modem PreVersion"
    	::= { prever 5 }

sysODUFWPreVer      		OBJECT-TYPE
    	SYNTAX      		DisplayString (SIZE(0..80))
    	MAX-ACCESS  		read-only
    	STATUS      		current
    	DESCRIPTION 		"ODU 1 FW PreVersion"
    	::= { prever 6 }

model             		OBJECT IDENTIFIER ::= { sys 3  }

sysIDUModel      		OBJECT-TYPE
    	SYNTAX      		DisplayString (SIZE(0..80))
    	MAX-ACCESS  		read-only
    	STATUS      		current
    	DESCRIPTION 		"IDU Model"
    	::= { model 1 }

sysODUModel      		OBJECT-TYPE
    	SYNTAX      		DisplayString (SIZE(0..80))
    	MAX-ACCESS  		read-only
    	STATUS      		current
    	DESCRIPTION 		"ODU 1 model"
    	::= { model 2 }

sysIDUSerialID      		OBJECT-TYPE
    	SYNTAX      		DisplayString (SIZE(0..80))
    	MAX-ACCESS  		read-only
    	STATUS      		current
    	DESCRIPTION 		"IDU Serial ID"
    	::= { model 3 }

sysODUSerialID      		OBJECT-TYPE
    	SYNTAX      		DisplayString (SIZE(0..80))
    	MAX-ACCESS  		read-only
    	STATUS      		current
    	DESCRIPTION 		"ODU 1 Serial ID"
    	::= { model 4 }

mac 				OBJECT IDENTIFIER ::= { sys 4  }

sysMACeth1      		OBJECT-TYPE
    	SYNTAX      		DisplayString (SIZE(12))
    	MAX-ACCESS  		read-only
    	STATUS      		current
    	DESCRIPTION 		"MAC address of Ethernet 1"
    	::= { mac 1 }

sysMACeth2      		OBJECT-TYPE
    	SYNTAX      		DisplayString (SIZE(12))
    	MAX-ACCESS  		read-only
    	STATUS      		current
    	DESCRIPTION 		"MAC address of Ethernet 2"
    	::= { mac 2 }

ipconfig 			OBJECT IDENTIFIER ::= { sys 5  }

sysIpAddressess      		OBJECT-TYPE
    	SYNTAX      		IpAddress
    	MAX-ACCESS  		read-write
    	STATUS      		current
    	DESCRIPTION 		"IP address"
    	::= { ipconfig 1 }

sysSubnetMask      		OBJECT-TYPE
    	SYNTAX      		IpAddress
    	MAX-ACCESS  		read-write
    	STATUS      		current
    	DESCRIPTION 		"Subnet mask"
    	::= { ipconfig 2 }

sysDefaultGateway      		OBJECT-TYPE
    	SYNTAX      		IpAddress
    	MAX-ACCESS  		read-write
    	STATUS      		current
    	DESCRIPTION 		"Default gateway"
    	::= { ipconfig 3 }

sysRemarkSystem      		OBJECT-TYPE
    	SYNTAX      		DisplayString (SIZE(1..100))
    	MAX-ACCESS  		read-write
    	STATUS      		current
    	DESCRIPTION 		"System remarks"
    	::= { sys 6 }

ibm 				OBJECT IDENTIFIER ::= { sys 7  }

sysIBMEnable                   	OBJECT-TYPE
        SYNTAX                  INTEGER { disable(0), enable(1) }
        MAX-ACCESS              read-write
        STATUS                  current
        DESCRIPTION             "Enable/Disable Inband Management feature"
        ::= { ibm 1 }

sysIBMIp                       	OBJECT-TYPE
        SYNTAX                  IpAddress
        MAX-ACCESS              read-write
        STATUS                  current
        DESCRIPTION             "Assign/Display IBM Vlan IP"
        ::= { ibm 2 }

sysIBMNetmask                  	OBJECT-TYPE
        SYNTAX                  IpAddress
        MAX-ACCESS              read-write
        STATUS                  current
        DESCRIPTION             "Assign/Display IBM Netmask"
        ::= { ibm 3 }

community       		OBJECT IDENTIFIER ::= { sys 8 }

sysSNMPReadCommStr  		OBJECT-TYPE
    	SYNTAX      		DisplayString (SIZE(1..32))
    	MAX-ACCESS  		read-write
    	STATUS      		current
    	DESCRIPTION 		"SNMP agent read community string"
    	::= { community 1 }

sysSNMPWriteCommStr 		OBJECT-TYPE
    	SYNTAX      		DisplayString (SIZE(1..32))
    	MAX-ACCESS  		read-write
    	STATUS      		current
    	DESCRIPTION 		"SNMP agent Write community string"
    	::= { community 2 }

sysSNMPTrapCommStr 		OBJECT-TYPE
    	SYNTAX      		DisplayString (SIZE(1..32))
    	MAX-ACCESS  		read-write
    	STATUS      		current
    	DESCRIPTION 		"SNMP trap community string"
    	::= { community 3 }

trapinfo       			OBJECT IDENTIFIER ::= { sys 9 }

trap1       			OBJECT IDENTIFIER ::= { trapinfo 1 }

sysSNMPTrap1Enable           	OBJECT-TYPE
    	SYNTAX              	INTEGER { off(0), on(1) }
    	MAX-ACCESS          	read-write
    	STATUS              	current
    	DESCRIPTION         	"Enable/Disable SNMP Trap 1"
    	::= { trap1 1 }

sysSNMPTrapIp1       		OBJECT-TYPE
    	SYNTAX              	IpAddress
    	MAX-ACCESS          	read-write
    	STATUS              	current
    	DESCRIPTION         	"Trap Destination IP Address 1"
    	::= { trap1 2 }

trap2       			OBJECT IDENTIFIER ::= { trapinfo 2 }

sysSNMPTrap2Enable           	OBJECT-TYPE
    	SYNTAX              	INTEGER { off(0), on(1) }
    	MAX-ACCESS          	read-write
    	STATUS              	current
    	DESCRIPTION         	"Enable/Disable SNMP Trap 2"
    	::= { trap2 1 }

sysSNMPTrapIP2       		OBJECT-TYPE
    	SYNTAX              	IpAddress
    	MAX-ACCESS          	read-write
    	STATUS              	current
    	DESCRIPTION         	"Trap Destination IP Address 2"
    	::= { trap2 2 }

trap3       			OBJECT IDENTIFIER ::= { trapinfo 3 }

sysSNMPTrap3Enable           	OBJECT-TYPE
    	SYNTAX              	INTEGER { off(0), on(1) }
    	MAX-ACCESS          	read-write
    	STATUS              	current
    	DESCRIPTION         	"Enable/Disable SNMP Trap 2"
    	::= { trap3 1 }

sysSNMPTrapIP3       		OBJECT-TYPE
    	SYNTAX              	IpAddress
    	MAX-ACCESS          	read-write
    	STATUS              	current
    	DESCRIPTION         	"Trap Destination IP Address 3"
    	::= { trap3 2 }

trap4       			OBJECT IDENTIFIER ::= { trapinfo 4 }

sysSNMPTrap4Enable           	OBJECT-TYPE
    	SYNTAX              	INTEGER { off(0), on(1) }
    	MAX-ACCESS          	read-write
    	STATUS              	current
    	DESCRIPTION         	"Enable/Disable SNMP Trap 4"
    	::= { trap4 1 }

sysSNMPTrapIP4       		OBJECT-TYPE
    	SYNTAX              	IpAddress
    	MAX-ACCESS          	read-write
    	STATUS              	current
    	DESCRIPTION         	"Trap Destination IP Address 4"
    	::= { trap4 2 }

trap5       			OBJECT IDENTIFIER ::= { trapinfo 5 }

sysSNMPTrap5Enable           	OBJECT-TYPE
    	SYNTAX              	INTEGER { off(0), on(1) }
    	MAX-ACCESS          	read-write
    	STATUS              	current
    	DESCRIPTION         	"Enable/Disable SNMP Trap 5"
    	::= { trap5 1 }

sysSNMPTrapIP5       		OBJECT-TYPE
    	SYNTAX              	IpAddress
    	MAX-ACCESS          	read-write
    	STATUS              	current
    	DESCRIPTION         	"Trap Destination IP Address 5"
    	::= { trap5 2 }

image       			OBJECT IDENTIFIER ::= { sys 10 }

sysImageUpgrade           	OBJECT-TYPE
   	SYNTAX              	INTEGER { idu(0), odu(1) }
    	MAX-ACCESS          	read-write
    	STATUS              	current
    	DESCRIPTION         	"Upgrade SW image"
    	::= { image 1 }

sysImageUpgradeStatus   	OBJECT-TYPE
    	SYNTAX              	INTEGER { success(0), failed(1), inprogress(2) }
    	MAX-ACCESS          	read-only
    	STATUS              	current
    	DESCRIPTION         	"Get the current image upgrade progress status"
    	::= { image 2 }

sysImageToggle          	OBJECT-TYPE
    	SYNTAX              	INTEGER { current(0), toggle(1) }
    	MAX-ACCESS          	read-write
    	STATUS              	current
    	DESCRIPTION         	"Toggle to previous image"
    	::= { image 3 }

sysConfigOption         	OBJECT-TYPE
    	SYNTAX              	INTEGER { na(0), export(1), import(2), remove(3), save(4) }
    	MAX-ACCESS          	read-write
    	STATUS              	current
    	DESCRIPTION         	"Perform config export, import or remove configuration file"
    	::= { sys 11 }

diagnostic              	OBJECT IDENTIFIER ::= { sys 12 }

sysDiagnostic           	OBJECT-TYPE
    	SYNTAX              	INTEGER { na(0), diagnostic(1) }
    	MAX-ACCESS          	read-write
    	STATUS              	current
    	DESCRIPTION         	"Run diagnostic and put the data in a file"
    	::= { diagnostic 1 }

sysDiagnosticStatus     	OBJECT-TYPE
    	SYNTAX              	INTEGER { success(0), notready(1) }
    	MAX-ACCESS          	read-only
    	STATUS              	current
    	DESCRIPTION         	"Display current status of diagnostic command"
    	::= { diagnostic 2 }

syslog                  	OBJECT IDENTIFIER ::= { sys 13 }

sysSyslogExport         	OBJECT-TYPE
    	SYNTAX              	INTEGER { na(0), export(1), clear(2) }
    	MAX-ACCESS          	read-write
   	STATUS              	current
    	DESCRIPTION         	"export syslog into a file"
    	::= { syslog 1 }

sysSyslogLevel          	OBJECT-TYPE
    	SYNTAX              	INTEGER { nosyslog(0), level0(1), level1(2), level01(3),
				level2(4), level02(5), level12(6), level012(7) }
    	MAX-ACCESS          	read-write
    	STATUS              	current
    	DESCRIPTION         	"bitmap value for the loglevel"
    	::= { syslog 2 }

sysReboot               	OBJECT-TYPE
    	SYNTAX              	INTEGER { na(0), reboot(1) }
    	MAX-ACCESS          	read-write
    	STATUS              	current
    	DESCRIPTION         	"Reboot the system"
    	::= { sys 14 }

sysResetOption         		OBJECT-TYPE
    	SYNTAX              	INTEGER { ipconfig(0), factory(1), license(2) }
    	MAX-ACCESS          	read-write
    	STATUS              	current
    	DESCRIPTION         	"Perform config export, import or remove configuration file"
    	::= { sys 15 }

sysDatapath         		OBJECT-TYPE
    	SYNTAX              	INTEGER 
    	MAX-ACCESS          	read-write
    	STATUS              	current
    	DESCRIPTION         	"Configure Datapath profile"
    	::= { sys 16 }

alarm                   	OBJECT IDENTIFIER ::= { sys 17 }

sysAlarm1               	OBJECT-TYPE
    	SYNTAX              	INTEGER { off(0), on(1) }
    	MAX-ACCESS          	read-write
    	STATUS              	current
    	DESCRIPTION         	"Enable/Disable Alarm1"
    	::= { alarm 1 }

sysAlarm2               	OBJECT-TYPE
    	SYNTAX              	INTEGER { off(0), on(1) }
    	MAX-ACCESS          	read-write
    	STATUS              	current
    	DESCRIPTION         	"Enable/Disable Alarm2"
    	::= { alarm 2 }

sysFanCtrl         		OBJECT-TYPE
    	SYNTAX              	INTEGER { fanoff(0), fan1on(1), fan2ON(2) }
    	MAX-ACCESS          	read-write
    	STATUS              	current
    	DESCRIPTION         	"Turn On/Off Fans"
    	::= { sys 18 }

sysIDUTemp              	OBJECT-TYPE
    	SYNTAX              	INTEGER
    	MAX-ACCESS          	read-only
    	STATUS              	current
    	DESCRIPTION         	"PIC's current temperatur reading in Celsius"
    	::= { sys 19 }

daemon                  	OBJECT IDENTIFIER ::= { sys 20 }

sysHTTPD                	OBJECT-TYPE
    	SYNTAX              	INTEGER { off(0), on(1) }
    	MAX-ACCESS          	read-write
    	STATUS              	current
    	DESCRIPTION         	"Enable or disable HTTPD"
    	::= { daemon 1 }

sysSNMPD                	OBJECT-TYPE
    	SYNTAX              	INTEGER { off(0), on(1) }
    	MAX-ACCESS          	read-write
    	STATUS              	current
    	DESCRIPTION         	"Enable or disable SNMPD"
    	::= { daemon 2 }

sysTFTPD                	OBJECT-TYPE
    	SYNTAX              	INTEGER { off(0), on(1) }
    	MAX-ACCESS          	read-write
    	STATUS              	current
    	DESCRIPTION         	"Enable or disable TFPTD"
    	::= { daemon 3 }

sysTelnetd                	OBJECT-TYPE
    	SYNTAX              	INTEGER { off(0), on(1) }
    	MAX-ACCESS          	read-write
    	STATUS              	current
    	DESCRIPTION         	"Enable or disable Telnetd"
    	::= { daemon 4 }

sysRPSEnable              	OBJECT-TYPE
    	SYNTAX              	INTEGER { off(0), on(1) }
    	MAX-ACCESS          	read-write
    	STATUS              	current
    	DESCRIPTION         	"Enable or disable Rapid port shutdown feature"
    	::= { sys 21 }

sysClearCounter              	OBJECT-TYPE
    	SYNTAX              	INTEGER { na(0), clear(1) }
    	MAX-ACCESS          	read-write
    	STATUS              	current
    	DESCRIPTION         	"Clear data port counters"
    	::= { sys 22 }

tdm-mode                     	OBJECT IDENTIFIER ::= { sys 23 }

sysTdmMode              	OBJECT-TYPE
    	SYNTAX              	INTEGER { t1(0), e1(1) }
    	MAX-ACCESS          	read-only
    	STATUS              	current
    	DESCRIPTION         	"Select TDM Mdoe - T1 or E1"
    	::= { tdm-mode 1 }

sysTdmCoding            	OBJECT-TYPE
    	SYNTAX              	INTEGER { ami(0), b8zs(1), hdb3(2) }
    	MAX-ACCESS          	read-only
    	STATUS              	current
    	DESCRIPTION         	"Select TDM line coding"
    	::= { tdm-mode 2 }

license                     	OBJECT IDENTIFIER ::= { sys 24 }

speedlicense                     OBJECT IDENTIFIER ::= { license 1 }

sysSpeedLicenseEnable          OBJECT-TYPE
        SYNTAX          	INTEGER { none(0), key1(1), key2(2) }
    	MAX-ACCESS          	read-only
    	STATUS              	current
    	DESCRIPTION         	"License Key enable flag for the speed"
    	::= { speedlicense 1 }

sysSpeedLicenseKey1              OBJECT-TYPE
    	SYNTAX      		DisplayString (SIZE(0..40))
    	MAX-ACCESS          	read-write
    	STATUS              	current
    	DESCRIPTION         	"LicenseKey for the frequency"
    	::= { speedlicense 2 }

sysSpeedLicenseKey2              OBJECT-TYPE
    	SYNTAX      		DisplayString (SIZE(0..40))
    	MAX-ACCESS          	read-write
    	STATUS              	current
    	DESCRIPTION         	"LicenseKey for the frequency"
    	::= { speedlicense 3 }

tdmlicense                     OBJECT IDENTIFIER ::= { license 2 }

sysTDMLicenseEnable          OBJECT-TYPE
        SYNTAX          	INTEGER { disable(0), enable(1) }
    	MAX-ACCESS          	read-only
    	STATUS              	current
    	DESCRIPTION         	"LicenseKey enable flag for the TDM"
    	::= { tdmlicense 1 }

sysTDMLicenseKey             OBJECT-TYPE
    	SYNTAX      		DisplayString (SIZE(0..40))
    	MAX-ACCESS          	read-write
    	STATUS              	current
    	DESCRIPTION         	"LicenseKey for the TDM"
    	::= { tdmlicense 2 }

sysIDULED             		OBJECT-TYPE
    	SYNTAX      		INTEGER { rssi(0), tdm(1) }
    	MAX-ACCESS          	read-write
    	STATUS              	current
    	DESCRIPTION         	"IDU LED display option"
    	::= { sys 25 }

sysFailoverMode             	OBJECT-TYPE
    	SYNTAX      		INTEGER { off(0), on-port-off(1), on-port-on(2) }
    	MAX-ACCESS          	read-write
    	STATUS              	current
    	DESCRIPTION         	"Failover feature"
    	::= { sys 26 }

sysUtype             		OBJECT-TYPE
    	SYNTAX      		INTEGER { no-utype(0), active(1), standby(2) }
    	MAX-ACCESS          	read-write
    	STATUS              	current
    	DESCRIPTION         	"Current Unit type"
    	::= { sys 27 }

sysSyncStatus             	OBJECT-TYPE
    	SYNTAX      		INTEGER { not-synchronized(0), synchronized(1) }
    	MAX-ACCESS          	read-write
    	STATUS              	current
    	DESCRIPTION         	"Perform synchronization from active unit"
    	::= { sys 28 }

standbystatus             	OBJECT IDENTIFIER ::= { sys 29  }

sysStandbyLinkStatus             OBJECT-TYPE
    	SYNTAX      		INTEGER { no-lock(0), lock(1) }
    	MAX-ACCESS          	read-only
    	STATUS              	current
    	DESCRIPTION         	"Standby link status"
    	::= { standbystatus 1 }

sysStandbyODUStatus             OBJECT-TYPE
    	SYNTAX      		INTEGER { no-lock(0), lock(1) }
    	MAX-ACCESS          	read-only
    	STATUS              	current
    	DESCRIPTION         	"Standby link status"
    	::= { standbystatus 2 }

sysStandbyRSSI             	OBJECT-TYPE
    	SYNTAX      		INTEGER 
    	MAX-ACCESS          	read-only
    	STATUS              	current
    	DESCRIPTION         	"Standby link status"
    	::= { standbystatus 3 }

sysStandbyMSE             	OBJECT-TYPE
    	SYNTAX      		INTEGER 
    	MAX-ACCESS          	read-only
    	STATUS              	current
    	DESCRIPTION         	"Standby link status"
    	::= { standbystatus 4 }

sysGuardTime             	OBJECT-TYPE
    	SYNTAX      		INTEGER 
    	MAX-ACCESS          	read-write
    	STATUS              	current
    	DESCRIPTION         	"Guardtime for re-enable HW switchover"
    	::= { sys 30 }

reload             		OBJECT IDENTIFIER ::= { sys 31  }

sysReloadIn             	OBJECT-TYPE
    	SYNTAX      		INTEGER 
    	MAX-ACCESS          	read-write
    	STATUS              	current
    	DESCRIPTION         	"Time duration for the reload feature"
    	::= { reload 1 }

sysReloadCancel             	OBJECT-TYPE
    	SYNTAX      		INTEGER 
    	MAX-ACCESS          	read-write
    	STATUS              	current
    	DESCRIPTION         	"Cancel reload timer"
    	::= { reload 2 }

sysReloadRemain             	OBJECT-TYPE
    	SYNTAX      		INTEGER 
    	MAX-ACCESS          	read-only
    	STATUS              	current
    	DESCRIPTION         	"remaining time before reload occurs"
    	::= { reload 3 }

snap             		OBJECT IDENTIFIER ::= { sys 32  }

sysStatusSave             	OBJECT-TYPE
    	SYNTAX      		INTEGER 
    	MAX-ACCESS          	read-write
    	STATUS              	current
    	DESCRIPTION         	"Take a snap shot of current config and save on flash"
    	::= { snap 1 }

sysStatusCompare             	OBJECT-TYPE
    	SYNTAX      		INTEGER 
    	MAX-ACCESS          	read-write
    	STATUS              	current
    	DESCRIPTION         	"Compare current config with the saved config"
    	::= { snap 2 }

remote             		OBJECT IDENTIFIER ::= { sys 33  }

sysRemoteLinkStatus            	OBJECT-TYPE
    	SYNTAX      		INTEGER 
    	MAX-ACCESS          	read-only
    	STATUS              	current
    	DESCRIPTION         	"Display remote link status"
    	::= { remote 1 }

sysRemoteLinkODUStatus          OBJECT-TYPE
    	SYNTAX      		INTEGER 
    	MAX-ACCESS          	read-only
    	STATUS              	current
    	DESCRIPTION         	"Display remote ODU status"
    	::= { remote 2 }

remote-rssi             	OBJECT IDENTIFIER ::= { remote 3  }

sysRemoteLinkRSSI          	OBJECT-TYPE
    	SYNTAX      		Opaque 
    	MAX-ACCESS          	read-only
    	STATUS              	current
    	DESCRIPTION         	"Display remote RSSI in float value"
    	::= { remote-rssi 1 }

sysRemoteLinkRSSI          	OBJECT-TYPE
    	SYNTAX      		INTEGER 
    	MAX-ACCESS          	read-only
    	STATUS              	current
    	DESCRIPTION         	"Display remote RSSI in integer value"
    	::= { remote-rssi 2 }



remote-mse             	OBJECT IDENTIFIER ::= { remote 4  }

sysRemoteLinkMSE          	OBJECT-TYPE
    	SYNTAX      		Opaque 
    	MAX-ACCESS          	read-only
    	STATUS              	current
    	DESCRIPTION         	"Display remote MSE in float value"
    	::= { remote-mse 1 }

sysRemoteLinkMSE          	OBJECT-TYPE
    	SYNTAX      		INTEGER 
    	MAX-ACCESS          	read-only
    	STATUS              	current
    	DESCRIPTION         	"Display remote MSE in integer value"
    	::= { remote-mse 2 }


threshold             		OBJECT IDENTIFIER ::= { sys 34  }

th-rssi             		OBJECT IDENTIFIER ::= { threshold 1  }

sysThresholdRSSIMin          	OBJECT-TYPE
    	SYNTAX      		INTEGER 
    	MAX-ACCESS          	read-write
    	STATUS              	current
    	DESCRIPTION         	"Display/Configure minimum threshold RSSI"
    	::= { th-rssi 1 }

sysThresholdRSSIMax          	OBJECT-TYPE
    	SYNTAX      		INTEGER 
    	MAX-ACCESS          	read-write
    	STATUS              	current
    	DESCRIPTION         	"Display/Configure maximum threshold RSSI"
    	::= { th-rssi 2 }

sysThresholdRSSIAction          OBJECT-TYPE
    	SYNTAX      		INTEGER 
    	MAX-ACCESS          	read-write
    	STATUS              	current
    	DESCRIPTION         	"Display/Configure threshold RSSI action"
    	::= { th-rssi 3 }

th-mse                          OBJECT IDENTIFIER ::= { threshold 2  }

sysThresholdMSEMin             OBJECT-TYPE
        SYNTAX                  INTEGER
        MAX-ACCESS              read-write
        STATUS                  current
        DESCRIPTION             "Display/Configure minimum threshold MSE"
        ::= { th-mse 1 }

sysThresholdMSEMax             OBJECT-TYPE
        SYNTAX                  INTEGER 
        MAX-ACCESS              read-write
        STATUS                  current
        DESCRIPTION             "Display/Configure maximum threshold MSE"
        ::= { th-mse 2 }

sysThresholdMSEAction          OBJECT-TYPE
        SYNTAX                  INTEGER 
        MAX-ACCESS              read-write
        STATUS                  current
        DESCRIPTION             "Display/Configure threshold MSE action"
        ::= { th-mse 3 }       

th-ber                          OBJECT IDENTIFIER ::= { threshold 3  }

sysThresholdBERMin              OBJECT-TYPE
        SYNTAX                  INTEGER
        MAX-ACCESS              read-write
        STATUS                  current
        DESCRIPTION             "Display/Configure minimum threshold BER"
        ::= { th-ber 1 }

sysThresholdBERMax              OBJECT-TYPE
        SYNTAX                  INTEGER
        MAX-ACCESS              read-write
        STATUS                  current
        DESCRIPTION             "Display/Configure maximum threshold BER"
        ::= { th-ber 2 }

sysThresholdBERAction          OBJECT-TYPE
        SYNTAX                  INTEGER
        MAX-ACCESS              read-write
        STATUS                  current
        DESCRIPTION             "Display/Configure threshold BER action"
        ::= { th-ber 3 } 

th-fer                          OBJECT IDENTIFIER ::= { threshold 4  }

sysThresholdFERMin              OBJECT-TYPE
        SYNTAX                  INTEGER
        MAX-ACCESS              read-write
        STATUS                  current
        DESCRIPTION             "Display/Configure minimum threshold FER"
        ::= { th-fer 1 }

sysThresholdFERMax              OBJECT-TYPE
        SYNTAX                  INTEGER
        MAX-ACCESS              read-write
        STATUS                  current
        DESCRIPTION             "Display/Configure maximum threshold FER"
        ::= { th-fer 2 }

sysThresholdFERAction          OBJECT-TYPE
        SYNTAX                  INTEGER
        MAX-ACCESS              read-write
        STATUS                  current
        DESCRIPTION             "Display/Configure threshold FER action"
        ::= { th-fer 3 }

th-idu-temp                     OBJECT IDENTIFIER ::= { threshold 5  }

sysThresholdIDUTempMin          OBJECT-TYPE
        SYNTAX                  INTEGER
        MAX-ACCESS              read-write
        STATUS                  current
        DESCRIPTION             "Display/Configure minimum IDU temp"
        ::= { th-idu-temp 1 }

sysThresholdIDUTempMax              OBJECT-TYPE
        SYNTAX                  INTEGER
        MAX-ACCESS              read-write
        STATUS                  current
        DESCRIPTION             "Display/Configure maximum IDU temp"
        ::= { th-idu-temp 2 }

sysThresholdIDUTempAction          OBJECT-TYPE
        SYNTAX                  INTEGER
        MAX-ACCESS              read-write
        STATUS                  current
        DESCRIPTION             "Display/Configure threshold IDU temp"
        ::= { th-idu-temp 3 }

th-odu-temp                     OBJECT IDENTIFIER ::= { threshold 6  }

sysThresholdODUTempMin          OBJECT-TYPE
        SYNTAX                  INTEGER
        MAX-ACCESS              read-write
        STATUS                  current
        DESCRIPTION             "Display/Configure minimum ODU temp"
        ::= { th-odu-temp 1 }

sysThresholdODUTempMax              OBJECT-TYPE
        SYNTAX                  INTEGER
        MAX-ACCESS              read-write
        STATUS                  current
        DESCRIPTION             "Display/Configure maximum ODU temp"
        ::= { th-odu-temp 2 }

sysThresholdODUTempAction          OBJECT-TYPE
        SYNTAX                  INTEGER
        MAX-ACCESS              read-write
        STATUS                  current
        DESCRIPTION             "Display/Configure threshold ODU temp"
        ::= { th-odu-temp 3 }

th-in-port                     OBJECT IDENTIFIER ::= { threshold 7  }

sysThresholdInPortUtilMin          OBJECT-TYPE
        SYNTAX                  INTEGER
        MAX-ACCESS              read-write
        STATUS                  current
        DESCRIPTION             "Display/Configure minimum In port util"
        ::= { th-in-port 1 }

sysThresholdInPortUtilMax       OBJECT-TYPE
        SYNTAX                  INTEGER
        MAX-ACCESS              read-write
        STATUS                  current
        DESCRIPTION             "Display/Configure maximum In port util"
        ::= { th-in-port 2 }

sysThresholdInPortUtilAction    OBJECT-TYPE
        SYNTAX                  INTEGER
        MAX-ACCESS              read-write
        STATUS                  current
        DESCRIPTION             "Display/Configure threshold In port util action"
        ::= { th-in-port 3 }

th-out-port                     OBJECT IDENTIFIER ::= { threshold 8  }

sysThresholdOutPortUtilMin          OBJECT-TYPE
        SYNTAX                  INTEGER
        MAX-ACCESS              read-write
        STATUS                  current
        DESCRIPTION             "Display/Configure minimum Out port util"
        ::= { th-out-port 1 }

sysThresholdOutPortUtilMax       OBJECT-TYPE
        SYNTAX                  INTEGER
        MAX-ACCESS              read-write
        STATUS                  current
        DESCRIPTION             "Display/Configure maximum Out port util"
        ::= { th-out-port 2 }

sysThresholdOutPortUtilAction    OBJECT-TYPE
        SYNTAX                  INTEGER
        MAX-ACCESS              read-write
        STATUS                  current
        DESCRIPTION             "Display/Configure threshold Out port util action"
        ::= { th-out-port 3 }

sysEgressMargin    		OBJECT-TYPE
        SYNTAX                  INTEGER
        MAX-ACCESS              read-write
        STATUS                  current
        DESCRIPTION             "Display/Configure Ethernet Egress margin"
        ::= { sys 35 }

sysQOSMode    			OBJECT-TYPE
        SYNTAX                  INTEGER
        MAX-ACCESS              read-write
        STATUS                  current
        DESCRIPTION             "Display/Configure QOS Mode"
        ::= { sys 36 }

sysWebRefreshRate    		OBJECT-TYPE
        SYNTAX                  INTEGER
        MAX-ACCESS              read-write
        STATUS                  current
        DESCRIPTION             "Display/Configure Web refresh rate"
        ::= { sys 37 }

modemLoopbackMode       	OBJECT-TYPE
        SYNTAX          	INTEGER { off(0), digital(1), if(2), rfgen(3), rfrefl(4) }
        MAX-ACCESS      	read-write
        STATUS          	current
        DESCRIPTION     	"Set/Display the Loopback Mode"
        ::= { modem 1 }

modemDataPattern        	OBJECT-TYPE
        SYNTAX          	INTEGER { external(0), internal(1) }
        MAX-ACCESS      	read-write
        STATUS          	current
        DESCRIPTION     	"Set/Display the current Loopback Pattern (source)"
        ::= { modem 2 }

acm             		OBJECT IDENTIFIER ::= { modem 3  }

modemACMEnable        		OBJECT-TYPE
        SYNTAX          	INTEGER { off(0), on(1) }
        MAX-ACCESS      	read-write
        STATUS          	current
        DESCRIPTION     	"Set/Display acm feature for modem 2"
        ::= { acm 1 }

profile             		OBJECT IDENTIFIER ::= { acm 2  }

modemACMProfileQPSKEnable      OBJECT-TYPE
        SYNTAX          	INTEGER { off(0), on(1) }
        MAX-ACCESS      	read-only
        STATUS          	current
        DESCRIPTION     	"Set/Display ACM profile enable flag for modem 2"
        ::= { profile 1 }

modemACMProfile16QEnable      OBJECT-TYPE
        SYNTAX          	INTEGER { off(0), on(1) }
        MAX-ACCESS      	read-only
        STATUS          	current
        DESCRIPTION     	"Set/Display ACM profile enable flag for modem 2"
        ::= { profile 2 }

modemACMProfile32QEnable      OBJECT-TYPE
        SYNTAX          	INTEGER { off(0), on(1) }
        MAX-ACCESS      	read-only
        STATUS          	current
        DESCRIPTION     	"Set/Display ACM profile enable flag for modem 2"
        ::= { profile 3 }

modemACMProfile64QEnable      OBJECT-TYPE
        SYNTAX          	INTEGER { off(0), on(1) }
        MAX-ACCESS      	read-only
        STATUS          	current
        DESCRIPTION     	"Set/Display ACM profile enable flag for modem 2"
        ::= { profile 4 }

modemACMProfile128QEnable      OBJECT-TYPE
        SYNTAX          	INTEGER { off(0), on(1) }
        MAX-ACCESS      	read-only
        STATUS          	current
        DESCRIPTION     	"Set/Display ACM profile enable flag for modem 2"
        ::= { profile 5 }

modemACMProfile256QEnable      OBJECT-TYPE
        SYNTAX          	INTEGER { off(0), on(1) }
        MAX-ACCESS      	read-only
        STATUS          	current
        DESCRIPTION     	"Set/Display ACM profile enable flag for modem 2"
        ::= { profile 6 }

improve             		OBJECT IDENTIFIER ::= { acm 3  }

qpsk-improve                    OBJECT IDENTIFIER ::= { improve 1  }

modemACMQPSKMSEImporve      	OBJECT-TYPE
        SYNTAX          	Opaque
        MAX-ACCESS      	read-write
        STATUS          	current
        DESCRIPTION     	"Set/Display ACM MSE improve value for QPSK"
        ::= { qpsk-improve 1 }

modemACMQPSKMSEImporveInt       OBJECT-TYPE
        SYNTAX                  INTEGER
        MAX-ACCESS              read-write
        STATUS                  current
        DESCRIPTION             "Set/Display ACM MSE improve value for QPSK in INTEGER"
        ::= { qpsk-improve 2 }

qam16-improve                   OBJECT IDENTIFIER ::= { improve 2 }

modemACM16QMSEImprove      	OBJECT-TYPE
        SYNTAX          	Opaque
        MAX-ACCESS      	read-write
        STATUS          	current
        DESCRIPTION     	"Set/Display ACM MSE improve value for 16Q"
        ::= { qam16-improve 1 }

modemACM16QMSEImproveInt        OBJECT-TYPE
        SYNTAX                  INTEGER
        MAX-ACCESS              read-write
        STATUS                  current
        DESCRIPTION             "Set/Display ACM MSE improve value for 16Q in INTEGER"
        ::= { qam16-improve 2 }

qam32-improve                   OBJECT IDENTIFIER ::= { improve 3 }

modemACM32QMSEImprove      	OBJECT-TYPE
        SYNTAX          	Opaque
        MAX-ACCESS      	read-write
        STATUS          	current
        DESCRIPTION     	"Set/Display ACM MSE improve value for 32Q"
        ::= { qam32-improve 1 }

modemACM32QMSEImproveInt        OBJECT-TYPE
        SYNTAX                  INTEGER
        MAX-ACCESS              read-write
        STATUS                  current
        DESCRIPTION             "Set/Display ACM MSE improve value for 32Q INTEGER"
        ::= { qam32-improve 2 }

qam64-improve                   OBJECT IDENTIFIER ::= { improve 4 }

modemACM64QMSEImprove      	OBJECT-TYPE
        SYNTAX          	Opaque
        MAX-ACCESS      	read-write
        STATUS          	current
        DESCRIPTION     	"Set/Display ACM MSE improve value for 64Q"
        ::= { qam64-improve 1 }

modemACM64QMSEImproveInt        OBJECT-TYPE
        SYNTAX                  INTEGER
        MAX-ACCESS              read-write
        STATUS                  current
        DESCRIPTION             "Set/Display ACM MSE improve value for 64Q in INTEGER"
        ::= { qam64-improve 2 }

qam128-improve                  OBJECT IDENTIFIER ::= { improve 5 }

modemACM128QMSEImprove      	OBJECT-TYPE
        SYNTAX          	Opaque
        MAX-ACCESS      	read-write
        STATUS          	current
        DESCRIPTION     	"Set/Display ACM MSE improve value for 128Q"
        ::= { qam128-improve 1 }

modemACM128QMSEImproveInt       OBJECT-TYPE
        SYNTAX                  INTEGER
        MAX-ACCESS              read-write
        STATUS                  current
        DESCRIPTION             "Set/Display ACM MSE improve value for 128Q in INTEGER"
        ::= { qam128-improve 2 }

qam256-improve                  OBJECT IDENTIFIER ::= { improve 6 }

modemACM256QMSEImprove      	OBJECT-TYPE
        SYNTAX          	Opaque
        MAX-ACCESS      	read-write
        STATUS          	current
        DESCRIPTION     	"Set/Display ACM MSE improve value for 256Q"
        ::= { qam256-improve 1 }

modemACM256QMSEImproveInt       OBJECT-TYPE
        SYNTAX                  Opaque
        MAX-ACCESS              read-write
        STATUS                  current
        DESCRIPTION             "Set/Display ACM MSE improve value for 256Q in INTEGER"
        ::= { qam256-improve 2 }


degrade             		OBJECT IDENTIFIER ::= { acm 4  }

qpsk-degrade                    OBJECT IDENTIFIER ::= { degrade 1  }

modemACMQPSKMSEDegrade      	OBJECT-TYPE
        SYNTAX          	Opaque
        MAX-ACCESS      	read-write
        STATUS          	current
        DESCRIPTION     	"Set/Display ACM MSE degrade value for QPSK"
        ::= { qpsk-degrade 1 }

modemACMQPSKMSEDegradeInt       OBJECT-TYPE
        SYNTAX                  INTEGER
        MAX-ACCESS              read-write
        STATUS                  current
        DESCRIPTION             "Set/Display ACM MSE degrade value for QPSK in INTEGER"
        ::= { qpsk-degrade 2 }

qam16-degrade                   OBJECT IDENTIFIER ::= { degrade 2  }

modemACM16QMSEDegrade      	OBJECT-TYPE
        SYNTAX          	Opaque
        MAX-ACCESS      	read-write
        STATUS          	current
        DESCRIPTION     	"Set/Display ACM MSE degrade value for 16Q"
        ::= { qam16-degrade 1 }

modemACM16QMSEDegradeInt        OBJECT-TYPE
        SYNTAX                  INTEGER
        MAX-ACCESS              read-write
        STATUS                  current
        DESCRIPTION             "Set/Display ACM MSE degrade value for 16Q in INTEGER"
        ::= { qam16-degrade 2 }

qam32-degrade                   OBJECT IDENTIFIER ::= { degrade 3 }

modemACM32QMSEDegrade      	OBJECT-TYPE
        SYNTAX          	Opaque
        MAX-ACCESS      	read-write
        STATUS          	current
        DESCRIPTION     	"Set/Display ACM MSE degrade value for 32Q"
        ::= { qam32-degrade 1 }

modemACM32QMSEDegradeInt        OBJECT-TYPE
        SYNTAX                  INTEGER
        MAX-ACCESS              read-write
        STATUS                  current
        DESCRIPTION             "Set/Display ACM MSE degrade value for 32Q in INTEGER"
        ::= { qam32-degrade 2 }

qam64-degrade                   OBJECT IDENTIFIER ::= { degrade 4 }

modemACM64QMSEDegrade      	OBJECT-TYPE
        SYNTAX          	Opaque
        MAX-ACCESS      	read-write
        STATUS          	current
        DESCRIPTION     	"Set/Display ACM MSE degrade value for 64Q"
        ::= { qam64-degrade 1 }

modemACM64QMSEDegradeInt        OBJECT-TYPE
        SYNTAX                  INTEGER
        MAX-ACCESS              read-write
        STATUS                  current
        DESCRIPTION             "Set/Display ACM MSE degrade value for 64Q in INTEGER"
        ::= { qam64-degrade 2 }

qam128-degrade                  OBJECT IDENTIFIER ::= { degrade 5 }

modemACM128QMSEDegrade      	OBJECT-TYPE
        SYNTAX          	Opaque
        MAX-ACCESS      	read-write
        STATUS          	current
        DESCRIPTION     	"Set/Display ACM MSE degrade value for 128Q"
        ::= { qam128-degrade 1 }

modemACM128QMSEDegradeInt       OBJECT-TYPE
        SYNTAX                  INTEGER
        MAX-ACCESS              read-write
        STATUS                  current
        DESCRIPTION             "Set/Display ACM MSE degrade value for 128Q in INTEGER"
        ::= { qam128-degrade 2 }

qam256-degrade                  OBJECT IDENTIFIER ::= { degrade 6 }

modemACM256QMSEDegrade      	OBJECT-TYPE
        SYNTAX          	Opaque
        MAX-ACCESS      	read-write
        STATUS          	current
        DESCRIPTION     	"Set/Display ACM MSE degrade value for 256Q"
        ::= { qam256-degrade 1 }

modemACM256QMSEDegradeInt       OBJECT-TYPE
        SYNTAX                  INTEGER
        MAX-ACCESS              read-write
        STATUS                  current
        DESCRIPTION             "Set/Display ACM MSE degrade value for 256Q in INTEGER"
        ::= { qam256-degrade 2 }


link             		OBJECT IDENTIFIER ::= { modem 4  }

modemBER      			OBJECT-TYPE
        SYNTAX          	INTEGER
        MAX-ACCESS      	read-only
        STATUS          	current
        DESCRIPTION     	"Set/Display BER value"
        ::= { link 1 }

mse             		OBJECT IDENTIFIER ::= { link 2  }

modemMSE      			OBJECT-TYPE
        SYNTAX          	INTEGER
        MAX-ACCESS      	read-only
        STATUS          	current
        DESCRIPTION     	"Display MSE value"
        ::= { mse 1 }

modemMSEInt      		OBJECT-TYPE
        SYNTAX          	INTEGER
        MAX-ACCESS      	read-only
        STATUS          	current
        DESCRIPTION     	"Display MSE value"
        ::= { mse 2 }

modemMSEInst      		OBJECT-TYPE
        SYNTAX          	INTEGER
        MAX-ACCESS      	read-only
        STATUS          	current
        DESCRIPTION     	"Display instantaneous MSE value"
        ::= { mse 3 }

modemFER      			OBJECT-TYPE
        SYNTAX          	INTEGER
        MAX-ACCESS      	read-only
        STATUS          	current
        DESCRIPTION     	"Set/Display FER value"
        ::= { link 3 }

lock             		OBJECT IDENTIFIER ::= { modem 5  }

modemLockStatus      		OBJECT-TYPE
        SYNTAX          	INTEGER { nolock(0), lock(1), na(2) }
        MAX-ACCESS      	read-only
        STATUS          	current
        DESCRIPTION     	"Set/Display link lock statsu"
        ::= { lock 1 }

modemTimingLockStatus      	OBJECT-TYPE
        SYNTAX          	INTEGER { nolock(0), lock(1), na(2) }
        MAX-ACCESS      	read-only
        STATUS          	current
        DESCRIPTION     	"Set/Display timing lock statsu"
        ::= { lock 2 }

modemPreambleLockStatus      	OBJECT-TYPE
        SYNTAX          	INTEGER { nolock(0), lock(1), na(2) }
        MAX-ACCESS      	read-only
        STATUS          	current
        DESCRIPTION     	"Set/Display preamble lock statsu"
        ::= { lock 3 }

modemLDPCLocktatus      	OBJECT-TYPE
        SYNTAX          	INTEGER { nolock(0), lock(1) , na(2)}
        MAX-ACCESS      	read-only
        STATUS          	current
        DESCRIPTION     	"Set/Display LDPC lock statsu"
        ::= { lock 4 }

debug             		OBJECT IDENTIFIER ::= { modem 6  }

modemLDPCStressDecoder      	OBJECT-TYPE
        SYNTAX          	INTEGER
        MAX-ACCESS      	read-only
        STATUS          	current
        DESCRIPTION     	"Display LDPC Stress Decoder"
        ::= { debug 1 }

modemIDURSSI      		OBJECT-TYPE
        SYNTAX          	INTEGER
        MAX-ACCESS      	read-only
        STATUS          	current
        DESCRIPTION     	"Display IDU RSSI"
        ::= { debug 2 }

modemRadioMSE      		OBJECT-TYPE
        SYNTAX          	INTEGER
        MAX-ACCESS      	read-only
        STATUS          	current
        DESCRIPTION     	"Display Radio MSE"
        ::= { debug 3 }

modemUncorrectedBlocks      	OBJECT-TYPE
        SYNTAX          	INTEGER
        MAX-ACCESS      	read-only
        STATUS          	current
        DESCRIPTION     	"Display Uncorrected blocks"
        ::= { debug 4 }

custom             		OBJECT IDENTIFIER ::= { modem 7  }

modemCustomProfileEnable      	OBJECT-TYPE
        SYNTAX          	INTEGER
        MAX-ACCESS      	read-write
        STATUS          	current
        DESCRIPTION     	"Display custom profile enable option"
        ::= { custom 1 }

modemCustomProfileDatapath      OBJECT-TYPE
        SYNTAX          	INTEGER
        MAX-ACCESS      	read-only
        STATUS          	current
        DESCRIPTION     	"Display custom profile datapath option"
        ::= { custom 2 }

modemCustomProfileAcm           OBJECT-TYPE
        SYNTAX          	INTEGER
        MAX-ACCESS      	read-only
        STATUS          	current
        DESCRIPTION     	"Display custom profile ACM enable option"
        ::= { custom 3 }

modemCustomProfileBandwidth     OBJECT-TYPE
        SYNTAX          	INTEGER
        MAX-ACCESS      	read-only
        STATUS          	current
        DESCRIPTION     	"Display custom profile bandwidth option"
        ::= { custom 4 }

modemCustomProfileModulation    OBJECT-TYPE
        SYNTAX          	INTEGER
        MAX-ACCESS      	read-only
        STATUS          	current
        DESCRIPTION     	"Display custom profile modulation option"
        ::= { custom 5 }

freq             		OBJECT IDENTIFIER ::= { rf 1  }

txfreq             		OBJECT IDENTIFIER ::= { freq 1  }

rfTxFrequency      		OBJECT-TYPE
        SYNTAX          	Opaque
        MAX-ACCESS      	read-write
        STATUS          	current
        DESCRIPTION     	"Set/Display TX frequency"
        ::= { txfreq 1 }

rfTxFrequencyInt      		OBJECT-TYPE
        SYNTAX          	INTEGER
        MAX-ACCESS      	read-write
        STATUS          	current
        DESCRIPTION     	"Set/Display TX frequency in integer value"
        ::= { txfreq 2 }

rxfreq             		OBJECT IDENTIFIER ::= { freq 2  }

rfRxFrequency      		OBJECT-TYPE
        SYNTAX          	Opaque
        MAX-ACCESS      	read-only
        STATUS          	current
        DESCRIPTION     	"Display RX frequency"
        ::= { rxfreq 1 }

rfRxFrequencyInt      		OBJECT-TYPE
        SYNTAX          	INTEGER
        MAX-ACCESS      	read-only
        STATUS          	current
        DESCRIPTION     	"Display RX frequency in integer value"
        ::= { rxfreq 2 }

duplex             		OBJECT IDENTIFIER ::= { freq 3  }

rfFreqDuplex      		OBJECT-TYPE
        SYNTAX          	Opaque
        MAX-ACCESS      	read-write
        STATUS          	current
        DESCRIPTION     	"Display frequency duplex"
        ::= { duplex 1 }

rfFreqDuplexInt      		OBJECT-TYPE
        SYNTAX          	INTEGER
        MAX-ACCESS      	read-write
        STATUS          	current
        DESCRIPTION     	"Display frequency duplex in integer value"
        ::= { duplex 2 }

freqmax            		OBJECT IDENTIFIER ::= { freq 4  }

rfFreqMax      			OBJECT-TYPE
        SYNTAX          	Opaque
        MAX-ACCESS      	read-only
        STATUS          	current
        DESCRIPTION     	"Display maximum TX frequency"
        ::= { freqmax 1 }

rfFreqMaxInt      		OBJECT-TYPE
        SYNTAX          	INTEGER
        MAX-ACCESS      	read-only
        STATUS          	current
        DESCRIPTION     	"Display maximum TX frequency in integer value"
        ::= { freqmax 2 }

freqmin           		OBJECT IDENTIFIER ::= { freq 5  }

rfFreqMin      			OBJECT-TYPE
        SYNTAX          	Opaque
        MAX-ACCESS      	read-only
        STATUS          	current
        DESCRIPTION     	"Display minimum TX frequency"
        ::= { freqmin 1 }

rfFreqMinInt      		OBJECT-TYPE
        SYNTAX          	INTEGER
        MAX-ACCESS      	read-only
        STATUS          	current
        DESCRIPTION     	"Display minimum TX frequency in integer value"
        ::= { freqmin 2 }



rfDefaultOpmode      		OBJECT-TYPE
    	SYNTAX              	INTEGER { off(0), on(1) }
        MAX-ACCESS      	read-write
        STATUS          	current
        DESCRIPTION     	"Set/Display default opmode setting  "
        ::= { rf 2 }

rfOpmode      			OBJECT-TYPE
    	SYNTAX              	INTEGER { off(0), on(1) }
        MAX-ACCESS      	read-write
        STATUS          	current
        DESCRIPTION     	"Set/Display current opmode setting  "
        ::= { rf 3 }

power             		OBJECT IDENTIFIER ::= { rf 4  }

rfPower      			OBJECT-TYPE
        SYNTAX          	Opaque
        MAX-ACCESS      	read-write
        STATUS          	current
        DESCRIPTION     	"Set/Display TX power.  SNMPc does not support
				setting and displaying float value."
        ::= { power 1 }

rfPowerInt      		OBJECT-TYPE
        SYNTAX          	INTEGER
        MAX-ACCESS      	read-write
        STATUS          	current
        DESCRIPTION     	"Set/Display TX power 1/10 dB in step size "
        ::= { power 2 }


cableloss             		OBJECT IDENTIFIER ::= { rf 5  }

cableloss140             	OBJECT IDENTIFIER ::= { cableloss 1  }

rfCableloss140      		OBJECT-TYPE
        SYNTAX          	Opaque
        MAX-ACCESS      	read-write
        STATUS          	current
        DESCRIPTION     	"Set/Display Cableloss 140.  SNMPc does not
				support setting and displaying float value."
        ::= { cableloss140  1 }

rfCableloss140Int      		OBJECT-TYPE
        SYNTAX          	INTEGER
        MAX-ACCESS      	read-write
        STATUS          	current
        DESCRIPTION     	"Set/Display Cableloss 140 in 100th dB"
        ::= { cableloss140  2 }

cableloss315             	OBJECT IDENTIFIER ::= { cableloss 2  }

rfCableloss315      		OBJECT-TYPE
        SYNTAX          	Opaque
        MAX-ACCESS      	read-write
        STATUS          	current
        DESCRIPTION     	"Set/Display Cableloss 315. SNMPc does not
                                support setting and displaying float value. "
        ::= { cableloss315 1 }

rfCableloss315Int      		OBJECT-TYPE
        SYNTAX          	INTEGER
        MAX-ACCESS      	read-write
        STATUS          	current
        DESCRIPTION     	"Set/Display Cableloss 315 in 100th dB "
        ::= { cableloss315 2 }

cableloss915             	OBJECT IDENTIFIER ::= { cableloss 3  }

rfCableloss915      		OBJECT-TYPE
        SYNTAX          	Opaque
        MAX-ACCESS      	read-write
        STATUS          	current
        DESCRIPTION     	"Set/Display Cableloss 915. SNMPc does not
                                support setting and displaying float value.  "
        ::= { cableloss915 1 }

rfCableloss915Int      		OBJECT-TYPE
        SYNTAX          	INTEGER
        MAX-ACCESS      	read-write
        STATUS          	current
        DESCRIPTION     	"Set/Display Cableloss 915 in 100th dB "
        ::= { cableloss915 2 }

speed             		OBJECT IDENTIFIER ::= { rf 6  }

rfChannelWidth      		OBJECT-TYPE
        SYNTAX          	INTEGER
        MAX-ACCESS      	read-write
        STATUS          	current
        DESCRIPTION     	"Set/Display Speed channel width  "
        ::= { speed 1 }

rfModulation      		OBJECT-TYPE
	SYNTAX          	INTEGER { qpsk(0), qam16(1), qam32(2), qam64(3), qam128(4), qam256(5) }
        MAX-ACCESS      	read-write
        STATUS          	current
        DESCRIPTION     	"Set/Display Speed modulation  "
        ::= { speed 2 }

symrate                           OBJECT IDENTIFIER ::= { speed 3  }

rfSymrate      			OBJECT-TYPE
        SYNTAX          	Opaque
        MAX-ACCESS      	read-only
        STATUS          	current
        DESCRIPTION     	"Display Speed symbol rate  "
        ::= { symrate 1 }

rfSymrateInt      		OBJECT-TYPE
        SYNTAX          	INTEGER
        MAX-ACCESS      	read-only
        STATUS          	current
        DESCRIPTION     	"Display Speed symbol rate in INTEGER "
        ::= { symrate 2 }

sp                           	OBJECT IDENTIFIER ::= { speed 4  }

rfSpeed      			OBJECT-TYPE
        SYNTAX          	Opaque
        MAX-ACCESS      	read-only
        STATUS          	current
        DESCRIPTION     	"Display Speed rate  "
        ::= { sp 1 }

rfSpeedInt      		OBJECT-TYPE
        SYNTAX          	INTEGER
        MAX-ACCESS      	read-only
        STATUS          	current
        DESCRIPTION     	"Display Speed rate in INTEGER "
        ::= { sp 2 }

atpc             		OBJECT IDENTIFIER ::= { rf 7  }

rfATPCEnable      		OBJECT-TYPE
    	SYNTAX              	INTEGER { off(0), on(1) }
        MAX-ACCESS      	read-write
        STATUS          	current
        DESCRIPTION     	"Set/Display current status of ATPC feature  "
        ::= { atpc 1 }

rfATPCMaxPower      		OBJECT-TYPE
        SYNTAX          	Opaque
        MAX-ACCESS      	read-write
        STATUS          	current
        DESCRIPTION     	"Display ATPC maximum power  "
        ::= { atpc 2 }

rfATPCStepSize      		OBJECT-TYPE
        SYNTAX          	INTEGER
        MAX-ACCESS      	read-write
        STATUS          	current
        DESCRIPTION     	"Display ATPC step size  "
        ::= { atpc 3 }

rfAlignmentMode      		OBJECT-TYPE
    	SYNTAX              	INTEGER { off(0), on(1) }
        MAX-ACCESS      	read-write
        STATUS          	current
        DESCRIPTION     	"Set/Display current status of alignment mode  "
        ::= { rf 8 }

targetrssi             		OBJECT IDENTIFIER ::= { rf 9  }

rfTargetRSSI      		OBJECT-TYPE
        SYNTAX          	Opaque
        MAX-ACCESS      	read-write
        STATUS          	current
        DESCRIPTION     	"Set/Display target RSSI value SNMPc does not
                                support setting and displaying float value."
        ::= { targetrssi 1 }

rfTargetRSSIInt      		OBJECT-TYPE
        SYNTAX          	INTEGER
        MAX-ACCESS      	read-write
        STATUS          	current
        DESCRIPTION     	"Set/Display target RSSI value in 100th of dB"
        ::= { targetrssi 2 }

rfODULEDEnable      		OBJECT-TYPE
    	SYNTAX              	INTEGER { off(0), on(1) }
        MAX-ACCESS      	read-write
        STATUS          	current
        DESCRIPTION     	"Set/Display current status of ODU LED display  "
        ::= { rf 10 }

rfODUPowerEnable      		OBJECT-TYPE
    	SYNTAX              	INTEGER { off(0), on(1) }
        MAX-ACCESS      	read-write
        STATUS          	current
        DESCRIPTION     	"Set/Display current status of ODU power  "
        ::= { rf 11 }

rfODURxAGC      		OBJECT-TYPE
    	SYNTAX              	INTEGER { off(0), on(1) }
        MAX-ACCESS      	read-write
        STATUS          	current
        DESCRIPTION     	"Set/Display current status of ODU RXAGC loop  "
        ::= { rf 12 }

rfODUTemp      		OBJECT-TYPE
    	SYNTAX              	INTEGER
        MAX-ACCESS      	read-only
        STATUS          	current
        DESCRIPTION     	"Display current ODU temperature  "
        ::= { rf 13 }

rssi             		OBJECT IDENTIFIER ::= { rf 14  }

rfRSSI      			OBJECT-TYPE
        SYNTAX          	Opaque
        MAX-ACCESS      	read-only
        STATUS          	current
        DESCRIPTION     	"Display current RSSI value in float "
        ::= { rssi 1 }

rfRSSIInt      			OBJECT-TYPE
    	SYNTAX              	INTEGER
        MAX-ACCESS      	read-only
        STATUS          	current
        DESCRIPTION     	"Display current RSSI value  "
        ::= { rssi 2 }

rfRSSIInst      		OBJECT-TYPE
    	SYNTAX              	INTEGER
        MAX-ACCESS      	read-only
        STATUS          	current
        DESCRIPTION     	"Display instantanous RSSI value"
        ::= { rssi 3 }

pll             		OBJECT IDENTIFIER ::= { rf 15  }

rfODURFpll      		OBJECT-TYPE
    	SYNTAX              	INTEGER { nolock(0), lock(1), na(2) }
        MAX-ACCESS      	read-write
        STATUS          	current
        DESCRIPTION     	"Display current status of ODU RF PLL  "
        ::= { pll 1 }

rfODUIFpll      		OBJECT-TYPE
    	SYNTAX              	INTEGER { nolock(0), lock(1), na(2) }
        MAX-ACCESS      	read-write
        STATUS          	current
        DESCRIPTION     	"Display current status of ODU IF PLL  "
        ::= { pll 2 }

rfODUTxpll      		OBJECT-TYPE
    	SYNTAX              	INTEGER { nolock(0), lock(1), na(2) }
        MAX-ACCESS      	read-write
        STATUS          	current
        DESCRIPTION     	"Display current status of ODU TX PLL  "
        ::= { pll 3 }

rfODURxpll      		OBJECT-TYPE
    	SYNTAX              	INTEGER { nolock(0), lock(1), na(2) }
        MAX-ACCESS      	read-write
        STATUS          	current
        DESCRIPTION     	"Display current status of ODU RX PLL  "
        ::= { pll 4 }

rfIDUTxpll      		OBJECT-TYPE
    	SYNTAX              	INTEGER { nolock(0), lock(1), na(2) }
        MAX-ACCESS      	read-write
        STATUS          	current
        DESCRIPTION     	"Display current status of IDU TX PLL  "
        ::= { pll 5 }

incounter             		OBJECT IDENTIFIER ::= { rf 16  }

rfInDataOctets      		OBJECT-TYPE
    	SYNTAX             	Counter32
        MAX-ACCESS      	read-only
        STATUS          	current
        DESCRIPTION     	"Display RF IN data octets counter  "
        ::= { incounter 1 }

rfInDataPackets      		OBJECT-TYPE
    	SYNTAX             	Counter32
        MAX-ACCESS      	read-only
        STATUS          	current
        DESCRIPTION     	"Display RF IN data packets counter  "
        ::= { incounter 2 }

rfInDataDropPackets      	OBJECT-TYPE
    	SYNTAX             	Counter32
        MAX-ACCESS      	read-only
        STATUS          	current
        DESCRIPTION     	"Display RF IN data drop packets counter  "
        ::= { incounter 3 }

rfInPortRate      		OBJECT-TYPE
    	SYNTAX             	INTEGER
        MAX-ACCESS      	read-only
        STATUS          	current
        DESCRIPTION     	"Display RF IN port rate  "
        ::= { incounter 4 }

rfInPortUtil      		OBJECT-TYPE
    	SYNTAX             	INTEGER
        MAX-ACCESS      	read-only
        STATUS          	current
        DESCRIPTION     	"Display RF IN port utilization  "
        ::= { incounter 5 }

outcounter             		OBJECT IDENTIFIER ::= { rf 17  }

rfOutDataOctets      		OBJECT-TYPE
    	SYNTAX             	Counter32
        MAX-ACCESS      	read-only
        STATUS          	current
        DESCRIPTION     	"Display RF OUT data octets counter  "
        ::= { outcounter 1 }

rfOutDataPackets      		OBJECT-TYPE
    	SYNTAX             	Counter32
        MAX-ACCESS      	read-only
        STATUS          	current
        DESCRIPTION     	"Display RF OUT data packets counter  "
        ::= { outcounter 2 }

rfOutPortRate      		OBJECT-TYPE
    	SYNTAX             	INTEGER
        MAX-ACCESS      	read-only
        STATUS          	current
        DESCRIPTION     	"Display RF OUT port rate  "
        ::= { outcounter 3 }

rfOutPortUtil      		OBJECT-TYPE
    	SYNTAX             	INTEGER
        MAX-ACCESS      	read-only
        STATUS          	current
        DESCRIPTION     	"Display RF OUT port utilization  "
        ::= { outcounter 4 }


eth1             		OBJECT IDENTIFIER ::= { gige 1  }

config1             		OBJECT IDENTIFIER ::= { eth1 1  }

gigeEth1AutNegotiate      	OBJECT-TYPE
    	SYNTAX              	INTEGER { off(0), on(1) }
        MAX-ACCESS      	read-write
        STATUS          	current
        DESCRIPTION     	"Set/Display auto neogitate setting for ETH 1"
        ::= { config1 1 }

gigeEth1Duplex      		OBJECT-TYPE
    	SYNTAX              	INTEGER { half(0), full(1) }
        MAX-ACCESS      	read-write
        STATUS          	current
        DESCRIPTION     	"Set/Display duplex setting for ETH 1"
        ::= { config1 2 }

gigeEth1Enable      		OBJECT-TYPE
    	SYNTAX              	INTEGER { off(0), on(1) }
        MAX-ACCESS      	read-write
        STATUS          	current
        DESCRIPTION     	"Set/Display enable setting for ETH 1"
        ::= { config1 3 }

gigeEth1MaxRate      		OBJECT-TYPE
    	SYNTAX              	INTEGER
        MAX-ACCESS      	read-write
        STATUS          	current
        DESCRIPTION     	"Set/Display max rate setting for ETH 1"
        ::= { config1 4 }

gigeEth1PauseFrame      	OBJECT-TYPE
    	SYNTAX              	INTEGER { off(0), on(1) }
        MAX-ACCESS      	read-write
        STATUS          	current
        DESCRIPTION     	"Set/Display pause frame setting for ETH 1"
        ::= { config1 5 }

gigeEth1Priority      		OBJECT-TYPE
        SYNTAX          	INTEGER
        MAX-ACCESS      	read-write
        STATUS          	current
        DESCRIPTION     	"Set/Display priority setting for ETH 1"
        ::= { config1 6 }

gigeEth1Speed      		OBJECT-TYPE
        SYNTAX          	INTEGER 
        MAX-ACCESS      	read-write
        STATUS          	current
        DESCRIPTION     	"Set/Display speed setting for ETH 1"
        ::= { config1 7 }

gigeEth1Status      		OBJECT-TYPE
    	SYNTAX              	INTEGER { off(0), on(1) }
        MAX-ACCESS      	read-only
        STATUS          	current
        DESCRIPTION     	"Set/Display port status for ETH 1"
        ::= { config1 8 }

counter1             		OBJECT IDENTIFIER ::= { eth1 2  }

gigeEth1InOctets      		OBJECT-TYPE
        SYNTAX          	Counter32 
        MAX-ACCESS      	read-only
        STATUS          	current
        DESCRIPTION     	"Display ETH1 IN octets counter"
        ::= { counter1 1 }

gigeEth1InUcastPackets      	OBJECT-TYPE
        SYNTAX          	Counter32 
        MAX-ACCESS      	read-only
        STATUS          	current
        DESCRIPTION     	"Display ETH1 IN unicast packet counter"
        ::= { counter1 2 }

gigeEth1InNUcastPackets      	OBJECT-TYPE
        SYNTAX          	Counter32 
        MAX-ACCESS      	read-only
        STATUS          	current
        DESCRIPTION     	"Display ETH1 IN non-unicast packet counter"
        ::= { counter1 3 }

gigeEth1InTotalPackets      	OBJECT-TYPE
        SYNTAX          	Counter32 
        MAX-ACCESS      	read-only
        STATUS          	current
        DESCRIPTION     	"Display ETH1 IN non-unicast packet counter"
        ::= { counter1 4 }

gigeEth1OutOctets      		OBJECT-TYPE
        SYNTAX          	Counter32 
        MAX-ACCESS      	read-only
        STATUS          	current
        DESCRIPTION     	"Display ETH1 OUT octets counter"
        ::= { counter1 5 }

gigeEth1OutUcastPackets      	OBJECT-TYPE
        SYNTAX          	Counter32 
        MAX-ACCESS      	read-only
        STATUS          	current
        DESCRIPTION     	"Display ETH1 OUT unicast packet counter"
        ::= { counter1 6 }

gigeEth1OutNUcastPackets      	OBJECT-TYPE
        SYNTAX          	Counter32 
        MAX-ACCESS      	read-only
        STATUS          	current
        DESCRIPTION     	"Display ETH1 OUT non-unicast packet counter"
        ::= { counter1 7 }

gigeEth1OutTotalPackets      	OBJECT-TYPE
        SYNTAX          	Counter32 
        MAX-ACCESS      	read-only
        STATUS          	current
        DESCRIPTION     	"Display ETH1 OUT total packet counter"
        ::= { counter1 8 }

gigeEth1CRCError      		OBJECT-TYPE
        SYNTAX          	Counter32 
        MAX-ACCESS      	read-only
        STATUS          	current
        DESCRIPTION     	"Display ETH1 CRC error counter"
        ::= { counter1 9 }

gigeEth1CollisionError      	OBJECT-TYPE
        SYNTAX          	Counter32 
        MAX-ACCESS      	read-only
        STATUS          	current
        DESCRIPTION     	"Display ETH1 Collision error counter"
        ::= { counter1 10 }

gigeEth1InPortRate      	OBJECT-TYPE
        SYNTAX          	INTEGER 
        MAX-ACCESS      	read-only
        STATUS          	current
        DESCRIPTION     	"Display ETH1 In Port Rate"
        ::= { counter1 11 }

gigeEth1InPortUtil      	OBJECT-TYPE
        SYNTAX          	INTEGER 
        MAX-ACCESS      	read-only
        STATUS          	current
        DESCRIPTION     	"Display ETH1 In Port utilization"
        ::= { counter1 12 }

gigeEth1OutPortRate      	OBJECT-TYPE
        SYNTAX          	INTEGER 
        MAX-ACCESS      	read-only
        STATUS          	current
        DESCRIPTION     	"Display ETH1 Out Port Rate"
        ::= { counter1 13 }

gigeEth1OutPortUtil      	OBJECT-TYPE
        SYNTAX          	INTEGER 
        MAX-ACCESS      	read-only
        STATUS          	current
        DESCRIPTION     	"Display ETH1 Out Port utilization"
        ::= { counter1 14 }

dscp             		OBJECT IDENTIFIER ::= { eth1 3  }

gigeEth1DSCPSource1      	OBJECT-TYPE
        SYNTAX          	INTEGER 
        MAX-ACCESS      	read-write
        STATUS          	current
        DESCRIPTION     	"Set/Display ETH1 priority number for DSCP source 1"
        ::= { dscp 1 }

gigeEth1DSCPSource2      	OBJECT-TYPE
        SYNTAX          	INTEGER 
        MAX-ACCESS      	read-write
        STATUS          	current
        DESCRIPTION     	"Set/Display ETH1 priority number for DSCP source 2"
        ::= { dscp 2 }


gigeEth1DSCPSource3      	OBJECT-TYPE
        SYNTAX          	INTEGER 
        MAX-ACCESS      	read-write
        STATUS          	current
        DESCRIPTION     	"Set/Display ETH1 priority number for DSCP source 3"
        ::= { dscp 3 }


gigeEth1DSCPSource4      	OBJECT-TYPE
        SYNTAX          	INTEGER 
        MAX-ACCESS      	read-write
        STATUS          	current
        DESCRIPTION     	"Set/Display ETH1 priority number for DSCP source 4"
        ::= { dscp 4 }


gigeEth1DSCPSource5      	OBJECT-TYPE
        SYNTAX          	INTEGER 
        MAX-ACCESS      	read-write
        STATUS          	current
        DESCRIPTION     	"Set/Display ETH1 priority number for DSCP source 5"
        ::= { dscp 5 }


gigeEth1DSCPSource6      	OBJECT-TYPE
        SYNTAX          	INTEGER 
        MAX-ACCESS      	read-write
        STATUS          	current
        DESCRIPTION     	"Set/Display ETH1 priority number for DSCP source 6"
        ::= { dscp 6 }


gigeEth1DSCPSource7      	OBJECT-TYPE
        SYNTAX          	INTEGER 
        MAX-ACCESS      	read-write
        STATUS          	current
        DESCRIPTION     	"Set/Display ETH1 priority number for DSCP source 7"
        ::= { dscp 7 }


gigeEth1DSCPSource8      	OBJECT-TYPE
        SYNTAX          	INTEGER 
        MAX-ACCESS      	read-write
        STATUS          	current
        DESCRIPTION     	"Set/Display ETH1 priority number for DSCP source 8"
        ::= { dscp 8 }


gigeEth1DSCPSource9      	OBJECT-TYPE
        SYNTAX          	INTEGER 
        MAX-ACCESS      	read-write
        STATUS          	current
        DESCRIPTION     	"Set/Display ETH1 priority number for DSCP source 9"
        ::= { dscp 9 }


gigeEth1DSCPSource10      	OBJECT-TYPE
        SYNTAX          	INTEGER 
        MAX-ACCESS      	read-write
        STATUS          	current
        DESCRIPTION     	"Set/Display ETH1 priority number for DSCP source 10"
        ::= { dscp 10 }


gigeEth1DSCPSource11      	OBJECT-TYPE
        SYNTAX          	INTEGER 
        MAX-ACCESS      	read-write
        STATUS          	current
        DESCRIPTION     	"Set/Display ETH1 priority number for DSCP source 11"
        ::= { dscp 11 }


gigeEth1DSCPSource12      	OBJECT-TYPE
        SYNTAX          	INTEGER 
        MAX-ACCESS      	read-write
        STATUS          	current
        DESCRIPTION     	"Set/Display ETH1 priority number for DSCP source 12"
        ::= { dscp 12 }


gigeEth1DSCPSource13      	OBJECT-TYPE
        SYNTAX          	INTEGER 
        MAX-ACCESS      	read-write
        STATUS          	current
        DESCRIPTION     	"Set/Display ETH1 priority number for DSCP source 13"
        ::= { dscp 13 }


gigeEth1DSCPSource14      	OBJECT-TYPE
        SYNTAX          	INTEGER 
        MAX-ACCESS      	read-write
        STATUS          	current
        DESCRIPTION     	"Set/Display ETH1 priority number for DSCP source 14"
        ::= { dscp 14 }


gigeEth1DSCPSource15      	OBJECT-TYPE
        SYNTAX          	INTEGER 
        MAX-ACCESS      	read-write
        STATUS          	current
        DESCRIPTION     	"Set/Display ETH1 priority number for DSCP source 15"
        ::= { dscp 15 }

gigeEth1DSCPSource16      	OBJECT-TYPE
        SYNTAX          	INTEGER 
        MAX-ACCESS      	read-write
        STATUS          	current
        DESCRIPTION     	"Set/Display ETH1 priority number for DSCP source 16"
        ::= { dscp 16 }


gigeEth1DSCPSource17      	OBJECT-TYPE
        SYNTAX          	INTEGER 
        MAX-ACCESS      	read-write
        STATUS          	current
        DESCRIPTION     	"Set/Display ETH1 priority number for DSCP source 17"
        ::= { dscp 17 }


gigeEth1DSCPSource18      	OBJECT-TYPE
        SYNTAX          	INTEGER 
        MAX-ACCESS      	read-write
        STATUS          	current
        DESCRIPTION     	"Set/Display ETH1 priority number for DSCP source 18"
        ::= { dscp 18 }


gigeEth1DSCPSource19      	OBJECT-TYPE
        SYNTAX          	INTEGER 
        MAX-ACCESS      	read-write
        STATUS          	current
        DESCRIPTION     	"Set/Display ETH1 priority number for DSCP source 19"
        ::= { dscp 19 }


gigeEth1DSCPSource20      	OBJECT-TYPE
        SYNTAX          	INTEGER 
        MAX-ACCESS      	read-write
        STATUS          	current
        DESCRIPTION     	"Set/Display ETH1 priority number for DSCP source 20"
        ::= { dscp 20 }


gigeEth1DSCPSource21      	OBJECT-TYPE
        SYNTAX          	INTEGER 
        MAX-ACCESS      	read-write
        STATUS          	current
        DESCRIPTION     	"Set/Display ETH1 priority number for DSCP source 21"
        ::= { dscp 21 }


gigeEth1DSCPSource22      	OBJECT-TYPE
        SYNTAX          	INTEGER 
        MAX-ACCESS      	read-write
        STATUS          	current
        DESCRIPTION     	"Set/Display ETH1 priority number for DSCP source 22"
        ::= { dscp 22 }


gigeEth1DSCPSource23      	OBJECT-TYPE
        SYNTAX          	INTEGER 
        MAX-ACCESS      	read-write
        STATUS          	current
        DESCRIPTION     	"Set/Display ETH1 priority number for DSCP source 23"
        ::= { dscp 23 }


gigeEth1DSCPSource24      	OBJECT-TYPE
        SYNTAX          	INTEGER 
        MAX-ACCESS      	read-write
        STATUS          	current
        DESCRIPTION     	"Set/Display ETH1 priority number for DSCP source 24"
        ::= { dscp 24 }


gigeEth1DSCPSource25      	OBJECT-TYPE
        SYNTAX          	INTEGER 
        MAX-ACCESS      	read-write
        STATUS          	current
        DESCRIPTION     	"Set/Display ETH1 priority number for DSCP source 25"
        ::= { dscp 25 }

gigeEth1DSCPSource26      	OBJECT-TYPE
        SYNTAX          	INTEGER 
        MAX-ACCESS      	read-write
        STATUS          	current
        DESCRIPTION     	"Set/Display ETH1 priority number for DSCP source 26"
        ::= { dscp 26 }

gigeEth1DSCPSource27      	OBJECT-TYPE
        SYNTAX          	INTEGER 
        MAX-ACCESS      	read-write
        STATUS          	current
        DESCRIPTION     	"Set/Display ETH1 priority number for DSCP source 27"
        ::= { dscp 27 }

gigeEth1DSCPSource28      	OBJECT-TYPE
        SYNTAX          	INTEGER 
        MAX-ACCESS      	read-write
        STATUS          	current
        DESCRIPTION     	"Set/Display ETH1 priority number for DSCP source 28"
        ::= { dscp 28 }

gigeEth1DSCPSource29      	OBJECT-TYPE
        SYNTAX          	INTEGER 
        MAX-ACCESS      	read-write
        STATUS          	current
        DESCRIPTION     	"Set/Display ETH1 priority number for DSCP source 29"
        ::= { dscp 29 }

gigeEth1DSCPSource30      	OBJECT-TYPE
        SYNTAX          	INTEGER 
        MAX-ACCESS      	read-write
        STATUS          	current
        DESCRIPTION     	"Set/Display ETH1 priority number for DSCP source 30"
        ::= { dscp 30 }

gigeEth1DSCPSource31      	OBJECT-TYPE
        SYNTAX          	INTEGER 
        MAX-ACCESS      	read-write
        STATUS          	current
        DESCRIPTION     	"Set/Display ETH1 priority number for DSCP source 31"
        ::= { dscp 31 }

gigeEth1DSCPSource32      	OBJECT-TYPE
        SYNTAX          	INTEGER 
        MAX-ACCESS      	read-write
        STATUS          	current
        DESCRIPTION     	"Set/Display ETH1 priority number for DSCP source 32"
        ::= { dscp 32 }

gigeEth1DSCPSource33      	OBJECT-TYPE
        SYNTAX          	INTEGER 
        MAX-ACCESS      	read-write
        STATUS          	current
        DESCRIPTION     	"Set/Display ETH1 priority number for DSCP source 33"
        ::= { dscp 33 }

gigeEth1DSCPSource34      	OBJECT-TYPE
        SYNTAX          	INTEGER 
        MAX-ACCESS      	read-write
        STATUS          	current
        DESCRIPTION     	"Set/Display ETH1 priority number for DSCP source 34"
        ::= { dscp 34 }

gigeEth1DSCPSource35      	OBJECT-TYPE
        SYNTAX          	INTEGER 
        MAX-ACCESS      	read-write
        STATUS          	current
        DESCRIPTION     	"Set/Display ETH1 priority number for DSCP source 35"
        ::= { dscp 35 }

gigeEth1DSCPSource36      	OBJECT-TYPE
        SYNTAX          	INTEGER 
        MAX-ACCESS      	read-write
        STATUS          	current
        DESCRIPTION     	"Set/Display ETH1 priority number for DSCP source 36"
        ::= { dscp 36 }

gigeEth1DSCPSource37      	OBJECT-TYPE
        SYNTAX          	INTEGER 
        MAX-ACCESS      	read-write
        STATUS          	current
        DESCRIPTION     	"Set/Display ETH1 priority number for DSCP source 37"
        ::= { dscp 37 }

gigeEth1DSCPSource38      	OBJECT-TYPE
        SYNTAX          	INTEGER 
        MAX-ACCESS      	read-write
        STATUS          	current
        DESCRIPTION     	"Set/Display ETH1 priority number for DSCP source 38"
        ::= { dscp 38 }

gigeEth1DSCPSource39      	OBJECT-TYPE
        SYNTAX          	INTEGER 
        MAX-ACCESS      	read-write
        STATUS          	current
        DESCRIPTION     	"Set/Display ETH1 priority number for DSCP source 39"
        ::= { dscp 39 }

gigeEth1DSCPSource40      	OBJECT-TYPE
        SYNTAX          	INTEGER 
        MAX-ACCESS      	read-write
        STATUS          	current
        DESCRIPTION     	"Set/Display ETH1 priority number for DSCP source 40"
        ::= { dscp 40 }

gigeEth1DSCPSource41      	OBJECT-TYPE
        SYNTAX          	INTEGER 
        MAX-ACCESS      	read-write
        STATUS          	current
        DESCRIPTION     	"Set/Display ETH1 priority number for DSCP source 41"
        ::= { dscp 41 }

gigeEth1DSCPSource42      	OBJECT-TYPE
        SYNTAX          	INTEGER 
        MAX-ACCESS      	read-write
        STATUS          	current
        DESCRIPTION     	"Set/Display ETH1 priority number for DSCP source 42"
        ::= { dscp 42 }

gigeEth1DSCPSource43      	OBJECT-TYPE
        SYNTAX          	INTEGER 
        MAX-ACCESS      	read-write
        STATUS          	current
        DESCRIPTION     	"Set/Display ETH1 priority number for DSCP source 43"
        ::= { dscp 43 }

gigeEth1DSCPSource44      	OBJECT-TYPE
        SYNTAX          	INTEGER 
        MAX-ACCESS      	read-write
        STATUS          	current
        DESCRIPTION     	"Set/Display ETH1 priority number for DSCP source 44"
        ::= { dscp 44 }

gigeEth1DSCPSource45      	OBJECT-TYPE
        SYNTAX          	INTEGER 
        MAX-ACCESS      	read-write
        STATUS          	current
        DESCRIPTION     	"Set/Display ETH1 priority number for DSCP source 45"
        ::= { dscp 45 }

gigeEth1DSCPSource46      	OBJECT-TYPE
        SYNTAX          	INTEGER 
        MAX-ACCESS      	read-write
        STATUS          	current
        DESCRIPTION     	"Set/Display ETH1 priority number for DSCP source 46"
        ::= { dscp 46 }

gigeEth1DSCPSource47      	OBJECT-TYPE
        SYNTAX          	INTEGER 
        MAX-ACCESS      	read-write
        STATUS          	current
        DESCRIPTION     	"Set/Display ETH1 priority number for DSCP source 47"
        ::= { dscp 47 }

gigeEth1DSCPSource48      	OBJECT-TYPE
        SYNTAX          	INTEGER 
        MAX-ACCESS      	read-write
        STATUS          	current
        DESCRIPTION     	"Set/Display ETH1 priority number for DSCP source 48"
        ::= { dscp 48 }

gigeEth1DSCPSource49      	OBJECT-TYPE
        SYNTAX          	INTEGER 
        MAX-ACCESS      	read-write
        STATUS          	current
        DESCRIPTION     	"Set/Display ETH1 priority number for DSCP source 49"
        ::= { dscp 49 }

gigeEth1DSCPSource50      	OBJECT-TYPE
        SYNTAX          	INTEGER 
        MAX-ACCESS      	read-write
        STATUS          	current
        DESCRIPTION     	"Set/Display ETH1 priority number for DSCP source 50"
        ::= { dscp 50 }

gigeEth1DSCPSource51      	OBJECT-TYPE
        SYNTAX          	INTEGER 
        MAX-ACCESS      	read-write
        STATUS          	current
        DESCRIPTION     	"Set/Display ETH1 priority number for DSCP source 51"
        ::= { dscp 51 }

gigeEth1DSCPSource52      	OBJECT-TYPE
        SYNTAX          	INTEGER 
        MAX-ACCESS      	read-write
        STATUS          	current
        DESCRIPTION     	"Set/Display ETH1 priority number for DSCP source 52"
        ::= { dscp 52 }

gigeEth1DSCPSource53      	OBJECT-TYPE
        SYNTAX          	INTEGER 
        MAX-ACCESS      	read-write
        STATUS          	current
        DESCRIPTION     	"Set/Display ETH1 priority number for DSCP source 53"
        ::= { dscp 53 }

gigeEth1DSCPSource54      	OBJECT-TYPE
        SYNTAX          	INTEGER 
        MAX-ACCESS      	read-write
        STATUS          	current
        DESCRIPTION     	"Set/Display ETH1 priority number for DSCP source 54"
        ::= { dscp 54 }

gigeEth1DSCPSource55      	OBJECT-TYPE
        SYNTAX          	INTEGER 
        MAX-ACCESS      	read-write
        STATUS          	current
        DESCRIPTION     	"Set/Display ETH1 priority number for DSCP source 55"
        ::= { dscp 55 }

gigeEth1DSCPSource56      	OBJECT-TYPE
        SYNTAX          	INTEGER 
        MAX-ACCESS      	read-write
        STATUS          	current
        DESCRIPTION     	"Set/Display ETH1 priority number for DSCP source 56"
        ::= { dscp 56 }

gigeEth1DSCPSource57      	OBJECT-TYPE
        SYNTAX          	INTEGER 
        MAX-ACCESS      	read-write
        STATUS          	current
        DESCRIPTION     	"Set/Display ETH1 priority number for DSCP source 57"
        ::= { dscp 57 }

gigeEth1DSCPSource58      	OBJECT-TYPE
        SYNTAX          	INTEGER 
        MAX-ACCESS      	read-write
        STATUS          	current
        DESCRIPTION     	"Set/Display ETH1 priority number for DSCP source 58"
        ::= { dscp 58 }

gigeEth1DSCPSource59      	OBJECT-TYPE
        SYNTAX          	INTEGER 
        MAX-ACCESS      	read-write
        STATUS          	current
        DESCRIPTION     	"Set/Display ETH1 priority number for DSCP source 59"
        ::= { dscp 59 }

gigeEth1DSCPSource60      	OBJECT-TYPE
        SYNTAX          	INTEGER 
        MAX-ACCESS      	read-write
        STATUS          	current
        DESCRIPTION     	"Set/Display ETH1 priority number for DSCP source 60"
        ::= { dscp 60 }

gigeEth1DSCPSource61      	OBJECT-TYPE
        SYNTAX          	INTEGER 
        MAX-ACCESS      	read-write
        STATUS          	current
        DESCRIPTION     	"Set/Display ETH1 priority number for DSCP source 61"
        ::= { dscp 61 }

gigeEth1DSCPSource62      	OBJECT-TYPE
        SYNTAX          	INTEGER 
        MAX-ACCESS      	read-write
        STATUS          	current
        DESCRIPTION     	"Set/Display ETH1 priority number for DSCP source 62"
        ::= { dscp 62 }

gigeEth1DSCPSource63      	OBJECT-TYPE
        SYNTAX          	INTEGER 
        MAX-ACCESS      	read-write
        STATUS          	current
        DESCRIPTION     	"Set/Display ETH1 priority number for DSCP source 63"
        ::= { dscp 63 }

eth2             		OBJECT IDENTIFIER ::= { gige 2  }

config2             		OBJECT IDENTIFIER ::= { eth2 1  }

gigeEth2AutNegotiate      	OBJECT-TYPE
    	SYNTAX              	INTEGER { off(0), on(1) }
        MAX-ACCESS      	read-write
        STATUS          	current
        DESCRIPTION     	"Set/Display auto neogitate setting for ETH 2"
        ::= { config2 1 }

gigeEth2Duplex      		OBJECT-TYPE
    	SYNTAX              	INTEGER { half(0), full(1) }
        MAX-ACCESS      	read-write
        STATUS          	current
        DESCRIPTION     	"Set/Display duplex setting for ETH 2"
        ::= { config2 2 }

gigeEth2Enable      		OBJECT-TYPE
    	SYNTAX              	INTEGER { off(0), on(1) }
        MAX-ACCESS      	read-write
        STATUS          	current
        DESCRIPTION     	"Set/Display enable setting for ETH 2"
        ::= { config2 3 }

gigeEth2MaxRate      		OBJECT-TYPE
    	SYNTAX              	INTEGER
        MAX-ACCESS      	read-write
        STATUS          	current
        DESCRIPTION     	"Set/Display max rate setting for ETH 2"
        ::= { config2 4 }

gigeEth2PauseFrame      	OBJECT-TYPE
    	SYNTAX              	INTEGER { off(0), on(1) }
        MAX-ACCESS      	read-write
        STATUS          	current
        DESCRIPTION     	"Set/Display pause frame setting for ETH 2"
        ::= { config2 5 }

gigeEth2Priority      		OBJECT-TYPE
        SYNTAX          	INTEGER
        MAX-ACCESS      	read-write
        STATUS          	current
        DESCRIPTION     	"Set/Display priority setting for ETH 2"
        ::= { config2 6 }

gigeEth2Speed      		OBJECT-TYPE
        SYNTAX          	INTEGER 
        MAX-ACCESS      	read-write
        STATUS          	current
        DESCRIPTION     	"Set/Display speed setting for ETH 2"
        ::= { config2 7 }

gigeEth2Status      		OBJECT-TYPE
    	SYNTAX              	INTEGER { off(0), on(1) }
        MAX-ACCESS      	read-only
        STATUS          	current
        DESCRIPTION     	"Set/Display port status for ETH 2"
        ::= { config2 8 }

counter2             		OBJECT IDENTIFIER ::= { eth2 2  }

gigeEth2InOctets      		OBJECT-TYPE
        SYNTAX          	Counter32 
        MAX-ACCESS      	read-only
        STATUS          	current
        DESCRIPTION     	"Display ETH2 IN octets counter"
        ::= { counter2 1 }

gigeEth2InUcastPackets      	OBJECT-TYPE
        SYNTAX          	Counter32 
        MAX-ACCESS      	read-only
        STATUS          	current
        DESCRIPTION     	"Display ETH2 IN unicast packet counter"
        ::= { counter2 2 }

gigeEth2InNUcastPackets      	OBJECT-TYPE
        SYNTAX          	Counter32 
        MAX-ACCESS      	read-only
        STATUS          	current
        DESCRIPTION     	"Display ETH2 IN non-unicast packet counter"
        ::= { counter2 3 }

gigeEth2InTotalPackets      	OBJECT-TYPE
        SYNTAX          	Counter32 
        MAX-ACCESS      	read-only
        STATUS          	current
        DESCRIPTION     	"Display ETH2 IN non-unicast packet counter"
        ::= { counter2 4 }

gigeEth2OutOctets      		OBJECT-TYPE
        SYNTAX          	Counter32 
        MAX-ACCESS      	read-only
        STATUS          	current
        DESCRIPTION     	"Display ETH2 OUT octets counter"
        ::= { counter2 5 }

gigeEth2OutUcastPackets      	OBJECT-TYPE
        SYNTAX          	Counter32 
        MAX-ACCESS      	read-only
        STATUS          	current
        DESCRIPTION     	"Display ETH2 OUT unicast packet counter"
        ::= { counter2 6 }

gigeEth2OutNUcastPackets      	OBJECT-TYPE
        SYNTAX          	Counter32 
        MAX-ACCESS      	read-only
        STATUS          	current
        DESCRIPTION     	"Display ETH2 OUT non-unicast packet counter"
        ::= { counter2 7 }

gigeEth2OutTotalPackets      	OBJECT-TYPE
        SYNTAX          	Counter32 
        MAX-ACCESS      	read-only
        STATUS          	current
        DESCRIPTION     	"Display ETH2 OUT total packet counter"
        ::= { counter2 8 }

gigeEth2CRCError      		OBJECT-TYPE
        SYNTAX          	Counter32 
        MAX-ACCESS      	read-only
        STATUS          	current
        DESCRIPTION     	"Display ETH2 CRC error counter"
        ::= { counter2 9 }

gigeEth2CollisionError      	OBJECT-TYPE
        SYNTAX          	Counter32 
        MAX-ACCESS      	read-only
        STATUS          	current
        DESCRIPTION     	"Display ETH2 Collision error counter"
        ::= { counter2 10 }

gigeEth2InPortRate              OBJECT-TYPE
        SYNTAX                  INTEGER
        MAX-ACCESS              read-only
        STATUS                  current
        DESCRIPTION             "Display ETH1 In Port Rate"
        ::= { counter1 11 }

gigeEth2InPortUtil              OBJECT-TYPE
        SYNTAX                  INTEGER
        MAX-ACCESS              read-only
        STATUS                  current
        DESCRIPTION             "Display ETH1 In Port utilization"
        ::= { counter1 12 }

gigeEth2OutPortRate             OBJECT-TYPE
        SYNTAX                  INTEGER
        MAX-ACCESS              read-only
        STATUS                  current
        DESCRIPTION             "Display ETH1 Out Port Rate"
        ::= { counter1 13 }

gigeEth2OutPortUtil             OBJECT-TYPE
        SYNTAX                  INTEGER 
        MAX-ACCESS              read-only
        STATUS                  current
        DESCRIPTION             "Display ETH1 Out Port utilization"
        ::= { counter1 14 }

dscp             		OBJECT IDENTIFIER ::= { eth2 3  }

gigeEth2DSCPSource1      	OBJECT-TYPE
        SYNTAX          	INTEGER 
        MAX-ACCESS      	read-write
        STATUS          	current
        DESCRIPTION     	"Set/Display Eth2 priority number for DSCP source 1"
        ::= { dscp 1 }

gigeEth2DSCPSource2      	OBJECT-TYPE
        SYNTAX          	INTEGER 
        MAX-ACCESS      	read-write
        STATUS          	current
        DESCRIPTION     	"Set/Display Eth2 priority number for DSCP source 2"
        ::= { dscp 2 }


gigeEth2DSCPSource3      	OBJECT-TYPE
        SYNTAX          	INTEGER 
        MAX-ACCESS      	read-write
        STATUS          	current
        DESCRIPTION     	"Set/Display Eth2 priority number for DSCP source 3"
        ::= { dscp 3 }


gigeEth2DSCPSource4      	OBJECT-TYPE
        SYNTAX          	INTEGER 
        MAX-ACCESS      	read-write
        STATUS          	current
        DESCRIPTION     	"Set/Display Eth2 priority number for DSCP source 4"
        ::= { dscp 4 }


gigeEth2DSCPSource5      	OBJECT-TYPE
        SYNTAX          	INTEGER 
        MAX-ACCESS      	read-write
        STATUS          	current
        DESCRIPTION     	"Set/Display Eth2 priority number for DSCP source 5"
        ::= { dscp 5 }


gigeEth2DSCPSource6      	OBJECT-TYPE
        SYNTAX          	INTEGER 
        MAX-ACCESS      	read-write
        STATUS          	current
        DESCRIPTION     	"Set/Display Eth2 priority number for DSCP source 6"
        ::= { dscp 6 }


gigeEth2DSCPSource7      	OBJECT-TYPE
        SYNTAX          	INTEGER 
        MAX-ACCESS      	read-write
        STATUS          	current
        DESCRIPTION     	"Set/Display Eth2 priority number for DSCP source 7"
        ::= { dscp 7 }


gigeEth2DSCPSource8      	OBJECT-TYPE
        SYNTAX          	INTEGER 
        MAX-ACCESS      	read-write
        STATUS          	current
        DESCRIPTION     	"Set/Display Eth2 priority number for DSCP source 8"
        ::= { dscp 8 }


gigeEth2DSCPSource9      	OBJECT-TYPE
        SYNTAX          	INTEGER 
        MAX-ACCESS      	read-write
        STATUS          	current
        DESCRIPTION     	"Set/Display Eth2 priority number for DSCP source 9"
        ::= { dscp 9 }

gigeEth2DSCPSource10      	OBJECT-TYPE
        SYNTAX          	INTEGER 
        MAX-ACCESS      	read-write
        STATUS          	current
        DESCRIPTION     	"Set/Display Eth2 priority number for DSCP source 10"
        ::= { dscp 10 }


gigeEth2DSCPSource11      	OBJECT-TYPE
        SYNTAX          	INTEGER 
        MAX-ACCESS      	read-write
        STATUS          	current
        DESCRIPTION     	"Set/Display Eth2 priority number for DSCP source 11"
        ::= { dscp 11 }


gigeEth2DSCPSource12      	OBJECT-TYPE
        SYNTAX          	INTEGER 
        MAX-ACCESS      	read-write
        STATUS          	current
        DESCRIPTION     	"Set/Display Eth2 priority number for DSCP source 12"
        ::= { dscp 12 }


gigeEth2DSCPSource13      	OBJECT-TYPE
        SYNTAX          	INTEGER 
        MAX-ACCESS      	read-write
        STATUS          	current
        DESCRIPTION     	"Set/Display Eth2 priority number for DSCP source 13"
        ::= { dscp 13 }


gigeEth2DSCPSource14      	OBJECT-TYPE
        SYNTAX          	INTEGER 
        MAX-ACCESS      	read-write
        STATUS          	current
        DESCRIPTION     	"Set/Display Eth2 priority number for DSCP source 14"
        ::= { dscp 14 }


gigeEth2DSCPSource15      	OBJECT-TYPE
        SYNTAX          	INTEGER 
        MAX-ACCESS      	read-write
        STATUS          	current
        DESCRIPTION     	"Set/Display Eth2 priority number for DSCP source 15"
        ::= { dscp 15 }

gigeEth2DSCPSource16      	OBJECT-TYPE
        SYNTAX          	INTEGER 
        MAX-ACCESS      	read-write
        STATUS          	current
        DESCRIPTION     	"Set/Display Eth2 priority number for DSCP source 16"
        ::= { dscp 16 }


gigeEth2DSCPSource17      	OBJECT-TYPE
        SYNTAX          	INTEGER 
        MAX-ACCESS      	read-write
        STATUS          	current
        DESCRIPTION     	"Set/Display Eth2 priority number for DSCP source 17"
        ::= { dscp 17 }


gigeEth2DSCPSource18      	OBJECT-TYPE
        SYNTAX          	INTEGER 
        MAX-ACCESS      	read-write
        STATUS          	current
        DESCRIPTION     	"Set/Display Eth2 priority number for DSCP source 18"
        ::= { dscp 18 }


gigeEth2DSCPSource19      	OBJECT-TYPE
        SYNTAX          	INTEGER 
        MAX-ACCESS      	read-write
        STATUS          	current
        DESCRIPTION     	"Set/Display Eth2 priority number for DSCP source 19"
        ::= { dscp 19 }


gigeEth2DSCPSource20      	OBJECT-TYPE
        SYNTAX          	INTEGER 
        MAX-ACCESS      	read-write
        STATUS          	current
        DESCRIPTION     	"Set/Display Eth2 priority number for DSCP source 20"
        ::= { dscp 20 }


gigeEth2DSCPSource21      	OBJECT-TYPE
        SYNTAX          	INTEGER 
        MAX-ACCESS      	read-write
        STATUS          	current
        DESCRIPTION     	"Set/Display Eth2 priority number for DSCP source 21"
        ::= { dscp 21 }


gigeEth2DSCPSource22      	OBJECT-TYPE
        SYNTAX          	INTEGER 
        MAX-ACCESS      	read-write
        STATUS          	current
        DESCRIPTION     	"Set/Display Eth2 priority number for DSCP source 22"
        ::= { dscp 22 }

gigeEth2DSCPSource23      	OBJECT-TYPE
        SYNTAX          	INTEGER 
        MAX-ACCESS      	read-write
        STATUS          	current
        DESCRIPTION     	"Set/Display Eth2 priority number for DSCP source 23"
        ::= { dscp 23 }


gigeEth2DSCPSource24      	OBJECT-TYPE
        SYNTAX          	INTEGER 
        MAX-ACCESS      	read-write
        STATUS          	current
        DESCRIPTION     	"Set/Display Eth2 priority number for DSCP source 24"
        ::= { dscp 24 }


gigeEth2DSCPSource25      	OBJECT-TYPE
        SYNTAX          	INTEGER 
        MAX-ACCESS      	read-write
        STATUS          	current
        DESCRIPTION     	"Set/Display Eth2 priority number for DSCP source 25"
        ::= { dscp 25 }

gigeEth2DSCPSource26      	OBJECT-TYPE
        SYNTAX          	INTEGER 
        MAX-ACCESS      	read-write
        STATUS          	current
        DESCRIPTION     	"Set/Display Eth2 priority number for DSCP source 26"
        ::= { dscp 26 }

gigeEth2DSCPSource27      	OBJECT-TYPE
        SYNTAX          	INTEGER 
        MAX-ACCESS      	read-write
        STATUS          	current
        DESCRIPTION     	"Set/Display Eth2 priority number for DSCP source 27"
        ::= { dscp 27 }

gigeEth2DSCPSource28      	OBJECT-TYPE
        SYNTAX          	INTEGER 
        MAX-ACCESS      	read-write
        STATUS          	current
        DESCRIPTION     	"Set/Display Eth2 priority number for DSCP source 28"
        ::= { dscp 28 }

gigeEth2DSCPSource29      	OBJECT-TYPE
        SYNTAX          	INTEGER 
        MAX-ACCESS      	read-write
        STATUS          	current
        DESCRIPTION     	"Set/Display Eth2 priority number for DSCP source 29"
        ::= { dscp 29 }

gigeEth2DSCPSource30      	OBJECT-TYPE
        SYNTAX          	INTEGER 
        MAX-ACCESS      	read-write
        STATUS          	current
        DESCRIPTION     	"Set/Display Eth2 priority number for DSCP source 30"
        ::= { dscp 30 }

gigeEth2DSCPSource31      	OBJECT-TYPE
        SYNTAX          	INTEGER 
        MAX-ACCESS      	read-write
        STATUS          	current
        DESCRIPTION     	"Set/Display Eth2 priority number for DSCP source 31"
        ::= { dscp 31 }

gigeEth2DSCPSource32      	OBJECT-TYPE
        SYNTAX          	INTEGER 
        MAX-ACCESS      	read-write
        STATUS          	current
        DESCRIPTION     	"Set/Display Eth2 priority number for DSCP source 32"
        ::= { dscp 32 }

gigeEth2DSCPSource33      	OBJECT-TYPE
        SYNTAX          	INTEGER 
        MAX-ACCESS      	read-write
        STATUS          	current
        DESCRIPTION     	"Set/Display Eth2 priority number for DSCP source 33"
        ::= { dscp 33 }

gigeEth2DSCPSource34      	OBJECT-TYPE
        SYNTAX          	INTEGER 
        MAX-ACCESS      	read-write
        STATUS          	current
        DESCRIPTION     	"Set/Display Eth2 priority number for DSCP source 34"
        ::= { dscp 34 }

gigeEth2DSCPSource35      	OBJECT-TYPE
        SYNTAX          	INTEGER 
        MAX-ACCESS      	read-write
        STATUS          	current
        DESCRIPTION     	"Set/Display Eth2 priority number for DSCP source 35"
        ::= { dscp 35 }

gigeEth2DSCPSource36      	OBJECT-TYPE
        SYNTAX          	INTEGER 
        MAX-ACCESS      	read-write
        STATUS          	current
        DESCRIPTION     	"Set/Display Eth2 priority number for DSCP source 36"
        ::= { dscp 36 }

gigeEth2DSCPSource37      	OBJECT-TYPE
        SYNTAX          	INTEGER 
        MAX-ACCESS      	read-write
        STATUS          	current
        DESCRIPTION     	"Set/Display Eth2 priority number for DSCP source 37"
        ::= { dscp 37 }

gigeEth2DSCPSource38      	OBJECT-TYPE
        SYNTAX          	INTEGER 
        MAX-ACCESS      	read-write
        STATUS          	current
        DESCRIPTION     	"Set/Display Eth2 priority number for DSCP source 38"
        ::= { dscp 38 }

gigeEth2DSCPSource39      	OBJECT-TYPE
        SYNTAX          	INTEGER 
        MAX-ACCESS      	read-write
        STATUS          	current
        DESCRIPTION     	"Set/Display Eth2 priority number for DSCP source 39"
        ::= { dscp 39 }

gigeEth2DSCPSource40      	OBJECT-TYPE
        SYNTAX          	INTEGER 
        MAX-ACCESS      	read-write
        STATUS          	current
        DESCRIPTION     	"Set/Display Eth2 priority number for DSCP source 40"
        ::= { dscp 40 }

gigeEth2DSCPSource41      	OBJECT-TYPE
        SYNTAX          	INTEGER 
        MAX-ACCESS      	read-write
        STATUS          	current
        DESCRIPTION     	"Set/Display Eth2 priority number for DSCP source 41"
        ::= { dscp 41 }

gigeEth2DSCPSource42      	OBJECT-TYPE
        SYNTAX          	INTEGER 
        MAX-ACCESS      	read-write
        STATUS          	current
        DESCRIPTION     	"Set/Display Eth2 priority number for DSCP source 42"
        ::= { dscp 42 }

gigeEth2DSCPSource43      	OBJECT-TYPE
        SYNTAX          	INTEGER 
        MAX-ACCESS      	read-write
        STATUS          	current
        DESCRIPTION     	"Set/Display Eth2 priority number for DSCP source 43"
        ::= { dscp 43 }

gigeEth2DSCPSource44      	OBJECT-TYPE
        SYNTAX          	INTEGER 
        MAX-ACCESS      	read-write
        STATUS          	current
        DESCRIPTION     	"Set/Display Eth2 priority number for DSCP source 44"
        ::= { dscp 44 }

gigeEth2DSCPSource45      	OBJECT-TYPE
        SYNTAX          	INTEGER 
        MAX-ACCESS      	read-write
        STATUS          	current
        DESCRIPTION     	"Set/Display Eth2 priority number for DSCP source 45"
        ::= { dscp 45 }

gigeEth2DSCPSource46      	OBJECT-TYPE
        SYNTAX          	INTEGER 
        MAX-ACCESS      	read-write
        STATUS          	current
        DESCRIPTION     	"Set/Display Eth2 priority number for DSCP source 46"
        ::= { dscp 46 }

gigeEth2DSCPSource47      	OBJECT-TYPE
        SYNTAX          	INTEGER 
        MAX-ACCESS      	read-write
        STATUS          	current
        DESCRIPTION     	"Set/Display Eth2 priority number for DSCP source 47"
        ::= { dscp 47 }

gigeEth2DSCPSource48      	OBJECT-TYPE
        SYNTAX          	INTEGER 
        MAX-ACCESS      	read-write
        STATUS          	current
        DESCRIPTION     	"Set/Display Eth2 priority number for DSCP source 48"
        ::= { dscp 48 }

gigeEth2DSCPSource49      	OBJECT-TYPE
        SYNTAX          	INTEGER 
        MAX-ACCESS      	read-write
        STATUS          	current
        DESCRIPTION     	"Set/Display Eth2 priority number for DSCP source 49"
        ::= { dscp 49 }

gigeEth2DSCPSource50      	OBJECT-TYPE
        SYNTAX          	INTEGER 
        MAX-ACCESS      	read-write
        STATUS          	current
        DESCRIPTION     	"Set/Display Eth2 priority number for DSCP source 50"
        ::= { dscp 50 }

gigeEth2DSCPSource51      	OBJECT-TYPE
        SYNTAX          	INTEGER 
        MAX-ACCESS      	read-write
        STATUS          	current
        DESCRIPTION     	"Set/Display Eth2 priority number for DSCP source 51"
        ::= { dscp 51 }

gigeEth2DSCPSource52      	OBJECT-TYPE
        SYNTAX          	INTEGER 
        MAX-ACCESS      	read-write
        STATUS          	current
        DESCRIPTION     	"Set/Display Eth2 priority number for DSCP source 52"
        ::= { dscp 52 }

gigeEth2DSCPSource53      	OBJECT-TYPE
        SYNTAX          	INTEGER 
        MAX-ACCESS      	read-write
        STATUS          	current
        DESCRIPTION     	"Set/Display Eth2 priority number for DSCP source 53"
        ::= { dscp 53 }

gigeEth2DSCPSource54      	OBJECT-TYPE
        SYNTAX          	INTEGER 
        MAX-ACCESS      	read-write
        STATUS          	current
        DESCRIPTION     	"Set/Display Eth2 priority number for DSCP source 54"
        ::= { dscp 54 }

gigeEth2DSCPSource55      	OBJECT-TYPE
        SYNTAX          	INTEGER 
        MAX-ACCESS      	read-write
        STATUS          	current
        DESCRIPTION     	"Set/Display Eth2 priority number for DSCP source 55"
        ::= { dscp 55 }

gigeEth2DSCPSource56      	OBJECT-TYPE
        SYNTAX          	INTEGER 
        MAX-ACCESS      	read-write
        STATUS          	current
        DESCRIPTION     	"Set/Display Eth2 priority number for DSCP source 56"
        ::= { dscp 56 }

gigeEth2DSCPSource57      	OBJECT-TYPE
        SYNTAX          	INTEGER 
        MAX-ACCESS      	read-write
        STATUS          	current
        DESCRIPTION     	"Set/Display Eth2 priority number for DSCP source 57"
        ::= { dscp 57 }

gigeEth2DSCPSource58      	OBJECT-TYPE
        SYNTAX          	INTEGER 
        MAX-ACCESS      	read-write
        STATUS          	current
        DESCRIPTION     	"Set/Display Eth2 priority number for DSCP source 58"
        ::= { dscp 58 }

gigeEth2DSCPSource59      	OBJECT-TYPE
        SYNTAX          	INTEGER 
        MAX-ACCESS      	read-write
        STATUS          	current
        DESCRIPTION     	"Set/Display Eth2 priority number for DSCP source 59"
        ::= { dscp 59 }

gigeEth2DSCPSource60      	OBJECT-TYPE
        SYNTAX          	INTEGER 
        MAX-ACCESS      	read-write
        STATUS          	current
        DESCRIPTION     	"Set/Display Eth2 priority number for DSCP source 60"
        ::= { dscp 60 }

gigeEth2DSCPSource61      	OBJECT-TYPE
        SYNTAX          	INTEGER 
        MAX-ACCESS      	read-write
        STATUS          	current
        DESCRIPTION     	"Set/Display Eth2 priority number for DSCP source 61"
        ::= { dscp 61 }

gigeEth2DSCPSource62      	OBJECT-TYPE
        SYNTAX          	INTEGER 
        MAX-ACCESS      	read-write
        STATUS          	current
        DESCRIPTION     	"Set/Display Eth2 priority number for DSCP source 62"
        ::= { dscp 62 }

gigeEth2DSCPSource63      	OBJECT-TYPE
        SYNTAX          	INTEGER 
        MAX-ACCESS      	read-write
        STATUS          	current
        DESCRIPTION     	"Set/Display Eth2 priority number for DSCP source 63"
        ::= { dscp 63 }


eth3             		OBJECT IDENTIFIER ::= { gige 3  }

config3             		OBJECT IDENTIFIER ::= { eth3 1  }

gigeEth3AutNegotiate      	OBJECT-TYPE
    	SYNTAX              	INTEGER { off(0), on(1) }
        MAX-ACCESS      	read-write
        STATUS          	current
        DESCRIPTION     	"Set/Display auto neogitate setting for ETH 3"
        ::= { config3 1 }

gigeEth3Duplex      		OBJECT-TYPE
    	SYNTAX              	INTEGER { half(0), full(1) }
        MAX-ACCESS      	read-write
        STATUS          	current
        DESCRIPTION     	"Set/Display duplex setting for ETH 3"
        ::= { config3 2 }

gigeEth3Enable      		OBJECT-TYPE
    	SYNTAX              	INTEGER { off(0), on(1) }
        MAX-ACCESS      	read-write
        STATUS          	current
        DESCRIPTION     	"Set/Display enable setting for ETH 3"
        ::= { config3 3 }

gigeEth3MaxRate      		OBJECT-TYPE
    	SYNTAX              	INTEGER
        MAX-ACCESS      	read-write
        STATUS          	current
        DESCRIPTION     	"Set/Display max rate setting for ETH 3"
        ::= { config3 4 }

gigeEth3PauseFrame      	OBJECT-TYPE
    	SYNTAX              	INTEGER { off(0), on(1) }
        MAX-ACCESS      	read-write
        STATUS          	current
        DESCRIPTION     	"Set/Display pause frame setting for ETH 3"
        ::= { config3 5 }

gigeEth3Priority      		OBJECT-TYPE
        SYNTAX          	INTEGER
        MAX-ACCESS      	read-write
        STATUS          	current
        DESCRIPTION     	"Set/Display priority setting for ETH 3"
        ::= { config3 6 }

gigeEth3Speed      		OBJECT-TYPE
        SYNTAX          	INTEGER 
        MAX-ACCESS      	read-write
        STATUS          	current
        DESCRIPTION     	"Set/Display speed setting for ETH 3"
        ::= { config3 7 }

gigeEth3Status      		OBJECT-TYPE
    	SYNTAX              	INTEGER { off(0), on(1) }
        MAX-ACCESS      	read-only
        STATUS          	current
        DESCRIPTION     	"Set/Display port status for ETH 3"
        ::= { config3 8 }

counter3             		OBJECT IDENTIFIER ::= { eth3 2  }

gigeEth2InOctets      		OBJECT-TYPE
        SYNTAX          	Counter32 
        MAX-ACCESS      	read-only
        STATUS          	current
        DESCRIPTION     	"Display ETH3 IN octets counter"
        ::= { counter3 1 }

gigeEth3InUcastPackets      	OBJECT-TYPE
        SYNTAX          	Counter32 
        MAX-ACCESS      	read-only
        STATUS          	current
        DESCRIPTION     	"Display ETH3 IN unicast packet counter"
        ::= { counter3 2 }

gigeEth3InNUcastPackets      	OBJECT-TYPE
        SYNTAX          	Counter32 
        MAX-ACCESS      	read-only
        STATUS          	current
        DESCRIPTION     	"Display ETH3 IN non-unicast packet counter"
        ::= { counter3 3 }

gigeEth3InTotalPackets      	OBJECT-TYPE
        SYNTAX          	Counter32 
        MAX-ACCESS      	read-only
        STATUS          	current
        DESCRIPTION     	"Display ETH3 IN non-unicast packet counter"
        ::= { counter3 4 }

gigeEth3OutOctets      		OBJECT-TYPE
        SYNTAX          	Counter32 
        MAX-ACCESS      	read-only
        STATUS          	current
        DESCRIPTION     	"Display ETH3 OUT octets counter"
        ::= { counter3 5 }

gigeEth3OutUcastPackets      	OBJECT-TYPE
        SYNTAX          	Counter32 
        MAX-ACCESS      	read-only
        STATUS          	current
        DESCRIPTION     	"Display ETH3 OUT unicast packet counter"
        ::= { counter3 6 }

gigeEth3OutNUcastPackets      	OBJECT-TYPE
        SYNTAX          	Counter32 
        MAX-ACCESS      	read-only
        STATUS          	current
        DESCRIPTION     	"Display ETH3 OUT non-unicast packet counter"
        ::= { counter3 7 }

gigeEth3OutTotalPackets      	OBJECT-TYPE
        SYNTAX          	Counter32 
        MAX-ACCESS      	read-only
        STATUS          	current
        DESCRIPTION     	"Display ETH3 OUT total packet counter"
        ::= { counter3 8 }

gigeEth3CRCError      		OBJECT-TYPE
        SYNTAX          	Counter32 
        MAX-ACCESS      	read-only
        STATUS          	current
        DESCRIPTION     	"Display ETH3 CRC error counter"
        ::= { counter3 9 }

gigeEth3CollisionError      	OBJECT-TYPE
        SYNTAX          	Counter32 
        MAX-ACCESS      	read-only
        STATUS          	current
        DESCRIPTION     	"Display ETH3 Collision error counter"
        ::= { counter3 10 }

gigeEth3InPortRate              OBJECT-TYPE
        SYNTAX                  INTEGER
        MAX-ACCESS              read-only
        STATUS                  current
        DESCRIPTION             "Display Eth3 In Port Rate"
        ::= { counter3 11 }

gigeEth3InPortUtil              OBJECT-TYPE
        SYNTAX                  INTEGER
        MAX-ACCESS              read-only
        STATUS                  current
        DESCRIPTION             "Display Eth3 In Port utilization"
        ::= { counter3 12 }

gigeEth3OutPortRate             OBJECT-TYPE
        SYNTAX                  INTEGER
        MAX-ACCESS              read-only
        STATUS                  current
        DESCRIPTION             "Display Eth3 Out Port Rate"
        ::= { counter3 13 }

gigeEth3OutPortUtil             OBJECT-TYPE
        SYNTAX                  INTEGER 
        MAX-ACCESS              read-only
        STATUS                  current
        DESCRIPTION             "Display Eth3 Out Port utilization"
        ::= { counter3 14 }

dscp             		OBJECT IDENTIFIER ::= { eth3 3  }

gigeEth3DSCPSource1      	OBJECT-TYPE
        SYNTAX          	INTEGER 
        MAX-ACCESS      	read-write
        STATUS          	current
        DESCRIPTION     	"Set/Display Eth3 priority number for DSCP source 1"
        ::= { dscp 1 }

gigeEth3DSCPSource2      	OBJECT-TYPE
        SYNTAX          	INTEGER 
        MAX-ACCESS      	read-write
        STATUS          	current
        DESCRIPTION     	"Set/Display Eth3 priority number for DSCP source 2"
        ::= { dscp 2 }


gigeEth3DSCPSource3      	OBJECT-TYPE
        SYNTAX          	INTEGER 
        MAX-ACCESS      	read-write
        STATUS          	current
        DESCRIPTION     	"Set/Display Eth3 priority number for DSCP source 3"
        ::= { dscp 3 }


gigeEth3DSCPSource4      	OBJECT-TYPE
        SYNTAX          	INTEGER 
        MAX-ACCESS      	read-write
        STATUS          	current
        DESCRIPTION     	"Set/Display Eth3 priority number for DSCP source 4"
        ::= { dscp 4 }


gigeEth3DSCPSource5      	OBJECT-TYPE
        SYNTAX          	INTEGER 
        MAX-ACCESS      	read-write
        STATUS          	current
        DESCRIPTION     	"Set/Display Eth3 priority number for DSCP source 5"
        ::= { dscp 5 }


gigeEth3DSCPSource6      	OBJECT-TYPE
        SYNTAX          	INTEGER 
        MAX-ACCESS      	read-write
        STATUS          	current
        DESCRIPTION     	"Set/Display Eth3 priority number for DSCP source 6"
        ::= { dscp 6 }


gigeEth3DSCPSource7      	OBJECT-TYPE
        SYNTAX          	INTEGER 
        MAX-ACCESS      	read-write
        STATUS          	current
        DESCRIPTION     	"Set/Display Eth3 priority number for DSCP source 7"
        ::= { dscp 7 }


gigeEth3DSCPSource8      	OBJECT-TYPE
        SYNTAX          	INTEGER 
        MAX-ACCESS      	read-write
        STATUS          	current
        DESCRIPTION     	"Set/Display Eth3 priority number for DSCP source 8"
        ::= { dscp 8 }


gigeEth3DSCPSource9      	OBJECT-TYPE
        SYNTAX          	INTEGER 
        MAX-ACCESS      	read-write
        STATUS          	current
        DESCRIPTION     	"Set/Display Eth3 priority number for DSCP source 9"
        ::= { dscp 9 }


gigeEth3DSCPSource10      	OBJECT-TYPE
        SYNTAX          	INTEGER 
        MAX-ACCESS      	read-write
        STATUS          	current
        DESCRIPTION     	"Set/Display Eth3 priority number for DSCP source 10"
        ::= { dscp 10 }


gigeEth3DSCPSource11      	OBJECT-TYPE
        SYNTAX          	INTEGER 
        MAX-ACCESS      	read-write
        STATUS          	current
        DESCRIPTION     	"Set/Display Eth3 priority number for DSCP source 11"
        ::= { dscp 11 }


gigeEth3DSCPSource12      	OBJECT-TYPE
        SYNTAX          	INTEGER 
        MAX-ACCESS      	read-write
        STATUS          	current
        DESCRIPTION     	"Set/Display Eth3 priority number for DSCP source 12"
        ::= { dscp 12 }


gigeEth3DSCPSource13      	OBJECT-TYPE
        SYNTAX          	INTEGER 
        MAX-ACCESS      	read-write
        STATUS          	current
        DESCRIPTION     	"Set/Display Eth3 priority number for DSCP source 13"
        ::= { dscp 13 }


gigeEth3DSCPSource14      	OBJECT-TYPE
        SYNTAX          	INTEGER 
        MAX-ACCESS      	read-write
        STATUS          	current
        DESCRIPTION     	"Set/Display Eth3 priority number for DSCP source 14"
        ::= { dscp 14 }


gigeEth3DSCPSource15      	OBJECT-TYPE
        SYNTAX          	INTEGER 
        MAX-ACCESS      	read-write
        STATUS          	current
        DESCRIPTION     	"Set/Display Eth3 priority number for DSCP source 15"
        ::= { dscp 15 }

gigeEth3DSCPSource16      	OBJECT-TYPE
        SYNTAX          	INTEGER 
        MAX-ACCESS      	read-write
        STATUS          	current
        DESCRIPTION     	"Set/Display Eth3 priority number for DSCP source 16"
        ::= { dscp 16 }


gigeEth3DSCPSource17      	OBJECT-TYPE
        SYNTAX          	INTEGER 
        MAX-ACCESS      	read-write
        STATUS          	current
        DESCRIPTION     	"Set/Display Eth3 priority number for DSCP source 17"
        ::= { dscp 17 }


gigeEth3DSCPSource18      	OBJECT-TYPE
        SYNTAX          	INTEGER 
        MAX-ACCESS      	read-write
        STATUS          	current
        DESCRIPTION     	"Set/Display Eth3 priority number for DSCP source 18"
        ::= { dscp 18 }


gigeEth3DSCPSource19      	OBJECT-TYPE
        SYNTAX          	INTEGER 
        MAX-ACCESS      	read-write
        STATUS          	current
        DESCRIPTION     	"Set/Display Eth3 priority number for DSCP source 19"
        ::= { dscp 19 }


gigeEth3DSCPSource20      	OBJECT-TYPE
        SYNTAX          	INTEGER 
        MAX-ACCESS      	read-write
        STATUS          	current
        DESCRIPTION     	"Set/Display Eth3 priority number for DSCP source 20"
        ::= { dscp 20 }


gigeEth3DSCPSource21      	OBJECT-TYPE
        SYNTAX          	INTEGER 
        MAX-ACCESS      	read-write
        STATUS          	current
        DESCRIPTION     	"Set/Display Eth3 priority number for DSCP source 21"
        ::= { dscp 21 }


gigeEth3DSCPSource22      	OBJECT-TYPE
        SYNTAX          	INTEGER 
        MAX-ACCESS      	read-write
        STATUS          	current
        DESCRIPTION     	"Set/Display Eth3 priority number for DSCP source 22"
        ::= { dscp 22 }


gigeEth3DSCPSource23      	OBJECT-TYPE
        SYNTAX          	INTEGER 
        MAX-ACCESS      	read-write
        STATUS          	current
        DESCRIPTION     	"Set/Display Eth3 priority number for DSCP source 23"
        ::= { dscp 23 }


gigeEth3DSCPSource24      	OBJECT-TYPE
        SYNTAX          	INTEGER 
        MAX-ACCESS      	read-write
        STATUS          	current
        DESCRIPTION     	"Set/Display Eth3 priority number for DSCP source 24"
        ::= { dscp 24 }


gigeEth3DSCPSource25      	OBJECT-TYPE
        SYNTAX          	INTEGER 
        MAX-ACCESS      	read-write
        STATUS          	current
        DESCRIPTION     	"Set/Display Eth3 priority number for DSCP source 25"
        ::= { dscp 25 }

gigeEth3DSCPSource26      	OBJECT-TYPE
        SYNTAX          	INTEGER 
        MAX-ACCESS      	read-write
        STATUS          	current
        DESCRIPTION     	"Set/Display Eth3 priority number for DSCP source 26"
        ::= { dscp 26 }

gigeEth3DSCPSource27      	OBJECT-TYPE
        SYNTAX          	INTEGER 
        MAX-ACCESS      	read-write
        STATUS          	current
        DESCRIPTION     	"Set/Display Eth3 priority number for DSCP source 27"
        ::= { dscp 27 }

gigeEth3DSCPSource28      	OBJECT-TYPE
        SYNTAX          	INTEGER 
        MAX-ACCESS      	read-write
        STATUS          	current
        DESCRIPTION     	"Set/Display Eth3 priority number for DSCP source 28"
        ::= { dscp 28 }

gigeEth3DSCPSource29      	OBJECT-TYPE
        SYNTAX          	INTEGER 
        MAX-ACCESS      	read-write
        STATUS          	current
        DESCRIPTION     	"Set/Display Eth3 priority number for DSCP source 29"
        ::= { dscp 29 }

gigeEth3DSCPSource30      	OBJECT-TYPE
        SYNTAX          	INTEGER 
        MAX-ACCESS      	read-write
        STATUS          	current
        DESCRIPTION     	"Set/Display Eth3 priority number for DSCP source 30"
        ::= { dscp 30 }

gigeEth3DSCPSource31      	OBJECT-TYPE
        SYNTAX          	INTEGER 
        MAX-ACCESS      	read-write
        STATUS          	current
        DESCRIPTION     	"Set/Display Eth3 priority number for DSCP source 31"
        ::= { dscp 31 }

gigeEth3DSCPSource32      	OBJECT-TYPE
        SYNTAX          	INTEGER 
        MAX-ACCESS      	read-write
        STATUS          	current
        DESCRIPTION     	"Set/Display Eth3 priority number for DSCP source 32"
        ::= { dscp 32 }

gigeEth3DSCPSource33      	OBJECT-TYPE
        SYNTAX          	INTEGER 
        MAX-ACCESS      	read-write
        STATUS          	current
        DESCRIPTION     	"Set/Display Eth3 priority number for DSCP source 33"
        ::= { dscp 33 }

gigeEth3DSCPSource34      	OBJECT-TYPE
        SYNTAX          	INTEGER 
        MAX-ACCESS      	read-write
        STATUS          	current
        DESCRIPTION     	"Set/Display Eth3 priority number for DSCP source 34"
        ::= { dscp 34 }

gigeEth3DSCPSource35      	OBJECT-TYPE
        SYNTAX          	INTEGER 
        MAX-ACCESS      	read-write
        STATUS          	current
        DESCRIPTION     	"Set/Display Eth3 priority number for DSCP source 35"
        ::= { dscp 35 }

gigeEth3DSCPSource36      	OBJECT-TYPE
        SYNTAX          	INTEGER 
        MAX-ACCESS      	read-write
        STATUS          	current
        DESCRIPTION     	"Set/Display Eth3 priority number for DSCP source 36"
        ::= { dscp 36 }

gigeEth3DSCPSource37      	OBJECT-TYPE
        SYNTAX          	INTEGER 
        MAX-ACCESS      	read-write
        STATUS          	current
        DESCRIPTION     	"Set/Display Eth3 priority number for DSCP source 37"
        ::= { dscp 37 }

gigeEth3DSCPSource38      	OBJECT-TYPE
        SYNTAX          	INTEGER 
        MAX-ACCESS      	read-write
        STATUS          	current
        DESCRIPTION     	"Set/Display Eth3 priority number for DSCP source 38"
        ::= { dscp 38 }

gigeEth3DSCPSource39      	OBJECT-TYPE
        SYNTAX          	INTEGER 
        MAX-ACCESS      	read-write
        STATUS          	current
        DESCRIPTION     	"Set/Display Eth3 priority number for DSCP source 39"
        ::= { dscp 39 }

gigeEth3DSCPSource40      	OBJECT-TYPE
        SYNTAX          	INTEGER 
        MAX-ACCESS      	read-write
        STATUS          	current
        DESCRIPTION     	"Set/Display Eth3 priority number for DSCP source 40"
        ::= { dscp 40 }

gigeEth3DSCPSource41      	OBJECT-TYPE
        SYNTAX          	INTEGER 
        MAX-ACCESS      	read-write
        STATUS          	current
        DESCRIPTION     	"Set/Display Eth3 priority number for DSCP source 41"
        ::= { dscp 41 }

gigeEth3DSCPSource42      	OBJECT-TYPE
        SYNTAX          	INTEGER 
        MAX-ACCESS      	read-write
        STATUS          	current
        DESCRIPTION     	"Set/Display Eth3 priority number for DSCP source 42"
        ::= { dscp 42 }

gigeEth3DSCPSource43      	OBJECT-TYPE
        SYNTAX          	INTEGER 
        MAX-ACCESS      	read-write
        STATUS          	current
        DESCRIPTION     	"Set/Display Eth3 priority number for DSCP source 43"
        ::= { dscp 43 }

gigeEth3DSCPSource44      	OBJECT-TYPE
        SYNTAX          	INTEGER 
        MAX-ACCESS      	read-write
        STATUS          	current
        DESCRIPTION     	"Set/Display Eth3 priority number for DSCP source 44"
        ::= { dscp 44 }

gigeEth3DSCPSource45      	OBJECT-TYPE
        SYNTAX          	INTEGER 
        MAX-ACCESS      	read-write
        STATUS          	current
        DESCRIPTION     	"Set/Display Eth3 priority number for DSCP source 45"
        ::= { dscp 45 }

gigeEth3DSCPSource46      	OBJECT-TYPE
        SYNTAX          	INTEGER 
        MAX-ACCESS      	read-write
        STATUS          	current
        DESCRIPTION     	"Set/Display Eth3 priority number for DSCP source 46"
        ::= { dscp 46 }

gigeEth3DSCPSource47      	OBJECT-TYPE
        SYNTAX          	INTEGER 
        MAX-ACCESS      	read-write
        STATUS          	current
        DESCRIPTION     	"Set/Display Eth3 priority number for DSCP source 47"
        ::= { dscp 47 }

gigeEth3DSCPSource48      	OBJECT-TYPE
        SYNTAX          	INTEGER 
        MAX-ACCESS      	read-write
        STATUS          	current
        DESCRIPTION     	"Set/Display Eth3 priority number for DSCP source 48"
        ::= { dscp 48 }

gigeEth3DSCPSource49      	OBJECT-TYPE
        SYNTAX          	INTEGER 
        MAX-ACCESS      	read-write
        STATUS          	current
        DESCRIPTION     	"Set/Display Eth3 priority number for DSCP source 49"
        ::= { dscp 49 }

gigeEth3DSCPSource50      	OBJECT-TYPE
        SYNTAX          	INTEGER 
        MAX-ACCESS      	read-write
        STATUS          	current
        DESCRIPTION     	"Set/Display Eth3 priority number for DSCP source 50"
        ::= { dscp 50 }

gigeEth3DSCPSource51      	OBJECT-TYPE
        SYNTAX          	INTEGER 
        MAX-ACCESS      	read-write
        STATUS          	current
        DESCRIPTION     	"Set/Display Eth3 priority number for DSCP source 51"
        ::= { dscp 51 }

gigeEth3DSCPSource52      	OBJECT-TYPE
        SYNTAX          	INTEGER 
        MAX-ACCESS      	read-write
        STATUS          	current
        DESCRIPTION     	"Set/Display Eth3 priority number for DSCP source 52"
        ::= { dscp 52 }

gigeEth3DSCPSource53      	OBJECT-TYPE
        SYNTAX          	INTEGER 
        MAX-ACCESS      	read-write
        STATUS          	current
        DESCRIPTION     	"Set/Display Eth3 priority number for DSCP source 53"
        ::= { dscp 53 }

gigeEth3DSCPSource54      	OBJECT-TYPE
        SYNTAX          	INTEGER 
        MAX-ACCESS      	read-write
        STATUS          	current
        DESCRIPTION     	"Set/Display Eth3 priority number for DSCP source 54"
        ::= { dscp 54 }

gigeEth3DSCPSource55      	OBJECT-TYPE
        SYNTAX          	INTEGER 
        MAX-ACCESS      	read-write
        STATUS          	current
        DESCRIPTION     	"Set/Display Eth3 priority number for DSCP source 55"
        ::= { dscp 55 }

gigeEth3DSCPSource56      	OBJECT-TYPE
        SYNTAX          	INTEGER 
        MAX-ACCESS      	read-write
        STATUS          	current
        DESCRIPTION     	"Set/Display Eth3 priority number for DSCP source 56"
        ::= { dscp 56 }

gigeEth3DSCPSource57      	OBJECT-TYPE
        SYNTAX          	INTEGER 
        MAX-ACCESS      	read-write
        STATUS          	current
        DESCRIPTION     	"Set/Display Eth3 priority number for DSCP source 57"
        ::= { dscp 57 }

gigeEth3DSCPSource58      	OBJECT-TYPE
        SYNTAX          	INTEGER 
        MAX-ACCESS      	read-write
        STATUS          	current
        DESCRIPTION     	"Set/Display Eth3 priority number for DSCP source 58"
        ::= { dscp 58 }

gigeEth3DSCPSource59      	OBJECT-TYPE
        SYNTAX          	INTEGER 
        MAX-ACCESS      	read-write
        STATUS          	current
        DESCRIPTION     	"Set/Display Eth3 priority number for DSCP source 59"
        ::= { dscp 59 }

gigeEth3DSCPSource60      	OBJECT-TYPE
        SYNTAX          	INTEGER 
        MAX-ACCESS      	read-write
        STATUS          	current
        DESCRIPTION     	"Set/Display Eth3 priority number for DSCP source 60"
        ::= { dscp 60 }

gigeEth3DSCPSource61      	OBJECT-TYPE
        SYNTAX          	INTEGER 
        MAX-ACCESS      	read-write
        STATUS          	current
        DESCRIPTION     	"Set/Display Eth3 priority number for DSCP source 61"
        ::= { dscp 61 }

gigeEth3DSCPSource62      	OBJECT-TYPE
        SYNTAX          	INTEGER 
        MAX-ACCESS      	read-write
        STATUS          	current
        DESCRIPTION     	"Set/Display Eth3 priority number for DSCP source 62"
        ::= { dscp 62 }

gigeEth3DSCPSource63      	OBJECT-TYPE
        SYNTAX          	INTEGER 
        MAX-ACCESS      	read-write
        STATUS          	current
        DESCRIPTION     	"Set/Display Eth3 priority number for DSCP source 63"
        ::= { dscp 63 }

eth4             		OBJECT IDENTIFIER ::= { gige 4  }

config4             		OBJECT IDENTIFIER ::= { eth4 1  }

gigeEth4AutNegotiate      	OBJECT-TYPE
    	SYNTAX              	INTEGER { off(0), on(1) }
        MAX-ACCESS      	read-write
        STATUS          	current
        DESCRIPTION     	"Set/Display auto neogitate setting for ETH 4"
        ::= { config4 1 }

gigeEth4Duplex      		OBJECT-TYPE
    	SYNTAX              	INTEGER { half(0), full(1) }
        MAX-ACCESS      	read-write
        STATUS          	current
        DESCRIPTION     	"Set/Display duplex setting for ETH 4"
        ::= { config4 2 }

gigeEth4Enable      		OBJECT-TYPE
    	SYNTAX              	INTEGER { off(0), on(1) }
        MAX-ACCESS      	read-write
        STATUS          	current
        DESCRIPTION     	"Set/Display enable setting for ETH 4"
        ::= { config4 3 }

gigeEth4MaxRate      		OBJECT-TYPE
    	SYNTAX              	INTEGER
        MAX-ACCESS      	read-write
        STATUS          	current
        DESCRIPTION     	"Set/Display max rate setting for ETH 4"
        ::= { config4 4 }

gigeEth4PauseFrame      	OBJECT-TYPE
    	SYNTAX              	INTEGER { off(0), on(1) }
        MAX-ACCESS      	read-write
        STATUS          	current
        DESCRIPTION     	"Set/Display pause frame setting for ETH 4"
        ::= { config4 5 }

gigeEth4Priority      		OBJECT-TYPE
        SYNTAX          	INTEGER
        MAX-ACCESS      	read-write
        STATUS          	current
        DESCRIPTION     	"Set/Display priority setting for ETH 4"
        ::= { config4 6 }

gigeEth4Speed      		OBJECT-TYPE
        SYNTAX          	INTEGER 
        MAX-ACCESS      	read-write
        STATUS          	current
        DESCRIPTION     	"Set/Display speed setting for ETH 4"
        ::= { config4 7 }

gigeEth4Status      		OBJECT-TYPE
    	SYNTAX              	INTEGER { off(0), on(1) }
        MAX-ACCESS      	read-only
        STATUS          	current
        DESCRIPTION     	"Set/Display port status for ETH 4"
        ::= { config4 8 }

counter4             		OBJECT IDENTIFIER ::= { eth4 2  }

gigeEth4InOctets      		OBJECT-TYPE
        SYNTAX          	Counter32 
        MAX-ACCESS      	read-only
        STATUS          	current
        DESCRIPTION     	"Display ETH4 IN octets counter"
        ::= { counter4 1 }

gigeEth4InUcastPackets      	OBJECT-TYPE
        SYNTAX          	Counter32 
        MAX-ACCESS      	read-only
        STATUS          	current
        DESCRIPTION     	"Display ETH4 IN unicast packet counter"
        ::= { counter4 2 }

gigeEth4InNUcastPackets      	OBJECT-TYPE
        SYNTAX          	Counter32 
        MAX-ACCESS      	read-only
        STATUS          	current
        DESCRIPTION     	"Display ETH4 IN non-unicast packet counter"
        ::= { counter4 3 }

gigeEth4InTotalPackets      	OBJECT-TYPE
        SYNTAX          	Counter32 
        MAX-ACCESS      	read-only
        STATUS          	current
        DESCRIPTION     	"Display ETH4 IN non-unicast packet counter"
        ::= { counter4 4 }

gigeEth4OutOctets      		OBJECT-TYPE
        SYNTAX          	Counter32 
        MAX-ACCESS      	read-only
        STATUS          	current
        DESCRIPTION     	"Display ETH4 OUT octets counter"
        ::= { counter4 5 }

gigeEth4OutUcastPackets      	OBJECT-TYPE
        SYNTAX          	Counter32 
        MAX-ACCESS      	read-only
        STATUS          	current
        DESCRIPTION     	"Display ETH4 OUT unicast packet counter"
        ::= { counter4 6 }

gigeEth4OutNUcastPackets      	OBJECT-TYPE
        SYNTAX          	Counter32 
        MAX-ACCESS      	read-only
        STATUS          	current
        DESCRIPTION     	"Display ETH4 OUT non-unicast packet counter"
        ::= { counter4 7 }

gigeEth4OutTotalPackets      	OBJECT-TYPE
        SYNTAX          	Counter32 
        MAX-ACCESS      	read-only
        STATUS          	current
        DESCRIPTION     	"Display ETH4 OUT total packet counter"
        ::= { counter4 8 }

gigeEth4CRCError      		OBJECT-TYPE
        SYNTAX          	Counter32 
        MAX-ACCESS      	read-only
        STATUS          	current
        DESCRIPTION     	"Display ETH4 CRC error counter"
        ::= { counter4 9 }

gigeEth4CollisionError      	OBJECT-TYPE
        SYNTAX          	Counter32 
        MAX-ACCESS      	read-only
        STATUS          	current
        DESCRIPTION     	"Display ETH4 Collision error counter"
        ::= { counter4 10 }

gigeEth4InPortRate              OBJECT-TYPE
        SYNTAX                  INTEGER
        MAX-ACCESS              read-only
        STATUS                  current
        DESCRIPTION             "Display ETH1 In Port Rate"
        ::= { counter1 11 }

gigeEth4InPortUtil              OBJECT-TYPE
        SYNTAX                  INTEGER
        MAX-ACCESS              read-only
        STATUS                  current
        DESCRIPTION             "Display ETH1 In Port utilization"
        ::= { counter1 12 }

gigeEth4OutPortRate             OBJECT-TYPE
        SYNTAX                  INTEGER
        MAX-ACCESS              read-only
        STATUS                  current
        DESCRIPTION             "Display ETH1 Out Port Rate"
        ::= { counter1 13 }

gigeEth4OutPortUtil             OBJECT-TYPE
        SYNTAX                  INTEGER 
        MAX-ACCESS              read-only
        STATUS                  current
        DESCRIPTION             "Display ETH1 Out Port utilization"
        ::= { counter1 14 }

dscp             		OBJECT IDENTIFIER ::= { eth4 3  }

gigeEth4DSCPSource1      	OBJECT-TYPE
        SYNTAX          	INTEGER 
        MAX-ACCESS      	read-write
        STATUS          	current
        DESCRIPTION     	"Set/Display Eth4 priority number for DSCP source 1"
        ::= { dscp 1 }

gigeEth4DSCPSource2      	OBJECT-TYPE
        SYNTAX          	INTEGER 
        MAX-ACCESS      	read-write
        STATUS          	current
        DESCRIPTION     	"Set/Display Eth4 priority number for DSCP source 2"
        ::= { dscp 2 }


gigeEth4DSCPSource3      	OBJECT-TYPE
        SYNTAX          	INTEGER 
        MAX-ACCESS      	read-write
        STATUS          	current
        DESCRIPTION     	"Set/Display Eth4 priority number for DSCP source 3"
        ::= { dscp 3 }


gigeEth4DSCPSource4      	OBJECT-TYPE
        SYNTAX          	INTEGER 
        MAX-ACCESS      	read-write
        STATUS          	current
        DESCRIPTION     	"Set/Display Eth4 priority number for DSCP source 4"
        ::= { dscp 4 }


gigeEth4DSCPSource5      	OBJECT-TYPE
        SYNTAX          	INTEGER 
        MAX-ACCESS      	read-write
        STATUS          	current
        DESCRIPTION     	"Set/Display Eth4 priority number for DSCP source 5"
        ::= { dscp 5 }


gigeEth4DSCPSource6      	OBJECT-TYPE
        SYNTAX          	INTEGER 
        MAX-ACCESS      	read-write
        STATUS          	current
        DESCRIPTION     	"Set/Display Eth4 priority number for DSCP source 6"
        ::= { dscp 6 }


gigeEth4DSCPSource7      	OBJECT-TYPE
        SYNTAX          	INTEGER 
        MAX-ACCESS      	read-write
        STATUS          	current
        DESCRIPTION     	"Set/Display Eth4 priority number for DSCP source 7"
        ::= { dscp 7 }


gigeEth4DSCPSource8      	OBJECT-TYPE
        SYNTAX          	INTEGER 
        MAX-ACCESS      	read-write
        STATUS          	current
        DESCRIPTION     	"Set/Display Eth4 priority number for DSCP source 8"
        ::= { dscp 8 }


gigeEth4DSCPSource9      	OBJECT-TYPE
        SYNTAX          	INTEGER 
        MAX-ACCESS      	read-write
        STATUS          	current
        DESCRIPTION     	"Set/Display Eth4 priority number for DSCP source 9"
        ::= { dscp 9 }


gigeEth4DSCPSource10      	OBJECT-TYPE
        SYNTAX          	INTEGER 
        MAX-ACCESS      	read-write
        STATUS          	current
        DESCRIPTION     	"Set/Display Eth4 priority number for DSCP source 10"
        ::= { dscp 10 }


gigeEth4DSCPSource11      	OBJECT-TYPE
        SYNTAX          	INTEGER 
        MAX-ACCESS      	read-write
        STATUS          	current
        DESCRIPTION     	"Set/Display Eth4 priority number for DSCP source 11"
        ::= { dscp 11 }


gigeEth4DSCPSource12      	OBJECT-TYPE
        SYNTAX          	INTEGER 
        MAX-ACCESS      	read-write
        STATUS          	current
        DESCRIPTION     	"Set/Display Eth4 priority number for DSCP source 12"
        ::= { dscp 12 }


gigeEth4DSCPSource13      	OBJECT-TYPE
        SYNTAX          	INTEGER 
        MAX-ACCESS      	read-write
        STATUS          	current
        DESCRIPTION     	"Set/Display Eth4 priority number for DSCP source 13"
        ::= { dscp 13 }


gigeEth4DSCPSource14      	OBJECT-TYPE
        SYNTAX          	INTEGER 
        MAX-ACCESS      	read-write
        STATUS          	current
        DESCRIPTION     	"Set/Display Eth4 priority number for DSCP source 14"
        ::= { dscp 14 }


gigeEth4DSCPSource15      	OBJECT-TYPE
        SYNTAX          	INTEGER 
        MAX-ACCESS      	read-write
        STATUS          	current
        DESCRIPTION     	"Set/Display Eth4 priority number for DSCP source 15"
        ::= { dscp 15 }

gigeEth4DSCPSource16      	OBJECT-TYPE
        SYNTAX          	INTEGER 
        MAX-ACCESS      	read-write
        STATUS          	current
        DESCRIPTION     	"Set/Display Eth4 priority number for DSCP source 16"
        ::= { dscp 16 }


gigeEth4DSCPSource17      	OBJECT-TYPE
        SYNTAX          	INTEGER 
        MAX-ACCESS      	read-write
        STATUS          	current
        DESCRIPTION     	"Set/Display Eth4 priority number for DSCP source 17"
        ::= { dscp 17 }


gigeEth4DSCPSource18      	OBJECT-TYPE
        SYNTAX          	INTEGER 
        MAX-ACCESS      	read-write
        STATUS          	current
        DESCRIPTION     	"Set/Display Eth4 priority number for DSCP source 18"
        ::= { dscp 18 }


gigeEth4DSCPSource19      	OBJECT-TYPE
        SYNTAX          	INTEGER 
        MAX-ACCESS      	read-write
        STATUS          	current
        DESCRIPTION     	"Set/Display Eth4 priority number for DSCP source 19"
        ::= { dscp 19 }


gigeEth4DSCPSource20      	OBJECT-TYPE
        SYNTAX          	INTEGER 
        MAX-ACCESS      	read-write
        STATUS          	current
        DESCRIPTION     	"Set/Display Eth4 priority number for DSCP source 20"
        ::= { dscp 20 }


gigeEth4DSCPSource21      	OBJECT-TYPE
        SYNTAX          	INTEGER 
        MAX-ACCESS      	read-write
        STATUS          	current
        DESCRIPTION     	"Set/Display Eth4 priority number for DSCP source 21"
        ::= { dscp 21 }


gigeEth4DSCPSource22      	OBJECT-TYPE
        SYNTAX          	INTEGER 
        MAX-ACCESS      	read-write
        STATUS          	current
        DESCRIPTION     	"Set/Display Eth4 priority number for DSCP source 22"
        ::= { dscp 22 }


gigeEth4DSCPSource23      	OBJECT-TYPE
        SYNTAX          	INTEGER 
        MAX-ACCESS      	read-write
        STATUS          	current
        DESCRIPTION     	"Set/Display Eth4 priority number for DSCP source 23"
        ::= { dscp 23 }


gigeEth4DSCPSource24      	OBJECT-TYPE
        SYNTAX          	INTEGER 
        MAX-ACCESS      	read-write
        STATUS          	current
        DESCRIPTION     	"Set/Display Eth4 priority number for DSCP source 24"
        ::= { dscp 24 }


gigeEth4DSCPSource25      	OBJECT-TYPE
        SYNTAX          	INTEGER 
        MAX-ACCESS      	read-write
        STATUS          	current
        DESCRIPTION     	"Set/Display Eth4 priority number for DSCP source 25"
        ::= { dscp 25 }

gigeEth4DSCPSource26      	OBJECT-TYPE
        SYNTAX          	INTEGER 
        MAX-ACCESS      	read-write
        STATUS          	current
        DESCRIPTION     	"Set/Display Eth4 priority number for DSCP source 26"
        ::= { dscp 26 }

gigeEth4DSCPSource27      	OBJECT-TYPE
        SYNTAX          	INTEGER 
        MAX-ACCESS      	read-write
        STATUS          	current
        DESCRIPTION     	"Set/Display Eth4 priority number for DSCP source 27"
        ::= { dscp 27 }

gigeEth4DSCPSource28      	OBJECT-TYPE
        SYNTAX          	INTEGER 
        MAX-ACCESS      	read-write
        STATUS          	current
        DESCRIPTION     	"Set/Display Eth4 priority number for DSCP source 28"
        ::= { dscp 28 }

gigeEth4DSCPSource29      	OBJECT-TYPE
        SYNTAX          	INTEGER 
        MAX-ACCESS      	read-write
        STATUS          	current
        DESCRIPTION     	"Set/Display Eth4 priority number for DSCP source 29"
        ::= { dscp 29 }

gigeEth4DSCPSource30      	OBJECT-TYPE
        SYNTAX          	INTEGER 
        MAX-ACCESS      	read-write
        STATUS          	current
        DESCRIPTION     	"Set/Display Eth4 priority number for DSCP source 30"
        ::= { dscp 30 }

gigeEth4DSCPSource31      	OBJECT-TYPE
        SYNTAX          	INTEGER 
        MAX-ACCESS      	read-write
        STATUS          	current
        DESCRIPTION     	"Set/Display Eth4 priority number for DSCP source 31"
        ::= { dscp 31 }

gigeEth4DSCPSource32      	OBJECT-TYPE
        SYNTAX          	INTEGER 
        MAX-ACCESS      	read-write
        STATUS          	current
        DESCRIPTION     	"Set/Display Eth4 priority number for DSCP source 32"
        ::= { dscp 32 }

gigeEth4DSCPSource33      	OBJECT-TYPE
        SYNTAX          	INTEGER 
        MAX-ACCESS      	read-write
        STATUS          	current
        DESCRIPTION     	"Set/Display Eth4 priority number for DSCP source 33"
        ::= { dscp 33 }

gigeEth4DSCPSource34      	OBJECT-TYPE
        SYNTAX          	INTEGER 
        MAX-ACCESS      	read-write
        STATUS          	current
        DESCRIPTION     	"Set/Display Eth4 priority number for DSCP source 34"
        ::= { dscp 34 }

gigeEth4DSCPSource35      	OBJECT-TYPE
        SYNTAX          	INTEGER 
        MAX-ACCESS      	read-write
        STATUS          	current
        DESCRIPTION     	"Set/Display Eth4 priority number for DSCP source 35"
        ::= { dscp 35 }

gigeEth4DSCPSource36      	OBJECT-TYPE
        SYNTAX          	INTEGER 
        MAX-ACCESS      	read-write
        STATUS          	current
        DESCRIPTION     	"Set/Display Eth4 priority number for DSCP source 36"
        ::= { dscp 36 }

gigeEth4DSCPSource37      	OBJECT-TYPE
        SYNTAX          	INTEGER 
        MAX-ACCESS      	read-write
        STATUS          	current
        DESCRIPTION     	"Set/Display Eth4 priority number for DSCP source 37"
        ::= { dscp 37 }

gigeEth4DSCPSource38      	OBJECT-TYPE
        SYNTAX          	INTEGER 
        MAX-ACCESS      	read-write
        STATUS          	current
        DESCRIPTION     	"Set/Display Eth4 priority number for DSCP source 38"
        ::= { dscp 38 }

gigeEth4DSCPSource39      	OBJECT-TYPE
        SYNTAX          	INTEGER 
        MAX-ACCESS      	read-write
        STATUS          	current
        DESCRIPTION     	"Set/Display Eth4 priority number for DSCP source 39"
        ::= { dscp 39 }

gigeEth4DSCPSource40      	OBJECT-TYPE
        SYNTAX          	INTEGER 
        MAX-ACCESS      	read-write
        STATUS          	current
        DESCRIPTION     	"Set/Display Eth4 priority number for DSCP source 40"
        ::= { dscp 40 }

gigeEth4DSCPSource41      	OBJECT-TYPE
        SYNTAX          	INTEGER 
        MAX-ACCESS      	read-write
        STATUS          	current
        DESCRIPTION     	"Set/Display Eth4 priority number for DSCP source 41"
        ::= { dscp 41 }

gigeEth4DSCPSource42      	OBJECT-TYPE
        SYNTAX          	INTEGER 
        MAX-ACCESS      	read-write
        STATUS          	current
        DESCRIPTION     	"Set/Display Eth4 priority number for DSCP source 42"
        ::= { dscp 42 }

gigeEth4DSCPSource43      	OBJECT-TYPE
        SYNTAX          	INTEGER 
        MAX-ACCESS      	read-write
        STATUS          	current
        DESCRIPTION     	"Set/Display Eth4 priority number for DSCP source 43"
        ::= { dscp 43 }

gigeEth4DSCPSource44      	OBJECT-TYPE
        SYNTAX          	INTEGER 
        MAX-ACCESS      	read-write
        STATUS          	current
        DESCRIPTION     	"Set/Display Eth4 priority number for DSCP source 44"
        ::= { dscp 44 }

gigeEth4DSCPSource45      	OBJECT-TYPE
        SYNTAX          	INTEGER 
        MAX-ACCESS      	read-write
        STATUS          	current
        DESCRIPTION     	"Set/Display Eth4 priority number for DSCP source 45"
        ::= { dscp 45 }

gigeEth4DSCPSource46      	OBJECT-TYPE
        SYNTAX          	INTEGER 
        MAX-ACCESS      	read-write
        STATUS          	current
        DESCRIPTION     	"Set/Display Eth4 priority number for DSCP source 46"
        ::= { dscp 46 }

gigeEth4DSCPSource47      	OBJECT-TYPE
        SYNTAX          	INTEGER 
        MAX-ACCESS      	read-write
        STATUS          	current
        DESCRIPTION     	"Set/Display Eth4 priority number for DSCP source 47"
        ::= { dscp 47 }

gigeEth4DSCPSource48      	OBJECT-TYPE
        SYNTAX          	INTEGER 
        MAX-ACCESS      	read-write
        STATUS          	current
        DESCRIPTION     	"Set/Display Eth4 priority number for DSCP source 48"
        ::= { dscp 48 }

gigeEth4DSCPSource49      	OBJECT-TYPE
        SYNTAX          	INTEGER 
        MAX-ACCESS      	read-write
        STATUS          	current
        DESCRIPTION     	"Set/Display Eth4 priority number for DSCP source 49"
        ::= { dscp 49 }

gigeEth4DSCPSource50      	OBJECT-TYPE
        SYNTAX          	INTEGER 
        MAX-ACCESS      	read-write
        STATUS          	current
        DESCRIPTION     	"Set/Display Eth4 priority number for DSCP source 50"
        ::= { dscp 50 }

gigeEth4DSCPSource51      	OBJECT-TYPE
        SYNTAX          	INTEGER 
        MAX-ACCESS      	read-write
        STATUS          	current
        DESCRIPTION     	"Set/Display Eth4 priority number for DSCP source 51"
        ::= { dscp 51 }

gigeEth4DSCPSource52      	OBJECT-TYPE
        SYNTAX          	INTEGER 
        MAX-ACCESS      	read-write
        STATUS          	current
        DESCRIPTION     	"Set/Display Eth4 priority number for DSCP source 52"
        ::= { dscp 52 }

gigeEth4DSCPSource53      	OBJECT-TYPE
        SYNTAX          	INTEGER 
        MAX-ACCESS      	read-write
        STATUS          	current
        DESCRIPTION     	"Set/Display Eth4 priority number for DSCP source 53"
        ::= { dscp 53 }

gigeEth4DSCPSource54      	OBJECT-TYPE
        SYNTAX          	INTEGER 
        MAX-ACCESS      	read-write
        STATUS          	current
        DESCRIPTION     	"Set/Display Eth4 priority number for DSCP source 54"
        ::= { dscp 54 }

gigeEth4DSCPSource55      	OBJECT-TYPE
        SYNTAX          	INTEGER 
        MAX-ACCESS      	read-write
        STATUS          	current
        DESCRIPTION     	"Set/Display Eth4 priority number for DSCP source 55"
        ::= { dscp 55 }

gigeEth4DSCPSource56      	OBJECT-TYPE
        SYNTAX          	INTEGER 
        MAX-ACCESS      	read-write
        STATUS          	current
        DESCRIPTION     	"Set/Display Eth4 priority number for DSCP source 56"
        ::= { dscp 56 }

gigeEth4DSCPSource57      	OBJECT-TYPE
        SYNTAX          	INTEGER 
        MAX-ACCESS      	read-write
        STATUS          	current
        DESCRIPTION     	"Set/Display Eth4 priority number for DSCP source 57"
        ::= { dscp 57 }

gigeEth4DSCPSource58      	OBJECT-TYPE
        SYNTAX          	INTEGER 
        MAX-ACCESS      	read-write
        STATUS          	current
        DESCRIPTION     	"Set/Display Eth4 priority number for DSCP source 58"
        ::= { dscp 58 }

gigeEth4DSCPSource59      	OBJECT-TYPE
        SYNTAX          	INTEGER 
        MAX-ACCESS      	read-write
        STATUS          	current
        DESCRIPTION     	"Set/Display Eth4 priority number for DSCP source 59"
        ::= { dscp 59 }

gigeEth4DSCPSource60      	OBJECT-TYPE
        SYNTAX          	INTEGER 
        MAX-ACCESS      	read-write
        STATUS          	current
        DESCRIPTION     	"Set/Display Eth4 priority number for DSCP source 60"
        ::= { dscp 60 }

gigeEth4DSCPSource61      	OBJECT-TYPE
        SYNTAX          	INTEGER 
        MAX-ACCESS      	read-write
        STATUS          	current
        DESCRIPTION     	"Set/Display Eth4 priority number for DSCP source 61"
        ::= { dscp 61 }

gigeEth4DSCPSource62      	OBJECT-TYPE
        SYNTAX          	INTEGER 
        MAX-ACCESS      	read-write
        STATUS          	current
        DESCRIPTION     	"Set/Display Eth4 priority number for DSCP source 62"
        ::= { dscp 62 }

gigeEth4DSCPSource63      	OBJECT-TYPE
        SYNTAX          	INTEGER 
        MAX-ACCESS      	read-write
        STATUS          	current
        DESCRIPTION     	"Set/Display Eth4 priority number for DSCP source 63"
        ::= { dscp 63 }

cos             		OBJECT IDENTIFIER ::= { gige 5  }

gigeEthPriority0COS      	OBJECT-TYPE
        SYNTAX          	INTEGER 
        MAX-ACCESS      	read-write
        STATUS          	current
        DESCRIPTION     	"Display ETH priority1 cOS queue number"
        ::= { cos 1 }

gigeEthPriority1COS      	OBJECT-TYPE
        SYNTAX          	INTEGER 
        MAX-ACCESS      	read-write
        STATUS          	current
        DESCRIPTION     	"Display ETH priority1 cOS queue number"
        ::= { cos 2 }

gigeEthPriority2COS      	OBJECT-TYPE
        SYNTAX          	INTEGER 
        MAX-ACCESS      	read-write
        STATUS          	current
        DESCRIPTION     	"Display ETH priority1 cOS queue number"
        ::= { cos 3 }

gigeEthPriority3COS      	OBJECT-TYPE
        SYNTAX          	INTEGER 
        MAX-ACCESS      	read-write
        STATUS          	current
        DESCRIPTION     	"Display ETH priority1 cOS queue number"
        ::= { cos 4 }

gigeEthPriority4COS      	OBJECT-TYPE
        SYNTAX          	INTEGER 
        MAX-ACCESS      	read-write
        STATUS          	current
        DESCRIPTION     	"Display ETH priority1 cOS queue number"
        ::= { cos 5 }

gigeEthPriority5COS      	OBJECT-TYPE
        SYNTAX          	INTEGER 
        MAX-ACCESS      	read-write
        STATUS          	current
        DESCRIPTION     	"Display ETH priority1 cOS queue number"
        ::= { cos 6 }

gigeEthPriority6COS      	OBJECT-TYPE
        SYNTAX          	INTEGER 
        MAX-ACCESS      	read-write
        STATUS          	current
        DESCRIPTION     	"Display ETH priority1 cOS queue number"
        ::= { cos 7 }

gigeEthPriority7COS      	OBJECT-TYPE
        SYNTAX          	INTEGER 
        MAX-ACCESS      	read-write
        STATUS          	current
        DESCRIPTION     	"Display ETH priority1 cOS queue number"
        ::= { cos 8 }

weight             		OBJECT IDENTIFIER ::= { gige 6  }

gigeEthPriority0DSCPWeight      OBJECT-TYPE
        SYNTAX          	INTEGER 
        MAX-ACCESS      	read-write
        STATUS          	current
        DESCRIPTION     	"Display ETH priority0 DSCP weight"
        ::= { weight 1 }

gigeEthPriority1DSCPWeight      OBJECT-TYPE
        SYNTAX          	INTEGER 
        MAX-ACCESS      	read-write
        STATUS          	current
        DESCRIPTION     	"Display ETH priority1 DSCP weight"
        ::= { weight 2 }

gigeEthPriority2DSCPWeight      OBJECT-TYPE
        SYNTAX          	INTEGER 
        MAX-ACCESS      	read-write
        STATUS          	current
        DESCRIPTION     	"Display ETH priority2 DSCP weight"
        ::= { weight 3 }

gigeEthPriority3DSCPWeight      OBJECT-TYPE
        SYNTAX          	INTEGER 
        MAX-ACCESS      	read-write
        STATUS          	current
        DESCRIPTION     	"Display ETH priority3 DSCP weight"
        ::= { weight 4 }

gigeEthPriority4DSCPWeight      OBJECT-TYPE
        SYNTAX          	INTEGER 
        MAX-ACCESS      	read-write
        STATUS          	current
        DESCRIPTION     	"Display ETH priority4 DSCP weight"
        ::= { weight 5 }

gigeEthPriority5DSCPWeight      OBJECT-TYPE
        SYNTAX          	INTEGER 
        MAX-ACCESS      	read-write
        STATUS          	current
        DESCRIPTION     	"Display ETH priority5 DSCP weight"
        ::= { weight 6 }

gigeEthPriority6DSCPWeight      OBJECT-TYPE
        SYNTAX          	INTEGER 
        MAX-ACCESS      	read-write
        STATUS          	current
        DESCRIPTION     	"Display ETH priority6 DSCP weight"
        ::= { weight 7 }

gigeEthPriority7DSCPWeight      OBJECT-TYPE
        SYNTAX          	INTEGER 
        MAX-ACCESS      	read-write
        STATUS          	current
        DESCRIPTION     	"Display ETH priority7 DSCP weight"
        ::= { weight 8 }


tdm1             		OBJECT IDENTIFIER ::= { tdm 1  }

tdm-config1             	OBJECT IDENTIFIER ::= { tdm1 1  }

tdmPort1Status      		OBJECT-TYPE
    	SYNTAX              	INTEGER { off(0), on(1) }
        MAX-ACCESS      	read-only
        STATUS          	current
        DESCRIPTION     	"Display TDM port1 status"
        ::= { tdm-config1 1 }

tdmPort1CableConfig      	OBJECT-TYPE
    	SYNTAX              	INTEGER { len0-133(0), len133-266(1), len266-399(2), len399-533(3),
					  len355-655(4) }
        MAX-ACCESS      	read-only
        STATUS          	current
        DESCRIPTION     	"Display TDM port1 cable configuration"
        ::= { tdm-config1 2 }

tdm-counter1             	OBJECT IDENTIFIER ::= { tdm1 2  }

tdmPort1CounterCrcBlockErrors  	OBJECT-TYPE
    	SYNTAX              	Counter32
        MAX-ACCESS      	read-only
        STATUS          	current
        DESCRIPTION     	"Display TDM port1 Crc Block error Counter"
        ::= { tdm-counter1 1 }

tdmPort1CounterExCrcErrors      OBJECT-TYPE
    	SYNTAX              	Counter32
        MAX-ACCESS      	read-only
        STATUS          	current
        DESCRIPTION     	"Display TDM port1 excessive CRC block Counter"
        ::= { tdm-counter1 2 }

tdmPort1CounterFBAErrors      	OBJECT-TYPE
    	SYNTAX              	Counter32
        MAX-ACCESS      	read-only
        STATUS          	current
        DESCRIPTION     	"Display TDM port1 FBA Errors Counter"
        ::= { tdm-counter1 3 }

tdmPort1CounterFEBErrors      	OBJECT-TYPE
    	SYNTAX              	Counter32
        MAX-ACCESS      	read-only
        STATUS          	current
        DESCRIPTION     	"Display TDM port1 FEB Errors Counter"
        ::= { tdm-counter1 4 }

tdmPort1CounterLCViolations    	OBJECT-TYPE
    	SYNTAX              	Counter32
        MAX-ACCESS      	read-only
        STATUS          	current
        DESCRIPTION     	"Display TDM port1 LC Violations Counter"
        ::= { tdm-counter1 5 }

tdm-alarm1             	OBJECT IDENTIFIER ::= { tdm1 3  }

tdmPort1AlarmLOS      		OBJECT-TYPE
    	SYNTAX              	Counter32
        MAX-ACCESS      	read-only
        STATUS          	current
        DESCRIPTION     	"Display TDM port1 LOS alarm"
        ::= { tdm-alarm1 1 }

tdmPort1AlarmLOF      		OBJECT-TYPE
    	SYNTAX              	Counter32
        MAX-ACCESS      	read-only
        STATUS          	current
        DESCRIPTION     	"Display TDM port1 LOF alarm"
        ::= { tdm-alarm1 2 }

tdmPort1AlarmAIS      		OBJECT-TYPE
    	SYNTAX              	Counter32
        MAX-ACCESS      	read-only
        STATUS          	current
        DESCRIPTION     	"Display TDM port1 AIS alarm"
        ::= { tdm-alarm1 3 }

tdmPort1AlarmTS16AIS      	OBJECT-TYPE
    	SYNTAX              	Counter32
        MAX-ACCESS      	read-only
        STATUS          	current
        DESCRIPTION     	"Display TDM port1 TS16AIS alarm"
        ::= { tdm-alarm1 4 }

tdmPort1AlarmRAI      		OBJECT-TYPE
    	SYNTAX              	Counter32
        MAX-ACCESS      	read-only
        STATUS          	current
        DESCRIPTION     	"Display TDM port1 RAI alarm"
        ::= { tdm-alarm1 5 }

tdmPort1AlarmRMA      		OBJECT-TYPE
    	SYNTAX              	Counter32
        MAX-ACCESS      	read-only
        STATUS          	current
        DESCRIPTION     	"Display TDM port1 RMA alarm"
        ::= { tdm-alarm1 6 }

tdmPort1AlarmLCMFA      	OBJECT-TYPE
    	SYNTAX              	Counter32
        MAX-ACCESS      	read-only
        STATUS          	current
        DESCRIPTION     	"Display TDM port1 LCMFA alarm"
        ::= { tdm-alarm1 7 }

tdmPort1AlarmLSMFA      	OBJECT-TYPE
    	SYNTAX              	Counter32
        MAX-ACCESS      	read-only
        STATUS          	current
        DESCRIPTION     	"Display TDM port1 LSMFA alarm"
        ::= { tdm-alarm1 8 }

tdm2             		OBJECT IDENTIFIER ::= { tdm 2  }

tdm-config2             	OBJECT IDENTIFIER ::= { tdm2 1  }

tdmPort2Status      		OBJECT-TYPE
    	SYNTAX              	INTEGER { off(0), on(1) }
        MAX-ACCESS      	read-only
        STATUS          	current
        DESCRIPTION     	"Display TDM port2 status"
        ::= { tdm-config2 1 }

tdmPort2CableConfig      	OBJECT-TYPE
    	SYNTAX              	INTEGER { len0-133(0), len133-266(1), len266-399(2), len399-533(3),
					  len355-655(4) }
        MAX-ACCESS      	read-only
        STATUS          	current
        DESCRIPTION     	"Display TDM port2 cable configuration"
        ::= { tdm-config2 2 }

tdm-counter2             	OBJECT IDENTIFIER ::= { tdm2 2  }

tdmPort2CounterCrcBlockErrors  	OBJECT-TYPE
    	SYNTAX              	Counter32
        MAX-ACCESS      	read-only
        STATUS          	current
        DESCRIPTION     	"Display TDM port2 Crc Block error Counter"
        ::= { tdm-counter2 1 }

tdmPort2CounterExCrcErrors      OBJECT-TYPE
    	SYNTAX              	Counter32
        MAX-ACCESS      	read-only
        STATUS          	current
        DESCRIPTION     	"Display TDM port2 excessive CRC block Counter"
        ::= { tdm-counter2 2 }

tdmPort2CounterFBAErrors      	OBJECT-TYPE
    	SYNTAX              	Counter32
        MAX-ACCESS      	read-only
        STATUS          	current
        DESCRIPTION     	"Display TDM port2 FBA Errors Counter"
        ::= { tdm-counter2 3 }

tdmPort2CounterFEBErrors      	OBJECT-TYPE
    	SYNTAX              	Counter32
        MAX-ACCESS      	read-only
        STATUS          	current
        DESCRIPTION     	"Display TDM port2 FEB Errors Counter"
        ::= { tdm-counter2 4 }

tdmPort2CounterLCViolations    	OBJECT-TYPE
    	SYNTAX              	Counter32
        MAX-ACCESS      	read-only
        STATUS          	current
        DESCRIPTION     	"Display TDM port2 LC Violations Counter"
        ::= { tdm-counter2 5 }

tdm-alarm2             	OBJECT IDENTIFIER ::= { tdm2 3  }

tdmPort2AlarmLOS      		OBJECT-TYPE
    	SYNTAX              	Counter32
        MAX-ACCESS      	read-only
        STATUS          	current
        DESCRIPTION     	"Display TDM port2 LOS alarm"
        ::= { tdm-alarm2 1 }

tdmPort2AlarmLOF      		OBJECT-TYPE
    	SYNTAX              	Counter32
        MAX-ACCESS      	read-only
        STATUS          	current
        DESCRIPTION     	"Display TDM port2 LOF alarm"
        ::= { tdm-alarm2 2 }

tdmPort2AlarmAIS      		OBJECT-TYPE
    	SYNTAX              	Counter32
        MAX-ACCESS      	read-only
        STATUS          	current
        DESCRIPTION     	"Display TDM port2 AIS alarm"
        ::= { tdm-alarm2 3 }

tdmPort2AlarmTS16AIS      	OBJECT-TYPE
    	SYNTAX              	Counter32
        MAX-ACCESS      	read-only
        STATUS          	current
        DESCRIPTION     	"Display TDM port2 TS16AIS alarm"
        ::= { tdm-alarm2 4 }

tdmPort2AlarmRAI      		OBJECT-TYPE
    	SYNTAX              	Counter32
        MAX-ACCESS      	read-only
        STATUS          	current
        DESCRIPTION     	"Display TDM port2 RAI alarm"
        ::= { tdm-alarm2 5 }

tdmPort2AlarmRMA      		OBJECT-TYPE
    	SYNTAX              	Counter32
        MAX-ACCESS      	read-only
        STATUS          	current
        DESCRIPTION     	"Display TDM port2 RMA alarm"
        ::= { tdm-alarm2 6 }

tdmPort2AlarmLCMFA      	OBJECT-TYPE
    	SYNTAX              	Counter32
        MAX-ACCESS      	read-only
        STATUS          	current
        DESCRIPTION     	"Display TDM port2 LCMFA alarm"
        ::= { tdm-alarm2 7 }

tdmPort2AlarmLSMFA      	OBJECT-TYPE
    	SYNTAX              	Counter32
        MAX-ACCESS      	read-only
        STATUS          	current
        DESCRIPTION     	"Display TDM port2 LSMFA alarm"
        ::= { tdm-alarm2 8 }

tdm3             		OBJECT IDENTIFIER ::= { tdm 3  }

tdm-config3             	OBJECT IDENTIFIER ::= { tdm3 1  }

tdmPort3Status      		OBJECT-TYPE
    	SYNTAX              	INTEGER { off(0), on(1) }
        MAX-ACCESS      	read-only
        STATUS          	current
        DESCRIPTION     	"Display TDM port3 status"
        ::= { tdm-config3 1 }

tdmPort3CableConfig      	OBJECT-TYPE
    	SYNTAX              	INTEGER { len0-133(0), len133-266(1), len266-399(2), len399-533(3),
					  len355-655(4) }
        MAX-ACCESS      	read-only
        STATUS          	current
        DESCRIPTION     	"Display TDM port3 cable configuration"
        ::= { tdm-config3 2 }

tdm-counter3             	OBJECT IDENTIFIER ::= { tdm3 2  }

tdmPort3CounterCrcBlockErrors  	OBJECT-TYPE
    	SYNTAX              	Counter32
        MAX-ACCESS      	read-only
        STATUS          	current
        DESCRIPTION     	"Display TDM port3 Crc Block error Counter"
        ::= { tdm-counter3 1 }

tdmPort3CounterExCrcErrors      OBJECT-TYPE
    	SYNTAX              	Counter32
        MAX-ACCESS      	read-only
        STATUS          	current
        DESCRIPTION     	"Display TDM port3 excessive CRC block Counter"
        ::= { tdm-counter3 2 }

tdmPort3CounterFBAErrors      	OBJECT-TYPE
    	SYNTAX              	Counter32
        MAX-ACCESS      	read-only
        STATUS          	current
        DESCRIPTION     	"Display TDM port3 FBA Errors Counter"
        ::= { tdm-counter3 3 }

tdmPort3CounterFEBErrors      	OBJECT-TYPE
    	SYNTAX              	Counter32
        MAX-ACCESS      	read-only
        STATUS          	current
        DESCRIPTION     	"Display TDM port3 FEB Errors Counter"
        ::= { tdm-counter3 4 }

tdmPort3CounterLCViolations    	OBJECT-TYPE
    	SYNTAX              	Counter32
        MAX-ACCESS      	read-only
        STATUS          	current
        DESCRIPTION     	"Display TDM port3 LC Violations Counter"
        ::= { tdm-counter3 5 }

tdm-alarm3             	OBJECT IDENTIFIER ::= { tdm3 3  }

tdmPort3AlarmLOS      		OBJECT-TYPE
    	SYNTAX              	Counter32
        MAX-ACCESS      	read-only
        STATUS          	current
        DESCRIPTION     	"Display TDM port3 LOS alarm"
        ::= { tdm-alarm3 1 }

tdmPort3AlarmLOF      		OBJECT-TYPE
    	SYNTAX              	Counter32
        MAX-ACCESS      	read-only
        STATUS          	current
        DESCRIPTION     	"Display TDM port3 LOF alarm"
        ::= { tdm-alarm3 2 }

tdmPort3AlarmAIS      		OBJECT-TYPE
    	SYNTAX              	Counter32
        MAX-ACCESS      	read-only
        STATUS          	current
        DESCRIPTION     	"Display TDM port3 AIS alarm"
        ::= { tdm-alarm3 3 }

tdmPort3AlarmTS16AIS      	OBJECT-TYPE
    	SYNTAX              	Counter32
        MAX-ACCESS      	read-only
        STATUS          	current
        DESCRIPTION     	"Display TDM port3 TS16AIS alarm"
        ::= { tdm-alarm3 4 }

tdmPort3AlarmRAI      		OBJECT-TYPE
    	SYNTAX              	Counter32
        MAX-ACCESS      	read-only
        STATUS          	current
        DESCRIPTION     	"Display TDM port3 RAI alarm"
        ::= { tdm-alarm3 5 }

tdmPort3AlarmRMA      		OBJECT-TYPE
    	SYNTAX              	Counter32
        MAX-ACCESS      	read-only
        STATUS          	current
        DESCRIPTION     	"Display TDM port3 RMA alarm"
        ::= { tdm-alarm3 6 }

tdmPort3AlarmLCMFA      	OBJECT-TYPE
    	SYNTAX              	Counter32
        MAX-ACCESS      	read-only
        STATUS          	current
        DESCRIPTION     	"Display TDM port3 LCMFA alarm"
        ::= { tdm-alarm3 7 }

tdmPort3AlarmLSMFA      	OBJECT-TYPE
    	SYNTAX              	Counter32
        MAX-ACCESS      	read-only
        STATUS          	current
        DESCRIPTION     	"Display TDM port3 LSMFA alarm"
        ::= { tdm-alarm3 8 }

tdm4             		OBJECT IDENTIFIER ::= { tdm 4  }

tdm-config4             	OBJECT IDENTIFIER ::= { tdm4 1  }

tdmPort4Status      		OBJECT-TYPE
    	SYNTAX              	INTEGER { off(0), on(1) }
        MAX-ACCESS      	read-only
        STATUS          	current
        DESCRIPTION     	"Display TDM port4 status"
        ::= { tdm-config4 1 }

tdmPort4CableConfig      	OBJECT-TYPE
    	SYNTAX              	INTEGER { len0-133(0), len133-266(1), len266-399(2), len399-533(3),
					  len355-655(4) }
        MAX-ACCESS      	read-only
        STATUS          	current
        DESCRIPTION     	"Display TDM port4 cable configuration"
        ::= { tdm-config4 2 }

tdm-counter4             	OBJECT IDENTIFIER ::= { tdm4 2  }

tdmPort4CounterCrcBlockErrors  	OBJECT-TYPE
    	SYNTAX              	Counter32
        MAX-ACCESS      	read-only
        STATUS          	current
        DESCRIPTION     	"Display TDM port4 Crc Block error Counter"
        ::= { tdm-counter4 1 }

tdmPort4CounterExCrcErrors      OBJECT-TYPE
    	SYNTAX              	Counter32
        MAX-ACCESS      	read-only
        STATUS          	current
        DESCRIPTION     	"Display TDM port4 excessive CRC block Counter"
        ::= { tdm-counter4 2 }

tdmPort4CounterFBAErrors      	OBJECT-TYPE
    	SYNTAX              	Counter32
        MAX-ACCESS      	read-only
        STATUS          	current
        DESCRIPTION     	"Display TDM port4 FBA Errors Counter"
        ::= { tdm-counter4 3 }

tdmPort4CounterFEBErrors      	OBJECT-TYPE
    	SYNTAX              	Counter32
        MAX-ACCESS      	read-only
        STATUS          	current
        DESCRIPTION     	"Display TDM port4 FEB Errors Counter"
        ::= { tdm-counter4 4 }

tdmPort4CounterLCViolations    	OBJECT-TYPE
    	SYNTAX              	Counter32
        MAX-ACCESS      	read-only
        STATUS          	current
        DESCRIPTION     	"Display TDM port4 LC Violations Counter"
        ::= { tdm-counter4 5 }

tdm-alarm4             	OBJECT IDENTIFIER ::= { tdm4 3  }

tdmPort4AlarmLOS      		OBJECT-TYPE
    	SYNTAX              	Counter32
        MAX-ACCESS      	read-only
        STATUS          	current
        DESCRIPTION     	"Display TDM port4 LOS alarm"
        ::= { tdm-alarm4 1 }

tdmPort4AlarmLOF      		OBJECT-TYPE
    	SYNTAX              	Counter32
        MAX-ACCESS      	read-only
        STATUS          	current
        DESCRIPTION     	"Display TDM port4 LOF alarm"
        ::= { tdm-alarm4 2 }

tdmPort4AlarmAIS      		OBJECT-TYPE
    	SYNTAX              	Counter32
        MAX-ACCESS      	read-only
        STATUS          	current
        DESCRIPTION     	"Display TDM port4 AIS alarm"
        ::= { tdm-alarm4 3 }

tdmPort4AlarmTS16AIS      	OBJECT-TYPE
    	SYNTAX              	Counter32
        MAX-ACCESS      	read-only
        STATUS          	current
        DESCRIPTION     	"Display TDM port4 TS16AIS alarm"
        ::= { tdm-alarm4 4 }

tdmPort4AlarmRAI      		OBJECT-TYPE
    	SYNTAX              	Counter32
        MAX-ACCESS      	read-only
        STATUS          	current
        DESCRIPTION     	"Display TDM port4 RAI alarm"
        ::= { tdm-alarm4 5 }

tdmPort4AlarmRMA      		OBJECT-TYPE
    	SYNTAX              	Counter32
        MAX-ACCESS      	read-only
        STATUS          	current
        DESCRIPTION     	"Display TDM port4 RMA alarm"
        ::= { tdm-alarm4 6 }

tdmPort4AlarmLCMFA      	OBJECT-TYPE
    	SYNTAX              	Counter32
        MAX-ACCESS      	read-only
        STATUS          	current
        DESCRIPTION     	"Display TDM port4 LCMFA alarm"
        ::= { tdm-alarm4 7 }

tdmPort4AlarmLSMFA      	OBJECT-TYPE
    	SYNTAX              	Counter32
        MAX-ACCESS      	read-only
        STATUS          	current
        DESCRIPTION     	"Display TDM port4 LSMFA alarm"
        ::= { tdm-alarm4 8 }

tdm5             		OBJECT IDENTIFIER ::= { tdm 5  }

tdm-config5             	OBJECT IDENTIFIER ::= { tdm5 1  }

tdmPort5Status      		OBJECT-TYPE
    	SYNTAX              	INTEGER { off(0), on(1) }
        MAX-ACCESS      	read-only
        STATUS          	current
        DESCRIPTION     	"Display TDM port5 status"
        ::= { tdm-config5 1 }

tdmPort5CableConfig      	OBJECT-TYPE
    	SYNTAX              	INTEGER { len0-133(0), len133-266(1), len266-399(2), len399-533(3),
					  len355-655(4) }
        MAX-ACCESS      	read-only
        STATUS          	current
        DESCRIPTION     	"Display TDM port5 cable configuration"
        ::= { tdm-config5 2 }

tdm-counter5             	OBJECT IDENTIFIER ::= { tdm5 2  }

tdmPort5CounterCrcBlockErrors  	OBJECT-TYPE
    	SYNTAX              	Counter32
        MAX-ACCESS      	read-only
        STATUS          	current
        DESCRIPTION     	"Display TDM port5 Crc Block error Counter"
        ::= { tdm-counter5 1 }

tdmPort5CounterExCrcErrors      OBJECT-TYPE
    	SYNTAX              	Counter32
        MAX-ACCESS      	read-only
        STATUS          	current
        DESCRIPTION     	"Display TDM port5 excessive CRC block Counter"
        ::= { tdm-counter5 2 }

tdmPort5CounterFBAErrors      	OBJECT-TYPE
    	SYNTAX              	Counter32
        MAX-ACCESS      	read-only
        STATUS          	current
        DESCRIPTION     	"Display TDM port5 FBA Errors Counter"
        ::= { tdm-counter5 3 }

tdmPort5CounterFEBErrors      	OBJECT-TYPE
    	SYNTAX              	Counter32
        MAX-ACCESS      	read-only
        STATUS          	current
        DESCRIPTION     	"Display TDM port5 FEB Errors Counter"
        ::= { tdm-counter5 4 }

tdmPort5CounterLCViolations    	OBJECT-TYPE
    	SYNTAX              	Counter32
        MAX-ACCESS      	read-only
        STATUS          	current
        DESCRIPTION     	"Display TDM port5 LC Violations Counter"
        ::= { tdm-counter5 5 }

tdm-alarm5             	OBJECT IDENTIFIER ::= { tdm5 3  }

tdmPort5AlarmLOS      		OBJECT-TYPE
    	SYNTAX              	Counter32
        MAX-ACCESS      	read-only
        STATUS          	current
        DESCRIPTION     	"Display TDM port5 LOS alarm"
        ::= { tdm-alarm5 1 }

tdmPort5AlarmLOF      		OBJECT-TYPE
    	SYNTAX              	Counter32
        MAX-ACCESS      	read-only
        STATUS          	current
        DESCRIPTION     	"Display TDM port5 LOF alarm"
        ::= { tdm-alarm5 2 }

tdmPort5AlarmAIS      		OBJECT-TYPE
    	SYNTAX              	Counter32
        MAX-ACCESS      	read-only
        STATUS          	current
        DESCRIPTION     	"Display TDM port5 AIS alarm"
        ::= { tdm-alarm5 3 }

tdmPort5AlarmTS16AIS      	OBJECT-TYPE
    	SYNTAX              	Counter32
        MAX-ACCESS      	read-only
        STATUS          	current
        DESCRIPTION     	"Display TDM port5 TS16AIS alarm"
        ::= { tdm-alarm5 4 }

tdmPort5AlarmRAI      		OBJECT-TYPE
    	SYNTAX              	Counter32
        MAX-ACCESS      	read-only
        STATUS          	current
        DESCRIPTION     	"Display TDM port5 RAI alarm"
        ::= { tdm-alarm5 5 }

tdmPort5AlarmRMA      		OBJECT-TYPE
    	SYNTAX              	Counter32
        MAX-ACCESS      	read-only
        STATUS          	current
        DESCRIPTION     	"Display TDM port5 RMA alarm"
        ::= { tdm-alarm5 6 }

tdmPort5AlarmLCMFA      	OBJECT-TYPE
    	SYNTAX              	Counter32
        MAX-ACCESS      	read-only
        STATUS          	current
        DESCRIPTION     	"Display TDM port5 LCMFA alarm"
        ::= { tdm-alarm5 7 }

tdmPort5AlarmLSMFA      	OBJECT-TYPE
    	SYNTAX              	Counter32
        MAX-ACCESS      	read-only
        STATUS          	current
        DESCRIPTION     	"Display TDM port5 LSMFA alarm"
        ::= { tdm-alarm5 8 }

tdm6             		OBJECT IDENTIFIER ::= { tdm 6  }

tdm-config6             	OBJECT IDENTIFIER ::= { tdm6 1  }

tdmPort6Status      		OBJECT-TYPE
    	SYNTAX              	INTEGER { off(0), on(1) }
        MAX-ACCESS      	read-only
        STATUS          	current
        DESCRIPTION     	"Display TDM port6 status"
        ::= { tdm-config6 1 }

tdmPort6CableConfig      	OBJECT-TYPE
    	SYNTAX              	INTEGER { len0-133(0), len133-266(1), len266-399(2), len399-533(3),
					  len355-655(4) }
        MAX-ACCESS      	read-only
        STATUS          	current
        DESCRIPTION     	"Display TDM port6 cable configuration"
        ::= { tdm-config6 2 }

tdm-counter6             	OBJECT IDENTIFIER ::= { tdm6 2  }

tdmPort6CounterCrcBlockErrors  	OBJECT-TYPE
    	SYNTAX              	Counter32
        MAX-ACCESS      	read-only
        STATUS          	current
        DESCRIPTION     	"Display TDM port6 Crc Block error Counter"
        ::= { tdm-counter6 1 }

tdmPort6CounterExCrcErrors      OBJECT-TYPE
    	SYNTAX              	Counter32
        MAX-ACCESS      	read-only
        STATUS          	current
        DESCRIPTION     	"Display TDM port6 excessive CRC block Counter"
        ::= { tdm-counter6 2 }

tdmPort6CounterFBAErrors      	OBJECT-TYPE
    	SYNTAX              	Counter32
        MAX-ACCESS      	read-only
        STATUS          	current
        DESCRIPTION     	"Display TDM port6 FBA Errors Counter"
        ::= { tdm-counter6 3 }

tdmPort6CounterFEBErrors      	OBJECT-TYPE
    	SYNTAX              	Counter32
        MAX-ACCESS      	read-only
        STATUS          	current
        DESCRIPTION     	"Display TDM port6 FEB Errors Counter"
        ::= { tdm-counter6 4 }

tdmPort6CounterLCViolations    	OBJECT-TYPE
    	SYNTAX              	Counter32
        MAX-ACCESS      	read-only
        STATUS          	current
        DESCRIPTION     	"Display TDM port6 LC Violations Counter"
        ::= { tdm-counter6 5 }

tdm-alarm6             	OBJECT IDENTIFIER ::= { tdm6 3  }

tdmPort6AlarmLOS      		OBJECT-TYPE
    	SYNTAX              	Counter32
        MAX-ACCESS      	read-only
        STATUS          	current
        DESCRIPTION     	"Display TDM port6 LOS alarm"
        ::= { tdm-alarm6 1 }

tdmPort6AlarmLOF      		OBJECT-TYPE
    	SYNTAX              	Counter32
        MAX-ACCESS      	read-only
        STATUS          	current
        DESCRIPTION     	"Display TDM port6 LOF alarm"
        ::= { tdm-alarm6 2 }

tdmPort6AlarmAIS      		OBJECT-TYPE
    	SYNTAX              	Counter32
        MAX-ACCESS      	read-only
        STATUS          	current
        DESCRIPTION     	"Display TDM port6 AIS alarm"
        ::= { tdm-alarm6 3 }

tdmPort6AlarmTS16AIS      	OBJECT-TYPE
    	SYNTAX              	Counter32
        MAX-ACCESS      	read-only
        STATUS          	current
        DESCRIPTION     	"Display TDM port6 TS16AIS alarm"
        ::= { tdm-alarm6 4 }

tdmPort6AlarmRAI      		OBJECT-TYPE
    	SYNTAX              	Counter32
        MAX-ACCESS      	read-only
        STATUS          	current
        DESCRIPTION     	"Display TDM port6 RAI alarm"
        ::= { tdm-alarm6 5 }

tdmPort6AlarmRMA      		OBJECT-TYPE
    	SYNTAX              	Counter32
        MAX-ACCESS      	read-only
        STATUS          	current
        DESCRIPTION     	"Display TDM port6 RMA alarm"
        ::= { tdm-alarm6 6 }

tdmPort6AlarmLCMFA      	OBJECT-TYPE
    	SYNTAX              	Counter32
        MAX-ACCESS      	read-only
        STATUS          	current
        DESCRIPTION     	"Display TDM port6 LCMFA alarm"
        ::= { tdm-alarm6 7 }

tdmPort6AlarmLSMFA      	OBJECT-TYPE
    	SYNTAX              	Counter32
        MAX-ACCESS      	read-only
        STATUS          	current
        DESCRIPTION     	"Display TDM port6 LSMFA alarm"
        ::= { tdm-alarm6 8 }

tdm7             		OBJECT IDENTIFIER ::= { tdm 7  }

tdm-config7             	OBJECT IDENTIFIER ::= { tdm7 1  }

tdmPort7Status      		OBJECT-TYPE
    	SYNTAX              	INTEGER { off(0), on(1) }
        MAX-ACCESS      	read-only
        STATUS          	current
        DESCRIPTION     	"Display TDM port7 status"
        ::= { tdm-config7 1 }

tdmPort7CableConfig      	OBJECT-TYPE
    	SYNTAX              	INTEGER { len0-133(0), len133-266(1), len266-399(2), len399-533(3),
					  len355-655(4) }
        MAX-ACCESS      	read-only
        STATUS          	current
        DESCRIPTION     	"Display TDM port7 cable configuration"
        ::= { tdm-config7 2 }

tdm-counter7             	OBJECT IDENTIFIER ::= { tdm7 2  }

tdmPort7CounterCrcBlockErrors  	OBJECT-TYPE
    	SYNTAX              	Counter32
        MAX-ACCESS      	read-only
        STATUS          	current
        DESCRIPTION     	"Display TDM port7 Crc Block error Counter"
        ::= { tdm-counter7 1 }

tdmPort7CounterExCrcErrors      OBJECT-TYPE
    	SYNTAX              	Counter32
        MAX-ACCESS      	read-only
        STATUS          	current
        DESCRIPTION     	"Display TDM port7 excessive CRC block Counter"
        ::= { tdm-counter7 2 }

tdmPort7CounterFBAErrors      	OBJECT-TYPE
    	SYNTAX              	Counter32
        MAX-ACCESS      	read-only
        STATUS          	current
        DESCRIPTION     	"Display TDM port7 FBA Errors Counter"
        ::= { tdm-counter7 3 }

tdmPort7CounterFEBErrors      	OBJECT-TYPE
    	SYNTAX              	Counter32
        MAX-ACCESS      	read-only
        STATUS          	current
        DESCRIPTION     	"Display TDM port7 FEB Errors Counter"
        ::= { tdm-counter7 4 }

tdmPort7CounterLCViolations    	OBJECT-TYPE
    	SYNTAX              	Counter32
        MAX-ACCESS      	read-only
        STATUS          	current
        DESCRIPTION     	"Display TDM port7 LC Violations Counter"
        ::= { tdm-counter7 5 }

tdm-alarm7             	OBJECT IDENTIFIER ::= { tdm7 3  }

tdmPort7AlarmLOS      		OBJECT-TYPE
    	SYNTAX              	Counter32
        MAX-ACCESS      	read-only
        STATUS          	current
        DESCRIPTION     	"Display TDM port7 LOS alarm"
        ::= { tdm-alarm7 1 }

tdmPort7AlarmLOF      		OBJECT-TYPE
    	SYNTAX              	Counter32
        MAX-ACCESS      	read-only
        STATUS          	current
        DESCRIPTION     	"Display TDM port7 LOF alarm"
        ::= { tdm-alarm7 2 }

tdmPort7AlarmAIS      		OBJECT-TYPE
    	SYNTAX              	Counter32
        MAX-ACCESS      	read-only
        STATUS          	current
        DESCRIPTION     	"Display TDM port7 AIS alarm"
        ::= { tdm-alarm7 3 }

tdmPort7AlarmTS16AIS      	OBJECT-TYPE
    	SYNTAX              	Counter32
        MAX-ACCESS      	read-only
        STATUS          	current
        DESCRIPTION     	"Display TDM port7 TS16AIS alarm"
        ::= { tdm-alarm7 4 }

tdmPort7AlarmRAI      		OBJECT-TYPE
    	SYNTAX              	Counter32
        MAX-ACCESS      	read-only
        STATUS          	current
        DESCRIPTION     	"Display TDM port7 RAI alarm"
        ::= { tdm-alarm7 5 }

tdmPort7AlarmRMA      		OBJECT-TYPE
    	SYNTAX              	Counter32
        MAX-ACCESS      	read-only
        STATUS          	current
        DESCRIPTION     	"Display TDM port7 RMA alarm"
        ::= { tdm-alarm7 6 }

tdmPort7AlarmLCMFA      	OBJECT-TYPE
    	SYNTAX              	Counter32
        MAX-ACCESS      	read-only
        STATUS          	current
        DESCRIPTION     	"Display TDM port7 LCMFA alarm"
        ::= { tdm-alarm7 7 }

tdmPort7AlarmLSMFA      	OBJECT-TYPE
    	SYNTAX              	Counter32
        MAX-ACCESS      	read-only
        STATUS          	current
        DESCRIPTION     	"Display TDM port7 LSMFA alarm"
        ::= { tdm-alarm7 8 }

tdm8             		OBJECT IDENTIFIER ::= { tdm 8  }

tdm-config8             	OBJECT IDENTIFIER ::= { tdm8 1  }

tdmPort8Status      		OBJECT-TYPE
    	SYNTAX              	INTEGER { off(0), on(1) }
        MAX-ACCESS      	read-only
        STATUS          	current
        DESCRIPTION     	"Display TDM port8 status"
        ::= { tdm-config8 1 }

tdmPort8CableConfig      	OBJECT-TYPE
    	SYNTAX              	INTEGER { len0-133(0), len133-266(1), len266-399(2), len399-533(3),
					  len355-655(4) }
        MAX-ACCESS      	read-only
        STATUS          	current
        DESCRIPTION     	"Display TDM port8 cable configuration"
        ::= { tdm-config8 2 }

tdm-counter8             	OBJECT IDENTIFIER ::= { tdm8 2  }

tdmPort8CounterCrcBlockErrors  	OBJECT-TYPE
    	SYNTAX              	Counter32
        MAX-ACCESS      	read-only
        STATUS          	current
        DESCRIPTION     	"Display TDM port8 Crc Block error Counter"
        ::= { tdm-counter8 1 }

tdmPort8CounterExCrcErrors      OBJECT-TYPE
    	SYNTAX              	Counter32
        MAX-ACCESS      	read-only
        STATUS          	current
        DESCRIPTION     	"Display TDM port8 excessive CRC block Counter"
        ::= { tdm-counter8 2 }

tdmPort8CounterFBAErrors      	OBJECT-TYPE
    	SYNTAX              	Counter32
        MAX-ACCESS      	read-only
        STATUS          	current
        DESCRIPTION     	"Display TDM port8 FBA Errors Counter"
        ::= { tdm-counter8 3 }

tdmPort8CounterFEBErrors      	OBJECT-TYPE
    	SYNTAX              	Counter32
        MAX-ACCESS      	read-only
        STATUS          	current
        DESCRIPTION     	"Display TDM port8 FEB Errors Counter"
        ::= { tdm-counter8 4 }

tdmPort8CounterLCViolations    	OBJECT-TYPE
    	SYNTAX              	Counter32
        MAX-ACCESS      	read-only
        STATUS          	current
        DESCRIPTION     	"Display TDM port8 LC Violations Counter"
        ::= { tdm-counter8 5 }

tdm-alarm8             	OBJECT IDENTIFIER ::= { tdm8 3  }

tdmPort8AlarmLOS      		OBJECT-TYPE
    	SYNTAX              	Counter32
        MAX-ACCESS      	read-only
        STATUS          	current
        DESCRIPTION     	"Display TDM port8 LOS alarm"
        ::= { tdm-alarm8 1 }

tdmPort8AlarmLOF      		OBJECT-TYPE
    	SYNTAX              	Counter32
        MAX-ACCESS      	read-only
        STATUS          	current
        DESCRIPTION     	"Display TDM port8 LOF alarm"
        ::= { tdm-alarm8 2 }

tdmPort8AlarmAIS      		OBJECT-TYPE
    	SYNTAX              	Counter32
        MAX-ACCESS      	read-only
        STATUS          	current
        DESCRIPTION     	"Display TDM port8 AIS alarm"
        ::= { tdm-alarm8 3 }

tdmPort8AlarmTS16AIS      	OBJECT-TYPE
    	SYNTAX              	Counter32
        MAX-ACCESS      	read-only
        STATUS          	current
        DESCRIPTION     	"Display TDM port8 TS16AIS alarm"
        ::= { tdm-alarm8 4 }

tdmPort8AlarmRAI      		OBJECT-TYPE
    	SYNTAX              	Counter32
        MAX-ACCESS      	read-only
        STATUS          	current
        DESCRIPTION     	"Display TDM port8 RAI alarm"
        ::= { tdm-alarm8 5 }

tdmPort8AlarmRMA      		OBJECT-TYPE
    	SYNTAX              	Counter32
        MAX-ACCESS      	read-only
        STATUS          	current
        DESCRIPTION     	"Display TDM port8 RMA alarm"
        ::= { tdm-alarm8 6 }

tdmPort8AlarmLCMFA      	OBJECT-TYPE
    	SYNTAX              	Counter32
        MAX-ACCESS      	read-only
        STATUS          	current
        DESCRIPTION     	"Display TDM port8 LCMFA alarm"
        ::= { tdm-alarm8 7 }

tdmPort8AlarmLSMFA      	OBJECT-TYPE
    	SYNTAX              	Counter32
        MAX-ACCESS      	read-only
        STATUS          	current
        DESCRIPTION     	"Display TDM port8 LSMFA alarm"
        ::= { tdm-alarm8 8 }

trapStartUp             	NOTIFICATION-TYPE
        STATUS          	current
        DESCRIPTION     	"send traps when the system starts up"
        ::= { trangotrap 1 }

trapReboot              	NOTIFICATION-TYPE
        STATUS          	current
        DESCRIPTION     	"send traps when the system reboots"
        ::= { trangotrap 2 }

traprps         		OBJECT IDENTIFIER ::= { trangotrap 3 }

trapRPSPortUp   		NOTIFICATION-TYPE
        STATUS          	current
        DESCRIPTION     	"send traps when the rapid port up occurs"
        ::= { traprps 1 }

trapRPSPortDown   		NOTIFICATION-TYPE
        STATUS          	current
        DESCRIPTION     	"send traps when the rapid port down occurs"
        ::= { traprps 2 }

trapeth         		OBJECT IDENTIFIER ::= { trangotrap 4 }

trapEth1StatusUpdate    	NOTIFICATION-TYPE
        STATUS          	current
        DESCRIPTION     	"send traps when ethernet port 1 status changed"
        ::= { trapeth 1 }

trapEth2StatusUpdate    	NOTIFICATION-TYPE
        STATUS          	current
        DESCRIPTION     	"send traps when ethernet port 2 status changed"
        ::= { trapeth 2 }

trapEth3StatusUpdate    	NOTIFICATION-TYPE
        STATUS          	current
        DESCRIPTION     	"send traps when ethernet port 3 status changed"
        ::= { trapeth 3 }

trapEth4StatusUpdate    	NOTIFICATION-TYPE
        STATUS          	current
        DESCRIPTION     	"send traps when ethernet port 4 status changed"
        ::= { trapeth 4 }

trapLinkLock          		NOTIFICATION-TYPE
        STATUS          	current
        DESCRIPTION     	"send traps when the system lose modem lock"
        ::= { trangotrap 5 }

trap-threshold         		OBJECT IDENTIFIER ::= { trangotrap 6 }

trapIDUTempMin          	NOTIFICATION-TYPE
        STATUS          	current
        DESCRIPTION     	"send traps when the IDU temp below min"
        ::= { trap-threshold 1 }

trapIDUTempMax          	NOTIFICATION-TYPE
        STATUS          	current
        DESCRIPTION     	"send traps when the IDU temp above max"
        ::= { trap-threshold 2 }

trapODUTempMin          	NOTIFICATION-TYPE
        STATUS          	current
        DESCRIPTION     	"send traps when the ODU temp below min"
        ::= { trap-threshold 3 }

trapODUTempMax          	NOTIFICATION-TYPE
        STATUS          	current
        DESCRIPTION     	"send traps when the ODU temp above max"
        ::= { trap-threshold 4 }

trapMSEMin          		NOTIFICATION-TYPE
        STATUS          	current
        DESCRIPTION     	"send traps when the MSE below min"
        ::= { trap-threshold 5 }

trapMSEMax          		NOTIFICATION-TYPE
        STATUS          	current
        DESCRIPTION     	"send traps when the MSE above max"
        ::= { trap-threshold 6 }

trapBERMin          		NOTIFICATION-TYPE
        STATUS          	current
        DESCRIPTION     	"send traps when the BER below min"
        ::= { trap-threshold 7 }

trapBERMax          		NOTIFICATION-TYPE
        STATUS          	current
        DESCRIPTION     	"send traps when the BER above max"
        ::= { trap-threshold 8 }

trapFERMin          		NOTIFICATION-TYPE
        STATUS          	current
        DESCRIPTION     	"send traps when the FER below min"
        ::= { trap-threshold 9 }

trapFERMax          		NOTIFICATION-TYPE
        STATUS          	current
        DESCRIPTION     	"send traps when the FER above max"
        ::= { trap-threshold 10 }

trapRSSIMin          		NOTIFICATION-TYPE
        STATUS          	current
        DESCRIPTION     	"send traps when the RSSI below min"
        ::= { trap-threshold 11 }

trapRSSIMax          		NOTIFICATION-TYPE
        STATUS          	current
        DESCRIPTION     	"send traps when the RSSI above max"
        ::= { trap-threshold 12 }

trapInPortUtilMin         	NOTIFICATION-TYPE
        STATUS          	current
        DESCRIPTION     	"send traps when IN port utilization below min"
        ::= { trap-threshold 13 }

trapInPortUtilMax          		NOTIFICATION-TYPE
        STATUS          	current
        DESCRIPTION     	"send traps when IN port utilization above max"
        ::= { trap-threshold 14 }

trapOutPortUtilMin         	NOTIFICATION-TYPE
        STATUS          	current
        DESCRIPTION     	"send traps when OUT port utilization below min"
        ::= { trap-threshold 15 }

trapOutPortUtilMax          		NOTIFICATION-TYPE
        STATUS          	current
        DESCRIPTION     	"send traps when OUT port utilization above max"
        ::= { trap-threshold 16 }

trap-voltage         		OBJECT IDENTIFIER ::= { trangotrap 7 }

trapVoltage1-25Failure          NOTIFICATION-TYPE
        STATUS          	current
        DESCRIPTION     	"send traps when 1.25V power failed"
        ::= { trap-voltage 1 }

trapVoltage2-5Failure          NOTIFICATION-TYPE
        STATUS          	current
        DESCRIPTION     	"send traps when 2.5V power failed"
        ::= { trap-voltage 2 }

trapVoltage3-3Failure          NOTIFICATION-TYPE
        STATUS          	current
        DESCRIPTION     	"send traps when 3.3V power failed"
        ::= { trap-voltage 3 }


trapVoltage5Failure          NOTIFICATION-TYPE
        STATUS          	current
        DESCRIPTION     	"send traps when 5V power failed"
        ::= { trap-voltage 4 }

trap-tdm         		OBJECT IDENTIFIER ::= { trangotrap 8 }

trapTdm1StatusUpdate          NOTIFICATION-TYPE
        STATUS          	current
        DESCRIPTION     	"send traps when TDM1 status changed"
        ::= { trap-tdm 1 }

trapTdm2StatusUpdate          NOTIFICATION-TYPE
        STATUS          	current
        DESCRIPTION     	"send traps when TDM2 status changed"
        ::= { trap-tdm 2 }

trapTdm3StatusUpdate          NOTIFICATION-TYPE
        STATUS          	current
        DESCRIPTION     	"send traps when TDM3 status changed"
        ::= { trap-tdm 3 }

trapTdm4StatusUpdate          NOTIFICATION-TYPE
        STATUS          	current
        DESCRIPTION     	"send traps when TDM4 status changed"
        ::= { trap-tdm 4 }

trapTdm5StatusUpdate          NOTIFICATION-TYPE
        STATUS          	current
        DESCRIPTION     	"send traps when TDM5 status changed"
        ::= { trap-tdm 5 }

trapTdm6StatusUpdate          NOTIFICATION-TYPE
        STATUS          	current
        DESCRIPTION     	"send traps when TDM6 status changed"
        ::= { trap-tdm 6 }

trapTdm7StatusUpdate          NOTIFICATION-TYPE
        STATUS          	current
        DESCRIPTION     	"send traps when TDM7 status changed"
        ::= { trap-tdm 7 }

trapTdm8StatusUpdate          NOTIFICATION-TYPE
        STATUS          	current
        DESCRIPTION     	"send traps when TDM8 status changed"
        ::= { trap-tdm 8 }

trap-switchover         	OBJECT IDENTIFIER ::= { trangotrap 9 }

trapManaulSwitchover          NOTIFICATION-TYPE
        STATUS          	current
        DESCRIPTION     	"send traps when manual switchover occurs"
        ::= { trap-switchover 1 }

trapHWSwitchover          	NOTIFICATION-TYPE
        STATUS          	current
        DESCRIPTION     	"send traps when HW switchover occurs"
        ::= { trap-switchover 2 }

trap-cable         		OBJECT IDENTIFIER ::= { trangotrap 10 }

trapRedundancyCableRemoved      NOTIFICATION-TYPE
        STATUS          	current
        DESCRIPTION     	"send traps when redundancy cable removed"
        ::= { trap-cable 1 }

trapRedundancyCableRemoved      NOTIFICATION-TYPE
        STATUS          	current
        DESCRIPTION     	"send traps when redundancy cable re-connected"
        ::= { trap-cable 2 }

trapLostODUCommunication        NOTIFICATION-TYPE
        STATUS          	current
        DESCRIPTION     	"send traps when lost ODU communication"
        ::= { trangotrap 11 }

trap-utype         	OBJECT IDENTIFIER ::= { trangotrap 12 }

trapUtypeActiveElected        	NOTIFICATION-TYPE
        STATUS          	current
        DESCRIPTION     	"send traps when elected to be active unit"
        ::= { trap-utype 1 }

trapUtypeStandbyElected        	NOTIFICATION-TYPE
        STATUS          	current
        DESCRIPTION     	"send traps when elected to be standby unit"
        ::= { trap-utype 2 }

trapActiveDetected        	NOTIFICATION-TYPE
        STATUS          	current
        DESCRIPTION     	"send traps when detecting a active unit"
        ::= { trap-utype 3 }

trapStandbyDetected        	NOTIFICATION-TYPE
        STATUS          	current
        DESCRIPTION     	"send traps when detecting a standby unit"
        ::= { trap-utype 4 }

trapActiveDown        		NOTIFICATION-TYPE
        STATUS          	current
        DESCRIPTION     	"send traps when detecting active unit is down"
        ::= { trap-utype 5 }

trapStandbyDown        		NOTIFICATION-TYPE
        STATUS          	current
        DESCRIPTION     	"send traps when detecting standby unit is down"
        ::= { trap-utype 6 }

trapSynchronization        	NOTIFICATION-TYPE
        STATUS          	current
        DESCRIPTION     	"send traps when unit perform synchronization"
        ::= { trangotrap 13 }




END
