-- *****************************************************************
--
-- stn-pptpt.mib:  
--      Spring Tide Networks PPTP Trap MIB file.
--
--
--      Copyright (c) 1999, 2000 by Spring Tide Networks, Inc.
--                      ALL RIGHTS RESERVED       
--
-- *****************************************************************

-- MIB Object definitions for Spring Tide Network PPTP traps

STN-PPTP-TRAP-MIB DEFINITIONS ::= BEGIN

    IMPORTS
        MODULE-IDENTITY,
        OBJECT-TYPE,
        NOTIFICATION-TYPE, 
        IpAddress
                FROM SNMPv2-SMI

        DisplayString
                FROM SNMPv2-TC

        MODULE-COMPLIANCE, 
        OBJECT-GROUP
                FROM SNMPv2-CONF

        stnNotification
               FROM SPRING-TIDE-NETWORKS-SMI

        stnPptpTraps
               FROM STN-PPTP-MIB

        stnEngineIndex,
        stnEngineSlot,
        stnEngineCpu
                FROM STN-CHASSIS-MIB

        stnRouterIndex,
        stnSubnetInterfaceIndex
               FROM STN-ROUTER-MIB;


    stnPptpTrap       MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes the traps for 
                         Spring Tide Networks PPTP."
        ::= { stnPptpTraps 1 }


    --
    -- Top Level STN PPTP Trap MIB Objects
    --
    stnPptpTrapVars		OBJECT IDENTIFIER ::= { stnPptpTrap 1 }
    stnPptpNotificationPrefix   OBJECT IDENTIFIER ::= { stnPptpTrap 2 }
    stnPptpNotification		OBJECT IDENTIFIER ::= { stnPptpNotificationPrefix 0 }


    --
    -- STN PPTP trap support objects.
    --
    stnPptpTunnelLocalHostname OBJECT-TYPE
        SYNTAX          DisplayString
        MAX-ACCESS      read-only
        STATUS          current
        DESCRIPTION     "This object contains the host name supplied during 
                         the tunnel establishment phase to the PPTP peer."
        ::= { stnPptpTrapVars 1 }

    stnPptpTunnelLocalIpAddress OBJECT-TYPE
        SYNTAX          IpAddress
        MAX-ACCESS      read-only
        STATUS          current
        DESCRIPTION     "This object contains the local IP address of the 
                         tunnel endpoint."
        ::= { stnPptpTrapVars 2 }

    stnPptpTunnelRemoteHostname OBJECT-TYPE
        SYNTAX          DisplayString
        MAX-ACCESS      read-only
        STATUS          current
        DESCRIPTION     "This object contains the host name as discovered
                         during the tunnel establishment phase of the 
                         PPTP peer."
        ::= { stnPptpTrapVars 3 }

    stnPptpTunnelRemoteIpAddress OBJECT-TYPE
        SYNTAX          IpAddress
        MAX-ACCESS      read-only
        STATUS          current
        DESCRIPTION     "This object contains the IP address of the remote 
                         tunnel endpoint."
        ::= { stnPptpTrapVars 4 }


    --
    -- STN Traps & Notifications 
    --
    stnTunnelPptpAuthenFailure NOTIFICATION-TYPE
        OBJECTS         { stnRouterIndex,
                          stnSubnetInterfaceIndex,
                          stnPptpTunnelLocalHostname,
                          stnPptpTunnelRemoteHostname,
                          stnPptpTunnelRemoteIpAddress }
        STATUS          current
        DESCRIPTION     "A stnTunnelPptpAuthenFailure trap signifies that the
                        agent entity has detected an attempt to establish a 
                        tunnel to a remote peer has failed authentication.
                        The generation of this trap can be controlled by the
                        PPTPTraps configuration object."
           ::= { stnPptpNotification 1 }

    stnTunnelPptpLimitExceeded NOTIFICATION-TYPE
        OBJECTS         { stnEngineIndex, stnEngineSlot, stnEngineCpu }
        STATUS          current
        DESCRIPTION     "A stnTunnelPptpLimitExceeded trap signifies that the
                        agent entity has detected that the number of PPTP
                        tunnels allowed on the indicated slot/cpu has been 
                        exceeded. 
                        The generation of this trap can be controlled by the
                        PPTPTraps configuration object."
           ::= { stnPptpNotification 2 }

    stnTunnelPacProvLimitExceeded NOTIFICATION-TYPE
        OBJECTS         { stnRouterIndex,
                          stnSubnetInterfaceIndex,
                          stnPptpTunnelLocalHostname,
                          stnPptpTunnelLocalIpAddress }
        STATUS          current
        DESCRIPTION     "A stnTunnelPacProvLimitExceeded trap signifies that 
                        the agent entity has detected that the number of PPTP
                        locally initiated tunnels allowed by the provisioner
                        has been exceeded for the indicated router. 
                        The generation of this trap can be controlled by the
                        PPTPTraps configuration object."
           ::= { stnPptpNotification 3 }

    stnTunnelPnsProvLimitExceeded NOTIFICATION-TYPE
        OBJECTS         { stnRouterIndex,
                          stnSubnetInterfaceIndex,
                          stnPptpTunnelLocalHostname,
                          stnPptpTunnelLocalIpAddress }
        STATUS          current
        DESCRIPTION     "A stnTunnelPnsProvLimitExceeded trap signifies that 
                        the agent entity has detected that the number of PPTP
                        remotely initiated tunnels allowed by the provisioner
                        has been exceeded for the indicated router. 
                        The generation of this trap can be controlled by the
                        PPTPTraps configuration object."
           ::= { stnPptpNotification 4 }

    stnCallPptpLimitExceeded NOTIFICATION-TYPE
        OBJECTS         { stnEngineIndex, stnEngineSlot, stnEngineCpu }
        STATUS          current
        DESCRIPTION     "A stnCallPptpLimitExceeded trap signifies that the
                        agent entity has detected that the number of PPTP
                        calls allowed on the indicated slot/cpu has been 
                        exceeded. 
                        The generation of this trap can be controlled by the
                        PPTPTraps configuration object."
           ::= { stnPptpNotification 5 }

    stnCallPacProvLimitExceeded NOTIFICATION-TYPE
        OBJECTS         { stnRouterIndex,
                          stnSubnetInterfaceIndex,
                          stnPptpTunnelLocalHostname,
                          stnPptpTunnelRemoteHostname,
                          stnPptpTunnelRemoteIpAddress }
        STATUS          current
        DESCRIPTION     "A stnCallPacProvLimitExceeded trap signifies that 
                        the agent entity has detected that the number of PPTP
                        locally initiated calls allowed by the provisioner
                        has been exceeded for the indicated router. 
                        The generation of this trap can be controlled by the
                        PPTPTraps configuration object."
           ::= { stnPptpNotification 6 }

    stnCallPnsProvLimitExceeded NOTIFICATION-TYPE
        OBJECTS         { stnRouterIndex,
                          stnSubnetInterfaceIndex,
                          stnPptpTunnelLocalHostname,
                          stnPptpTunnelRemoteHostname,
                          stnPptpTunnelRemoteIpAddress }
        STATUS          current
        DESCRIPTION     "A stnCallPnsProvLimitExceeded trap signifies that 
                        the agent entity has detected that the number of PPTP
                        remotely initiated calls allowed by the provisioner
                        has been exceeded for the indicated router. 
                        The generation of this trap can be controlled by the
                        PPTPTraps configuration object."
           ::= { stnPptpNotification 7 }


END
