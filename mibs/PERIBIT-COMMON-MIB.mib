PERIBIT-COMMON-MIB DEFINITIONS ::= BEGIN

	IMPORTS
		MODULE-IDENTITY, OBJECT-IDENTITY,
		OBJECT-TYPE, NOTIFICATION-TYPE,
		Integer32
			FROM SNMPv2-SMI
--		MODULE-COMPLIANCE, OBJECT-GROUP
--			FROM SNMPv2-CONF
		DisplayString, TruthValue
			FROM SNMPv2-TC
		TcChassisType
			FROM PERIBIT-GLOBAL-TC
		pnModules, pnCommonMib
			FROM PERIBIT-GLOBAL-REG;

	pnCommonMibModule MODULE-IDENTITY
		LAST-UPDATED			"200206030000Z"
		ORGANIZATION			"Peribit Networks, Inc"
		CONTACT-INFO			"
					Customer Support
					Peribit Networks, Inc.
					2300 Central Expressway
					Santa Clara, CA 95050

					+1 866-PERIBIT
					support@peribit.com"

		DESCRIPTION				"
			A MIB module containing definitions of managed objects
			implemented by all Peribit Networks' products."

		REVISION				"200309300845Z"
		DESCRIPTION				"
			Fix minor error in description of pnSysDaylightSaving."
 
		REVISION				"200304010000Z"
		DESCRIPTION				"
			Add interface duplex mismatch notification."

		REVISION				"200303100000Z"
		DESCRIPTION				"
			Add interface speed mismatch notifications."

		REVISION				"200206030000Z"
		DESCRIPTION				"
			Add Fan notifications."

		REVISION				"200203270000Z"
		DESCRIPTION				"
			Add FaultTolerantPassthrough notification."

		REVISION				"200202220000Z"
		DESCRIPTION				"
			Add LoginFailure notification."

		REVISION				"200201230000Z"
		DESCRIPTION				"
			Add LicenseWillExpire notification."

		REVISION				"200201170000Z"
		DESCRIPTION				"
			Add ThruputLimitExceeded notification."

		REVISION				"200108070000Z"
		DESCRIPTION				"
			Rev 1.0
			Initial version of MIB module PERIBIT-COMMON-MIB."

		::= { pnModules 3 }

	pnCommonConfMib OBJECT-IDENTITY
		STATUS					current
		DESCRIPTION				"
			Sub-tree for Sequence Reducer MIB conformance statements."
		::= { pnCommonMib 1 }

	pnCommonObjs OBJECT-IDENTITY
		STATUS					current
		DESCRIPTION				"
			Sub-tree for common MIB objects."
		::= { pnCommonMib 2 }

	pnCommonEvents OBJECT-IDENTITY
		STATUS					current
		DESCRIPTION				"
			Sub-tree for common MIB events."
		::= { pnCommonMib 3 }

	-- Top level groups

	pnSys OBJECT-IDENTITY
		STATUS					current
		DESCRIPTION				"
			Sub-tree for common system objects."
		::= { pnCommonObjs 1 }

	pnChassis OBJECT-IDENTITY
		STATUS					current
		DESCRIPTION				"
			Sub-tree for common chassis information."
		::= { pnCommonObjs 2 }

	----------------------------------------------------------------------
	-- System objects

	pnSysSwVersion OBJECT-TYPE
		SYNTAX      DisplayString (SIZE(0..32))
		MAX-ACCESS  read-only
		STATUS      current
		DESCRIPTION
			"Full software version. The first two components of the full
			version are the major and minor versions. The third component
			indicates the maintenance release number and the fourth,
			the build number."
		::= { pnSys 1 }

	pnSysHwVersion OBJECT-TYPE
		SYNTAX      DisplayString (SIZE(0..32))
		MAX-ACCESS  read-only
		STATUS      current
		DESCRIPTION
			"Hardware version of the unit."
		::= { pnSys 2 }

	pnSysSerialNumber OBJECT-TYPE
		SYNTAX      DisplayString (SIZE(0..128))
		MAX-ACCESS  read-only
		STATUS      current
		DESCRIPTION
			"The serial number of the unit. If not available,
			an empty string is returned."
		::= { pnSys 3 }

	pnSysTimeZoneOffset OBJECT-TYPE
		SYNTAX      Integer32
		MAX-ACCESS  read-only
		STATUS      current
		DESCRIPTION
			"The offset in seconds from UTC of the system's time zone.
			Values are negative for locations west of UTC and positive
			for locations east of UTC."
		::= { pnSys 4 }

	pnSysDaylightSaving OBJECT-TYPE
		SYNTAX      TruthValue
		MAX-ACCESS  read-only
		STATUS      current
		DESCRIPTION
			"Whether daylight savings are currently in effect for the
			system's time zone."
		::= { pnSys 5 }

	----------------------------------------------------------------------
	-- Chassis

	pnChassisType OBJECT-TYPE
		SYNTAX      TcChassisType
		MAX-ACCESS  read-only
		STATUS      current
		DESCRIPTION
			"Chassis type for this Peribit device."
		::= { pnChassis 1 }

	----------------------------------------------------------------------
	-- Events

	pnCommonEventObjs OBJECT-IDENTITY
		STATUS					current
		DESCRIPTION				"
			Branch for objects meant only to be sent in event varbinds."
		::= { pnCommonEvents 1 }

	pnCommonEventEvents OBJECT-IDENTITY
		STATUS					current
		DESCRIPTION				"
			Branch for the events themselves."
		::= { pnCommonEvents 2 }

	pnCommonEventEventsV2 OBJECT-IDENTITY
		STATUS					current
		DESCRIPTION				"
			Branch for SNMPv2 events. The OIDs for SNMPv2 events should
			have a zero as the next-to-last sub-identifier (as specified
			in RFC1902)."
		::= { pnCommonEventEvents 0 }

	-- Objects sent only in events

	pnCommonEventDescr OBJECT-TYPE
		SYNTAX					DisplayString
		MAX-ACCESS				accessible-for-notify
		STATUS					current
		DESCRIPTION
			"String that provides a textual description of the event."
		::= { pnCommonEventObjs 1 }

	-- Event descriptions

	pnCommonEventInFailSafeMode NOTIFICATION-TYPE
		STATUS  current
		DESCRIPTION
			"This trap is sent when the device boots up in fail-safe mode.
			This can happen for one of the following reasons:
			o Fail-safe reboot was explicitly initiated by the user.
			o The device rebooted automatically too many times because of
			  the failure of internal consistency checks or the failure of
			  tests that verify proper operation of the device."
		::= { pnCommonEventEventsV2 1 }

	pnCommonEventPowerSupplyFailure NOTIFICATION-TYPE
		STATUS  current
		DESCRIPTION
			"One or more sources of power to the system has failed.
			A redundant power-supply has presumably taken over.

			NOTE: This trap is for future use.
			      Peribit devices currently do not generate this trap."
		::= { pnCommonEventEventsV2 2 }

	pnCommonEventPowerSupplyOk NOTIFICATION-TYPE
		STATUS  current
		DESCRIPTION
			"One or more previously failed sources of power is now
			working normally. The transition to normal condition happened
			without the system having to be restarted.

			NOTE: This trap is for future use.
			      Peribit devices currently do not generate this trap."
		::= { pnCommonEventEventsV2 3 }

	pnCommonEventLicenseExpired NOTIFICATION-TYPE
		OBJECTS { pnCommonEventDescr }
		STATUS  current
		DESCRIPTION
			"The license for the system expired.
			As a result, the system will switch over to
			and stay in pass-through mode."
		::= { pnCommonEventEventsV2 4 }

	pnCommonEventThruputLimitExceeded NOTIFICATION-TYPE
		OBJECTS { pnCommonEventDescr }
		STATUS  current
		DESCRIPTION
			"The throughput of traffic through the device
			has exceeded the limit for which it has
			been licensed."
		::= { pnCommonEventEventsV2 5 }

	pnCommonEventLicenseWillExpire NOTIFICATION-TYPE
		OBJECTS { pnCommonEventDescr }
		STATUS  current
		DESCRIPTION
			"The license for the system is about to
			expire shortly. When it eventually does
			expire, the system will switch over to
			and stay in pass-through mode."
		::= { pnCommonEventEventsV2 6 }

	pnCommonEventLoginFailure NOTIFICATION-TYPE
		OBJECTS { pnCommonEventDescr }
		STATUS  current
		DESCRIPTION
			"A user's login attempt via the console/ssh/web server
			failed due to incorrect username or password."
		::= { pnCommonEventEventsV2 7 }

	pnCommonEventFaultTolerantPassThrough NOTIFICATION-TYPE
		OBJECTS { pnCommonEventDescr }
		STATUS  current
		DESCRIPTION
			"An anomalous health condition was detected.
			It would have subsequently triggered hardware
			pass through mode followed by a reboot."
		::= { pnCommonEventEventsV2 8 }

	pnCommonEventFanFailure NOTIFICATION-TYPE
		OBJECTS { pnCommonEventDescr }
		STATUS  current
		DESCRIPTION
			"A cooling fan inside the device has failed.
			The 'pnCommonEventDescr' object has the name of
			the fan that failed."
		::= { pnCommonEventEventsV2 9 }

	pnCommonEventFanSpeedVariation NOTIFICATION-TYPE
		OBJECTS { pnCommonEventDescr }
		STATUS  current
		DESCRIPTION
			"The speed of a cooling fan inside the device is either
			too low or too high. The 'pnCommonEventDescr' object
			has the name of the fan that has the problem."
		::= { pnCommonEventEventsV2 10 }

	pnCommonEventFanOk NOTIFICATION-TYPE
		OBJECTS { pnCommonEventDescr }
		STATUS  current
		DESCRIPTION
			"A cooling fan inside the device that had previously
			failed or whose speed variation was high is now
			working properly. The 'pnCommonEventDescr' object
			has the name of the fan that has recovered."
		::= { pnCommonEventEventsV2 11 }

	pnCommonEventInterfaceSpeedMismatch NOTIFICATION-TYPE
		OBJECTS { pnCommonEventDescr }
		STATUS  current
		DESCRIPTION
			"A mismatch is detected between the local and remote 
			interface settings. This can happen due to a mismatch
			in the local and remote interface speed or mode. "
		::= { pnCommonEventEventsV2 12 }

	pnCommonEventInterfaceSpeedOk NOTIFICATION-TYPE
		OBJECTS { pnCommonEventDescr }
		STATUS  current
		DESCRIPTION
			"A mismatch previously detected between the local and remote 
			interface settings is now resolved. The local and remote interface
			speed and mode are matched. "
		::= { pnCommonEventEventsV2 13 }

	pnCommonEventInterfaceDuplexMismatch NOTIFICATION-TYPE
		OBJECTS { pnCommonEventDescr }
		STATUS  current
		DESCRIPTION
			"A possible mismatch was detected between the duplex setting
			of either the local or remote interface and that of the
			device attached to that interface. The interface (local
			or remote) is identified by the 'pnCommonEventDescr' object.

			Note that this notification is quite different from
			pnCommonEventInterfaceSpeedMismatch, which compares the
			local and remote interfaces on the same Peribit device."
		::= { pnCommonEventEventsV2 14 }

    pnCommonEventIpsecSecurityAssociationAdded NOTIFICATION-TYPE
        OBJECTS { pnCommonEventDescr }
        STATUS  current
        DESCRIPTION
            "An IPSec security association has been negotiated and added
            to security association database."
        ::= { pnCommonEventEventsV2 15 }

    pnCommonEventIpsecSecurityAssociationExpired NOTIFICATION-TYPE
        OBJECTS { pnCommonEventDescr }
        STATUS  current
        DESCRIPTION
            "An IPSec security association has been deleted from the
            security association database."
        ::= { pnCommonEventEventsV2 16 }

    pnCommonEventIpsecSecurityAssociationDeleted NOTIFICATION-TYPE
        OBJECTS { pnCommonEventDescr }
        STATUS  current
        DESCRIPTION
            "An IPSec security association has been deleted from the
            security association database."
        ::= { pnCommonEventEventsV2 17 }
END

-- End - PERIBIT-COMMON-MIB Module

-- ========================================================================
-- Start - PERIBIT-SR-MIB Module

-- Peribit MIB for the Sequence Reducer
--
-- The convention described in "Understanding SNMP MIBs"
-- (David Perkins, Evan McGinnis), Chapter 8, has generally been followed.
