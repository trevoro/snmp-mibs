-- Copyright 1995 by 3Com Corporation.  All rights reserved.
-- MIB file name:  lanplex-opt-fddi-mib
-- available in these 3Com devices:  Lanplex hubs
-- For support or more info, check 3Com's web page at http://www.3com.com

		-- Lanplex Optional FDDI MIB for SMT 7
		-- Version 1.1.2
		-- Apr 27, 1994

		-- 3Com Corporation
		-- 85 Rangeway Road
		-- North Billerica, MA 01862
		-- (508) 670-9009

		-- Change History:
		--     4/27/94  eah  Added fddimibSMTCFState and fddimibSMTPeerWrapFlag
		--                   to the lpOptSMTPeerWrapCondition
		--                   Changed upstream duplicate address object from
		--                   fddimibMACSMTAddress to fddimibMACUpstreamNbr, and
		--                   added fddimibMACDaFlag and fddimibMACUnaDaFlag to
		--                   the lpOptMACDuplicateAddressCondition
		--                   Added fddimibMACNotCopiedFlag to the 
		--                   lpOptMACNotCopiedCondition
		--                   Added fddimibPORTLerFlag to the lpOptPORTLerCondition
		--     4/11/94  eah  Changed IMPORTS so that lanplex is imported from
		--                   LANPLEX-MIB-1-2-9
		--     6/15/93  eah  Changed IMPORTS and traps to use new Version 3.2
		--                   of draft fddi mib
		--     6/11/93  eah  Corrected path so that lanplexOptFddi is under
		--                   lanplex 10, not synernetics 10


		LANPLEX-OPT-FDDI-MIB-1-1-2 DEFINITIONS ::= BEGIN

		IMPORTS
			enterprises, Counter					FROM RFC1155-SMI
			OBJECT-TYPE				FROM RFC-1212
			TRAP-TYPE				FROM RFC-1215
			FddiTimeNano,
			FddiSMTStationIdType,
			fddimibSMTStationId,
			fddimibSMTCFState,
			fddimibSMTPeerWrapFlag,
			fddimibMACSMTAddress,
			fddimibMACDaFlag,
			fddimibMACUnaDaFlag,
			fddimibMACFrameErrorFlag,
			fddimibMACFrameCts,
			fddimibMACErrorCts,
			fddimibMACLostCts,
			fddimibMACFrameErrorRatio,
			fddimibMACNotCopiedCts,
			fddimibMACCopiedCts,
			fddimibMACNotCopiedRatio,
			fddimibMACNotCopiedFlag,
			fddimibMACUpstreamNbr,
			fddimibMACOldUpstreamNbr,
			fddimibMACDownstreamNbr,
			fddimibMACOldDownstreamNbr,
			fddimibMACCurrentPath,
			fddimibMACAvailablePaths,
			fddimibMACRequestedPaths,
			fddimibPORTLerCutoff,
			fddimibPORTLerAlarm,
			fddimibPORTLerEstimate,
			fddimibPORTLemRejectCts,
			fddimibPORTLemCts,
			fddimibPORTLerFlag,
			fddimibPORTMyType,
			fddimibPORTConnectState,
			fddimibPORTNeighborType,
			fddimibPORTPCWithhold,
			fddimibPORTAvailablePaths,
			fddimibPORTCurrentPath,
			fddimibPORTRequestedPaths	FROM DRAFT-FDDI-MIB-VER-3-2;

		synernetics		OBJECT IDENTIFIER ::= { enterprises 114 }
		lanplex			OBJECT IDENTIFIER ::= { synernetics 1 }
		lanplexOptFddi	OBJECT IDENTIFIER ::= { lanplex 10 }

		-- groups

		lpOptSMT		OBJECT IDENTIFIER ::= { lanplexOptFddi 1 }
		lpOptMAC		OBJECT IDENTIFIER ::= { lanplexOptFddi 2 }
		lpOptPATH		OBJECT IDENTIFIER ::= { lanplexOptFddi 3 }
		lpOptPORT		OBJECT IDENTIFIER ::= { lanplexOptFddi 4 }

		-- the lpOptSMT group

		-- the lpOptSMTTable

		lpOptSMTTable OBJECT-TYPE
			SYNTAX  SEQUENCE OF LpOptSMTEntry
			ACCESS  not-accessible
			STATUS  mandatory
			DESCRIPTION
					"A list of optional SMT entries.  The number of entries
					shall not exceed the value of snmpFddiSMTNumber."
			::= { lpOptSMT 1 }

		lpOptSMTEntry OBJECT-TYPE
			SYNTAX  LpOptSMTEntry
			ACCESS  not-accessible
			STATUS  mandatory
			DESCRIPTION
					"An optional SMT entry containing information common to
					a given optional SMT."
			INDEX   { lpOptSMTIndex }
			::= { lpOptSMTTable 1 }

		LpOptSMTEntry ::=
			SEQUENCE {
				lpOptSMTIndex
					INTEGER,
				lpOptSMTManufacturerOUI
					OCTET STRING,
				lpOptSMTManufacturerData
					OCTET STRING,
				lpOptSMTHoldState
					INTEGER,
				lpOptSMTSetCount
					INTEGER,
				lpOptSMTLastSetStationId
					FddiSMTStationIdType
			}

		lpOptSMTIndex OBJECT-TYPE
			SYNTAX	INTEGER (1..65535)
			ACCESS	read-only
			STATUS	mandatory
			DESCRIPTION
					"A unique value for each SMT.  Its value ranges
					between 1 and the value of snmpFddiSMTNumber.  The
					value for each SMT must remain constant at least
					from one re-initialization of the entity's network
					management system to the next re-initialization."
			::= { lpOptSMTEntry 1 }

		lpOptSMTManufacturerOUI OBJECT-TYPE
			SYNTAX  OCTET STRING (SIZE (3))
			ACCESS  read-only
			STATUS  mandatory
			DESCRIPTION
					"The three octets of manufacturer data which make
					up the manufacturerOUI component."
			REFERENCE
					"ANSI { fddiSMT 16 }"
			::= { lpOptSMTEntry 2 }

		lpOptSMTManufacturerData OBJECT-TYPE
			SYNTAX  OCTET STRING (SIZE (29))
			ACCESS  read-only
			STATUS  mandatory
			DESCRIPTION
					"The 29 octets of manufacturer data which make up the
					manufacturerData component."
			REFERENCE
					"ANSI { fddiSMT 16 }"
			::= { lpOptSMTEntry 3 }

		lpOptSMTHoldState OBJECT-TYPE
			SYNTAX	INTEGER {
						not-implemented(1),		-- holding not implemented
						not-holding(2),
						holding-prm(3),			-- holding on primary
						holding-sec(4)			-- holding on secondary
					}
			ACCESS	read-only
			STATUS	mandatory
			DESCRIPTION
					"This variable indicates the current state of the
					Hold function. The value 'not-holding' is the
					default and initial value.  The value must be set
					to 'not-holding' as part of Active_Actions and
					when the conditions causing 'holding-prm' or
					'holding-sec' are no longer true. The value
					'holding-prm' must be set when the condition
					(notTR_Flag & not RE_Flag & (PC_LS=QLS | LEM_Fail
					| TNE>NS_Max | (not LS_Flag & TPC > T_Out))) is
					satisfied in state PC8:ACTIVE for the A Port. The
					value 'holding-sec' must be set when the condition
					(notTR_Flag & not RE_Flag & (PC_LS=QLS | LEM_Fail
					| TNE>NS_Max | (not LS_Flag & TPC > T_Out))) is
					satisfied in state PC8:ACTIVE for the B Port."
			REFERENCE
					"ANSI { fddiSMT 43 }"
			::= { lpOptSMTEntry 4 }

		lpOptSMTSetCount OBJECT-TYPE
			SYNTAX	INTEGER
			ACCESS	read-only
			STATUS	mandatory
			DESCRIPTION
					"This variable is composed of a count incremented
					in response to a Set operation on the MIB, and the
					time of the change, however only the count is
					reported here (refer to ANSI SMT 8.4.1)."
			REFERENCE
					"ANSI { fddiSMT 53 }"
			::= { lpOptSMTEntry 5 }

		lpOptSMTLastSetStationId OBJECT-TYPE
			SYNTAX	FddiSMTStationIdType
			ACCESS	read-only
			STATUS	mandatory
			DESCRIPTION
					"The Station ID of the station that effected the last
					change in the FDDI MIB."
			REFERENCE
					"ANSI { fddiSMT 54 }"
			::= { lpOptSMTEntry 6 }

		-- the lpOptMAC group

		-- the lpOptMACBridgeFunctionTable

		lpOptMACBridgeFunctionTable OBJECT-TYPE
			SYNTAX  SEQUENCE OF LpOptMACBridgeFunctionEntry
			ACCESS  not-accessible
			STATUS  mandatory
			DESCRIPTION
					"A list of MAC bridge function entries."
			::= { lpOptMAC 1 }

		lpOptMACBridgeFunctionEntry OBJECT-TYPE
			SYNTAX  LpOptMACBridgeFunctionEntry
			ACCESS  not-accessible
			STATUS  mandatory
			DESCRIPTION
					"Bridge function information for a given MAC 
					within a given SMT."
			INDEX	{ lpOptMACBridgeFunctionSMTIndex, 
					lpOptMACBridgeFunctionMACIndex }
			::= { lpOptMACBridgeFunctionTable 1 }

		LpOptMACBridgeFunctionEntry ::=
			SEQUENCE {
				lpOptMACBridgeFunctionSMTIndex
					INTEGER,
				lpOptMACBridgeFunctionMACIndex
					INTEGER,
				lpOptMACBridgeFunctions
					INTEGER
			}

		lpOptMACBridgeFunctionSMTIndex OBJECT-TYPE
			SYNTAX	INTEGER (1..65535)
			ACCESS	read-only
			STATUS	mandatory
			DESCRIPTION
					"A unique value for each SMT.  Its value ranges
					between 1 and the value of snmpFddiSMTNumber.  The
					value for each SMT must remain constant at least
					from one re-initialization of the entity's network
					management system to the next re-initialization."
			::= { lpOptMACBridgeFunctionEntry 1 }

		lpOptMACBridgeFunctionMACIndex OBJECT-TYPE
			SYNTAX  INTEGER (1..65535)
			ACCESS  read-only
			STATUS  mandatory
			DESCRIPTION
					"Index variable for uniquely identifying the MAC
					object instances."
			REFERENCE
					"ANSI { fddiMAC 34 }"
			::= { lpOptMACBridgeFunctionEntry 2 }

		lpOptMACBridgeFunctions OBJECT-TYPE
			SYNTAX	INTEGER (-1..7)
			ACCESS	read-only
			STATUS	mandatory
			DESCRIPTION
					"Indicates the MAC's optional bridging functions.

					The Value -1 is used to indicate that bridging is
					not supported by this MAC.

					The value is a sum.  This value initially takes
					the value zero, then for each function present, 2
					raised to a power is added to the sum.  The powers
					are according to the following table:

					Function	Power
						tb		0 -- Transparent bridging active
						sr		1 -- Src routing active
						srt		2 -- Src routing transparent active
					"
			REFERENCE
					"ANSI { fddiMAC 12 }"
			::= { lpOptMACBridgeFunctionEntry 3 }

		-- the lpOptMACTPriTable

		lpOptMACTPriTable OBJECT-TYPE
			SYNTAX  SEQUENCE OF LpOptMACTPriEntry
			ACCESS  not-accessible
			STATUS  mandatory
			DESCRIPTION
					"A list of MAC T-Pri entries."
			::= { lpOptMAC 2 }

		lpOptMACTPriEntry OBJECT-TYPE
			SYNTAX  LpOptMACTPriEntry
			ACCESS  not-accessible
			STATUS  mandatory
			DESCRIPTION
					"A collection of T-Pri information for a given MAC within
					a given SMT."
			INDEX	{ lpOptMACTPriSMTIndex, lpOptMACTPriMACIndex }
			::= { lpOptMACTPriTable 1 }

		LpOptMACTPriEntry ::=
			SEQUENCE {
				lpOptMACTPriSMTIndex
					INTEGER,
				lpOptMACTPriMACIndex
					INTEGER,
				lpOptMACTPri0
					FddiTimeNano,
				lpOptMACTPri1
					FddiTimeNano,
				lpOptMACTPri2
					FddiTimeNano,
				lpOptMACTPri3
					FddiTimeNano,
				lpOptMACTPri4
					FddiTimeNano,
				lpOptMACTPri5
					FddiTimeNano,
				lpOptMACTPri6
					FddiTimeNano
			}

		lpOptMACTPriSMTIndex OBJECT-TYPE
			SYNTAX	INTEGER (1..65535)
			ACCESS	read-only
			STATUS	mandatory
			DESCRIPTION
					"A unique value for each SMT.  Its value ranges
					between 1 and the value of snmpFddiSMTNumber.  The
					value for each SMT must remain constant at least
					from one re-initialization of the entity's network
					management system to the next re-initialization."
			::= { lpOptMACTPriEntry 1 }

		lpOptMACTPriMACIndex OBJECT-TYPE
			SYNTAX  INTEGER (1..65535)
			ACCESS  read-only
			STATUS  mandatory
			DESCRIPTION
					"Index variable for uniquely identifying the MAC
					object instances."
			REFERENCE
					"ANSI { fddiMAC 34 }"
			::= { lpOptMACTPriEntry 2 }

		lpOptMACTPri0 OBJECT-TYPE
			SYNTAX  FddiTimeNano
			ACCESS	read-only
			STATUS  mandatory
			DESCRIPTION
					"This attribute is an unsigned twos-complement T_pri
					threshold as described in the MAC standard converted
					to non-twos-complement form and reported in 1 ns units."
			REFERENCE
					"ANSI { fddiMAC 56 }"
			::= { lpOptMACTPriEntry 3 }

		lpOptMACTPri1 OBJECT-TYPE
			SYNTAX  FddiTimeNano
			ACCESS	read-only
			STATUS  mandatory
			DESCRIPTION
					"This attribute is an unsigned twos-complement T_pri
					threshold as described in the MAC standard converted
					to non-twos-complement form and reported in 1 ns units."
			REFERENCE
					"ANSI { fddiMAC 57 }"
			::= { lpOptMACTPriEntry 4 }

		lpOptMACTPri2 OBJECT-TYPE
			SYNTAX  FddiTimeNano
			ACCESS	read-only
			STATUS  mandatory
			DESCRIPTION
					"This attribute is an unsigned twos-complement T_pri
					threshold as described in the MAC standard converted
					to non-twos-complement form and reported in 1 ns units."
			REFERENCE
					"ANSI { fddiMAC 58 }"
			::= { lpOptMACTPriEntry 5 }

		lpOptMACTPri3 OBJECT-TYPE
			SYNTAX  FddiTimeNano
			ACCESS	read-only
			STATUS  mandatory
			DESCRIPTION
					"This attribute is an unsigned twos-complement T_pri
					threshold as described in the MAC standard converted
					to non-twos-complement form and reported in 1 ns units."
			REFERENCE
					"ANSI { fddiMAC 59 }"
			::= { lpOptMACTPriEntry 6 }

		lpOptMACTPri4 OBJECT-TYPE
			SYNTAX  FddiTimeNano
			ACCESS	read-only
			STATUS  mandatory
			DESCRIPTION
					"This attribute is an unsigned twos-complement T_pri
					threshold as described in the MAC standard converted
					to non-twos-complement form and reported in 1 ns units."
			REFERENCE
					"ANSI { fddiMAC 60 }"
			::= { lpOptMACTPriEntry 7 }

		lpOptMACTPri5 OBJECT-TYPE
			SYNTAX  FddiTimeNano
			ACCESS	read-only
			STATUS  mandatory
			DESCRIPTION
					"This attribute is an unsigned twos-complement T_pri
					threshold as described in the MAC standard converted
					to non-twos-complement form and reported in 1 ns units."
			REFERENCE
					"ANSI { fddiMAC 61 }"
			::= { lpOptMACTPriEntry 8 }

		lpOptMACTPri6 OBJECT-TYPE
			SYNTAX  FddiTimeNano
			ACCESS	read-only
			STATUS  mandatory
			DESCRIPTION
					"This attribute is an unsigned twos-complement T_pri
					threshold as described in the MAC standard converted
					to non-twos-complement form and reported in 1 ns units."
			REFERENCE
					"ANSI { fddiMAC 62 }"
			::= { lpOptMACTPriEntry 9 }

		-- the lpOptPATH group

		-- the lpOptPATHRingTable

		lpOptPATHRingTable OBJECT-TYPE
			SYNTAX  SEQUENCE OF LpOptPATHRingEntry
			ACCESS  not-accessible
			STATUS  mandatory
			DESCRIPTION
					"A list of PATH ring entries."
			::= { lpOptPATH 1 }

		lpOptPATHRingEntry OBJECT-TYPE
			SYNTAX  LpOptPATHRingEntry
			ACCESS  not-accessible
			STATUS  mandatory
			DESCRIPTION
					"Ring latency, trace status, and T-Rmode information for a
					given PATH within a given SMT."
			INDEX   { lpOptPATHRingSMTIndex, lpOptPATHRingPATHIndex }
			::= { lpOptPATHRingTable 1 }

		LpOptPATHRingEntry ::=
			SEQUENCE {
				lpOptPATHRingSMTIndex
					INTEGER,
				lpOptPATHRingPATHIndex
					INTEGER,
				lpOptPATHRingLatency
					FddiTimeNano,
				lpOptPATHTraceStatus
					INTEGER,
				lpOptPATHT-Rmode
					FddiTimeNano
			}

		lpOptPATHRingSMTIndex OBJECT-TYPE
			SYNTAX	INTEGER (1..65535)
			ACCESS	read-only
			STATUS	mandatory
			DESCRIPTION
					"A unique value for each SMT.  Its value ranges
					between 1 and the value of snmpFddiSMTNumber.  The
					value for each SMT must remain constant at least
					from one re-initialization of the entity's network
					management system to the next re-initialization."
			::= { lpOptPATHRingEntry 1 }

		lpOptPATHRingPATHIndex OBJECT-TYPE
			SYNTAX  INTEGER (1..255)
			ACCESS  read-only
			STATUS  mandatory
			DESCRIPTION
					"Index variable for uniquely identifying the
					primary, secondary and local PATH object
					instances. Local PATH object instances are
					represented with integer values 3 to 255."
			REFERENCE
					"ANSI { fddiPATH 11 }"
			::= { lpOptPATHRingEntry 2 }

		lpOptPATHRingLatency OBJECT-TYPE
			SYNTAX  FddiTimeNano
			ACCESS  read-write
			STATUS  mandatory
			DESCRIPTION
					"Gives the total accumulated latency of the ring 
					associated with this path.  May be measured directly
					by the station or calculated by a management station.
					Values of this object are reported in 1 ns units."
			REFERENCE
					"ANSI { fddiPATH 13 }"
			::= { lpOptPATHRingEntry 3 }

		lpOptPATHTraceStatus OBJECT-TYPE
			SYNTAX  INTEGER (0..15)
			ACCESS  read-only
			STATUS  mandatory
			DESCRIPTION
					"This attribute indicates the current trace status of
					the path.

					The value is a sum which represents all of the trace
					status information which applies.  This value initially
					takes the value zero, then for each condition which
					applies, 2 raised to a power is added to the sum.  the
					powers are according to the following table:

					TraceStatus	   Power
				  traceinitiated	0
				tracepropragated	1
				 traceterminated	2
					tracetimeout	3"

			REFERENCE
					"ANSI { fddiPATH 14 }"
			::= { lpOptPATHRingEntry 4 }

		lpOptPATHT-Rmode OBJECT-TYPE
			SYNTAX  FddiTimeNano
			ACCESS  read-write
			STATUS  mandatory
			DESCRIPTION
					"Used by RMT to limit the duration of restricted dialogs
					on a path.  This object is reported in 1 ns units."
			REFERENCE
					"ANSI { fddiPATH 19 }"
			::= { lpOptPATHRingEntry 5 }

		-- the lpOptPATHSbaTable

		lpOptPATHSbaTable OBJECT-TYPE
			SYNTAX  SEQUENCE OF LpOptPATHSbaEntry
			ACCESS  not-accessible
			STATUS  mandatory
			DESCRIPTION
					"A list of PATH Sba entries."
			::= { lpOptPATH 2 }

		lpOptPATHSbaEntry OBJECT-TYPE
			SYNTAX  LpOptPATHSbaEntry
			ACCESS  not-accessible
			STATUS  mandatory
			DESCRIPTION
					"Sba information for a given PATH within a given SMT."
			INDEX   { lpOptPATHSbaSMTIndex, lpOptPATHSbaPATHIndex }
			::= { lpOptPATHSbaTable 1 }

		LpOptPATHSbaEntry ::=
			SEQUENCE {
				lpOptPATHSbaSMTIndex
					INTEGER,
				lpOptPATHSbaPATHIndex
					INTEGER,
				lpOptPATHSbaPayload
					INTEGER,
				lpOptPATHSbaOverhead
					INTEGER,
				lpOptPATHSbaAvailable
					INTEGER
			}

		lpOptPATHSbaSMTIndex OBJECT-TYPE
			SYNTAX	INTEGER (1..65535)
			ACCESS	read-only
			STATUS	mandatory
			DESCRIPTION
					"A unique value for each SMT.  Its value ranges
					between 1 and the value of snmpFddiSMTNumber.  The
					value for each SMT must remain constant at least
					from one re-initialization of the entity's network
					management system to the next re-initialization."
			::= { lpOptPATHSbaEntry 1 }

		lpOptPATHSbaPATHIndex OBJECT-TYPE
			SYNTAX  INTEGER (1..255)
			ACCESS  read-only
			STATUS  mandatory
			DESCRIPTION
					"Index variable for uniquely identifying the
					primary, secondary and local PATH object
					instances. Local PATH object instances are
					represented with integer values 3 to 255."
			REFERENCE
					"ANSI { fddiPATH 11 }"
			::= { lpOptPATHSbaEntry 2 }

		lpOptPATHSbaPayload OBJECT-TYPE
			SYNTAX  INTEGER (0..1562)
			ACCESS  read-write
			STATUS  mandatory
			DESCRIPTION
					"The payload portion of the Synchronous Bandwidth
					Allocation for thi path.  This value represents the
					maximum number of bytes of data allocated for
					transmission per 125 microseconds."
			REFERENCE
					"ANSI { fddiPATH 15 }"
			::= { lpOptPATHSbaEntry 3 }

		lpOptPATHSbaOverhead OBJECT-TYPE
			SYNTAX  INTEGER
			ACCESS  read-write
			STATUS  mandatory
			DESCRIPTION
					"The overhead portion of the Synchronous Bandwith
					Allocation for this path.  This value repersents the
					maximum number of bytes overhead (token capture, frame
					header, etc.) used pre negotiated Target Token Rotation
					Time (T_neg)."
			REFERENCE
					"ANSI { fddiPATH 16 }"
			::= { lpOptPATHSbaEntry 4 }

		lpOptPATHSbaAvailable OBJECT-TYPE
			SYNTAX  INTEGER (0..12500000)
			ACCESS  read-write
			STATUS  mandatory
			DESCRIPTION
					"This value is the maximum Synchronous Bandwith available
					for a path in bytes per second."
			REFERENCE
					"ANSI { fddiPATH 20 }"
			::= { lpOptPATHSbaEntry 5 }

		-- the lpOptPORT group

		-- the lpOptPORTTable

		lpOptPORTTable OBJECT-TYPE
			SYNTAX  SEQUENCE OF LpOptPORTEntry
			ACCESS  not-accessible
			STATUS  mandatory
			DESCRIPTION
					"A list of optional PORT entries."
			::= { lpOptPORT 1 }

		lpOptPORTEntry OBJECT-TYPE
			SYNTAX  LpOptPORTEntry
			ACCESS  not-accessible
			STATUS  mandatory
			DESCRIPTION
					"MAC loop time and EB error count information for a 
					given PORT within a given SMT."
			INDEX   { lpOptPORTSMTIndex, lpOptPORTIndex }
			::= { lpOptPORTTable 1 }

		LpOptPORTEntry ::=
			SEQUENCE {
				lpOptPORTSMTIndex
					INTEGER,
				lpOptPORTIndex
					INTEGER,
				lpOptPORTMACLoopTime
					FddiTimeNano,
				lpOptPORTEBErrorCt
					Counter
			}

		lpOptPORTSMTIndex OBJECT-TYPE
			SYNTAX	INTEGER (1..65535)
			ACCESS	read-only
			STATUS	mandatory
			DESCRIPTION
					"A unique value for each SMT.  Its value ranges
					between 1 and the value of snmpFddiSMTNumber.  The
					value for each SMT must remain constant at least
					from one re-initialization of the entity's network
					management system to the next re-initialization."
			::= { lpOptPORTEntry 1 }

		lpOptPORTIndex OBJECT-TYPE
			SYNTAX  INTEGER (1..65535)
			ACCESS  read-only
			STATUS  mandatory
			DESCRIPTION
					"Index variable for uniquely identifying the PORT
					object instances."
			REFERENCE
					"ANSI { fddiPORT 29 }"
			::= { lpOptPORTEntry 2 }

		lpOptPORTMACLoopTime OBJECT-TYPE
			SYNTAX  FddiTimeNano
			ACCESS  read-write
			STATUS  mandatory
			DESCRIPTION
					"This attribute controls the value used for T_Next(9)
					(see 9.4.4.2.3).  This object is reported in 1 ns 
					units."
			REFERENCE
					"ANSI { fddiPORT 21 }"
			::= { lpOptPORTEntry 3 }

		lpOptPORTEBErrorCt OBJECT-TYPE
			SYNTAX  Counter
			ACCESS  read-only
			STATUS  mandatory
			DESCRIPTION
					"A count that should as closely as possible match the 
					times an Elasticity Buffer Error has occurred while in
					active line state."
			REFERENCE
					"ANSI { fddiPORT 41 }"
			::= { lpOptPORTEntry 4 }

		-- the lpOptPORTLSTable

		lpOptPORTLSTable OBJECT-TYPE
			SYNTAX  SEQUENCE OF LpOptPORTLSEntry
			ACCESS  not-accessible
			STATUS  mandatory
			DESCRIPTION
					"A list of optional PORT line state entries."
			::= { lpOptPORT 2 }

		lpOptPORTLSEntry OBJECT-TYPE
			SYNTAX  LpOptPORTLSEntry
			ACCESS  not-accessible
			STATUS  mandatory
			DESCRIPTION
					"Maintenance line state and PC line state information
					for a given PORT within a given SMT."
			INDEX   { lpOptPORTLSSMTIndex, lpOptPORTLSPORTIndex }
			::= { lpOptPORTLSTable 1 }

		LpOptPORTLSEntry ::=
			SEQUENCE {
				lpOptPORTLSSMTIndex
					INTEGER,
				lpOptPORTLSPORTIndex
					INTEGER,
				lpOptPORTMaintLS
					INTEGER,
				lpOptPORTPCLS
					INTEGER
			}

		lpOptPORTLSSMTIndex OBJECT-TYPE
			SYNTAX	INTEGER (1..65535)
			ACCESS	read-only
			STATUS	mandatory
			DESCRIPTION
					"A unique value for each SMT.  Its value ranges
					between 1 and the value of snmpFddiSMTNumber.  The
					value for each SMT must remain constant at least
					from one re-initialization of the entity's network
					management system to the next re-initialization."
			::= { lpOptPORTLSEntry 1 }

		lpOptPORTLSPORTIndex OBJECT-TYPE
			SYNTAX  INTEGER (1..65535)
			ACCESS  read-only
			STATUS  mandatory
			DESCRIPTION
					"Index variable for uniquely identifying the PORT
					object instances."
			REFERENCE
					"ANSI { fddiPORT 29 }"
			::= { lpOptPORTLSEntry 2 }

		lpOptPORTMaintLS OBJECT-TYPE
			SYNTAX  INTEGER {
						quiet(1),
						idle(2),
						master(3),
						halt(4),
						receive-active(5),
						receive-unknown(6),
						receive-noise(7)
					}
			ACCESS  read-write
			STATUS  mandatory
			DESCRIPTION
					"The PORT Maintenance Line State specifies the line state
					(Maint_LS) to be transmitted when the PCM state machine 
					for the port is in state PC9 Maint."
			REFERENCE
					"ANSI { fddiPORT 31 }"
			::= { lpOptPORTLSEntry 3 }

		lpOptPORTPCLS OBJECT-TYPE
			SYNTAX  INTEGER {
						quiet(1),
						idle(2),
						master(3),
						halt(4),
						receive-active(5),
						receive-unknown(6),
						receive-noise(7)
					}
			ACCESS  read-only
			STATUS  mandatory
			DESCRIPTION
					"This attribute indicates the line state (PC_LS) received
					by the port."
			REFERENCE
					"ANSI { fddiPORT 34 }"
			::= { lpOptPORTLSEntry 4 }

		-- traps

		-- SMT events

		lpOptSMTHoldCondition TRAP-TYPE
			ENTERPRISE	lanplexOptFddi
			VARIABLES	{ fddimibSMTStationId,
						lpOptSMTHoldState }
			DESCRIPTION
					"Generated when fddiSMTHoldState (fddimibSMTHoldState)
					assumes the state holding-prm or holding-sec.  This 
					notification is a Condition in the Status Report
					Protocol (see 7.2.7 and 8.3)."
			REFERENCE
					"ANSI { fddiSMT 71 }"
			::= 1

		lpOptSMTPeerWrapCondition TRAP-TYPE
			ENTERPRISE	lanplexOptFddi
			VARIABLES	{ fddimibSMTStationId,
						fddimibSMTCFState,
						fddimibSMTPeerWrapFlag }
			DESCRIPTION
					"This condition is active when fddiSMTPeerWrapFlag 
					(fddimibSMTPeerWrapFlag) is set.  This notification is
					a Condition in the Status Report Protocol (see 7.2.7 
					and 8.3)."
			REFERENCE
					"ANSI { fddiSMT 72 }"
			::= 2

		-- MAC events

		lpOptMACDuplicateAddressCondition TRAP-TYPE
			ENTERPRISE	lanplexOptFddi
			VARIABLES	{ fddimibSMTStationId,
						fddimibMACSMTAddress,
						fddimibMACUpstreamNbr,
						fddimibMACDaFlag,
						fddimibMACUnaDaFlag }
			DESCRIPTION
					"This condition is active when either fddiMACDA-Flag
					(fddimibMACDaFlag) or fddiMACUNDA-Flag 
					(fddimibMACUnaDaFlag) is set.  This event is handled
					as a Condition in the Status Report Protocol (see 7.2.7
					and 8.3)."
			REFERENCE
					"ANSI { fddiMAC 140 }"
			::= 3

		lpOptMACFrameErrorCondition TRAP-TYPE
			ENTERPRISE	lanplexOptFddi
			VARIABLES	{ fddimibSMTStationId,
						fddimibMACFrameErrorFlag,
						fddimibMACFrameCts,
						fddimibMACErrorCts,
						fddimibMACLostCts,
						fddimibMACFrameErrorRatio }
			DESCRIPTION
					"Generated when the fddiMACFrameErrorRatio 
					(fddimibMACFrameErrorRatio) is greater than or equal
					to fddiMACFrameErrorThreshold 
					(fddimibMACFrameErrorThreshold).  This event is handled
					as a Condition in the Status Report Protocol (see 7.2.7
					and 8.3)."
			REFERENCE
					"ANSI { fddiMAC 141 }"
			::= 4

		lpOptMACNotCopiedCondition TRAP-TYPE
			ENTERPRISE	lanplexOptFddi
			VARIABLES	{ fddimibSMTStationId,
						fddimibMACNotCopiedCts,
						fddimibMACCopiedCts,
						fddimibMACNotCopiedRatio,
						fddimibMACNotCopiedFlag }
			DESCRIPTION
					"Generated when the fddiMACNotCopiedRatio 
					(fddimibMACNotCopiedRatio) is greater than or equal to 
					the fddiMACNotCopiedThreshold (lpOptMACNotCopiedThreshold).
					This event is handled as a Condition in the Status Report 
					Protocol (see 7.2.7 and 8.3)."
			REFERENCE
					"ANSI { fddiMAC 142 }"
			::= 5

		lpOptMACNeighborChangeEvent TRAP-TYPE
			ENTERPRISE	lanplexOptFddi
			VARIABLES	{ fddimibSMTStationId,
						fddimibMACUpstreamNbr,
						fddimibMACOldUpstreamNbr,
						fddimibMACDownstreamNbr,
						fddimibMACOldDownstreamNbr,
						fddimibMACCurrentPath,
						fddimibMACSMTAddress }
			DESCRIPTION
					"Generated when a change in a MAC's upstream neighbor
					address or downstream neighbor address is detected.
					(see 7.2.7 and 8.3)."
			REFERENCE
					"ANSI { fddiMAC 143 }"
			::= 6

		lpOptMACPathChangeEvent TRAP-TYPE
			ENTERPRISE	lanplexOptFddi
			VARIABLES	{ fddimibSMTStationId,
						fddimibMACAvailablePaths,
						fddimibMACCurrentPath,
						fddimibMACRequestedPaths }
			DESCRIPTION
					"This event is generated when the value of the 
					fddiMACCurrentPath (fddimibMACCurrentPath) changes.
					This event shall be supressed if the value changes
					from isolated to local or local to isolated (see
					7.2.7 and 8.3)."
			REFERENCE
					"ANSI { fddiMAC 144 }"
			::= 7

		-- PORT events

		lpOptPORTLerCondition TRAP-TYPE
			ENTERPRISE	lanplexOptFddi
			VARIABLES	{ fddimibSMTStationId,
						fddimibPORTLerCutoff,
						fddimibPORTLerAlarm,
						fddimibPORTLerEstimate,
						fddimibPORTLemRejectCts,
						fddimibPORTLemCts,
						fddimibPORTLerFlag }
			DESCRIPTION
					"This condition becomes active when the value of 
					fddiPORTLer-Estimate (fddimibPORTLerEstimate)
					is less than or equal to fddiPORTLer-Alarm
					(fddimibPORTLerAlarm).  This will be reported
					with the Status Report Frames (SRF) (see 7.2.7 
					and 8.3)."
			REFERENCE
					"ANSI { fddiPORT 80 }"
			::= 8

		lpOptPORTUndesiredConnAttemptEvent TRAP-TYPE
			ENTERPRISE	lanplexOptFddi
			VARIABLES	{ fddimibSMTStationId,
						fddimibPORTMyType,
						fddimibPORTConnectState,
						fddimibPORTNeighborType,
						fddimibPORTPCWithhold }
			DESCRIPTION
					"Generated when an undesired connection attempt has
					been made (see 5.2.4, 7.2.7, and 8.3)."
			REFERENCE
					"ANSI { fddiPORT 81 }"
			::= 9

		lpOptPORTEBErrorCondition TRAP-TYPE
			ENTERPRISE	lanplexOptFddi
			VARIABLES	{ fddimibSMTStationId,
						lpOptPORTEBErrorCt }
			DESCRIPTION
					"Generated when the Elasticity Buffer Error-Ct
					(lpOptPORTEBErrorCt) increments.  This is handled
					as a condition in the Status Report Protocol.  It
					is generated when an increment occurs in the 
					station's sampling period (see 7.2.7 and 8.3)."
			REFERENCE
					"ANSI { fddiPORT 82 }"
			::= 10

		lpOptPORTPathChangeEvent TRAP-TYPE
			ENTERPRISE	lanplexOptFddi
			VARIABLES	{ fddimibSMTStationId,
						fddimibPORTAvailablePaths,
						fddimibPORTCurrentPath,
						fddimibPORTRequestedPaths,
						fddimibPORTMyType,
						fddimibPORTNeighborType }
			DESCRIPTION
					"This event is generated when the value of the 
					fddiPORTCurrentPath (lpOptPORTCurrentPath)
					changes.  This event shall be surpressed if the
					value changes from isolated to local or local
					to isolated (see 7.2.7 and 8.3)."
			REFERENCE
					"ANSI { fddiPORT 83 }"
			::= 11

		END
