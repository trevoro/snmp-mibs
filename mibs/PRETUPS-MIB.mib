PRETUPS-MIB DEFINITIONS ::= BEGIN
IMPORTS
    MODULE-IDENTITY, NOTIFICATION-TYPE,
    Integer32, Unsigned32,
    TimeTicks, Counter32, Counter64,
    IpAddress, Opaque, mib-2,enterprises       FROM SNMPv2-SMI
    TimeStamp, DateAndTime,
    StorageType, RowStatus,
    TAddress, TDomain              FROM SNMPv2-TC
    SnmpAdminString, SnmpEngineID  FROM SNMP-FRAMEWORK-MIB
    MODULE-COMPLIANCE, OBJECT-GROUP     FROM SNMPv2-CONF;
btsl  MODULE-IDENTITY
              LAST-UPDATED "200406120718Z"
              ORGANIZATION "Bharti Telesoft International Pvt. Limited "
              CONTACT-INFO "F-89/6 Okhla Phase 1
                             New Delhi-20"
              DESCRIPTION "PRETUPS"
      ::={enterprises 19338}
pretups  OBJECT IDENTIFIER ::={btsl 9}
-- traps data
pretupsnotification  OBJECT IDENTIFIER ::={pretups 2}
-- traps data
pretupsnotification1  OBJECT IDENTIFIER ::={pretupsnotification 0}
-- traps data
database        OBJECT IDENTIFIER ::={pretupsnotification1 1}
-- traps data
databasedown    NOTIFICATION-TYPE
       STATUS  current
       DESCRIPTION  "Database Connection IS DOWN."
          ::={database 0}
-- traps data
databaseup    NOTIFICATION-TYPE
       STATUS  current
       DESCRIPTION  "Database Connection IS UP."
          ::={database 1}
-- traps data
systemerrorerror        OBJECT IDENTIFIER ::={pretupsnotification1 2}
-- traps data
systemerrorerrordown    NOTIFICATION-TYPE
       STATUS  current
       DESCRIPTION  "System Error."
          ::={systemerrorerror 0}
-- traps data
systemerrorerrorup    NOTIFICATION-TYPE
       STATUS  current
       DESCRIPTION  "System Error."
          ::={systemerrorerror 1}
-- traps data

systeminfo      OBJECT IDENTIFIER ::={pretupsnotification1 3}
-- traps data
systeminfodown    NOTIFICATION-TYPE
       STATUS  current
       DESCRIPTION  "System Information."
          ::={systeminfo 0}
-- traps data
systeminfoup    NOTIFICATION-TYPE
       STATUS  current
       DESCRIPTION  "System Information."
          ::={systeminfo 1}
-- traps data
interfaceinvaliedresponse       OBJECT IDENTIFIER ::={pretupsnotification1 4}
-- traps data
interfaceinvaliedresponsedown    NOTIFICATION-TYPE
       STATUS  current
       DESCRIPTION  "Interface Invalid Response."
          ::={interfaceinvaliedresponse 0}
-- traps data
interfaceinvaliedresponseup    NOTIFICATION-TYPE
       STATUS  current
       DESCRIPTION  "Interface Invalid Response"
          ::={interfaceinvaliedresponse 1}
-- traps data


retry  OBJECT IDENTIFIER ::={pretupsnotification1 5}
-- traps data
retrydown    NOTIFICATION-TYPE
       STATUS  current
       DESCRIPTION  "Interface Retry Attempt Failed"
          ::={retry 0}
-- traps data
retryup    NOTIFICATION-TYPE
       STATUS  current
       DESCRIPTION  "Interface Retry Attempt Failed"
          ::={retry 1}
-- traps data


interface  OBJECT IDENTIFIER ::={pretupsnotification1 6}
-- traps data

interfacedown    NOTIFICATION-TYPE
       STATUS  current
       DESCRIPTION  "Interface Request Failed"
          ::={interface 0}
-- traps data
interfaceup    NOTIFICATION-TYPE
       STATUS  current
       DESCRIPTION  "Interface Request Failed"
          ::={interface 1}
-- traps data

interfaceresponse  OBJECT IDENTIFIER ::={pretupsnotification1 7}
-- traps data

interfaceresponsedown    NOTIFICATION-TYPE
       STATUS  current
       DESCRIPTION  "Interface Response Exception"
          ::={interfaceresponse 0}
-- traps data
interfaceresponseup    NOTIFICATION-TYPE
       STATUS  current
       DESCRIPTION  "Interface Response Exception"
          ::={interfaceresponse 1}
-- traps data

adminopt  OBJECT IDENTIFIER ::={pretupsnotification1 8}
-- traps data

adminoptdown    NOTIFICATION-TYPE
       STATUS  current
       DESCRIPTION  "Network Status Change"
          ::={adminopt 0}
-- traps data
adminoptup    NOTIFICATION-TYPE
       STATUS  current
  DESCRIPTION  "Network Status Change"
          ::={adminopt 1}
-- traps data


urlMonitoring  OBJECT IDENTIFIER ::={pretups 1}

alarm  OBJECT IDENTIFIER ::={urlMonitoring 1}

oam  OBJECT IDENTIFIER ::={alarm 6}

loadBlancer1  NOTIFICATION-TYPE

       STATUS  current
       DESCRIPTION  "Load Blancer is Down"
          ::={oam 0}


loadBlancer2  NOTIFICATION-TYPE

       STATUS  current
       DESCRIPTION  "Load Blancer is Down"
          ::={oam 1}
END
