Wellfleet-FSM-MIB DEFINITIONS ::= BEGIN

-- Created by mdl2asn version 3.1
-- Creation date: Wed Aug 30 16:41:41 EDT 1995


    IMPORTS

      Gauge
        FROM RFC1155-SMI
      OBJECT-TYPE
        FROM RFC-1212
      DisplayString
        FROM RFC1213-MIB
      wfFileSystemGroup
        FROM Wellfleet-COMMON-MIB;


    wfFsBase	OBJECT IDENTIFIER ::= { wfFileSystemGroup 1 }

    wfFsVolLastUpdated OBJECT-TYPE
        SYNTAX	OCTET STRING
        ACCESS	read-only
        STATUS	mandatory
        DESCRIPTION
                "Date and time the volume table was last updated"
        ::= { wfFsBase 1 }

    wfFsVols OBJECT-TYPE
        SYNTAX	Gauge
        ACCESS	read-only
        STATUS	mandatory
        DESCRIPTION
                "The number of rows in the volume table"
        ::= { wfFsBase 2 }

    wfFsVolTable OBJECT-TYPE
        SYNTAX	SEQUENCE OF WfFsVolEntry
        ACCESS	not-accessible
        STATUS	mandatory
        DESCRIPTION
                "Volume table"
        ::= { wfFileSystemGroup 2 }

    wfFsVolEntry OBJECT-TYPE
        SYNTAX	WfFsVolEntry
        ACCESS	not-accessible
        STATUS	mandatory
        DESCRIPTION
                "A row in the Volume table"
        INDEX	{ wfFsVolID }
        ::= { wfFsVolTable 1 }

    WfFsVolEntry ::= SEQUENCE {
    	    wfFsVolID
    		INTEGER,
    	    wfFsSlot
    		INTEGER,
    	    wfFsType
    		INTEGER,
    	    wfFsRemoveable
    		INTEGER,
    	    wfFsAccess
    		INTEGER,
    	    wfFsState
    		INTEGER,
    	    wfFsSize
    		Gauge,
    	    wfFsFreeSize
    		Gauge,
    	    wfFsContigFree
    		Gauge,
    	    wfFsNumFiles
    		Gauge,
    	    wfFsLastWritten
    		OCTET STRING,
    	    wfFsBecameActive
    		OCTET STRING,
    	    wfFsAction
    		INTEGER,
    	    wfFsActionArg
    		OBJECT IDENTIFIER,
    	    wfFsPercentDone
    		INTEGER
        }

    wfFsVolID OBJECT-TYPE
        SYNTAX	INTEGER
        ACCESS	read-only
        STATUS	mandatory
        DESCRIPTION
                "Volume number"
        ::= { wfFsVolEntry 1 }

    wfFsSlot OBJECT-TYPE
        SYNTAX	INTEGER
        ACCESS	read-only
        STATUS	mandatory
        DESCRIPTION
                "Processor owning the volume"
        ::= { wfFsVolEntry 2 }

    wfFsType OBJECT-TYPE
        SYNTAX	INTEGER {
    		    dos(1),
    		    nvfs(2),
    		    unix(3)
    		}
        ACCESS	read-only
        STATUS	mandatory
        DESCRIPTION
                "Type of volume - DOS, NVFS or UNIX"
        ::= { wfFsVolEntry 3 }

    wfFsRemoveable OBJECT-TYPE
        SYNTAX	INTEGER {
    		    remove(1),
    		    fixed(2)
    		}
        ACCESS	read-only
        STATUS	mandatory
        DESCRIPTION
                "Can this file system be removed or is it a fixed file system"
        ::= { wfFsVolEntry 4 }

    wfFsAccess OBJECT-TYPE
        SYNTAX	INTEGER {
    		    unknown(1),
    		    readonly(2),
    		    readwrite(3)
    		}
        ACCESS	read-only
        STATUS	mandatory
        DESCRIPTION
                "Read only or read-write file system. DOS file systems are always set
                to unknown since we can't tell what the state is until we actually
                try to write to the disk."
        ::= { wfFsVolEntry 5 }

    wfFsState OBJECT-TYPE
        SYNTAX	INTEGER {
    		    ok(1),
    		    corrupt(2),
    		    busy(3),
    		    present(4),
    		    incomplete(5)
    		}
        ACCESS	read-only
        STATUS	mandatory
        DESCRIPTION
                "The state that the file system is in. If it is corrupted then it is
                unusable, if it is busy, the MIB is being updated.  Floppy not present is
                a state used in DOS only and means that the floppy isn't there or we
                couldn't mount it.  Incomplete means that we got a mount for a DOS floppy
                duing boot, but because of 30 second timeouts in DOS, we are not willing
                to take the hit during boot.  Fill in minimal information and let Site
                Manager do the 'DIR' that will fill in the rest."
        ::= { wfFsVolEntry 6 }

    wfFsSize OBJECT-TYPE
        SYNTAX	Gauge
        ACCESS	read-only
        STATUS	mandatory
        DESCRIPTION
                "Physical size in bytes"
        ::= { wfFsVolEntry 7 }

    wfFsFreeSize OBJECT-TYPE
        SYNTAX	Gauge
        ACCESS	read-only
        STATUS	mandatory
        DESCRIPTION
                "Total available bytes"
        ::= { wfFsVolEntry 8 }

    wfFsContigFree OBJECT-TYPE
        SYNTAX	Gauge
        ACCESS	read-only
        STATUS	mandatory
        DESCRIPTION
                "The amount of contiguous bytes free. In DOS and UNIX, contiguous = free.
                In NVFS, this may not be true."
        ::= { wfFsVolEntry 9 }

    wfFsNumFiles OBJECT-TYPE
        SYNTAX	Gauge
        ACCESS	read-only
        STATUS	mandatory
        DESCRIPTION
                "The number of files on this volume"
        ::= { wfFsVolEntry 10 }

    wfFsLastWritten OBJECT-TYPE
        SYNTAX	OCTET STRING
        ACCESS	read-only
        STATUS	mandatory
        DESCRIPTION
                "The last time a write request was written to this volume"
        ::= { wfFsVolEntry 11 }

    wfFsBecameActive OBJECT-TYPE
        SYNTAX	OCTET STRING
        ACCESS	read-only
        STATUS	mandatory
        DESCRIPTION
                "The date and time this volume became active"
        ::= { wfFsVolEntry 12 }

    wfFsAction OBJECT-TYPE
        SYNTAX	INTEGER {
    		    dir(1),
    		    format(2),
    		    compact(3),
    		    purge(4),
    		    partcre(5),
    		    partdel(6),
		    noaction(7)
    		}
        ACCESS	read-write
        STATUS	mandatory
        DESCRIPTION
                "When set, performs a volume command (compact, format, dir, purge)"
	DEFVAL { noaction }
        ::= { wfFsVolEntry 13 }

    wfFsActionArg OBJECT-TYPE
        SYNTAX	OBJECT IDENTIFIER
        ACCESS	read-write
        STATUS	mandatory
        DESCRIPTION
                "Optional argument for directory action for viewing file hierarchies"
        ::= { wfFsVolEntry 14 }

    wfFsPercentDone OBJECT-TYPE
        SYNTAX	INTEGER
        ACCESS	read-only
        STATUS	mandatory
        DESCRIPTION
                "Percent of task completed"
        ::= { wfFsVolEntry 15 }

    wfFsDirBase	OBJECT IDENTIFIER ::= { wfFileSystemGroup 3 }

    wfFsDirEntries OBJECT-TYPE
        SYNTAX	Gauge
        ACCESS	read-only
        STATUS	mandatory
        DESCRIPTION
                "Number of entries in the directory table"
        ::= { wfFsDirBase 1 }

    wfFsDirLastUpdated OBJECT-TYPE
        SYNTAX	OCTET STRING
        ACCESS	read-only
        STATUS	mandatory
        DESCRIPTION
                "Time the directory table was last updated"
        ::= { wfFsDirBase 2 }

    wfFsDirTable OBJECT-TYPE
        SYNTAX	SEQUENCE OF WfFsDirEntry
        ACCESS	not-accessible
        STATUS	mandatory
        DESCRIPTION
                "Directory table"
        ::= { wfFileSystemGroup 5 }

    wfFsDirEntry OBJECT-TYPE
        SYNTAX	WfFsDirEntry
        ACCESS	not-accessible
        STATUS	mandatory
        DESCRIPTION
                "An entry in the directory table"
        INDEX	{ wfFsDirVolID,
    		  wfFsDirFileIndex }
        ::= { wfFsDirTable 1 }

    WfFsDirEntry ::= SEQUENCE {
    	    wfFsDirVolID
    		INTEGER,
    	    wfFsDirFileIndex
    		OBJECT IDENTIFIER,
    	    wfFsDirFileName
    		DisplayString,
    	    wfFsDirCreated
    		OCTET STRING,
    	    wfFsDirFileSize
    		Gauge,
    	    wfFsDirFileMask
    		Gauge
        }

    wfFsDirVolID OBJECT-TYPE
        SYNTAX	INTEGER
        ACCESS	read-only
        STATUS	mandatory
        DESCRIPTION
                "Volume number that this directory entry is contained on"
        ::= { wfFsDirEntry 1 }

    wfFsDirFileIndex OBJECT-TYPE
        SYNTAX	OBJECT IDENTIFIER
        ACCESS	read-only
        STATUS	mandatory
        DESCRIPTION
                "Hierarchical file index"
        ::= { wfFsDirEntry 2 }

    wfFsDirFileName OBJECT-TYPE
        SYNTAX	DisplayString
        ACCESS	read-only
        STATUS	mandatory
        DESCRIPTION
                "Name of the file"
        ::= { wfFsDirEntry 3 }

    wfFsDirCreated OBJECT-TYPE
        SYNTAX	OCTET STRING
        ACCESS	read-only
        STATUS	mandatory
        DESCRIPTION
                "When the file was created"
        ::= { wfFsDirEntry 4 }

    wfFsDirFileSize OBJECT-TYPE
        SYNTAX	Gauge
        ACCESS	read-only
        STATUS	mandatory
        DESCRIPTION
                "Size of the file"
        ::= { wfFsDirEntry 5 }

    wfFsDirFileMask OBJECT-TYPE
        SYNTAX	Gauge
        ACCESS	read-only
        STATUS	mandatory
        DESCRIPTION
                "Access mode on file for UNIX and DOS file systems"
        ::= { wfFsDirEntry 6 }

    END  -- Wellfleet-FSM-MIB
