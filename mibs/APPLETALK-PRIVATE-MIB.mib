APPLETALK-PRIVATE-MIB DEFINITIONS ::= BEGIN

-- Referencing the parent branch.

IMPORTS
            MODULE-IDENTITY, OBJECT-TYPE 		FROM SNMPv2-SMI
	    RowStatus					FROM SNMPv2-TC
	    cjnProtocol                             	FROM Cajun-ROOT; 

cjnAtalk MODULE-IDENTITY
        LAST-UPDATED "9903090000Z" -- Tuesday Mar 9, 1999
        ORGANIZATION "Lucent's Concord Technology Center (CTC)"
        CONTACT-INFO
	        "Erick Crowell -- ecrowell@lucent.com
		 Raj Duggal (Group Leader) -- rduggal@lucent.com
	         Simon Fang sfang@lucent.com
		 Michael C. Cambria -- mcambria@lucent.com"

	DESCRIPTION
       		"Cajun Private Apple Talk Routing MIB"
	::= { cjnProtocol 4 }

    	DdpAddress ::=	-- 2 octets of net number
			-- 1 octet of node number
		OCTET STRING (SIZE (3))

DisplayString ::= OCTET STRING

-- APPLETALK (Apple Talk Phase II Routing) Global Configuration Group
--
	cjnAtGblGroup	OBJECT IDENTIFIER ::= { cjnAtalk 1 }

	cjnAtIsEnabled OBJECT-TYPE
              SYNTAX  INTEGER {
        	  false(1),
		   true(2)
		}	
              MAX-ACCESS  read-write
              STATUS  current
              DESCRIPTION
            	   "Enables Apple Talk Routing services on this device."
    	  ::= { cjnAtGblGroup 1 }

	cjnAtGlobalStatsReset  OBJECT-TYPE
	    SYNTAX  INTEGER {
	      disable(1),
	      enable(2)
	    }	
	   MAX-ACCESS read-write
	   STATUS current
	   DESCRIPTION
	   "When set to the value enable (2) all Apple Talk Global Statistics are
	  reset to zero after which the value of this MIB object returns to disable(1)"
	   ::= { cjnAtGblGroup 2 }


-- APPLETALK (Apple Talk Phase II Routing) Interface Zone Group
--

	cjnAtIfZoneGroup	OBJECT IDENTIFIER ::= { cjnAtalk 2 }

          cjnAtIfNextZoneIndex OBJECT-TYPE
                  SYNTAX INTEGER
                  MAX-ACCESS read-only
                  STATUS current
                  DESCRIPTION
                      "The next AtIfZoneIndex value to be used to create a new row."
                  ::= { cjnAtIfZoneGroup 1 }


          cjnAtIfZoneTable OBJECT-TYPE
                  SYNTAX SEQUENCE OF CjnAtIfZoneEntry
                  MAX-ACCESS not-accessible
                  STATUS current
                  DESCRIPTION
                      "A list of Apple Talk Interface Zone Entries for this entity."
                  ::= { cjnAtIfZoneGroup 2 }

          cjnAtIfZoneEntry OBJECT-TYPE
                  SYNTAX CjnAtIfZoneEntry
                  MAX-ACCESS not-accessible
                  STATUS current
                  DESCRIPTION
                      "The Interface Zone Entry to a particular port."
                  INDEX { cjnAtPortIndex, cjnAtIfZoneIndex }
                  ::= { cjnAtIfZoneTable 1 }

          CjnAtIfZoneEntry ::= SEQUENCE {
	  	  cjnAtIfZoneIndex		INTEGER,
                  cjnAtIfZoneName		OCTET STRING,
                  cjnAtIfZoneDefault		INTEGER,
                  cjnAtIfZoneRowStatus		RowStatus
          }

          cjnAtIfZoneIndex OBJECT-TYPE
                  SYNTAX INTEGER
                  MAX-ACCESS read-only
                  STATUS current
                  DESCRIPTION
                      "An integer that is unique to the IfZoneName
                      that is present in this entry.  For any given
                      zone name, every zipEntry that has an equal zone
                      name will have the same IfZoneIndex."
                  ::= { cjnAtIfZoneEntry 1 }

          cjnAtIfZoneName OBJECT-TYPE
                  SYNTAX OCTET STRING (SIZE(1..32))
                  MAX-ACCESS read-create
                  STATUS current
                  DESCRIPTION
                      "The ASCII zone name of this entry."
                  ::= { cjnAtIfZoneEntry 2 }

	  cjnAtIfZoneDefault  OBJECT-TYPE
	      	SYNTAX  INTEGER {
			yes(1),
			no(2),
			guessed(3)
		}	
	  	MAX-ACCESS read-create
		STATUS current
		DESCRIPTION
		    "When set to the value yes (1) this zone name is the default zone name
		    for the port.  When set to no(2), this zone name is not the default
		    zone name for the port."
		DEFVAL {2}
		::= { cjnAtIfZoneEntry 3 }

	  cjnAtIfZoneRowStatus OBJECT-TYPE
                  SYNTAX RowStatus
                  MAX-ACCESS read-create
                  STATUS current
                  DESCRIPTION
                      "The status of this entry in the table.  Note the available states:
		      active(1), -- Obviously Active on this interface.
		      notInService(2) -- Configured on Interface but disabled.
		      notReady(3), -- Interface entry NOT FULLY configured.
		      createAndGo(4), -- NOT SUPPORTED.
		      createAndWait(5)  
		      or destroy(6) "
                  ::= { cjnAtIfZoneEntry 4 }


-- APPLETALK (Apple Talk Phase II Routing) Static Route Group
--

	cjnAtStatRtGroup	OBJECT IDENTIFIER ::= { cjnAtalk 3 }

          cjnAtStatRtTable OBJECT-TYPE
                  SYNTAX SEQUENCE OF CjnAtStatRtEntry
                  MAX-ACCESS not-accessible
                  STATUS current
                  DESCRIPTION
                      "A list of Apple Talk Static Route Entries for this entity."
                  ::= { cjnAtStatRtGroup 1 }

          cjnAtStatRtEntry OBJECT-TYPE
                  SYNTAX CjnAtStatRtEntry
                  MAX-ACCESS not-accessible
                  STATUS current
                  DESCRIPTION
                      "The Static Route Entry to a particular network range."
                  INDEX { cjnAtStatRtRangeStart }
                  ::= { cjnAtStatRtTable 1 }

          CjnAtStatRtEntry ::= SEQUENCE {
                  cjnAtStatRtRangeStart  INTEGER,
                  cjnAtStatRtRangeEnd    INTEGER,
		  cjnAtStatRtRowStatus	 RowStatus,
                  cjnAtStatRtNextHop     DdpAddress,
                  cjnAtStatRtType        INTEGER
          }

          cjnAtStatRtRangeStart OBJECT-TYPE
                  SYNTAX INTEGER
                  MAX-ACCESS read-only
                  STATUS current
                  DESCRIPTION
                      "The first DDP network address in the network
                      range to which this routing entry pertains.
                      This is a two octet DDP network address in
                      network byte order."
                  ::= { cjnAtStatRtEntry 1 }

          cjnAtStatRtRangeEnd OBJECT-TYPE
                  SYNTAX INTEGER
                  MAX-ACCESS read-write
                  STATUS current
                  DESCRIPTION
                      "The last DDP network address in the network range
                      to which this routing entry pertains.  This is a
                      two octet DDP network address in network byte
                      order.  If the network to which this routing
                      entry pertains is a Phase 1 network or a
                      non-extended network, the value for rtmpRangeEnd
                      shall be two octets of zero."
                  ::= { cjnAtStatRtEntry 2 }

          cjnAtStatRtRowStatus OBJECT-TYPE
                  SYNTAX RowStatus
                  MAX-ACCESS read-write
                  STATUS current
                  DESCRIPTION
                      "The Ddp Address of the next hop in the route to this entry's
                      destination network."
                  ::= { cjnAtStatRtEntry 3 }

          cjnAtStatRtNextHop OBJECT-TYPE
                  SYNTAX DdpAddress
                  MAX-ACCESS read-write
                  STATUS current
                  DESCRIPTION
                      "The Ddp Address of the next hop in the route to this entry's
                      destination network."
                  ::= { cjnAtStatRtEntry 4 }

          cjnAtStatRtType OBJECT-TYPE
                  SYNTAX INTEGER {
                          low(1),
                          high(2)
                  }
                  MAX-ACCESS read-write
                  STATUS current
                  DESCRIPTION
                      "The type of Static Route Entry."
		  DEFVAL {1}
                  ::= { cjnAtStatRtEntry 5 }


-- APPLETALK (Apple Talk Phase II Routing) Static Route Zone Group
--

	cjnAtStatRtZoneGroup	OBJECT IDENTIFIER ::= { cjnAtalk 4 }

          cjnAtNextStatRtZoneIndex OBJECT-TYPE
                  SYNTAX INTEGER
                  MAX-ACCESS read-only
                  STATUS current
                  DESCRIPTION
                      "The next StatRtZoneIndex value to be used for row creation."
                  ::= { cjnAtStatRtZoneGroup 1 }


          cjnAtStatRtZoneTable OBJECT-TYPE
                  SYNTAX SEQUENCE OF CjnAtStatRtZoneEntry
                  MAX-ACCESS not-accessible
                  STATUS current
                  DESCRIPTION
                      "A list of Apple Talk Static Route Zone Entries for this entity."
                  ::= { cjnAtStatRtZoneGroup 2 }

          cjnAtStatRtZoneEntry OBJECT-TYPE
                  SYNTAX CjnAtStatRtZoneEntry
                  MAX-ACCESS not-accessible
                  STATUS current
                  DESCRIPTION
                      "The Zone Entry to a particular Static Route."
                  INDEX { cjnAtStatRtRangeStart, cjnAtStatRtZoneIndex }
                  ::= { cjnAtStatRtZoneTable 1 }

          CjnAtStatRtZoneEntry ::= SEQUENCE {
                  cjnAtStatRtZoneIndex			INTEGER,
                  cjnAtStatRtZoneName			OCTET STRING,
		  cjnAtStatRtZoneRowStatus		RowStatus
          }

          cjnAtStatRtZoneIndex OBJECT-TYPE
                  SYNTAX INTEGER
                  MAX-ACCESS read-only
                  STATUS current
                  DESCRIPTION
                      "An integer that is unique to the StatRtZoneName
                      that is present in this entry.  For any given
                      zone name, every zipEntry that has an equal zone
                      name will have the same StatRtZoneIndex."
                  ::= { cjnAtStatRtZoneEntry 1 }

          cjnAtStatRtZoneName OBJECT-TYPE
                  SYNTAX OCTET STRING (SIZE(1..32))
                  MAX-ACCESS read-create
                  STATUS current
                  DESCRIPTION
                      "The ASCII zone name of this entry."
                  ::= { cjnAtStatRtZoneEntry 2 }

	  cjnAtStatRtZoneRowStatus OBJECT-TYPE
                  SYNTAX RowStatus
                  MAX-ACCESS read-create
                  STATUS current
                  DESCRIPTION
                      "The status of this entry in the table.  Note the available states:
		      active(1), -- Obviously Active on this interface.
		      notInService(2) -- Configured on Interface but disabled.
		      notReady(3), -- Interface entry NOT FULLY configured.
		      createAndGo(4), -- NOT SUPPORTED.
		      createAndWait(5)  
		      or destroy(6) "
                  ::= { cjnAtStatRtZoneEntry 3 }

-- APPLETALK (Apple Talk Phase II Routing) AARP Group
--

	  cjnAtAarp		OBJECT IDENTIFIER ::= { cjnAtalk 5 }

          cjnAarpReset OBJECT-TYPE
	      SYNTAX  INTEGER {
	      	disable(1),
		enable(2)
		}	
	    	MAX-ACCESS read-write
		STATUS current
		DESCRIPTION
		    "When set to the value enable (2) all Apple Talk AARP Table is 
		    cleared, after which the value of this MIB object returns
		    to disable(1)"
      		::= { cjnAtAarp 1 }

          cjnAarpTable OBJECT-TYPE
                  SYNTAX SEQUENCE OF CjnAarpEntry
                  MAX-ACCESS not-accessible
                  STATUS current
                  DESCRIPTION
                      "The AppleTalk Address Translation Table
                      contains an equivalence of AppleTalk Network
                      Addresses to the link layer physical address."
                  ::= { cjnAtAarp 2 }

          cjnAarpEntry OBJECT-TYPE
                  SYNTAX CjnAarpEntry
                  MAX-ACCESS not-accessible
                  STATUS current
                  DESCRIPTION
                      "Each entry contains one AppleTalk Network
                      Address to physical address equivalence."
                  INDEX { cjnAtPortIfIndex, cjnAarpNetAddress }
                  ::= { cjnAarpTable 1 }

          CjnAarpEntry ::= SEQUENCE {
		  cjnAarpRowStatus   RowStatus,
                  cjnAarpPhysAddress OCTET STRING,
                  cjnAarpNetAddress  DdpAddress,
		  cjnAarpDescr	     DisplayString,
		  cjnAarpType	     INTEGER,
		  cjnAarpTtl	     INTEGER
          }

	  cjnAarpRowStatus OBJECT-TYPE
                  SYNTAX RowStatus
                  MAX-ACCESS read-write
                  STATUS current
                  DESCRIPTION
                      "The status of this entry in the table.  Note the available states:
		active(1), -- Obviously Active on this interface.
		notInService(2) -- Configured on Interface but disabled.
		notReady(3), -- Interface entry NOT FULLY configured.
		createAndGo(4), -- NOT SUPPORTED.
		createAndWait(5)  
		or destroy(6) "
                  ::= { cjnAarpEntry 1 }

          cjnAarpPhysAddress OBJECT-TYPE
                  SYNTAX OCTET STRING
                  MAX-ACCESS read-only
                  STATUS current
                  DESCRIPTION
                      "The media-dependent physical address"
                  ::= { cjnAarpEntry 2 }

          cjnAarpNetAddress OBJECT-TYPE
                 SYNTAX DdpAddress
                 MAX-ACCESS read-only
                 STATUS current
                 DESCRIPTION
                      "The AppleTalk Network Address corresponding to
                     the media-dependent physical address.  Note:  When cjnAarpType is
		     either broadcast or multicast, this field represents only the beginning
		     network in the network range."
                 ::= { cjnAarpEntry 3 }

          cjnAarpDescr OBJECT-TYPE
                  SYNTAX DisplayString
                  MAX-ACCESS read-only
                  STATUS current
                  DESCRIPTION
                      "A text string containing information about the
                      port.  This string is intended for presentation
                      to a human; it must not contain anything but
                      printable ASCII characters."
                  ::= { cjnAarpEntry 4 }

          cjnAarpType OBJECT-TYPE
                  SYNTAX INTEGER {
                       unknown(1),
		       broadcast(2),
		       multicast(3),
		       local(4),
		       remote(5),
		       static(6),
                       router(7)
                  }
                  MAX-ACCESS read-only
                  STATUS current
                  DESCRIPTION
                      "The type of this AARP entry."
                  ::= { cjnAarpEntry 5 }

          cjnAarpTtl OBJECT-TYPE
                  SYNTAX INTEGER
                  MAX-ACCESS read-only
                  STATUS current
                  DESCRIPTION
                      "The TTL of this AARP entry."
                  ::= { cjnAarpEntry 6 }

-- APPLETALK (Apple Talk Phase II Routing) RTMP Group
--
	  cjnAtRtmp		OBJECT IDENTIFIER ::= { cjnAtalk 6 }

          cjnRtmpReset OBJECT-TYPE
	      SYNTAX  INTEGER {
	      	disable(1),
		enable(2)
		}	
	    	MAX-ACCESS read-write
		STATUS current
		DESCRIPTION
		    "When set to the value enable (2) all Apple Talk Route Table is 
		    cleared, after which the value of this MIB object returns
		    to disable(1)"
      		::= { cjnAtRtmp 1 }

          cjnRtmpTable OBJECT-TYPE
                  SYNTAX SEQUENCE OF CjnRtmpEntry
                  MAX-ACCESS not-accessible
                  STATUS current
                  DESCRIPTION
                      "A list of Routing Table Maintenance Protocol
                      entries for this entity."
                  ::= { cjnAtRtmp 2 }

          cjnRtmpEntry OBJECT-TYPE
                  SYNTAX CjnRtmpEntry
                  MAX-ACCESS not-accessible
                  STATUS current
                  DESCRIPTION
                      "The route entry to a particular network range."
                  INDEX { cjnRtmpRangeStart }
                  ::= { cjnRtmpTable 1 }

          CjnRtmpEntry ::= SEQUENCE {
                  cjnRtmpRangeStart  INTEGER,
                  cjnRtmpRangeEnd    INTEGER,
                  cjnRtmpNextHop     DdpAddress,
                  cjnRtmpHops        INTEGER,
                  cjnRtmpState       INTEGER,
		  cjnRtmpOwner	     INTEGER,
		  cjnRtmpDescr	     DisplayString,
		  cjnRtmpRowStatus   RowStatus
          }

          cjnRtmpRangeStart OBJECT-TYPE
                  SYNTAX INTEGER
                  MAX-ACCESS read-only
                  STATUS current
                  DESCRIPTION
                      "The first DDP network address in the network
                      range to which this routing entry pertains.
                      This is a two octet DDP network address in
                      network byte order."
                  ::= { cjnRtmpEntry 1 }

          cjnRtmpRangeEnd OBJECT-TYPE
                  SYNTAX INTEGER
                  MAX-ACCESS read-only
                  STATUS current
                  DESCRIPTION
                      "The last DDP network address in the network range
                      to which this routing entry pertains.  This is a
                      two octet DDP network address in network byte
                      order.  If the network to which this routing
                      entry pertains is a Phase 1 network or a
                      non-extended network, the value for rtmpRangeEnd
                      shall be two octets of zero."
                  ::= { cjnRtmpEntry 2 }

          cjnRtmpNextHop OBJECT-TYPE
                  SYNTAX DdpAddress
                  MAX-ACCESS read-only
                  STATUS current
                  DESCRIPTION
                      "The next hop in the route to this entry's
                      destination network."
                  ::= { cjnRtmpEntry 3 }

          cjnRtmpHops OBJECT-TYPE
                  SYNTAX INTEGER
                  MAX-ACCESS read-only
                  STATUS current
                  DESCRIPTION
                      "The number of hops required to reach the
                      destination network to which this routing
                      entry pertains."
                  ::= { cjnRtmpEntry 4 }

          cjnRtmpState OBJECT-TYPE
                  SYNTAX INTEGER {
                      good(1),
                      suspect(2),
                      goingBad(3),
                      bad(4) -- may be removed from table
                  }
                  MAX-ACCESS read-only
                  STATUS current
                  DESCRIPTION
                      "The status of the information contained in this
                      route entry.

                      Setting this object to the value bad(4) has the
                      effect of invalidating the corresponding entry
                      in the rtmpTable.  That is, it  effectively
                      disassociates the mapping identified with said
                      entry.  It is an implementation-specific matter
                      as to whether the agent removes an invalidated
                      entry from the table.  Accordingly, management
                      stations must be prepared to receive from agents
                      tabular information corresponding to entries not
                      currently in use.  Proper interpretation of such
                      entries requires examination of the relevant
                      rtmpState object."
                  ::= { cjnRtmpEntry 5 }

          cjnRtmpOwner OBJECT-TYPE
                  SYNTAX INTEGER {
		  	local(1),
			static(2),
			remote(3)
		  }
                  MAX-ACCESS read-only
                  STATUS current
                  DESCRIPTION
                      "The Owner of this Route Entry."
                  ::= { cjnRtmpEntry 6 }

          cjnRtmpDescr OBJECT-TYPE
                  SYNTAX DisplayString
                  MAX-ACCESS read-only
                  STATUS current
                  DESCRIPTION
                      "A text string containing information about the
                      port used to forward to the next hop.  This string
		      is intended for presentation to a human; it must
		      not contain anything but printable ASCII characters."
                  ::= { cjnRtmpEntry 7 }

	  cjnRtmpRowStatus OBJECT-TYPE
                  SYNTAX RowStatus
                  MAX-ACCESS read-write
                  STATUS current
                  DESCRIPTION
                      "The status of this entry in the table.  Note the available states:
		active(1), -- Obviously Active on this interface.
		notInService(2) -- Configured on Interface but disabled.
		notReady(3), -- Interface entry NOT FULLY configured.
		createAndGo(4), -- NOT SUPPORTED.
		createAndWait(5)  
		or destroy(6) "
                  ::= { cjnRtmpEntry 8 }

-- APPLETALK (Apple Talk Phase II Routing) ZIP Group
--
	  cjnAtZip		OBJECT IDENTIFIER ::= { cjnAtalk 7 }

          cjnZipTable OBJECT-TYPE
                  SYNTAX SEQUENCE OF CjnZipEntry
                  MAX-ACCESS not-accessible
                  STATUS current
                  DESCRIPTION
                      "The table of zone information for reachable
                      AppleTalk networks."
                  ::= { cjnAtZip 1 }

          cjnZipEntry OBJECT-TYPE
                  SYNTAX CjnZipEntry
                  MAX-ACCESS not-accessible
                  STATUS current
                  DESCRIPTION
                      "An entry of zone information for a particular
                      zone and network combination."
                  INDEX { cjnZipZoneNetStart, cjnZipZoneIndex }
                  ::= { cjnZipTable 1 }

          CjnZipEntry ::= SEQUENCE {
                  cjnZipZoneIndex    INTEGER,
		  cjnZipZoneName     OCTET STRING,
                  cjnZipZoneNetStart INTEGER,
                  cjnZipZoneNetEnd   INTEGER
          }

          cjnZipZoneIndex OBJECT-TYPE
                  SYNTAX INTEGER
                  MAX-ACCESS read-only
                  STATUS current
                  DESCRIPTION
                      "An integer that is unique to the zipZoneName
                      that is present in this entry.  For any given
                      zone name, every zipEntry that has an equal zone
                      name will have the same zipZoneIndex."
                  ::= { cjnZipEntry 1 }

          cjnZipZoneName OBJECT-TYPE
                  SYNTAX OCTET STRING (SIZE(1..32))
                  MAX-ACCESS read-only
                  STATUS current
                  DESCRIPTION
                      "The ASCII zone name of this entry."
                  ::= { cjnZipEntry 2 }

          cjnZipZoneNetStart OBJECT-TYPE
                  SYNTAX INTEGER
                  MAX-ACCESS read-only
                  STATUS current
                  DESCRIPTION
                      "The network that starts the range for this
                      entry.  This address is a two octet DDP network
                      address in network byte order."
                  ::= { cjnZipEntry 3 }

          cjnZipZoneNetEnd OBJECT-TYPE
                  SYNTAX INTEGER
                  MAX-ACCESS read-only
                  STATUS current
                  DESCRIPTION
                      "The network that ends the range for this
                      entry.  This address is a two octet DDP network
                      address in network byte order.  If the network
                      to which this zip entry pertains is a Phase 1
                      network or a non-extended network, the value for
                      zipZoneNetEnd shall be two bytes of zero."
                  ::= { cjnZipEntry 4 }

-- APPLETALK (Apple Talk Phase II Routing) NBP Group
--

	  cjnAtNbp	  OBJECT IDENTIFIER ::= { cjnAtalk 8 }

          cjnNbpTable OBJECT-TYPE
                  SYNTAX SEQUENCE OF CjnNbpEntry
                  MAX-ACCESS not-accessible
                  STATUS current
                  DESCRIPTION
                      "The table of NBP services registered on this
                      entity."
                  ::= { cjnAtNbp 1 }

          cjnNbpEntry OBJECT-TYPE
                  SYNTAX CjnNbpEntry
                  MAX-ACCESS not-accessible
                  STATUS current
                  DESCRIPTION
                      "The description of an NBP service registered on
                      this entity."
                  INDEX { cjnNbpIndex }
                  ::= { cjnNbpTable  1 }

           CjnNbpEntry ::= SEQUENCE {
                  cjnNbpIndex        INTEGER,
                  cjnNbpObject       OCTET STRING,
                  cjnNbpType         OCTET STRING,
                  cjnNbpZone         OCTET STRING,
                  cjnNbpState        INTEGER
           }

          cjnNbpIndex OBJECT-TYPE
                  SYNTAX INTEGER
                  MAX-ACCESS read-only
                  STATUS current
                  DESCRIPTION
                      "The index of this NBP entry.  This value ranges
                      from 1 to the number of NBP entries currently
                      registered on this entity."
                  ::= { cjnNbpEntry 1 }

          cjnNbpObject OBJECT-TYPE
                  SYNTAX OCTET STRING (SIZE(1..32))
                  MAX-ACCESS read-only
                  STATUS current
                  DESCRIPTION
                      "The name of the service described by this entity."
                  ::= { cjnNbpEntry 2 }

          cjnNbpType OBJECT-TYPE
                  SYNTAX OCTET STRING (SIZE(1..32))
                  MAX-ACCESS read-only
                  STATUS current
                  DESCRIPTION
                      "The type of the service described by this entity."
                  ::= { cjnNbpEntry 3 }

          cjnNbpZone OBJECT-TYPE
                  SYNTAX OCTET STRING (SIZE(1..32))
                  MAX-ACCESS read-only
                  STATUS current
                  DESCRIPTION
                      "The zone the service described by this entity is registered in."
                  ::= { cjnNbpEntry 4 }

          cjnNbpState OBJECT-TYPE
                  SYNTAX INTEGER {
                          valid(1),
                          invalid(2)
                  }
                  MAX-ACCESS read-write
                  STATUS current
                  DESCRIPTION
                      "The state of this NBP entry.

                      Setting this object to the value invalid(2) has
                      the effect of invalidating the corresponding
                      entry in the nbpTable.  That is, it effectively
                      disassociates the mapping identified with said
                      entry.  It is an implementation-specific matter
                      as to whether the agent removes an invalidated
                      entry from the table.
                      Accordingly, management stations must be
                      prepared to receive from agents tabular
                      information corresponding to entries not
                      currently in use.  Proper interpretation of
                      such entries requires examination of the
                      relevant nbpState object."
                  ::= { cjnNbpEntry 5 }


-- APPLETALK (Apple Talk Phase II Routing) ATEcho Group
--
	  cjnAtEcho	OBJECT IDENTIFIER ::= { cjnAtalk 9 }

          cjnAtEchoRequests OBJECT-TYPE
                  SYNTAX INTEGER
                  MAX-ACCESS read-only
                  STATUS current
                  DESCRIPTION
                      "The number of AppleTalk echo requests received."
                  ::= { cjnAtEcho 1 }

          cjnAtEchoReplies OBJECT-TYPE
                  SYNTAX INTEGER
                  MAX-ACCESS read-only
                  STATUS current
                  DESCRIPTION
                      "The number of AppleTalk echo replies sent."
                  ::= { cjnAtEcho 2 }

          cjnAtEchoTimeouts OBJECT-TYPE
                  SYNTAX INTEGER
                  MAX-ACCESS read-only
                  STATUS current
                  DESCRIPTION
                      "The number of AppleTalk echo request timeouts."
                  ::= { cjnAtEcho 3 }

          cjnAtEchoSend OBJECT-TYPE
                  SYNTAX DdpAddress
                  MAX-ACCESS read-write
                  STATUS current
                  DESCRIPTION
                      "Causes an Apple Talk Echo Request to be sent to the
		      supplied Apple Talk Address."
                  ::= { cjnAtEcho 4 }

	  cjnAtEchoReset  OBJECT-TYPE
	      	SYNTAX  INTEGER {
			disable(1),
			enable(2)
			}	
		MAX-ACCESS read-write
		STATUS current
	        DESCRIPTION
		   "When set to the value enable (2) all Apple Talk Echo
		   Counters are reset to zero after which the value of
		   this MIB object returns to disable(1)"
	       	::= { cjnAtEcho 5 }

-- APPLETALK (Apple Talk Phase II Routing) Global Statistics Group
--
	cjnAtGblStatsGroup	OBJECT IDENTIFIER ::= { cjnAtalk 10 }

	cjnAtDdp		OBJECT IDENTIFIER ::= { cjnAtGblStatsGroup 1 }

          -- The DDP Group

          cjnDdpOutRequests OBJECT-TYPE
                  SYNTAX INTEGER
                  MAX-ACCESS read-write
                  STATUS current
                  DESCRIPTION
                      "The total number of DDP datagrams which were
                      supplied to DDP by local DDP clients in requests
                      for transmission.  Note that this counter does
                      not include any datagrams counted in
                      ddpForwRequests."
                  ::= { cjnAtDdp 1 }

          cjnDdpOutShorts OBJECT-TYPE
                  SYNTAX INTEGER
                  MAX-ACCESS read-write
                  STATUS current
                  DESCRIPTION
                      "The total number of short DDP datagrams which
                      were transmitted from this entity."
                  ::= { cjnAtDdp 2 }

          cjnDdpOutLongs OBJECT-TYPE
                  SYNTAX INTEGER
                  MAX-ACCESS read-write
                  STATUS current
                  DESCRIPTION
                      "The total number of long DDP datagrams which were
                      transmitted from this entity."
                  ::= { cjnAtDdp 3 }

          cjnDdpInReceives OBJECT-TYPE
                  SYNTAX INTEGER
                  MAX-ACCESS read-write
                  STATUS current
                  DESCRIPTION
                      "The total number of input datagrams received by
                      DDP, including those received in error."
                  ::= { cjnAtDdp 4 }

          cjnDdpForwRequests OBJECT-TYPE
                  SYNTAX INTEGER
                  MAX-ACCESS read-write
                  STATUS current
                  DESCRIPTION
                      "The number of input datagrams for which this
                      entity was not their final DDP destination, as
                      a result of which an attempt was made to find a
                      route to forward them to that final destination."
                  ::= { cjnAtDdp 5 }

          cjnDdpInLocalDatagrams OBJECT-TYPE
                  SYNTAX INTEGER
                  MAX-ACCESS read-write
                  STATUS current
                  DESCRIPTION
                      "The total number of input DDP datagrams for
                      which this entity was their final DDP
                      destination."
                  ::= { cjnAtDdp 6 }

          cjnDdpNoProtocolHandlers OBJECT-TYPE
                  SYNTAX INTEGER
                  MAX-ACCESS read-write
                  STATUS current
                  DESCRIPTION
                      "The total number of DDP datagrams addressed to
                      this entity that were addressed to an upper
                      layer protocol for which no protocol handler
                      existed."
                  ::= { cjnAtDdp 7 }

          cjnDdpOutNoRoutes OBJECT-TYPE
                  SYNTAX INTEGER
                  MAX-ACCESS read-write
                  STATUS current
                  DESCRIPTION
                      "The total number of DDP datagrams dropped
                      because a route could not be found to their
                      final destination."
                  ::= { cjnAtDdp 8 }

          cjnDdpTooShortErrors OBJECT-TYPE
                  SYNTAX INTEGER
                  MAX-ACCESS read-write
                  STATUS current
                  DESCRIPTION
                      "The total number of input DDP datagrams dropped
                      because the received data length was less than
                      the data length specified in the DDP header or
                      the received data length was less than the
                      length of the expected DDP header."
                  ::= { cjnAtDdp 9 }

          cjnDdpTooLongErrors OBJECT-TYPE
                  SYNTAX INTEGER
                  MAX-ACCESS read-write
                  STATUS current
                  DESCRIPTION
                      "The total number of input DDP datagrams dropped
                      because the received data length was greater
                      than the data length specified in the DDP header
                      or because they exceeded the maximum DDP
                      datagram size."
                  ::= { cjnAtDdp 10 }

          cjnDdpBroadcastErrors OBJECT-TYPE
                  SYNTAX INTEGER
                  MAX-ACCESS read-write
                  STATUS current
                  DESCRIPTION
                      "The total number of input DDP datagrams dropped
                      because this entity was not their final
                      destination and they were addressed to the link
                      level broadcast."
                  ::= { cjnAtDdp 11 }

          cjnDdpShortDDPErrors OBJECT-TYPE
                  SYNTAX INTEGER
                  MAX-ACCESS read-write
                  STATUS current
                  DESCRIPTION
                      "The total number of input DDP datagrams dropped
                      because this entity was not their final
                      destination and their type was short DDP."
                  ::= { cjnAtDdp 12 }

          cjnDdpHopCountErrors OBJECT-TYPE
                  SYNTAX INTEGER
                  MAX-ACCESS read-write
                  STATUS current
                  DESCRIPTION
                      "The total number of input DDP datagrams dropped
                      because this entity was not their final
                      destination and their hop count would exceed 15."
                  ::= { cjnAtDdp 13 }

          cjnDdpChecksumErrors OBJECT-TYPE
                  SYNTAX INTEGER
                  MAX-ACCESS read-write
                  STATUS current
                  DESCRIPTION
                      "The total number of input DDP datagrams dropped
                      because of a checksum error."
                  ::= { cjnAtDdp 14 }

          cjnDdpAarpRqRcv OBJECT-TYPE
                  SYNTAX INTEGER
                  MAX-ACCESS read-write
                  STATUS current
                  DESCRIPTION
                      "The total number of input AARP Requests Received."
                  ::= { cjnAtDdp 15 }

          cjnDdpAarpReplyRcv OBJECT-TYPE
                  SYNTAX INTEGER
                  MAX-ACCESS read-write
                  STATUS current
                  DESCRIPTION
                      "The total number of input AARP Replies Received."
                  ::= { cjnAtDdp 16 }

          cjnDdpAarpRqTx OBJECT-TYPE
                  SYNTAX INTEGER
                  MAX-ACCESS read-write
                  STATUS current
                  DESCRIPTION
                      "The total number of output AARP Requests Transmitted."
                  ::= { cjnAtDdp 17 }

          cjnDdpAarpReplyTx OBJECT-TYPE
                  SYNTAX INTEGER
                  MAX-ACCESS read-write
                  STATUS current
                  DESCRIPTION
                      "The total number of output AARP Replies Transmitted."
                  ::= { cjnAtDdp 18 }

          cjnDdpAarpBadPdu OBJECT-TYPE
                  SYNTAX INTEGER
                  MAX-ACCESS read-write
                  STATUS current
                  DESCRIPTION
                      "The total number of bad AARP PDU."
                  ::= { cjnAtDdp 19 }

          cjnDdpCfgAddrError OBJECT-TYPE
                  SYNTAX INTEGER
                  MAX-ACCESS read-write
                  STATUS current
                  DESCRIPTION
                      "The total number of configuration address errors."
                  ::= { cjnAtDdp 20 }

          cjnDdpCfgZoneError OBJECT-TYPE
                  SYNTAX INTEGER
                  MAX-ACCESS read-write
                  STATUS current
                  DESCRIPTION
                      "The total number of configuration zone errors."
                  ::= { cjnAtDdp 21 }

          cjnDdpEchoRqRcv OBJECT-TYPE
                  SYNTAX INTEGER
                  MAX-ACCESS read-write
                  STATUS current
                  DESCRIPTION
                      "The total number of input Echo Requests Received."
                  ::= { cjnAtDdp 22 }

          cjnDdpEchoReplyRcv OBJECT-TYPE
                  SYNTAX INTEGER
                  MAX-ACCESS read-write
                  STATUS current
                  DESCRIPTION
                      "The total number of input Echo Replies Received."
                  ::= { cjnAtDdp 23 }

          cjnDdpEchoRqTx OBJECT-TYPE
                  SYNTAX INTEGER
                  MAX-ACCESS read-write
                  STATUS current
                  DESCRIPTION
                      "The total number of output Echo Requests Transmitted."
                  ::= { cjnAtDdp 24 }

 



-- APPLETALK (Apple Talk Phase II Routing) Port Group
--

	cjnAtPortConfGroup		OBJECT IDENTIFIER ::= { cjnAtalk 11 }

          cjnAtPortNextIndex OBJECT-TYPE
                  SYNTAX INTEGER 
                  MAX-ACCESS read-only
                  STATUS current
                  DESCRIPTION
                      "The next cjnAtPortIndex to be used for row creation."
                  ::= { cjnAtPortConfGroup 1 }


          cjnAtPortTable OBJECT-TYPE
                  SYNTAX SEQUENCE OF CjnAtPortEntry
                  MAX-ACCESS not-accessible
                  STATUS current
                  DESCRIPTION
                      "A list of Cajun AppleTalk ports for this entity."
                  ::= { cjnAtPortConfGroup 2 }

          cjnAtPortEntry OBJECT-TYPE
                  SYNTAX CjnAtPortEntry
                  MAX-ACCESS not-accessible
                  STATUS current
                  DESCRIPTION
                      "The description of one of the Cajun AppleTalk
                      ports on this entity."
                  INDEX { cjnAtPortIndex }
                  ::= { cjnAtPortTable 1 }

          CjnAtPortEntry ::= SEQUENCE {
                  cjnAtPortIndex               INTEGER,		--
		  cjnAtPortRowStatus	       RowStatus,	-- 
                  cjnAtPortDescr               DisplayString,	-- Text Name
		  cjnAtPortMetric	       INTEGER,		-- Metric
		  cjnAtPortFrameType	       INTEGER,		-- Frame Type
                  cjnAtPortNetStart            INTEGER,		-- Begin
                  cjnAtPortNetEnd              INTEGER,		-- End
                  cjnAtPortNetAddress          DdpAddress,	-- NetNum.Node
                  cjnAtPortAdminState          INTEGER,		-- Admin State
                  cjnAtPortIfIndex             INTEGER,		-- IfIndex
		  cjnAtPortVlan		       DisplayString,   -- VLAN
	 	  cjnAtPortClearZones          INTEGER          -- Clear Zones
          }

          cjnAtPortIndex OBJECT-TYPE
                  SYNTAX INTEGER
                  MAX-ACCESS read-only
                  STATUS current
                  DESCRIPTION
                      "A unique value for each AppleTalk port.
                      Its value is between 1 and the total number of
                      AppleTalk ports.  The value for each port must
                      remain constant at least from the
                      re-initialization of the entity's network
                      management system to the next
                      re-initialization."
                  ::= { cjnAtPortEntry 1 }

	cjnAtPortRowStatus OBJECT-TYPE
              SYNTAX  RowStatus	
              MAX-ACCESS  read-create
              STATUS  current
              DESCRIPTION
                      "The Status of this entry in the table.  Note the
		available states: 
		active(1), -- Obviously Active on this interface.
		notInService(2) -- Configured on Interface but disabled.
		notReady(3), -- Interface entry NOT FULLY configured.
		createAndGo(4), -- NOT SUPPORTED.
		createAndWait(5)  
		or destroy(6) "
	      ::= { cjnAtPortEntry 2 }

          cjnAtPortDescr OBJECT-TYPE
                  SYNTAX DisplayString(SIZE(1..32))
                  MAX-ACCESS read-create
                  STATUS current
                  DESCRIPTION
                      "A text string containing information about the
                      port.  This string is intended for presentation
                      to a human; it must not contain anything but
                      printable ASCII characters."
                  ::= { cjnAtPortEntry 3 }

          cjnAtPortMetric OBJECT-TYPE
                  SYNTAX INTEGER
                  MAX-ACCESS read-create
                  STATUS current
                  DESCRIPTION
                      "The metric assigned to this port."
		  DEFVAL {1}
                  ::= { cjnAtPortEntry 4 }

          cjnAtPortFrameType OBJECT-TYPE
                  SYNTAX INTEGER {
		  	snap(1),
			ethernet2 (2)
		  }
                  MAX-ACCESS read-create
                  STATUS current
                  DESCRIPTION
                      "The type of Ethernet Frames to be used by the port
		      for Apple Talk."
		  DEFVAL {1}
                  ::= { cjnAtPortEntry 5 }

          cjnAtPortNetStart OBJECT-TYPE
                  SYNTAX INTEGER (0..65279)
                  MAX-ACCESS read-create
                  STATUS current
                  DESCRIPTION
                      "The first AppleTalk network address in the range
                      configured for this port.  This is a two octet
                      DDP network address in network byte order."
		  DEFVAL {0}
                  ::= { cjnAtPortEntry 6 }

          cjnAtPortNetEnd OBJECT-TYPE
                  SYNTAX INTEGER (0..65279)
                  MAX-ACCESS read-create
                  STATUS current
                  DESCRIPTION
                      "The last AppleTalk network address in the range
                      configured for this port.  This is a two octet
                      DDP network address in network byte order.  If the
                      network to which this AppleTalk port is
                      connected is a Phase 1 network or a non-extended
                      network, the value for atportNetEnd shall be two
                      octets of zero."
		  DEFVAL {0}
                  ::= { cjnAtPortEntry 7 }

          cjnAtPortNetAddress OBJECT-TYPE
                  SYNTAX DdpAddress
                  MAX-ACCESS read-create
                  STATUS current
                  DESCRIPTION
                      "The AppleTalk network address configured for this port."
		  DEFVAL {"000000"}
                  ::= { cjnAtPortEntry 8 }

          cjnAtPortAdminState OBJECT-TYPE
                  SYNTAX INTEGER {
                       enabled(1),
                       disabled(2)
                  }
                  MAX-ACCESS read-create
                  STATUS current
                  DESCRIPTION
                      "The configuration status of this port."
                  ::= { cjnAtPortEntry 9 }

          cjnAtPortIfIndex OBJECT-TYPE
                  SYNTAX INTEGER
                  MAX-ACCESS read-only
                  STATUS current
                  DESCRIPTION
                      "The physical interface associated with this
		      Appletalk port. The interface identified by a 
		      particular value of this index is the same 
		      interface as identified by the same value of ifIndex."
                  ::= { cjnAtPortEntry 10 }

          cjnAtPortVlan OBJECT-TYPE
                  SYNTAX DisplayString (SIZE(1..32))
                  MAX-ACCESS read-create
                  STATUS current
                  DESCRIPTION
                      "The vlan associated with this AppleTalk port."
                  ::= { cjnAtPortEntry 11 }

          cjnAtPortClearZones OBJECT-TYPE
                  SYNTAX INTEGER {
                       enabled(1),
                       disabled(2)
		  }
                  MAX-ACCESS read-create
                  STATUS current
                  DESCRIPTION
                      "set to enabled will clear all zones on this at port."
                  ::= { cjnAtPortEntry 12 }

-- APPLETALK (Apple Talk Phase II Routing) Interface State Group
--

	cjnAtPortStateGroup		OBJECT IDENTIFIER ::= { cjnAtalk 12 }

	cjnAtPortStateTable OBJECT-TYPE
           SYNTAX  SEQUENCE OF CjnAtPortStateEntry
           MAX-ACCESS  not-accessible
           STATUS  current
           DESCRIPTION
           "A list of interface specific Apple Talk Port State Entries"
	   ::= {cjnAtPortStateGroup 3 }

	cjnAtPortStateEntry OBJECT-TYPE
	   SYNTAX  CjnAtPortStateEntry
           MAX-ACCESS  not-accessible
           STATUS  current
           DESCRIPTION
           "An cajun Apple Talk Port State instance"
           INDEX   { cjnAtPortStateIndex }
           ::= { cjnAtPortStateTable 1 }

	CjnAtPortStateEntry ::= SEQUENCE {
		cjnAtPortStateIndex		INTEGER,	--
		cjnAtPortStateDescr		DisplayString,	-- Text Name
		cjnAtPortStateNetConfig		INTEGER,	-- Seed
		cjnAtPortStateNetStart		INTEGER,	-- Begin
		cjnAtPortStateNetEnd		INTEGER,	-- End
		cjnAtPortStateNetAddress	DdpAddress,	-- NetNum.Node
		cjnAtPortStateState		INTEGER		-- State
		}
		
	cjnAtPortStateIndex OBJECT-TYPE
              SYNTAX  INTEGER
	      MAX-ACCESS  read-only
              STATUS  current
              DESCRIPTION
		"The globally unique value for this Apple Talk Port.
		This number MUST exist in the cjnIpIfTable ?? to be valid."
	      ::= { cjnAtPortStateEntry 1 } 

          cjnAtPortStateDescr OBJECT-TYPE
	      SYNTAX DisplayString
	      MAX-ACCESS read-only
	      STATUS current
	      DESCRIPTION
		  "A text string containing information about the port.
		  This string is intended for presentation to a human; it 
		  must not contain anything but printable ASCII characters."
                  ::= { cjnAtPortStateEntry 2 }

          cjnAtPortStateNetConfig OBJECT-TYPE
                  SYNTAX INTEGER {
                      configured(1),  -- explicit configuration.
                      garnered(2),    -- assumed from inspection of net.
                      guessed(3),     -- a "random" configuration.
                      unconfigured(4)
                  }
                  MAX-ACCESS read-only
                  STATUS current
                  DESCRIPTION
                      "The configuration status of this port."
                  ::= { cjnAtPortStateEntry 3 }

          cjnAtPortStateNetStart OBJECT-TYPE
                  SYNTAX INTEGER
                  MAX-ACCESS read-only
                  STATUS current
                  DESCRIPTION
                      "The first AppleTalk network address in the range
                      currently used for this port.  This is a two octet
                      DDP network address in network byte order."
                  ::= { cjnAtPortStateEntry 4 }

          cjnAtPortStateNetEnd OBJECT-TYPE
                  SYNTAX INTEGER
                  MAX-ACCESS read-only
                  STATUS current
                  DESCRIPTION
                      "The last AppleTalk network address in the range
                      currently used for this port.  This is a two octet
                      DDP network address in network byte order.  If the
                      network to which this AppleTalk port is
                      connected is a Phase 1 network or a non-extended
                      network, the value for atportNetEnd shall be two
                      octets of zero."
                  ::= { cjnAtPortStateEntry 5 }

          cjnAtPortStateNetAddress OBJECT-TYPE
                  SYNTAX DdpAddress
                  MAX-ACCESS read-only
                  STATUS current
                  DESCRIPTION
                      "The AppleTalk network address being used on this port."
                  ::= { cjnAtPortStateEntry 6 }

          cjnAtPortStateState OBJECT-TYPE
                  SYNTAX INTEGER {
                      down(1),
                      up(2)
                  }
                  MAX-ACCESS read-only
                  STATUS current
                  DESCRIPTION
                      "The operational status of this port."
                  ::= { cjnAtPortStateEntry 7 }


-- APPLETALK (Apple Talk Phase II Routing) Filter Group
--

	cjnAtFilterGroup	OBJECT IDENTIFIER ::= { cjnAtalk 13 }

          cjnAtFilterTable OBJECT-TYPE
                  SYNTAX SEQUENCE OF CjnAtFilterEntry
                  MAX-ACCESS not-accessible
                  STATUS current
                  DESCRIPTION
                      "A list of Apple Talk Filters for this entity."
                  ::= { cjnAtFilterGroup 1 }

          cjnAtFilterEntry OBJECT-TYPE
                  SYNTAX CjnAtFilterEntry
                  MAX-ACCESS not-accessible
                  STATUS current
                  DESCRIPTION
                      "The Filters defined."
                  INDEX { cjnAtFilterIndex }
                  ::= { cjnAtFilterTable 1 }

          CjnAtFilterEntry ::= SEQUENCE {
	  	  cjnAtFilterIndex	INTEGER,
                  cjnAtFilterRowStatus	RowStatus,
                  cjnAtFilterItem	INTEGER,
		  cjnAtFilterOperation	INTEGER,
                  cjnAtFilterString	OCTET STRING
          }

          cjnAtFilterIndex OBJECT-TYPE
                  SYNTAX INTEGER
                  MAX-ACCESS read-only
                  STATUS current
                  DESCRIPTION
                      "An integer that is unique to the Filter that is present in this
		      entry."
                  ::= { cjnAtFilterEntry 1 }

	  cjnAtFilterRowStatus OBJECT-TYPE
                  SYNTAX RowStatus
                  MAX-ACCESS read-create
                  STATUS current
                  DESCRIPTION
                      "The status of this entry in the table.  Note the available states:
		      active(1), -- Obviously Active on this interface.
		      notInService(2) -- Configured on Interface but disabled.
		      notReady(3), -- Interface entry NOT FULLY configured.
		      createAndGo(4), -- NOT SUPPORTED.
		      createAndWait(5)  
		      or destroy(6) "
                  ::= { cjnAtFilterEntry 2 }

	  cjnAtFilterItem  OBJECT-TYPE
	      	SYNTAX  INTEGER {
			zoneName(1),
			nbpObject(2)
		}	
	  	MAX-ACCESS read-create
		STATUS current
		DESCRIPTION
		    "When set to the value zone_name(1) this filter applies to zone names.
		    When set to nbp_object(2), this filter applies to nbp object names."
		::= { cjnAtFilterEntry 3 }

	  cjnAtFilterOperation  OBJECT-TYPE
	      	SYNTAX  INTEGER {
			permit(1),
			deny(2)
		}	
	  	MAX-ACCESS read-create
		STATUS current
		DESCRIPTION
		    "When set to the value permit(1) objects with this name 
		    will not be filtered.  When set to no(2), objects with this name
		    will be filtered."
		DEFVAL {2}
		::= { cjnAtFilterEntry 4 }

          cjnAtFilterString OBJECT-TYPE
                  SYNTAX OCTET STRING (SIZE(1..32))
                  MAX-ACCESS read-create
                  STATUS current
                  DESCRIPTION
                      "The ASCII name of the entry to be filtered.
		      When FilterItem is zone_name(1), string is the name of the zone to
		      be filtered.  When FilterItem is nbp_object(2), string is the name
		      of the nbp object to be filtered."
                  ::= { cjnAtFilterEntry 5 }



-- APPLETALK (Apple Talk Phase II Routing) Access List to Interface Group
--

	cjnAtAccessIfGroup	OBJECT IDENTIFIER ::= { cjnAtalk 14 }

          cjnAtAccessIfTable OBJECT-TYPE
                  SYNTAX SEQUENCE OF CjnAtAccessIfEntry
                  MAX-ACCESS not-accessible
                  STATUS current
                  DESCRIPTION
                      "A list of Apple Talk Filters on Apple Talk Interfaces."
                  ::= { cjnAtAccessIfGroup 1 }

          cjnAtAccessIfEntry OBJECT-TYPE
                  SYNTAX CjnAtAccessIfEntry
                  MAX-ACCESS not-accessible
                  STATUS current
                  DESCRIPTION
                      "The Zone Filters defined."
                  INDEX { cjnAtFilterIndex, cjnAtPortIndex }
                  ::= { cjnAtAccessIfTable 1 }

          CjnAtAccessIfEntry ::= SEQUENCE {
                  cjnAtAccessIfRowStatus	RowStatus
          }

	  cjnAtAccessIfRowStatus OBJECT-TYPE
                  SYNTAX RowStatus
                  MAX-ACCESS read-create
                  STATUS current
                  DESCRIPTION
                      "The status of this entry in the table.  Note the available states:
		      active(1), -- Obviously Active on this interface.
		      notInService(2) -- Configured on Interface but disabled.
		      notReady(3), -- Interface entry NOT FULLY configured.
		      createAndGo(4), -- NOT SUPPORTED.
		      createAndWait(5)  
		      or destroy(6) "
                  ::= { cjnAtAccessIfEntry 1 }

END
