PVC-TRAP-MIB DEFINITIONS ::= BEGIN


-- Copyright 1999 Nortel Networks, Inc.
-- All rights reserved.
-- This Nortel Networks SNMP Management Information Base Specification
-- (Specification) embodies Nortel Networks' confidential and
-- proprietary intellectual property. Nortel Networks retains all
-- title and ownership in the Specification, including any
-- revisions.

-- This Specification is supplied "AS IS," and Nortel Networks makes
-- no warranty, either express or implied, as to the use,
-- operation, condition, or performance of the Specification.


-- Imports

IMPORTS
    TRAP-TYPE    FROM RFC-1215
    cnPvcTraps   FROM CENTILLION-ROOT-MIB
    atmPortCardIndex, atmPortPortIndex
                 FROM CENTILLION-ATMCFG-MIB
    atmPvcCktId  FROM CENTILLION-ATMMON-MIB;

-- SECTION 2: PVC traps definitions

remotePvcDown  TRAP-TYPE
    ENTERPRISE      cnPvcTraps
    VARIABLES       { atmPortCardIndex,
                      atmPortPortIndex,
                      atmPvcCktId
                      }
--  STATUS      mandatory
    DESCRIPTION
        " This trap is sent when a CLC PVC goes down
          i.e. the RemotePvcStatus indicator is set to
          down.
            atmPortCardIndex.........the ATM card id.
            atmPortPortIndex.........the ATM port id.
            atmPvcCktId..............the PVC ckt id."
 ::= 1

END


-- SECTION 1: Top Level Definitions
