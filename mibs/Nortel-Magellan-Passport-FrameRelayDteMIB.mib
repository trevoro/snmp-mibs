Nortel-Magellan-Passport-FrameRelayDteMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      PassportCounter64,
      InterfaceIndex,
      Gauge32,
      Integer32,
      Unsigned32
   FROM Nortel-Magellan-Passport-StandardTextualConventionsMIB

      DashedHexString,
      NonReplicated,
      HexString,
      EnterpriseDateAndTime,
      Link
   FROM Nortel-Magellan-Passport-TextualConventionsMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayDte Enterprise MIB."

frameRelayDteMIB OBJECT IDENTIFIER ::= { passportMIBs 32 }










-- FrameRelayDte/n
-- The FrameRelayDte component defines the general parameters for 
-- implementing the Frame Relay DTE interface.

frDte OBJECT IDENTIFIER ::= { components 101 }



frDteRowStatusTable OBJECT-TYPE
   SYNTAX     SEQUENCE OF FrDteRowStatusEntry
   ACCESS     not-accessible
   STATUS     mandatory
   DESCRIPTION
     "This entry controls the addition and deletion of 
      frDte components."
::= { frDte 1 }

frDteRowStatusEntry OBJECT-TYPE
   SYNTAX     FrDteRowStatusEntry
   ACCESS     not-accessible
   STATUS     mandatory
   DESCRIPTION
     "A single entry in the table represents a single 
      frDte component."
   INDEX {
      frDteIndex }
::= { frDteRowStatusTable 1 }

FrDteRowStatusEntry ::= SEQUENCE {
   frDteRowStatus
      RowStatus,
   frDteComponentName
      DisplayString,
   frDteStorageType
      StorageType,
   frDteIndex
      Integer32 }

frDteRowStatus OBJECT-TYPE
   SYNTAX     RowStatus 
   ACCESS     read-write
   STATUS     mandatory
   DESCRIPTION
     "This variable is used as the basis for SNMP naming of
      frDte components.
      These components can be added and deleted."
::= { frDteRowStatusEntry 1 }

frDteComponentName OBJECT-TYPE
   SYNTAX     DisplayString 
   ACCESS     read-only
   STATUS     mandatory
   DESCRIPTION
     "This variable provides the component's string name for
      use with the ASCII Console Interface"
::= { frDteRowStatusEntry 2 }

frDteStorageType OBJECT-TYPE
   SYNTAX     StorageType 
   ACCESS     read-only
   STATUS     mandatory
   DESCRIPTION
     "This variable represents the storage type value for the
      frDte tables."
::= { frDteRowStatusEntry 4 }

frDteIndex OBJECT-TYPE
   SYNTAX     Integer32 (1..65535)
   ACCESS     not-accessible
   STATUS     mandatory
   DESCRIPTION
     "This variable represents the index for the frDte tables."
::= { frDteRowStatusEntry 10 }

frDteCidDataTable OBJECT-TYPE
   SYNTAX     SEQUENCE OF FrDteCidDataEntry
   ACCESS     not-accessible
   STATUS     mandatory
   DESCRIPTION
     "This group contains the attribute for a component's Customer 
      Identifier (CID). Refer to the attribute description for a detailed 
      explanation of CIDs."
::= { frDte 20 }

frDteCidDataEntry OBJECT-TYPE
   SYNTAX     FrDteCidDataEntry
   ACCESS     not-accessible
   STATUS     mandatory
   DESCRIPTION
     "An entry in the frDteCidDataTable."
   INDEX {
      frDteIndex }
::= { frDteCidDataTable 1 }

FrDteCidDataEntry ::= SEQUENCE {
   frDteCustomerIdentifier
      Unsigned32 }

frDteCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { frDteCidDataEntry 1 }

frDteIfEntryTable OBJECT-TYPE
   SYNTAX     SEQUENCE OF FrDteIfEntryEntry
   ACCESS     not-accessible
   STATUS     mandatory
   DESCRIPTION
     "This group contains the provisionable attributes for the ifEntry."
::= { frDte 21 }

frDteIfEntryEntry OBJECT-TYPE
   SYNTAX     FrDteIfEntryEntry
   ACCESS     not-accessible
   STATUS     mandatory
   DESCRIPTION
     "An entry in the frDteIfEntryTable."
   INDEX {
      frDteIndex }
::= { frDteIfEntryTable 1 }

FrDteIfEntryEntry ::= SEQUENCE {
   frDteIfAdminStatus
      INTEGER,
   frDteIfIndex
      InterfaceIndex }

frDteIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { frDteIfEntryEntry 1 }

frDteIfIndex OBJECT-TYPE
   SYNTAX     InterfaceIndex (1..65535)
   ACCESS     read-only
   STATUS     mandatory
   DESCRIPTION
     "This is the index for the IfEntry. Its value is automatically initialized 
      during the provisioning process."
::= { frDteIfEntryEntry 2 }

frDteProvTable OBJECT-TYPE
   SYNTAX     SEQUENCE OF FrDteProvEntry
   ACCESS     not-accessible
   STATUS     mandatory
   DESCRIPTION
     "This group contains the provisioned attributes for the FrDte component."
::= { frDte 22 }

frDteProvEntry OBJECT-TYPE
   SYNTAX     FrDteProvEntry
   ACCESS     not-accessible
   STATUS     mandatory
   DESCRIPTION
     "An entry in the frDteProvTable."
   INDEX {
      frDteIndex }
::= { frDteProvTable 1 }

FrDteProvEntry ::= SEQUENCE {
   frDteAcceptUndefinedDlci
      INTEGER }

frDteAcceptUndefinedDlci OBJECT-TYPE
   SYNTAX     INTEGER  {
                 enabled(1),
                 disabled(2) }
   ACCESS     read-write
   STATUS     mandatory
   DESCRIPTION
     "This parameter allows previously undefined Data Link Connection 
      Identifiers (DLCIs) to be dynamically accepted in the default remote 
      group. If set to enabled, undefined DLCIs will be accepted, if disabled, 
      they will not."
   DEFVAL     { enabled }
::= { frDteProvEntry 1 }

frDteStateTable OBJECT-TYPE
   SYNTAX     SEQUENCE OF FrDteStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frDte 23 }

frDteStateEntry OBJECT-TYPE
   SYNTAX     FrDteStateEntry
   ACCESS     not-accessible
   STATUS     mandatory
   DESCRIPTION
     "An entry in the frDteStateTable."
   INDEX {
      frDteIndex }
::= { frDteStateTable 1 }

FrDteStateEntry ::= SEQUENCE {
   frDteAdminState
      INTEGER,
   frDteOperationalState
      INTEGER,
   frDteUsageState
      INTEGER }

frDteAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frDteStateEntry 1 }

frDteOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frDteStateEntry 2 }

frDteUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frDteStateEntry 3 }

frDteOperStatusTable OBJECT-TYPE
   SYNTAX     SEQUENCE OF FrDteOperStatusEntry
   ACCESS     not-accessible
   STATUS     mandatory
   DESCRIPTION
     "This group includes the Operational Status attribute. This attribute 
      defines the current operational state of this component."
::= { frDte 24 }

frDteOperStatusEntry OBJECT-TYPE
   SYNTAX     FrDteOperStatusEntry
   ACCESS     not-accessible
   STATUS     mandatory
   DESCRIPTION
     "An entry in the frDteOperStatusTable."
   INDEX {
      frDteIndex }
::= { frDteOperStatusTable 1 }

FrDteOperStatusEntry ::= SEQUENCE {
   frDteSnmpOperStatus
      INTEGER }

frDteSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { frDteOperStatusEntry 1 }

frDteOperTable OBJECT-TYPE
   SYNTAX     SEQUENCE OF FrDteOperEntry
   ACCESS     not-accessible
   STATUS     mandatory
   DESCRIPTION
     "This group contains the operational attributes for the FrDte component."
::= { frDte 25 }

frDteOperEntry OBJECT-TYPE
   SYNTAX     FrDteOperEntry
   ACCESS     not-accessible
   STATUS     mandatory
   DESCRIPTION
     "An entry in the frDteOperTable."
   INDEX {
      frDteIndex }
::= { frDteOperTable 1 }

FrDteOperEntry ::= SEQUENCE {
   frDteLinkOperState
      INTEGER }

frDteLinkOperState OBJECT-TYPE
   SYNTAX     INTEGER  {
                 active(1),
                 down(2),
                 polling(3) }
   ACCESS     read-only
   STATUS     mandatory
   DESCRIPTION
     "This attribute describes the operational state of the Link Control 
      protocol. If the interface to the physical link hardware is inactive, the 
      linkOperState is in the down state. 
      
      The polling state only occurs when the Local Management Interface 
      (LMI) is enabled and the physical link is active. The polling state 
      indicates LMI is polling for its peer. Once communication is established 
      the linkOperState will transition to the active state. 
      
      If the procedure attribute of the Lmi component is set to none, 
      linkOperState will transition to the active state once the physical link 
      becomes active."
   DEFVAL     { down }
::= { frDteOperEntry 1 }

frDteErrTable OBJECT-TYPE
   SYNTAX     SEQUENCE OF FrDteErrEntry
   ACCESS     not-accessible
   STATUS     mandatory
   DESCRIPTION
     "This group contains the SNMP frErrEntry attributes for the FrDte 
      component."
::= { frDte 26 }

frDteErrEntry OBJECT-TYPE
   SYNTAX     FrDteErrEntry
   ACCESS     not-accessible
   STATUS     mandatory
   DESCRIPTION
     "An entry in the frDteErrTable."
   INDEX {
      frDteIndex }
::= { frDteErrTable 1 }

FrDteErrEntry ::= SEQUENCE {
   frDteErrType
      INTEGER,
   frDteErrData
      HexString,
   frDteErrTime
      EnterpriseDateAndTime,
   frDteErrDiscards
      Counter32,
   frDteErrFaults
      Counter32,
   frDteErrFaultTime
      EnterpriseDateAndTime }

frDteErrType OBJECT-TYPE
   SYNTAX     INTEGER  {
                 unknownError(1),
                 receiveShort(2),
                 receiveLong(3),
                 illegalDlci(4),
                 dlcmiProtoErr(5),
                 dlcmiUnknownIe(6),
                 dlcmiSequenceErr(7),
                 dlcmiUnknownRpt(8),
                 noErrorSinceReset(9) }
   ACCESS     read-only
   STATUS     mandatory
   DESCRIPTION
     "The type of error that was last seen on this interface. The error types are 
      as follows:
      
      receiveShort: This error indicates a received frame was discarded 
      because it was less than four octets long or it was missing the 
      Organizationally Unique Identifier (OUI) for a SNAP header.
      
      receiveLong: This error indicates a received frame was discarded 
      because it was longer than expected. This error is currently not used on 
      this interface.
      
      illegalDlci: This error indicates that a received frame was discarded 
      because it's Q.922 address was not two octets in length. This error could 
      also indicate that a frame was discarded because it was received on a 
      DLCI reserved for LMI which had not been provisioned active.
      
      dlcmiProtoErr: This error indicates an LMI frame was received with 
      contents formatted incorrectly.
      
      dlcmiUnknownIe: This error indicates that an LMI frame was received 
      which contained an unsupported Information Element (IE) type
      
      dlcmiSequenceErr: This error indicates that an LMI frame was received 
      whose Keep Alive Sequence was incorrect.
      
      dlcmiUnknownRpt: This error indicates that an LMI frame was received 
      which contained a Report-type Information Element with an invalid type 
      of report.
      
      noErrorSinceReset: This error type indicates that there has not been an 
      error since the interface has been reset.
      
      unknownError: This error type contains the cumulation of receive 
      frame errors that did not fit one of the MIB error descriptions above. 
      These errors include those counted by the following attributes:
      
      ulpUnknownProtocol - A received frame was discarded because the 
      Upper Level Protocol (ULP) encapsulation used was unsupported.
      
      badFc - A received frame was discarded because the frame control 
      character was incorrect.
      
      defragSequenceErrors - A fragment was received which was discarded 
      due to an out of sequence error detection."
   DEFVAL     { noErrorSinceReset }
::= { frDteErrEntry 2 }

frDteErrData OBJECT-TYPE
   SYNTAX     HexString (SIZE (64))
   ACCESS     read-only
   STATUS     mandatory
   DESCRIPTION
     "An octet string containing the first part of the frame in which an error 
      was last detected."
::= { frDteErrEntry 3 }

frDteErrTime OBJECT-TYPE
   SYNTAX     EnterpriseDateAndTime (SIZE (0 | 19))
   ACCESS     read-only
   STATUS     mandatory
   DESCRIPTION
     "The time at which the last error was detected and recorded in errType."
::= { frDteErrEntry 4 }

frDteErrDiscards OBJECT-TYPE
   SYNTAX     Counter32 
   ACCESS     read-only
   STATUS     mandatory
   DESCRIPTION
     "Number of inbound frames dropped because of format errors or because 
      the virtual circuit was not known. Format errors, in this case, are any 
      errors which would prevent the system from recognizing the DLCI and 
      placing the error in the discard category.
      
      This counter will wrap around to 0 when it exceeds its maximum count."
::= { frDteErrEntry 6 }

frDteErrFaults OBJECT-TYPE
   SYNTAX     Counter32 
   ACCESS     read-only
   STATUS     mandatory
   DESCRIPTION
     "This attribute counts the number of times LMI has taken down the 
      interface. When the procedure attribute of the Lmi component is set to 
      none, this counter will not be incremented.
      
      This counter will wrap around to 0 when it exceeds its maximum count."
::= { frDteErrEntry 7 }

frDteErrFaultTime OBJECT-TYPE
   SYNTAX     EnterpriseDateAndTime (SIZE (0 | 19))
   ACCESS     read-only
   STATUS     mandatory
   DESCRIPTION
     "The last time the errFaults counter was incremented."
::= { frDteErrEntry 8 }

frDteErrStatsTable OBJECT-TYPE
   SYNTAX     SEQUENCE OF FrDteErrStatsEntry
   ACCESS     not-accessible
   STATUS     mandatory
   DESCRIPTION
     "This group contains error counters for the FrDte."
::= { frDte 27 }

frDteErrStatsEntry OBJECT-TYPE
   SYNTAX     FrDteErrStatsEntry
   ACCESS     not-accessible
   STATUS     mandatory
   DESCRIPTION
     "An entry in the frDteErrStatsTable."
   INDEX {
      frDteIndex }
::= { frDteErrStatsTable 1 }

FrDteErrStatsEntry ::= SEQUENCE {
   frDteXmitDiscardPvcDown
      Counter32,
   frDteXmitDiscardLmiInactive
      Counter32,
   frDteXmitDiscardFramerDown
      Counter32,
   frDteXmitDiscardPvcInactive
      Counter32,
   frDteXmitDiscardCirExceeded
      Counter32,
   frDteRecvDiscardPvcDown
      Counter32,
   frDteRecvDiscardLmiInactive
      Counter32,
   frDteRecvDiscardPvcInactive
      Counter32,
   frDteBadFc
      Counter32,
   frDteUlpUnknownProtocol
      Counter32,
   frDteDefragSequenceErrors
      Counter32,
   frDteReceiveShort
      Counter32,
   frDteIllegalDlci
      Counter32,
   frDteDlcmiProtoErr
      Counter32,
   frDteDlcmiUnknownIe
      Counter32,
   frDteDlcmiSequenceErr
      Counter32,
   frDteDlcmiUnknownRpt
      Counter32 }

frDteXmitDiscardPvcDown OBJECT-TYPE
   SYNTAX     Counter32 
   ACCESS     read-only
   STATUS     mandatory
   DESCRIPTION
     "Count of transmitted frames discarded because the Dlci or a component 
      positioned in a hierarchically fashion above it (e.g. it's remote group or 
      the FrDte component) was administratively disabled.
      
      This counter will wrap around to 0 when it exceeds its maximum count."
::= { frDteErrStatsEntry 1 }

frDteXmitDiscardLmiInactive OBJECT-TYPE
   SYNTAX     Counter32 
   ACCESS     read-only
   STATUS     mandatory
   DESCRIPTION
     "Count of transmitted frames discarded because the Local Management 
      Interface (LMI) was not yet active (i.e. LMI was still in the polling 
      state).
      
      This counter will wrap around to 0 when it exceeds its maximum count."
::= { frDteErrStatsEntry 2 }

frDteXmitDiscardFramerDown OBJECT-TYPE
   SYNTAX     Counter32 
   ACCESS     read-only
   STATUS     mandatory
   DESCRIPTION
     "Count of transmitted frames discarded because the framer component 
      was down.
      
      This counter will wrap around to 0 when it exceeds its maximum count."
::= { frDteErrStatsEntry 3 }

frDteXmitDiscardPvcInactive OBJECT-TYPE
   SYNTAX     Counter32 
   ACCESS     read-only
   STATUS     mandatory
   DESCRIPTION
     "Count of transmitted frames discarded because the Local Management 
      Interface (LMI) had inactivated or invalidated the Dlci.
      
      This counter will wrap around to 0 when it exceeds its maximum count."
::= { frDteErrStatsEntry 4 }

frDteXmitDiscardCirExceeded OBJECT-TYPE
   SYNTAX     Counter32 
   ACCESS     read-only
   STATUS     mandatory
   DESCRIPTION
     "Count of transmitted frames discarded because CIR was enabled on a 
      Dlci without a HibernationQueue subcomponent and the traffic 
      exceeded the combined Committed and Excess Burst thresholds.
      
      This counter will wrap around to 0 when it exceeds its maximum count."
::= { frDteErrStatsEntry 5 }

frDteRecvDiscardPvcDown OBJECT-TYPE
   SYNTAX     Counter32 
   ACCESS     read-only
   STATUS     mandatory
   DESCRIPTION
     "Count of received frames discarded because the Dlci or a component 
      positioned in a hierarchically fashion above it (e.g. it's remote group or 
      the FrDte component) was administratively disabled.
      
      This counter will wrap around to 0 when it exceeds its maximum count."
::= { frDteErrStatsEntry 6 }

frDteRecvDiscardLmiInactive OBJECT-TYPE
   SYNTAX     Counter32 
   ACCESS     read-only
   STATUS     mandatory
   DESCRIPTION
     "Count of received frames discarded because the Local Management 
      Interface (LMI) was not yet active (i.e. LMI was still in the polling 
      state).
      
      This counter will wrap around to 0 when it exceeds its maximum count."
::= { frDteErrStatsEntry 7 }

frDteRecvDiscardPvcInactive OBJECT-TYPE
   SYNTAX     Counter32 
   ACCESS     read-only
   STATUS     mandatory
   DESCRIPTION
     "Count of received frames discarded because the Local Management 
      Interface (LMI) had inactivated or invalidated the Dlci.
      
      This counter will wrap around to 0 when it exceeds its maximum count."
::= { frDteErrStatsEntry 8 }

frDteBadFc OBJECT-TYPE
   SYNTAX     Counter32 
   ACCESS     read-only
   STATUS     mandatory
   DESCRIPTION
     "Count of received frames discarded because the frame control character 
      was incorrect. This may indicate that the other side of the link is 
      configured for a different link level protocol.
      
      This counter will wrap around to 0 when it exceeds its maximum count."
::= { frDteErrStatsEntry 9 }

frDteUlpUnknownProtocol OBJECT-TYPE
   SYNTAX     Counter32 
   ACCESS     read-only
   STATUS     mandatory
   DESCRIPTION
     "Count of received frames discarded because the Upper Level Protocol 
      (ULP) encapsulation used was unsupported.
      
      This counter will wrap around to 0 when it exceeds its maximum count."
::= { frDteErrStatsEntry 10 }

frDteDefragSequenceErrors OBJECT-TYPE
   SYNTAX     Counter32 
   ACCESS     read-only
   STATUS     mandatory
   DESCRIPTION
     "Count of fragments received which were discarded due to out of 
      sequence error detection.
      
      This counter will wrap around to 0 when it exceeds its maximum count."
::= { frDteErrStatsEntry 11 }

frDteReceiveShort OBJECT-TYPE
   SYNTAX     Counter32 
   ACCESS     read-only
   STATUS     mandatory
   DESCRIPTION
     "Count of received frames (including LMI frames) discarded because 
      they were less than four octets long or they were missing the 
      Organizationally Unique Identifier (OUI) for a SNAP header.
      
      This counter will wrap around to 0 when it exceeds its maximum count."
::= { frDteErrStatsEntry 12 }

frDteIllegalDlci OBJECT-TYPE
   SYNTAX     Counter32 
   ACCESS     read-only
   STATUS     mandatory
   DESCRIPTION
     "Count of received frames discarded because their Q.922 address was not 
      two octets in length. This count also includes frames discarded because 
      they were received on a Dlci reserved for LMI which had not been 
      provisioned active.
      
      This counter will wrap around to 0 when it exceeds its maximum count."
::= { frDteErrStatsEntry 13 }

frDteDlcmiProtoErr OBJECT-TYPE
   SYNTAX     Counter32 
   ACCESS     read-only
   STATUS     mandatory
   DESCRIPTION
     "Count of received LMI frames whose contents were formatted 
      incorrectly.
      
      This counter will wrap around to 0 when it exceeds its maximum count."
::= { frDteErrStatsEntry 14 }

frDteDlcmiUnknownIe OBJECT-TYPE
   SYNTAX     Counter32 
   ACCESS     read-only
   STATUS     mandatory
   DESCRIPTION
     "Count of received LMI frames which contained an unsupported 
      Information Element (IE) type.
      
      This counter will wrap around to 0 when it exceeds its maximum count."
::= { frDteErrStatsEntry 15 }

frDteDlcmiSequenceErr OBJECT-TYPE
   SYNTAX     Counter32 
   ACCESS     read-only
   STATUS     mandatory
   DESCRIPTION
     "Count of received LMI frames whose Keep Alive Sequence was 
      incorrect.
      
      This counter will wrap around to 0 when it exceeds its maximum count."
::= { frDteErrStatsEntry 16 }

frDteDlcmiUnknownRpt OBJECT-TYPE
   SYNTAX     Counter32 
   ACCESS     read-only
   STATUS     mandatory
   DESCRIPTION
     "Count of received LMI frames which contained a Report-type 
      Information Element with an invalid type of report.
      
      This counter will wrap around to 0 when it exceeds its maximum count."
::= { frDteErrStatsEntry 17 }


-- 
-- FrDte/n Framer
-- 
-- The Framer component controls link layer framing for application 
-- components sending and receiving data on a link interface. It is also 
-- through Framer, that an application component is associated with a 
-- specific hardware link interface.
-- 
-- The Framer component provides provisional attributes related to 
-- datapath aspects of the hardware interface (such as crc and frame length) 
-- rather than interface specific attributes (such as modem leads and 
-- clocking) which are associated with specific hardware components (such 
-- as V35/n or DS1/n). The Framer component also provides a provisional 
-- attribute which binds the application component to a specific hardware 
-- component.
-- 
-- The Framer component contains operational attributes for link interface 
-- datapath statistics (such as frame counts and aborts).
-- 

frDteFramer OBJECT IDENTIFIER ::= { frDte 2 }



frDteFramerRowStatusTable OBJECT-TYPE
   SYNTAX     SEQUENCE OF FrDteFramerRowStatusEntry
   ACCESS     not-accessible
   STATUS     mandatory
   DESCRIPTION
     "This entry controls the addition and deletion of 
      frDteFramer components."
::= { frDteFramer 1 }

frDteFramerRowStatusEntry OBJECT-TYPE
   SYNTAX     FrDteFramerRowStatusEntry
   ACCESS     not-accessible
   STATUS     mandatory
   DESCRIPTION
     "A single entry in the table represents a single 
      frDteFramer component."
   INDEX {
      frDteIndex,
      frDteFramerIndex }
::= { frDteFramerRowStatusTable 1 }

FrDteFramerRowStatusEntry ::= SEQUENCE {
   frDteFramerRowStatus
      RowStatus,
   frDteFramerComponentName
      DisplayString,
   frDteFramerStorageType
      StorageType,
   frDteFramerIndex
      NonReplicated }

frDteFramerRowStatus OBJECT-TYPE
   SYNTAX     RowStatus 
   ACCESS     read-write
   STATUS     mandatory
   DESCRIPTION
     "This variable is used as the basis for SNMP naming of
      frDteFramer components.
      These components can be added and deleted."
::= { frDteFramerRowStatusEntry 1 }

frDteFramerComponentName OBJECT-TYPE
   SYNTAX     DisplayString 
   ACCESS     read-only
   STATUS     mandatory
   DESCRIPTION
     "This variable provides the component's string name for
      use with the ASCII Console Interface"
::= { frDteFramerRowStatusEntry 2 }

frDteFramerStorageType OBJECT-TYPE
   SYNTAX     StorageType 
   ACCESS     read-only
   STATUS     mandatory
   DESCRIPTION
     "This variable represents the storage type value for the
      frDteFramer tables."
::= { frDteFramerRowStatusEntry 4 }

frDteFramerIndex OBJECT-TYPE
   SYNTAX     NonReplicated 
   ACCESS     not-accessible
   STATUS     mandatory
   DESCRIPTION
     "This variable represents the index for the frDteFramer tables."
::= { frDteFramerRowStatusEntry 10 }

frDteFramerProvTable OBJECT-TYPE
   SYNTAX     SEQUENCE OF FrDteFramerProvEntry
   ACCESS     not-accessible
   STATUS     mandatory
   DESCRIPTION
     "This group contains the base provisioning data for the Framer 
      component. Application or hardware interface specific provisioning data 
      is contained in other provisional Framer groups."
::= { frDteFramer 10 }

frDteFramerProvEntry OBJECT-TYPE
   SYNTAX     FrDteFramerProvEntry
   ACCESS     not-accessible
   STATUS     mandatory
   DESCRIPTION
     "An entry in the frDteFramerProvTable."
   INDEX {
      frDteIndex,
      frDteFramerIndex }
::= { frDteFramerProvTable 1 }

FrDteFramerProvEntry ::= SEQUENCE {
   frDteFramerInterfaceName
      Link }

frDteFramerInterfaceName OBJECT-TYPE
   SYNTAX     Link 
   ACCESS     read-write
   STATUS     mandatory
   DESCRIPTION
     "This attribute contains a hardware component name.
      
      The attribute associates the application with a specific link. This defines 
      the module processor on which Framer's parent component (as well as 
      Framer itself) will run."
::= { frDteFramerProvEntry 1 }

frDteFramerStateTable OBJECT-TYPE
   SYNTAX     SEQUENCE OF FrDteFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frDteFramer 12 }

frDteFramerStateEntry OBJECT-TYPE
   SYNTAX     FrDteFramerStateEntry
   ACCESS     not-accessible
   STATUS     mandatory
   DESCRIPTION
     "An entry in the frDteFramerStateTable."
   INDEX {
      frDteIndex,
      frDteFramerIndex }
::= { frDteFramerStateTable 1 }

FrDteFramerStateEntry ::= SEQUENCE {
   frDteFramerAdminState
      INTEGER,
   frDteFramerOperationalState
      INTEGER,
   frDteFramerUsageState
      INTEGER }

frDteFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frDteFramerStateEntry 1 }

frDteFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frDteFramerStateEntry 2 }

frDteFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frDteFramerStateEntry 3 }

frDteFramerStatsTable OBJECT-TYPE
   SYNTAX     SEQUENCE OF FrDteFramerStatsEntry
   ACCESS     not-accessible
   STATUS     mandatory
   DESCRIPTION
     "This group contains the operational statistics data for a Framer 
      component."
::= { frDteFramer 13 }

frDteFramerStatsEntry OBJECT-TYPE
   SYNTAX     FrDteFramerStatsEntry
   ACCESS     not-accessible
   STATUS     mandatory
   DESCRIPTION
     "An entry in the frDteFramerStatsTable."
   INDEX {
      frDteIndex,
      frDteFramerIndex }
::= { frDteFramerStatsTable 1 }

FrDteFramerStatsEntry ::= SEQUENCE {
   frDteFramerFrmToIf
      Counter32,
   frDteFramerFrmFromIf
      Counter32,
   frDteFramerAborts
      Counter32,
   frDteFramerCrcErrors
      Counter32,
   frDteFramerLrcErrors
      Counter32,
   frDteFramerNonOctetErrors
      Counter32,
   frDteFramerOverruns
      Counter32,
   frDteFramerUnderruns
      Counter32,
   frDteFramerLargeFrmErrors
      Counter32 }

frDteFramerFrmToIf OBJECT-TYPE
   SYNTAX     Counter32 
   ACCESS     read-only
   STATUS     mandatory
   DESCRIPTION
     "This attribute counts the number of frames transmitted to the link 
      interface by Framer.
      
      Note: This does not include the number of frames transmitted directly to 
      the hardware queue, thus bypassing the Framer component."
::= { frDteFramerStatsEntry 1 }

frDteFramerFrmFromIf OBJECT-TYPE
   SYNTAX     Counter32 
   ACCESS     read-only
   STATUS     mandatory
   DESCRIPTION
     "This attribute counts the number of frames received from the link 
      interface by Framer."
::= { frDteFramerStatsEntry 2 }

frDteFramerAborts OBJECT-TYPE
   SYNTAX     Counter32 
   ACCESS     read-only
   STATUS     mandatory
   DESCRIPTION
     "This attribute counts the total number of aborts received."
::= { frDteFramerStatsEntry 3 }

frDteFramerCrcErrors OBJECT-TYPE
   SYNTAX     Counter32 
   ACCESS     read-only
   STATUS     mandatory
   DESCRIPTION
     "This attribute counts the total number of frames with CRC errors."
::= { frDteFramerStatsEntry 4 }

frDteFramerLrcErrors OBJECT-TYPE
   SYNTAX     Counter32 
   ACCESS     read-only
   STATUS     mandatory
   DESCRIPTION
     "This attribute counts the total number of frames with LRC errors."
::= { frDteFramerStatsEntry 5 }

frDteFramerNonOctetErrors OBJECT-TYPE
   SYNTAX     Counter32 
   ACCESS     read-only
   STATUS     mandatory
   DESCRIPTION
     "This attribute counts the total number of frames that were non octet 
      aligned."
::= { frDteFramerStatsEntry 6 }

frDteFramerOverruns OBJECT-TYPE
   SYNTAX     Counter32 
   ACCESS     read-only
   STATUS     mandatory
   DESCRIPTION
     "This attribute counts the total number of frames received from the link 
      for which overruns occurred."
::= { frDteFramerStatsEntry 7 }

frDteFramerUnderruns OBJECT-TYPE
   SYNTAX     Counter32 
   ACCESS     read-only
   STATUS     mandatory
   DESCRIPTION
     "This attribute counts the total number of frames transmitted to the link 
      for which underruns occurred."
::= { frDteFramerStatsEntry 8 }

frDteFramerLargeFrmErrors OBJECT-TYPE
   SYNTAX     Counter32 
   ACCESS     read-only
   STATUS     mandatory
   DESCRIPTION
     "This attribute counts the total number of frames received which were too 
      large. The frame exceeded the maximumFrameLengthLimit 
      provisioned attribute or it contained more than the 255 block hardware 
      limit."
::= { frDteFramerStatsEntry 9 }

frDteFramerUtilTable OBJECT-TYPE
   SYNTAX     SEQUENCE OF FrDteFramerUtilEntry
   ACCESS     not-accessible
   STATUS     mandatory
   DESCRIPTION
     "This group contains the link utilization operational data for a Framer 
      component."
::= { frDteFramer 14 }

frDteFramerUtilEntry OBJECT-TYPE
   SYNTAX     FrDteFramerUtilEntry
   ACCESS     not-accessible
   STATUS     mandatory
   DESCRIPTION
     "An entry in the frDteFramerUtilTable."
   INDEX {
      frDteIndex,
      frDteFramerIndex }
::= { frDteFramerUtilTable 1 }

FrDteFramerUtilEntry ::= SEQUENCE {
   frDteFramerNormPrioLinkUtilToIf
      Gauge32,
   frDteFramerNormPrioLinkUtilFromIf
      Gauge32 }

frDteFramerNormPrioLinkUtilToIf OBJECT-TYPE
   SYNTAX     Gauge32 (0..100)
   ACCESS     read-only
   STATUS     mandatory
   DESCRIPTION
     "This attribute is the utilization of the normal priority data sent to the link 
      as a percentage of the available bandwidth on the link. The utilization is 
      the average for the last minute."
   DEFVAL     { 0 }
::= { frDteFramerUtilEntry 1 }

frDteFramerNormPrioLinkUtilFromIf OBJECT-TYPE
   SYNTAX     Gauge32 (0..100)
   ACCESS     read-only
   STATUS     mandatory
   DESCRIPTION
     "This attribute is the utilization of the normal priority data received from 
      the link as a percentage of the available bandwidth on the link. The 
      utilization is the average for the last minute."
   DEFVAL     { 0 }
::= { frDteFramerUtilEntry 3 }


-- FrDte/n Lmi
-- This component defines parameters for implementing the Local 
-- Management Interface (LMI) protocol for the FrDte interface.

frDteLmi OBJECT IDENTIFIER ::= { frDte 3 }



frDteLmiRowStatusTable OBJECT-TYPE
   SYNTAX     SEQUENCE OF FrDteLmiRowStatusEntry
   ACCESS     not-accessible
   STATUS     mandatory
   DESCRIPTION
     "This entry controls the addition and deletion of 
      frDteLmi components."
::= { frDteLmi 1 }

frDteLmiRowStatusEntry OBJECT-TYPE
   SYNTAX     FrDteLmiRowStatusEntry
   ACCESS     not-accessible
   STATUS     mandatory
   DESCRIPTION
     "A single entry in the table represents a single 
      frDteLmi component."
   INDEX {
      frDteIndex,
      frDteLmiIndex }
::= { frDteLmiRowStatusTable 1 }

FrDteLmiRowStatusEntry ::= SEQUENCE {
   frDteLmiRowStatus
      RowStatus,
   frDteLmiComponentName
      DisplayString,
   frDteLmiStorageType
      StorageType,
   frDteLmiIndex
      NonReplicated }

frDteLmiRowStatus OBJECT-TYPE
   SYNTAX     RowStatus 
   ACCESS     read-only
   STATUS     mandatory
   DESCRIPTION
     "This variable is used as the basis for SNMP naming of
      frDteLmi components.
      These components cannot be added nor deleted."
::= { frDteLmiRowStatusEntry 1 }

frDteLmiComponentName OBJECT-TYPE
   SYNTAX     DisplayString 
   ACCESS     read-only
   STATUS     mandatory
   DESCRIPTION
     "This variable provides the component's string name for
      use with the ASCII Console Interface"
::= { frDteLmiRowStatusEntry 2 }

frDteLmiStorageType OBJECT-TYPE
   SYNTAX     StorageType 
   ACCESS     read-only
   STATUS     mandatory
   DESCRIPTION
     "This variable represents the storage type value for the
      frDteLmi tables."
::= { frDteLmiRowStatusEntry 4 }

frDteLmiIndex OBJECT-TYPE
   SYNTAX     NonReplicated 
   ACCESS     not-accessible
   STATUS     mandatory
   DESCRIPTION
     "This variable represents the index for the frDteLmi tables."
::= { frDteLmiRowStatusEntry 10 }

frDteLmiProvTable OBJECT-TYPE
   SYNTAX     SEQUENCE OF FrDteLmiProvEntry
   ACCESS     not-accessible
   STATUS     mandatory
   DESCRIPTION
     "This group contains the provisioned attributes for the Lmi component."
::= { frDteLmi 10 }

frDteLmiProvEntry OBJECT-TYPE
   SYNTAX     FrDteLmiProvEntry
   ACCESS     not-accessible
   STATUS     mandatory
   DESCRIPTION
     "An entry in the frDteLmiProvTable."
   INDEX {
      frDteIndex,
      frDteLmiIndex }
::= { frDteLmiProvTable 1 }

FrDteLmiProvEntry ::= SEQUENCE {
   frDteLmiProcedures
      INTEGER,
   frDteLmiPollingInterval
      Unsigned32,
   frDteLmiFullEnquiryInterval
      Unsigned32,
   frDteLmiErrorThreshold
      Unsigned32,
   frDteLmiMonitoredEvents
      Unsigned32 }

frDteLmiProcedures OBJECT-TYPE
   SYNTAX     INTEGER  {
                 none(1),
                 vendorForum(2),
                 ansi(3),
                 itu(5) }
   ACCESS     read-write
   STATUS     mandatory
   DESCRIPTION
     "This attribute selects the Local Management Interface (LMI) protocol to 
      be used on the interface. This attribute is equivalent to the SNMP 
      variable frDlcmiState. The vendorForum LMI protocol automatically 
      implies that the DLCI used by the protocol is 1023. The ansi (T1.617 
      Annex D) and itu (ITU-T Recommendation Q.933 Annex A) LMI 
      protocols use DLCI 0. If none is selected, no LMI procedures will run 
      on the interface. Note that the ITU-T Recommendation Q.933 was 
      previously a CCITT recommendation."
   DEFVAL     { itu }
::= { frDteLmiProvEntry 1 }

frDteLmiPollingInterval OBJECT-TYPE
   SYNTAX     Unsigned32 (5..30)
   ACCESS     read-write
   STATUS     mandatory
   DESCRIPTION
     "This is the number of seconds between successive status enquiry 
      messages. This field corresponds to the parameter T391 described in the 
      ANSI T1.617-1991 Annex D."
   DEFVAL     { 10 }
::= { frDteLmiProvEntry 4 }

frDteLmiFullEnquiryInterval OBJECT-TYPE
   SYNTAX     Unsigned32 (1..255)
   ACCESS     read-write
   STATUS     mandatory
   DESCRIPTION
     "The count of status polls before a full status enquiry message is issued. 
      Every nth poll will request a full status. This field corresponds to the 
      parameter N391 described in the ANSI T1.617-1991 Annex D."
   DEFVAL     { 6 }
::= { frDteLmiProvEntry 5 }

frDteLmiErrorThreshold OBJECT-TYPE
   SYNTAX     Unsigned32 (1..10)
   ACCESS     read-write
   STATUS     mandatory
   DESCRIPTION
     "The number of errors detected within the monitored events window 
      before declaring the link non-functional. This field corresponds to the 
      parameter N392 described in the ANSI T1.617-1991 Annex D."
   DEFVAL     { 3 }
::= { frDteLmiProvEntry 6 }

frDteLmiMonitoredEvents OBJECT-TYPE
   SYNTAX     Unsigned32 (1..10)
   ACCESS     read-write
   STATUS     mandatory
   DESCRIPTION
     "The number of status polling intervals over which the errorthreshold is 
      counted This is used to determine if the errorThreshold is exceeded. 
      This field corresponds to the parameter N393 described in the ANSI 
      T1.617-1991 Annex D."
   DEFVAL     { 4 }
::= { frDteLmiProvEntry 7 }

frDteLmiOperTable OBJECT-TYPE
   SYNTAX     SEQUENCE OF FrDteLmiOperEntry
   ACCESS     not-accessible
   STATUS     mandatory
   DESCRIPTION
     "This group contains the operational attributes for the Lmi component."
::= { frDteLmi 11 }

frDteLmiOperEntry OBJECT-TYPE
   SYNTAX     FrDteLmiOperEntry
   ACCESS     not-accessible
   STATUS     mandatory
   DESCRIPTION
     "An entry in the frDteLmiOperTable."
   INDEX {
      frDteIndex,
      frDteLmiIndex }
::= { frDteLmiOperTable 1 }

FrDteLmiOperEntry ::= SEQUENCE {
   frDteLmiLmiStatus
      INTEGER }

frDteLmiLmiStatus OBJECT-TYPE
   SYNTAX     INTEGER  {
                 running(1),
                 fault(2),
                 initializing(3) }
   ACCESS     read-only
   STATUS     mandatory
   DESCRIPTION
     "This indicates the status of the Frame Relay interface as determined by 
      the performance of the link management interface (LMI). If no LMI is 
      running, lmiStatus will stay in the running state indefinitely."
::= { frDteLmiOperEntry 2 }


-- FrDte/n Rg/n
-- 
-- This component describes the links between a group of Dlcis and a 
-- Protocol Port.
-- 
-- The Rg/1 instance is required.

frDteRg OBJECT IDENTIFIER ::= { frDte 4 }



frDteRgRowStatusTable OBJECT-TYPE
   SYNTAX     SEQUENCE OF FrDteRgRowStatusEntry
   ACCESS     not-accessible
   STATUS     mandatory
   DESCRIPTION
     "This entry controls the addition and deletion of 
      frDteRg components."
::= { frDteRg 1 }

frDteRgRowStatusEntry OBJECT-TYPE
   SYNTAX     FrDteRgRowStatusEntry
   ACCESS     not-accessible
   STATUS     mandatory
   DESCRIPTION
     "A single entry in the table represents a single 
      frDteRg component."
   INDEX {
      frDteIndex,
      frDteRgIndex }
::= { frDteRgRowStatusTable 1 }

FrDteRgRowStatusEntry ::= SEQUENCE {
   frDteRgRowStatus
      RowStatus,
   frDteRgComponentName
      DisplayString,
   frDteRgStorageType
      StorageType,
   frDteRgIndex
      Integer32 }

frDteRgRowStatus OBJECT-TYPE
   SYNTAX     RowStatus 
   ACCESS     read-write
   STATUS     mandatory
   DESCRIPTION
     "This variable is used as the basis for SNMP naming of
      frDteRg components.
      These components can be added and deleted."
::= { frDteRgRowStatusEntry 1 }

frDteRgComponentName OBJECT-TYPE
   SYNTAX     DisplayString 
   ACCESS     read-only
   STATUS     mandatory
   DESCRIPTION
     "This variable provides the component's string name for
      use with the ASCII Console Interface"
::= { frDteRgRowStatusEntry 2 }

frDteRgStorageType OBJECT-TYPE
   SYNTAX     StorageType 
   ACCESS     read-only
   STATUS     mandatory
   DESCRIPTION
     "This variable represents the storage type value for the
      frDteRg tables."
::= { frDteRgRowStatusEntry 4 }

frDteRgIndex OBJECT-TYPE
   SYNTAX     Integer32 (1..256)
   ACCESS     not-accessible
   STATUS     mandatory
   DESCRIPTION
     "This variable represents the index for the frDteRg tables."
::= { frDteRgRowStatusEntry 10 }

frDteRgIfEntryTable OBJECT-TYPE
   SYNTAX     SEQUENCE OF FrDteRgIfEntryEntry
   ACCESS     not-accessible
   STATUS     mandatory
   DESCRIPTION
     "This group contains the provisionable attributes for the ifEntry."
::= { frDteRg 10 }

frDteRgIfEntryEntry OBJECT-TYPE
   SYNTAX     FrDteRgIfEntryEntry
   ACCESS     not-accessible
   STATUS     mandatory
   DESCRIPTION
     "An entry in the frDteRgIfEntryTable."
   INDEX {
      frDteIndex,
      frDteRgIndex }
::= { frDteRgIfEntryTable 1 }

FrDteRgIfEntryEntry ::= SEQUENCE {
   frDteRgIfAdminStatus
      INTEGER,
   frDteRgIfIndex
      InterfaceIndex }

frDteRgIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { frDteRgIfEntryEntry 1 }

frDteRgIfIndex OBJECT-TYPE
   SYNTAX     InterfaceIndex (1..65535)
   ACCESS     read-only
   STATUS     mandatory
   DESCRIPTION
     "This is the index for the IfEntry. Its value is automatically initialized 
      during the provisioning process."
::= { frDteRgIfEntryEntry 2 }

frDteRgProvTable OBJECT-TYPE
   SYNTAX     SEQUENCE OF FrDteRgProvEntry
   ACCESS     not-accessible
   STATUS     mandatory
   DESCRIPTION
     "This group contains the provisioned attributes for the Remote Group 
      component."
::= { frDteRg 11 }

frDteRgProvEntry OBJECT-TYPE
   SYNTAX     FrDteRgProvEntry
   ACCESS     not-accessible
   STATUS     mandatory
   DESCRIPTION
     "An entry in the frDteRgProvTable."
   INDEX {
      frDteIndex,
      frDteRgIndex }
::= { frDteRgProvTable 1 }

FrDteRgProvEntry ::= SEQUENCE {
   frDteRgMaxTransmissionUnit
      Unsigned32 }

frDteRgMaxTransmissionUnit OBJECT-TYPE
   SYNTAX     Unsigned32 (262..9190)
   ACCESS     read-write
   STATUS     mandatory
   DESCRIPTION
     "The Maximum Transmission Unit size of the largest datagram 
      (including Frame Relay header) which can be sent on the interface."
   DEFVAL     { 1604 }
::= { frDteRgProvEntry 1 }

frDteRgMpTable OBJECT-TYPE
   SYNTAX     SEQUENCE OF FrDteRgMpEntry
   ACCESS     not-accessible
   STATUS     mandatory
   DESCRIPTION
     "This group contains the base provisioning data for the Media 
      Application component."
::= { frDteRg 12 }

frDteRgMpEntry OBJECT-TYPE
   SYNTAX     FrDteRgMpEntry
   ACCESS     not-accessible
   STATUS     mandatory
   DESCRIPTION
     "An entry in the frDteRgMpTable."
   INDEX {
      frDteIndex,
      frDteRgIndex }
::= { frDteRgMpTable 1 }

FrDteRgMpEntry ::= SEQUENCE {
   frDteRgLinkToProtocolPort
      Link }

frDteRgLinkToProtocolPort OBJECT-TYPE
   SYNTAX     Link 
   ACCESS     read-write
   STATUS     mandatory
   DESCRIPTION
     "This attribute contains a protocol port component name. The attribute 
      associates the application with a protocol port."
::= { frDteRgMpEntry 1 }

frDteRgStateTable OBJECT-TYPE
   SYNTAX     SEQUENCE OF FrDteRgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frDteRg 13 }

frDteRgStateEntry OBJECT-TYPE
   SYNTAX     FrDteRgStateEntry
   ACCESS     not-accessible
   STATUS     mandatory
   DESCRIPTION
     "An entry in the frDteRgStateTable."
   INDEX {
      frDteIndex,
      frDteRgIndex }
::= { frDteRgStateTable 1 }

FrDteRgStateEntry ::= SEQUENCE {
   frDteRgAdminState
      INTEGER,
   frDteRgOperationalState
      INTEGER,
   frDteRgUsageState
      INTEGER }

frDteRgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frDteRgStateEntry 1 }

frDteRgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frDteRgStateEntry 2 }

frDteRgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frDteRgStateEntry 3 }

frDteRgOperStatusTable OBJECT-TYPE
   SYNTAX     SEQUENCE OF FrDteRgOperStatusEntry
   ACCESS     not-accessible
   STATUS     mandatory
   DESCRIPTION
     "This group includes the Operational Status attribute. This attribute 
      defines the current operational state of this component."
::= { frDteRg 14 }

frDteRgOperStatusEntry OBJECT-TYPE
   SYNTAX     FrDteRgOperStatusEntry
   ACCESS     not-accessible
   STATUS     mandatory
   DESCRIPTION
     "An entry in the frDteRgOperStatusTable."
   INDEX {
      frDteIndex,
      frDteRgIndex }
::= { frDteRgOperStatusTable 1 }

FrDteRgOperStatusEntry ::= SEQUENCE {
   frDteRgSnmpOperStatus
      INTEGER }

frDteRgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { frDteRgOperStatusEntry 1 }

frDteRgLtDlciTable OBJECT-TYPE
   SYNTAX     SEQUENCE OF FrDteRgLtDlciEntry
   ACCESS     not-accessible
   STATUS     mandatory
   DESCRIPTION
     "This attribute associates a Rg component with zero or more StDlci 
      components. The Rg and StDlci components must be under the same 
      FrDte component."
::= { frDteRg 219 }

frDteRgLtDlciEntry OBJECT-TYPE
   SYNTAX     FrDteRgLtDlciEntry
   ACCESS     not-accessible
   STATUS     mandatory
   DESCRIPTION
     "An entry in the frDteRgLtDlciTable."
   INDEX {
      frDteIndex,
      frDteRgIndex,
      frDteRgLtDlciValue }
::= { frDteRgLtDlciTable 1 }

FrDteRgLtDlciEntry ::= SEQUENCE {
   frDteRgLtDlciValue
      Link,
   frDteRgLtDlciRowStatus
      RowStatus }

frDteRgLtDlciValue OBJECT-TYPE
   SYNTAX     Link 
   ACCESS     read-write
   STATUS     mandatory
   DESCRIPTION
     "This variable represents both the value and the index for the
      frDteRgLtDlciTable."
::= { frDteRgLtDlciEntry 1 }

frDteRgLtDlciRowStatus OBJECT-TYPE
   SYNTAX     RowStatus 
   ACCESS     write-only
   STATUS     mandatory
   DESCRIPTION
     "This variable is used to control the addition and deletion 
      of individual values of the frDteRgLtDlciTable."
::= { frDteRgLtDlciEntry 2 }


-- 
-- FrDte/n Rg/n Bridged Frame Routing
-- 
-- The BridgedFrameRouting component defines the parameters for 
-- implementing the Bridged Frame Routing port.

frDteRgBfr OBJECT IDENTIFIER ::= { frDteRg 15 }



frDteRgBfrRowStatusTable OBJECT-TYPE
   SYNTAX     SEQUENCE OF FrDteRgBfrRowStatusEntry
   ACCESS     not-accessible
   STATUS     mandatory
   DESCRIPTION
     "This entry controls the addition and deletion of 
      frDteRgBfr components."
::= { frDteRgBfr 1 }

frDteRgBfrRowStatusEntry OBJECT-TYPE
   SYNTAX     FrDteRgBfrRowStatusEntry
   ACCESS     not-accessible
   STATUS     mandatory
   DESCRIPTION
     "A single entry in the table represents a single 
      frDteRgBfr component."
   INDEX {
      frDteIndex,
      frDteRgIndex,
      frDteRgBfrIndex }
::= { frDteRgBfrRowStatusTable 1 }

FrDteRgBfrRowStatusEntry ::= SEQUENCE {
   frDteRgBfrRowStatus
      RowStatus,
   frDteRgBfrComponentName
      DisplayString,
   frDteRgBfrStorageType
      StorageType,
   frDteRgBfrIndex
      NonReplicated }

frDteRgBfrRowStatus OBJECT-TYPE
   SYNTAX     RowStatus 
   ACCESS     read-write
   STATUS     mandatory
   DESCRIPTION
     "This variable is used as the basis for SNMP naming of
      frDteRgBfr components.
      These components can be added and deleted."
::= { frDteRgBfrRowStatusEntry 1 }

frDteRgBfrComponentName OBJECT-TYPE
   SYNTAX     DisplayString 
   ACCESS     read-only
   STATUS     mandatory
   DESCRIPTION
     "This variable provides the component's string name for
      use with the ASCII Console Interface"
::= { frDteRgBfrRowStatusEntry 2 }

frDteRgBfrStorageType OBJECT-TYPE
   SYNTAX     StorageType 
   ACCESS     read-only
   STATUS     mandatory
   DESCRIPTION
     "This variable represents the storage type value for the
      frDteRgBfr tables."
::= { frDteRgBfrRowStatusEntry 4 }

frDteRgBfrIndex OBJECT-TYPE
   SYNTAX     NonReplicated 
   ACCESS     not-accessible
   STATUS     mandatory
   DESCRIPTION
     "This variable represents the index for the frDteRgBfr tables."
::= { frDteRgBfrRowStatusEntry 10 }

frDteRgBfrProvTable OBJECT-TYPE
   SYNTAX     SEQUENCE OF FrDteRgBfrProvEntry
   ACCESS     not-accessible
   STATUS     mandatory
   DESCRIPTION
     "This group contains the provisioning attributes for the Bfr component."
::= { frDteRgBfr 10 }

frDteRgBfrProvEntry OBJECT-TYPE
   SYNTAX     FrDteRgBfrProvEntry
   ACCESS     not-accessible
   STATUS     mandatory
   DESCRIPTION
     "An entry in the frDteRgBfrProvTable."
   INDEX {
      frDteIndex,
      frDteRgIndex,
      frDteRgBfrIndex }
::= { frDteRgBfrProvTable 1 }

FrDteRgBfrProvEntry ::= SEQUENCE {
   frDteRgBfrMacType
      INTEGER,
   frDteRgBfrBfrIndex
      INTEGER }

frDteRgBfrMacType OBJECT-TYPE
   SYNTAX     INTEGER  {
                 fddi(0),
                 enet(1),
                 tokenRing(2) }
   ACCESS     read-write
   STATUS     mandatory
   DESCRIPTION
     "This attribute specifies the MAC address type of the Bfr component. 
      The value must be chosen based on the media of the traffic source. For 
      traffic originated from FDDI, use fddi; for ethernet, use enet; for token 
      ring, use tokenRing"
   DEFVAL     { enet }
::= { frDteRgBfrProvEntry 1 }

frDteRgBfrBfrIndex OBJECT-TYPE
   SYNTAX     INTEGER (0..511)
   ACCESS     read-write
   STATUS     mandatory
   DESCRIPTION
     "This attribute specifies the value which is used to derive a unique MAC 
      address for the Bfr. The bfrIndex must be unique across all Bfrs on the 
      same Lp."
::= { frDteRgBfrProvEntry 2 }

frDteRgBfrOprTable OBJECT-TYPE
   SYNTAX     SEQUENCE OF FrDteRgBfrOprEntry
   ACCESS     not-accessible
   STATUS     mandatory
   DESCRIPTION
     "This group contains the operational attributes for the Bfr component.."
::= { frDteRgBfr 11 }

frDteRgBfrOprEntry OBJECT-TYPE
   SYNTAX     FrDteRgBfrOprEntry
   ACCESS     not-accessible
   STATUS     mandatory
   DESCRIPTION
     "An entry in the frDteRgBfrOprTable."
   INDEX {
      frDteIndex,
      frDteRgIndex,
      frDteRgBfrIndex }
::= { frDteRgBfrOprTable 1 }

FrDteRgBfrOprEntry ::= SEQUENCE {
   frDteRgBfrMacAddr
      DashedHexString }

frDteRgBfrMacAddr OBJECT-TYPE
   SYNTAX     DashedHexString (SIZE (6))
   ACCESS     read-only
   STATUS     mandatory
   DESCRIPTION
     "This attribute indicates the unique MAC address of the Bfr component. 
      This value is derived by the value of the attribute bfrIndex.
      The value is displayed as cannonical format."
::= { frDteRgBfrOprEntry 1 }


-- FrDte/n DynDlciDefs
-- This component defines the default values that will be used when a Dlci 
-- of creationType dynamic is created.

frDteDynDlciDefs OBJECT IDENTIFIER ::= { frDte 5 }



frDteDynDlciDefsRowStatusTable OBJECT-TYPE
   SYNTAX     SEQUENCE OF FrDteDynDlciDefsRowStatusEntry
   ACCESS     not-accessible
   STATUS     mandatory
   DESCRIPTION
     "This entry controls the addition and deletion of 
      frDteDynDlciDefs components."
::= { frDteDynDlciDefs 1 }

frDteDynDlciDefsRowStatusEntry OBJECT-TYPE
   SYNTAX     FrDteDynDlciDefsRowStatusEntry
   ACCESS     not-accessible
   STATUS     mandatory
   DESCRIPTION
     "A single entry in the table represents a single 
      frDteDynDlciDefs component."
   INDEX {
      frDteIndex,
      frDteDynDlciDefsIndex }
::= { frDteDynDlciDefsRowStatusTable 1 }

FrDteDynDlciDefsRowStatusEntry ::= SEQUENCE {
   frDteDynDlciDefsRowStatus
      RowStatus,
   frDteDynDlciDefsComponentName
      DisplayString,
   frDteDynDlciDefsStorageType
      StorageType,
   frDteDynDlciDefsIndex
      NonReplicated }

frDteDynDlciDefsRowStatus OBJECT-TYPE
   SYNTAX     RowStatus 
   ACCESS     read-only
   STATUS     mandatory
   DESCRIPTION
     "This variable is used as the basis for SNMP naming of
      frDteDynDlciDefs components.
      These components cannot be added nor deleted."
::= { frDteDynDlciDefsRowStatusEntry 1 }

frDteDynDlciDefsComponentName OBJECT-TYPE
   SYNTAX     DisplayString 
   ACCESS     read-only
   STATUS     mandatory
   DESCRIPTION
     "This variable provides the component's string name for
      use with the ASCII Console Interface"
::= { frDteDynDlciDefsRowStatusEntry 2 }

frDteDynDlciDefsStorageType OBJECT-TYPE
   SYNTAX     StorageType 
   ACCESS     read-only
   STATUS     mandatory
   DESCRIPTION
     "This variable represents the storage type value for the
      frDteDynDlciDefs tables."
::= { frDteDynDlciDefsRowStatusEntry 4 }

frDteDynDlciDefsIndex OBJECT-TYPE
   SYNTAX     NonReplicated 
   ACCESS     not-accessible
   STATUS     mandatory
   DESCRIPTION
     "This variable represents the index for the frDteDynDlciDefs tables."
::= { frDteDynDlciDefsRowStatusEntry 10 }

frDteDynDlciDefsProvTable OBJECT-TYPE
   SYNTAX     SEQUENCE OF FrDteDynDlciDefsProvEntry
   ACCESS     not-accessible
   STATUS     mandatory
   DESCRIPTION
     "This group contains the provisioned attributes for a virtual circuit. These 
      attributes represent the default settings for the resulting Dlci components 
      and can be operationally changed using the corresponding attributes 
      under the Dlci component."
::= { frDteDynDlciDefs 10 }

frDteDynDlciDefsProvEntry OBJECT-TYPE
   SYNTAX     FrDteDynDlciDefsProvEntry
   ACCESS     not-accessible
   STATUS     mandatory
   DESCRIPTION
     "An entry in the frDteDynDlciDefsProvTable."
   INDEX {
      frDteIndex,
      frDteDynDlciDefsIndex }
::= { frDteDynDlciDefsProvTable 1 }

FrDteDynDlciDefsProvEntry ::= SEQUENCE {
   frDteDynDlciDefsStdRowStatus
      INTEGER,
   frDteDynDlciDefsRateEnforcement
      INTEGER,
   frDteDynDlciDefsCommittedInformationRate
      Unsigned32,
   frDteDynDlciDefsCommittedBurst
      Unsigned32,
   frDteDynDlciDefsExcessBurst
      Unsigned32,
   frDteDynDlciDefsExcessBurstAction
      INTEGER,
   frDteDynDlciDefsIpCos
      Unsigned32 }

frDteDynDlciDefsStdRowStatus OBJECT-TYPE
   SYNTAX     INTEGER  {
                 active(1),
                 notInService(2) }
   ACCESS     read-write
   STATUS     mandatory
   DESCRIPTION
     "This attribute is used to manage the status of a StDlci component.
      
      Set to active to enable the StDlci component.
      Set to notInService to disable the StDlci component.
      Set to createAndGo (SNMP only) to create a new StDlci component.
      Set to destroy (SNMP only) to delete an existing StDlci component."
   DEFVAL     { active }
::= { frDteDynDlciDefsProvEntry 1 }

frDteDynDlciDefsRateEnforcement OBJECT-TYPE
   SYNTAX     INTEGER  {
                 enabled(1),
                 disabled(2) }
   ACCESS     read-write
   STATUS     mandatory
   DESCRIPTION
     "This attribute specifies whether the CIR attributes 
      committedInformationRate, committedBurst, and excessBurst are used to 
      define rate enforcement on this user DLCI.
      
      If rateEnforcement is enabled, and the combined Committed and Excess 
      burst thresholds are exceeded, the frame in violation will be discarded 
      immediately if a HibernationQueue subcomponent is not provisioned 
      under the StDlci component. If a HibernationQueue is provisioned, the 
      frame will be placed on the HibernationQueue at time of violation and 
      transmission will be attempted later after the point at which the burst 
      thresholds will no longer be exceeded.
      
      Setting all the CIR attributes to zero has the same affect as setting this 
      attribute to disabled."
   DEFVAL     { disabled }
::= { frDteDynDlciDefsProvEntry 2 }

frDteDynDlciDefsCommittedInformationRate OBJECT-TYPE
   SYNTAX     Unsigned32 (0..48000000)
   ACCESS     read-write
   STATUS     mandatory
   DESCRIPTION
     "The average number of bits to be transferred per second over the DLCI 
      to the DCE. When this attribute is set to zero, the link speed will be used 
      instead."
   DEFVAL     { 64000 }
::= { frDteDynDlciDefsProvEntry 3 }

frDteDynDlciDefsCommittedBurst OBJECT-TYPE
   SYNTAX     Unsigned32 (0..2048000)
   ACCESS     read-write
   STATUS     mandatory
   DESCRIPTION
     "The committed burst size (in bits) to which the DLCI wants to 
      subscribe."
   DEFVAL     { 64000 }
::= { frDteDynDlciDefsProvEntry 4 }

frDteDynDlciDefsExcessBurst OBJECT-TYPE
   SYNTAX     Unsigned32 (0..2048000)
   ACCESS     read-write
   STATUS     mandatory
   DESCRIPTION
     "The excess burst size (in bits) to which the DLCI wants to subscribe."
   DEFVAL     { 0 }
::= { frDteDynDlciDefsProvEntry 5 }

frDteDynDlciDefsExcessBurstAction OBJECT-TYPE
   SYNTAX     INTEGER  {
                 none(1),
                 setDeBit(2) }
   ACCESS     read-write
   STATUS     mandatory
   DESCRIPTION
     "This attribute specifies the action taken when the committedBurst size 
      has been exceeded on the DLCI but the excessBurst size has not. If the 
      attribute is set to setDeBit, the Discard Eligibility bit in the Frame Relay 
      header will be turned on. If the attribute is set to none, no action will be 
      taken."
   DEFVAL     { none }
::= { frDteDynDlciDefsProvEntry 6 }

frDteDynDlciDefsIpCos OBJECT-TYPE
   SYNTAX     Unsigned32 (0..3)
   ACCESS     read-write
   STATUS     mandatory
   DESCRIPTION
     "This attribute specifies the initial Class of Service (CoS) given to each 
      packet received on the on the virtual circuit identified by the dlci. The 
      CoS value n is used to select Vr/<string> QosP/n. which determines the 
      QualityofService-Profile to be used when the packet is forwarded.
      
      The intial CoS given to a packet by the assignedQoS attribute may be 
      overriden when the cosPolicyAssignment attribute is defined on the 
      IpPort or Ip components. 
      
      When a packet is to be transmitted on a frDte protocol port where 
      multiple virtual circuits are available for the packet's next hop, the 
      packet is forwarded using the dlci where the ipCos value matches the 
      CoS of the packet. When the packets's CoS does not match the ipCos 
      value of any of the available virtual circuits, the packet will be 
      forwarded using next lowest CoS; failing this, the packet will be 
      forwarded using the next highest CoS."
   DEFVAL     { 0 }
::= { frDteDynDlciDefsProvEntry 7 }


-- FrDte/n StDlci/n
-- This component is used to provision a static virtual circuit on the Frame 
-- Relay DTE interface. For each StDlci provisioned, there will be a 
-- matching Dlci component. Dlci components of creationType dynamic 
-- will be converted to static without disruption of service when a StDlci 
-- component is provisioned with the same instance number.

frDteStDlci OBJECT IDENTIFIER ::= { frDte 6 }



frDteStDlciRowStatusTable OBJECT-TYPE
   SYNTAX     SEQUENCE OF FrDteStDlciRowStatusEntry
   ACCESS     not-accessible
   STATUS     mandatory
   DESCRIPTION
     "This entry controls the addition and deletion of 
      frDteStDlci components."
::= { frDteStDlci 1 }

frDteStDlciRowStatusEntry OBJECT-TYPE
   SYNTAX     FrDteStDlciRowStatusEntry
   ACCESS     not-accessible
   STATUS     mandatory
   DESCRIPTION
     "A single entry in the table represents a single 
      frDteStDlci component."
   INDEX {
      frDteIndex,
      frDteStDlciIndex }
::= { frDteStDlciRowStatusTable 1 }

FrDteStDlciRowStatusEntry ::= SEQUENCE {
   frDteStDlciRowStatus
      RowStatus,
   frDteStDlciComponentName
      DisplayString,
   frDteStDlciStorageType
      StorageType,
   frDteStDlciIndex
      Integer32 }

frDteStDlciRowStatus OBJECT-TYPE
   SYNTAX     RowStatus 
   ACCESS     read-write
   STATUS     mandatory
   DESCRIPTION
     "This variable is used as the basis for SNMP naming of
      frDteStDlci components.
      These components can be added and deleted."
::= { frDteStDlciRowStatusEntry 1 }

frDteStDlciComponentName OBJECT-TYPE
   SYNTAX     DisplayString 
   ACCESS     read-only
   STATUS     mandatory
   DESCRIPTION
     "This variable provides the component's string name for
      use with the ASCII Console Interface"
::= { frDteStDlciRowStatusEntry 2 }

frDteStDlciStorageType OBJECT-TYPE
   SYNTAX     StorageType 
   ACCESS     read-only
   STATUS     mandatory
   DESCRIPTION
     "This variable represents the storage type value for the
      frDteStDlci tables."
::= { frDteStDlciRowStatusEntry 4 }

frDteStDlciIndex OBJECT-TYPE
   SYNTAX     Integer32 (16..1007)
   ACCESS     not-accessible
   STATUS     mandatory
   DESCRIPTION
     "This variable represents the index for the frDteStDlci tables."
::= { frDteStDlciRowStatusEntry 10 }

frDteStDlciProvTable OBJECT-TYPE
   SYNTAX     SEQUENCE OF FrDteStDlciProvEntry
   ACCESS     not-accessible
   STATUS     mandatory
   DESCRIPTION
     "This group contains the provisioned attributes for a virtual circuit. These 
      attributes represent the default settings for the resulting Dlci components 
      and can be operationally changed using the corresponding attributes 
      under the Dlci component."
::= { frDteStDlci 10 }

frDteStDlciProvEntry OBJECT-TYPE
   SYNTAX     FrDteStDlciProvEntry
   ACCESS     not-accessible
   STATUS     mandatory
   DESCRIPTION
     "An entry in the frDteStDlciProvTable."
   INDEX {
      frDteIndex,
      frDteStDlciIndex }
::= { frDteStDlciProvTable 1 }

FrDteStDlciProvEntry ::= SEQUENCE {
   frDteStDlciStdRowStatus
      INTEGER,
   frDteStDlciRateEnforcement
      INTEGER,
   frDteStDlciCommittedInformationRate
      Unsigned32,
   frDteStDlciCommittedBurst
      Unsigned32,
   frDteStDlciExcessBurst
      Unsigned32,
   frDteStDlciExcessBurstAction
      INTEGER,
   frDteStDlciIpCos
      Unsigned32 }

frDteStDlciStdRowStatus OBJECT-TYPE
   SYNTAX     INTEGER  {
                 active(1),
                 notInService(2) }
   ACCESS     read-write
   STATUS     mandatory
   DESCRIPTION
     "This attribute is used to manage the status of a StDlci component.
      
      Set to active to enable the StDlci component.
      Set to notInService to disable the StDlci component.
      Set to createAndGo (SNMP only) to create a new StDlci component.
      Set to destroy (SNMP only) to delete an existing StDlci component."
   DEFVAL     { active }
::= { frDteStDlciProvEntry 1 }

frDteStDlciRateEnforcement OBJECT-TYPE
   SYNTAX     INTEGER  {
                 enabled(1),
                 disabled(2) }
   ACCESS     read-write
   STATUS     mandatory
   DESCRIPTION
     "This attribute specifies whether the CIR attributes 
      committedInformationRate, committedBurst, and excessBurst are used to 
      define rate enforcement on this user DLCI.
      
      If rateEnforcement is enabled, and the combined Committed and Excess 
      burst thresholds are exceeded, the frame in violation will be discarded 
      immediately if a HibernationQueue subcomponent is not provisioned 
      under the StDlci component. If a HibernationQueue is provisioned, the 
      frame will be placed on the HibernationQueue at time of violation and 
      transmission will be attempted later after the point at which the burst 
      thresholds will no longer be exceeded.
      
      Setting all the CIR attributes to zero has the same affect as setting this 
      attribute to disabled."
   DEFVAL     { disabled }
::= { frDteStDlciProvEntry 2 }

frDteStDlciCommittedInformationRate OBJECT-TYPE
   SYNTAX     Unsigned32 (0..48000000)
   ACCESS     read-write
   STATUS     mandatory
   DESCRIPTION
     "The average number of bits to be transferred per second over the DLCI 
      to the DCE. When this attribute is set to zero, the link speed will be used 
      instead."
   DEFVAL     { 64000 }
::= { frDteStDlciProvEntry 3 }

frDteStDlciCommittedBurst OBJECT-TYPE
   SYNTAX     Unsigned32 (0..2048000)
   ACCESS     read-write
   STATUS     mandatory
   DESCRIPTION
     "The committed burst size (in bits) to which the DLCI wants to 
      subscribe."
   DEFVAL     { 64000 }
::= { frDteStDlciProvEntry 4 }

frDteStDlciExcessBurst OBJECT-TYPE
   SYNTAX     Unsigned32 (0..2048000)
   ACCESS     read-write
   STATUS     mandatory
   DESCRIPTION
     "The excess burst size (in bits) to which the DLCI wants to subscribe."
   DEFVAL     { 0 }
::= { frDteStDlciProvEntry 5 }

frDteStDlciExcessBurstAction OBJECT-TYPE
   SYNTAX     INTEGER  {
                 none(1),
                 setDeBit(2) }
   ACCESS     read-write
   STATUS     mandatory
   DESCRIPTION
     "This attribute specifies the action taken when the committedBurst size 
      has been exceeded on the DLCI but the excessBurst size has not. If the 
      attribute is set to setDeBit, the Discard Eligibility bit in the Frame Relay 
      header will be turned on. If the attribute is set to none, no action will be 
      taken."
   DEFVAL     { none }
::= { frDteStDlciProvEntry 6 }

frDteStDlciIpCos OBJECT-TYPE
   SYNTAX     Unsigned32 (0..3)
   ACCESS     read-write
   STATUS     mandatory
   DESCRIPTION
     "This attribute specifies the initial Class of Service (CoS) given to each 
      packet received on the on the virtual circuit identified by the dlci. The 
      CoS value n is used to select Vr/<string> QosP/n. which determines the 
      QualityofService-Profile to be used when the packet is forwarded.
      
      The intial CoS given to a packet by the assignedQoS attribute may be 
      overriden when the cosPolicyAssignment attribute is defined on the 
      IpPort or Ip components. 
      
      When a packet is to be transmitted on a frDte protocol port where 
      multiple virtual circuits are available for the packet's next hop, the 
      packet is forwarded using the dlci where the ipCos value matches the 
      CoS of the packet. When the packets's CoS does not match the ipCos 
      value of any of the available virtual circuits, the packet will be 
      forwarded using next lowest CoS; failing this, the packet will be 
      forwarded using the next highest CoS."
   DEFVAL     { 0 }
::= { frDteStDlciProvEntry 7 }

frDteStDlciRgLinkTable OBJECT-TYPE
   SYNTAX     SEQUENCE OF FrDteStDlciRgLinkEntry
   ACCESS     not-accessible
   STATUS     mandatory
   DESCRIPTION
     "This group provides the link between a Dlci and a remoteGroup."
::= { frDteStDlci 11 }

frDteStDlciRgLinkEntry OBJECT-TYPE
   SYNTAX     FrDteStDlciRgLinkEntry
   ACCESS     not-accessible
   STATUS     mandatory
   DESCRIPTION
     "An entry in the frDteStDlciRgLinkTable."
   INDEX {
      frDteIndex,
      frDteStDlciIndex }
::= { frDteStDlciRgLinkTable 1 }

FrDteStDlciRgLinkEntry ::= SEQUENCE {
   frDteStDlciLinkToRemoteGroup
      Link }

frDteStDlciLinkToRemoteGroup OBJECT-TYPE
   SYNTAX     Link 
   ACCESS     read-write
   STATUS     mandatory
   DESCRIPTION
     "This attribute associates a StDlci component with a Rg component. 
      Provisioned StDlci components must be linked to a Rg component 
      which is under the same FrDte component."
::= { frDteStDlciRgLinkEntry 1 }


-- FrDte/n StDlci/n Hq
-- This component provides a Hibernation Queue capability for a Dlci 
-- component which has been provisioned with CIR enforcement enabled. 
-- The HibernationQueue provides priority placement of frames on the 
-- queue, Time To Live (TTL) discarding of frames from the queue, and 
-- queue statistics.

frDteStDlciHq OBJECT IDENTIFIER ::= { frDteStDlci 2 }



frDteStDlciHqRowStatusTable OBJECT-TYPE
   SYNTAX     SEQUENCE OF FrDteStDlciHqRowStatusEntry
   ACCESS     not-accessible
   STATUS     mandatory
   DESCRIPTION
     "This entry controls the addition and deletion of 
      frDteStDlciHq components."
::= { frDteStDlciHq 1 }

frDteStDlciHqRowStatusEntry OBJECT-TYPE
   SYNTAX     FrDteStDlciHqRowStatusEntry
   ACCESS     not-accessible
   STATUS     mandatory
   DESCRIPTION
     "A single entry in the table represents a single 
      frDteStDlciHq component."
   INDEX {
      frDteIndex,
      frDteStDlciIndex,
      frDteStDlciHqIndex }
::= { frDteStDlciHqRowStatusTable 1 }

FrDteStDlciHqRowStatusEntry ::= SEQUENCE {
   frDteStDlciHqRowStatus
      RowStatus,
   frDteStDlciHqComponentName
      DisplayString,
   frDteStDlciHqStorageType
      StorageType,
   frDteStDlciHqIndex
      NonReplicated }

frDteStDlciHqRowStatus OBJECT-TYPE
   SYNTAX     RowStatus 
   ACCESS     read-write
   STATUS     mandatory
   DESCRIPTION
     "This variable is used as the basis for SNMP naming of
      frDteStDlciHq components.
      These components can be added and deleted."
::= { frDteStDlciHqRowStatusEntry 1 }

frDteStDlciHqComponentName OBJECT-TYPE
   SYNTAX     DisplayString 
   ACCESS     read-only
   STATUS     mandatory
   DESCRIPTION
     "This variable provides the component's string name for
      use with the ASCII Console Interface"
::= { frDteStDlciHqRowStatusEntry 2 }

frDteStDlciHqStorageType OBJECT-TYPE
   SYNTAX     StorageType 
   ACCESS     read-only
   STATUS     mandatory
   DESCRIPTION
     "This variable represents the storage type value for the
      frDteStDlciHq tables."
::= { frDteStDlciHqRowStatusEntry 4 }

frDteStDlciHqIndex OBJECT-TYPE
   SYNTAX     NonReplicated 
   ACCESS     not-accessible
   STATUS     mandatory
   DESCRIPTION
     "This variable represents the index for the frDteStDlciHq tables."
::= { frDteStDlciHqRowStatusEntry 10 }

frDteStDlciHqProvTable OBJECT-TYPE
   SYNTAX     SEQUENCE OF FrDteStDlciHqProvEntry
   ACCESS     not-accessible
   STATUS     mandatory
   DESCRIPTION
     "This group contains the Link Emission Queue provisioned attributes."
::= { frDteStDlciHq 10 }

frDteStDlciHqProvEntry OBJECT-TYPE
   SYNTAX     FrDteStDlciHqProvEntry
   ACCESS     not-accessible
   STATUS     mandatory
   DESCRIPTION
     "An entry in the frDteStDlciHqProvTable."
   INDEX {
      frDteIndex,
      frDteStDlciIndex,
      frDteStDlciHqIndex }
::= { frDteStDlciHqProvTable 1 }

FrDteStDlciHqProvEntry ::= SEQUENCE {
   frDteStDlciHqMaxPackets
      Unsigned32,
   frDteStDlciHqMaxMsecData
      Unsigned32,
   frDteStDlciHqMaxPercentMulticast
      Unsigned32,
   frDteStDlciHqTimeToLive
      Unsigned32 }

frDteStDlciHqMaxPackets OBJECT-TYPE
   SYNTAX     Unsigned32 (0..2048)
   ACCESS     read-write
   STATUS     mandatory
   DESCRIPTION
     "This attribute specifies the maximum number of packets allowed in the 
      Leq before being discarded. If this attribute is set to zero then the 
      maximum number of packets is calculated from the transmit data rate. 
      This calculated value is placed in queuePktThreshold."
   DEFVAL     { 0 }
::= { frDteStDlciHqProvEntry 1 }

frDteStDlciHqMaxMsecData OBJECT-TYPE
   SYNTAX     Unsigned32 (100..60000)
   ACCESS     read-write
   STATUS     mandatory
   DESCRIPTION
     "This attribute specifies the maximum number of 'Milliseconds worth of 
      data' allowed in the Leq before packets are discarded. The 
      queueByteThreshold will be calculated from this attribute, based on the 
      transmit data rate."
   DEFVAL     { 10000 }
::= { frDteStDlciHqProvEntry 2 }

frDteStDlciHqMaxPercentMulticast OBJECT-TYPE
   SYNTAX     Unsigned32 (1..100)
   ACCESS     read-write
   STATUS     mandatory
   DESCRIPTION
     "This attribute specifies the maximum percentage of multicast packets 
      allowed in the Leq, based on queuePktThreshold, before being 
      discarded. The calculated value will be placed in 
      queueMulticastThreshold."
   DEFVAL     { 50 }
::= { frDteStDlciHqProvEntry 3 }

frDteStDlciHqTimeToLive OBJECT-TYPE
   SYNTAX     Unsigned32 (100..60000)
   ACCESS     read-write
   STATUS     mandatory
   DESCRIPTION
     "This attribute specifies the 'Milliseconds Time To Live' of packets in 
      the Leq. If the timeToLive of a packet expires, it will be discarded."
   DEFVAL     { 10000 }
::= { frDteStDlciHqProvEntry 4 }

frDteStDlciHqStatsTable OBJECT-TYPE
   SYNTAX     SEQUENCE OF FrDteStDlciHqStatsEntry
   ACCESS     not-accessible
   STATUS     mandatory
   DESCRIPTION
     "This group contains HibernationQueue general statistics."
::= { frDteStDlciHq 11 }

frDteStDlciHqStatsEntry OBJECT-TYPE
   SYNTAX     FrDteStDlciHqStatsEntry
   ACCESS     not-accessible
   STATUS     mandatory
   DESCRIPTION
     "An entry in the frDteStDlciHqStatsTable."
   INDEX {
      frDteIndex,
      frDteStDlciIndex,
      frDteStDlciHqIndex }
::= { frDteStDlciHqStatsTable 1 }

FrDteStDlciHqStatsEntry ::= SEQUENCE {
   frDteStDlciHqTimedOutPkt
      Counter32,
   frDteStDlciHqQueuePurgeDiscards
      Counter32 }

frDteStDlciHqTimedOutPkt OBJECT-TYPE
   SYNTAX     Counter32 
   ACCESS     read-only
   STATUS     mandatory
   DESCRIPTION
     "This attribute counts the number of packets that have been discarded due 
      to exceeding the timeToLive. This counter will wrap around to 0 when it 
      exceeds its maximum count."
::= { frDteStDlciHqStatsEntry 1 }

frDteStDlciHqQueuePurgeDiscards OBJECT-TYPE
   SYNTAX     Counter32 
   ACCESS     read-only
   STATUS     mandatory
   DESCRIPTION
     "This attribute counts the total number of packets discarded by a queue 
      purge which occurs when the Dlci goes down. This counter will wrap 
      around to 0 when it exceeds its maximum count."
::= { frDteStDlciHqStatsEntry 2 }

frDteStDlciHqTStatsTable OBJECT-TYPE
   SYNTAX     SEQUENCE OF FrDteStDlciHqTStatsEntry
   ACCESS     not-accessible
   STATUS     mandatory
   DESCRIPTION
     "This group contains Link Emission Queue total statistics."
::= { frDteStDlciHq 12 }

frDteStDlciHqTStatsEntry OBJECT-TYPE
   SYNTAX     FrDteStDlciHqTStatsEntry
   ACCESS     not-accessible
   STATUS     mandatory
   DESCRIPTION
     "An entry in the frDteStDlciHqTStatsTable."
   INDEX {
      frDteIndex,
      frDteStDlciIndex,
      frDteStDlciHqIndex }
::= { frDteStDlciHqTStatsTable 1 }

FrDteStDlciHqTStatsEntry ::= SEQUENCE {
   frDteStDlciHqTotalPktHandled
      Counter32,
   frDteStDlciHqTotalPktForwarded
      Counter32,
   frDteStDlciHqTotalPktQueued
      Counter32,
   frDteStDlciHqTotalMulticastPkt
      Counter32,
   frDteStDlciHqTotalPktDiscards
      Counter32 }

frDteStDlciHqTotalPktHandled OBJECT-TYPE
   SYNTAX     Counter32 
   ACCESS     read-only
   STATUS     mandatory
   DESCRIPTION
     "This attribute counts the total number of packets handled by the Leq. 
      This counter will wrap around to 0 when it exceeds its maximum count."
::= { frDteStDlciHqTStatsEntry 1 }

frDteStDlciHqTotalPktForwarded OBJECT-TYPE
   SYNTAX     Counter32 
   ACCESS     read-only
   STATUS     mandatory
   DESCRIPTION
     "This attribute counts the total number of packets forwarded by the Leq. 
      This counter will wrap around to 0 when it exceeds its maximum count."
::= { frDteStDlciHqTStatsEntry 2 }

frDteStDlciHqTotalPktQueued OBJECT-TYPE
   SYNTAX     Counter32 
   ACCESS     read-only
   STATUS     mandatory
   DESCRIPTION
     "This attribute counts the total number of packets that required queuing 
      by the Leq due to transmit congestion. This counter will wrap around to 
      0 when it exceeds its maximum count."
::= { frDteStDlciHqTStatsEntry 3 }

frDteStDlciHqTotalMulticastPkt OBJECT-TYPE
   SYNTAX     Counter32 
   ACCESS     read-only
   STATUS     mandatory
   DESCRIPTION
     "This attribute counts the total number of multicast packets handled by 
      this instance of FrDte. This counter will wrap around to 0 when it 
      exceeds its maximum count."
::= { frDteStDlciHqTStatsEntry 4 }

frDteStDlciHqTotalPktDiscards OBJECT-TYPE
   SYNTAX     Counter32 
   ACCESS     read-only
   STATUS     mandatory
   DESCRIPTION
     "This attribute counts the total number of packets that were discarded for 
      this instance of FrDte. This is the sum of timedOutPkt, 
      forcedPktDiscards, queuePurgeDiscards, pktThresholdExceeded, 
      byteThresholdExceeded, mulThresholdExceeded and 
      memThresholdExceeded. This counter will wrap around to 0 when it 
      exceeds its maximum count."
::= { frDteStDlciHqTStatsEntry 5 }

frDteStDlciHqCStatsTable OBJECT-TYPE
   SYNTAX     SEQUENCE OF FrDteStDlciHqCStatsEntry
   ACCESS     not-accessible
   STATUS     mandatory
   DESCRIPTION
     "This group contains Link Emission Queue current statistics."
::= { frDteStDlciHq 13 }

frDteStDlciHqCStatsEntry OBJECT-TYPE
   SYNTAX     FrDteStDlciHqCStatsEntry
   ACCESS     not-accessible
   STATUS     mandatory
   DESCRIPTION
     "An entry in the frDteStDlciHqCStatsTable."
   INDEX {
      frDteIndex,
      frDteStDlciIndex,
      frDteStDlciHqIndex }
::= { frDteStDlciHqCStatsTable 1 }

FrDteStDlciHqCStatsEntry ::= SEQUENCE {
   frDteStDlciHqCurrentPktQueued
      Gauge32,
   frDteStDlciHqCurrentBytesQueued
      Gauge32,
   frDteStDlciHqCurrentMulticastQueued
      Gauge32 }

frDteStDlciHqCurrentPktQueued OBJECT-TYPE
   SYNTAX     Gauge32 (0..4294967295)
   ACCESS     read-only
   STATUS     mandatory
   DESCRIPTION
     "This attribute contains the current number of packets queued."
   DEFVAL     { 0 }
::= { frDteStDlciHqCStatsEntry 1 }

frDteStDlciHqCurrentBytesQueued OBJECT-TYPE
   SYNTAX     Gauge32 (0..4294967295)
   ACCESS     read-only
   STATUS     mandatory
   DESCRIPTION
     "This attribute contains the current number of bytes queued."
   DEFVAL     { 0 }
::= { frDteStDlciHqCStatsEntry 2 }

frDteStDlciHqCurrentMulticastQueued OBJECT-TYPE
   SYNTAX     Gauge32 (0..4294967295)
   ACCESS     read-only
   STATUS     mandatory
   DESCRIPTION
     "This attribute counts the current number of multicast packets in the 
      queue."
   DEFVAL     { 0 }
::= { frDteStDlciHqCStatsEntry 3 }

frDteStDlciHqThrStatsTable OBJECT-TYPE
   SYNTAX     SEQUENCE OF FrDteStDlciHqThrStatsEntry
   ACCESS     not-accessible
   STATUS     mandatory
   DESCRIPTION
     "This group contains Link Emission Queue threshold statistics."
::= { frDteStDlciHq 14 }

frDteStDlciHqThrStatsEntry OBJECT-TYPE
   SYNTAX     FrDteStDlciHqThrStatsEntry
   ACCESS     not-accessible
   STATUS     mandatory
   DESCRIPTION
     "An entry in the frDteStDlciHqThrStatsTable."
   INDEX {
      frDteIndex,
      frDteStDlciIndex,
      frDteStDlciHqIndex }
::= { frDteStDlciHqThrStatsTable 1 }

FrDteStDlciHqThrStatsEntry ::= SEQUENCE {
   frDteStDlciHqQueuePktThreshold
      Unsigned32,
   frDteStDlciHqPktThresholdExceeded
      Counter32,
   frDteStDlciHqQueueByteThreshold
      Unsigned32,
   frDteStDlciHqByteThresholdExceeded
      Counter32,
   frDteStDlciHqQueueMulticastThreshold
      Unsigned32,
   frDteStDlciHqMulThresholdExceeded
      Counter32,
   frDteStDlciHqMemThresholdExceeded
      Counter32 }

frDteStDlciHqQueuePktThreshold OBJECT-TYPE
   SYNTAX     Unsigned32 (0..4294967295)
   ACCESS     read-only
   STATUS     mandatory
   DESCRIPTION
     "This attribute is the maximum number of packets that can be contained 
      in the queue before being discarded. If maxPackets was set to 0 then this 
      attribute will contain the value that has been calculated based on the 
      transmit data rate. If maxPackets was set to one or more than this 
      attribute will contain that number."
   DEFVAL     { 0 }
::= { frDteStDlciHqThrStatsEntry 1 }

frDteStDlciHqPktThresholdExceeded OBJECT-TYPE
   SYNTAX     Counter32 
   ACCESS     read-only
   STATUS     mandatory
   DESCRIPTION
     "This attribute counts the number of packets discarded due to the 
      queuePktThreshold being exceeded. This counter will wrap around to 0 
      when it exceeds its maximum count."
::= { frDteStDlciHqThrStatsEntry 2 }

frDteStDlciHqQueueByteThreshold OBJECT-TYPE
   SYNTAX     Unsigned32 (0..4294967295)
   ACCESS     read-only
   STATUS     mandatory
   DESCRIPTION
     "This attribute is the maximum number of bytes allowed in the queue 
      based on maxMsecData and the transmit data rate."
   DEFVAL     { 0 }
::= { frDteStDlciHqThrStatsEntry 3 }

frDteStDlciHqByteThresholdExceeded OBJECT-TYPE
   SYNTAX     Counter32 
   ACCESS     read-only
   STATUS     mandatory
   DESCRIPTION
     "This attribute counts the number of packets discarded due to the 
      queueByteThreshold being exceeded. This counter will wrap around to 0 
      when it exceeds its maximum count."
::= { frDteStDlciHqThrStatsEntry 4 }

frDteStDlciHqQueueMulticastThreshold OBJECT-TYPE
   SYNTAX     Unsigned32 (0..4294967295)
   ACCESS     read-only
   STATUS     mandatory
   DESCRIPTION
     "This attribute is the number of multicast packets allowed in the queue 
      based on maxPercentMulticast and maxPackets."
   DEFVAL     { 0 }
::= { frDteStDlciHqThrStatsEntry 5 }

frDteStDlciHqMulThresholdExceeded OBJECT-TYPE
   SYNTAX     Counter32 
   ACCESS     read-only
   STATUS     mandatory
   DESCRIPTION
     "This attribute counts the number of packets discarded due to the 
      queueMulticastThreshold being exceeded. This counter will wrap 
      around to 0 when it exceeds its maximum count."
::= { frDteStDlciHqThrStatsEntry 6 }

frDteStDlciHqMemThresholdExceeded OBJECT-TYPE
   SYNTAX     Counter32 
   ACCESS     read-only
   STATUS     mandatory
   DESCRIPTION
     "This attribute counts the number of packets discarded due to exceeding 
      the memory usage threshold for Leq. The memory usage threshold is 
      determined by the Leq software, guaranteeing that the Leq does not 
      consume all of the memory. This counter will wrap around to 0 when it 
      exceeds its maximum count."
::= { frDteStDlciHqThrStatsEntry 7 }


-- FrDte/n Leq 
-- This component provides a means of statistics gathering and packet 
-- discard.

frDteLeq OBJECT IDENTIFIER ::= { frDte 7 }



frDteLeqRowStatusTable OBJECT-TYPE
   SYNTAX     SEQUENCE OF FrDteLeqRowStatusEntry
   ACCESS     not-accessible
   STATUS     mandatory
   DESCRIPTION
     "This entry controls the addition and deletion of 
      frDteLeq components."
::= { frDteLeq 1 }

frDteLeqRowStatusEntry OBJECT-TYPE
   SYNTAX     FrDteLeqRowStatusEntry
   ACCESS     not-accessible
   STATUS     mandatory
   DESCRIPTION
     "A single entry in the table represents a single 
      frDteLeq component."
   INDEX {
      frDteIndex,
      frDteLeqIndex }
::= { frDteLeqRowStatusTable 1 }

FrDteLeqRowStatusEntry ::= SEQUENCE {
   frDteLeqRowStatus
      RowStatus,
   frDteLeqComponentName
      DisplayString,
   frDteLeqStorageType
      StorageType,
   frDteLeqIndex
      NonReplicated }

frDteLeqRowStatus OBJECT-TYPE
   SYNTAX     RowStatus 
   ACCESS     read-write
   STATUS     mandatory
   DESCRIPTION
     "This variable is used as the basis for SNMP naming of
      frDteLeq components.
      These components can be added and deleted."
::= { frDteLeqRowStatusEntry 1 }

frDteLeqComponentName OBJECT-TYPE
   SYNTAX     DisplayString 
   ACCESS     read-only
   STATUS     mandatory
   DESCRIPTION
     "This variable provides the component's string name for
      use with the ASCII Console Interface"
::= { frDteLeqRowStatusEntry 2 }

frDteLeqStorageType OBJECT-TYPE
   SYNTAX     StorageType 
   ACCESS     read-only
   STATUS     mandatory
   DESCRIPTION
     "This variable represents the storage type value for the
      frDteLeq tables."
::= { frDteLeqRowStatusEntry 4 }

frDteLeqIndex OBJECT-TYPE
   SYNTAX     NonReplicated 
   ACCESS     not-accessible
   STATUS     mandatory
   DESCRIPTION
     "This variable represents the index for the frDteLeq tables."
::= { frDteLeqRowStatusEntry 10 }

frDteLeqProvTable OBJECT-TYPE
   SYNTAX     SEQUENCE OF FrDteLeqProvEntry
   ACCESS     not-accessible
   STATUS     mandatory
   DESCRIPTION
     "This group contains the Link Emission Queue provisioned attributes."
::= { frDteLeq 10 }

frDteLeqProvEntry OBJECT-TYPE
   SYNTAX     FrDteLeqProvEntry
   ACCESS     not-accessible
   STATUS     mandatory
   DESCRIPTION
     "An entry in the frDteLeqProvTable."
   INDEX {
      frDteIndex,
      frDteLeqIndex }
::= { frDteLeqProvTable 1 }

FrDteLeqProvEntry ::= SEQUENCE {
   frDteLeqMaxPackets
      Unsigned32,
   frDteLeqMaxMsecData
      Unsigned32,
   frDteLeqMaxPercentMulticast
      Unsigned32,
   frDteLeqTimeToLive
      Unsigned32 }

frDteLeqMaxPackets OBJECT-TYPE
   SYNTAX     Unsigned32 (0..2048)
   ACCESS     read-write
   STATUS     mandatory
   DESCRIPTION
     "This attribute specifies the maximum number of packets allowed in the 
      Leq before being discarded. If this attribute is set to zero then the 
      maximum number of packets is calculated from the transmit data rate. 
      This calculated value is placed in queuePktThreshold."
   DEFVAL     { 0 }
::= { frDteLeqProvEntry 1 }

frDteLeqMaxMsecData OBJECT-TYPE
   SYNTAX     Unsigned32 (100..60000)
   ACCESS     read-write
   STATUS     mandatory
   DESCRIPTION
     "This attribute specifies the maximum number of 'Milliseconds worth of 
      data' allowed in the Leq before packets are discarded. The 
      queueByteThreshold will be calculated from this attribute, based on the 
      transmit data rate."
   DEFVAL     { 10000 }
::= { frDteLeqProvEntry 2 }

frDteLeqMaxPercentMulticast OBJECT-TYPE
   SYNTAX     Unsigned32 (1..100)
   ACCESS     read-write
   STATUS     mandatory
   DESCRIPTION
     "This attribute specifies the maximum percentage of multicast packets 
      allowed in the Leq, based on queuePktThreshold, before being 
      discarded. The calculated value will be placed in 
      queueMulticastThreshold."
   DEFVAL     { 50 }
::= { frDteLeqProvEntry 3 }

frDteLeqTimeToLive OBJECT-TYPE
   SYNTAX     Unsigned32 (100..60000)
   ACCESS     read-write
   STATUS     mandatory
   DESCRIPTION
     "This attribute specifies the 'Milliseconds Time To Live' of packets in 
      the Leq. If the timeToLive of a packet expires, it will be discarded."
   DEFVAL     { 10000 }
::= { frDteLeqProvEntry 4 }

frDteLeqStatsTable OBJECT-TYPE
   SYNTAX     SEQUENCE OF FrDteLeqStatsEntry
   ACCESS     not-accessible
   STATUS     mandatory
   DESCRIPTION
     "This group contains Link Emission Queue general statistics."
::= { frDteLeq 11 }

frDteLeqStatsEntry OBJECT-TYPE
   SYNTAX     FrDteLeqStatsEntry
   ACCESS     not-accessible
   STATUS     mandatory
   DESCRIPTION
     "An entry in the frDteLeqStatsTable."
   INDEX {
      frDteIndex,
      frDteLeqIndex }
::= { frDteLeqStatsTable 1 }

FrDteLeqStatsEntry ::= SEQUENCE {
   frDteLeqTimedOutPkt
      Counter32,
   frDteLeqHardwareForcedPkt
      Counter32,
   frDteLeqForcedPktDiscards
      Counter32,
   frDteLeqQueuePurgeDiscards
      Counter32 }

frDteLeqTimedOutPkt OBJECT-TYPE
   SYNTAX     Counter32 
   ACCESS     read-only
   STATUS     mandatory
   DESCRIPTION
     "This attribute counts the number of packets that have been discarded due 
      to exceeding the timeToLive. This counter will wrap around to 0 when it 
      exceeds its maximum count."
::= { frDteLeqStatsEntry 1 }

frDteLeqHardwareForcedPkt OBJECT-TYPE
   SYNTAX     Counter32 
   ACCESS     read-only
   STATUS     mandatory
   DESCRIPTION
     "This attribute counts the number of hardware forced packets on this 
      instance of FrDte. This counter will wrap around to 0 when it exceeds 
      its maximum count."
::= { frDteLeqStatsEntry 2 }

frDteLeqForcedPktDiscards OBJECT-TYPE
   SYNTAX     Counter32 
   ACCESS     read-only
   STATUS     mandatory
   DESCRIPTION
     "This attribute counts the total number of hardware forced packets that 
      had to be discarded due to link failure. This counter will wrap around to 
      0 when it exceeds its maximum count."
::= { frDteLeqStatsEntry 3 }

frDteLeqQueuePurgeDiscards OBJECT-TYPE
   SYNTAX     Counter32 
   ACCESS     read-only
   STATUS     mandatory
   DESCRIPTION
     "This attribute counts the total number of packets discarded by a queue 
      purge (i.e. a discarding of all packets on the queue). This counter will 
      wrap around to 0 when it exceeds its maximum count."
::= { frDteLeqStatsEntry 4 }

frDteLeqTStatsTable OBJECT-TYPE
   SYNTAX     SEQUENCE OF FrDteLeqTStatsEntry
   ACCESS     not-accessible
   STATUS     mandatory
   DESCRIPTION
     "This group contains Link Emission Queue total statistics."
::= { frDteLeq 12 }

frDteLeqTStatsEntry OBJECT-TYPE
   SYNTAX     FrDteLeqTStatsEntry
   ACCESS     not-accessible
   STATUS     mandatory
   DESCRIPTION
     "An entry in the frDteLeqTStatsTable."
   INDEX {
      frDteIndex,
      frDteLeqIndex }
::= { frDteLeqTStatsTable 1 }

FrDteLeqTStatsEntry ::= SEQUENCE {
   frDteLeqTotalPktHandled
      Counter32,
   frDteLeqTotalPktForwarded
      Counter32,
   frDteLeqTotalPktQueued
      Counter32,
   frDteLeqTotalMulticastPkt
      Counter32,
   frDteLeqTotalPktDiscards
      Counter32 }

frDteLeqTotalPktHandled OBJECT-TYPE
   SYNTAX     Counter32 
   ACCESS     read-only
   STATUS     mandatory
   DESCRIPTION
     "This attribute counts the total number of packets handled by the Leq. 
      This counter will wrap around to 0 when it exceeds its maximum count."
::= { frDteLeqTStatsEntry 1 }

frDteLeqTotalPktForwarded OBJECT-TYPE
   SYNTAX     Counter32 
   ACCESS     read-only
   STATUS     mandatory
   DESCRIPTION
     "This attribute counts the total number of packets forwarded by the Leq. 
      This counter will wrap around to 0 when it exceeds its maximum count."
::= { frDteLeqTStatsEntry 2 }

frDteLeqTotalPktQueued OBJECT-TYPE
   SYNTAX     Counter32 
   ACCESS     read-only
   STATUS     mandatory
   DESCRIPTION
     "This attribute counts the total number of packets that required queuing 
      by the Leq due to transmit congestion. This counter will wrap around to 
      0 when it exceeds its maximum count."
::= { frDteLeqTStatsEntry 3 }

frDteLeqTotalMulticastPkt OBJECT-TYPE
   SYNTAX     Counter32 
   ACCESS     read-only
   STATUS     mandatory
   DESCRIPTION
     "This attribute counts the total number of multicast packets handled by 
      this instance of FrDte. This counter will wrap around to 0 when it 
      exceeds its maximum count."
::= { frDteLeqTStatsEntry 4 }

frDteLeqTotalPktDiscards OBJECT-TYPE
   SYNTAX     Counter32 
   ACCESS     read-only
   STATUS     mandatory
   DESCRIPTION
     "This attribute counts the total number of packets that were discarded for 
      this instance of FrDte. This is the sum of timedOutPkt, 
      forcedPktDiscards, queuePurgeDiscards, pktThresholdExceeded, 
      byteThresholdExceeded, mulThresholdExceeded and 
      memThresholdExceeded. This counter will wrap around to 0 when it 
      exceeds its maximum count."
::= { frDteLeqTStatsEntry 5 }

frDteLeqCStatsTable OBJECT-TYPE
   SYNTAX     SEQUENCE OF FrDteLeqCStatsEntry
   ACCESS     not-accessible
   STATUS     mandatory
   DESCRIPTION
     "This group contains Link Emission Queue current statistics."
::= { frDteLeq 13 }

frDteLeqCStatsEntry OBJECT-TYPE
   SYNTAX     FrDteLeqCStatsEntry
   ACCESS     not-accessible
   STATUS     mandatory
   DESCRIPTION
     "An entry in the frDteLeqCStatsTable."
   INDEX {
      frDteIndex,
      frDteLeqIndex }
::= { frDteLeqCStatsTable 1 }

FrDteLeqCStatsEntry ::= SEQUENCE {
   frDteLeqCurrentPktQueued
      Gauge32,
   frDteLeqCurrentBytesQueued
      Gauge32,
   frDteLeqCurrentMulticastQueued
      Gauge32 }

frDteLeqCurrentPktQueued OBJECT-TYPE
   SYNTAX     Gauge32 (0..4294967295)
   ACCESS     read-only
   STATUS     mandatory
   DESCRIPTION
     "This attribute contains the current number of packets queued."
   DEFVAL     { 0 }
::= { frDteLeqCStatsEntry 1 }

frDteLeqCurrentBytesQueued OBJECT-TYPE
   SYNTAX     Gauge32 (0..4294967295)
   ACCESS     read-only
   STATUS     mandatory
   DESCRIPTION
     "This attribute contains the current number of bytes queued."
   DEFVAL     { 0 }
::= { frDteLeqCStatsEntry 2 }

frDteLeqCurrentMulticastQueued OBJECT-TYPE
   SYNTAX     Gauge32 (0..4294967295)
   ACCESS     read-only
   STATUS     mandatory
   DESCRIPTION
     "This attribute counts the current number of multicast packets in the 
      queue."
   DEFVAL     { 0 }
::= { frDteLeqCStatsEntry 3 }

frDteLeqThrStatsTable OBJECT-TYPE
   SYNTAX     SEQUENCE OF FrDteLeqThrStatsEntry
   ACCESS     not-accessible
   STATUS     mandatory
   DESCRIPTION
     "This group contains Link Emission Queue threshold statistics."
::= { frDteLeq 14 }

frDteLeqThrStatsEntry OBJECT-TYPE
   SYNTAX     FrDteLeqThrStatsEntry
   ACCESS     not-accessible
   STATUS     mandatory
   DESCRIPTION
     "An entry in the frDteLeqThrStatsTable."
   INDEX {
      frDteIndex,
      frDteLeqIndex }
::= { frDteLeqThrStatsTable 1 }

FrDteLeqThrStatsEntry ::= SEQUENCE {
   frDteLeqQueuePktThreshold
      Unsigned32,
   frDteLeqPktThresholdExceeded
      Counter32,
   frDteLeqQueueByteThreshold
      Unsigned32,
   frDteLeqByteThresholdExceeded
      Counter32,
   frDteLeqQueueMulticastThreshold
      Unsigned32,
   frDteLeqMulThresholdExceeded
      Counter32,
   frDteLeqMemThresholdExceeded
      Counter32 }

frDteLeqQueuePktThreshold OBJECT-TYPE
   SYNTAX     Unsigned32 (0..4294967295)
   ACCESS     read-only
   STATUS     mandatory
   DESCRIPTION
     "This attribute is the maximum number of packets that can be contained 
      in the queue before being discarded. If maxPackets was set to 0 then this 
      attribute will contain the value that has been calculated based on the 
      transmit data rate. If maxPackets was set to one or more than this 
      attribute will contain that number."
   DEFVAL     { 0 }
::= { frDteLeqThrStatsEntry 1 }

frDteLeqPktThresholdExceeded OBJECT-TYPE
   SYNTAX     Counter32 
   ACCESS     read-only
   STATUS     mandatory
   DESCRIPTION
     "This attribute counts the number of packets discarded due to the 
      queuePktThreshold being exceeded. This counter will wrap around to 0 
      when it exceeds its maximum count."
::= { frDteLeqThrStatsEntry 2 }

frDteLeqQueueByteThreshold OBJECT-TYPE
   SYNTAX     Unsigned32 (0..4294967295)
   ACCESS     read-only
   STATUS     mandatory
   DESCRIPTION
     "This attribute is the maximum number of bytes allowed in the queue 
      based on maxMsecData and the transmit data rate."
   DEFVAL     { 0 }
::= { frDteLeqThrStatsEntry 3 }

frDteLeqByteThresholdExceeded OBJECT-TYPE
   SYNTAX     Counter32 
   ACCESS     read-only
   STATUS     mandatory
   DESCRIPTION
     "This attribute counts the number of packets discarded due to the 
      queueByteThreshold being exceeded. This counter will wrap around to 0 
      when it exceeds its maximum count."
::= { frDteLeqThrStatsEntry 4 }

frDteLeqQueueMulticastThreshold OBJECT-TYPE
   SYNTAX     Unsigned32 (0..4294967295)
   ACCESS     read-only
   STATUS     mandatory
   DESCRIPTION
     "This attribute is the number of multicast packets allowed in the queue 
      based on maxPercentMulticast and maxPackets."
   DEFVAL     { 0 }
::= { frDteLeqThrStatsEntry 5 }

frDteLeqMulThresholdExceeded OBJECT-TYPE
   SYNTAX     Counter32 
   ACCESS     read-only
   STATUS     mandatory
   DESCRIPTION
     "This attribute counts the number of packets discarded due to the 
      queueMulticastThreshold being exceeded. This counter will wrap 
      around to 0 when it exceeds its maximum count."
::= { frDteLeqThrStatsEntry 6 }

frDteLeqMemThresholdExceeded OBJECT-TYPE
   SYNTAX     Counter32 
   ACCESS     read-only
   STATUS     mandatory
   DESCRIPTION
     "This attribute counts the number of packets discarded due to exceeding 
      the memory usage threshold for Leq. The memory usage threshold is 
      determined by the Leq software, guaranteeing that the Leq does not 
      consume all of the memory. This counter will wrap around to 0 when it 
      exceeds its maximum count."
::= { frDteLeqThrStatsEntry 7 }

-- 
-- *** THIS SUBTREE CURRENTLY NOT IMPLEMENTED ***
-- 

-- FrDte/n Dlci/n
-- This component provides access to both static and dynamic virtual 
-- circuit instances.

frDteDlci OBJECT IDENTIFIER ::= { frDte 8 }



frDteDlciRowStatusTable OBJECT-TYPE
   SYNTAX     SEQUENCE OF FrDteDlciRowStatusEntry
   ACCESS     not-accessible
   STATUS     mandatory
   DESCRIPTION
     "*** THIS TABLE CURRENTLY NOT IMPLEMENTED ***

      This entry controls the addition and deletion of 
      frDteDlci components."
::= { frDteDlci 1 }

frDteDlciRowStatusEntry OBJECT-TYPE
   SYNTAX     FrDteDlciRowStatusEntry
   ACCESS     not-accessible
   STATUS     mandatory
   DESCRIPTION
     "A single entry in the table represents a single 
      frDteDlci component."
   INDEX {
      frDteIndex,
      frDteDlciIndex }
::= { frDteDlciRowStatusTable 1 }

FrDteDlciRowStatusEntry ::= SEQUENCE {
   frDteDlciRowStatus
      RowStatus,
   frDteDlciComponentName
      DisplayString,
   frDteDlciStorageType
      StorageType,
   frDteDlciIndex
      Integer32 }

frDteDlciRowStatus OBJECT-TYPE
   SYNTAX     RowStatus 
   ACCESS     read-only
   STATUS     mandatory
   DESCRIPTION
     "This variable is used as the basis for SNMP naming of
      frDteDlci components.
      These components cannot be added nor deleted."
::= { frDteDlciRowStatusEntry 1 }

frDteDlciComponentName OBJECT-TYPE
   SYNTAX     DisplayString 
   ACCESS     read-only
   STATUS     mandatory
   DESCRIPTION
     "This variable provides the component's string name for
      use with the ASCII Console Interface"
::= { frDteDlciRowStatusEntry 2 }

frDteDlciStorageType OBJECT-TYPE
   SYNTAX     StorageType 
   ACCESS     read-only
   STATUS     mandatory
   DESCRIPTION
     "This variable represents the storage type value for the
      frDteDlci tables."
::= { frDteDlciRowStatusEntry 4 }

frDteDlciIndex OBJECT-TYPE
   SYNTAX     Integer32 (0..1023)
   ACCESS     not-accessible
   STATUS     mandatory
   DESCRIPTION
     "This variable represents the index for the frDteDlci tables."
::= { frDteDlciRowStatusEntry 10 }

frDteDlciStateTable OBJECT-TYPE
   SYNTAX     SEQUENCE OF FrDteDlciStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frDteDlci 10 }

frDteDlciStateEntry OBJECT-TYPE
   SYNTAX     FrDteDlciStateEntry
   ACCESS     not-accessible
   STATUS     mandatory
   DESCRIPTION
     "An entry in the frDteDlciStateTable."
   INDEX {
      frDteIndex,
      frDteDlciIndex }
::= { frDteDlciStateTable 1 }

FrDteDlciStateEntry ::= SEQUENCE {
   frDteDlciAdminState
      INTEGER,
   frDteDlciOperationalState
      INTEGER,
   frDteDlciUsageState
      INTEGER }

frDteDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frDteDlciStateEntry 1 }

frDteDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frDteDlciStateEntry 2 }

frDteDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frDteDlciStateEntry 3 }

frDteDlciOperTable OBJECT-TYPE
   SYNTAX     SEQUENCE OF FrDteDlciOperEntry
   ACCESS     not-accessible
   STATUS     mandatory
   DESCRIPTION
     "*** THIS TABLE CURRENTLY NOT IMPLEMENTED ***

      This group contains the operational attributes for the Dlci component."
::= { frDteDlci 11 }

frDteDlciOperEntry OBJECT-TYPE
   SYNTAX     FrDteDlciOperEntry
   ACCESS     not-accessible
   STATUS     mandatory
   DESCRIPTION
     "An entry in the frDteDlciOperTable."
   INDEX {
      frDteIndex,
      frDteDlciIndex }
::= { frDteDlciOperTable 1 }

FrDteDlciOperEntry ::= SEQUENCE {
   frDteDlciDlciState
      INTEGER,
   frDteDlciLastTimeChange
      EnterpriseDateAndTime,
   frDteDlciSentFrames
      Counter32,
   frDteDlciSentOctets
      Counter32,
   frDteDlciReceivedFrames
      Counter32,
   frDteDlciReceivedOctets
      Counter32,
   frDteDlciReceivedFECNs
      Counter32,
   frDteDlciReceivedBECNs
      Counter32,
   frDteDlciDiscardedFrames
      Counter32,
   frDteDlciCreationType
      INTEGER,
   frDteDlciCreationTime
      EnterpriseDateAndTime,
   frDteDlciRateEnforcement
      INTEGER,
   frDteDlciCommittedInformationRate
      Gauge32,
   frDteDlciCommittedBurst
      Unsigned32,
   frDteDlciExcessBurst
      Unsigned32,
   frDteDlciExcessBurstAction
      INTEGER }

frDteDlciDlciState OBJECT-TYPE
   SYNTAX     INTEGER  {
                 invalid(1),
                 active(2),
                 inactive(3) }
   ACCESS     read-only
   STATUS     mandatory
   DESCRIPTION
     "This attribute reflects the current operational circuit state of the Dlci. 
      The state active indicates that the circuit is up and inactive that the 
      circuit is down. The state invalid means the circuit has been deleted by 
      the DCE (via Lmi)."
   DEFVAL     { inactive }
::= { frDteDlciOperEntry 4 }

frDteDlciLastTimeChange OBJECT-TYPE
   SYNTAX     EnterpriseDateAndTime (SIZE (0 | 19))
   ACCESS     read-only
   STATUS     mandatory
   DESCRIPTION
     "The last time dlciState changed state."
::= { frDteDlciOperEntry 5 }

frDteDlciSentFrames OBJECT-TYPE
   SYNTAX     Counter32 
   ACCESS     read-only
   STATUS     mandatory
   DESCRIPTION
     "Number of frames transmitted across the interface. This counter will 
      wrap around to 0 when it exceeds its maximum count."
::= { frDteDlciOperEntry 7 }

frDteDlciSentOctets OBJECT-TYPE
   SYNTAX     Counter32 
   ACCESS     read-only
   STATUS     mandatory
   DESCRIPTION
     "The number of octets sent from this virtual circuit since it was created. 
      This counter will wrap around to 0 when it exceeds its maximum count."
::= { frDteDlciOperEntry 8 }

frDteDlciReceivedFrames OBJECT-TYPE
   SYNTAX     Counter32 
   ACCESS     read-only
   STATUS     mandatory
   DESCRIPTION
     "Number of frames received across the interface. This counter will wrap 
      around to 0 when it exceeds its maximum count."
::= { frDteDlciOperEntry 9 }

frDteDlciReceivedOctets OBJECT-TYPE
   SYNTAX     Counter32 
   ACCESS     read-only
   STATUS     mandatory
   DESCRIPTION
     "The number of octets sent from this virtual circuit since it was created. 
      This counter will wrap around to 0 when it exceeds its maximum count."
::= { frDteDlciOperEntry 10 }

frDteDlciReceivedFECNs OBJECT-TYPE
   SYNTAX     Counter32 
   ACCESS     read-only
   STATUS     mandatory
   DESCRIPTION
     "Number of frames with the FECN bit set received from the network. 
      This counter will wrap around to 0 when it exceeds its maximum count."
::= { frDteDlciOperEntry 11 }

frDteDlciReceivedBECNs OBJECT-TYPE
   SYNTAX     Counter32 
   ACCESS     read-only
   STATUS     mandatory
   DESCRIPTION
     "Number of frames with the BECN bit set received from the network. 
      This counter will wrap around to 0 when it exceeds its maximum count."
::= { frDteDlciOperEntry 12 }

frDteDlciDiscardedFrames OBJECT-TYPE
   SYNTAX     Counter32 
   ACCESS     read-only
   STATUS     mandatory
   DESCRIPTION
     "The number of inbound frames dropped because of format errors, or 
      because the VC was inactive. This counter will wrap around to 0 when it 
      exceeds its maximum count."
::= { frDteDlciOperEntry 13 }

frDteDlciCreationType OBJECT-TYPE
   SYNTAX     INTEGER  {
                 static(1),
                 dynamic(2) }
   ACCESS     read-only
   STATUS     mandatory
   DESCRIPTION
     "This indicates whether the virtual circuit was manually created (static), 
      or dynamically created (dynamic) via the data link control management 
      interface."
::= { frDteDlciOperEntry 14 }

frDteDlciCreationTime OBJECT-TYPE
   SYNTAX     EnterpriseDateAndTime (SIZE (0 | 19))
   ACCESS     read-only
   STATUS     mandatory
   DESCRIPTION
     "The time when the circuit was created, whether by the Data Link 
      Connection Management Interface or by an SNMP set request."
::= { frDteDlciOperEntry 15 }

frDteDlciRateEnforcement OBJECT-TYPE
   SYNTAX     INTEGER  {
                 enabled(1),
                 disabled(2) }
   ACCESS     read-write
   STATUS     mandatory
   DESCRIPTION
     "This attribute specifies whether the CIR attributes 
      committedInformationRate, committedBurst, and excessBurst are used to 
      define rate enforcement on this user DLCI.
      
      If rateEnforcement is enabled, and the combined Committed and Excess 
      burst thresholds are exceeded, the frame in violation will be discarded 
      immediately if a HibernationQueue subcomponent is not provisioned 
      under the StDlci component (static entries only). If a HibernationQueue 
      is provisioned, the frame will be placed on the HibernationQueue at 
      time of violation and transmission will be attempted later after the point 
      at which the burst thresholds will no longer be exceeded.
      
      Setting all the CIR attributes to zero has the same affect as setting this 
      attribute to disabled.
      
      Setting this attribute will operationally override the corresponding 
      provisional value on static entries."
   DEFVAL     { disabled }
::= { frDteDlciOperEntry 17 }

frDteDlciCommittedInformationRate OBJECT-TYPE
   SYNTAX     Gauge32 (0..48000000)
   ACCESS     read-write
   STATUS     mandatory
   DESCRIPTION
     "The average number of bits to be transferred per second over the DLCI 
      to the DCE. When this attribute is set to zero, the link speed will be used 
      instead.
      
      Setting this attribute will operationally override the corresponding 
      provisional value on static entries."
   DEFVAL     { 64000 }
::= { frDteDlciOperEntry 18 }

frDteDlciCommittedBurst OBJECT-TYPE
   SYNTAX     Unsigned32 (0..2048000)
   ACCESS     read-write
   STATUS     mandatory
   DESCRIPTION
     "The committed burst size (in bits) to which the DLCI wants to 
      subscribe.
      
      Setting this attribute will operationally override the corresponding 
      provisional value on static entries."
   DEFVAL     { 64000 }
::= { frDteDlciOperEntry 19 }

frDteDlciExcessBurst OBJECT-TYPE
   SYNTAX     Unsigned32 (0..2048000)
   ACCESS     read-write
   STATUS     mandatory
   DESCRIPTION
     "The excess burst size (in bits) to which the DLCI wants to subscribe.
      
      Setting this attribute will operationally override the corresponding 
      provisional value on static entries."
   DEFVAL     { 0 }
::= { frDteDlciOperEntry 20 }

frDteDlciExcessBurstAction OBJECT-TYPE
   SYNTAX     INTEGER  {
                 none(1),
                 setDeBit(2) }
   ACCESS     read-write
   STATUS     mandatory
   DESCRIPTION
     "This attribute specifies the action taken when the committedBurst size 
      has been exceeded on the Dlci but the excessBurst size has not. If the 
      attribute is set to setDeBit, the Discard Eligibility bit in the Frame Relay 
      header will be turned on. If the attribute is set to none, no action will be 
      taken.
      
      Setting this attribute will operationally override the corresponding 
      provisional value on static entries."
   DEFVAL     { none }
::= { frDteDlciOperEntry 21 }


-- FrUni/n VirtualFramer
-- FrDte/n VirtualFramer
-- The VirtualFramer component binds two services together to 
-- provide data transfer between them. It is mutually exclusive from 
-- Framer component. 

frDteVFramer OBJECT IDENTIFIER ::= { frDte 9 }



frDteVFramerRowStatusTable OBJECT-TYPE
   SYNTAX     SEQUENCE OF FrDteVFramerRowStatusEntry
   ACCESS     not-accessible
   STATUS     mandatory
   DESCRIPTION
     "This entry controls the addition and deletion of 
      frDteVFramer components."
::= { frDteVFramer 1 }

frDteVFramerRowStatusEntry OBJECT-TYPE
   SYNTAX     FrDteVFramerRowStatusEntry
   ACCESS     not-accessible
   STATUS     mandatory
   DESCRIPTION
     "A single entry in the table represents a single 
      frDteVFramer component."
   INDEX {
      frDteIndex,
      frDteVFramerIndex }
::= { frDteVFramerRowStatusTable 1 }

FrDteVFramerRowStatusEntry ::= SEQUENCE {
   frDteVFramerRowStatus
      RowStatus,
   frDteVFramerComponentName
      DisplayString,
   frDteVFramerStorageType
      StorageType,
   frDteVFramerIndex
      NonReplicated }

frDteVFramerRowStatus OBJECT-TYPE
   SYNTAX     RowStatus 
   ACCESS     read-write
   STATUS     mandatory
   DESCRIPTION
     "This variable is used as the basis for SNMP naming of
      frDteVFramer components.
      These components can be added and deleted."
::= { frDteVFramerRowStatusEntry 1 }

frDteVFramerComponentName OBJECT-TYPE
   SYNTAX     DisplayString 
   ACCESS     read-only
   STATUS     mandatory
   DESCRIPTION
     "This variable provides the component's string name for
      use with the ASCII Console Interface"
::= { frDteVFramerRowStatusEntry 2 }

frDteVFramerStorageType OBJECT-TYPE
   SYNTAX     StorageType 
   ACCESS     read-only
   STATUS     mandatory
   DESCRIPTION
     "This variable represents the storage type value for the
      frDteVFramer tables."
::= { frDteVFramerRowStatusEntry 4 }

frDteVFramerIndex OBJECT-TYPE
   SYNTAX     NonReplicated 
   ACCESS     not-accessible
   STATUS     mandatory
   DESCRIPTION
     "This variable represents the index for the frDteVFramer tables."
::= { frDteVFramerRowStatusEntry 10 }

frDteVFramerProvTable OBJECT-TYPE
   SYNTAX     SEQUENCE OF FrDteVFramerProvEntry
   ACCESS     not-accessible
   STATUS     mandatory
   DESCRIPTION
     "This group contains provisionable attributes for the VirtualFramer 
      component."
::= { frDteVFramer 10 }

frDteVFramerProvEntry OBJECT-TYPE
   SYNTAX     FrDteVFramerProvEntry
   ACCESS     not-accessible
   STATUS     mandatory
   DESCRIPTION
     "An entry in the frDteVFramerProvTable."
   INDEX {
      frDteIndex,
      frDteVFramerIndex }
::= { frDteVFramerProvTable 1 }

FrDteVFramerProvEntry ::= SEQUENCE {
   frDteVFramerOtherVirtualFramer
      Link,
   frDteVFramerLogicalProcessor
      Link }

frDteVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { frDteVFramerProvEntry 1 }

frDteVFramerLogicalProcessor OBJECT-TYPE
   SYNTAX     Link 
   ACCESS     read-write
   STATUS     mandatory
   DESCRIPTION
     "This attribute specifies the logical processor on which the service 
      component will reside."
::= { frDteVFramerProvEntry 2 }

frDteVFramerStateTable OBJECT-TYPE
   SYNTAX     SEQUENCE OF FrDteVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frDteVFramer 11 }

frDteVFramerStateEntry OBJECT-TYPE
   SYNTAX     FrDteVFramerStateEntry
   ACCESS     not-accessible
   STATUS     mandatory
   DESCRIPTION
     "An entry in the frDteVFramerStateTable."
   INDEX {
      frDteIndex,
      frDteVFramerIndex }
::= { frDteVFramerStateTable 1 }

FrDteVFramerStateEntry ::= SEQUENCE {
   frDteVFramerAdminState
      INTEGER,
   frDteVFramerOperationalState
      INTEGER,
   frDteVFramerUsageState
      INTEGER }

frDteVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frDteVFramerStateEntry 1 }

frDteVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frDteVFramerStateEntry 2 }

frDteVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frDteVFramerStateEntry 3 }

frDteVFramerStatsTable OBJECT-TYPE
   SYNTAX     SEQUENCE OF FrDteVFramerStatsEntry
   ACCESS     not-accessible
   STATUS     mandatory
   DESCRIPTION
     "This group contains the operational statistics data for a 
      VirtualFramer component."
::= { frDteVFramer 12 }

frDteVFramerStatsEntry OBJECT-TYPE
   SYNTAX     FrDteVFramerStatsEntry
   ACCESS     not-accessible
   STATUS     mandatory
   DESCRIPTION
     "An entry in the frDteVFramerStatsTable."
   INDEX {
      frDteIndex,
      frDteVFramerIndex }
::= { frDteVFramerStatsTable 1 }

FrDteVFramerStatsEntry ::= SEQUENCE {
   frDteVFramerFrmToOtherVFramer
      PassportCounter64,
   frDteVFramerFrmFromOtherVFramer
      PassportCounter64,
   frDteVFramerOctetFromOtherVFramer
      PassportCounter64 }

frDteVFramerFrmToOtherVFramer OBJECT-TYPE
   SYNTAX     PassportCounter64 
   ACCESS     read-only
   STATUS     mandatory
   DESCRIPTION
     "This attribute counts the frames transmitted to the 
      otherVirtualFramer."
::= { frDteVFramerStatsEntry 2 }

frDteVFramerFrmFromOtherVFramer OBJECT-TYPE
   SYNTAX     PassportCounter64 
   ACCESS     read-only
   STATUS     mandatory
   DESCRIPTION
     "This attribute counts the frames received from the 
      otherVirtualFramer."
::= { frDteVFramerStatsEntry 3 }

frDteVFramerOctetFromOtherVFramer OBJECT-TYPE
   SYNTAX     PassportCounter64 
   ACCESS     read-only
   STATUS     mandatory
   DESCRIPTION
     "This attribute counts the octets received from the 
      otherVirtualFramer."
::= { frDteVFramerStatsEntry 5 }




-- 
-- Version and Compliance statements
-- 



-- Object-Group Statement:
-- A list of all current accessible leaf objects.

-- OBJECTS { frDteDynDlciDefsRateEnforcement,
--           frDteCustomerIdentifier,
--           frDteStDlciHqMemThresholdExceeded,
--           frDteFramerNonOctetErrors,
--           frDteDlciReceivedBECNs,
--           frDteFramerUsageState,
--           frDteDlcmiProtoErr,
--           frDteStDlciHqQueuePktThreshold,
--           frDteFramerNormPrioLinkUtilFromIf,
--           frDteRgBfrComponentName,
--           frDteFramerLargeFrmErrors,
--           frDteUsageState,
--           frDteStDlciCommittedInformationRate,
--           frDteLeqTotalPktQueued,
--           frDteLeqMemThresholdExceeded,
--           frDteStDlciStdRowStatus,
--           frDteFramerInterfaceName,
--           frDteDlciExcessBurstAction,
--           frDteLmiStorageType,
--           frDteStDlciExcessBurst,
--           frDteErrData,
--           frDteStDlciHqQueueByteThreshold,
--           frDteStDlciComponentName,
--           frDteFramerOperationalState,
--           frDteErrType,
--           frDteVFramerUsageState,
--           frDteStDlciHqTotalPktQueued,
--           frDteOperationalState,
--           frDteDlciOperationalState,
--           frDteDlcmiUnknownRpt,
--           frDteLeqCurrentBytesQueued,
--           frDteStDlciHqRowStatus,
--           frDteVFramerComponentName,
--           frDteStDlciHqQueuePurgeDiscards,
--           frDteDlciSentOctets,
--           frDteFramerLrcErrors,
--           frDteLeqTotalPktHandled,
--           frDteLmiRowStatus,
--           frDteFramerAborts,
--           frDteRgComponentName,
--           frDteStDlciExcessBurstAction,
--           frDteStDlciHqCurrentPktQueued,
--           frDteStDlciHqTotalPktDiscards,
--           frDteDlciCommittedBurst,
--           frDteXmitDiscardFramerDown,
--           frDteVFramerLogicalProcessor,
--           frDteDynDlciDefsCommittedBurst,
--           frDteStDlciHqQueueMulticastThreshold,
--           frDteLeqTotalPktForwarded,
--           frDteLeqCurrentPktQueued,
--           frDteLeqTotalPktDiscards,
--           frDteVFramerOperationalState,
--           frDteLeqMaxPercentMulticast,
--           frDteXmitDiscardCirExceeded,
--           frDteErrDiscards,
--           frDteLinkOperState,
--           frDteRgBfrStorageType,
--           frDteErrFaultTime,
--           frDteVFramerOtherVirtualFramer,
--           frDteAcceptUndefinedDlci,
--           frDteStDlciHqTimeToLive,
--           frDteLeqForcedPktDiscards,
--           frDteStDlciHqTotalPktHandled,
--           frDteDlciReceivedFrames,
--           frDteFramerUnderruns,
--           frDteRgBfrMacType,
--           frDteStDlciStorageType,
--           frDteDynDlciDefsIpCos,
--           frDteDlciReceivedOctets,
--           frDteStDlciCommittedBurst,
--           frDteDlciCreationTime,
--           frDteLeqTimeToLive,
--           frDteDlciCreationType,
--           frDteReceiveShort,
--           frDteXmitDiscardPvcInactive,
--           frDteXmitDiscardPvcDown,
--           frDteDynDlciDefsExcessBurstAction,
--           frDteDlcmiUnknownIe,
--           frDteRgSnmpOperStatus,
--           frDteRgIfIndex,
--           frDteStDlciHqTotalMulticastPkt,
--           frDteDlciComponentName,
--           frDteRgBfrRowStatus,
--           frDteDlciCommittedInformationRate,
--           frDteLmiErrorThreshold,
--           frDteStDlciHqCurrentMulticastQueued,
--           frDteVFramerRowStatus,
--           frDteVFramerStorageType,
--           frDteComponentName,
--           frDteDlciExcessBurst,
--           frDteLmiPollingInterval,
--           frDteDynDlciDefsCommittedInformationRate,
--           frDteLeqTotalMulticastPkt,
--           frDteRgStorageType,
--           frDteLeqQueueMulticastThreshold,
--           frDteStDlciRowStatus,
--           frDteDynDlciDefsExcessBurst,
--           frDteRgMaxTransmissionUnit,
--           frDteErrTime,
--           frDteDynDlciDefsComponentName,
--           frDteStDlciHqPktThresholdExceeded,
--           frDteDlciLastTimeChange,
--           frDteFramerComponentName,
--           frDteStDlciHqStorageType,
--           frDteVFramerOctetFromOtherVFramer,
--           frDteStDlciRateEnforcement,
--           frDteLeqMaxMsecData,
--           frDteStDlciHqMaxMsecData,
--           frDteFramerFrmToIf,
--           frDteDlciDlciState,
--           frDteDlciReceivedFECNs,
--           frDteRgAdminState,
--           frDteLmiMonitoredEvents,
--           frDteStDlciHqMaxPackets,
--           frDteLmiLmiStatus,
--           frDteRgBfrMacAddr,
--           frDteDlcmiSequenceErr,
--           frDteRgIfAdminStatus,
--           frDteLeqQueuePktThreshold,
--           frDteStDlciHqMaxPercentMulticast,
--           frDteLeqMaxPackets,
--           frDteErrFaults,
--           frDteRgLtDlciRowStatus,
--           frDteIllegalDlci,
--           frDteLeqCurrentMulticastQueued,
--           frDteRgBfrBfrIndex,
--           frDteLeqPktThresholdExceeded,
--           frDteRgUsageState,
--           frDteStDlciHqByteThresholdExceeded,
--           frDteLeqComponentName,
--           frDteStDlciLinkToRemoteGroup,
--           frDteRgLtDlciValue,
--           frDteDlciSentFrames,
--           frDteDynDlciDefsStdRowStatus,
--           frDteRecvDiscardPvcDown,
--           frDteStDlciHqComponentName,
--           frDteLeqStorageType,
--           frDteLeqByteThresholdExceeded,
--           frDteDefragSequenceErrors,
--           frDteLeqHardwareForcedPkt,
--           frDteDlciStorageType,
--           frDteSnmpOperStatus,
--           frDteRgOperationalState,
--           frDteBadFc,
--           frDteIfIndex,
--           frDteLeqQueuePurgeDiscards,
--           frDteFramerNormPrioLinkUtilToIf,
--           frDteLmiComponentName,
--           frDteRowStatus,
--           frDteDynDlciDefsStorageType,
--           frDteFramerFrmFromIf,
--           frDteRecvDiscardPvcInactive,
--           frDteFramerStorageType,
--           frDteFramerAdminState,
--           frDteLmiProcedures,
--           frDteStDlciHqTimedOutPkt,
--           frDteRecvDiscardLmiInactive,
--           frDteFramerCrcErrors,
--           frDteStorageType,
--           frDteLeqTimedOutPkt,
--           frDteRgLinkToProtocolPort,
--           frDteDlciAdminState,
--           frDteLeqRowStatus,
--           frDteStDlciIpCos,
--           frDteStDlciHqTotalPktForwarded,
--           frDteVFramerFrmToOtherVFramer,
--           frDteStDlciHqMulThresholdExceeded,
--           frDteDlciRowStatus,
--           frDteFramerOverruns,
--           frDteLmiFullEnquiryInterval,
--           frDteUlpUnknownProtocol,
--           frDteXmitDiscardLmiInactive,
--           frDteDlciDiscardedFrames,
--           frDteVFramerAdminState,
--           frDteDynDlciDefsRowStatus,
--           frDteAdminState,
--           frDteStDlciHqCurrentBytesQueued,
--           frDteLeqMulThresholdExceeded,
--           frDteFramerRowStatus,
--           frDteDlciRateEnforcement,
--           frDteLeqQueueByteThreshold,
--           frDteDlciUsageState,
--           frDteIfAdminStatus,
--           frDteVFramerFrmFromOtherVFramer,
--           frDteRgRowStatus }
-- STATUS  mandatory
-- DESCRIPTION
--   "A list of all current accessible leaf objects."

frameRelayDteGroup OBJECT IDENTIFIER ::= { frameRelayDteMIB 1 }
frameRelayDteGroupBE OBJECT IDENTIFIER ::= { frameRelayDteGroup 5 }
frameRelayDteGroupBE00 OBJECT IDENTIFIER ::= { frameRelayDteGroupBE 1 }
frameRelayDteGroupBE00A OBJECT IDENTIFIER ::= { frameRelayDteGroupBE00 2 }



-- Agent-Capabilities Statement:

-- PRODUCT-RELEASE "Passport Release 7.0 FrameRelayDte."
-- STATUS          mandatory
-- DESCRIPTION     "FrameRelayDte MIB: MIB Version BE00A,
--                  Software Version BG00S4C."
-- SUPPORTS        Nortel-Magellan-Passport-FrameRelayDteMIB
--    INCLUDES     { frameRelayDteGroupBE00A }
--        draft-ietf-iplpdn-frmib-dte-02.txt
--        (a draft for the evolution of RFC1315)
-- 
-- SUPPORTS RFCxxxx-MIB
--    INCLUDES        { frDlcmiTable, frCircuitTable, frErrTable }  
--     				   frameRelayTrapControl is not supported.
--  
--        variations for frDlcmiTable
--  
--    VARIATION		frDlcmiState
--       SYNTAX INTEGER      {
--       noLmiConfigured   (1),
--       lmiRev1           (2),
--       ansiT1-617-D      (3),     ANSI T1.617 Annex D
--       ccitt-933-A       (5)      CCITT Q933 Annex A
--       }
--       DEFVAL            { ccitt-933-A }
--       DESCRIPTION       "The ANSI T1.617 Annix B procedures are not supported."
--  
--    VARIATION		frDlcmiAddress
--       SYNTAX INTEGER      {
--       q922              (4)      Final Standard
--       }
--       DEFVAL            { q922 }
--       DESCRIPTION       "The Q.921, Q.922 (March 90), and Q.922 (November 90)
--                         address schemes are not supported."
--  
--    VARIATION		frDlcmiAddressLen
--       SYNTAX INTEGER      {
--       two-octets        (2)
--       }
--       DEFVAL            { two-octets }
--       DESCRIPTION       "Three and four octet addresses are not supported."
--  
--    VARIATION		frDlcmiMaxSupportedVCs
--       SYNTAX            Integer32 (1024)
--       DEFVAL            { 1024 }
--       DESCRIPTION       "Only 1024 virtual circuits are supported per ifEntry."
--  
--    VARIATION		frDlcmiMulticast
--       SYNTAX INTEGER      {
--        nonBroadcast     (1)
--       }
--       DEFVAL            { nonBroadcast }
--       DESCRIPTION       "Broadcast virtual circuits are not supported."
--  
--       variations for frCircuitTable
--  
--    VARIATION		frCircuitState
--       MAX-ACCESS        read-only
--       DEFVAL            { inactive }
--       DESCRIPTION       "Write access is not supported, use frCircuitRowStatus
--                         instead.  Defaults to inactive."
--  
--    VARIATION		frCircuitCommittedBurst
--       DEFVAL            { 64000 }
--       DESCRIPTION       "This implementation defaults to 64000 bits."
--  
--    VARIATION		frCircuitThroughput
--       DEFVAL            { 64000 }
--       DESCRIPTION       "This implementation defaults to 64000 bits/sec."
-- 
-- 
-- 
-- 

frameRelayDteCapabilities OBJECT IDENTIFIER ::= { frameRelayDteMIB 3 }
frameRelayDteCapabilitiesBE OBJECT IDENTIFIER ::= { frameRelayDteCapabilities 5 }
frameRelayDteCapabilitiesBE00 OBJECT IDENTIFIER ::= { frameRelayDteCapabilitiesBE 1 }
frameRelayDteCapabilitiesBE00A OBJECT IDENTIFIER ::= { frameRelayDteCapabilitiesBE00 2 }





END
