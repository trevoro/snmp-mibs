-- 
-- Copyright 1999 by Fore Systems, Inc. 
-- Converted to SMIv2 rfc 2578,2579,2580 - STD 58
--
-- Copyright 1993, 1994, 1995 by Fore Systems, Inc.

Fore-E1-MIB DEFINITIONS ::= BEGIN

IMPORTS
	Counter32, Integer32,
	OBJECT-TYPE,
	MODULE-IDENTITY				FROM SNMPv2-SMI
	asx					FROM Fore-Common-MIB;

------------------------------------------------------------------------
-- The implementation of the foreE1 tables is mandatory
-- for all switches that have E1 port module.

foreE1    MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION
           "This mib implements management tables for the E1 port module."
    ::= { asx 8 }

e1ConfGroup		OBJECT IDENTIFIER ::= { foreE1 1 }
e1StatsGroup		OBJECT IDENTIFIER ::= { foreE1 2 }

------------------------------------------------------------------------
-- The E1 configuration Group

e1ConfTable OBJECT-TYPE
	SYNTAX	SEQUENCE OF E1ConfEntry
	MAX-ACCESS	not-accessible
	STATUS	current
	DESCRIPTION
		"A table of E1 switch port configuration information."
	::= { e1ConfGroup 1 }

e1ConfEntry OBJECT-TYPE
	SYNTAX	E1ConfEntry
	MAX-ACCESS	not-accessible
	STATUS	current
	DESCRIPTION
		"A table entry containing E1 configuration information for each
		port. Not all RFC1406 configuration table variables are
		included, and some are modified."
	INDEX	{ e1ConfBoard, e1ConfModule, e1ConfPort }
	::= { e1ConfTable 1 }

E1ConfEntry ::=
	SEQUENCE {
		e1ConfBoard		Integer32,
		e1ConfModule		Integer32,
		e1ConfPort		Integer32,
		e1LineType		INTEGER,
		e1LineCoding		INTEGER,
		e1SendCode		INTEGER,
		e1ReceiveCode		INTEGER,
		e1LoopbackConfig	INTEGER,
		e1TxClockSource		INTEGER,
		e1LineStatus		INTEGER,
		e1IdleUnassignedCells	INTEGER,
		e1LineLength		INTEGER,
		e1LineTypeFraming	INTEGER,
		e1RxScrambling		INTEGER,
		e1TxScrambling		INTEGER
}

e1ConfBoard OBJECT-TYPE
	SYNTAX	Integer32
	MAX-ACCESS	read-only
	STATUS	current
	DESCRIPTION
		"The index of this port's switch board."
	::= { e1ConfEntry 1 }

e1ConfModule OBJECT-TYPE
	SYNTAX	Integer32
	MAX-ACCESS	read-only
	STATUS	current
	DESCRIPTION
		"The network module of this port."
	::= { e1ConfEntry 2 }

e1ConfPort OBJECT-TYPE
	SYNTAX	Integer32
	MAX-ACCESS	read-only
	STATUS	current
	DESCRIPTION
		"The number of this port."
	::= { e1ConfEntry 3 }

e1LineType OBJECT-TYPE
	SYNTAX	INTEGER {
		e1Other (1),
		e1NoCRC (2),
		e1CRC (3),
		e1MF (4),
		e1CRCMF (5)
		}
	MAX-ACCESS	read-only
	STATUS	current
	DESCRIPTION
		"This variable indicates the variety of E1 Line implementing
		this circuit. The type of circuit affects the number of bits
		per second that the circuit can reasonably carry, as well as
		the interpretation of the usage and error statistics. This
		variable is defined in the rfc1406 configuration table as
		dsx1LineType.

		According to rfc1406, the different values are:
		e1NoCRC		CCITT recommendation G.704 (table a)
		e1CRC		CCITT recommendation G.704 (table b)
		e1MF		G.704(table a) with TS16 multifatming enabled
		e1MFCRC		G.704(table b) with TS16 multifatming enabled."
	::= { e1ConfEntry 4 }

e1LineCoding OBJECT-TYPE
	SYNTAX	INTEGER {
		e1Other (1),
		e1HDB3 (2),
		e1AMI (3)
		}
	MAX-ACCESS	read-only
	STATUS	current
	DESCRIPTION
		"This variable describes the variety of Zero Code suppression
		used on this link, which in turn affects a number of its
		characteristics. e1AMI(3) refers to a mode wherein no zero
		code suppression is present and the line encoding does not
		solve the problem directly. In this application, the higher
		layer must provide data which meets or exceeds the pulse
		density re-quirements, such as inverting HDLC data. This
		variable is defined in the rfc1406 configuration table as
		dsx1LineCoding."
	::= { e1ConfEntry 5 }

e1SendCode OBJECT-TYPE
	SYNTAX	INTEGER {
		e1SendNoCode (1),
		e1SendLineCode (2),
		e1SendPayloadCode (3),
		e1SendResetCode (4),
		e1SendQRS (5),
		e1Send511Pattern (6),
		e1Send3in24Pattern (7),
		e1SendOtherTestPattern (8)
		}
	MAX-ACCESS	read-only
	STATUS	current
	DESCRIPTION
		"This variable indicates what type of code is being sent across
		the E1 interface by the device.

		The values mean:
		e1SendNoCode		sending looped or normal data
		e1SendLineCode		sending request for a line loopback
		e1SendPayloadCode	sending a request for a payload
					loopback
		e1SendResetCode		sending a loopback termination request
		e1SendQRS		sending a Quasi-Random Signal (QRS)
					test pattern
		e1Send511Pattern	sending a 511 bit fixed test pattern
		e1Send3in24Pattern	sending a fixed test pattern of 3 bits
					set in 24
		e1SendOtherTestPattern	sending a test pattern other than the
					above."
	::= { e1ConfEntry 6 }

e1ReceiveCode OBJECT-TYPE
	SYNTAX	INTEGER {
		e1ReceiveNoCode (1),
		e1ReceiveLineCode (2),
		e1ReceivePayloadCode (3),
		e1ReceiveResetCode (4),
		e1SendQRS (5),
		e1Send511Pattern (6),
		e1Send3in24Pattern (7),
		e1SendOtherTestPattern (8)
		}
	MAX-ACCESS	read-only
	STATUS	current
	DESCRIPTION
		"This variable indicates the type of code that was received
		across the E1 interface.

		The values mean:
		e1ReceiveNoCode receiving looped or normal data
		e1ReceiveLineCode	receiving request for a line loopback
		e1ReceivePayloadCode	receiving a request for a payload
					loopback
		e1ReceiveResetCode	receiving a loopback deactivation
					request
		e1ReceiveQRS		receiving a Quasi-Random Signal (QRS)
					test pattern
		e1Receive511Pattern	receiving a 511 bit fixed test pattern
		e1Receive3in24Pattern	receiving a fixed test pattern of 3
					bits set in 24
		e1ReceiveOtherTestPattern receiving a test pattern other than
					the above."
	::= { e1ConfEntry 7 }

e1LoopbackConfig OBJECT-TYPE
	SYNTAX	INTEGER {
		e1NoLoop (1),
		e1LineLoop (2),
		e1PayloadLoop (3),
		e1DiagLoop (4),
		e1OtherLoop (5)
		}
	MAX-ACCESS	read-write
	STATUS	current
	DESCRIPTION
		"This variable represents the loopback configuration of the E1
		interface. This variable is defined in the rfc1406
		configuration table as dsx1LoopbackConfig, with slightly
		different values.

		e1NoLoop (1) means that the interface is not in a loopback
		state.

		e1LineLoop (2) means that cells that are processed by the
		receiving component are not written into the receive FIFO, but
		into the transmit FIFO for retransmission.

		e1PayloadLoop (3) means that the receive signal is looped back
		for retransmission after it has passed through the port's
		reframing function.

		e1DiagLoop (4) means that the transmit data stream is looped
		back to the receiver.

		e1OtherLoop (5) means that the interface is in a loopback that
		is not defined here."
	DEFVAL	{ e1NoLoop }
	::= { e1ConfEntry 8 }

e1TxClockSource OBJECT-TYPE
	SYNTAX	INTEGER {
		rxTiming (1),
		localTiming (2)
		}
	MAX-ACCESS	read-write
	STATUS	current
	DESCRIPTION
		"The source of the transmit clock. rxTiming(1) indicated that
		the recovered receive clock is used as the transmit clock.
		localTiming(2) indicates that a local source clock is used as
		the transmit clock. To determine which local source clock is
		used advise the ntGlobalClock in the netmodTimingTable for this
		netmod (refer to the Fore-Switch-MIB for more information)."
	DEFVAL	{ localTiming }
	::= { e1ConfEntry 9 }

e1LineStatus OBJECT-TYPE
	SYNTAX	INTEGER (1..65534)
	MAX-ACCESS	read-only
	STATUS	current
	DESCRIPTION
		"This variable indicates the Line Status of the interface. A
		similar object is defined in the rfc1406 configuration table as
		dsx1LineStatus. The variable contains loopback state
		information and failure state information. It is a bit map
		represented as a sum. The e1NoAlarm should be set if and only
		if no other flag is set.

		The various bit positions are:
		1	e1NoAlarm
		2	e1RxFarEndLOF	Far end LOF (Receiving Yellow Alarm
					Indication)
		4	e1TxFarEndLOF	Near end sending LOF Indication
					(Yellow Alarm)
		8	e1RxAIS		Far end sending AIS
		16	e1TxAIS		Near end sending AIS (Not used)
		32	e1LOF		Near end Loss Of Frame (Red Alarm)
		64	e1LOS		Near end Loss Of Signal
		128	e1LoopbackState	Near end is in loopback mode
		256	e1RxPLCPYel	Receving PLCP Yellow
		512	e1TxPLCPYel	Transmitting PLCP Yellow
		1024	e1RxPLCPLOF	Receiving PLCP LOF
		2048	e1RcvTestCode	Receiving a test pattern
		4096	e1OtherFailure	any line status not defined here
		32768	e1RxLCD		Receiving LCD failure indication."
	::= { e1ConfEntry 10 }

e1IdleUnassignedCells OBJECT-TYPE
	SYNTAX	INTEGER {
		unassigned(1),
		idle(2)
		}
	MAX-ACCESS	read-write
	STATUS	current
	DESCRIPTION
		"This variable indicates the types of cells that should be sent
		in case there is no real data to send. According to the ATM
		Forum, Unassigned cells should be sent (octet 1-3 are 0's,
		octet 4 is 0000xxx0, where x is 'don't care'). According to the
		CCITT specifications, Idle cells should be sent (everything is
		'0' except for the CLP bit which is '1'). By default,
		unassigned cells are transmitted is case there is no data to
		send."
	DEFVAL	{ unassigned }
	::= { e1ConfEntry 11 }

e1LineLength OBJECT-TYPE
	SYNTAX	INTEGER {
		e1LineLt110 (1),
		e1Line110-220 (2),
		e1Line220-330 (3),
		e1Line330-440 (4),
		e1Line440-550 (5),
		e1Line550-660 (6),
		e1LineG703-75 (7),
		e1LineG703-120 (8),
		e1LineLt110Alt (9),
		e1Line110-220Alt (10),
		e1Line220-330Alt (11),
		e1Line330-440Alt (12),
		e1Line440-550Alt (13),
		e1Line550-660Alt (14),
		e1LineG703-75Alt (15),
		e1LineG703-120Alt (16)
		}
	MAX-ACCESS	read-write
	STATUS	current
	DESCRIPTION
		"This variable represents the length of the physical cable
		connected to the e1 port. The user has to set this object to
		match the physical cable in order to get the netmod to receive
		the signal on the cable.

		The different values are:
		e1LineLt110 (1) means the line is shorter than 110 ft,
		e1Line110-220 (2) means the line is between 110 and 220 ft,
		e1Line220-330 (3) means the line is between 220 and 330 ft,
		e1Line330-440 (4) means the line is between 330 and 440 ft,
		e1Line440-550 (5) means the line is between 440 and 550 ft,
		e1Line550-660 (6) means the line is between 550 and 660 ft,
		e1LineG703-75 (7) G703 standard (75 ohm coaxial line),
		e1LineG703-120 (8) G703 standard (120 ohm symmetrical line)."
	DEFVAL	{ e1LineLt110 }
	::= { e1ConfEntry 12 }

e1LineTypeFraming OBJECT-TYPE
	SYNTAX	INTEGER {
		other (1),
		e1Hcs (2),
		e1Plcp (3)
		}
	MAX-ACCESS	read-write
	STATUS	current
	DESCRIPTION
		"This variable indicates the way ATM cells are constructed from
		the E1 stream.

		e1Hcs(2) indicates that the ATM cells are constructed upon the
		Header Check Sequence (HCS) inside the ATM cell
		header.

		e1Plcp(3) indicates that the ATM cells are constructed from the
		E1 PLCP (Physical Layer Convergence Protocol) bits."
	::= { e1ConfEntry 13 }

e1RxScrambling OBJECT-TYPE
	SYNTAX  INTEGER {
		descrambling(1),
		noDescrambling(2)
		}
	MAX-ACCESS  read-write
	STATUS  current
	DESCRIPTION
		"This variable indicates whether the information is being
		descrambled on receiving. It should be set the same as the
		transmitting side."
	DEFVAL { descrambling }
	::= { e1ConfEntry 14 }

e1TxScrambling OBJECT-TYPE
	SYNTAX  INTEGER {
		scrambling(1),
		noScrambling(2)
		}
	MAX-ACCESS  read-write
	STATUS  current
	DESCRIPTION
		"This variable indicates whether the information (48 octet
		payload) is being scrambled before transmitting. It should
		be set the same as the receiving side."
	DEFVAL { scrambling }
	::= { e1ConfEntry 15 }

------------------------------------------------------------------------
-- The E1 Statistics Group

e1FramingTable OBJECT-TYPE
	SYNTAX	SEQUENCE OF E1FramingEntry
	MAX-ACCESS	not-accessible
	STATUS	current
	DESCRIPTION
		"A table of E1 framing statistics information."
	::= { e1StatsGroup 1 }

e1FramingEntry OBJECT-TYPE
	SYNTAX	E1FramingEntry
	MAX-ACCESS	not-accessible
	STATUS	current
	DESCRIPTION
		"A table entry containing E1 framing statistics information."
	INDEX	{ e1FramingBoard, e1FramingModule, e1FramingPort }
	::= { e1FramingTable 1 }

E1FramingEntry ::=
	SEQUENCE {
		e1FramingBoard		Integer32,
		e1FramingModule		Integer32,
		e1FramingPort		Integer32,

		e1FramingLCVs		Counter32,
		e1FramingFERRs		Counter32,
		e1FramingFEBEs		Counter32,
		e1FramingCRCs		Counter32,

		e1FramingOOFs		Counter32,
		e1FramingLOSs		Counter32,
		e1FramingAISs		Counter32,
		e1FramingAISDs		Counter32,
		e1FramingRedAlarms	Counter32,
		e1FramingYellowAlarms	Counter32
	}

e1FramingBoard OBJECT-TYPE
	SYNTAX	Integer32
	MAX-ACCESS	read-only
	STATUS	current
	DESCRIPTION
		"The index of this port's switch board."
	::= { e1FramingEntry 1 }

e1FramingModule OBJECT-TYPE
	SYNTAX	Integer32
	MAX-ACCESS	read-only
	STATUS	current
	DESCRIPTION
		"The network module of this port."
	::= { e1FramingEntry 2 }

e1FramingPort OBJECT-TYPE
	SYNTAX	Integer32
	MAX-ACCESS	read-only
	STATUS	current
	DESCRIPTION
		"The number of this port."
	::= { e1FramingEntry 3 }

e1FramingLCVs OBJECT-TYPE
	SYNTAX	Counter32
	MAX-ACCESS	read-only
	STATUS	current
	DESCRIPTION
		"The number of Line Code Violations (LCV) that were detected by
		the E1 Receive Framer block."
	::= { e1FramingEntry 4 }

e1FramingFERRs OBJECT-TYPE
	SYNTAX	Counter32
	MAX-ACCESS	read-only
	STATUS	current
	DESCRIPTION
		"Number of E1 framing error (FERR) events."
	::= { e1FramingEntry 5 }

e1FramingFEBEs OBJECT-TYPE
	SYNTAX	Counter32
	MAX-ACCESS	read-only
	STATUS	current
	DESCRIPTION
		"Number of E1 far end block errors."
	::= { e1FramingEntry 6 }

e1FramingCRCs OBJECT-TYPE
	SYNTAX	Counter32
	MAX-ACCESS	read-only
	STATUS	current
	DESCRIPTION
		"The number cyclic redundancy errors."
	::= { e1FramingEntry 7 }

e1FramingOOFs OBJECT-TYPE
	SYNTAX	Counter32
	MAX-ACCESS	read-only
	STATUS	current
	DESCRIPTION
		"Number of seconds when OOF (loss of basic frame alignment)
		errors were detected."
	::= { e1FramingEntry 8 }

e1FramingLOSs OBJECT-TYPE
	SYNTAX	Counter32
	MAX-ACCESS	read-only
	STATUS	current
	DESCRIPTION
		"Number of seconds when LOS (loss of signal) error events were
		experienced."
	::= { e1FramingEntry 9 }

e1FramingAISs OBJECT-TYPE
	SYNTAX	Counter32
	MAX-ACCESS	read-only
	STATUS	current
	DESCRIPTION
		"Number of seconds when AIS (alarm indication signal) error
		events were experienced."
	::= { e1FramingEntry 10 }

e1FramingAISDs OBJECT-TYPE
	SYNTAX	Counter32
	MAX-ACCESS	read-only
	STATUS	current
	DESCRIPTION
		"Number of seconds when AISD (unframed pattern of all ones)
		error events were experienced."
	::= { e1FramingEntry 11 }

e1FramingRedAlarms OBJECT-TYPE
	SYNTAX	Counter32
	MAX-ACCESS	read-only
	STATUS	current
	DESCRIPTION
		"Number of seconds when Red Alarm events were experienced."
	::= { e1FramingEntry 12 }

e1FramingYellowAlarms OBJECT-TYPE
	SYNTAX	Counter32
	MAX-ACCESS	read-only
	STATUS	current
	DESCRIPTION
		"Number of seconds when Yellow Alarm events were experienced."
	::= { e1FramingEntry 13 }

------------------------------------------------------------------------

e1PlcpTable OBJECT-TYPE
	SYNTAX	SEQUENCE OF E1PlcpEntry
	MAX-ACCESS	not-accessible
	STATUS	current
	DESCRIPTION
		"A table of E1 Physical Layer Convergence Protocol (Procedure)
		statistics information."
	::= { e1StatsGroup 2 }

e1PlcpEntry OBJECT-TYPE
	SYNTAX	E1PlcpEntry
	MAX-ACCESS	not-accessible
	STATUS	current
	DESCRIPTION
		"A table entry containing E1 PLCP statistics information."
	INDEX	{ e1PlcpBoard, e1PlcpModule, e1PlcpPort }
	::= { e1PlcpTable 1 }

E1PlcpEntry ::=
	SEQUENCE {
		e1PlcpBoard	Integer32,
		e1PlcpModule	Integer32,
		e1PlcpPort	Integer32,

		e1PlcpBIP8s	Counter32,
		e1PlcpFERRs	Counter32,
		e1PlcpFEBEs	Counter32,
		e1PlcpLOFs	Counter32,
		e1PlcpYellows	Counter32
	}

e1PlcpBoard OBJECT-TYPE
	SYNTAX	Integer32
	MAX-ACCESS	read-only
	STATUS	current
	DESCRIPTION
		"The index of this port's switch board."
	::= { e1PlcpEntry 1 }

e1PlcpModule OBJECT-TYPE
	SYNTAX	Integer32
	MAX-ACCESS	read-only
	STATUS	current
	DESCRIPTION
		"The network module of this port."
	::= { e1PlcpEntry 2 }

e1PlcpPort OBJECT-TYPE
	SYNTAX	Integer32
	MAX-ACCESS	read-only
	STATUS	current
	DESCRIPTION
		"The number of this port."
	::= { e1PlcpEntry 3 }

e1PlcpBIP8s OBJECT-TYPE
	SYNTAX	Counter32
	MAX-ACCESS	read-only
	STATUS	current
	DESCRIPTION
		"Number of BIP-8 (Bit Interleaved Parity - 8) error events. The
		BIP-8 is calculated over the Path Overhead field and the
		associated ATM cell of the previous frame. A BIP-N is a method
		of error monitoring. An N bit code is generated by the
		transmitting equipment in such a manner that the first bit of
		the code provides even parity over the first bit of all N-bit
		sequences in the previous VT SPE, the second bit provides even
		parity over the second bits of all N-bit sequences within the
		specified portion, etc."
	::= { e1PlcpEntry 4 }

e1PlcpFERRs OBJECT-TYPE
	SYNTAX	Counter32
	MAX-ACCESS	read-only
	STATUS	current
	DESCRIPTION
		"Number of Physical Layer Convergence Protocol (PLCP) octet
		error events."
	::= { e1PlcpEntry 5 }

e1PlcpFEBEs OBJECT-TYPE
	SYNTAX	Counter32
	MAX-ACCESS	read-only
	STATUS	current
	DESCRIPTION
		"Number of ATM Far End Block Error (FEBE) events."
	::= { e1PlcpEntry 6 }

e1PlcpLOFs OBJECT-TYPE
	SYNTAX	Counter32
	MAX-ACCESS	read-only
	STATUS	current
	DESCRIPTION
		"The number of seconds in which Loss Of Frame (LOF) errors were
		detected by the PLCP (Physical Layer Convergence Protocol)
		receiver. LOF is declared when an Out-Of-Frame state persists
		for more than 1ms. LOF is removed when in-frame state persists
		for more than 12ms."
	::= { e1PlcpEntry 7 }

e1PlcpYellows OBJECT-TYPE
	SYNTAX	Counter32
	MAX-ACCESS	read-only
	STATUS	current
	DESCRIPTION
		"The number of seconds in which Yellow alarm errors were
		detected by the PLCP (Physical Layer Convergence Protocol)
		receiver. Yellow alarm is asserted when 10 consecutive yellow
		signal bits are set to logical 1. Yellow signals are used to
		alert upstream terminals of a downstream failure in order to
		initiate trunk conditioning on the failure circuit."
	::= { e1PlcpEntry 8 }

------------------------------------------------------------------------

e1AtmTable OBJECT-TYPE
	SYNTAX	SEQUENCE OF E1AtmEntry
	MAX-ACCESS	not-accessible
	STATUS	current
	DESCRIPTION
		"A table of E1 ATM statistics information."
	::= { e1StatsGroup 3 }

e1AtmEntry OBJECT-TYPE
	SYNTAX	E1AtmEntry
	MAX-ACCESS	not-accessible
	STATUS	current
	DESCRIPTION
		"A table entry containing E1 ATM statistics information."
	INDEX	{ e1AtmBoard, e1AtmModule, e1AtmPort }
	::= { e1AtmTable 1 }

E1AtmEntry ::=
	SEQUENCE {
		e1AtmBoard		Integer32,
		e1AtmModule		Integer32,
		e1AtmPort		Integer32,

		e1AtmHCSs		Counter32,
		e1AtmRxCells		Counter32,
		e1AtmTxCells		Counter32,
		e1AtmUHCSs		Counter32,
		e1AtmCHCSs		Counter32,
		e1AtmLCDs		Counter32
	}

e1AtmBoard OBJECT-TYPE
	SYNTAX	Integer32
	MAX-ACCESS	read-only
	STATUS	current
	DESCRIPTION
		"The index of this port's switch board."
	::= { e1AtmEntry 1 }

e1AtmModule OBJECT-TYPE
	SYNTAX	Integer32
	MAX-ACCESS	read-only
	STATUS	current
	DESCRIPTION
		"The network module of this port."
	::= { e1AtmEntry 2 }

e1AtmPort OBJECT-TYPE
	SYNTAX	Integer32
	MAX-ACCESS	read-only
	STATUS	current
	DESCRIPTION
		"The number of this port."
	::= { e1AtmEntry 3 }

e1AtmHCSs OBJECT-TYPE
	SYNTAX	Counter32
	MAX-ACCESS	read-only
	STATUS	current
	DESCRIPTION
		"Number of header check sequence (HCS) error events. The HCS
		is a CRC-8 calculation over the first 4 octets of the ATM cell
		header."
	::= { e1AtmEntry 4 }

e1AtmRxCells OBJECT-TYPE
	SYNTAX	Counter32
	MAX-ACCESS	read-only
	STATUS	current
	DESCRIPTION
		"Number of ATM cells that were received."
	::= { e1AtmEntry 5 }

e1AtmTxCells OBJECT-TYPE
	SYNTAX	Counter32
	MAX-ACCESS	read-only
	STATUS	current
	DESCRIPTION
		"Number of non-null ATM cells that were transmitted."
	::= { e1AtmEntry 6 }

e1AtmUHCSs OBJECT-TYPE
	SYNTAX	Counter32
	MAX-ACCESS	read-only
	STATUS	current
	DESCRIPTION
		"Number of uncorrectable header check sequence (HCS) error
		events.	The HCS is a CRC-8 calculation over the first 4 octets
		of the ATM cell header."
	::= { e1AtmEntry 7 }

e1AtmCHCSs OBJECT-TYPE
	SYNTAX	Counter32
	MAX-ACCESS	read-only
	STATUS	current
	DESCRIPTION
		"Number of correctable header check sequence (HCS) error
		events.	The HCS is a CRC-8 calculation over the first 4 octets
		of the ATM cell header."
	::= { e1AtmEntry 8 }

e1AtmLCDs OBJECT-TYPE
	SYNTAX	Counter32
	MAX-ACCESS	read-only
	STATUS	current
	DESCRIPTION
		"The number of seconds in which Loss of Cell Delineation (LCD)
		has occurred.  An LCD defect is detected when an out of cell
		delination state has persisted for 4ms.  An LCD defect is
		cleared when the sync state has been maintained for 4ms."
	::= { e1AtmEntry 9 }

END
