-- *********************************************************************
-- CISCO-UNIFIED-COMPUTING-ADAPTOR-MIB.my
-- 
-- MIB representation of the Cisco Unified Computing System
-- ADAPTOR management information model package
-- 
-- Created October 2017 by Charles Bullis
-- 
-- Copyright (c) 2005-2017 Cisco Systems, Inc. All rights reserved.
-- 
-- *********************************************************************

CISCO-UNIFIED-COMPUTING-ADAPTOR-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsAdaptorAdapterStatsTrafficDir,
    CucsAdaptorAdminPowerState,
    CucsAdaptorAdminState,
    CucsAdaptorCIoEpIfType,
    CucsAdaptorCapDefFwVersionOpr,
    CucsAdaptorCapDefType,
    CucsAdaptorCapSpecType,
    CucsAdaptorComparisonOper,
    CucsAdaptorDefaultAction,
    CucsAdaptorDynamicConfigParams,
    CucsAdaptorEthAdvFilterProfileAdminState,
    CucsAdaptorEthArfsProfileAccelaratedRFS,
    CucsAdaptorEthInterruptProfileCoalescingType,
    CucsAdaptorEthInterruptScalingProfileAdminState,
    CucsAdaptorEthNVGREProfileAdminState,
    CucsAdaptorEthOffloadProfileLargeReceive,
    CucsAdaptorEthOffloadProfileTcpRxChecksum,
    CucsAdaptorEthOffloadProfileTcpSegment,
    CucsAdaptorEthOffloadProfileTcpTxChecksum,
    CucsAdaptorEthPortBySizeLargeStatsHistThresholded,
    CucsAdaptorEthPortBySizeLargeStatsThresholded,
    CucsAdaptorEthPortBySizeSmallStatsHistThresholded,
    CucsAdaptorEthPortBySizeSmallStatsThresholded,
    CucsAdaptorEthPortErrStatsHistThresholded,
    CucsAdaptorEthPortErrStatsThresholded,
    CucsAdaptorEthPortMcastStatsHistThresholded,
    CucsAdaptorEthPortMcastStatsThresholded,
    CucsAdaptorEthPortOutsizedStatsHistThresholded,
    CucsAdaptorEthPortOutsizedStatsThresholded,
    CucsAdaptorEthPortStatsHistThresholded,
    CucsAdaptorEthPortStatsThresholded,
    CucsAdaptorEthRoCEProfileAdminState,
    CucsAdaptorEthVxLANProfileAdminState,
    CucsAdaptorEtherIfStatsHistThresholded,
    CucsAdaptorEtherIfStatsThresholded,
    CucsAdaptorExtEthIfFsmCurrentFsm,
    CucsAdaptorExtEthIfFsmStageName,
    CucsAdaptorExtEthIfFsmTaskItem,
    CucsAdaptorExtEthIfPcEpPortId,
    CucsAdaptorExtEthIfPcEpSlotId,
    CucsAdaptorExtEthIfPcPortId,
    CucsAdaptorExtEthIfPcTransport,
    CucsAdaptorExtIfAdminState,
    CucsAdaptorExtIfEpIfRole,
    CucsAdaptorExtIfEpType,
    CucsAdaptorExtIfPcIfRole,
    CucsAdaptorExtIfPcType,
    CucsAdaptorExtIpV6RssHashProfileIpHash,
    CucsAdaptorExtIpV6RssHashProfileTcpHash,
    CucsAdaptorExternalEpLocale,
    CucsAdaptorExternalPcLocale,
    CucsAdaptorFcErrorRecoveryProfileFcpErrorRecovery,
    CucsAdaptorFcIfEventStatsHistThresholded,
    CucsAdaptorFcIfEventStatsThresholded,
    CucsAdaptorFcIfFC4StatsHistThresholded,
    CucsAdaptorFcIfFC4StatsThresholded,
    CucsAdaptorFcIfFrameStatsHistThresholded,
    CucsAdaptorFcIfFrameStatsThresholded,
    CucsAdaptorFcPortStatsHistThresholded,
    CucsAdaptorFcPortStatsThresholded,
    CucsAdaptorHostEthIfFsmCurrentFsm,
    CucsAdaptorHostEthIfFsmStageName,
    CucsAdaptorHostEthIfFsmTaskItem,
    CucsAdaptorHostEthIfHostPort,
    CucsAdaptorHostEthIfTransport,
    CucsAdaptorHostFcIfAdminState,
    CucsAdaptorHostFcIfFsmCurrentFsm,
    CucsAdaptorHostFcIfFsmStageName,
    CucsAdaptorHostFcIfFsmTaskItem,
    CucsAdaptorHostFcIfHostPort,
    CucsAdaptorHostFcIfPersBind,
    CucsAdaptorHostFcIfTransport,
    CucsAdaptorHostIfAdminState,
    CucsAdaptorHostIfBootDev,
    CucsAdaptorHostMgmtCapPreboot,
    CucsAdaptorHostMgmtCapPresence,
    CucsAdaptorHostPortId,
    CucsAdaptorHostServiceEthIfIfRole,
    CucsAdaptorHostVisibility,
    CucsAdaptorIScsiCapBootOrderType,
    CucsAdaptorInterruptMode,
    CucsAdaptorIpV4RssHashProfileIpHash,
    CucsAdaptorIpV4RssHashProfileTcpHash,
    CucsAdaptorIpV6RssHashProfileIpHash,
    CucsAdaptorIpV6RssHashProfileTcpHash,
    CucsAdaptorIscsiProtConnectionTimeOut,
    CucsAdaptorIscsiProtDhcpTimeOut,
    CucsAdaptorIscsiProtLunBusyRetryCount,
    CucsAdaptorLanCapDefaultVlan,
    CucsAdaptorLinkState,
    CucsAdaptorLldpCapSupport,
    CucsAdaptorMenloBaseErrorStatsHistThresholded,
    CucsAdaptorMenloBaseErrorStatsThresholded,
    CucsAdaptorMenloDcePortStatsHistThresholded,
    CucsAdaptorMenloDcePortStatsThresholded,
    CucsAdaptorMenloEthErrorStatsHistThresholded,
    CucsAdaptorMenloEthErrorStatsThresholded,
    CucsAdaptorMenloEthStatsHistThresholded,
    CucsAdaptorMenloEthStatsThresholded,
    CucsAdaptorMenloFcErrorStatsHistThresholded,
    CucsAdaptorMenloFcErrorStatsThresholded,
    CucsAdaptorMenloFcStatsHistThresholded,
    CucsAdaptorMenloFcStatsThresholded,
    CucsAdaptorMenloHostPortStatsHistThresholded,
    CucsAdaptorMenloHostPortStatsThresholded,
    CucsAdaptorMenloMcpuErrorStatsHistThresholded,
    CucsAdaptorMenloMcpuErrorStatsThresholded,
    CucsAdaptorMenloMcpuStatsHistThresholded,
    CucsAdaptorMenloMcpuStatsThresholded,
    CucsAdaptorMenloNetEgStatsHistThresholded,
    CucsAdaptorMenloNetEgStatsThresholded,
    CucsAdaptorMenloNetInStatsHistThresholded,
    CucsAdaptorMenloNetInStatsThresholded,
    CucsAdaptorMenloQErrorStatsHistThresholded,
    CucsAdaptorMenloQErrorStatsThresholded,
    CucsAdaptorMenloQStatsHistThresholded,
    CucsAdaptorMenloQStatsThresholded,
    CucsAdaptorMenloQueueStatsComponent,
    CucsAdaptorMenloStatsIndex,
    CucsAdaptorMgmtCapMode,
    CucsAdaptorMgmtCapOperPowerRequirement,
    CucsAdaptorMgmtCapRebootActionOnDestructive,
    CucsAdaptorNwMgmtCapApi,
    CucsAdaptorNwMgmtCapMgmtTransport,
    CucsAdaptorOffloadMethod,
    CucsAdaptorPIoEpIfType,
    CucsAdaptorProtocolProfileConnectionTimeOut,
    CucsAdaptorProtocolProfileLunBusyRetryCount,
    CucsAdaptorPurpose,
    CucsAdaptorReachability,
    CucsAdaptorRnicCapSpecType,
    CucsAdaptorRssProfileReceiveSideScaling,
    CucsAdaptorSanCapHostNvram,
    CucsAdaptorUnitExtnId,
    CucsAdaptorUnitId,
    CucsAdaptorUnitVisibility,
    CucsAdaptorVnicStatsHistThresholded,
    CucsAdaptorVnicStatsThresholded,
    CucsAddressType,
    CucsConditionRemoteInvRslt,
    CucsEquipmentConnectionStatus,
    CucsEquipmentOperability,
    CucsEquipmentPowerState,
    CucsEquipmentPresence,
    CucsEquipmentSensorThresholdStatus,
    CucsEtherSatelliteConnectionDisc,
    CucsFabricAVlanAssocPrimaryVlanSwitchId,
    CucsFabricAVlanSharing,
    CucsFabricAVlanTransport,
    CucsFabricAVlanType,
    CucsFabricAVsanTransport,
    CucsFabricAVsanType,
    CucsFabricEpVlanVlanType,
    CucsFabricMembershipStatus,
    CucsFabricVlanAssocPrimaryVlanState,
    CucsFabricVlanOperState,
    CucsFabricVlanOverlapState,
    CucsFabricVnetEpIfRole,
    CucsFabricVnetEpLocale,
    CucsFabricVnetEpPolicyOwner,
    CucsFabricVsanOperState,
    CucsFabricZoningState,
    CucsFsmCompletion,
    CucsFsmFlags,
    CucsFsmFsmStageStatus,
    CucsFsmLifecycle,
    CucsLstorageBootDevice,
    CucsNetworkConnectionType,
    CucsNetworkLocale,
    CucsNetworkPhysEpIfType,
    CucsNetworkPortOperState,
    CucsNetworkPortRole,
    CucsNetworkSide,
    CucsNetworkSwitchId,
    CucsNetworkTransport,
    CucsNetworkVnetEpIfType,
    CucsPolicyPolicyOwner,
    CucsPortEthSpeed,
    CucsVnicVirtualizationPreferenceType
        FROM CISCO-UNIFIED-COMPUTING-TC-MIB;

cucsAdaptorObjects MODULE-IDENTITY
    LAST-UPDATED    "201710060000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        ADAPTOR management information model package"
    ::= { ciscoUnifiedComputingMIBObjects 3 }

cucsAdaptorCapQualTable OBJECT-TYPE
    SYNTAX           SEQUENCE OF CucsAdaptorCapQualEntry
    MAX-ACCESS       not-accessible
    STATUS           current
    DESCRIPTION
        "Cisco UCS adaptor:CapQual managed object table"
    ::= { cucsAdaptorObjects 1 }

cucsAdaptorCapQualEntry OBJECT-TYPE
    SYNTAX           CucsAdaptorCapQualEntry
    MAX-ACCESS       not-accessible
    STATUS           current
    DESCRIPTION
        "Entry for the cucsAdaptorCapQualTable table."
    INDEX { cucsAdaptorCapQualInstanceId }
    ::= { cucsAdaptorCapQualTable 1 }

CucsAdaptorCapQualEntry ::= SEQUENCE {
    cucsAdaptorCapQualInstanceId                                     CucsManagedObjectId,
    cucsAdaptorCapQualDn                                             CucsManagedObjectDn,
    cucsAdaptorCapQualRn                                             SnmpAdminString,
    cucsAdaptorCapQualMaximum                                        Gauge32,
    cucsAdaptorCapQualModel                                          SnmpAdminString,
    cucsAdaptorCapQualType                                           CucsAdaptorCapDefType,
    cucsAdaptorCapQualFwVersionHi                                    SnmpAdminString,
    cucsAdaptorCapQualFwVersionLo                                    SnmpAdminString,
    cucsAdaptorCapQualFwVersionOpr                                   CucsAdaptorCapDefFwVersionOpr,
    cucsAdaptorCapQualNfVersionLo                                    SnmpAdminString
}

cucsAdaptorCapQualInstanceId OBJECT-TYPE
    SYNTAX       CucsManagedObjectId
    MAX-ACCESS   not-accessible
    STATUS       current
    DESCRIPTION
        "Instance identifier of the managed object."
    ::= { cucsAdaptorCapQualEntry 1 }

cucsAdaptorCapQualDn OBJECT-TYPE
    SYNTAX       CucsManagedObjectDn
    MAX-ACCESS   read-only
    STATUS       current
    DESCRIPTION
        "Cisco UCS adaptor:CapQual:dn managed object property"
    ::= { cucsAdaptorCapQualEntry 2 }

cucsAdaptorCapQualRn OBJECT-TYPE
    SYNTAX       SnmpAdminString
    MAX-ACCESS   read-only
    STATUS       current
    DESCRIPTION
        "Cisco UCS adaptor:CapQual:rn managed object property"
    ::= { cucsAdaptorCapQualEntry 3 }

cucsAdaptorCapQualMaximum OBJECT-TYPE
    SYNTAX       Gauge32
    MAX-ACCESS   read-only
    STATUS       current
    DESCRIPTION
        "Cisco UCS adaptor:CapQual:maximum managed object property"
    ::= { cucsAdaptorCapQualEntry 4 }

cucsAdaptorCapQualModel OBJECT-TYPE
    SYNTAX       SnmpAdminString
    MAX-ACCESS   read-only
    STATUS       current
    DESCRIPTION
        "Cisco UCS adaptor:CapQual:model managed object property"
    ::= { cucsAdaptorCapQualEntry 5 }

cucsAdaptorCapQualType OBJECT-TYPE
    SYNTAX       CucsAdaptorCapDefType
    MAX-ACCESS   read-only
    STATUS       current
    DESCRIPTION
        "Cisco UCS adaptor:CapQual:type managed object property"
    ::= { cucsAdaptorCapQualEntry 6 }

cucsAdaptorCapQualFwVersionHi OBJECT-TYPE
    SYNTAX       SnmpAdminString
    MAX-ACCESS   read-only
    STATUS       current
    DESCRIPTION
        "Cisco UCS adaptor:CapQual:fwVersionHi managed object property"
    ::= { cucsAdaptorCapQualEntry 7 }

cucsAdaptorCapQualFwVersionLo OBJECT-TYPE
    SYNTAX       SnmpAdminString
    MAX-ACCESS   read-only
    STATUS       current
    DESCRIPTION
        "Cisco UCS adaptor:CapQual:fwVersionLo managed object property"
    ::= { cucsAdaptorCapQualEntry 8 }

cucsAdaptorCapQualFwVersionOpr OBJECT-TYPE
    SYNTAX       CucsAdaptorCapDefFwVersionOpr
    MAX-ACCESS   read-only
    STATUS       current
    DESCRIPTION
        "Cisco UCS adaptor:CapQual:fwVersionOpr managed object property"
    ::= { cucsAdaptorCapQualEntry 9 }

cucsAdaptorCapQualNfVersionLo OBJECT-TYPE
    SYNTAX       SnmpAdminString
    MAX-ACCESS   read-only
    STATUS       current
    DESCRIPTION
        "Cisco UCS adaptor:CapQual:nfVersionLo managed object property"
    ::= { cucsAdaptorCapQualEntry 10 }

cucsAdaptorCapSpecTable OBJECT-TYPE
    SYNTAX           SEQUENCE OF CucsAdaptorCapSpecEntry
    MAX-ACCESS       not-accessible
    STATUS           current
    DESCRIPTION
        "Cisco UCS adaptor:CapSpec managed object table"
    ::= { cucsAdaptorObjects 2 }

cucsAdaptorCapSpecEntry OBJECT-TYPE
    SYNTAX           CucsAdaptorCapSpecEntry
    MAX-ACCESS       not-accessible
    STATUS           current
    DESCRIPTION
        "Entry for the cucsAdaptorCapSpecTable table."
    INDEX { cucsAdaptorCapSpecInstanceId }
    ::= { cucsAdaptorCapSpecTable 1 }

CucsAdaptorCapSpecEntry ::= SEQUENCE {
    cucsAdaptorCapSpecInstanceId                                     CucsManagedObjectId,
    cucsAdaptorCapSpecDn                                             CucsManagedObjectDn,
    cucsAdaptorCapSpecRn                                             SnmpAdminString,
    cucsAdaptorCapSpecMaximum                                        Gauge32,
    cucsAdaptorCapSpecType                                           CucsAdaptorCapSpecType,
    cucsAdaptorCapSpecFwVersionHi                                    SnmpAdminString,
    cucsAdaptorCapSpecFwVersionLo                                    SnmpAdminString,
    cucsAdaptorCapSpecFwVersionOpr                                   CucsAdaptorCapDefFwVersionOpr,
    cucsAdaptorCapSpecNfVersionLo                                    SnmpAdminString
}

cucsAdaptorCapSpecInstanceId OBJECT-TYPE
    SYNTAX       CucsManagedObjectId
    MAX-ACCESS   not-accessible
    STATUS       current
    DESCRIPTION
        "Instance identifier of the managed object."
    ::= { cucsAdaptorCapSpecEntry 1 }

cucsAdaptorCapSpecDn OBJECT-TYPE
    SYNTAX       CucsManagedObjectDn
    MAX-ACCESS   read-only
    STATUS       current
    DESCRIPTION
        "Cisco UCS adaptor:CapSpec:dn managed object property"
    ::= { cucsAdaptorCapSpecEntry 2 }

cucsAdaptorCapSpecRn OBJECT-TYPE
    SYNTAX       SnmpAdminString
    MAX-ACCESS   read-only
    STATUS       current
    DESCRIPTION
        "Cisco UCS adaptor:CapSpec:rn managed object property"
    ::= { cucsAdaptorCapSpecEntry 3 }

cucsAdaptorCapSpecMaximum OBJECT-TYPE
    SYNTAX       Gauge32
    MAX-ACCESS   read-only
    STATUS       current
    DESCRIPTION
        "Cisco UCS adaptor:CapSpec:maximum managed object property"
    ::= { cucsAdaptorCapSpecEntry 4 }

cucsAdaptorCapSpecType OBJECT-TYPE
    SYNTAX       CucsAdaptorCapSpecType
    MAX-ACCESS   read-only
    STATUS       current
    DESCRIPTION
        "Cisco UCS adaptor:CapSpec:type managed object property"
    ::= { cucsAdaptorCapSpecEntry 5 }

cucsAdaptorCapSpecFwVersionHi OBJECT-TYPE
    SYNTAX       SnmpAdminString
    MAX-ACCESS   read-only
    STATUS       current
    DESCRIPTION
        "Cisco UCS adaptor:CapSpec:fwVersionHi managed object property"
    ::= { cucsAdaptorCapSpecEntry 6 }

cucsAdaptorCapSpecFwVersionLo OBJECT-TYPE
    SYNTAX       SnmpAdminString
    MAX-ACCESS   read-only
    STATUS       current
    DESCRIPTION
        "Cisco UCS adaptor:CapSpec:fwVersionLo managed object property"
    ::= { cucsAdaptorCapSpecEntry 7 }

cucsAdaptorCapSpecFwVersionOpr OBJECT-TYPE
    SYNTAX       CucsAdaptorCapDefFwVersionOpr
    MAX-ACCESS   read-only
    STATUS       current
    DESCRIPTION
        "Cisco UCS adaptor:CapSpec:fwVersionOpr managed object property"
    ::= { cucsAdaptorCapSpecEntry 8 }

cucsAdaptorCapSpecNfVersionLo OBJECT-TYPE
    SYNTAX       SnmpAdminString
    MAX-ACCESS   read-only
    STATUS       current
    DESCRIPTION
        "Cisco UCS adaptor:CapSpec:nfVersionLo managed object property"
    ::= { cucsAdaptorCapSpecEntry 9 }

cucsAdaptorDiagCapTable OBJECT-TYPE
    SYNTAX           SEQUENCE OF CucsAdaptorDiagCapEntry
    MAX-ACCESS       not-accessible
    STATUS           current
    DESCRIPTION
        "Cisco UCS adaptor:DiagCap managed object table"
    ::= { cucsAdaptorObjects 94 }

cucsAdaptorDiagCapEntry OBJECT-TYPE
    SYNTAX           CucsAdaptorDiagCapEntry
    MAX-ACCESS       not-accessible
    STATUS           current
    DESCRIPTION
        "Entry for the cucsAdaptorDiagCapTable table."
    INDEX { cucsAdaptorDiagCapInstanceId }
    ::= { cucsAdaptorDiagCapTable 1 }

CucsAdaptorDiagCapEntry ::= SEQUENCE {
    cucsAdaptorDiagCapInstanceId                                     CucsManagedObjectId,
    cucsAdaptorDiagCapDn                                             CucsManagedObjectDn,
    cucsAdaptorDiagCapRn                                             SnmpAdminString,
    cucsAdaptorDiagCapEnableLldpTransmit                             TruthValue
}

cucsAdaptorDiagCapInstanceId OBJECT-TYPE
    SYNTAX       CucsManagedObjectId
    MAX-ACCESS   not-accessible
    STATUS       current
    DESCRIPTION
        "Instance identifier of the managed object."
    ::= { cucsAdaptorDiagCapEntry 1 }

cucsAdaptorDiagCapDn OBJECT-TYPE
    SYNTAX       CucsManagedObjectDn
    MAX-ACCESS   read-only
    STATUS       current
    DESCRIPTION
        "Cisco UCS adaptor:DiagCap:dn managed object property"
    ::= { cucsAdaptorDiagCapEntry 2 }

cucsAdaptorDiagCapRn OBJECT-TYPE
    SYNTAX       SnmpAdminString
    MAX-ACCESS   read-only
    STATUS       current
    DESCRIPTION
        "Cisco UCS adaptor:DiagCap:rn managed object property"
    ::= { cucsAdaptorDiagCapEntry 3 }

cucsAdaptorDiagCapEnableLldpTransmit OBJECT-TYPE
    SYNTAX       TruthValue
    MAX-ACCESS   read-only
    STATUS       current
    DESCRIPTION
        "Cisco UCS adaptor:DiagCap:enableLldpTransmit managed
        object property"
    ::= { cucsAdaptorDiagCapEntry 4 }

cucsAdaptorDynamicConfigCapTable OBJECT-TYPE
    SYNTAX           SEQUENCE OF CucsAdaptorDynamicConfigCapEntry
    MAX-ACCESS       not-accessible
    STATUS           current
    DESCRIPTION
        "Cisco UCS adaptor:DynamicConfigCap managed object table"
    ::= { cucsAdaptorObjects 122 }

cucsAdaptorDynamicConfigCapEntry OBJECT-TYPE
    SYNTAX           CucsAdaptorDynamicConfigCapEntry
    MAX-ACCESS       not-accessible
    STATUS           current
    DESCRIPTION
        "Entry for the cucsAdaptorDynamicConfigCapTable table."
    INDEX { cucsAdaptorDynamicConfigCapInstanceId }
    ::= { cucsAdaptorDynamicConfigCapTable 1 }

CucsAdaptorDynamicConfigCapEntry ::= SEQUENCE {
    cucsAdaptorDynamicConfigCapInstanceId                            CucsManagedObjectId,
    cucsAdaptorDynamicConfigCapDn                                    CucsManagedObjectDn,
    cucsAdaptorDynamicConfigCapRn                                    SnmpAdminString,
    cucsAdaptorDynamicConfigCapDynamicParams                         CucsAdaptorDynamicConfigParams,
    cucsAdaptorDynamicConfigCapFwVersionHi                           SnmpAdminString,
    cucsAdaptorDynamicConfigCapFwVersionLo                           SnmpAdminString,
    cucsAdaptorDynamicConfigCapFwVersionOper                         CucsAdaptorComparisonOper
}

cucsAdaptorDynamicConfigCapInstanceId OBJECT-TYPE
    SYNTAX       CucsManagedObjectId
    MAX-ACCESS   not-accessible
    STATUS       current
    DESCRIPTION
        "Instance identifier of the managed object."
    ::= { cucsAdaptorDynamicConfigCapEntry 1 }

cucsAdaptorDynamicConfigCapDn OBJECT-TYPE
    SYNTAX       CucsManagedObjectDn
    MAX-ACCESS   read-only
    STATUS       current
    DESCRIPTION
        "Cisco UCS adaptor:DynamicConfigCap:dn managed object property"
    ::= { cucsAdaptorDynamicConfigCapEntry 2 }

cucsAdaptorDynamicConfigCapRn OBJECT-TYPE
    SYNTAX       SnmpAdminString
    MAX-ACCESS   read-only
    STATUS       current
    DESCRIPTION
        "Cisco UCS adaptor:DynamicConfigCap:rn managed object property"
    ::= { cucsAdaptorDynamicConfigCapEntry 3 }

cucsAdaptorDynamicConfigCapDynamicParams OBJECT-TYPE
    SYNTAX       CucsAdaptorDynamicConfigParams
    MAX-ACCESS   read-only
    STATUS       current
    DESCRIPTION
        "Cisco UCS adaptor:DynamicConfigCap:dynamicParams
        managed object property"
    ::= { cucsAdaptorDynamicConfigCapEntry 4 }

cucsAdaptorDynamicConfigCapFwVersionHi OBJECT-TYPE
    SYNTAX       SnmpAdminString
    MAX-ACCESS   read-only
    STATUS       current
    DESCRIPTION
        "Cisco UCS adaptor:DynamicConfigCap:fwVersionHi
        managed object property"
    ::= { cucsAdaptorDynamicConfigCapEntry 5 }

cucsAdaptorDynamicConfigCapFwVersionLo OBJECT-TYPE
    SYNTAX       SnmpAdminString
    MAX-ACCESS   read-only
    STATUS       current
    DESCRIPTION
        "Cisco UCS adaptor:DynamicConfigCap:fwVersionLo
        managed object property"
    ::= { cucsAdaptorDynamicConfigCapEntry 6 }

cucsAdaptorDynamicConfigCapFwVersionOper OBJECT-TYPE
    SYNTAX       CucsAdaptorComparisonOper
    MAX-ACCESS   read-only
    STATUS       current
    DESCRIPTION
        "Cisco UCS adaptor:DynamicConfigCap:fwVersionOper
        managed object property"
    ::= { cucsAdaptorDynamicConfigCapEntry 7 }

cucsAdaptorEthAdvFilterProfileTable OBJECT-TYPE
    SYNTAX           SEQUENCE OF CucsAdaptorEthAdvFilterProfileEntry
    MAX-ACCESS       not-accessible
    STATUS           current
    DESCRIPTION
        "Cisco UCS adaptor:EthAdvFilterProfile managed object table"
    ::= { cucsAdaptorObjects 135 }

cucsAdaptorEthAdvFilterProfileEntry OBJECT-TYPE
    SYNTAX           CucsAdaptorEthAdvFilterProfileEntry
    MAX-ACCESS       not-accessible
    STATUS           current
    DESCRIPTION
        "Entry for the cucsAdaptorEthAdvFilterProfileTable table."
    INDEX { cucsAdaptorEthAdvFilterProfileInstanceId }
    ::= { cucsAdaptorEthAdvFilterProfileTable 1 }

CucsAdaptorEthAdvFilterProfileEntry ::= SEQUENCE {
    cucsAdaptorEthAdvFilterProfileInstanceId                         CucsManagedObjectId,
    cucsAdaptorEthAdvFilterProfileDn                                 CucsManagedObjectDn,
    cucsAdaptorEthAdvFilterProfileRn                                 SnmpAdminString,
    cucsAdaptorEthAdvFilterProfileAdminState                         CucsAdaptorEthAdvFilterProfileAdminState
}

cucsAdaptorEthAdvFilterProfileInstanceId OBJECT-TYPE
    SYNTAX       CucsManagedObjectId
    MAX-ACCESS   not-accessible
    STATUS       current
    DESCRIPTION
        "Instance identifier of the managed object."
    ::= { cucsAdaptorEthAdvFilterProfileEntry 1 }

cucsAdaptorEthAdvFilterProfileDn OBJECT-TYPE
    SYNTAX       CucsManagedObjectDn
    MAX-ACCESS   read-only
    STATUS       current
    DESCRIPTION
        "Cisco UCS adaptor:EthAdvFilterProfile:dn managed object property"
    ::= { cucsAdaptorEthAdvFilterProfileEntry 2 }

cucsAdaptorEthAdvFilterProfileRn OBJECT-TYPE
    SYNTAX       SnmpAdminString
    MAX-ACCESS   read-only
    STATUS       current
    DESCRIPTION
        "Cisco UCS adaptor:EthAdvFilterProfile:rn managed object property"
    ::= { cucsAdaptorEthAdvFilterProfileEntry 3 }

cucsAdaptorEthAdvFilterProfileAdminState OBJECT-TYPE
    SYNTAX       CucsAdaptorEthAdvFilterProfileAdminState
    MAX-ACCESS   read-only
    STATUS       current
    DESCRIPTION
        "Cisco UCS adaptor:EthAdvFilterProfile:adminState
        managed object property"
    ::= { cucsAdaptorEthAdvFilterProfileEntry 4 }

cucsAdaptorEthArfsProfileTable OBJECT-TYPE
    SYNTAX           SEQUENCE OF CucsAdaptorEthArfsProfileEntry
    MAX-ACCESS       not-accessible
    STATUS           current
    DESCRIPTION
        "Cisco UCS adaptor:EthArfsProfile managed object table"
    ::= { cucsAdaptorObjects 116 }

cucsAdaptorEthArfsProfileEntry OBJECT-TYPE
    SYNTAX           CucsAdaptorEthArfsProfileEntry
    MAX-ACCESS       not-accessible
    STATUS           current
    DESCRIPTION
        "Entry for the cucsAdaptorEthArfsProfileTable table."
    INDEX { cucsAdaptorEthArfsProfileInstanceId }
    ::= { cucsAdaptorEthArfsProfileTable 1 }

CucsAdaptorEthArfsProfileEntry ::= SEQUENCE {
    cucsAdaptorEthArfsProfileInstanceId                              CucsManagedObjectId,
    cucsAdaptorEthArfsProfileDn                                      CucsManagedObjectDn,
    cucsAdaptorEthArfsProfileRn                                      SnmpAdminString,
    cucsAdaptorEthArfsProfileAccelaratedRFS                          CucsAdaptorEthArfsProfileAccelaratedRFS
}

cucsAdaptorEthArfsProfileInstanceId OBJECT-TYPE
    SYNTAX       CucsManagedObjectId
    MAX-ACCESS   not-accessible
    STATUS       current
    DESCRIPTION
        "Instance identifier of the managed object."
    ::= { cucsAdaptorEthArfsProfileEntry 1 }

cucsAdaptorEthArfsProfileDn OBJECT-TYPE
    SYNTAX       CucsManagedObjectDn
    MAX-ACCESS   read-only
    STATUS       current
    DESCRIPTION
        "Cisco UCS adaptor:EthArfsProfile:dn managed object property"
    ::= { cucsAdaptorEthArfsProfileEntry 2 }

cucsAdaptorEthArfsProfileRn OBJECT-TYPE
    SYNTAX       SnmpAdminString
    MAX-ACCESS   read-only
    STATUS       current
    DESCRIPTION
        "Cisco UCS adaptor:EthArfsProfile:rn managed object property"
    ::= { cucsAdaptorEthArfsProfileEntry 3 }

cucsAdaptorEthArfsProfileAccelaratedRFS OBJECT-TYPE
    SYNTAX       CucsAdaptorEthArfsProfileAccelaratedRFS
    MAX-ACCESS   read-only
    STATUS       current
    DESCRIPTION
        "Cisco UCS adaptor:EthArfsProfile:accelaratedRFS
        managed object property"
    ::= { cucsAdaptorEthArfsProfileEntry 4 }

cucsAdaptorEthCompQueueProfileTable OBJECT-TYPE
    SYNTAX           SEQUENCE OF CucsAdaptorEthCompQueueProfileEntry
    MAX-ACCESS       not-accessible
    STATUS           current
    DESCRIPTION
        "Cisco UCS adaptor:EthCompQueueProfile managed object table"
    ::= { cucsAdaptorObjects 3 }

cucsAdaptorEthCompQueueProfileEntry OBJECT-TYPE
    SYNTAX           CucsAdaptorEthCompQueueProfileEntry
    MAX-ACCESS       not-accessible
    STATUS           current
    DESCRIPTION
        "Entry for the cucsAdaptorEthCompQueueProfileTable table."
    INDEX { cucsAdaptorEthCompQueueProfileInstanceId }
    ::= { cucsAdaptorEthCompQueueProfileTable 1 }

CucsAdaptorEthCompQueueProfileEntry ::= SEQUENCE {
    cucsAdaptorEthCompQueueProfileInstanceId                         CucsManagedObjectId,
    cucsAdaptorEthCompQueueProfileDn                                 CucsManagedObjectDn,
    cucsAdaptorEthCompQueueProfileRn                                 SnmpAdminString,
    cucsAdaptorEthCompQueueProfileCount                              Gauge32,
    cucsAdaptorEthCompQueueProfileRingSize                           Gauge32
}

cucsAdaptorEthCompQueueProfileInstanceId OBJECT-TYPE
    SYNTAX       CucsManagedObjectId
    MAX-ACCESS   not-accessible
    STATUS       current
    DESCRIPTION
        "Instance identifier of the managed object."
    ::= { cucsAdaptorEthCompQueueProfileEntry 1 }

cucsAdaptorEthCompQueueProfileDn OBJECT-TYPE
    SYNTAX       CucsManagedObjectDn
    MAX-ACCESS   read-only
    STATUS       current
    DESCRIPTION
        "Cisco UCS adaptor:EthCompQueueProfile:dn managed object property"
    ::= { cucsAdaptorEthCompQueueProfileEntry 2 }

cucsAdaptorEthCompQueueProfileRn OBJECT-TYPE
    SYNTAX       SnmpAdminString
    MAX-ACCESS   read-only
    STATUS       current
    DESCRIPTION
        "Cisco UCS adaptor:EthCompQueueProfile:rn managed object property"
    ::= { cucsAdaptorEthCompQueueProfileEntry 3 }

cucsAdaptorEthCompQueueProfileCount OBJECT-TYPE
    SYNTAX       Gauge32
    MAX-ACCESS   read-only
    STATUS       current
    DESCRIPTION
        "Cisco UCS adaptor:EthCompQueueProfile:count managed
        object property"
    ::= { cucsAdaptorEthCompQueueProfileEntry 4 }

cucsAdaptorEthCompQueueProfileRingSize OBJECT-TYPE
    SYNTAX       Gauge32
    MAX-ACCESS   read-only
    STATUS       current
    DESCRIPTION
        "Cisco UCS adaptor:EthCompQueueProfile:ringSize
        managed object property"
    ::= { cucsAdaptorEthCompQueueProfileEntry 5 }

cucsAdaptorEthFailoverProfileTable OBJECT-TYPE
    SYNTAX           SEQUENCE OF CucsAdaptorEthFailoverProfileEntry
    MAX-ACCESS       not-accessible
    STATUS           current
    DESCRIPTION
        "Cisco UCS adaptor:EthFailoverProfile managed object table"
    ::= { cucsAdaptorObjects 4 }

cucsAdaptorEthFailoverProfileEntry OBJECT-TYPE
    SYNTAX           CucsAdaptorEthFailoverProfileEntry
    MAX-ACCESS       not-accessible
    STATUS           current
    DESCRIPTION
        "Entry for the cucsAdaptorEthFailoverProfileTable table."
    INDEX { cucsAdaptorEthFailoverProfileInstanceId }
    ::= { cucsAdaptorEthFailoverProfileTable 1 }

CucsAdaptorEthFailoverProfileEntry ::= SEQUENCE {
    cucsAdaptorEthFailoverProfileInstanceId                          CucsManagedObjectId,
    cucsAdaptorEthFailoverProfileDn                                  CucsManagedObjectDn,
    cucsAdaptorEthFailoverProfileRn                                  SnmpAdminString,
    cucsAdaptorEthFailoverProfileTimeout                             Gauge32
}

cucsAdaptorEthFailoverProfileInstanceId OBJECT-TYPE
    SYNTAX       CucsManagedObjectId
    MAX-ACCESS   not-accessible
    STATUS       current
    DESCRIPTION
        "Instance identifier of the managed object."
    ::= { cucsAdaptorEthFailoverProfileEntry 1 }

cucsAdaptorEthFailoverProfileDn OBJECT-TYPE
    SYNTAX       CucsManagedObjectDn
    MAX-ACCESS   read-only
    STATUS       current
    DESCRIPTION
        "Cisco UCS adaptor:EthFailoverProfile:dn managed object property"
    ::= { cucsAdaptorEthFailoverProfileEntry 2 }

cucsAdaptorEthFailoverProfileRn OBJECT-TYPE
    SYNTAX       SnmpAdminString
    MAX-ACCESS   read-only
    STATUS       current
    DESCRIPTION
        "Cisco UCS adaptor:EthFailoverProfile:rn managed object property"
    ::= { cucsAdaptorEthFailoverProfileEntry 3 }

cucsAdaptorEthFailoverProfileTimeout OBJECT-TYPE
    SYNTAX       Gauge32
    MAX-ACCESS   read-only
    STATUS       current
    DESCRIPTION
        "Cisco UCS adaptor:EthFailoverProfile:timeout managed
        object property"
    ::= { cucsAdaptorEthFailoverProfileEntry 4 }

cucsAdaptorEthInterruptProfileTable OBJECT-TYPE
    SYNTAX           SEQUENCE OF CucsAdaptorEthInterruptProfileEntry
    MAX-ACCESS       not-accessible
    STATUS           current
    DESCRIPTION
        "Cisco UCS adaptor:EthInterruptProfile managed object table"
    ::= { cucsAdaptorObjects 5 }

cucsAdaptorEthInterruptProfileEntry OBJECT-TYPE
    SYNTAX           CucsAdaptorEthInterruptProfileEntry
    MAX-ACCESS       not-accessible
    STATUS           current
    DESCRIPTION
        "Entry for the cucsAdaptorEthInterruptProfileTable table."
    INDEX { cucsAdaptorEthInterruptProfileInstanceId }
    ::= { cucsAdaptorEthInterruptProfileTable 1 }

CucsAdaptorEthInterruptProfileEntry ::= SEQUENCE {
    cucsAdaptorEthInterruptProfileInstanceId                         CucsManagedObjectId,
    cucsAdaptorEthInterruptProfileDn                                 CucsManagedObjectDn,
    cucsAdaptorEthInterruptProfileRn                                 SnmpAdminString,
    cucsAdaptorEthInterruptProfileCoalescingTime                     Gauge32,
    cucsAdaptorEthInterruptProfileCoalescingType                     CucsAdaptorEthInterruptProfileCoalescingType,
    cucsAdaptorEthInterruptProfileCount                              Gauge32,
    cucsAdaptorEthInterruptProfileMode                               CucsAdaptorInterruptMode
}

cucsAdaptorEthInterruptProfileInstanceId OBJECT-TYPE
    SYNTAX       CucsManagedObjectId
    MAX-ACCESS   not-accessible
    STATUS       current
    DESCRIPTION
        "Instance identifier of the managed object."
    ::= { cucsAdaptorEthInterruptProfileEntry 1 }

cucsAdaptorEthInterruptProfileDn OBJECT-TYPE
    SYNTAX       CucsManagedObjectDn
    MAX-ACCESS   read-only
    STATUS       current
    DESCRIPTION
        "Cisco UCS adaptor:EthInterruptProfile:dn managed object property"
    ::= { cucsAdaptorEthInterruptProfileEntry 2 }

cucsAdaptorEthInterruptProfileRn OBJECT-TYPE
    SYNTAX       SnmpAdminString
    MAX-ACCESS   read-only
    STATUS       current
    DESCRIPTION
        "Cisco UCS adaptor:EthInterruptProfile:rn managed object property"
    ::= { cucsAdaptorEthInterruptProfileEntry 3 }

cucsAdaptorEthInterruptProfileCoalescingTime OBJECT-TYPE
    SYNTAX       Gauge32
    MAX-ACCESS   read-only
    STATUS       current
    DESCRIPTION
        "Cisco UCS adaptor:EthInterruptProfile:coalescingTime
        managed object property"
    ::= { cucsAdaptorEthInterruptProfileEntry 4 }

cucsAdaptorEthInterruptProfileCoalescingType OBJECT-TYPE
    SYNTAX       CucsAdaptorEthInterruptProfileCoalescingType
    MAX-ACCESS   read-only
    STATUS       current
    DESCRIPTION
        "Cisco UCS adaptor:EthInterruptProfile:coalescingType
        managed object property"
    ::= { cucsAdaptorEthInterruptProfileEntry 5 }

cucsAdaptorEthInterruptProfileCount OBJECT-TYPE
    SYNTAX       Gauge32
    MAX-ACCESS   read-only
    STATUS       current
    DESCRIPTION
        "Cisco UCS adaptor:EthInterruptProfile:count managed
        object property"
    ::= { cucsAdaptorEthInterruptProfileEntry 6 }

cucsAdaptorEthInterruptProfileMode OBJECT-TYPE
    SYNTAX       CucsAdaptorInterruptMode
    MAX-ACCESS   read-only
    STATUS       current
    DESCRIPTION
        "Cisco UCS adaptor:EthInterruptProfile:mode managed
        object property"
    ::= { cucsAdaptorEthInterruptProfileEntry 7 }

cucsAdaptorEthInterruptScalingProfileTable OBJECT-TYPE
    SYNTAX           SEQUENCE OF CucsAdaptorEthInterruptScalingProfileEntry
    MAX-ACCESS       not-accessible
    STATUS           current
    DESCRIPTION
        "Cisco UCS adaptor:EthInterruptScalingProfile managed
        object table"
    ::= { cucsAdaptorObjects 136 }

cucsAdaptorEthInterruptScalingProfileEntry OBJECT-TYPE
    SYNTAX           CucsAdaptorEthInterruptScalingProfileEntry
    MAX-ACCESS       not-accessible
    STATUS           current
    DESCRIPTION
        "Entry for the cucsAdaptorEthInterruptScalingProfileTable table."
    INDEX { cucsAdaptorEthInterruptScalingProfileInstanceId }
    ::= { cucsAdaptorEthInterruptScalingProfileTable 1 }

CucsAdaptorEthInterruptScalingProfileEntry ::= SEQUENCE {
    cucsAdaptorEthInterruptScalingProfileInstanceId                  CucsManagedObjectId,
    cucsAdaptorEthInterruptScalingProfileDn                          CucsManagedObjectDn,
    cucsAdaptorEthInterruptScalingProfileRn                          SnmpAdminString,
    cucsAdaptorEthInterruptScalingProfileAdminState                  CucsAdaptorEthInterruptScalingProfileAdminState
}

cucsAdaptorEthInterruptScalingProfileInstanceId OBJECT-TYPE
    SYNTAX       CucsManagedObjectId
    MAX-ACCESS   not-accessible
    STATUS       current
    DESCRIPTION
        "Instance identifier of the managed object."
    ::= { cucsAdaptorEthInterruptScalingProfileEntry 1 }

cucsAdaptorEthInterruptScalingProfileDn OBJECT-TYPE
    SYNTAX       CucsManagedObjectDn
    MAX-ACCESS   read-only
    STATUS       current
    DESCRIPTION
        "Cisco UCS adaptor:EthInterruptScalingProfile:dn
        managed object property"
    ::= { cucsAdaptorEthInterruptScalingProfileEntry 2 }

cucsAdaptorEthInterruptScalingProfileRn OBJECT-TYPE
    SYNTAX       SnmpAdminString
    MAX-ACCESS   read-only
    STATUS       current
    DESCRIPTION
        "Cisco UCS adaptor:EthInterruptScalingProfile:rn
        managed object property"
    ::= { cucsAdaptorEthInterruptScalingProfileEntry 3 }

cucsAdaptorEthInterruptScalingProfileAdminState OBJECT-TYPE
    SYNTAX       CucsAdaptorEthInterruptScalingProfileAdminState
    MAX-ACCESS   read-only
    STATUS       current
    DESCRIPTION
        "Cisco UCS adaptor:EthInterruptScalingProfile:adminState
        managed object property"
    ::= { cucsAdaptorEthInterruptScalingProfileEntry 4 }

cucsAdaptorEthNVGREProfileTable OBJECT-TYPE
    SYNTAX           SEQUENCE OF CucsAdaptorEthNVGREProfileEntry
    MAX-ACCESS       not-accessible
    STATUS           current
    DESCRIPTION
        "Cisco UCS adaptor:EthNVGREProfile managed object table"
    ::= { cucsAdaptorObjects 117 }

cucsAdaptorEthNVGREProfileEntry OBJECT-TYPE
    SYNTAX           CucsAdaptorEthNVGREProfileEntry
    MAX-ACCESS       not-accessible
    STATUS           current
    DESCRIPTION
        "Entry for the cucsAdaptorEthNVGREProfileTable table."
    INDEX { cucsAdaptorEthNVGREProfileInstanceId }
    ::= { cucsAdaptorEthNVGREProfileTable 1 }

CucsAdaptorEthNVGREProfileEntry ::= SEQUENCE {
    cucsAdaptorEthNVGREProfileInstanceId                             CucsManagedObjectId,
    cucsAdaptorEthNVGREProfileDn                                     CucsManagedObjectDn,
    cucsAdaptorEthNVGREProfileRn                                     SnmpAdminString,
    cucsAdaptorEthNVGREProfileAdminState                             CucsAdaptorEthNVGREProfileAdminState
}

cucsAdaptorEthNVGREProfileInstanceId OBJECT-TYPE
    SYNTAX       CucsManagedObjectId
    MAX-ACCESS   not-accessible
    STATUS       current
    DESCRIPTION
        "Instance identifier of the managed object."
    ::= { cucsAdaptorEthNVGREProfileEntry 1 }

cucsAdaptorEthNVGREProfileDn OBJECT-TYPE
    SYNTAX       CucsManagedObjectDn
    MAX-ACCESS   read-only
    STATUS       current
    DESCRIPTION
        "Cisco UCS adaptor:EthNVGREProfile:dn managed object property"
    ::= { cucsAdaptorEthNVGREProfileEntry 2 }

cucsAdaptorEthNVGREProfileRn OBJECT-TYPE
    SYNTAX       SnmpAdminString
    MAX-ACCESS   read-only
    STATUS       current
    DESCRIPTION
        "Cisco UCS adaptor:EthNVGREProfile:rn managed object property"
    ::= { cucsAdaptorEthNVGREProfileEntry 3 }

cucsAdaptorEthNVGREProfileAdminState OBJECT-TYPE
    SYNTAX       CucsAdaptorEthNVGREProfileAdminState
    MAX-ACCESS   read-only
    STATUS       current
    DESCRIPTION
        "Cisco UCS adaptor:EthNVGREProfile:adminState managed
        object property"
    ::= { cucsAdaptorEthNVGREProfileEntry 4 }

cucsAdaptorEthOffloadProfileTable OBJECT-TYPE
    SYNTAX           SEQUENCE OF CucsAdaptorEthOffloadProfileEntry
    MAX-ACCESS       not-accessible
    STATUS           current
    DESCRIPTION
        "Cisco UCS adaptor:EthOffloadProfile managed object table"
    ::= { cucsAdaptorObjects 6 }

cucsAdaptorEthOffloadProfileEntry OBJECT-TYPE
    SYNTAX           CucsAdaptorEthOffloadProfileEntry
    MAX-ACCESS       not-accessible
    STATUS           current
    DESCRIPTION
        "Entry for the cucsAdaptorEthOffloadProfileTable table."
    INDEX { cucsAdaptorEthOffloadProfileInstanceId }
    ::= { cucsAdaptorEthOffloadProfileTable 1 }

CucsAdaptorEthOffloadProfileEntry ::= SEQUENCE {
    cucsAdaptorEthOffloadProfileInstanceId                           CucsManagedObjectId,
    cucsAdaptorEthOffloadProfileDn                                   CucsManagedObjectDn,
    cucsAdaptorEthOffloadProfileRn                                   SnmpAdminString,
    cucsAdaptorEthOffloadProfileLargeReceive                         CucsAdaptorEthOffloadProfileLargeReceive,
    cucsAdaptorEthOffloadProfileTcpRxChecksum                        CucsAdaptorEthOffloadProfileTcpRxChecksum,
    cucsAdaptorEthOffloadProfileTcpSegment                           CucsAdaptorEthOffloadProfileTcpSegment,
    cucsAdaptorEthOffloadProfileTcpTxChecksum                        CucsAdaptorEthOffloadProfileTcpTxChecksum
}

cucsAdaptorEthOffloadProfileInstanceId OBJECT-TYPE
    SYNTAX       CucsManagedObjectId
    MAX-ACCESS   not-accessible
    STATUS       current
    DESCRIPTION
        "Instance identifier of the managed object."
    ::= { cucsAdaptorEthOffloadProfileEntry 1 }

cucsAdaptorEthOffloadProfileDn OBJECT-TYPE
    SYNTAX       CucsManagedObjectDn
    MAX-ACCESS   read-only
    STATUS       current
    DESCRIPTION
        "Cisco UCS adaptor:EthOffloadProfile:dn managed object property"
    ::= { cucsAdaptorEthOffloadProfileEntry 2 }

cucsAdaptorEthOffloadProfileRn OBJECT-TYPE
    SYNTAX       SnmpAdminString
    MAX-ACCESS   read-only
    STATUS       current
    DESCRIPTION
        "Cisco UCS adaptor:EthOffloadProfile:rn managed object property"
    ::= { cucsAdaptorEthOffloadProfileEntry 3 }

cucsAdaptorEthOffloadProfileLargeReceive OBJECT-TYPE
    SYNTAX       CucsAdaptorEthOffloadProfileLargeReceive
    MAX-ACCESS   read-only
    STATUS       current
    DESCRIPTION
        "Cisco UCS adaptor:EthOffloadProfile:largeReceive
        managed object property"
    ::= { cucsAdaptorEthOffloadProfileEntry 4 }

cucsAdaptorEthOffloadProfileTcpRxChecksum OBJECT-TYPE
    SYNTAX       CucsAdaptorEthOffloadProfileTcpRxChecksum
    MAX-ACCESS   read-only
    STATUS       current
    DESCRIPTION
        "Cisco UCS adaptor:EthOffloadProfile:tcpRxChecksum
        managed object property"
    ::= { cucsAdaptorEthOffloadProfileEntry 5 }

cucsAdaptorEthOffloadProfileTcpSegment OBJECT-TYPE
    SYNTAX       CucsAdaptorEthOffloadProfileTcpSegment
    MAX-ACCESS   read-only
    STATUS       current
    DESCRIPTION
        "Cisco UCS adaptor:EthOffloadProfile:tcpSegment
        managed object property"
    ::= { cucsAdaptorEthOffloadProfileEntry 6 }

cucsAdaptorEthOffloadProfileTcpTxChecksum OBJECT-TYPE
    SYNTAX       CucsAdaptorEthOffloadProfileTcpTxChecksum
    MAX-ACCESS   read-only
    STATUS       current
    DESCRIPTION
        "Cisco UCS adaptor:EthOffloadProfile:tcpTxChecksum
        managed object property"
    ::= { cucsAdaptorEthOffloadProfileEntry 7 }

cucsAdaptorEthPortBySizeLargeStatsTable OBJECT-TYPE
    SYNTAX           SEQUENCE OF CucsAdaptorEthPortBySizeLargeStatsEntry
    MAX-ACCESS       not-accessible
    STATUS           current
    DESCRIPTION
        "Cisco UCS adaptor:EthPortBySizeLargeStats managed object table"
    ::= { cucsAdaptorObjects 7 }

cucsAdaptorEthPortBySizeLargeStatsEntry OBJECT-TYPE
    SYNTAX           CucsAdaptorEthPortBySizeLargeStatsEntry
    MAX-ACCESS       not-accessible
    STATUS           current
    DESCRIPTION
        "Entry for the cucsAdaptorEthPortBySizeLargeStatsTable table."
    INDEX { cucsAdaptorEthPortBySizeLargeStatsInstanceId }
    ::= { cucsAdaptorEthPortBySizeLargeStatsTable 1 }

CucsAdaptorEthPortBySizeLargeStatsEntry ::= SEQUENCE {
    cucsAdaptorEthPortBySizeLargeStatsInstanceId                     CucsManagedObjectId,
    cucsAdaptorEthPortBySizeLargeStatsDn                             CucsManagedObjectDn,
    cucsAdaptorEthPortBySizeLargeStatsRn                             SnmpAdminString,
    cucsAdaptorEthPortBySizeLargeStatsGreaterThanOrEqualTo9216       Unsigned64,
    cucsAdaptorEthPortBySizeLargeStatsGreaterThanOrEqualTo9216Delta  Counter64,
    cucsAdaptorEthPortBySizeLargeStatsGreaterThanOrEqTo9216DeltaAvg  Unsigned64,
    cucsAdaptorEthPortBySizeLargeStatsGreaterThanOrEqTo9216DeltaMax  Unsigned64,
    cucsAdaptorEthPortBySizeLargeStatsGreaterThanOrEqTo9216DeltaMin  Unsigned64,
    cucsAdaptorEthPortBySizeLargeStatsIntervals                      Gauge32,
    cucsAdaptorEthPortBySizeLargeStatsLessThan2048                   Unsigned64,
    cucsAdaptorEthPortBySizeLargeStatsLessThan2048Delta              Counter64,
    cucsAdaptorEthPortBySizeLargeStatsLessThan2048DeltaAvg           Unsigned64,
    cucsAdaptorEthPortBySizeLargeStatsLessThan2048DeltaMax           Unsigned64,
    cucsAdaptorEthPortBySizeLargeStatsLessThan2048DeltaMin           Unsigned64,
    cucsAdaptorEthPortBySizeLargeStatsLessThan4096                   Unsigned64,
    cucsAdaptorEthPortBySizeLargeStatsLessThan4096Delta              Counter64,
    cucsAdaptorEthPortBySizeLargeStatsLessThan4096DeltaAvg           Unsigned64,
    cucsAdaptorEthPortBySizeLargeStatsLessThan4096DeltaMax           Unsigned64,
    cucsAdaptorEthPortBySizeLargeStatsLessThan4096DeltaMin           Unsigned64,
    cucsAdaptorEthPortBySizeLargeStatsLessThan8192                   Unsigned64,
    cucsAdaptorEthPortBySizeLargeStatsLessThan8192Delta              Counter64,
    cucsAdaptorEthPortBySizeLargeStatsLessThan8192DeltaAvg           Unsigned64,
    cucsAdaptorEthPortBySizeLargeStatsLessThan8192DeltaMax           Unsigned64,
    cucsAdaptorEthPortBySizeLargeStatsLessThan8192DeltaMin           Unsigned64,
    cucsAdaptorEthPortBySizeLargeStatsLessThan9216                   Unsigned64,
    cucsAdaptorEthPortBySizeLargeStatsLessThan9216Delta              Counter64,
    cucsAdaptorEthPortBySizeLargeStatsLessThan9216DeltaAvg           Unsigned64,
    cucsAdaptorEthPortBySizeLargeStatsLessThan9216DeltaMax           Unsigned64,
    cucsAdaptorEthPortBySizeLargeStatsLessThan9216DeltaMin           Unsigned64,
    cucsAdaptorEthPortBySizeLargeStatsLessThanOrEqualTo1518          Unsigned64,
    cucsAdaptorEthPortBySizeLargeStatsLessThanOrEqualTo1518Delta     Counter64,
    cucsAdaptorEthPortBySizeLargeStatsLessThanOrEqualTo1518DeltaAvg  Unsigned64,
    cucsAdaptorEthPortBySizeLargeStatsLessThanOrEqualTo1518DeltaMax  Unsigned64,
    cucsAdaptorEthPortBySizeLargeStatsLessThanOrEqualTo1518DeltaMin  Unsigned64,
    cucsAdaptorEthPortBySizeLargeStatsNoBreakdownGreaterThan1518     Unsigned64,
    cucsAdaptorEthPortBySizeLargeStatsNoBreakdownGrThan1518Delta     Counter64,
    cucsAdaptorEthPortBySizeLargeStatsNoBreakdownGrThan1518DeltaAvg  Unsigned64,
    cucsAdaptorEthPortBySizeLargeStatsNoBreakdownGrThan1518DeltaMax  Unsigned64,
    cucsAdaptorEthPortBySizeLargeStatsNoBreakdownGrThan1518DeltaMin  Unsigned64,
    cucsAdaptorEthPortBySizeLargeStatsSuspect                        TruthValue,
    cucsAdaptorEthPortBySizeLargeStatsThresholded                    CucsAdaptorEthPortBySizeLargeStatsThresholded,
    cucsAdaptorEthPortBySizeLargeStatsTimeCollected                  DateAndTime,
    cucsAdaptorEthPortBySizeLargeStatsTrafficDirection               CucsAdaptorAdapterStatsTrafficDir,
    cucsAdaptorEthPortBySizeLargeStatsUpdate                         Gauge32
}

cucsAdaptorEthPortBySizeLargeStatsInstanceId OBJECT-TYPE
    SYNTAX       CucsManagedObjectId
    MAX-ACCESS   not-accessible
    STATUS       current
    DESCRIPTION
        "Instance identifier of the managed object."
    ::= { cucsAdaptorEthPortBySizeLargeStatsEntry 1 }

cucsAdaptorEthPortBySizeLargeStatsDn OBJECT-TYPE
    SYNTAX       CucsManagedObjectDn
    MAX-ACCESS   read-only
    STATUS       current
    DESCRIPTION
        "Cisco UCS adaptor:EthPortBySizeLargeStats:dn managed
        object property"
    ::= { cucsAdaptorEthPortBySizeLargeStatsEntry 2 }

cucsAdaptorEthPortBySizeLargeStatsRn OBJECT-TYPE
    SYNTAX       SnmpAdminString
    MAX-ACCESS   read-only
    STATUS       current
    DESCRIPTION
        "Cisco UCS adaptor:EthPortBySizeLargeStats:rn managed
        object property"
    ::= { cucsAdaptorEthPortBySizeLargeStatsEntry 3 }

cucsAdaptorEthPortBySizeLargeStatsGreaterThanOrEqualTo9216 OBJECT-TYPE
    SYNTAX       Unsigned64
    MAX-ACCESS   read-only
    STATUS       current
    DESCRIPTION
        "Cisco UCS adaptor:EthPortBySizeLargeStats:greaterThanOrEqualTo921
        6 managed object property"
    ::= { cucsAdaptorEthPortBySizeLargeStatsEntry 4 }

cucsAdaptorEthPortBySizeLargeStatsGreaterThanOrEqualTo9216Delta OBJECT-TYPE
    SYNTAX       Counter64
    MAX-ACCESS   read-only
    STATUS       current
    DESCRIPTION
        "Cisco UCS adaptor:EthPortBySizeLargeStats:greaterThanOrEqualTo921
        6Delta managed object property"
    ::= { cucsAdaptorEthPortBySizeLargeStatsEntry 5 }

cucsAdaptorEthPortBySizeLargeStatsGreaterThanOrEqTo9216DeltaAvg OBJECT-TYPE
    SYNTAX       Unsigned64
    MAX-ACCESS   read-only
    STATUS       current
    DESCRIPTION
        "Cisco UCS adaptor:EthPortBySizeLargeStats:greaterThanOrEqualTo921
        6DeltaAvg managed object property"
    ::= { cucsAdaptorEthPortBySizeLargeStatsEntry 6 }

cucsAdaptorEthPortBySizeLargeStatsGreaterThanOrEqTo9216DeltaMax OBJECT-TYPE
    SYNTAX       Unsigned64
    MAX-ACCESS   read-only
    STATUS       current
    DESCRIPTION
        "Cisco UCS adaptor:EthPortBySizeLargeStats:greaterThanOrEqualTo921
        6DeltaMax managed object property"
    ::= { cucsAdaptorEthPortBySizeLargeStatsEntry 7 }

cucsAdaptorEthPortBySizeLargeStatsGreaterThanOrEqTo9216DeltaMin OBJECT-TYPE
    SYNTAX       Unsigned64
    MAX-ACCESS   read-only
    STATUS       current
    DESCRIPTION
        "Cisco UCS adaptor:EthPortBySizeLargeStats:greaterThanOrEqualTo921
        6DeltaMin managed object property"
    ::= { cucsAdaptorEthPortBySizeLargeStatsEntry 8 }

cucsAdaptorEthPortBySizeLargeStatsIntervals OBJECT-TYPE
    SYNTAX       Gauge32
    MAX-ACCESS   read-only
    STATUS       current
    DESCRIPTION
        "Cisco UCS adaptor:EthPortBySizeLargeStats:intervals
        managed object property"
    ::= { cucsAdaptorEthPortBySizeLargeStatsEntry 9 }

cucsAdaptorEthPortBySizeLargeStatsLessThan2048 OBJECT-TYPE
    SYNTAX       Unsigned64
    MAX-ACCESS   read-only
    STATUS       current
    DESCRIPTION
        "Cisco UCS adaptor:EthPortBySizeLargeStats:lessThan2048
        managed object property"
    ::= { cucsAdaptorEthPortBySizeLargeStatsEntry 10 }

cucsAdaptorEthPortBySizeLargeStatsLessThan2048Delta OBJECT-TYPE
    SYNTAX       Counter64
    MAX-ACCESS   read-only
    STATUS       current
    DESCRIPTION
        "Cisco UCS adaptor:EthPortBySizeLargeStats:lessThan2048Delta
        managed object property"
    ::= { cucsAdaptorEthPortBySizeLargeStatsEntry 11 }

cucsAdaptorEthPortBySizeLargeStatsLessThan2048DeltaAvg OBJECT-TYPE
    SYNTAX       Unsigned64
    MAX-ACCESS   read-only
    STATUS       current
    DESCRIPTION
        "Cisco UCS adaptor:EthPortBySizeLargeStats:lessThan2048DeltaAvg
        managed object property"
    ::= { cucsAdaptorEthPortBySizeLargeStatsEntry 12 }

cucsAdaptorEthPortBySizeLargeStatsLessThan2048DeltaMax OBJECT-TYPE
    SYNTAX       Unsigned64
    MAX-ACCESS   read-only
    STATUS       current
    DESCRIPTION
        "Cisco UCS adaptor:EthPortBySizeLargeStats:lessThan2048DeltaMax
        managed object property"
    ::= { cucsAdaptorEthPortBySizeLargeStatsEntry 13 }

cucsAdaptorEthPortBySizeLargeStatsLessThan2048DeltaMin OBJECT-TYPE
    SYNTAX       Unsigned64
    MAX-ACCESS   read-only
    STATUS       current
    DESCRIPTION
        "Cisco UCS adaptor:EthPortBySizeLargeStats:lessThan2048DeltaMin
        managed object property"
    ::= { cucsAdaptorEthPortBySizeLargeStatsEntry 14 }

cucsAdaptorEthPortBySizeLargeStatsLessThan4096 OBJECT-TYPE
    SYNTAX       Unsigned64
    MAX-ACCESS   read-only
    STATUS       current
    DESCRIPTION
        "Cisco UCS adaptor:EthPortBySizeLargeStats:lessThan4096
        managed object property"
    ::= { cucsAdaptorEthPortBySizeLargeStatsEntry 15 }

cucsAdaptorEthPortBySizeLargeStatsLessThan4096Delta OBJECT-TYPE
    SYNTAX       Counter64
    MAX-ACCESS   read-only
    STATUS       current
    DESCRIPTION
        "Cisco UCS adaptor:EthPortBySizeLargeStats:lessThan4096Delta
        managed object property"
    ::= { cucsAdaptorEthPortBySizeLargeStatsEntry 16 }

cucsAdaptorEthPortBySizeLargeStatsLessThan4096DeltaAvg OBJECT-TYPE
    SYNTAX       Unsigned64
    MAX-ACCESS   read-only
    STATUS       current
    DESCRIPTION
        "Cisco UCS adaptor:EthPortBySizeLargeStats:lessThan4096DeltaAvg
        managed object property"
    ::= { cucsAdaptorEthPortBySizeLargeStatsEntry 17 }

cucsAdaptorEthPortBySizeLargeStatsLessThan4096DeltaMax OBJECT-TYPE
    SYNTAX       Unsigned64
    MAX-ACCESS   read-only
    STATUS       current
    DESCRIPTION
        "Cisco UCS adaptor:EthPortBySizeLargeStats:lessThan4096DeltaMax
        managed object property"
    ::= { cucsAdaptorEthPortBySizeLargeStatsEntry 18 }

cucsAdaptorEthPortBySizeLargeStatsLessThan4096DeltaMin OBJECT-TYPE
    SYNTAX       Unsigned64
    MAX-ACCESS   read-only
    STATUS       current
    DESCRIPTION
        "Cisco UCS adaptor:EthPortBySizeLargeStats:lessThan4096DeltaMin
        managed object property"
    ::= { cucsAdaptorEthPortBySizeLargeStatsEntry 19 }

cucsAdaptorEthPortBySizeLargeStatsLessThan8192 OBJECT-TYPE
    SYNTAX       Unsigned64
    MAX-ACCESS   read-only
    STATUS       current
    DESCRIPTION
        "Cisco UCS adaptor:EthPortBySizeLargeStats:lessThan8192
        managed object property"
    ::= { cucsAdaptorEthPortBySizeLargeStatsEntry 20 }

cucsAdaptorEthPortBySizeLargeStatsLessThan8192Delta OBJECT-TYPE
    SYNTAX       Counter64
    MAX-ACCESS   read-only
    STATUS       current
    DESCRIPTION
        "Cisco UCS adaptor:EthPortBySizeLargeStats:lessThan8192Delta
        managed object property"
    ::= { cucsAdaptorEthPortBySizeLargeStatsEntry 21 }

cucsAdaptorEthPortBySizeLargeStatsLessThan8192DeltaAvg OBJECT-TYPE
    SYNTAX       Unsigned64
    MAX-ACCESS   read-only
    STATUS       current
    DESCRIPTION
        "Cisco UCS adaptor:EthPortBySizeLargeStats:lessThan8192DeltaAvg
        managed object property"
    ::= { cucsAdaptorEthPortBySizeLargeStatsEntry 22 }

cucsAdaptorEthPortBySizeLargeStatsLessThan8192DeltaMax OBJECT-TYPE
    SYNTAX       Unsigned64
    MAX-ACCESS   read-only
    STATUS       current
    DESCRIPTION
        "Cisco UCS adaptor:EthPortBySizeLargeStats:lessThan8192DeltaMax
        managed object property"
    ::= { cucsAdaptorEthPortBySizeLargeStatsEntry 23 }

cucsAdaptorEthPortBySizeLargeStatsLessThan8192DeltaMin OBJECT-TYPE
    SYNTAX       Unsigned64
    MAX-ACCESS   read-only
    STATUS       current
    DESCRIPTION
        "Cisco UCS adaptor:EthPortBySizeLargeStats:lessThan8192DeltaMin
        managed object property"
    ::= { cucsAdaptorEthPortBySizeLargeStatsEntry 24 }

cucsAdaptorEthPortBySizeLargeStatsLessThan9216 OBJECT-TYPE
    SYNTAX       Unsigned64
    MAX-ACCESS   read-only
    STATUS       current
    DESCRIPTION
        "Cisco UCS adaptor:EthPortBySizeLargeStats:lessThan9216
        managed object property"
    ::= { cucsAdaptorEthPortBySizeLargeStatsEntry 25 }

cucsAdaptorEthPortBySizeLargeStatsLessThan9216Delta OBJECT-TYPE
    SYNTAX       Counter64
    MAX-ACCESS   read-only
    STATUS       current
    DESCRIPTION
        "Cisco UCS adaptor:EthPortBySizeLargeStats:lessThan9216Delta
        managed object property"
    ::= { cucsAdaptorEthPortBySizeLargeStatsEntry 26 }

cucsAdaptorEthPortBySizeLargeStatsLessThan9216DeltaAvg OBJECT-TYPE
    SYNTAX       Unsigned64
    MAX-ACCESS   read-only
    STATUS       current
    DESCRIPTION
        "Cisco UCS adaptor:EthPortBySizeLargeStats:lessThan9216DeltaAvg
        managed object property"
    ::= { cucsAdaptorEthPortBySizeLargeStatsEntry 27 }

cucsAdaptorEthPortBySizeLargeStatsLessThan9216DeltaMax OBJECT-TYPE
    SYNTAX       Unsigned64
    MAX-ACCESS   read-only
    STATUS       current
    DESCRIPTION
        "Cisco UCS adaptor:EthPortBySizeLargeStats:lessThan9216DeltaMax
        managed object property"
    ::= { cucsAdaptorEthPortBySizeLargeStatsEntry 28 }

cucsAdaptorEthPortBySizeLargeStatsLessThan9216DeltaMin OBJECT-TYPE
    SYNTAX       Unsigned64
    MAX-ACCESS   read-only
    STATUS       current
    DESCRIPTION
        "Cisco UCS adaptor:EthPortBySizeLargeStats:lessThan9216DeltaMin
        managed object property"
    ::= { cucsAdaptorEthPortBySizeLargeStatsEntry 29 }

cucsAdaptorEthPortBySizeLargeStatsLessThanOrEqualTo1518 OBJECT-TYPE
    SYNTAX       Unsigned64
    MAX-ACCESS   read-only
    STATUS       current
    DESCRIPTION
        "Cisco UCS adaptor:EthPortBySizeLargeStats:lessThanOrEqualTo1518
        managed object property"
    ::= { cucsAdaptorEthPortBySizeLargeStatsEntry 30 }

cucsAdaptorEthPortBySizeLargeStatsLessThanOrEqualTo1518Delta OBJECT-TYPE
    SYNTAX       Counter64
    MAX-ACCESS   read-only
    STATUS       current
    DESCRIPTION
        "Cisco UCS adaptor:EthPortBySizeLargeStats:lessThanOrEqualTo1518De
        lta managed object property"
    ::= { cucsAdaptorEthPortBySizeLargeStatsEntry 31 }

cucsAdaptorEthPortBySizeLargeStatsLessThanOrEqualTo1518DeltaAvg OBJECT-TYPE
    SYNTAX       Unsigned64
    MAX-ACCESS   read-only
    STATUS       current
    DESCRIPTION
        "Cisco UCS adaptor:EthPortBySizeLargeStats:lessThanOrEqualTo1518De
        ltaAvg managed object property"
    ::= { cucsAdaptorEthPortBySizeLargeStatsEntry 32 }

cucsAdaptorEthPortBySizeLargeStatsLessThanOrEqualTo1518DeltaMax OBJECT-TYPE
    SYNTAX       Unsigned64
    MAX-ACCESS   read-only
    STATUS       current
    DESCRIPTION
        "Cisco UCS adaptor:EthPortBySizeLargeStats:lessThanOrEqualTo1518De
        ltaMax managed object property"
    ::= { cucsAdaptorEthPortBySizeLargeStatsEntry 33 }

cucsAdaptorEthPortBySizeLargeStatsLessThanOrEqualTo1518DeltaMin OBJECT-TYPE
    SYNTAX       Unsigned64
    MAX-ACCESS   read-only
    STATUS       current
    DESCRIPTION
        "Cisco UCS adaptor:EthPortBySizeLargeStats:lessThanOrEqualTo1518De
        ltaMin managed object property"
    ::= { cucsAdaptorEthPortBySizeLargeStatsEntry 34 }

cucsAdaptorEthPortBySizeLargeStatsNoBreakdownGreaterThan1518 OBJECT-TYPE
    SYNTAX       Unsigned64
    MAX-ACCESS   read-only
    STATUS       current
    DESCRIPTION
        "Cisco UCS adaptor:EthPortBySizeLargeStats:noBreakdownGreaterThan1
        518 managed object property"
    ::= { cucsAdaptorEthPortBySizeLargeStatsEntry 35 }

cucsAdaptorEthPortBySizeLargeStatsNoBreakdownGrThan1518Delta OBJECT-TYPE
    SYNTAX       Counter64
    MAX-ACCESS   read-only
    STATUS       current
    DESCRIPTION
        "Cisco UCS adaptor:EthPortBySizeLargeStats:noBreakdownGreaterThan1
        518Delta managed object property"
    ::= { cucsAdaptorEthPortBySizeLargeStatsEntry 36 }

cucsAdaptorEthPortBySizeLargeStatsNoBreakdownGrThan1518DeltaAvg OBJECT-TYPE
    SYNTAX       Unsigned64
    MAX-ACCESS   read-only
    STATUS       current
    DESCRIPTION
        "Cisco UCS adaptor:EthPortBySizeLargeStats:noBreakdownGreaterThan1
        518DeltaAvg managed object property"
    ::= { cucsAdaptorEthPortBySizeLargeStatsEntry 37 }

cucsAdaptorEthPortBySizeLargeStatsNoBreakdownGrThan1518DeltaMax OBJECT-TYPE
    SYNTAX       Unsigned64
    MAX-ACCESS   read-only
    STATUS       current
    DESCRIPTION
        "Cisco UCS adaptor:EthPortBySizeLargeStats:noBreakdownGreaterThan1
        518DeltaMax managed object property"
    ::= { cucsAdaptorEthPortBySizeLargeStatsEntry 38 }

cucsAdaptorEthPortBySizeLargeStatsNoBreakdownGrThan1518DeltaMin OBJECT-TYPE
    SYNTAX       Unsigned64
    MAX-ACCESS   read-only
    STATUS       current
    DESCRIPTION
        "Cisco UCS adaptor:EthPortBySizeLargeStats:noBreakdownGreaterThan1
        518DeltaMin managed object property"
    ::= { cucsAdaptorEthPortBySizeLargeStatsEntry 39 }

cucsAdaptorEthPortBySizeLargeStatsSuspect OBJECT-TYPE
    SYNTAX       TruthValue
    MAX-ACCESS   read-only
    STATUS       current
    DESCRIPTION
        "Cisco UCS adaptor:EthPortBySizeLargeStats:suspect
        managed object property"
    ::= { cucsAdaptorEthPortBySizeLargeStatsEntry 40 }

cucsAdaptorEthPortBySizeLargeStatsThresholded OBJECT-TYPE
    SYNTAX       CucsAdaptorEthPortBySizeLargeStatsThresholded
    MAX-ACCESS   read-only
    STATUS       current
    DESCRIPTION
        "Cisco UCS adaptor:EthPortBySizeLargeStats:thresholded
        managed object property"
    ::= { cucsAdaptorEthPortBySizeLargeStatsEntry 41 }

cucsAdaptorEthPortBySizeLargeStatsTimeCollected OBJECT-TYPE
    SYNTAX       DateAndTime
    MAX-ACCESS   read-only
    STATUS       current
    DESCRIPTION
        "Cisco UCS adaptor:EthPortBySizeLargeStats:timeCollected
        managed object property"
    ::= { cucsAdaptorEthPortBySizeLargeStatsEntry 42 }

cucsAdaptorEthPortBySizeLargeStatsTrafficDirection OBJECT-TYPE
    SYNTAX       CucsAdaptorAdapterStatsTrafficDir
    MAX-ACCESS   read-only
    STATUS       current
    DESCRIPTION
        "Cisco UCS adaptor:EthPortBySizeLargeStats:trafficDirection
        managed object property"
    ::= { cucsAdaptorEthPortBySizeLargeStatsEntry 43 }

cucsAdaptorEthPortBySizeLargeStatsUpdate OBJECT-TYPE
    SYNTAX       Gauge32
    MAX-ACCESS   read-only
    STATUS       current
    DESCRIPTION
        "Cisco UCS adaptor:EthPortBySizeLargeStats:update
        managed object property"
    ::= { cucsAdaptorEthPortBySizeLargeStatsEntry 44 }

cucsAdaptorEthPortBySizeLargeStatsHistTable OBJECT-TYPE
    SYNTAX           SEQUENCE OF CucsAdaptorEthPortBySizeLargeStatsHistEntry
    MAX-ACCESS       not-accessible
    STATUS           current
    DESCRIPTION
        "Cisco UCS adaptor:EthPortBySizeLargeStatsHist
        managed object table"
    ::= { cucsAdaptorObjects 8 }

cucsAdaptorEthPortBySizeLargeStatsHistEntry OBJECT-TYPE
    SYNTAX           CucsAdaptorEthPortBySizeLargeStatsHistEntry
    MAX-ACCESS       not-accessible
    STATUS           current
    DESCRIPTION
        "Entry for the cucsAdaptorEthPortBySizeLargeStatsHistTable table."
    INDEX { cucsAdaptorEthPortBySizeLargeStatsHistInstanceId }
    ::= { cucsAdaptorEthPortBySizeLargeStatsHistTable 1 }

CucsAdaptorEthPortBySizeLargeStatsHistEntry ::= SEQUENCE {
    cucsAdaptorEthPortBySizeLargeStatsHistInstanceId                 CucsManagedObjectId,
    cucsAdaptorEthPortBySizeLargeStatsHistDn                         CucsManagedObjectDn,
    cucsAdaptorEthPortBySizeLargeStatsHistRn                         SnmpAdminString,
    cucsAdaptorEthPortBySizeLargeStatsHistGreaterThanOrEqualTo9216   Unsigned64,
    cucsAdaptorEthPortBySizeLargeStatsHistGrThanOrEqTo9216Delta      Unsigned64,
    cucsAdaptorEthPortBySizeLargeStatsHistGrThanOrEqTo9216DeltaAvg   Unsigned64,
    cucsAdaptorEthPortBySizeLargeStatsHistGrThanOrEqTo9216DeltaMax   Unsigned64,
    cucsAdaptorEthPortBySizeLargeStatsHistGrThanOrEqTo9216DeltaMin   Unsigned64,
    cucsAdaptorEthPortBySizeLargeStatsHistId                         Unsigned64,
    cucsAdaptorEthPortBySizeLargeStatsHistLessThan2048               Unsigned64,
    cucsAdaptorEthPortBySizeLargeStatsHistLessThan2048Delta          Unsigned64,
    cucsAdaptorEthPortBySizeLargeStatsHistLessThan2048DeltaAvg       Unsigned64,
    cucsAdaptorEthPortBySizeLargeStatsHistLessThan2048DeltaMax       Unsigned64,
    cucsAdaptorEthPortBySizeLargeStatsHistLessThan2048DeltaMin       Unsigned64,
    cucsAdaptorEthPortBySizeLargeStatsHistLessThan4096               Unsigned64,
    cucsAdaptorEthPortBySizeLargeStatsHistLessThan4096Delta          Unsigned64,
    cucsAdaptorEthPortBySizeLargeStatsHistLessThan4096DeltaAvg       Unsigned64,
    cucsAdaptorEthPortBySizeLargeStatsHistLessThan4096DeltaMax       Unsigned64,
    cucsAdaptorEthPortBySizeLargeStatsHistLessThan4096DeltaMin       Unsigned64,
    cucsAdaptorEthPortBySizeLargeStatsHistLessThan8192               Unsigned64,
    cucsAdaptorEthPortBySizeLargeStatsHistLessThan8192Delta          Unsigned64,
    cucsAdaptorEthPortBySizeLargeStatsHistLessThan8192DeltaAvg       Unsigned64,
    cucsAdaptorEthPortBySizeLargeStatsHistLessThan8192DeltaMax       Unsigned64,
    cucsAdaptorEthPortBySizeLargeStatsHistLessThan8192DeltaMin       Unsigned64,
    cucsAdaptorEthPortBySizeLargeStatsHistLessThan9216               Unsigned64,
    cucsAdaptorEthPortBySizeLargeStatsHistLessThan9216Delta          Unsigned64,
    cucsAdaptorEthPortBySizeLargeStatsHistLessThan9216DeltaAvg       Unsigned64,
    cucsAdaptorEthPortBySizeLargeStatsHistLessThan9216DeltaMax       Unsigned64,
    cucsAdaptorEthPortBySizeLargeStatsHistLessThan9216DeltaMin       Unsigned64,
    cucsAdaptorEthPortBySizeLargeStatsHistLessThanOrEqualTo1518      Unsigned64,
    cucsAdaptorEthPortBySizeLargeStatsHistLessThanOrEqualTo1518Delta Unsigned64,
    cucsAdaptorEthPortBySizeLargeStatsHistLessThanOrEqTo1518DeltaAvg Unsigned64,
    cucsAdaptorEthPortBySizeLargeStatsHistLessThanOrEqTo1518DeltaMax Unsigned64,
    cucsAdaptorEthPortBySizeLargeStatsHistLessThanOrEqTo1518DeltaMin Unsigned64,
    cucsAdaptorEthPortBySizeLargeStatsHistMostRecent                 TruthValue,
    cucsAdaptorEthPortBySizeLargeStatsHistNoBreakdownGreaterThan1518 Unsigned64,
    cucsAdaptorEthPortBySizeLargeStatsHistNoBreakdownGrTh1518Delta   Unsigned64,
    cucsAdaptorEthPortBySizeLargeStatsHistNoBreakdnGrTh1518DeltaAvg  Unsigned64,
    cucsAdaptorEthPortBySizeLargeStatsHistNoBreakdnGrTh1518DeltaMax  Unsigned64,
    cucsAdaptorEthPortBySizeLargeStatsHistNoBreakdnGrTh1518DeltaMin  Unsigned64,
    cucsAdaptorEthPortBySizeLargeStatsHistSuspect                    TruthValue,
    cucsAdaptorEthPortBySizeLargeStatsHistThresholded                CucsAdaptorEthPortBySizeLargeStatsHistThresholded,
    cucsAdaptorEthPortBySizeLargeStatsHistTimeCollected              DateAndTime
}

cucsAdaptorEthPortBySizeLargeStatsHistInstanceId OBJECT-TYPE
    SYNTAX       CucsManagedObjectId
    MAX-ACCESS   not-accessible
    STATUS       current
    DESCRIPTION
        "Instance identifier of the managed object."
    ::= { cucsAdaptorEthPortBySizeLargeStatsHistEntry 1 }

cucsAdaptorEthPortBySizeLargeStatsHistDn OBJECT-TYPE
    SYNTAX       CucsManagedObjectDn
    MAX-ACCESS   read-only
    STATUS       current
    DESCRIPTION
        "Cisco UCS adaptor:EthPortBySizeLargeStatsHist:dn
        managed object property"
    ::= { cucsAdaptorEthPortBySizeLargeStatsHistEntry 2 }

cucsAdaptorEthPortBySizeLargeStatsHistRn OBJECT-TYPE
    SYNTAX       SnmpAdminString
    MAX-ACCESS   read-only
    STATUS       current
    DESCRIPTION
        "Cisco UCS adaptor:EthPortBySizeLargeStatsHist:rn
        managed object property"
    ::= { cucsAdaptorEthPortBySizeLargeStatsHistEntry 3 }

cucsAdaptorEthPortBySizeLargeStatsHistGreaterThanOrEqualTo9216 OBJECT-TYPE
    SYNTAX       Unsigned64
    MAX-ACCESS   read-only
    STATUS       current
    DESCRIPTION
        "Cisco UCS adaptor:EthPortBySizeLargeStatsHist:greaterThanOrEqualT
        o9216 managed object property"
    ::= { cucsAdaptorEthPortBySizeLargeStatsHistEntry 4 }

cucsAdaptorEthPortBySizeLargeStatsHistGrThanOrEqTo9216Delta OBJECT-TYPE
    SYNTAX       Unsigned64
    MAX-ACCESS   read-only
    STATUS       current
    DESCRIPTION
        "Cisco UCS adaptor:EthPortBySizeLargeStatsHist:greaterThanOrEqualT
        o9216Delta managed object property"
    ::= { cucsAdaptorEthPortBySizeLargeStatsHistEntry 5 }

cucsAdaptorEthPortBySizeLargeStatsHistGrThanOrEqTo9216DeltaAvg OBJECT-TYPE
    SYNTAX       Unsigned64
    MAX-ACCESS   read-only
    STATUS       current
    DESCRIPTION
        "Cisco UCS adaptor:EthPortBySizeLargeStatsHist:greaterThanOrEqualT
        o9216DeltaAvg managed object property"
    ::= { cucsAdaptorEthPortBySizeLargeStatsHistEntry 6 }

cucsAdaptorEthPortBySizeLargeStatsHistGrThanOrEqTo9216DeltaMax OBJECT-TYPE
    SYNTAX       Unsigned64
    MAX-ACCESS   read-only
    STATUS       current
    DESCRIPTION
        "Cisco UCS adaptor:EthPortBySizeLargeStatsHist:greaterThanOrEqualT
        o9216DeltaMax managed object property"
    ::= { cucsAdaptorEthPortBySizeLargeStatsHistEntry 7 }

cucsAdaptorEthPortBySizeLargeStatsHistGrThanOrEqTo9216DeltaMin OBJECT-TYPE
    SYNTAX       Unsigned64
    MAX-ACCESS   read-only
    STATUS       current
    DESCRIPTION
        "Cisco UCS adaptor:EthPortBySizeLargeStatsHist:greaterThanOrEqualT
        o9216DeltaMin managed object property"
    ::= { cucsAdaptorEthPortBySizeLargeStatsHistEntry 8 }

cucsAdaptorEthPortBySizeLargeStatsHistId OBJECT-TYPE
    SYNTAX       Unsigned64
    MAX-ACCESS   read-only
    STATUS       current
    DESCRIPTION
        "Cisco UCS adaptor:EthPortBySizeLargeStatsHist:id
        managed object property"
    ::= { cucsAdaptorEthPortBySizeLargeStatsHistEntry 9 }

cucsAdaptorEthPortBySizeLargeStatsHistLessThan2048 OBJECT-TYPE
    SYNTAX       Unsigned64
    MAX-ACCESS   read-only
    STATUS       current
    DESCRIPTION
        "Cisco UCS adaptor:EthPortBySizeLargeStatsHist:lessThan2048
        managed object property"
    ::= { cucsAdaptorEthPortBySizeLargeStatsHistEntry 10 }

cucsAdaptorEthPortBySizeLargeStatsHistLessThan2048Delta OBJECT-TYPE
    SYNTAX       Unsigned64
    MAX-ACCESS   read-only
    STATUS       current
    DESCRIPTION
        "Cisco UCS adaptor:EthPortBySizeLargeStatsHist:lessThan2048Delta
        managed object property"
    ::= { cucsAdaptorEthPortBySizeLargeStatsHistEntry 11 }

cucsAdaptorEthPortBySizeLargeStatsHistLessThan2048DeltaAvg OBJECT-TYPE
    SYNTAX       Unsigned64
    MAX-ACCESS   read-only
    STATUS       current
    DESCRIPTION
        "Cisco UCS adaptor:EthPortBySizeLargeStatsHist:lessThan2048DeltaAv
        g managed object property"
    ::= { cucsAdaptorEthPortBySizeLargeStatsHistEntry 12 }

cucsAdaptorEthPortBySizeLargeStatsHistLessThan2048DeltaMax OBJECT-TYPE
    SYNTAX       Unsigned64
    MAX-ACCESS   read-only
    STATUS       current
    DESCRIPTION
        "Cisco UCS adaptor:EthPortBySizeLargeStatsHist:lessThan2048DeltaMa
        x managed object property"
    ::= { cucsAdaptorEthPortBySizeLargeStatsHistEntry 13 }

cucsAdaptorEthPortBySizeLargeStatsHistLessThan2048DeltaMin OBJECT-TYPE
    SYNTAX       Unsigned64
    MAX-ACCESS   read-only
    STATUS       current
    DESCRIPTION
        "Cisco UCS adaptor:EthPortBySizeLargeStatsHist:lessThan2048DeltaMi
        n managed object property"
    ::= { cucsAdaptorEthPortBySizeLargeStatsHistEntry 14 }

cucsAdaptorEthPortBySizeLargeStatsHistLessThan4096 OBJECT-TYPE
    SYNTAX       Unsigned64
    MAX-ACCESS   read-only
    STATUS       current
    DESCRIPTION
        "Cisco UCS adaptor:EthPortBySizeLargeStatsHist:lessThan4096
        managed object property"
    ::= { cucsAdaptorEthPortBySizeLargeStatsHistEntry 15 }

cucsAdaptorEthPortBySizeLargeStatsHistLessThan4096Delta OBJECT-TYPE
    SYNTAX       Unsigned64
    MAX-ACCESS   read-only
    STATUS       current
    DESCRIPTION
        "Cisco UCS adaptor:EthPortBySizeLargeStatsHist:lessThan4096Delta
        managed object property"
    ::= { cucsAdaptorEthPortBySizeLargeStatsHistEntry 16 }

cucsAdaptorEthPortBySizeLargeStatsHistLessThan4096DeltaAvg OBJECT-TYPE
    SYNTAX       Unsigned64
    MAX-ACCESS   read-only
    STATUS       current
    DESCRIPTION
        "Cisco UCS adaptor:EthPortBySizeLargeStatsHist:lessThan4096DeltaAv
        g managed object property"
    ::= { cucsAdaptorEthPortBySizeLargeStatsHistEntry 17 }

cucsAdaptorEthPortBySizeLargeStatsHistLessThan4096DeltaMax OBJECT-TYPE
    SYNTAX       Unsigned64
    MAX-ACCESS   read-only
    STATUS       current
    DESCRIPTION
        "Cisco UCS adaptor:EthPortBySizeLargeStatsHist:lessThan4096DeltaMa
        x managed object property"
    ::= { cucsAdaptorEthPortBySizeLargeStatsHistEntry 18 }

cucsAdaptorEthPortBySizeLargeStatsHistLessThan4096DeltaMin OBJECT-TYPE
    SYNTAX       Unsigned64
    MAX-ACCESS   read-only
    STATUS       current
    DESCRIPTION
        "Cisco UCS adaptor:EthPortBySizeLargeStatsHist:lessThan4096DeltaMi
        n managed object property"
    ::= { cucsAdaptorEthPortBySizeLargeStatsHistEntry 19 }

cucsAdaptorEthPortBySizeLargeStatsHistLessThan8192 OBJECT-TYPE
    SYNTAX       Unsigned64
    MAX-ACCESS   read-only
    STATUS       current
    DESCRIPTION
        "Cisco UCS adaptor:EthPortBySizeLargeStatsHist:lessThan8192
        managed object property"
    ::= { cucsAdaptorEthPortBySizeLargeStatsHistEntry 20 }

cucsAdaptorEthPortBySizeLargeStatsHistLessThan8192Delta OBJECT-TYPE
    SYNTAX       Unsigned64
    MAX-ACCESS   read-only
    STATUS       current
    DESCRIPTION
        "Cisco UCS adaptor:EthPortBySizeLargeStatsHist:lessThan8192Delta
        managed object property"
    ::= { cucsAdaptorEthPortBySizeLargeStatsHistEntry 21 }

cucsAdaptorEthPortBySizeLargeStatsHistLessThan8192DeltaAvg OBJECT-TYPE
    SYNTAX       Unsigned64
    MAX-ACCESS   read-only
    STATUS       current
    DESCRIPTION
        "Cisco UCS adaptor:EthPortBySizeLargeStatsHist:lessThan8192DeltaAv
        g managed object property"
    ::= { cucsAdaptorEthPortBySizeLargeStatsHistEntry 22 }

cucsAdaptorEthPortBySizeLargeStatsHistLessThan8192DeltaMax OBJECT-TYPE
    SYNTAX       Unsigned64
    MAX-ACCESS   read-only
    STATUS       current
    DESCRIPTION
        "Cisco UCS adaptor:EthPortBySizeLargeStatsHist:lessThan8192DeltaMa
        x managed object property"
    ::= { cucsAdaptorEthPortBySizeLargeStatsHistEntry 23 }

cucsAdaptorEthPortBySizeLargeStatsHistLessThan8192DeltaMin OBJECT-TYPE
    SYNTAX       Unsigned64
    MAX-ACCESS   read-only
    STATUS       current
    DESCRIPTION
        "Cisco UCS adaptor:EthPortBySizeLargeStatsHist:lessThan8192DeltaMi
        n managed object property"
    ::= { cucsAdaptorEthPortBySizeLargeStatsHistEntry 24 }

cucsAdaptorEthPortBySizeLargeStatsHistLessThan9216 OBJECT-TYPE
    SYNTAX       Unsigned64
    MAX-ACCESS   read-only
    STATUS       current
    DESCRIPTION
        "Cisco UCS adaptor:EthPortBySizeLargeStatsHist:lessThan9216
        managed object property"
    ::= { cucsAdaptorEthPortBySizeLargeStatsHistEntry 25 }

cucsAdaptorEthPortBySizeLargeStatsHistLessThan9216Delta OBJECT-TYPE
    SYNTAX       Unsigned64
    MAX-ACCESS   read-only
    STATUS       current
    DESCRIPTION
        "Cisco UCS adaptor:EthPortBySizeLargeStatsHist:lessThan9216Delta
        managed object property"
    ::= { cucsAdaptorEthPortBySizeLargeStatsHistEntry 26 }

cucsAdaptorEthPortBySizeLargeStatsHistLessThan9216DeltaAvg OBJECT-TYPE
    SYNTAX       Unsigned64
    MAX-ACCESS   read-only
    STATUS       current
    DESCRIPTION
        "Cisco UCS adaptor:EthPortBySizeLargeStatsHist:lessThan9216DeltaAv
        g managed object property"
    ::= { cucsAdaptorEthPortBySizeLargeStatsHistEntry 27 }

cucsAdaptorEthPortBySizeLargeStatsHistLessThan9216DeltaMax OBJECT-TYPE
    SYNTAX       Unsigned64
    MAX-ACCESS   read-only
    STATUS       current
    DESCRIPTION
        "Cisco UCS adaptor:EthPortBySizeLargeStatsHist:lessThan9216DeltaMa
        x managed object property"
    ::= { cucsAdaptorEthPortBySizeLargeStatsHistEntry 28 }

cucsAdaptorEthPortBySizeLargeStatsHistLessThan9216DeltaMin OBJECT-TYPE
    SYNTAX       Unsigned64
    MAX-ACCESS   read-only
    STATUS       current
    DESCRIPTION
        "Cisco UCS adaptor:EthPortBySizeLargeStatsHist:lessThan9216DeltaMi
        n managed object property"
    ::= { cucsAdaptorEthPortBySizeLargeStatsHistEntry 29 }

cucsAdaptorEthPortBySizeLargeStatsHistLessThanOrEqualTo1518 OBJECT-TYPE
    SYNTAX       Unsigned64
    MAX-ACCESS   read-only
    STATUS       current
    DESCRIPTION
        "Cisco UCS adaptor:EthPortBySizeLargeStatsHist:lessThanOrEqualTo15
        18 managed object property"
    ::= { cucsAdaptorEthPortBySizeLargeStatsHistEntry 30 }

cucsAdaptorEthPortBySizeLargeStatsHistLessThanOrEqualTo1518Delta OBJECT-TYPE
    SYNTAX       Unsigned64
    MAX-ACCESS   read-only
    STATUS       current
    DESCRIPTION
        "Cisco UCS adaptor:EthPortBySizeLargeStatsHist:lessThanOrEqualTo15
        18Delta managed object property"
    ::= { cucsAdaptorEthPortBySizeLargeStatsHistEntry 31 }

cucsAdaptorEthPortBySizeLargeStatsHistLessThanOrEqTo1518DeltaAvg OBJECT-TYPE
    SYNTAX       Unsigned64
    MAX-ACCESS   read-only
    STATUS       current
    DESCRIPTION
        "Cisco UCS adaptor:EthPortBySizeLargeStatsHist:lessThanOrEqualTo15
        18DeltaAvg managed object property"
    ::= { cucsAdaptorEthPortBySizeLargeStatsHistEntry 32 }

cucsAdaptorEthPortBySizeLargeStatsHistLessThanOrEqTo1518DeltaMax OBJECT-TYPE
    SYNTAX       Unsigned64
    MAX-ACCESS   read-only
    STATUS       current
    DESCRIPTION
        "Cisco UCS adaptor:EthPortBySizeLargeStatsHist:lessThanOrEqualTo15
        18DeltaMax managed object property"
    ::= { cucsAdaptorEthPortBySizeLargeStatsHistEntry 33 }

cucsAdaptorEthPortBySizeLargeStatsHistLessThanOrEqTo1518DeltaMin OBJECT-TYPE
    SYNTAX       Unsigned64
    MAX-ACCESS   read-only
    STATUS       current
    DESCRIPTION
        "Cisco UCS adaptor:EthPortBySizeLargeStatsHist:lessThanOrEqualTo15
        18DeltaMin managed object property"
    ::= { cucsAdaptorEthPortBySizeLargeStatsHistEntry 34 }

cucsAdaptorEthPortBySizeLargeStatsHistMostRecent OBJECT-TYPE
    SYNTAX       TruthValue
    MAX-ACCESS   read-only
    STATUS       current
    DESCRIPTION
        "Cisco UCS adaptor:EthPortBySizeLargeStatsHist:mostRecent
        managed object property"
    ::= { cucsAdaptorEthPortBySizeLargeStatsHistEntry 35 }

cucsAdaptorEthPortBySizeLargeStatsHistNoBreakdownGreaterThan1518 OBJECT-TYPE
    SYNTAX       Unsigned64
    MAX-ACCESS   read-only
    STATUS       current
    DESCRIPTION
        "Cisco UCS adaptor:EthPortBySizeLargeStatsHist:noBreakdownGreaterT
        han1518 managed object property"
    ::= { cucsAdaptorEthPortBySizeLargeStatsHistEntry 36 }

cucsAdaptorEthPortBySizeLargeStatsHistNoBreakdownGrTh1518Delta OBJECT-TYPE
    SYNTAX       Unsigned64
    MAX-ACCESS   read-only
    STATUS       current
    DESCRIPTION
        "Cisco UCS adaptor:EthPortBySizeLargeStatsHist:noBreakdownGreaterT
        han1518Delta managed object property"
    ::= { cucsAdaptorEthPortBySizeLargeStatsHistEntry 37 }

cucsAdaptorEthPortBySizeLargeStatsHistNoBreakdnGrTh1518DeltaAvg OBJECT-TYPE
    SYNTAX       Unsigned64
    MAX-ACCESS   read-only
    STATUS       current
    DESCRIPTION
        "Cisco UCS adaptor:EthPortBySizeLargeStatsHist:noBreakdownGreaterT
        han1518DeltaAvg managed object property"
    ::= { cucsAdaptorEthPortBySizeLargeStatsHistEntry 38 }

cucsAdaptorEthPortBySizeLargeStatsHistNoBreakdnGrTh1518DeltaMax OBJECT-TYPE
    SYNTAX       Unsigned64
    MAX-ACCESS   read-only
    STATUS       current
    DESCRIPTION
        "Cisco UCS adaptor:EthPortBySizeLargeStatsHist:noBreakdownGreaterT
        han1518DeltaMax managed object property"
    ::= { cucsAdaptorEthPortBySizeLargeStatsHistEntry 39 }

cucsAdaptorEthPortBySizeLargeStatsHistNoBreakdnGrTh1518DeltaMin OBJECT-TYPE
    SYNTAX       Unsigned64
    MAX-ACCESS   read-only
    STATUS       current
    DESCRIPTION
        "Cisco UCS adaptor:EthPortBySizeLargeStatsHist:noBreakdownGreaterT
        han1518DeltaMin managed object property"
    ::= { cucsAdaptorEthPortBySizeLargeStatsHistEntry 40 }

cucsAdaptorEthPortBySizeLargeStatsHistSuspect OBJECT-TYPE
    SYNTAX       TruthValue
    MAX-ACCESS   read-only
    STATUS       current
    DESCRIPTION
        "Cisco UCS adaptor:EthPortBySizeLargeStatsHist:suspect
        managed object property"
    ::= { cucsAdaptorEthPortBySizeLargeStatsHistEntry 41 }

cucsAdaptorEthPortBySizeLargeStatsHistThresholded OBJECT-TYPE
    SYNTAX       CucsAdaptorEthPortBySizeLargeStatsHistThresholded
    MAX-ACCESS   read-only
    STATUS       current
    DESCRIPTION
        "Cisco UCS adaptor:EthPortBySizeLargeStatsHist:thresholded
        managed object property"
    ::= { cucsAdaptorEthPortBySizeLargeStatsHistEntry 42 }

cucsAdaptorEthPortBySizeLargeStatsHistTimeCollected OBJECT-TYPE
    SYNTAX       DateAndTime
    MAX-ACCESS   read-only
    STATUS       current
    DESCRIPTION
        "Cisco UCS adaptor:EthPortBySizeLargeStatsHist:timeCollected
        managed object property"
    ::= { cucsAdaptorEthPortBySizeLargeStatsHistEntry 43 }

cucsAdaptorEthPortBySizeSmallStatsTable OBJECT-TYPE
    SYNTAX           SEQUENCE OF CucsAdaptorEthPortBySizeSmallStatsEntry
    MAX-ACCESS       not-accessible
    STATUS           current
    DESCRIPTION
        "Cisco UCS adaptor:EthPortBySizeSmallStats managed object table"
    ::= { cucsAdaptorObjects 9 }

cucsAdaptorEthPortBySizeSmallStatsEntry OBJECT-TYPE
    SYNTAX           CucsAdaptorEthPortBySizeSmallStatsEntry
    MAX-ACCESS       not-accessible
    STATUS           current
    DESCRIPTION
        "Entry for the cucsAdaptorEthPortBySizeSmallStatsTable table."
    INDEX { cucsAdaptorEthPortBySizeSmallStatsInstanceId }
    ::= { cucsAdaptorEthPortBySizeSmallStatsTable 1 }

CucsAdaptorEthPortBySizeSmallStatsEntry ::= SEQUENCE {
    cucsAdaptorEthPortBySizeSmallStatsInstanceId                     CucsManagedObjectId,
    cucsAdaptorEthPortBySizeSmallStatsDn                             CucsManagedObjectDn,
    cucsAdaptorEthPortBySizeSmallStatsRn                             SnmpAdminString,
    cucsAdaptorEthPortBySizeSmallStatsEquals64                       Unsigned64,
    cucsAdaptorEthPortBySizeSmallStatsEquals64Delta                  Counter64,
    cucsAdaptorEthPortBySizeSmallStatsEquals64DeltaAvg               Unsigned64,
    cucsAdaptorEthPortBySizeSmallStatsEquals64DeltaMax               Unsigned64,
    cucsAdaptorEthPortBySizeSmallStatsEquals64DeltaMin               Unsigned64,
    cucsAdaptorEthPortBySizeSmallStatsIntervals                      Gauge32,
    cucsAdaptorEthPortBySizeSmallStatsLessThan1024                   Unsigned64,
    cucsAdaptorEthPortBySizeSmallStatsLessThan1024Delta              Counter64,
    cucsAdaptorEthPortBySizeSmallStatsLessThan1024DeltaAvg           Unsigned64,
    cucsAdaptorEthPortBySizeSmallStatsLessThan1024DeltaMax           Unsigned64,
    cucsAdaptorEthPortBySizeSmallStatsLessThan1024DeltaMin           Unsigned64,
    cucsAdaptorEthPortBySizeSmallStatsLessThan128                    Unsigned64,
    cucsAdaptorEthPortBySizeSmallStatsLessThan128Delta               Counter64,
    cucsAdaptorEthPortBySizeSmallStatsLessThan128DeltaAvg            Unsigned64,
    cucsAdaptorEthPortBySizeSmallStatsLessThan128DeltaMax            Unsigned64,
    cucsAdaptorEthPortBySizeSmallStatsLessThan128DeltaMin            Unsigned64,
    cucsAdaptorEthPortBySizeSmallStatsLessThan256                    Unsigned64,
    cucsAdaptorEthPortBySizeSmallStatsLessThan256Delta               Counter64,
    cucsAdaptorEthPortBySizeSmallStatsLessThan256DeltaAvg            Unsigned64,
    cucsAdaptorEthPortBySizeSmallStatsLessThan256DeltaMax            Unsigned64,
    cucsAdaptorEthPortBySizeSmallStatsLessThan256DeltaMin            Unsigned64,
    cucsAdaptorEthPortBySizeSmallStatsLessThan512                    Unsigned64,
    cucsAdaptorEthPortBySizeSmallStatsLessThan512Delta               Counter64,
    cucsAdaptorEthPortBySizeSmallStatsLessThan512DeltaAvg            Unsigned64,
    cucsAdaptorEthPortBySizeSmallStatsLessThan512DeltaMax            Unsigned64,
    cucsAdaptorEthPortBySizeSmallStatsLessThan512DeltaMin            Unsigned64,
    cucsAdaptorEthPortBySizeSmallStatsLessThan64                     Unsigned64,
    cucsAdaptorEthPortBySizeSmallStatsLessThan64Delta                Counter64,
    cucsAdaptorEthPortBySizeSmallStatsLessThan64DeltaAvg             Unsigned64,
    cucsAdaptorEthPortBySizeSmallStatsLessThan64DeltaMax             Unsigned64,
    cucsAdaptorEthPortBySizeSmallStatsLessThan64DeltaMin             Unsigned64,
    cucsAdaptorEthPortBySizeSmallStatsSuspect                        TruthValue,
    cucsAdaptorEthPortBySizeSmallStatsThresholded                    CucsAdaptorEthPortBySizeSmallStatsThresholded,
    cucsAdaptorEthPortBySizeSmallStatsTimeCollected                  DateAndTime,
    cucsAdaptorEthPortBySizeSmallStatsTrafficDirection               CucsAdaptorAdapterStatsTrafficDir,
    cucsAdaptorEthPortBySizeSmallStatsUpdate                         Gauge32
}

cucsAdaptorEthPortBySizeSmallStatsInstanceId OBJECT-TYPE
    SYNTAX       CucsManagedObjectId
    MAX-ACCESS   not-accessible
    STATUS       current
    DESCRIPTION
        "Instance identifier of the managed object."
    ::= { cucsAdaptorEthPortBySizeSmallStatsEntry 1 }

cucsAdaptorEthPortBySizeSmallStatsDn OBJECT-TYPE
    SYNTAX       CucsManagedObjectDn
    MAX-ACCESS   read-only
    STATUS       current
    DESCRIPTION
        "Cisco UCS adaptor:EthPortBySizeSmallStats:dn managed
        object property"
    ::= { cucsAdaptorEthPortBySizeSmallStatsEntry 2 }

cucsAdaptorEthPortBySizeSmallStatsRn OBJECT-TYPE
    SYNTAX       SnmpAdminString
    MAX-ACCESS   read-only
    STATUS       current
    DESCRIPTION
        "Cisco UCS adaptor:EthPortBySizeSmallStats:rn managed
        object property"
    ::= { cucsAdaptorEthPortBySizeSmallStatsEntry 3 }

cucsAdaptorEthPortBySizeSmallStatsEquals64 OBJECT-TYPE
    SYNTAX       Unsigned64
    MAX-ACCESS   read-only
    STATUS       current
    DESCRIPTION
        "Cisco UCS adaptor:EthPortBySizeSmallStats:equals64
        managed object property"
    ::= { cucsAdaptorEthPortBySizeSmallStatsEntry 4 }

cucsAdaptorEthPortBySizeSmallStatsEquals64Delta OBJECT-TYPE
    SYNTAX       Counter64
    MAX-ACCESS   read-only
    STATUS       current
    DESCRIPTION
        "Cisco UCS adaptor:EthPortBySizeSmallStats:equals64Delta
        managed object property"
    ::= { cucsAdaptorEthPortBySizeSmallStatsEntry 5 }

cucsAdaptorEthPortBySizeSmallStatsEquals64DeltaAvg OBJECT-TYPE
    SYNTAX       Unsigned64
    MAX-ACCESS   read-only
    STATUS       current
    DESCRIPTION
        "Cisco UCS adaptor:EthPortBySizeSmallStats:equals64DeltaAvg
        managed object property"
    ::= { cucsAdaptorEthPortBySizeSmallStatsEntry 6 }

cucsAdaptorEthPortBySizeSmallStatsEquals64DeltaMax OBJECT-TYPE
    SYNTAX       Unsigned64
    MAX-ACCESS   read-only
    STATUS       current
    DESCRIPTION
        "Cisco UCS adaptor:EthPortBySizeSmallStats:equals64DeltaMax
        managed object property"
    ::= { cucsAdaptorEthPortBySizeSmallStatsEntry 7 }

cucsAdaptorEthPortBySizeSmallStatsEquals64DeltaMin OBJECT-TYPE
    SYNTAX       Unsigned64
    MAX-ACCESS   read-only
    STATUS       current
    DESCRIPTION
        "Cisco UCS adaptor:EthPortBySizeSmallStats:equals64DeltaMin
        managed object property"
    ::= { cucsAdaptorEthPortBySizeSmallStatsEntry 8 }

cucsAdaptorEthPortBySizeSmallStatsIntervals OBJECT-TYPE
    SYNTAX       Gauge32
    MAX-ACCESS   read-only
    STATUS       current
    DESCRIPTION
        "Cisco UCS adaptor:EthPortBySizeSmallStats:intervals
        managed object property"
    ::= { cucsAdaptorEthPortBySizeSmallStatsEntry 9 }

cucsAdaptorEthPortBySizeSmallStatsLessThan1024 OBJECT-TYPE
    SYNTAX       Unsigned64
    MAX-ACCESS   read-only
    STATUS       current
    DESCRIPTION
        "Cisco UCS adaptor:EthPortBySizeSmallStats:lessThan1024
        managed object property"
    ::= { cucsAdaptorEthPortBySizeSmallStatsEntry 10 }

cucsAdaptorEthPortBySizeSmallStatsLessThan1024Delta OBJECT-TYPE
    SYNTAX       Counter64
    MAX-ACCESS   read-only
    STATUS       current
    DESCRIPTION
        "Cisco UCS adaptor:EthPortBySizeSmallStats:lessThan1024Delta
        managed object property"
    ::= { cucsAdaptorEthPortBySizeSmallStatsEntry 11 }

cucsAdaptorEthPortBySizeSmallStatsLessThan1024DeltaAvg OBJECT-TYPE
    SYNTAX       Unsigned64
    MAX-ACCESS   read-only
    STATUS       current
    DESCRIPTION
        "Cisco UCS adaptor:EthPortBySizeSmallStats:lessThan1024DeltaAvg
        managed object property"
    ::= { cucsAdaptorEthPortBySizeSmallStatsEntry 12 }

cucsAdaptorEthPortBySizeSmallStatsLessThan1024DeltaMax OBJECT-TYPE
    SYNTAX       Unsigned64
    MAX-ACCESS   read-only
    STATUS       current
    DESCRIPTION
        "Cisco UCS adaptor:EthPortBySizeSmallStats:lessThan1024DeltaMax
        managed object property"
    ::= { cucsAdaptorEthPortBySizeSmallStatsEntry 13 }

cucsAdaptorEthPortBySizeSmallStatsLessThan1024DeltaMin OBJECT-TYPE
    SYNTAX       Unsigned64
    MAX-ACCESS   read-only
    STATUS       current
    DESCRIPTION
        "Cisco UCS adaptor:EthPortBySizeSmallStats:lessThan1024DeltaMin
        managed object property"
    ::= { cucsAdaptorEthPortBySizeSmallStatsEntry 14 }

cucsAdaptorEthPortBySizeSmallStatsLessThan128 OBJECT-TYPE
    SYNTAX       Unsigned64
    MAX-ACCESS   read-only
    STATUS       current
    DESCRIPTION
        "Cisco UCS adaptor:EthPortBySizeSmallStats:lessThan128
        managed object property"
    ::= { cucsAdaptorEthPortBySizeSmallStatsEntry 15 }

cucsAdaptorEthPortBySizeSmallStatsLessThan128Delta OBJECT-TYPE
    SYNTAX       Counter64
    MAX-ACCESS   read-only
    STATUS       current
    DESCRIPTION
        "Cisco UCS adaptor:EthPortBySizeSmallStats:lessThan128Delta
        managed object property"
    ::= { cucsAdaptorEthPortBySizeSmallStatsEntry 16 }

cucsAdaptorEthPortBySizeSmallStatsLessThan128DeltaAvg OBJECT-TYPE
    SYNTAX       Unsigned64
    MAX-ACCESS   read-only
    STATUS       current
    DESCRIPTION
        "Cisco UCS adaptor:EthPortBySizeSmallStats:lessThan128DeltaAvg
        managed object property"
    ::= { cucsAdaptorEthPortBySizeSmallStatsEntry 17 }

cucsAdaptorEthPortBySizeSmallStatsLessThan128DeltaMax OBJECT-TYPE
    SYNTAX       Unsigned64
    MAX-ACCESS   read-only
    STATUS       current
    DESCRIPTION
        "Cisco UCS adaptor:EthPortBySizeSmallStats:lessThan128DeltaMax
        managed object property"
    ::= { cucsAdaptorEthPortBySizeSmallStatsEntry 18 }

cucsAdaptorEthPortBySizeSmallStatsLessThan128DeltaMin OBJECT-TYPE
    SYNTAX       Unsigned64
    MAX-ACCESS   read-only
    STATUS       current
    DESCRIPTION
        "Cisco UCS adaptor:EthPortBySizeSmallStats:lessThan128DeltaMin
        managed object property"
    ::= { cucsAdaptorEthPortBySizeSmallStatsEntry 19 }

cucsAdaptorEthPortBySizeSmallStatsLessThan256 OBJECT-TYPE
    SYNTAX       Unsigned64
    MAX-ACCESS   read-only
    STATUS       current
    DESCRIPTION
        "Cisco UCS adaptor:EthPortBySizeSmallStats:lessThan256
        managed object property"
    ::= { cucsAdaptorEthPortBySizeSmallStatsEntry 20 }

cucsAdaptorEthPortBySizeSmallStatsLessThan256Delta OBJECT-TYPE
    SYNTAX       Counter64
    MAX-ACCESS   read-only
    STATUS       current
    DESCRIPTION
        "Cisco UCS adaptor:EthPortBySizeSmallStats:lessThan256Delta
        managed object property"
    ::= { cucsAdaptorEthPortBySizeSmallStatsEntry 21 }

cucsAdaptorEthPortBySizeSmallStatsLessThan256DeltaAvg OBJECT-TYPE
    SYNTAX       Unsigned64
    MAX-ACCESS   read-only
    STATUS       current
    DESCRIPTION
        "Cisco UCS adaptor:EthPortBySizeSmallStats:lessThan256DeltaAvg
        managed object property"
    ::= { cucsAdaptorEthPortBySizeSmallStatsEntry 22 }

cucsAdaptorEthPortBySizeSmallStatsLessThan256DeltaMax OBJECT-TYPE
    SYNTAX       Unsigned64
    MAX-ACCESS   read-only
    STATUS       current
    DESCRIPTION
        "Cisco UCS adaptor:EthPortBySizeSmallStats:lessThan256DeltaMax
        managed object property"
    ::= { cucsAdaptorEthPortBySizeSmallStatsEntry 23 }

cucsAdaptorEthPortBySizeSmallStatsLessThan256DeltaMin OBJECT-TYPE
    SYNTAX       Unsigned64
    MAX-ACCESS   read-only
    STATUS       current
    DESCRIPTION
        "Cisco UCS adaptor:EthPortBySizeSmallStats:lessThan256DeltaMin
        managed object property"
    ::= { cucsAdaptorEthPortBySizeSmallStatsEntry 24 }

cucsAdaptorEthPortBySizeSmallStatsLessThan512 OBJECT-TYPE
    SYNTAX       Unsigned64
    MAX-ACCESS   read-only
    STATUS       current
    DESCRIPTION
        "Cisco UCS adaptor:EthPortBySizeSmallStats:lessThan512
        managed object property"
    ::= { cucsAdaptorEthPortBySizeSmallStatsEntry 25 }

cucsAdaptorEthPortBySizeSmallStatsLessThan512Delta OBJECT-TYPE
    SYNTAX       Counter64
    MAX-ACCESS   read-only
    STATUS       current
    DESCRIPTION
        "Cisco UCS adaptor:EthPortBySizeSmallStats:lessThan512Delta
        managed object property"
    ::= { cucsAdaptorEthPortBySizeSmallStatsEntry 26 }

cucsAdaptorEthPortBySizeSmallStatsLessThan512DeltaAvg OBJECT-TYPE
    SYNTAX       Unsigned64
    MAX-ACCESS   read-only
    STATUS       current
    DESCRIPTION
        "Cisco UCS adaptor:EthPortBySizeSmallStats:lessThan512DeltaAvg
        managed object property"
    ::= { cucsAdaptorEthPortBySizeSmallStatsEntry 27 }

cucsAdaptorEthPortBySizeSmallStatsLessThan512DeltaMax OBJECT-TYPE
    SYNTAX       Unsigned64
    MAX-ACCESS   read-only
    STATUS       current
    DESCRIPTION
        "Cisco UCS adaptor:EthPortBySizeSmallStats:lessThan512DeltaMax
        managed object property"
    ::= { cucsAdaptorEthPortBySizeSmallStatsEntry 28 }

cucsAdaptorEthPortBySizeSmallStatsLessThan512DeltaMin OBJECT-TYPE
    SYNTAX       Unsigned64
    MAX-ACCESS   read-only
    STATUS       current
    DESCRIPTION
        "Cisco UCS adaptor:EthPortBySizeSmallStats:lessThan512DeltaMin
        managed object property"
    ::= { cucsAdaptorEthPortBySizeSmallStatsEntry 29 }

cucsAdaptorEthPortBySizeSmallStatsLessThan64 OBJECT-TYPE
    SYNTAX       Unsigned64
    MAX-ACCESS   read-only
    STATUS       current
    DESCRIPTION
        "Cisco UCS adaptor:EthPortBySizeSmallStats:lessThan64
        managed object property"
    ::= { cucsAdaptorEthPortBySizeSmallStatsEntry 30 }

cucsAdaptorEthPortBySizeSmallStatsLessThan64Delta OBJECT-TYPE
    SYNTAX       Counter64
    MAX-ACCESS   read-only
    STATUS       current
    DESCRIPTION
        "Cisco UCS adaptor:EthPortBySizeSmallStats:lessThan64Delta
        managed object property"
    ::= { cucsAdaptorEthPortBySizeSmallStatsEntry 31 }

cucsAdaptorEthPortBySizeSmallStatsLessThan64DeltaAvg OBJECT-TYPE
    SYNTAX       Unsigned64
    MAX-ACCESS   read-only
    STATUS       current
    DESCRIPTION
        "Cisco UCS adaptor:EthPortBySizeSmallStats:lessThan64DeltaAvg
        managed object property"
    ::= { cucsAdaptorEthPortBySizeSmallStatsEntry 32 }

cucsAdaptorEthPortBySizeSmallStatsLessThan64DeltaMax OBJECT-TYPE
    SYNTAX       Unsigned64
    MAX-ACCESS   read-only
    STATUS       current
    DESCRIPTION
        "Cisco UCS adaptor:EthPortBySizeSmallStats:lessThan64DeltaMax
        managed object property"
    ::= { cucsAdaptorEthPortBySizeSmallStatsEntry 33 }

cucsAdaptorEthPortBySizeSmallStatsLessThan64DeltaMin OBJECT-TYPE
    SYNTAX       Unsigned64
    MAX-ACCESS   read-only
    STATUS       current
    DESCRIPTION
        "Cisco UCS adaptor:EthPortBySizeSmallStats:lessThan64DeltaMin
        managed object property"
    ::= { cucsAdaptorEthPortBySizeSmallStatsEntry 34 }

cucsAdaptorEthPortBySizeSmallStatsSuspect OBJECT-TYPE
    SYNTAX       TruthValue
    MAX-ACCESS   read-only
    STATUS       current
    DESCRIPTION
        "Cisco UCS adaptor:EthPortBySizeSmallStats:suspect
        managed object property"
    ::= { cucsAdaptorEthPortBySizeSmallStatsEntry 35 }

cucsAdaptorEthPortBySizeSmallStatsThresholded OBJECT-TYPE
    SYNTAX       CucsAdaptorEthPortBySizeSmallStatsThresholded
    MAX-ACCESS   read-only
    STATUS       current
    DESCRIPTION
        "Cisco UCS adaptor:EthPortBySizeSmallStats:thresholded
        managed object property"
    ::= { cucsAdaptorEthPortBySizeSmallStatsEntry 36 }

cucsAdaptorEthPortBySizeSmallStatsTimeCollected OBJECT-TYPE
    SYNTAX       DateAndTime
    MAX-ACCESS   read-only
    STATUS       current
    DESCRIPTION
        "Cisco UCS adaptor:EthPortBySizeSmallStats:timeCollected
        managed object property"
    ::= { cucsAdaptorEthPortBySizeSmallStatsEntry 37 }

cucsAdaptorEthPortBySizeSmallStatsTrafficDirection OBJECT-TYPE
    SYNTAX       CucsAdaptorAdapterStatsTrafficDir
    MAX-ACCESS   read-only
    STATUS       current
    DESCRIPTION
        "Cisco UCS adaptor:EthPortBySizeSmallStats:trafficDirection
        managed object property"
    ::= { cucsAdaptorEthPortBySizeSmallStatsEntry 38 }

cucsAdaptorEthPortBySizeSmallStatsUpdate OBJECT-TYPE
    SYNTAX       Gauge32
    MAX-ACCESS   read-only
    STATUS       current
    DESCRIPTION
        "Cisco UCS adaptor:EthPortBySizeSmallStats:update
        managed object property"
    ::= { cucsAdaptorEthPortBySizeSmallStatsEntry 39 }

cucsAdaptorEthPortBySizeSmallStatsHistTable OBJECT-TYPE
    SYNTAX           SEQUENCE OF CucsAdaptorEthPortBySizeSmallStatsHistEntry
    MAX-ACCESS       not-accessible
    STATUS           current
    DESCRIPTION
        "Cisco UCS adaptor:EthPortBySizeSmallStatsHist
        managed object table"
    ::= { cucsAdaptorObjects 10 }

cucsAdaptorEthPortBySizeSmallStatsHistEntry OBJECT-TYPE
    SYNTAX           CucsAdaptorEthPortBySizeSmallStatsHistEntry
    MAX-ACCESS       not-accessible
    STATUS           current
    DESCRIPTION
        "Entry for the cucsAdaptorEthPortBySizeSmallStatsHistTable table."
    INDEX { cucsAdaptorEthPortBySizeSmallStatsHistInstanceId }
    ::= { cucsAdaptorEthPortBySizeSmallStatsHistTable 1 }

CucsAdaptorEthPortBySizeSmallStatsHistEntry ::= SEQUENCE {
    cucsAdaptorEthPortBySizeSmallStatsHistInstanceId                 CucsManagedObjectId,
    cucsAdaptorEthPortBySizeSmallStatsHistDn                         CucsManagedObjectDn,
    cucsAdaptorEthPortBySizeSmallStatsHistRn                         SnmpAdminString,
    cucsAdaptorEthPortBySizeSmallStatsHistEquals64                   Unsigned64,
    cucsAdaptorEthPortBySizeSmallStatsHistEquals64Delta              Unsigned64,
    cucsAdaptorEthPortBySizeSmallStatsHistEquals64DeltaAvg           Unsigned64,
    cucsAdaptorEthPortBySizeSmallStatsHistEquals64DeltaMax           Unsigned64,
    cucsAdaptorEthPortBySizeSmallStatsHistEquals64DeltaMin           Unsigned64,
    cucsAdaptorEthPortBySizeSmallStatsHistId                         Unsigned64,
    cucsAdaptorEthPortBySizeSmallStatsHistLessThan1024               Unsigned64,
    cucsAdaptorEthPortBySizeSmallStatsHistLessThan1024Delta          Unsigned64,
    cucsAdaptorEthPortBySizeSmallStatsHistLessThan1024DeltaAvg       Unsigned64,
    cucsAdaptorEthPortBySizeSmallStatsHistLessThan1024DeltaMax       Unsigned64,
    cucsAdaptorEthPortBySizeSmallStatsHistLessThan1024DeltaMin       Unsigned64,
    cucsAdaptorEthPortBySizeSmallStatsHistLessThan128                Unsigned64,
    cucsAdaptorEthPortBySizeSmallStatsHistLessThan128Delta           Unsigned64,
    cucsAdaptorEthPortBySizeSmallStatsHistLessThan128DeltaAvg        Unsigned64,
    cucsAdaptorEthPortBySizeSmallStatsHistLessThan128DeltaMax        Unsigned64,
    cucsAdaptorEthPortBySizeSmallStatsHistLessThan128DeltaMin        Unsigned64,
    cucsAdaptorEthPortBySizeSmallStatsHistLessThan256                Unsigned64,
    cucsAdaptorEthPortBySizeSmallStatsHistLessThan256Delta           Unsigned64,
    cucsAdaptorEthPortBySizeSmallStatsHistLessThan256DeltaAvg        Unsigned64,
    cucsAdaptorEthPortBySizeSmallStatsHistLessThan256DeltaMax        Unsigned64,
    cucsAdaptorEthPortBySizeSmallStatsHistLessThan256DeltaMin        Unsigned64,
    cucsAdaptorEthPortBySizeSmallStatsHistLessThan512                Unsigned64,
    cucsAdaptorEthPortBySizeSmallStatsHistLessThan512Delta           Unsigned64,
    cucsAdaptorEthPortBySizeSmallStatsHistLessThan512DeltaAvg        Unsigned64,
    cucsAdaptorEthPortBySizeSmallStatsHistLessThan512DeltaMax        Unsigned64,
    cucsAdaptorEthPortBySizeSmallStatsHistLessThan512DeltaMin        Unsigned64,
    cucsAdaptorEthPortBySizeSmallStatsHistLessThan64                 Unsigned64,
    cucsAdaptorEthPortBySizeSmallStatsHistLessThan64Delta            Unsigned64,
    cucsAdaptorEthPortBySizeSmallStatsHistLessThan64DeltaAvg         Unsigned64,
    cucsAdaptorEthPortBySizeSmallStatsHistLessThan64DeltaMax         Unsigned64,
    cucsAdaptorEthPortBySizeSmallStatsHistLessThan64DeltaMin         Unsigned64,
    cucsAdaptorEthPortBySizeSmallStatsHistMostRecent                 TruthValue,
    cucsAdaptorEthPortBySizeSmallStatsHistSuspect                    TruthValue,
    cucsAdaptorEthPortBySizeSmallStatsHistThresholded                CucsAdaptorEthPortBySizeSmallStatsHistThresholded,
    cucsAdaptorEthPortBySizeSmallStatsHistTimeCollected              DateAndTime
}

cucsAdaptorEthPortBySizeSmallStatsHistInstanceId OBJECT-TYPE
    SYNTAX       CucsManagedObjectId
    MAX-ACCESS   not-accessible
    STATUS       current
    DESCRIPTION
        "Instance identifier of the managed object."
    ::= { cucsAdaptorEthPortBySizeSmallStatsHistEntry 1 }

cucsAdaptorEthPortBySizeSmallStatsHistDn OBJECT-TYPE
    SYNTAX       CucsManagedObjectDn
    MAX-ACCESS   read-only
    STATUS       current
    DESCRIPTION
        "Cisco UCS adaptor:EthPortBySizeSmallStatsHist:dn
        managed object property"
    ::= { cucsAdaptorEthPortBySizeSmallStatsHistEntry 2 }

cucsAdaptorEthPortBySizeSmallStatsHistRn OBJECT-TYPE
    SYNTAX       SnmpAdminString
    MAX-ACCESS   read-only
    STATUS       current
    DESCRIPTION
        "Cisco UCS adaptor:EthPortBySizeSmallStatsHist:rn
        managed object property"
    ::= { cucsAdaptorEthPortBySizeSmallStatsHistEntry 3 }

cucsAdaptorEthPortBySizeSmallStatsHistEquals64 OBJECT-TYPE
    SYNTAX       Unsigned64
    MAX-ACCESS   read-only
    STATUS       current
    DESCRIPTION
        "Cisco UCS adaptor:EthPortBySizeSmallStatsHist:equals64
        managed object property"
    ::= { cucsAdaptorEthPortBySizeSmallStatsHistEntry 4 }

cucsAdaptorEthPortBySizeSmallStatsHistEquals64Delta OBJECT-TYPE
    SYNTAX       Unsigned64
    MAX-ACCESS   read-only
    STATUS       current
    DESCRIPTION
        "Cisco UCS adaptor:EthPortBySizeSmallStatsHist:equals64Delta
        managed object property"
    ::= { cucsAdaptorEthPortBySizeSmallStatsHistEntry 5 }

cucsAdaptorEthPortBySizeSmallStatsHistEquals64DeltaAvg OBJECT-TYPE
    SYNTAX       Unsigned64
    MAX-ACCESS   read-only
    STATUS       current
    DESCRIPTION
        "Cisco UCS adaptor:EthPortBySizeSmallStatsHist:equals64DeltaAvg
        managed object property"
    ::= { cucsAdaptorEthPortBySizeSmallStatsHistEntry 6 }

cucsAdaptorEthPortBySizeSmallStatsHistEquals64DeltaMax OBJECT-TYPE
    SYNTAX       Unsigned64
    MAX-ACCESS   read-only
    STATUS       current
    DESCRIPTION
        "Cisco UCS adaptor:EthPortBySizeSmallStatsHist:equals64DeltaMax
        managed object property"
    ::= { cucsAdaptorEthPortBySizeSmallStatsHistEntry 7 }

cucsAdaptorEthPortBySizeSmallStatsHistEquals64DeltaMin OBJECT-TYPE
    SYNTAX       Unsigned64
    MAX-ACCESS   read-only
    STATUS       current
    DESCRIPTION
        "Cisco UCS adaptor:EthPortBySizeSmallStatsHist:equals64DeltaMin
        managed object property"
    ::= { cucsAdaptorEthPortBySizeSmallStatsHistEntry 8 }

cucsAdaptorEthPortBySizeSmallStatsHistId OBJECT-TYPE
    SYNTAX       Unsigned64
    MAX-ACCESS   read-only
    STATUS       current
    DESCRIPTION
        "Cisco UCS adaptor:EthPortBySizeSmallStatsHist:id
        managed object property"
    ::= { cucsAdaptorEthPortBySizeSmallStatsHistEntry 9 }

cucsAdaptorEthPortBySizeSmallStatsHistLessThan1024 OBJECT-TYPE
    SYNTAX       Unsigned64
    MAX-ACCESS   read-only
    STATUS       current
    DESCRIPTION
        "Cisco UCS adaptor:EthPortBySizeSmallStatsHist:lessThan1024
        managed object property"
    ::= { cucsAdaptorEthPortBySizeSmallStatsHistEntry 10 }

cucsAdaptorEthPortBySizeSmallStatsHistLessThan1024Delta OBJECT-TYPE
    SYNTAX       Unsigned64
    MAX-ACCESS   read-only
    STATUS       current
    DESCRIPTION
        "Cisco UCS adaptor:EthPortBySizeSmallStatsHist:lessThan1024Delta
        managed object property"
    ::= { cucsAdaptorEthPortBySizeSmallStatsHistEntry 11 }

cucsAdaptorEthPortBySizeSmallStatsHistLessThan1024DeltaAvg OBJECT-TYPE
    SYNTAX       Unsigned64
    MAX-ACCESS   read-only
    STATUS       current
    DESCRIPTION
        "Cisco UCS adaptor:EthPortBySizeSmallStatsHist:lessThan1024DeltaAv
        g managed object property"
    ::= { cucsAdaptorEthPortBySizeSmallStatsHistEntry 12 }

cucsAdaptorEthPortBySizeSmallStatsHistLessThan1024DeltaMax OBJECT-TYPE
    SYNTAX       Unsigned64
    MAX-ACCESS   read-only
    STATUS       current
    DESCRIPTION
        "Cisco UCS adaptor:EthPortBySizeSmallStatsHist:lessThan1024DeltaMa
        x managed object property"
    ::= { cucsAdaptorEthPortBySizeSmallStatsHistEntry 13 }

cucsAdaptorEthPortBySizeSmallStatsHistLessThan1024DeltaMin OBJECT-TYPE
    SYNTAX       Unsigned64
    MAX-ACCESS   read-only
    STATUS       current
    DESCRIPTION
        "Cisco UCS adaptor:EthPortBySizeSmallStatsHist:lessThan1024DeltaMi
        n managed object property"
    ::= { cucsAdaptorEthPortBySizeSmallStatsHistEntry 14 }

cucsAdaptorEthPortBySizeSmallStatsHistLessThan128 OBJECT-TYPE
    SYNTAX       Unsigned64
    MAX-ACCESS   read-only
    STATUS       current
    DESCRIPTION
        "Cisco UCS adaptor:EthPortBySizeSmallStatsHist:lessThan128
        managed object property"
    ::= { cucsAdaptorEthPortBySizeSmallStatsHistEntry 15 }

cucsAdaptorEthPortBySizeSmallStatsHistLessThan128Delta OBJECT-TYPE
    SYNTAX       Unsigned64
    MAX-ACCESS   read-only
    STATUS       current
    DESCRIPTION
        "Cisco UCS adaptor:EthPortBySizeSmallStatsHist:lessThan128Delta
        managed object property"
    ::= { cucsAdaptorEthPortBySizeSmallStatsHistEntry 16 }

cucsAdaptorEthPortBySizeSmallStatsHistLessThan128DeltaAvg OBJECT-TYPE
    SYNTAX       Unsigned64
    MAX-ACCESS   read-only
    STATUS       current
    DESCRIPTION
        "Cisco UCS adaptor:EthPortBySizeSmallStatsHist:lessThan128DeltaAvg
         managed object property"
    ::= { cucsAdaptorEthPortBySizeSmallStatsHistEntry 17 }

cucsAdaptorEthPortBySizeSmallStatsHistLessThan128DeltaMax OBJECT-TYPE
    SYNTAX       Unsigned64
    MAX-ACCESS   read-only
    STATUS       current
    DESCRIPTION
        "Cisco UCS adaptor:EthPortBySizeSmallStatsHist:lessThan128DeltaMax
         managed object property"
    ::= { cucsAdaptorEthPortBySizeSmallStatsHistEntry 18 }

cucsAdaptorEthPortBySizeSmallStatsHistLessThan128DeltaMin OBJECT-TYPE
    SYNTAX       Unsigned64
    MAX-ACCESS   read-only
    STATUS       current
    DESCRIPTION
        "Cisco UCS adaptor:EthPortBySizeSmallStatsHist:lessThan128DeltaMin
         managed object property"
    ::= { cucsAdaptorEthPortBySizeSmallStatsHistEntry 19 }

cucsAdaptorEthPortBySizeSmallStatsHistLessThan256 OBJECT-TYPE
    SYNTAX       Unsigned64
    MAX-ACCESS   read-only
    STATUS       current
    DESCRIPTION
        "Cisco UCS adaptor:EthPortBySizeSmallStatsHist:lessThan256
        managed object property"
    ::= { cucsAdaptorEthPortBySizeSmallStatsHistEntry 20 }

cucsAdaptorEthPortBySizeSmallStatsHistLessThan256Delta OBJECT-TYPE
    SYNTAX       Unsigned64
    MAX-ACCESS   read-only
    STATUS       current
    DESCRIPTION
        "Cisco UCS adaptor:EthPortBySizeSmallStatsHist:lessThan256Delta
        managed object property"
    ::= { cucsAdaptorEthPortBySizeSmallStatsHistEntry 21 }

cucsAdaptorEthPortBySizeSmallStatsHistLessThan256DeltaAvg OBJECT-TYPE
    SYNTAX       Unsigned64
    MAX-ACCESS   read-only
    STATUS       current
    DESCRIPTION
        "Cisco UCS adaptor:EthPortBySizeSmallStatsHist:lessThan256DeltaAvg
         managed object property"
    ::= { cucsAdaptorEthPortBySizeSmallStatsHistEntry 22 }

cucsAdaptorEthPortBySizeSmallStatsHistLessThan256DeltaMax OBJECT-TYPE
    SYNTAX       Unsigned64
    MAX-ACCESS   read-only
    STATUS       current
    DESCRIPTION
        "Cisco UCS adaptor:EthPortBySizeSmallStatsHist:lessThan256DeltaMax
         managed object property"
    ::= { cucsAdaptorEthPortBySizeSmallStatsHistEntry 23 }

cucsAdaptorEthPortBySizeSmallStatsHistLessThan256DeltaMin OBJECT-TYPE
    SYNTAX       Unsigned64
    MAX-ACCESS   read-only
    STATUS       current
    DESCRIPTION
        "Cisco UCS adaptor:EthPortBySizeSmallStatsHist:lessThan256DeltaMin
         managed object property"
    ::= { cucsAdaptorEthPortBySizeSmallStatsHistEntry 24 }

cucsAdaptorEthPortBySizeSmallStatsHistLessThan512 OBJECT-TYPE
    SYNTAX       Unsigned64
    MAX-ACCESS   read-only
    STATUS       current
    DESCRIPTION
        "Cisco UCS adaptor:EthPortBySizeSmallStatsHist:lessThan512
        managed object property"
    ::= { cucsAdaptorEthPortBySizeSmallStatsHistEntry 25 }

cucsAdaptorEthPortBySizeSmallStatsHistLessThan512Delta OBJECT-TYPE
    SYNTAX       Unsigned64
    MAX-ACCESS   read-only
    STATUS       current
    DESCRIPTION
        "Cisco UCS adaptor:EthPortBySizeSmallStatsHist:lessThan512Delta
        managed object property"
    ::= { cucsAdaptorEthPortBySizeSmallStatsHistEntry 26 }

cucsAdaptorEthPortBySizeSmallStatsHistLessThan512DeltaAvg OBJECT-TYPE
    SYNTAX       Unsigned64
    MAX-ACCESS   read-only
    STATUS       current
    DESCRIPTION
        "Cisco UCS adaptor:EthPortBySizeSmallStatsHist:lessThan512DeltaAvg
         managed object property"
    ::= { cucsAdaptorEthPortBySizeSmallStatsHistEntry 27 }

cucsAdaptorEthPortBySizeSmallStatsHistLessThan512DeltaMax OBJECT-TYPE
    SYNTAX       Unsigned64
    MAX-ACCESS   read-only
    STATUS       current
    DESCRIPTION
        "Cisco UCS adaptor:EthPortBySizeSmallStatsHist:lessThan512DeltaMax
         managed object property"
    ::= { cucsAdaptorEthPortBySizeSmallStatsHistEntry 28 }

cucsAdaptorEthPortBySizeSmallStatsHistLessThan512DeltaMin OBJECT-TYPE
    SYNTAX       Unsigned64
    MAX-ACCESS   read-only
    STATUS       current
    DESCRIPTION
        "Cisco UCS adaptor:EthPortBySizeSmallStatsHist:lessThan512DeltaMin
         managed object property"
    ::= { cucsAdaptorEthPortBySizeSmallStatsHistEntry 29 }

cucsAdaptorEthPortBySizeSmallStatsHistLessThan64 OBJECT-TYPE
    SYNTAX       Unsigned64
    MAX-ACCESS   read-only
    STATUS       current
    DESCRIPTION
        "Cisco UCS adaptor:EthPortBySizeSmallStatsHist:lessThan64
        managed object property"
    ::= { cucsAdaptorEthPortBySizeSmallStatsHistEntry 30 }

cucsAdaptorEthPortBySizeSmallStatsHistLessThan64Delta OBJECT-TYPE
    SYNTAX       Unsigned64
    MAX-ACCESS   read-only
    STATUS       current
    DESCRIPTION
        "Cisco UCS adaptor:EthPortBySizeSmallStatsHist:lessThan64Delta
        managed object property"
    ::= { cucsAdaptorEthPortBySizeSmallStatsHistEntry 31 }

cucsAdaptorEthPortBySizeSmallStatsHistLessThan64DeltaAvg OBJECT-TYPE
    SYNTAX       Unsigned64
    MAX-ACCESS   read-only
    STATUS       current
    DESCRIPTION
        "Cisco UCS adaptor:EthPortBySizeSmallStatsHist:lessThan64DeltaAvg
        managed object property"
    ::= { cucsAdaptorEthPortBySizeSmallStatsHistEntry 32 }

cucsAdaptorEthPortBySizeSmallStatsHistLessThan64DeltaMax OBJECT-TYPE
    SYNTAX       Unsigned64
    MAX-ACCESS   read-only
    STATUS       current
    DESCRIPTION
        "Cisco UCS adaptor:EthPortBySizeSmallStatsHist:lessThan64DeltaMax
        managed object property"
    ::= { cucsAdaptorEthPortBySizeSmallStatsHistEntry 33 }

cucsAdaptorEthPortBySizeSmallStatsHistLessThan64DeltaMin OBJECT-TYPE
    SYNTAX       Unsigned64
    MAX-ACCESS   read-only
    STATUS       current
    DESCRIPTION
        "Cisco UCS adaptor:EthPortBySizeSmallStatsHist:lessThan64DeltaMin
        managed object property"
    ::= { cucsAdaptorEthPortBySizeSmallStatsHistEntry 34 }

cucsAdaptorEthPortBySizeSmallStatsHistMostRecent OBJECT-TYPE
    SYNTAX       TruthValue
    MAX-ACCESS   read-only
    STATUS       current
    DESCRIPTION
        "Cisco UCS adaptor:EthPortBySizeSmallStatsHist:mostRecent
        managed object property"
    ::= { cucsAdaptorEthPortBySizeSmallStatsHistEntry 35 }

cucsAdaptorEthPortBySizeSmallStatsHistSuspect OBJECT-TYPE
    SYNTAX       TruthValue
    MAX-ACCESS   read-only
    STATUS       current
    DESCRIPTION
        "Cisco UCS adaptor:EthPortBySizeSmallStatsHist:suspect
        managed object property"
    ::= { cucsAdaptorEthPortBySizeSmallStatsHistEntry 36 }

cucsAdaptorEthPortBySizeSmallStatsHistThresholded OBJECT-TYPE
    SYNTAX       CucsAdaptorEthPortBySizeSmallStatsHistThresholded
    MAX-ACCESS   read-only
    STATUS       current
    DESCRIPTION
        "Cisco UCS adaptor:EthPortBySizeSmallStatsHist:thresholded
        managed object property"
    ::= { cucsAdaptorEthPortBySizeSmallStatsHistEntry 37 }

cucsAdaptorEthPortBySizeSmallStatsHistTimeCollected OBJECT-TYPE
    SYNTAX       DateAndTime
    MAX-ACCESS   read-only
    STATUS       current
    DESCRIPTION
        "Cisco UCS adaptor:EthPortBySizeSmallStatsHist:timeCollected
        managed object property"
    ::= { cucsAdaptorEthPortBySizeSmallStatsHistEntry 38 }

cucsAdaptorEthPortErrStatsTable OBJECT-TYPE
    SYNTAX           SEQUENCE OF CucsAdaptorEthPortErrStatsEntry
    MAX-ACCESS       not-accessible
    STATUS           current
    DESCRIPTION
        "Cisco UCS adaptor:EthPortErrStats managed object table"
    ::= { cucsAdaptorObjects 11 }

cucsAdaptorEthPortErrStatsEntry OBJECT-TYPE
    SYNTAX           CucsAdaptorEthPortErrStatsEntry
    MAX-ACCESS       not-accessible
    STATUS           current
    DESCRIPTION
        "Entry for the cucsAdaptorEthPortErrStatsTable table."
    INDEX { cucsAdaptorEthPortErrStatsInstanceId }
    ::= { cucsAdaptorEthPortErrStatsTable 1 }

CucsAdaptorEthPortErrStatsEntry ::= SEQUENCE {
    cucsAdaptorEthPortErrStatsInstanceId                             CucsManagedObjectId,
    cucsAdaptorEthPortErrStatsDn                                     CucsManagedObjectDn,
    cucsAdaptorEthPortErrStatsRn                                     SnmpAdminString,
    cucsAdaptorEthPortErrStatsBadCrcPackets                          Unsigned64,
    cucsAdaptorEthPortErrStatsBadCrcPacketsDelta                     Counter64,
    cucsAdaptorEthPortErrStatsBadCrcPacketsDeltaAvg                  Unsigned64,
    cucsAdaptorEthPortErrStatsBadCrcPacketsDeltaMax                  Unsigned64,
    cucsAdaptorEthPortErrStatsBadCrcPacketsDeltaMin                  Unsigned64,
    cucsAdaptorEthPortErrStatsBadLengthPackets                       Unsigned64,
    cucsAdaptorEthPortErrStatsBadLengthPacketsDelta                  Counter64,
    cucsAdaptorEthPortErrStatsBadLengthPacketsDeltaAvg               Unsigned64,
    cucsAdaptorEthPortErrStatsBadLengthPacketsDeltaMax               Unsigned64,
    cucsAdaptorEthPortErrStatsBadLengthPacketsDeltaMin               Unsigned64,
    cucsAdaptorEthPortErrStatsIntervals                              Gauge32,
    cucsAdaptorEthPortErrStatsMacDiscardedPackets                    Unsigned64,
    cucsAdaptorEthPortErrStatsMacDiscardedPacketsDelta               Counter64,
    cucsAdaptorEthPortErrStatsMacDiscardedPacketsDeltaAvg            Unsigned64,
    cucsAdaptorEthPortErrStatsMacDiscardedPacketsDeltaMax            Unsigned64,
    cucsAdaptorEthPortErrStatsMacDiscardedPacketsDeltaMin            Unsigned64,
    cucsAdaptorEthPortErrStatsSuspect                                TruthValue,
    cucsAdaptorEthPortErrStatsThresholded                            CucsAdaptorEthPortErrStatsThresholded,
    cucsAdaptorEthPortErrStatsTimeCollected                          DateAndTime,
    cucsAdaptorEthPortErrStatsTrafficDirection                       CucsAdaptorAdapterStatsTrafficDir,
    cucsAdaptorEthPortErrStatsUpdate                                 Gauge32
}

cucsAdaptorEthPortErrStatsInstanceId OBJECT-TYPE
    SYNTAX       CucsManagedObjectId
    MAX-ACCESS   not-accessible
    STATUS       current
    DESCRIPTION
        "Instance identifier of the managed object."
    ::= { cucsAdaptorEthPortErrStatsEntry 1 }

cucsAdaptorEthPortErrStatsDn OBJECT-TYPE
    SYNTAX       CucsManagedObjectDn
    MAX-ACCESS   read-only
    STATUS       current
    DESCRIPTION
        "Cisco UCS adaptor:EthPortErrStats:dn managed object property"
    ::= { cucsAdaptorEthPortErrStatsEntry 2 }

cucsAdaptorEthPortErrStatsRn OBJECT-TYPE
    SYNTAX       SnmpAdminString
    MAX-ACCESS   read-only
    STATUS       current
    DESCRIPTION
        "Cisco UCS adaptor:EthPortErrStats:rn managed object property"
    ::= { cucsAdaptorEthPortErrStatsEntry 3 }

cucsAdaptorEthPortErrStatsBadCrcPackets OBJECT-TYPE
    SYNTAX       Unsigned64
    MAX-ACCESS   read-only
    STATUS       current
    DESCRIPTION
        "Cisco UCS adaptor:EthPortErrStats:badCrcPackets
        managed object property"
    ::= { cucsAdaptorEthPortErrStatsEntry 4 }

cucsAdaptorEthPortErrStatsBadCrcPacketsDelta OBJECT-TYPE
    SYNTAX       Counter64
    MAX-ACCESS   read-only
    STATUS       current
    DESCRIPTION
        "Cisco UCS adaptor:EthPortErrStats:badCrcPacketsDelta
        managed object property"
    ::= { cucsAdaptorEthPortErrStatsEntry 5 }

cucsAdaptorEthPortErrStatsBadCrcPacketsDeltaAvg OBJECT-TYPE
    SYNTAX       Unsigned64
    MAX-ACCESS   read-only
    STATUS       current
    DESCRIPTION
        "Cisco UCS adaptor:EthPortErrStats:badCrcPacketsDeltaAvg
        managed object property"
    ::= { cucsAdaptorEthPortErrStatsEntry 6 }

cucsAdaptorEthPortErrStatsBadCrcPacketsDeltaMax OBJECT-TYPE
    SYNTAX       Unsigned64
    MAX-ACCESS   read-only
    STATUS       current
    DESCRIPTION
        "Cisco UCS adaptor:EthPortErrStats:badCrcPacketsDeltaMax
        managed object property"
    ::= { cucsAdaptorEthPortErrStatsEntry 7 }

cucsAdaptorEthPortErrStatsBadCrcPacketsDeltaMin OBJECT-TYPE
    SYNTAX       Unsigned64
    MAX-ACCESS   read-only
    STATUS       current
    DESCRIPTION
        "Cisco UCS adaptor:EthPortErrStats:badCrcPacketsDeltaMin
        managed object property"
    ::= { cucsAdaptorEthPortErrStatsEntry 8 }

cucsAdaptorEthPortErrStatsBadLengthPackets OBJECT-TYPE
    SYNTAX       Unsigned64
    MAX-ACCESS   read-only
    STATUS       current
    DESCRIPTION
        "Cisco UCS adaptor:EthPortErrStats:badLengthPackets
        managed object property"
    ::= { cucsAdaptorEthPortErrStatsEntry 9 }

cucsAdaptorEthPortErrStatsBadLengthPacketsDelta OBJECT-TYPE
    SYNTAX       Counter64
    MAX-ACCESS   read-only
    STATUS       current
    DESCRIPTION
        "Cisco UCS adaptor:EthPortErrStats:badLengthPacketsDelta
        managed object property"
    ::= { cucsAdaptorEthPortErrStatsEntry 10 }

cucsAdaptorEthPortErrStatsBadLengthPacketsDeltaAvg OBJECT-TYPE
    SYNTAX       Unsigned64
    MAX-ACCESS   read-only
    STATUS       current
    DESCRIPTION
        "Cisco UCS adaptor:EthPortErrStats:badLengthPacketsDeltaAvg
        managed object property"
    ::= { cucsAdaptorEthPortErrStatsEntry 11 }

cucsAdaptorEthPortErrStatsBadLengthPacketsDeltaMax OBJECT-TYPE
    SYNTAX       Unsigned64
    MAX-ACCESS   read-only
    STATUS       current
    DESCRIPTION
        "Cisco UCS adaptor:EthPortErrStats:badLengthPacketsDeltaMax
        managed object property"
    ::= { cucsAdaptorEthPortErrStatsEntry 12 }

cucsAdaptorEthPortErrStatsBadLengthPacketsDeltaMin OBJECT-TYPE
    SYNTAX       Unsigned64
    MAX-ACCESS   read-only
    STATUS       current
    DESCRIPTION
        "Cisco UCS adaptor:EthPortErrStats:badLengthPacketsDeltaMin
        managed object property"
    ::= { cucsAdaptorEthPortErrStatsEntry 13 }

cucsAdaptorEthPortErrStatsIntervals OBJECT-TYPE
    SYNTAX       Gauge32
    MAX-ACCESS   read-only
    STATUS       current
    DESCRIPTION
        "Cisco UCS adaptor:EthPortErrStats:intervals managed
        object property"
    ::= { cucsAdaptorEthPortErrStatsEntry 14 }

cucsAdaptorEthPortErrStatsMacDiscardedPackets OBJECT-TYPE
    SYNTAX       Unsigned64
    MAX-ACCESS   read-only
    STATUS       current
    DESCRIPTION
        "Cisco UCS adaptor:EthPortErrStats:macDiscardedPackets
        managed object property"
    ::= { cucsAdaptorEthPortErrStatsEntry 15 }

cucsAdaptorEthPortErrStatsMacDiscardedPacketsDelta OBJECT-TYPE
    SYNTAX       Counter64
    MAX-ACCESS   read-only
    STATUS       current
    DESCRIPTION
        "Cisco UCS adaptor:EthPortErrStats:macDiscardedPacketsDelta
        managed object property"
    ::= { cucsAdaptorEthPortErrStatsEntry 16 }

cucsAdaptorEthPortErrStatsMacDiscardedPacketsDeltaAvg OBJECT-TYPE
    SYNTAX       Unsigned64
    MAX-ACCESS   read-only
    STATUS       current
    DESCRIPTION
        "Cisco UCS adaptor:EthPortErrStats:macDiscardedPacketsDeltaAvg
        managed object property"
    ::= { cucsAdaptorEthPortErrStatsEntry 17 }

cucsAdaptorEthPortErrStatsMacDiscardedPacketsDeltaMax OBJECT-TYPE
    SYNTAX       Unsigned64
    MAX-ACCESS   read-only
    STATUS       current
    DESCRIPTION
        "Cisco UCS adaptor:EthPortErrStats:macDiscardedPacketsDeltaMax
        managed object property"
    ::= { cucsAdaptorEthPortErrStatsEntry 18 }

cucsAdaptorEthPortErrStatsMacDiscardedPacketsDeltaMin OBJECT-TYPE
    SYNTAX       Unsigned64
    MAX-ACCESS   read-only
    STATUS       current
    DESCRIPTION
        "Cisco UCS adaptor:EthPortErrStats:macDiscardedPacketsDeltaMin
        managed object property"
    ::= { cucsAdaptorEthPortErrStatsEntry 19 }

cucsAdaptorEthPortErrStatsSuspect OBJECT-TYPE
    SYNTAX       TruthValue
    MAX-ACCESS   read-only
    STATUS       current
    DESCRIPTION
        "Cisco UCS adaptor:EthPortErrStats:suspect managed
        object property"
    ::= { cucsAdaptorEthPortErrStatsEntry 20 }

cucsAdaptorEthPortErrStatsThresholded OBJECT-TYPE
    SYNTAX       CucsAdaptorEthPortErrStatsThresholded
    MAX-ACCESS   read-only
    STATUS       current
    DESCRIPTION
        "Cisco UCS adaptor:EthPortErrStats:thresholded
        managed object property"
    ::= { cucsAdaptorEthPortErrStatsEntry 21 }

cucsAdaptorEthPortErrStatsTimeCollected OBJECT-TYPE
    SYNTAX       DateAndTime
    MAX-ACCESS   read-only
    STATUS       current
    DESCRIPTION
        "Cisco UCS adaptor:EthPortErrStats:timeCollected
        managed object property"
    ::= { cucsAdaptorEthPortErrStatsEntry 22 }

cucsAdaptorEthPortErrStatsTrafficDirection OBJECT-TYPE
    SYNTAX       CucsAdaptorAdapterStatsTrafficDir
    MAX-ACCESS   read-only
    STATUS       current
    DESCRIPTION
        "Cisco UCS adaptor:EthPortErrStats:trafficDirection
        managed object property"
    ::= { cucsAdaptorEthPortErrStatsEntry 23 }

cucsAdaptorEthPortErrStatsUpdate OBJECT-TYPE
    SYNTAX       Gauge32
    MAX-ACCESS   read-only
    STATUS       current
    DESCRIPTION
        "Cisco UCS adaptor:EthPortErrStats:update managed object property"
    ::= { cucsAdaptorEthPortErrStatsEntry 24 }

cucsAdaptorEthPortErrStatsHistTable OBJECT-TYPE
    SYNTAX           SEQUENCE OF CucsAdaptorEthPortErrStatsHistEntry
    MAX-ACCESS       not-accessible
    STATUS           current
    DESCRIPTION
        "Cisco UCS adaptor:EthPortErrStatsHist managed object table"
    ::= { cucsAdaptorObjects 12 }

cucsAdaptorEthPortErrStatsHistEntry OBJECT-TYPE
    SYNTAX           CucsAdaptorEthPortErrStatsHistEntry
    MAX-ACCESS       not-accessible
    STATUS           current
    DESCRIPTION
        "Entry for the cucsAdaptorEthPortErrStatsHistTable table."
    INDEX { cucsAdaptorEthPortErrStatsHistInstanceId }
    ::= { cucsAdaptorEthPortErrStatsHistTable 1 }

CucsAdaptorEthPortErrStatsHistEntry ::= SEQUENCE {
    cucsAdaptorEthPortErrStatsHistInstanceId                         CucsManagedObjectId,
    cucsAdaptorEthPortErrStatsHistDn                                 CucsManagedObjectDn,
    cucsAdaptorEthPortErrStatsHistRn                                 SnmpAdminString,
    cucsAdaptorEthPortErrStatsHistBadCrcPackets                      Unsigned64,
    cucsAdaptorEthPortErrStatsHistBadCrcPacketsDelta                 Unsigned64,
    cucsAdaptorEthPortErrStatsHistBadCrcPacketsDeltaAvg              Unsigned64,
    cucsAdaptorEthPortErrStatsHistBadCrcPacketsDeltaMax              Unsigned64,
    cucsAdaptorEthPortErrStatsHistBadCrcPacketsDeltaMin              Unsigned64,
    cucsAdaptorEthPortErrStatsHistBadLengthPackets                   Unsigned64,
    cucsAdaptorEthPortErrStatsHistBadLengthPacketsDelta              Unsigned64,
    cucsAdaptorEthPortErrStatsHistBadLengthPacketsDeltaAvg           Unsigned64,
    cucsAdaptorEthPortErrStatsHistBadLengthPacketsDeltaMax           Unsigned64,
    cucsAdaptorEthPortErrStatsHistBadLengthPacketsDeltaMin           Unsigned64,
    cucsAdaptorEthPortErrStatsHistId                                 Unsigned64,
    cucsAdaptorEthPortErrStatsHistMacDiscardedPackets                Unsigned64,
    cucsAdaptorEthPortErrStatsHistMacDiscardedPacketsDelta           Unsigned64,
    cucsAdaptorEthPortErrStatsHistMacDiscardedPacketsDeltaAvg        Unsigned64,
    cucsAdaptorEthPortErrStatsHistMacDiscardedPacketsDeltaMax        Unsigned64,
    cucsAdaptorEthPortErrStatsHistMacDiscardedPacketsDeltaMin        Unsigned64,
    cucsAdaptorEthPortErrStatsHistMostRecent                         TruthValue,
    cucsAdaptorEthPortErrStatsHistSuspect                            TruthValue,
    cucsAdaptorEthPortErrStatsHistThresholded                        CucsAdaptorEthPortErrStatsHistThresholded,
    cucsAdaptorEthPortErrStatsHistTimeCollected                      DateAndTime
}

cucsAdaptorEthPortErrStatsHistInstanceId OBJECT-TYPE
    SYNTAX       CucsManagedObjectId
    MAX-ACCESS   not-accessible
    STATUS       current
    DESCRIPTION
        "Instance identifier of the managed object."
    ::= { cucsAdaptorEthPortErrStatsHistEntry 1 }

cucsAdaptorEthPortErrStatsHistDn OBJECT-TYPE
    SYNTAX       CucsManagedObjectDn
    MAX-ACCESS   read-only
    STATUS       current
    DESCRIPTION
        "Cisco UCS adaptor:EthPortErrStatsHist:dn managed object property"
    ::= { cucsAdaptorEthPortErrStatsHistEntry 2 }

cucsAdaptorEthPortErrStatsHistRn OBJECT-TYPE
    SYNTAX       SnmpAdminString
    MAX-ACCESS   read-only
    STATUS       current
    DESCRIPTION
        "Cisco UCS adaptor:EthPortErrStatsHist:rn managed object property"
    ::= { cucsAdaptorEthPortErrStatsHistEntry 3 }

cucsAdaptorEthPortErrStatsHistBadCrcPackets OBJECT-TYPE
    SYNTAX       Unsigned64
    MAX-ACCESS   read-only
    STATUS       current
    DESCRIPTION
        "Cisco UCS adaptor:EthPortErrStatsHist:badCrcPackets
        managed object property"
    ::= { cucsAdaptorEthPortErrStatsHistEntry 4 }

cucsAdaptorEthPortErrStatsHistBadCrcPacketsDelta OBJECT-TYPE
    SYNTAX       Unsigned64
    MAX-ACCESS   read-only
    STATUS       current
    DESCRIPTION
        "Cisco UCS adaptor:EthPortErrStatsHist:badCrcPacketsDelta
        managed object property"
    ::= { cucsAdaptorEthPortErrStatsHistEntry 5 }

cucsAdaptorEthPortErrStatsHistBadCrcPacketsDeltaAvg OBJECT-TYPE
    SYNTAX       Unsigned64
    MAX-ACCESS   read-only
    STATUS       current
    DESCRIPTION
        "Cisco UCS adaptor:EthPortErrStatsHist:badCrcPacketsDeltaAvg
        managed object property"
    ::= { cucsAdaptorEthPortErrStatsHistEntry 6 }

cucsAdaptorEthPortErrStatsHistBadCrcPacketsDeltaMax OBJECT-TYPE
    SYNTAX       Unsigned64
    MAX-ACCESS   read-only
    STATUS       current
    DESCRIPTION
        "Cisco UCS adaptor:EthPortErrStatsHist:badCrcPacketsDeltaMax
        managed object property"
    ::= { cucsAdaptorEthPortErrStatsHistEntry 7 }

cucsAdaptorEthPortErrStatsHistBadCrcPacketsDeltaMin OBJECT-TYPE
    SYNTAX       Unsigned64
    MAX-ACCESS   read-only
    STATUS       current
    DESCRIPTION
        "Cisco UCS adaptor:EthPortErrStatsHist:badCrcPacketsDeltaMin
        managed object property"
    ::= { cucsAdaptorEthPortErrStatsHistEntry 8 }

cucsAdaptorEthPortErrStatsHistBadLengthPackets OBJECT-TYPE
    SYNTAX       Unsigned64
    MAX-ACCESS   read-only
    STATUS       current
    DESCRIPTION
        "Cisco UCS adaptor:EthPortErrStatsHist:badLengthPackets
        managed object property"
    ::= { cucsAdaptorEthPortErrStatsHistEntry 9 }

cucsAdaptorEthPortErrStatsHistBadLengthPacketsDelta OBJECT-TYPE
    SYNTAX       Unsigned64
    MAX-ACCESS   read-only
    STATUS       current
    DESCRIPTION
        "Cisco UCS adaptor:EthPortErrStatsHist:badLengthPacketsDelta
        managed object property"
    ::= { cucsAdaptorEthPortErrStatsHistEntry 10 }

cucsAdaptorEthPortErrStatsHistBadLengthPacketsDeltaAvg OBJECT-TYPE
    SYNTAX       Unsigned64
    MAX-ACCESS   read-only
    STATUS       current
    DESCRIPTION
        "Cisco UCS adaptor:EthPortErrStatsHist:badLengthPacketsDeltaAvg
        managed object property"
    ::= { cucsAdaptorEthPortErrStatsHistEntry 11 }

cucsAdaptorEthPortErrStatsHistBadLengthPacketsDeltaMax OBJECT-TYPE
    SYNTAX       Unsigned64
    MAX-ACCESS   read-only
    STATUS       current
    DESCRIPTION
        "Cisco UCS adaptor:EthPortErrStatsHist:badLengthPacketsDeltaMax
        managed object property"
    ::= { cucsAdaptorEthPortErrStatsHistEntry 12 }

cucsAdaptorEthPortErrStatsHistBadLengthPacketsDeltaMin OBJECT-TYPE
    SYNTAX       Unsigned64
    MAX-ACCESS   read-only
    STATUS       current
    DESCRIPTION
        "Cisco UCS adaptor:EthPortErrStatsHist:badLengthPacketsDeltaMin
        managed object property"
    ::= { cucsAdaptorEthPortErrStatsHistEntry 13 }

cucsAdaptorEthPortErrStatsHistId OBJECT-TYPE
    SYNTAX       Unsigned64
    MAX-ACCESS   read-only
    STATUS       current
    DESCRIPTION
        "Cisco UCS adaptor:EthPortErrStatsHist:id managed object property"
    ::= { cucsAdaptorEthPortErrStatsHistEntry 14 }

cucsAdaptorEthPortErrStatsHistMacDiscardedPackets OBJECT-TYPE
    SYNTAX       Unsigned64
    MAX-ACCESS   read-only
    STATUS       current
    DESCRIPTION
        "Cisco UCS adaptor:EthPortErrStatsHist:macDiscardedPackets
        managed object property"
    ::= { cucsAdaptorEthPortErrStatsHistEntry 15 }

cucsAdaptorEthPortErrStatsHistMacDiscardedPacketsDelta OBJECT-TYPE
    SYNTAX       Unsigned64
    MAX-ACCESS   read-only
    STATUS       current
    DESCRIPTION
        "Cisco UCS adaptor:EthPortErrStatsHist:macDiscardedPacketsDelta
        managed object property"
    ::= { cucsAdaptorEthPortErrStatsHistEntry 16 }

cucsAdaptorEthPortErrStatsHistMacDiscardedPacketsDeltaAvg OBJECT-TYPE
    SYNTAX       Unsigned64
    MAX-ACCESS   read-only
    STATUS       current
    DESCRIPTION
        "Cisco UCS adaptor:EthPortErrStatsHist:macDiscardedPacketsDeltaAvg
         managed object property"
    ::= { cucsAdaptorEthPortErrStatsHistEntry 17 }

cucsAdaptorEthPortErrStatsHistMacDiscardedPacketsDeltaMax OBJECT-TYPE
    SYNTAX       Unsigned64
    MAX-ACCESS   read-only
    STATUS       current
    DESCRIPTION
        "Cisco UCS adaptor:EthPortErrStatsHist:macDiscardedPacketsDeltaMax
         managed object property"
    ::= { cucsAdaptorEthPortErrStatsHistEntry 18 }

cucsAdaptorEthPortErrStatsHistMacDiscardedPacketsDeltaMin OBJECT-TYPE
    SYNTAX       Unsigned64
    MAX-ACCESS   read-only
    STATUS       current
    DESCRIPTION
        "Cisco UCS adaptor:EthPortErrStatsHist:macDiscardedPacketsDeltaMin
         managed object property"
    ::= { cucsAdaptorEthPortErrStatsHistEntry 19 }

cucsAdaptorEthPortErrStatsHistMostRecent OBJECT-TYPE
    SYNTAX       TruthValue
    MAX-ACCESS   read-only
    STATUS       current
    DESCRIPTION
        "Cisco UCS adaptor:EthPortErrStatsHist:mostRecent
        managed object property"
    ::= { cucsAdaptorEthPortErrStatsHistEntry 20 }

cucsAdaptorEthPortErrStatsHistSuspect OBJECT-TYPE
    SYNTAX       TruthValue
    MAX-ACCESS   read-only
    STATUS       current
    DESCRIPTION
        "Cisco UCS adaptor:EthPortErrStatsHist:suspect
        managed object property"
    ::= { cucsAdaptorEthPortErrStatsHistEntry 21 }

cucsAdaptorEthPortErrStatsHistThresholded OBJECT-TYPE
    SYNTAX       CucsAdaptorEthPortErrStatsHistThresholded
    MAX-ACCESS   read-only
    STATUS       current
    DESCRIPTION
        "Cisco UCS adaptor:EthPortErrStatsHist:thresholded
        managed object property"
    ::= { cucsAdaptorEthPortErrStatsHistEntry 22 }

cucsAdaptorEthPortErrStatsHistTimeCollected OBJECT-TYPE
    SYNTAX       DateAndTime
    MAX-ACCESS   read-only
    STATUS       current
    DESCRIPTION
        "Cisco UCS adaptor:EthPortErrStatsHist:timeCollected
        managed object property"
    ::= { cucsAdaptorEthPortErrStatsHistEntry 23 }

cucsAdaptorEthPortMcastStatsTable OBJECT-TYPE
    SYNTAX           SEQUENCE OF CucsAdaptorEthPortMcastStatsEntry
    MAX-ACCESS       not-accessible
    STATUS           current
    DESCRIPTION
        "Cisco UCS adaptor:EthPortMcastStats managed object table"
    ::= { cucsAdaptorObjects 13 }

cucsAdaptorEthPortMcastStatsEntry OBJECT-TYPE
    SYNTAX           CucsAdaptorEthPortMcastStatsEntry
    MAX-ACCESS       not-accessible
    STATUS           current
    DESCRIPTION
        "Entry for the cucsAdaptorEthPortMcastStatsTable table."
    INDEX { cucsAdaptorEthPortMcastStatsInstanceId }
    ::= { cucsAdaptorEthPortMcastStatsTable 1 }

CucsAdaptorEthPortMcastStatsEntry ::= SEQUENCE {
    cucsAdaptorEthPortMcastStatsInstanceId                           CucsManagedObjectId,
    cucsAdaptorEthPortMcastStatsDn                                   CucsManagedObjectDn,
    cucsAdaptorEthPortMcastStatsRn                                   SnmpAdminString,
    cucsAdaptorEthPortMcastStatsBroadcastPackets                     Unsigned64,
    cucsAdaptorEthPortMcastStatsBroadcastPacketsDelta                Counter64,
    cucsAdaptorEthPortMcastStatsBroadcastPacketsDeltaAvg             Unsigned64,
    cucsAdaptorEthPortMcastStatsBroadcastPacketsDeltaMax             Unsigned64,
    cucsAdaptorEthPortMcastStatsBroadcastPacketsDeltaMin             Unsigned64,
    cucsAdaptorEthPortMcastStatsIntervals                            Gauge32,
    cucsAdaptorEthPortMcastStatsMulticastPackets                     Unsigned64,
    cucsAdaptorEthPortMcastStatsMulticastPacketsDelta                Counter64,
    cucsAdaptorEthPortMcastStatsMulticastPacketsDeltaAvg             Unsigned64,
    cucsAdaptorEthPortMcastStatsMulticastPacketsDeltaMax             Unsigned64,
    cucsAdaptorEthPortMcastStatsMulticastPacketsDeltaMin             Unsigned64,
    cucsAdaptorEthPortMcastStatsSuspect                              TruthValue,
    cucsAdaptorEthPortMcastStatsThresholded                          CucsAdaptorEthPortMcastStatsThresholded,
    cucsAdaptorEthPortMcastStatsTimeCollected                        DateAndTime,
    cucsAdaptorEthPortMcastStatsTrafficDirection                     CucsAdaptorAdapterStatsTrafficDir,
    cucsAdaptorEthPortMcastStatsUnicastPackets                       Unsigned64,
    cucsAdaptorEthPortMcastStatsUnicastPacketsDelta                  Counter64,
    cucsAdaptorEthPortMcastStatsUnicastPacketsDeltaAvg               Unsigned64,
    cucsAdaptorEthPortMcastStatsUnicastPacketsDeltaMax               Unsigned64,
    cucsAdaptorEthPortMcastStatsUnicastPacketsDeltaMin               Unsigned64,
    cucsAdaptorEthPortMcastStatsUpdate                               Gauge32
}

cucsAdaptorEthPortMcastStatsInstanceId OBJECT-TYPE
    SYNTAX       CucsManagedObjectId
    MAX-ACCESS   not-accessible
    STATUS       current
    DESCRIPTION
        "Instance identifier of the managed object."
    ::= { cucsAdaptorEthPortMcastStatsEntry 1 }

cucsAdaptorEthPortMcastStatsDn OBJECT-TYPE
    SYNTAX       CucsManagedObjectDn
    MAX-ACCESS   read-only
    STATUS       current
    DESCRIPTION
        "Cisco UCS adaptor:EthPortMcastStats:dn managed object property"
    ::= { cucsAdaptorEthPortMcastStatsEntry 2 }

cucsAdaptorEthPortMcastStatsRn OBJECT-TYPE
    SYNTAX       SnmpAdminString
    MAX-ACCESS   read-only
    STATUS       current
    DESCRIPTION
        "Cisco UCS adaptor:EthPortMcastStats:rn managed object property"
    ::= { cucsAdaptorEthPortMcastStatsEntry 3 }

cucsAdaptorEthPortMcastStatsBroadcastPackets OBJECT-TYPE
    SYNTAX       Unsigned64
    MAX-ACCESS   read-only
    STATUS       current
    DESCRIPTION
        "Cisco UCS adaptor:EthPortMcastStats:broadcastPackets
        managed object property"
    ::= { cucsAdaptorEthPortMcastStatsEntry 4 }

cucsAdaptorEthPortMcastStatsBroadcastPacketsDelta OBJECT-TYPE
    SYNTAX       Counter64
    MAX-ACCESS   read-only
    STATUS       current
    DESCRIPTION
        "Cisco UCS adaptor:EthPortMcastStats:broadcastPacketsDelta
        managed object property"
    ::= { cucsAdaptorEthPortMcastStatsEntry 5 }

cucsAdaptorEthPortMcastStatsBroadcastPacketsDeltaAvg OBJECT-TYPE
    SYNTAX       Unsigned64
    MAX-ACCESS   read-only
    STATUS       current
    DESCRIPTION
        "Cisco UCS adaptor:EthPortMcastStats:broadcastPacketsDeltaAvg
        managed object property"
    ::= { cucsAdaptorEthPortMcastStatsEntry 6 }

cucsAdaptorEthPortMcastStatsBroadcastPacketsDeltaMax OBJECT-TYPE
    SYNTAX       Unsigned64
    MAX-ACCESS   read-only
    STATUS       current
    DESCRIPTION
        "Cisco UCS adaptor:EthPortMcastStats:broadcastPacketsDeltaMax
        managed object property"
    ::= { cucsAdaptorEthPortMcastStatsEntry 7 }

cucsAdaptorEthPortMcastStatsBroadcastPacketsDeltaMin OBJECT-TYPE
    SYNTAX       Unsigned64
    MAX-ACCESS   read-only
    STATUS       current
    DESCRIPTION
        "Cisco UCS adaptor:EthPortMcastStats:broadcastPacketsDeltaMin
        managed object property"
    ::= { cucsAdaptorEthPortMcastStatsEntry 8 }

cucsAdaptorEthPortMcastStatsIntervals OBJECT-TYPE
    SYNTAX       Gauge32
    MAX-ACCESS   read-only
    STATUS       current
    DESCRIPTION
        "Cisco UCS adaptor:EthPortMcastStats:intervals
        managed object property"
    ::= { cucsAdaptorEthPortMcastStatsEntry 9 }

cucsAdaptorEthPortMcastStatsMulticastPackets OBJECT-TYPE
    SYNTAX       Unsigned64
    MAX-ACCESS   read-only
    STATUS       current
    DESCRIPTION
        "Cisco UCS adaptor:EthPortMcastStats:multicastPackets
        managed object property"
    ::= { cucsAdaptorEthPortMcastStatsEntry 10 }

cucsAdaptorEthPortMcastStatsMulticastPacketsDelta OBJECT-TYPE
    SYNTAX       Counter64
    MAX-ACCESS   read-only
    STATUS       current
    DESCRIPTION
        "Cisco UCS adaptor:EthPortMcastStats:multicastPacketsDelta
        managed object property"
    ::= { cucsAdaptorEthPortMcastStatsEntry 11 }

cucsAdaptorEthPortMcastStatsMulticastPacketsDeltaAvg OBJECT-TYPE
    SYNTAX       Unsigned64
    MAX-ACCESS   read-only
    STATUS       current
    DESCRIPTION
        "Cisco UCS adaptor:EthPortMcastStats:multicastPacketsDeltaAvg
        managed object property"
    ::= { cucsAdaptorEthPortMcastStatsEntry 12 }

cucsAdaptorEthPortMcastStatsMulticastPacketsDeltaMax OBJECT-TYPE
    SYNTAX       Unsigned64
    MAX-ACCESS   read-only
    STATUS       current
    DESCRIPTION
        "Cisco UCS adaptor:EthPortMcastStats:multicastPacketsDeltaMax
        managed object property"
    ::= { cucsAdaptorEthPortMcastStatsEntry 13 }

cucsAdaptorEthPortMcastStatsMulticastPacketsDeltaMin OBJECT-TYPE
    SYNTAX       Unsigned64
    MAX-ACCESS   read-only
    STATUS       current
    DESCRIPTION
        "Cisco UCS adaptor:EthPortMcastStats:multicastPacketsDeltaMin
        managed object property"
    ::= { cucsAdaptorEthPortMcastStatsEntry 14 }

cucsAdaptorEthPortMcastStatsSuspect OBJECT-TYPE
    SYNTAX       TruthValue
    MAX-ACCESS   read-only
    STATUS       current
    DESCRIPTION
        "Cisco UCS adaptor:EthPortMcastStats:suspect managed
        object property"
    ::= { cucsAdaptorEthPortMcastStatsEntry 15 }

cucsAdaptorEthPortMcastStatsThresholded OBJECT-TYPE
    SYNTAX       CucsAdaptorEthPortMcastStatsThresholded
    MAX-ACCESS   read-only
    STATUS       current
    DESCRIPTION
        "Cisco UCS adaptor:EthPortMcastStats:thresholded
        managed object property"
    ::= { cucsAdaptorEthPortMcastStatsEntry 16 }

cucsAdaptorEthPortMcastStatsTimeCollected OBJECT-TYPE
    SYNTAX       DateAndTime
    MAX-ACCESS   read-only
    STATUS       current
    DESCRIPTION
        "Cisco UCS adaptor:EthPortMcastStats:timeCollected
        managed object property"
    ::= { cucsAdaptorEthPortMcastStatsEntry 17 }

cucsAdaptorEthPortMcastStatsTrafficDirection OBJECT-TYPE
    SYNTAX       CucsAdaptorAdapterStatsTrafficDir
    MAX-ACCESS   read-only
    STATUS       current
    DESCRIPTION
        "Cisco UCS adaptor:EthPortMcastStats:trafficDirection
        managed object property"
    ::= { cucsAdaptorEthPortMcastStatsEntry 18 }

cucsAdaptorEthPortMcastStatsUnicastPackets OBJECT-TYPE
    SYNTAX       Unsigned64
    MAX-ACCESS   read-only
    STATUS       current
    DESCRIPTION
        "Cisco UCS adaptor:EthPortMcastStats:unicastPackets
        managed object property"
    ::= { cucsAdaptorEthPortMcastStatsEntry 19 }

cucsAdaptorEthPortMcastStatsUnicastPacketsDelta OBJECT-TYPE
    SYNTAX       Counter64
    MAX-ACCESS   read-only
    STATUS       current
    DESCRIPTION
        "Cisco UCS adaptor:EthPortMcastStats:unicastPacketsDelta
        managed object property"
    ::= { cucsAdaptorEthPortMcastStatsEntry 20 }

cucsAdaptorEthPortMcastStatsUnicastPacketsDeltaAvg OBJECT-TYPE
    SYNTAX       Unsigned64
    MAX-ACCESS   read-only
    STATUS       current
    DESCRIPTION
        "Cisco UCS adaptor:EthPortMcastStats:unicastPacketsDeltaAvg
        managed object property"
    ::= { cucsAdaptorEthPortMcastStatsEntry 21 }

cucsAdaptorEthPortMcastStatsUnicastPacketsDeltaMax OBJECT-TYPE
    SYNTAX       Unsigned64
    MAX-ACCESS   read-only
    STATUS       current
    DESCRIPTION
        "Cisco UCS adaptor:EthPortMcastStats:unicastPacketsDeltaMax
        managed object property"
    ::= { cucsAdaptorEthPortMcastStatsEntry 22 }

cucsAdaptorEthPortMcastStatsUnicastPacketsDeltaMin OBJECT-TYPE
    SYNTAX       Unsigned64
    MAX-ACCESS   read-only
    STATUS       current
    DESCRIPTION
        "Cisco UCS adaptor:EthPortMcastStats:unicastPacketsDeltaMin
        managed object property"
    ::= { cucsAdaptorEthPortMcastStatsEntry 23 }

cucsAdaptorEthPortMcastStatsUpdate OBJECT-TYPE
    SYNTAX       Gauge32
    MAX-ACCESS   read-only
    STATUS       current
    DESCRIPTION
        "Cisco UCS adaptor:EthPortMcastStats:update managed
        object property"
    ::= { cucsAdaptorEthPortMcastStatsEntry 24 }

cucsAdaptorEthPortMcastStatsHistTable OBJECT-TYPE
    SYNTAX           SEQUENCE OF CucsAdaptorEthPortMcastStatsHistEntry
    MAX-ACCESS       not-accessible
    STATUS           current
    DESCRIPTION
        "Cisco UCS adaptor:EthPortMcastStatsHist managed object table"
    ::= { cucsAdaptorObjects 14 }

cucsAdaptorEthPortMcastStatsHistEntry OBJECT-TYPE
    SYNTAX           CucsAdaptorEthPortMcastStatsHistEntry
    MAX-ACCESS       not-accessible
    STATUS           current
    DESCRIPTION
        "Entry for the cucsAdaptorEthPortMcastStatsHistTable table."
    INDEX { cucsAdaptorEthPortMcastStatsHistInstanceId }
    ::= { cucsAdaptorEthPortMcastStatsHistTable 1 }

CucsAdaptorEthPortMcastStatsHistEntry ::= SEQUENCE {
    cucsAdaptorEthPortMcastStatsHistInstanceId                       CucsManagedObjectId,
    cucsAdaptorEthPortMcastStatsHistDn                               CucsManagedObjectDn,
    cucsAdaptorEthPortMcastStatsHistRn                               SnmpAdminString,
    cucsAdaptorEthPortMcastStatsHistBroadcastPackets                 Unsigned64,
    cucsAdaptorEthPortMcastStatsHistBroadcastPacketsDelta            Unsigned64,
    cucsAdaptorEthPortMcastStatsHistBroadcastPacketsDeltaAvg         Unsigned64,
    cucsAdaptorEthPortMcastStatsHistBroadcastPacketsDeltaMax         Unsigned64,
    cucsAdaptorEthPortMcastStatsHistBroadcastPacketsDeltaMin         Unsigned64,
    cucsAdaptorEthPortMcastStatsHistId                               Unsigned64,
    cucsAdaptorEthPortMcastStatsHistMostRecent                       TruthValue,
    cucsAdaptorEthPortMcastStatsHistMulticastPackets                 Unsigned64,
    cucsAdaptorEthPortMcastStatsHistMulticastPacketsDelta            Unsigned64,
    cucsAdaptorEthPortMcastStatsHistMulticastPacketsDeltaAvg         Unsigned64,
    cucsAdaptorEthPortMcastStatsHistMulticastPacketsDeltaMax         Unsigned64,
    cucsAdaptorEthPortMcastStatsHistMulticastPacketsDeltaMin         Unsigned64,
    cucsAdaptorEthPortMcastStatsHistSuspect                          TruthValue,
    cucsAdaptorEthPortMcastStatsHistThresholded                      CucsAdaptorEthPortMcastStatsHistThresholded,
    cucsAdaptorEthPortMcastStatsHistTimeCollected                    DateAndTime,
    cucsAdaptorEthPortMcastStatsHistUnicastPackets                   Unsigned64,
    cucsAdaptorEthPortMcastStatsHistUnicastPacketsDelta              Unsigned64,
    cucsAdaptorEthPortMcastStatsHistUnicastPacketsDeltaAvg           Unsigned64,
    cucsAdaptorEthPortMcastStatsHistUnicastPacketsDeltaMax           Unsigned64,
    cucsAdaptorEthPortMcastStatsHistUnicastPacketsDeltaMin           Unsigned64
}

cucsAdaptorEthPortMcastStatsHistInstanceId OBJECT-TYPE
    SYNTAX       CucsManagedObjectId
    MAX-ACCESS   not-accessible
    STATUS       current
    DESCRIPTION
        "Instance identifier of the managed object."
    ::= { cucsAdaptorEthPortMcastStatsHistEntry 1 }

cucsAdaptorEthPortMcastStatsHistDn OBJECT-TYPE
    SYNTAX       CucsManagedObjectDn
    MAX-ACCESS   read-only
    STATUS       current
    DESCRIPTION
        "Cisco UCS adaptor:EthPortMcastStatsHist:dn managed
        object property"
    ::= { cucsAdaptorEthPortMcastStatsHistEntry 2 }

cucsAdaptorEthPortMcastStatsHistRn OBJECT-TYPE
    SYNTAX       SnmpAdminString
    MAX-ACCESS   read-only
    STATUS       current
    DESCRIPTION
        "Cisco UCS adaptor:EthPortMcastStatsHist:rn managed
        object property"
    ::= { cucsAdaptorEthPortMcastStatsHistEntry 3 }

cucsAdaptorEthPortMcastStatsHistBroadcastPackets OBJECT-TYPE
    SYNTAX       Unsigned64
    MAX-ACCESS   read-only
    STATUS       current
    DESCRIPTION
        "Cisco UCS adaptor:EthPortMcastStatsHist:broadcastPackets
        managed object property"
    ::= { cucsAdaptorEthPortMcastStatsHistEntry 4 }

cucsAdaptorEthPortMcastStatsHistBroadcastPacketsDelta OBJECT-TYPE
    SYNTAX       Unsigned64
    MAX-ACCESS   read-only
    STATUS       current
    DESCRIPTION
        "Cisco UCS adaptor:EthPortMcastStatsHist:broadcastPacketsDelta
        managed object property"
    ::= { cucsAdaptorEthPortMcastStatsHistEntry 5 }

cucsAdaptorEthPortMcastStatsHistBroadcastPacketsDeltaAvg OBJECT-TYPE
    SYNTAX       Unsigned64
    MAX-ACCESS   read-only
    STATUS       current
    DESCRIPTION
        "Cisco UCS adaptor:EthPortMcastStatsHist:broadcastPacketsDeltaAvg
        managed object property"
    ::= { cucsAdaptorEthPortMcastStatsHistEntry 6 }

cucsAdaptorEthPortMcastStatsHistBroadcastPacketsDeltaMax OBJECT-TYPE
    SYNTAX       Unsigned64
    MAX-ACCESS   read-only
    STATUS       current
    DESCRIPTION
        "Cisco UCS adaptor:EthPortMcastStatsHist:broadcastPacketsDeltaMax
        managed object property"
    ::= { cucsAdaptorEthPortMcastStatsHistEntry 7 }

cucsAdaptorEthPortMcastStatsHistBroadcastPacketsDeltaMin OBJECT-TYPE
    SYNTAX       Unsigned64
    MAX-ACCESS   read-only
    STATUS       current
    DESCRIPTION
        "Cisco UCS adaptor:EthPortMcastStatsHist:broadcastPacketsDeltaMin
        managed object property"
    ::= { cucsAdaptorEthPortMcastStatsHistEntry 8 }

cucsAdaptorEthPortMcastStatsHistId OBJECT-TYPE
    SYNTAX       Unsigned64
    MAX-ACCESS   read-only
    STATUS       current
    DESCRIPTION
        "Cisco UCS adaptor:EthPortMcastStatsHist:id managed
        object property"
    ::= { cucsAdaptorEthPortMcastStatsHistEntry 9 }

cucsAdaptorEthPortMcastStatsHistMostRecent OBJECT-TYPE
    SYNTAX       TruthValue
    MAX-ACCESS   read-only
    STATUS       current
    DESCRIPTION
        "Cisco UCS adaptor:EthPortMcastStatsHist:mostRecent
        managed object property"
    ::= { cucsAdaptorEthPortMcastStatsHistEntry 10 }

cucsAdaptorEthPortMcastStatsHistMulticastPackets OBJECT-TYPE
    SYNTAX       Unsigned64
    MAX-ACCESS   read-only
    STATUS       current
    DESCRIPTION
        "Cisco UCS adaptor:EthPortMcastStatsHist:multicastPackets
        managed object property"
    ::= { cucsAdaptorEthPortMcastStatsHistEntry 11 }

cucsAdaptorEthPortMcastStatsHistMulticastPacketsDelta OBJECT-TYPE
    SYNTAX       Unsigned64
    MAX-ACCESS   read-only
    STATUS       current
    DESCRIPTION
        "Cisco UCS adaptor:EthPortMcastStatsHist:multicastPacketsDelta
        managed object property"
    ::= { cucsAdaptorEthPortMcastStatsHistEntry 12 }

cucsAdaptorEthPortMcastStatsHistMulticastPacketsDeltaAvg OBJECT-TYPE
    SYNTAX       Unsigned64
    MAX-ACCESS   read-only
    STATUS       current
    DESCRIPTION
        "Cisco UCS adaptor:EthPortMcastStatsHist:multicastPacketsDeltaAvg
        managed object property"
    ::= { cucsAdaptorEthPortMcastStatsHistEntry 13 }

cucsAdaptorEthPortMcastStatsHistMulticastPacketsDeltaMax OBJECT-TYPE
    SYNTAX       Unsigned64
    MAX-ACCESS   read-only
    STATUS       current
    DESCRIPTION
        "Cisco UCS adaptor:EthPortMcastStatsHist:multicastPacketsDeltaMax
        managed object property"
    ::= { cucsAdaptorEthPortMcastStatsHistEntry 14 }

cucsAdaptorEthPortMcastStatsHistMulticastPacketsDeltaMin OBJECT-TYPE
    SYNTAX       Unsigned64
    MAX-ACCESS   read-only
    STATUS       current
    DESCRIPTION
        "Cisco UCS adaptor:EthPortMcastStatsHist:multicastPacketsDeltaMin
        managed object property"
    ::= { cucsAdaptorEthPortMcastStatsHistEntry 15 }

cucsAdaptorEthPortMcastStatsHistSuspect OBJECT-TYPE
    SYNTAX       TruthValue
    MAX-ACCESS   read-only
    STATUS       current
    DESCRIPTION
        "Cisco UCS adaptor:EthPortMcastStatsHist:suspect
        managed object property"
    ::= { cucsAdaptorEthPortMcastStatsHistEntry 16 }

cucsAdaptorEthPortMcastStatsHistThresholded OBJECT-TYPE
    SYNTAX       CucsAdaptorEthPortMcastStatsHistThresholded
    MAX-ACCESS   read-only
    STATUS       current
    DESCRIPTION
        "Cisco UCS adaptor:EthPortMcastStatsHist:thresholded
        managed object property"
    ::= { cucsAdaptorEthPortMcastStatsHistEntry 17 }

cucsAdaptorEthPortMcastStatsHistTimeCollected OBJECT-TYPE
    SYNTAX       DateAndTime
    MAX-ACCESS   read-only
    STATUS       current
    DESCRIPTION
        "Cisco UCS adaptor:EthPortMcastStatsHist:timeCollected
        managed object property"
    ::= { cucsAdaptorEthPortMcastStatsHistEntry 18 }

cucsAdaptorEthPortMcastStatsHistUnicastPackets OBJECT-TYPE
    SYNTAX       Unsigned64
    MAX-ACCESS   read-only
    STATUS       current
    DESCRIPTION
        "Cisco UCS adaptor:EthPortMcastStatsHist:unicastPackets
        managed object property"
    ::= { cucsAdaptorEthPortMcastStatsHistEntry 19 }

cucsAdaptorEthPortMcastStatsHistUnicastPacketsDelta OBJECT-TYPE
    SYNTAX       Unsigned64
    MAX-ACCESS   read-only
    STATUS       current
    DESCRIPTION
        "Cisco UCS adaptor:EthPortMcastStatsHist:unicastPacketsDelta
        managed object property"
    ::= { cucsAdaptorEthPortMcastStatsHistEntry 20 }

cucsAdaptorEthPortMcastStatsHistUnicastPacketsDeltaAvg OBJECT-TYPE
    SYNTAX       Unsigned64
    MAX-ACCESS   read-only
    STATUS       current
    DESCRIPTION
        "Cisco UCS adaptor:EthPortMcastStatsHist:unicastPacketsDeltaAvg
        managed object property"
    ::= { cucsAdaptorEthPortMcastStatsHistEntry 21 }

cucsAdaptorEthPortMcastStatsHistUnicastPacketsDeltaMax OBJECT-TYPE
    SYNTAX       Unsigned64
    MAX-ACCESS   read-only
    STATUS       current
    DESCRIPTION
        "Cisco UCS adaptor:EthPortMcastStatsHist:unicastPacketsDeltaMax
        managed object property"
    ::= { cucsAdaptorEthPortMcastStatsHistEntry 22 }

cucsAdaptorEthPortMcastStatsHistUnicastPacketsDeltaMin OBJECT-TYPE
    SYNTAX       Unsigned64
    MAX-ACCESS   read-only
    STATUS       current
    DESCRIPTION
        "Cisco UCS adaptor:EthPortMcastStatsHist:unicastPacketsDeltaMin
        managed object property"
    ::= { cucsAdaptorEthPortMcastStatsHistEntry 23 }

cucsAdaptorEthPortOutsizedStatsTable OBJECT-TYPE
    SYNTAX           SEQUENCE OF CucsAdaptorEthPortOutsizedStatsEntry
    MAX-ACCESS       not-accessible
    STATUS           current
    DESCRIPTION
        "Cisco UCS adaptor:EthPortOutsizedStats managed object table"
    ::= { cucsAdaptorObjects 15 }

cucsAdaptorEthPortOutsizedStatsEntry OBJECT-TYPE
    SYNTAX           CucsAdaptorEthPortOutsizedStatsEntry
    MAX-ACCESS       not-accessible
    STATUS           current
    DESCRIPTION
        "Entry for the cucsAdaptorEthPortOutsizedStatsTable table."
    INDEX { cucsAdaptorEthPortOutsizedStatsInstanceId }
    ::= { cucsAdaptorEthPortOutsizedStatsTable 1 }

CucsAdaptorEthPortOutsizedStatsEntry ::= SEQUENCE {
    cucsAdaptorEthPortOutsizedStatsInstanceId                        CucsManagedObjectId,
    cucsAdaptorEthPortOutsizedStatsDn                                CucsManagedObjectDn,
    cucsAdaptorEthPortOutsizedStatsRn                                SnmpAdminString,
    cucsAdaptorEthPortOutsizedStatsIntervals                         Gauge32,
    cucsAdaptorEthPortOutsizedStatsOversizedBadCrcPackets            Unsigned64,
    cucsAdaptorEthPortOutsizedStatsOversizedBadCrcPacketsDelta       Counter64,
    cucsAdaptorEthPortOutsizedStatsOversizedBadCrcPacketsDeltaAvg    Unsigned64,
    cucsAdaptorEthPortOutsizedStatsOversizedBadCrcPacketsDeltaMax    Unsigned64,
    cucsAdaptorEthPortOutsizedStatsOversizedBadCrcPacketsDeltaMin    Unsigned64,
    cucsAdaptorEthPortOutsizedStatsOversizedGoodCrcPackets           Unsigned64,
    cucsAdaptorEthPortOutsizedStatsOversizedGoodCrcPacketsDelta      Counter64,
    cucsAdaptorEthPortOutsizedStatsOversizedGoodCrcPacketsDeltaAvg   Unsigned64,
    cucsAdaptorEthPortOutsizedStatsOversizedGoodCrcPacketsDeltaMax   Unsigned64,
    cucsAdaptorEthPortOutsizedStatsOversizedGoodCrcPacketsDeltaMin   Unsigned64,
    cucsAdaptorEthPortOutsizedStatsOversizedPackets                  Unsigned64,
    cucsAdaptorEthPortOutsizedStatsOversizedPacketsDelta             Counter64,
    cucsAdaptorEthPortOutsizedStatsOversizedPacketsDeltaAvg          Unsigned64,
    cucsAdaptorEthPortOutsizedStatsOversizedPacketsDeltaMax          Unsigned64,
    cucsAdaptorEthPortOutsizedStatsOversizedPacketsDeltaMin          Unsigned64,
    cucsAdaptorEthPortOutsizedStatsSuspect                           TruthValue,
    cucsAdaptorEthPortOutsizedStatsThresholded                       CucsAdaptorEthPortOutsizedStatsThresholded,
    cucsAdaptorEthPortOutsizedStatsTimeCollected                     DateAndTime,
    cucsAdaptorEthPortOutsizedStatsTrafficDirection                  CucsAdaptorAdapterStatsTrafficDir,
    cucsAdaptorEthPortOutsizedStatsUndersizedBadCrcPackets           Unsigned64,
    cucsAdaptorEthPortOutsizedStatsUndersizedBadCrcPacketsDelta      Counter64,
    cucsAdaptorEthPortOutsizedStatsUndersizedBadCrcPacketsDeltaAvg   Unsigned64,
    cucsAdaptorEthPortOutsizedStatsUndersizedBadCrcPacketsDeltaMax   Unsigned64,
    cucsAdaptorEthPortOutsizedStatsUndersizedBadCrcPacketsDeltaMin   Unsigned64,
    cucsAdaptorEthPortOutsizedStatsUndersizedGoodCrcPackets          Unsigned64,
    cucsAdaptorEthPortOutsizedStatsUndersizedGoodCrcPacketsDelta     Counter64,
    cucsAdaptorEthPortOutsizedStatsUndersizedGoodCrcPacketsDeltaAvg  Unsigned64,
    cucsAdaptorEthPortOutsizedStatsUndersizedGoodCrcPacketsDeltaMax  Unsigned64,
    cucsAdaptorEthPortOutsizedStatsUndersizedGoodCrcPacketsDeltaMin  Unsigned64,
    cucsAdaptorEthPortOutsizedStatsUpdate                            Gauge32
}

cucsAdaptorEthPortOutsizedStatsInstanceId OBJECT-TYPE
    SYNTAX       CucsManagedObjectId
    MAX-ACCESS   not-accessible
    STATUS       current
    DESCRIPTION
        "Instance identifier of the managed object."
    ::= { cucsAdaptorEthPortOutsizedStatsEntry 1 }

cucsAdaptorEthPortOutsizedStatsDn OBJECT-TYPE
    SYNTAX       CucsManagedObjectDn
    MAX-ACCESS   read-only
    STATUS       current
    DESCRIPTION
        "Cisco UCS adaptor:EthPortOutsizedStats:dn managed
        object property"
    ::= { cucsAdaptorEthPortOutsizedStatsEntry 2 }

cucsAdaptorEthPortOutsizedStatsRn OBJECT-TYPE
    SYNTAX       SnmpAdminString
    MAX-ACCESS   read-only
    STATUS       current
    DESCRIPTION
        "Cisco UCS adaptor:EthPortOutsizedStats:rn managed
        object property"
    ::= { cucsAdaptorEthPortOutsizedStatsEntry 3 }

cucsAdaptorEthPortOutsizedStatsIntervals OBJECT-TYPE
    SYNTAX       Gauge32
    MAX-ACCESS   read-only
    STATUS       current
    DESCRIPTION
        "Cisco UCS adaptor:EthPortOutsizedStats:intervals
        managed object property"
    ::= { cucsAdaptorEthPortOutsizedStatsEntry 4 }

cucsAdaptorEthPortOutsizedStatsOversizedBadCrcPackets OBJECT-TYPE
    SYNTAX       Unsigned64
    MAX-ACCESS   read-only
    STATUS       current
    DESCRIPTION
        "Cisco UCS adaptor:EthPortOutsizedStats:oversizedBadCrcPackets
        managed object property"
    ::= { cucsAdaptorEthPortOutsizedStatsEntry 5 }

cucsAdaptorEthPortOutsizedStatsOversizedBadCrcPacketsDelta OBJECT-TYPE
    SYNTAX       Counter64
    MAX-ACCESS   read-only
    STATUS       current
    DESCRIPTION
        "Cisco UCS adaptor:EthPortOutsizedStats:oversizedBadCrcPacketsDelt
        a managed object property"
    ::= { cucsAdaptorEthPortOutsizedStatsEntry 6 }

cucsAdaptorEthPortOutsizedStatsOversizedBadCrcPacketsDeltaAvg OBJECT-TYPE
    SYNTAX       Unsigned64
    MAX-ACCESS   read-only
    STATUS       current
    DESCRIPTION
        "Cisco UCS adaptor:EthPortOutsizedStats:oversizedBadCrcPacketsDelt
        aAvg managed object property"
    ::= { cucsAdaptorEthPortOutsizedStatsEntry 7 }

cucsAdaptorEthPortOutsizedStatsOversizedBadCrcPacketsDeltaMax OBJECT-TYPE
    SYNTAX       Unsigned64
    MAX-ACCESS   read-only
    STATUS       current
    DESCRIPTION
        "Cisco UCS adaptor:EthPortOutsizedStats:oversizedBadCrcPacketsDelt
        aMax managed object property"
    ::= { cucsAdaptorEthPortOutsizedStatsEntry 8 }

cucsAdaptorEthPortOutsizedStatsOversizedBadCrcPacketsDeltaMin OBJECT-TYPE
    SYNTAX       Unsigned64
    MAX-ACCESS   read-only
    STATUS       current
    DESCRIPTION
        "Cisco UCS adaptor:EthPortOutsizedStats:oversizedBadCrcPacketsDelt
        aMin managed object property"
    ::= { cucsAdaptorEthPortOutsizedStatsEntry 9 }

cucsAdaptorEthPortOutsizedStatsOversizedGoodCrcPackets OBJECT-TYPE
    SYNTAX       Unsigned64
    MAX-ACCESS   read-only
    STATUS       current
    DESCRIPTION
        "Cisco UCS adaptor:EthPortOutsizedStats:oversizedGoodCrcPackets
        managed object property"
    ::= { cucsAdaptorEthPortOutsizedStatsEntry 10 }

cucsAdaptorEthPortOutsizedStatsOversizedGoodCrcPacketsDelta OBJECT-TYPE
    SYNTAX       Counter64
    MAX-ACCESS   read-only
    STATUS       current
    DESCRIPTION
        "Cisco UCS adaptor:EthPortOutsizedStats:oversizedGoodCrcPacketsDel
        ta managed object property"
    ::= { cucsAdaptorEthPortOutsizedStatsEntry 11 }

cucsAdaptorEthPortOutsizedStatsOversizedGoodCrcPacketsDeltaAvg OBJECT-TYPE
    SYNTAX       Unsigned64
    MAX-ACCESS   read-only
    STATUS       current
    DESCRIPTION
        "Cisco UCS adaptor:EthPortOutsizedStats:oversizedGoodCrcPacketsDel
        taAvg managed object property"
    ::= { cucsAdaptorEthPortOutsizedStatsEntry 12 }

cucsAdaptorEthPortOutsizedStatsOversizedGoodCrcPacketsDeltaMax OBJECT-TYPE
    SYNTAX       Unsigned64
    MAX-ACCESS   read-only
    STATUS       current
    DESCRIPTION
        "Cisco UCS adaptor:EthPortOutsizedStats:oversizedGoodCrcPacketsDel
        taMax managed object property"
    ::= { cucsAdaptorEthPortOutsizedStatsEntry 13 }

cucsAdaptorEthPortOutsizedStatsOversizedGoodCrcPacketsDeltaMin OBJECT-TYPE
    SYNTAX       Unsigned64
    MAX-ACCESS   read-only
    STATUS       current
    DESCRIPTION
        "Cisco UCS adaptor:EthPortOutsizedStats:oversizedGoodCrcPacketsDel
        taMin managed object property"
    ::= { cucsAdaptorEthPortOutsizedStatsEntry 14 }

cucsAdaptorEthPortOutsizedStatsOversizedPackets OBJECT-TYPE
    SYNTAX       Unsigned64
    MAX-ACCESS   read-only
    STATUS       current
    DESCRIPTION
        "Cisco UCS adaptor:EthPortOutsizedStats:oversizedPackets
        managed object property"
    ::= { cucsAdaptorEthPortOutsizedStatsEntry 15 }

cucsAdaptorEthPortOutsizedStatsOversizedPacketsDelta OBJECT-TYPE
    SYNTAX       Counter64
    MAX-ACCESS   read-only
    STATUS       current
    DESCRIPTION
        "Cisco UCS adaptor:EthPortOutsizedStats:oversizedPacketsDelta
        managed object property"
    ::= { cucsAdaptorEthPortOutsizedStatsEntry 16 }

cucsAdaptorEthPortOutsizedStatsOversizedPacketsDeltaAvg OBJECT-TYPE
    SYNTAX       Unsigned64
    MAX-ACCESS   read-only
    STATUS       current
    DESCRIPTION
        "Cisco UCS adaptor:EthPortOutsizedStats:oversizedPacketsDeltaAvg
        managed object property"
    ::= { cucsAdaptorEthPortOutsizedStatsEntry 17 }

cucsAdaptorEthPortOutsizedStatsOversizedPacketsDeltaMax OBJECT-TYPE
    SYNTAX       Unsigned64
    MAX-ACCESS   read-only
    STATUS       current
    DESCRIPTION
        "Cisco UCS adaptor:EthPortOutsizedStats:oversizedPacketsDeltaMax
        managed object property"
    ::= { cucsAdaptorEthPortOutsizedStatsEntry 18 }

cucsAdaptorEthPortOutsizedStatsOversizedPacketsDeltaMin OBJECT-TYPE
    SYNTAX       Unsigned64
    MAX-ACCESS   read-only
    STATUS       current
    DESCRIPTION
        "Cisco UCS adaptor:EthPortOutsizedStats:oversizedPacketsDeltaMin
        managed object property"
    ::= { cucsAdaptorEthPortOutsizedStatsEntry 19 }

cucsAdaptorEthPortOutsizedStatsSuspect OBJECT-TYPE
    SYNTAX       TruthValue
    MAX-ACCESS   read-only
    STATUS       current
    DESCRIPTION
        "Cisco UCS adaptor:EthPortOutsizedStats:suspect
        managed object property"
    ::= { cucsAdaptorEthPortOutsizedStatsEntry 20 }

cucsAdaptorEthPortOutsizedStatsThresholded OBJECT-TYPE
    SYNTAX       CucsAdaptorEthPortOutsizedStatsThresholded
    MAX-ACCESS   read-only
    STATUS       current
    DESCRIPTION
        "Cisco UCS adaptor:EthPortOutsizedStats:thresholded
        managed object property"
    ::= { cucsAdaptorEthPortOutsizedStatsEntry 21 }

cucsAdaptorEthPortOutsizedStatsTimeCollected OBJECT-TYPE
    SYNTAX       DateAndTime
    MAX-ACCESS   read-only
    STATUS       current
    DESCRIPTION
        "Cisco UCS adaptor:EthPortOutsizedStats:timeCollected
        managed object property"
    ::= { cucsAdaptorEthPortOutsizedStatsEntry 22 }

cucsAdaptorEthPortOutsizedStatsTrafficDirection OBJECT-TYPE
    SYNTAX       CucsAdaptorAdapterStatsTrafficDir
    MAX-ACCESS   read-only
    STATUS       current
    DESCRIPTION
        "Cisco UCS adaptor:EthPortOutsizedStats:trafficDirection
        managed object property"
    ::= { cucsAdaptorEthPortOutsizedStatsEntry 23 }

cucsAdaptorEthPortOutsizedStatsUndersizedBadCrcPackets OBJECT-TYPE
    SYNTAX       Unsigned64
    MAX-ACCESS   read-only
    STATUS       current
    DESCRIPTION
        "Cisco UCS adaptor:EthPortOutsizedStats:undersizedBadCrcPackets
        managed object property"
    ::= { cucsAdaptorEthPortOutsizedStatsEntry 24 }

cucsAdaptorEthPortOutsizedStatsUndersizedBadCrcPacketsDelta OBJECT-TYPE
    SYNTAX       Counter64
    MAX-ACCESS   read-only
    STATUS       current
    DESCRIPTION
        "Cisco UCS adaptor:EthPortOutsizedStats:undersizedBadCrcPacketsDel
        ta managed object property"
    ::= { cucsAdaptorEthPortOutsizedStatsEntry 25 }

cucsAdaptorEthPortOutsizedStatsUndersizedBadCrcPacketsDeltaAvg OBJECT-TYPE
    SYNTAX       Unsigned64
    MAX-ACCESS   read-only
    STATUS       current
    DESCRIPTION
        "Cisco UCS adaptor:EthPortOutsizedStats:undersizedBadCrcPacketsDel
        taAvg managed object property"
    ::= { cucsAdaptorEthPortOutsizedStatsEntry 26 }

cucsAdaptorEthPortOutsizedStatsUndersizedBadCrcPacketsDeltaMax OBJECT-TYPE
    SYNTAX       Unsigned64
    MAX-ACCESS   read-only
    STATUS       current
    DESCRIPTION
        "Cisco UCS adaptor:EthPortOutsizedStats:undersizedBadCrcPacketsDel
        taMax managed object property"
    ::= { cucsAdaptorEthPortOutsizedStatsEntry 27 }

cucsAdaptorEthPortOutsizedStatsUndersizedBadCrcPacketsDeltaMin OBJECT-TYPE
    SYNTAX       Unsigned64
    MAX-ACCESS   read-only
    STATUS       current
    DESCRIPTION
        "Cisco UCS adaptor:EthPortOutsizedStats:undersizedBadCrcPacketsDel
        taMin managed object property"
    ::= { cucsAdaptorEthPortOutsizedStatsEntry 28 }

cucsAdaptorEthPortOutsizedStatsUndersizedGoodCrcPackets OBJECT-TYPE
    SYNTAX       Unsigned64
    MAX-ACCESS   read-only
    STATUS       current
    DESCRIPTION
        "Cisco UCS adaptor:EthPortOutsizedStats:undersizedGoodCrcPackets
        managed object property"
    ::= { cucsAdaptorEthPortOutsizedStatsEntry 29 }

cucsAdaptorEthPortOutsizedStatsUndersizedGoodCrcPacketsDelta OBJECT-TYPE
    SYNTAX       Counter64
    MAX-ACCESS   read-only
    STATUS       current
    DESCRIPTION
        "Cisco UCS adaptor:EthPortOutsizedStats:undersizedGoodCrcPacketsDe
        lta managed object property"
    ::= { cucsAdaptorEthPortOutsizedStatsEntry 30 }

cucsAdaptorEthPortOutsizedStatsUndersizedGoodCrcPacketsDeltaAvg OBJECT-TYPE
    SYNTAX       Unsigned64
    MAX-ACCESS   read-only
    STATUS       current
    DESCRIPTION
        "Cisco UCS adaptor:EthPortOutsizedStats:undersizedGoodCrcPacketsDe
        ltaAvg managed object property"
    ::= { cucsAdaptorEthPortOutsizedStatsEntry 31 }

cucsAdaptorEthPortOutsizedStatsUndersizedGoodCrcPacketsDeltaMax OBJECT-TYPE
    SYNTAX       Unsigned64
    MAX-ACCESS   read-only
    STATUS       current
    DESCRIPTION
        "Cisco UCS adaptor:EthPortOutsizedStats:undersizedGoodCrcPacketsDe
        ltaMax managed object property"
    ::= { cucsAdaptorEthPortOutsizedStatsEntry 32 }

cucsAdaptorEthPortOutsizedStatsUndersizedGoodCrcPacketsDeltaMin OBJECT-TYPE
    SYNTAX       Unsigned64
    MAX-ACCESS   read-only
    STATUS       current
    DESCRIPTION
        "Cisco UCS adaptor:EthPortOutsizedStats:undersizedGoodCrcPacketsDe
        ltaMin managed object property"
    ::= { cucsAdaptorEthPortOutsizedStatsEntry 33 }

cucsAdaptorEthPortOutsizedStatsUpdate OBJECT-TYPE
    SYNTAX       Gauge32
    MAX-ACCESS   read-only
    STATUS       current
    DESCRIPTION
        "Cisco UCS adaptor:EthPortOutsizedStats:update
        managed object property"
    ::= { cucsAdaptorEthPortOutsizedStatsEntry 34 }

cucsAdaptorEthPortOutsizedStatsHistTable OBJECT-TYPE
    SYNTAX           SEQUENCE OF CucsAdaptorEthPortOutsizedStatsHistEntry
    MAX-ACCESS       not-accessible
    STATUS           current
    DESCRIPTION
        "Cisco UCS adaptor:EthPortOutsizedStatsHist managed object table"
    ::= { cucsAdaptorObjects 16 }

cucsAdaptorEthPortOutsizedStatsHistEntry OBJECT-TYPE
    SYNTAX           CucsAdaptorEthPortOutsizedStatsHistEntry
    MAX-ACCESS       not-accessible
    STATUS           current
    DESCRIPTION
        "Entry for the cucsAdaptorEthPortOutsizedStatsHistTable table."
    INDEX { cucsAdaptorEthPortOutsizedStatsHistInstanceId }
    ::= { cucsAdaptorEthPortOutsizedStatsHistTable 1 }

CucsAdaptorEthPortOutsizedStatsHistEntry ::= SEQUENCE {
    cucsAdaptorEthPortOutsizedStatsHistInstanceId                    CucsManagedObjectId,
    cucsAdaptorEthPortOutsizedStatsHistDn                            CucsManagedObjectDn,
    cucsAdaptorEthPortOutsizedStatsHistRn                            SnmpAdminString,
    cucsAdaptorEthPortOutsizedStatsHistId                            Unsigned64,
    cucsAdaptorEthPortOutsizedStatsHistMostRecent                    TruthValue,
    cucsAdaptorEthPortOutsizedStatsHistOversizedBadCrcPackets        Unsigned64,
    cucsAdaptorEthPortOutsizedStatsHistOversizedBadCrcPacketsDelta   Unsigned64,
    cucsAdaptorEthPortOutsizedStatsHistOversizedBadCrcPktsDeltaAvg   Unsigned64,
    cucsAdaptorEthPortOutsizedStatsHistOversizedBadCrcPktsDeltaMax   Unsigned64,
    cucsAdaptorEthPortOutsizedStatsHistOversizedBadCrcPktsDeltaMin   Unsigned64,
    cucsAdaptorEthPortOutsizedStatsHistOversizedGoodCrcPackets       Unsigned64,
    cucsAdaptorEthPortOutsizedStatsHistOversizedGoodCrcPacketsDelta  Unsigned64,
    cucsAdaptorEthPortOutsizedStatsHistOversizedGoodCrcPktsDeltaAvg  Unsigned64,
    cucsAdaptorEthPortOutsizedStatsHistOversizedGoodCrcPktsDeltaMax  Unsigned64,
    cucsAdaptorEthPortOutsizedStatsHistOversizedGoodCrcPktsDeltaMin  Unsigned64,
    cucsAdaptorEthPortOutsizedStatsHistOversizedPackets              Unsigned64,
    cucsAdaptorEthPortOutsizedStatsHistOversizedPacketsDelta         Unsigned64,
    cucsAdaptorEthPortOutsizedStatsHistOversizedPacketsDeltaAvg      Unsigned64,
    cucsAdaptorEthPortOutsizedStatsHistOversizedPacketsDeltaMax      Unsigned64,
    cucsAdaptorEthPortOutsizedStatsHistOversizedPacketsDeltaMin      Unsigned64,
    cucsAdaptorEthPortOutsizedStatsHistSuspect                       TruthValue,
    cucsAdaptorEthPortOutsizedStatsHistThresholded                   CucsAdaptorEthPortOutsizedStatsHistThresholded,
    cucsAdaptorEthPortOutsizedStatsHistTimeCollected                 DateAndTime,
    cucsAdaptorEthPortOutsizedStatsHistUndersizedBadCrcPackets       Unsigned64,
    cucsAdaptorEthPortOutsizedStatsHistUndersizedBadCrcPacketsDelta  Unsigned64,
    cucsAdaptorEthPortOutsizedStatsHistUndersizedBadCrcPktsDeltaAvg  Unsigned64,
    cucsAdaptorEthPortOutsizedStatsHistUndersizedBadCrcPktsDeltaMax  Unsigned64,
    cucsAdaptorEthPortOutsizedStatsHistUndersizedBadCrcPktsDeltaMin  Unsigned64,
    cucsAdaptorEthPortOutsizedStatsHistUndersizedGoodCrcPackets      Unsigned64,
    cucsAdaptorEthPortOutsizedStatsHistUndersizedGoodCrcPacketsDelta Unsigned64,
    cucsAdaptorEthPortOutsizedStatsHistUndersizedGoodCrcPktsDeltaAvg Unsigned64,
    cucsAdaptorEthPortOutsizedStatsHistUndersizedGoodCrcPktsDeltaMax Unsigned64,
    cucsAdaptorEthPortOutsizedStatsHistUndersizedGoodCrcPktsDeltaMin Unsigned64
}

cucsAdaptorEthPortOutsizedStatsHistInstanceId OBJECT-TYPE
    SYNTAX       CucsManagedObjectId
    MAX-ACCESS   not-accessible
    STATUS       current
    DESCRIPTION
        "Instance identifier of the managed object."
    ::= { cucsAdaptorEthPortOutsizedStatsHistEntry 1 }

cucsAdaptorEthPortOutsizedStatsHistDn OBJECT-TYPE
    SYNTAX       CucsManagedObjectDn
    MAX-ACCESS   read-only
    STATUS       current
    DESCRIPTION
        "Cisco UCS adaptor:EthPortOutsizedStatsHist:dn
        managed object property"
    ::= { cucsAdaptorEthPortOutsizedStatsHistEntry 2 }

cucsAdaptorEthPortOutsizedStatsHistRn OBJECT-TYPE
    SYNTAX       SnmpAdminString
    MAX-ACCESS   read-only
    STATUS       current
    DESCRIPTION
        "Cisco UCS adaptor:EthPortOutsizedStatsHist:rn
        managed object property"
    ::= { cucsAdaptorEthPortOutsizedStatsHistEntry 3 }

cucsAdaptorEthPortOutsizedStatsHistId OBJECT-TYPE
    SYNTAX       Unsigned64
    MAX-ACCESS   read-only
    STATUS       current
    DESCRIPTION
        "Cisco UCS adaptor:EthPortOutsizedStatsHist:id
        managed object property"
    ::= { cucsAdaptorEthPortOutsizedStatsHistEntry 4 }

cucsAdaptorEthPortOutsizedStatsHistMostRecent OBJECT-TYPE
    SYNTAX       TruthValue
    MAX-ACCESS   read-only
    STATUS       current
    DESCRIPTION
        "Cisco UCS adaptor:EthPortOutsizedStatsHist:mostRecent
        managed object property"
    ::= { cucsAdaptorEthPortOutsizedStatsHistEntry 5 }

cucsAdaptorEthPortOutsizedStatsHistOversizedBadCrcPackets OBJECT-TYPE
    SYNTAX       Unsigned64
    MAX-ACCESS   read-only
    STATUS       current
    DESCRIPTION
        "Cisco UCS adaptor:EthPortOutsizedStatsHist:oversizedBadCrcPackets
         managed object property"
    ::= { cucsAdaptorEthPortOutsizedStatsHistEntry 6 }

cucsAdaptorEthPortOutsizedStatsHistOversizedBadCrcPacketsDelta OBJECT-TYPE
    SYNTAX       Unsigned64
    MAX-ACCESS   read-only
    STATUS       current
    DESCRIPTION
        "Cisco UCS adaptor:EthPortOutsizedStatsHist:oversizedBadCrcPackets
        Delta managed object property"
    ::= { cucsAdaptorEthPortOutsizedStatsHistEntry 7 }

cucsAdaptorEthPortOutsizedStatsHistOversizedBadCrcPktsDeltaAvg OBJECT-TYPE
    SYNTAX       Unsigned64
    MAX-ACCESS   read-only
    STATUS       current
    DESCRIPTION
        "Cisco UCS adaptor:EthPortOutsizedStatsHist:oversizedBadCrcPackets
        DeltaAvg managed object property"
    ::= { cucsAdaptorEthPortOutsizedStatsHistEntry 8 }

cucsAdaptorEthPortOutsizedStatsHistOversizedBadCrcPktsDeltaMax OBJECT-TYPE
    SYNTAX       Unsigned64
    MAX-ACCESS   read-only
    STATUS       current
    DESCRIPTION
        "Cisco UCS adaptor:EthPortOutsizedStatsHist:oversizedBadCrcPackets
        DeltaMax managed object property"
    ::= { cucsAdaptorEthPortOutsizedStatsHistEntry 9 }

cucsAdaptorEthPortOutsizedStatsHistOversizedBadCrcPktsDeltaMin OBJECT-TYPE
    SYNTAX       Unsigned64
    MAX-ACCESS   read-only
    STATUS       current
    DESCRIPTION
        "Cisco UCS adaptor:EthPortOutsizedStatsHist:oversizedBadCrcPackets
        DeltaMin managed object property"
    ::= { cucsAdaptorEthPortOutsizedStatsHistEntry 10 }

cucsAdaptorEthPortOutsizedStatsHistOversizedGoodCrcPackets OBJECT-TYPE
    SYNTAX       Unsigned64
    MAX-ACCESS   read-only
    STATUS       current
    DESCRIPTION
        "Cisco UCS adaptor:EthPortOutsizedStatsHist:oversizedGoodCrcPacket
        s managed object property"
    ::= { cucsAdaptorEthPortOutsizedStatsHistEntry 11 }

cucsAdaptorEthPortOutsizedStatsHistOversizedGoodCrcPacketsDelta OBJECT-TYPE
    SYNTAX       Unsigned64
    MAX-ACCESS   read-only
    STATUS       current
    DESCRIPTION
        "Cisco UCS adaptor:EthPortOutsizedStatsHist:oversizedGoodCrcPacket
        sDelta managed object property"
    ::= { cucsAdaptorEthPortOutsizedStatsHistEntry 12 }

cucsAdaptorEthPortOutsizedStatsHistOversizedGoodCrcPktsDeltaAvg OBJECT-TYPE
    SYNTAX       Unsigned64
    MAX-ACCESS   read-only
    STATUS       current
    DESCRIPTION
        "Cisco UCS adaptor:EthPortOutsizedStatsHist:oversizedGoodCrcPacket
        sDeltaAvg managed object property"
    ::= { cucsAdaptorEthPortOutsizedStatsHistEntry 13 }

cucsAdaptorEthPortOutsizedStatsHistOversizedGoodCrcPktsDeltaMax OBJECT-TYPE
    SYNTAX       Unsigned64
    MAX-ACCESS   read-only
    STATUS       current
    DESCRIPTION
        "Cisco UCS adaptor:EthPortOutsizedStatsHist:oversizedGoodCrcPacket
        sDeltaMax managed object property"
    ::= { cucsAdaptorEthPortOutsizedStatsHistEntry 14 }

cucsAdaptorEthPortOutsizedStatsHistOversizedGoodCrcPktsDeltaMin OBJECT-TYPE
    SYNTAX       Unsigned64
    MAX-ACCESS   read-only
    STATUS       current
    DESCRIPTION
        "Cisco UCS adaptor:EthPortOutsizedStatsHist:oversizedGoodCrcPacket
        sDeltaMin managed object property"
    ::= { cucsAdaptorEthPortOutsizedStatsHistEntry 15 }

cucsAdaptorEthPortOutsizedStatsHistOversizedPackets OBJECT-TYPE
    SYNTAX       Unsigned64
    MAX-ACCESS   read-only
    STATUS       current
    DESCRIPTION
        "Cisco UCS adaptor:EthPortOutsizedStatsHist:oversizedPackets
        managed object property"
    ::= { cucsAdaptorEthPortOutsizedStatsHistEntry 16 }

cucsAdaptorEthPortOutsizedStatsHistOversizedPacketsDelta OBJECT-TYPE
    SYNTAX       Unsigned64
    MAX-ACCESS   read-only
    STATUS       current
    DESCRIPTION
        "Cisco UCS adaptor:EthPortOutsizedStatsHist:oversizedPacketsDelta
        managed object property"
    ::= { cucsAdaptorEthPortOutsizedStatsHistEntry 17 }

cucsAdaptorEthPortOutsizedStatsHistOversizedPacketsDeltaAvg OBJECT-TYPE
    SYNTAX       Unsigned64
    MAX-ACCESS   read-only
    STATUS       current
    DESCRIPTION
        "Cisco UCS adaptor:EthPortOutsizedStatsHist:oversizedPacketsDeltaA
        vg managed object property"
    ::= { cucsAdaptorEthPortOutsizedStatsHistEntry 18 }

cucsAdaptorEthPortOutsizedStatsHistOversizedPacketsDeltaMax OBJECT-TYPE
    SYNTAX       Unsigned64
    MAX-ACCESS   read-only
    STATUS       current
    DESCRIPTION
        "Cisco UCS adaptor:EthPortOutsizedStatsHist:oversizedPacketsDeltaM
        ax managed object property"
    ::= { cucsAdaptorEthPortOutsizedStatsHistEntry 19 }

cucsAdaptorEthPortOutsizedStatsHistOversizedPacketsDeltaMin OBJECT-TYPE
    SYNTAX       Unsigned64
    MAX-ACCESS   read-only
    STATUS       current
    DESCRIPTION
        "Cisco UCS adaptor:EthPortOutsizedStatsHist:oversizedPacketsDeltaM
        in managed object property"
    ::= { cucsAdaptorEthPortOutsizedStatsHistEntry 20 }

cucsAdaptorEthPortOutsizedStatsHistSuspect OBJECT-TYPE
    SYNTAX       TruthValue
    MAX-ACCESS   read-only
    STATUS       current
    DESCRIPTION
        "Cisco UCS adaptor:EthPortOutsizedStatsHist:suspect
        managed object property"
    ::= { cucsAdaptorEthPortOutsizedStatsHistEntry 21 }

cucsAdaptorEthPortOutsizedStatsHistThresholded OBJECT-TYPE
    SYNTAX       CucsAdaptorEthPortOutsizedStatsHistThresholded
    MAX-ACCESS   read-only
    STATUS       current
    DESCRIPTION
        "Cisco UCS adaptor:EthPortOutsizedStatsHist:thresholded
        managed object property"
    ::= { cucsAdaptorEthPortOutsizedStatsHistEntry 22 }

cucsAdaptorEthPortOutsizedStatsHistTimeCollected OBJECT-TYPE
    SYNTAX       DateAndTime
    MAX-ACCESS   read-only
    STATUS       current
    DESCRIPTION
        "Cisco UCS adaptor:EthPortOutsizedStatsHist:timeCollected
        managed object property"
    ::= { cucsAdaptorEthPortOutsizedStatsHistEntry 23 }

cucsAdaptorEthPortOutsizedStatsHistUndersizedBadCrcPackets OBJECT-TYPE
    SYNTAX       Unsigned64
    MAX-ACCESS   read-only
    STATUS       current
    DESCRIPTION
        "Cisco UCS adaptor:EthPortOutsizedStatsHist:undersizedBadCrcPacket
        s managed object property"
    ::= { cucsAdaptorEthPortOutsizedStatsHistEntry 24 }

cucsAdaptorEthPortOutsizedStatsHistUndersizedBadCrcPacketsDelta OBJECT-TYPE
    SYNTAX       Unsigned64
    MAX-ACCESS   read-only
    STATUS       current
    DESCRIPTION
        "Cisco UCS adaptor:EthPortOutsizedStatsHist:undersizedBadCrcPacket
        sDelta managed object property"
    ::= { cucsAdaptorEthPortOutsizedStatsHistEntry 25 }

cucsAdaptorEthPortOutsizedStatsHistUndersizedBadCrcPktsDeltaAvg OBJECT-TYPE
    SYNTAX       Unsigned64
    MAX-ACCESS   read-only
    STATUS       current
    DESCRIPTION
        "Cisco UCS adaptor:EthPortOutsizedStatsHist:undersizedBadCrcPacket
        sDeltaAvg managed object property"
    ::= { cucsAdaptorEthPortOutsizedStatsHistEntry 26 }

cucsAdaptorEthPortOutsizedStatsHistUndersizedBadCrcPktsDeltaMax OBJECT-TYPE
    SYNTAX       Unsigned64
    MAX-ACCESS   read-only
    STATUS       current
    DESCRIPTION
        "Cisco UCS adaptor:EthPortOutsizedStatsHist:undersizedBadCrcPacket
        sDeltaMax managed object property"
    ::= { cucsAdaptorEthPortOutsizedStatsHistEntry 27 }

cucsAdaptorEthPortOutsizedStatsHistUndersizedBadCrcPktsDeltaMin OBJECT-TYPE
    SYNTAX       Unsigned64
    MAX-ACCESS   read-only
    STATUS       current
    DESCRIPTION
        "Cisco UCS adaptor:EthPortOutsizedStatsHist:undersizedBadCrcPacket
        sDeltaMin managed object property"
    ::= { cucsAdaptorEthPortOutsizedStatsHistEntry 28 }

cucsAdaptorEthPortOutsizedStatsHistUndersizedGoodCrcPackets OBJECT-TYPE
    SYNTAX       Unsigned64
    MAX-ACCESS   read-only
    STATUS       current
    DESCRIPTION
        "Cisco UCS adaptor:EthPortOutsizedStatsHist:undersizedGoodCrcPacke
        ts managed object property"
    ::= { cucsAdaptorEthPortOutsizedStatsHistEntry 29 }

cucsAdaptorEthPortOutsizedStatsHistUndersizedGoodCrcPacketsDelta OBJECT-TYPE
    SYNTAX       Unsigned64
    MAX-ACCESS   read-only
    STATUS       current
    DESCRIPTION
        "Cisco UCS adaptor:EthPortOutsizedStatsHist:undersizedGoodCrcPacke
        tsDelta managed object property"
    ::= { cucsAdaptorEthPortOutsizedStatsHistEntry 30 }

cucsAdaptorEthPortOutsizedStatsHistUndersizedGoodCrcPktsDeltaAvg OBJECT-TYPE
    SYNTAX       Unsigned64
    MAX-ACCESS   read-only
    STATUS       current
    DESCRIPTION
        "Cisco UCS adaptor:EthPortOutsizedStatsHist:undersizedGoodCrcPacke
        tsDeltaAvg managed object property"
    ::= { cucsAdaptorEthPortOutsizedStatsHistEntry 31 }

cucsAdaptorEthPortOutsizedStatsHistUndersizedGoodCrcPktsDeltaMax OBJECT-TYPE
    SYNTAX       Unsigned64
    MAX-ACCESS   read-only
    STATUS       current
    DESCRIPTION
        "Cisco UCS adaptor:EthPortOutsizedStatsHist:undersizedGoodCrcPacke
        tsDeltaMax managed object property"
    ::= { cucsAdaptorEthPortOutsizedStatsHistEntry 32 }

cucsAdaptorEthPortOutsizedStatsHistUndersizedGoodCrcPktsDeltaMin OBJECT-TYPE
    SYNTAX       Unsigned64
    MAX-ACCESS   read-only
    STATUS       current
    DESCRIPTION
        "Cisco UCS adaptor:EthPortOutsizedStatsHist:undersizedGoodCrcPacke
        tsDeltaMin managed object property"
    ::= { cucsAdaptorEthPortOutsizedStatsHistEntry 33 }

cucsAdaptorEthPortStatsTable OBJECT-TYPE
    SYNTAX           SEQUENCE OF CucsAdaptorEthPortStatsEntry
    MAX-ACCESS       not-accessible
    STATUS           current
    DESCRIPTION
        "Cisco UCS adaptor:EthPortStats managed object table"
    ::= { cucsAdaptorObjects 17 }

cucsAdaptorEthPortStatsEntry OBJECT-TYPE
    SYNTAX           CucsAdaptorEthPortStatsEntry
    MAX-ACCESS       not-accessible
    STATUS           current
    DESCRIPTION
        "Entry for the cucsAdaptorEthPortStatsTable table."
    INDEX { cucsAdaptorEthPortStatsInstanceId }
    ::= { cucsAdaptorEthPortStatsTable 1 }

CucsAdaptorEthPortStatsEntry ::= SEQUENCE {
    cucsAdaptorEthPortStatsInstanceId                                CucsManagedObjectId,
    cucsAdaptorEthPortStatsDn                                        CucsManagedObjectDn,
    cucsAdaptorEthPortStatsRn                                        SnmpAdminString,
    cucsAdaptorEthPortStatsGoodPackets                               Unsigned64,
    cucsAdaptorEthPortStatsGoodPacketsDelta                          Counter64,
    cucsAdaptorEthPortStatsGoodPacketsDeltaAvg                       Unsigned64,
    cucsAdaptorEthPortStatsGoodPacketsDeltaMax                       Unsigned64,
    cucsAdaptorEthPortStatsGoodPacketsDeltaMin                       Unsigned64,
    cucsAdaptorEthPortStatsIntervals                                 Gauge32,
    cucsAdaptorEthPortStatsPausePackets                              Unsigned64,
    cucsAdaptorEthPortStatsPausePacketsDelta                         Counter64,
    cucsAdaptorEthPortStatsPausePacketsDeltaAvg                      Unsigned64,
    cucsAdaptorEthPortStatsPausePacketsDeltaMax                      Unsigned64,
    cucsAdaptorEthPortStatsPausePacketsDeltaMin                      Unsigned64,
    cucsAdaptorEthPortStatsPerPriorityPausePackets                   Unsigned64,
    cucsAdaptorEthPortStatsPerPriorityPausePacketsDelta              Counter64,
    cucsAdaptorEthPortStatsPerPriorityPausePacketsDeltaAvg           Unsigned64,
    cucsAdaptorEthPortStatsPerPriorityPausePacketsDeltaMax           Unsigned64,
    cucsAdaptorEthPortStatsPerPriorityPausePacketsDeltaMin           Unsigned64,
    cucsAdaptorEthPortStatsPppPackets                                Unsigned64,
    cucsAdaptorEthPortStatsPppPacketsDelta                           Counter64,
    cucsAdaptorEthPortStatsPppPacketsDeltaAvg                        Unsigned64,
    cucsAdaptorEthPortStatsPppPacketsDeltaMax                        Unsigned64,
    cucsAdaptorEthPortStatsPppPacketsDeltaMin                        Unsigned64,
    cucsAdaptorEthPortStatsSuspect                                   TruthValue,
    cucsAdaptorEthPortStatsThresholded                               CucsAdaptorEthPortStatsThresholded,
    cucsAdaptorEthPortStatsTimeCollected                             DateAndTime,
    cucsAdaptorEthPortStatsTotalPackets                              Unsigned64,
    cucsAdaptorEthPortStatsTotalPacketsDelta                         Counter64,
    cucsAdaptorEthPortStatsTotalPacketsDeltaAvg                      Unsigned64,
    cucsAdaptorEthPortStatsTotalPacketsDeltaMax                      Unsigned64,
    cucsAdaptorEthPortStatsTotalPacketsDeltaMin                      Unsigned64,
    cucsAdaptorEthPortStatsTrafficDirection                          CucsAdaptorAdapterStatsTrafficDir,
    cucsAdaptorEthPortStatsUpdate                                    Gauge32,
    cucsAdaptorEthPortStatsVlanPackets                               Unsigned64,
    cucsAdaptorEthPortStatsVlanPacketsDelta                          Counter64,
    cucsAdaptorEthPortStatsVlanPacketsDeltaAvg                       Unsigned64,
    cucsAdaptorEthPortStatsVlanPacketsDeltaMax                       Unsigned64,
    cucsAdaptorEthPortStatsVlanPacketsDeltaMin                       Unsigned64
}

cucsAdaptorEthPortStatsInstanceId OBJECT-TYPE
    SYNTAX       CucsManagedObjectId
    MAX-ACCESS   not-accessible
    STATUS       current
    DESCRIPTION
        "Instance identifier of the managed object."
    ::= { cucsAdaptorEthPortStatsEntry 1 }

cucsAdaptorEthPortStatsDn OBJECT-TYPE
    SYNTAX       CucsManagedObjectDn
    MAX-ACCESS   read-only
    STATUS       current
    DESCRIPTION
        "Cisco UCS adaptor:EthPortStats:dn managed object property"
    ::= { cucsAdaptorEthPortStatsEntry 2 }

cucsAdaptorEthPortStatsRn OBJECT-TYPE
    SYNTAX       SnmpAdminString
    MAX-ACCESS   read-only
    STATUS       current
    DESCRIPTION
        "Cisco UCS adaptor:EthPortStats:rn managed object property"
    ::= { cucsAdaptorEthPortStatsEntry 3 }

cucsAdaptorEthPortStatsGoodPackets OBJECT-TYPE
    SYNTAX       Unsigned64
    MAX-ACCESS   read-only
    STATUS       current
    DESCRIPTION
        "Cisco UCS adaptor:EthPortStats:goodPackets managed
        object property"
    ::= { cucsAdaptorEthPortStatsEntry 4 }

cucsAdaptorEthPortStatsGoodPacketsDelta OBJECT-TYPE
    SYNTAX       Counter64
    MAX-ACCESS   read-only
    STATUS       current
    DESCRIPTION
        "Cisco UCS adaptor:EthPortStats:goodPacketsDelta
        managed object property"
    ::= { cucsAdaptorEthPortStatsEntry 5 }

cucsAdaptorEthPortStatsGoodPacketsDeltaAvg OBJECT-TYPE
    SYNTAX       Unsigned64
    MAX-ACCESS   read-only
    STATUS       current
    DESCRIPTION
        "Cisco UCS adaptor:EthPortStats:goodPacketsDeltaAvg
        managed object property"
    ::= { cucsAdaptorEthPortStatsEntry 6 }

cucsAdaptorEthPortStatsGoodPacketsDeltaMax OBJECT-TYPE
    SYNTAX       Unsigned64
    MAX-ACCESS   read-only
    STATUS       current
    DESCRIPTION
        "Cisco UCS adaptor:EthPortStats:goodPacketsDeltaMax
        managed object property"
    ::= { cucsAdaptorEthPortStatsEntry 7 }

cucsAdaptorEthPortStatsGoodPacketsDeltaMin OBJECT-TYPE
    SYNTAX       Unsigned64
    MAX-ACCESS   read-only
    STATUS       current
    DESCRIPTION
        "Cisco UCS adaptor:EthPortStats:goodPacketsDeltaMin
        managed object property"
    ::= { cucsAdaptorEthPortStatsEntry 8 }

cucsAdaptorEthPortStatsIntervals OBJECT-TYPE
    SYNTAX       Gauge32
    MAX-ACCESS   read-only
    STATUS       current
    DESCRIPTION
        "Cisco UCS adaptor:EthPortStats:intervals managed object property"
    ::= { cucsAdaptorEthPortStatsEntry 9 }

cucsAdaptorEthPortStatsPausePackets OBJECT-TYPE
    SYNTAX       Unsigned64
    MAX-ACCESS   read-only
    STATUS       current
    DESCRIPTION
        "Cisco UCS adaptor:EthPortStats:pausePackets managed
        object property"
    ::= { cucsAdaptorEthPortStatsEntry 10 }

cucsAdaptorEthPortStatsPausePacketsDelta OBJECT-TYPE
    SYNTAX       Counter64
    MAX-ACCESS   read-only
    STATUS       current
    DESCRIPTION
        "Cisco UCS adaptor:EthPortStats:pausePacketsDelta
        managed object property"
    ::= { cucsAdaptorEthPortStatsEntry 11 }

cucsAdaptorEthPortStatsPausePacketsDeltaAvg OBJECT-TYPE
    SYNTAX       Unsigned64
    MAX-ACCESS   read-only
    STATUS       current
    DESCRIPTION
        "Cisco UCS adaptor:EthPortStats:pausePacketsDeltaAvg
        managed object property"
    ::= { cucsAdaptorEthPortStatsEntry 12 }

cucsAdaptorEthPortStatsPausePacketsDeltaMax OBJECT-TYPE
    SYNTAX       Unsigned64
    MAX-ACCESS   read-only
    STATUS       current
    DESCRIPTION
        "Cisco UCS adaptor:EthPortStats:pausePacketsDeltaMax
        managed object property"
    ::= { cucsAdaptorEthPortStatsEntry 13 }

cucsAdaptorEthPortStatsPausePacketsDeltaMin OBJECT-TYPE
    SYNTAX       Unsigned64
    MAX-ACCESS   read-only
    STATUS       current
    DESCRIPTION
        "Cisco UCS adaptor:EthPortStats:pausePacketsDeltaMin
        managed object property"
    ::= { cucsAdaptorEthPortStatsEntry 14 }

cucsAdaptorEthPortStatsPerPriorityPausePackets OBJECT-TYPE
    SYNTAX       Unsigned64
    MAX-ACCESS   read-only
    STATUS       current
    DESCRIPTION
        "Cisco UCS adaptor:EthPortStats:perPriorityPausePackets
        managed object property"
    ::= { cucsAdaptorEthPortStatsEntry 15 }

cucsAdaptorEthPortStatsPerPriorityPausePacketsDelta OBJECT-TYPE
    SYNTAX       Counter64
    MAX-ACCESS   read-only
    STATUS       current
    DESCRIPTION
        "Cisco UCS adaptor:EthPortStats:perPriorityPausePacketsDelta
        managed object property"
    ::= { cucsAdaptorEthPortStatsEntry 16 }

cucsAdaptorEthPortStatsPerPriorityPausePacketsDeltaAvg OBJECT-TYPE
    SYNTAX       Unsigned64
    MAX-ACCESS   read-only
    STATUS       current
    DESCRIPTION
        "Cisco UCS adaptor:EthPortStats:perPriorityPausePacketsDeltaAvg
        managed object property"
    ::= { cucsAdaptorEthPortStatsEntry 17 }

cucsAdaptorEthPortStatsPerPriorityPausePacketsDeltaMax OBJECT-TYPE
    SYNTAX       Unsigned64
    MAX-ACCESS   read-only
    STATUS       current
    DESCRIPTION
        "Cisco UCS adaptor:EthPortStats:perPriorityPausePacketsDeltaMax
        managed object property"
    ::= { cucsAdaptorEthPortStatsEntry 18 }

cucsAdaptorEthPortStatsPerPriorityPausePacketsDeltaMin OBJECT-TYPE
    SYNTAX       Unsigned64
    MAX-ACCESS   read-only
    STATUS       current
    DESCRIPTION
        "Cisco UCS adaptor:EthPortStats:perPriorityPausePacketsDeltaMin
        managed object property"
    ::= { cucsAdaptorEthPortStatsEntry 19 }

cucsAdaptorEthPortStatsPppPackets OBJECT-TYPE
    SYNTAX       Unsigned64
    MAX-ACCESS   read-only
    STATUS       current
    DESCRIPTION
        "Cisco UCS adaptor:EthPortStats:pppPackets managed
        object property"
    ::= { cucsAdaptorEthPortStatsEntry 20 }

cucsAdaptorEthPortStatsPppPacketsDelta OBJECT-TYPE
    SYNTAX       Counter64
    MAX-ACCESS   read-only
    STATUS       current
    DESCRIPTION
        "Cisco UCS adaptor:EthPortStats:pppPacketsDelta
        managed object property"
    ::= { cucsAdaptorEthPortStatsEntry 21 }

cucsAdaptorEthPortStatsPppPacketsDeltaAvg OBJECT-TYPE
    SYNTAX       Unsigned64
    MAX-ACCESS   read-only
    STATUS       current
    DESCRIPTION
        "Cisco UCS adaptor:EthPortStats:pppPacketsDeltaAvg
        managed object property"
    ::= { cucsAdaptorEthPortStatsEntry 22 }

cucsAdaptorEthPortStatsPppPacketsDeltaMax OBJECT-TYPE
    SYNTAX       Unsigned64
    MAX-ACCESS   read-only
    STATUS       current
    DESCRIPTION
        "Cisco UCS adaptor:EthPortStats:pppPacketsDeltaMax
        managed object property"
    ::= { cucsAdaptorEthPortStatsEntry 23 }

cucsAdaptorEthPortStatsPppPacketsDeltaMin OBJECT-TYPE
    SYNTAX       Unsigned64
    MAX-ACCESS   read-only
    STATUS       current
    DESCRIPTION
        "Cisco UCS adaptor:EthPortStats:pppPacketsDeltaMin
        managed object property"
    ::= { cucsAdaptorEthPortStatsEntry 24 }

cucsAdaptorEthPortStatsSuspect OBJECT-TYPE
    SYNTAX       TruthValue
    MAX-ACCESS   read-only
    STATUS       current
    DESCRIPTION
        "Cisco UCS adaptor:EthPortStats:suspect managed object property"
    ::= { cucsAdaptorEthPortStatsEntry 25 }

cucsAdaptorEthPortStatsThresholded OBJECT-TYPE
    SYNTAX       CucsAdaptorEthPortStatsThresholded
    MAX-ACCESS   read-only
    STATUS       current
    DESCRIPTION
        "Cisco UCS adaptor:EthPortStats:thresholded managed
        object property"
    ::= { cucsAdaptorEthPortStatsEntry 26 }

cucsAdaptorEthPortStatsTimeCollected OBJECT-TYPE
    SYNTAX       DateAndTime
    MAX-ACCESS   read-only
    STATUS       current
    DESCRIPTION
        "Cisco UCS adaptor:EthPortStats:timeCollected managed
        object property"
    ::= { cucsAdaptorEthPortStatsEntry 27 }

cucsAdaptorEthPortStatsTotalPackets OBJECT-TYPE
    SYNTAX       Unsigned64
    MAX-ACCESS   read-only
    STATUS       current
    DESCRIPTION
        "Cisco UCS adaptor:EthPortStats:totalPackets managed
        object property"
    ::= { cucsAdaptorEthPortStatsEntry 28 }

cucsAdaptorEthPortStatsTotalPacketsDelta OBJECT-TYPE
    SYNTAX       Counter64
    MAX-ACCESS   read-only
    STATUS       current
    DESCRIPTION
        "Cisco UCS adaptor:EthPortStats:totalPacketsDelta
        managed object property"
    ::= { cucsAdaptorEthPortStatsEntry 29 }

cucsAdaptorEthPortStatsTotalPacketsDeltaAvg OBJECT-TYPE
    SYNTAX       Unsigned64
    MAX-ACCESS   read-only
    STATUS       current
    DESCRIPTION
        "Cisco UCS adaptor:EthPortStats:totalPacketsDeltaAvg
        managed object property"
    ::= { cucsAdaptorEthPortStatsEntry 30 }

cucsAdaptorEthPortStatsTotalPacketsDeltaMax OBJECT-TYPE
    SYNTAX       Unsigned64
    MAX-ACCESS   read-only
    STATUS       current
    DESCRIPTION
        "Cisco UCS adaptor:EthPortStats:totalPacketsDeltaMax
        managed object property"
    ::= { cucsAdaptorEthPortStatsEntry 31 }

cucsAdaptorEthPortStatsTotalPacketsDeltaMin OBJECT-TYPE
    SYNTAX       Unsigned64
    MAX-ACCESS   read-only
    STATUS       current
    DESCRIPTION
        "Cisco UCS adaptor:EthPortStats:totalPacketsDeltaMin
        managed object property"
    ::= { cucsAdaptorEthPortStatsEntry 32 }

cucsAdaptorEthPortStatsTrafficDirection OBJECT-TYPE
    SYNTAX       CucsAdaptorAdapterStatsTrafficDir
    MAX-ACCESS   read-only
    STATUS       current
    DESCRIPTION
        "Cisco UCS adaptor:EthPortStats:trafficDirection
        managed object property"
    ::= { cucsAdaptorEthPortStatsEntry 33 }

cucsAdaptorEthPortStatsUpdate OBJECT-TYPE
    SYNTAX       Gauge32
    MAX-ACCESS   read-only
    STATUS       current
    DESCRIPTION
        "Cisco UCS adaptor:EthPortStats:update managed object property"
    ::= { cucsAdaptorEthPortStatsEntry 34 }

cucsAdaptorEthPortStatsVlanPackets OBJECT-TYPE
    SYNTAX       Unsigned64
    MAX-ACCESS   read-only
    STATUS       current
    DESCRIPTION
        "Cisco UCS adaptor:EthPortStats:vlanPackets managed
        object property"
    ::= { cucsAdaptorEthPortStatsEntry 35 }

cucsAdaptorEthPortStatsVlanPacketsDelta OBJECT-TYPE
    SYNTAX       Counter64
    MAX-ACCESS   read-only
    STATUS       current
    DESCRIPTION
        "Cisco UCS adaptor:EthPortStats:vlanPacketsDelta
        managed object property"
    ::= { cucsAdaptorEthPortStatsEntry 36 }

cucsAdaptorEthPortStatsVlanPacketsDeltaAvg OBJECT-TYPE
    SYNTAX       Unsigned64
    MAX-ACCESS   read-only
    STATUS       current
    DESCRIPTION
        "Cisco UCS adaptor:EthPortStats:vlanPacketsDeltaAvg
        managed object property"
    ::= { cucsAdaptorEthPortStatsEntry 37 }

cucsAdaptorEthPortStatsVlanPacketsDeltaMax OBJECT-TYPE
    SYNTAX       Unsigned64
    MAX-ACCESS   read-only
    STATUS       current
    DESCRIPTION
        "Cisco UCS adaptor:EthPortStats:vlanPacketsDeltaMax
        managed object property"
    ::= { cucsAdaptorEthPortStatsEntry 38 }

cucsAdaptorEthPortStatsVlanPacketsDeltaMin OBJECT-TYPE
    SYNTAX       Unsigned64
    MAX-ACCESS   read-only
    STATUS       current
    DESCRIPTION
        "Cisco UCS adaptor:EthPortStats:vlanPacketsDeltaMin
        managed object property"
    ::= { cucsAdaptorEthPortStatsEntry 39 }

cucsAdaptorEthPortStatsHistTable OBJECT-TYPE
    SYNTAX           SEQUENCE OF CucsAdaptorEthPortStatsHistEntry
    MAX-ACCESS       not-accessible
    STATUS           current
    DESCRIPTION
        "Cisco UCS adaptor:EthPortStatsHist managed object table"
    ::= { cucsAdaptorObjects 18 }

cucsAdaptorEthPortStatsHistEntry OBJECT-TYPE
    SYNTAX           CucsAdaptorEthPortStatsHistEntry
    MAX-ACCESS       not-accessible
    STATUS           current
    DESCRIPTION
        "Entry for the cucsAdaptorEthPortStatsHistTable table."
    INDEX { cucsAdaptorEthPortStatsHistInstanceId }
    ::= { cucsAdaptorEthPortStatsHistTable 1 }

CucsAdaptorEthPortStatsHistEntry ::= SEQUENCE {
    cucsAdaptorEthPortStatsHistInstanceId                            CucsManagedObjectId,
    cucsAdaptorEthPortStatsHistDn                                    CucsManagedObjectDn,
    cucsAdaptorEthPortStatsHistRn                                    SnmpAdminString,
    cucsAdaptorEthPortStatsHistGoodPackets                           Unsigned64,
    cucsAdaptorEthPortStatsHistGoodPacketsDelta                      Unsigned64,
    cucsAdaptorEthPortStatsHistGoodPacketsDeltaAvg                   Unsigned64,
    cucsAdaptorEthPortStatsHistGoodPacketsDeltaMax                   Unsigned64,
    cucsAdaptorEthPortStatsHistGoodPacketsDeltaMin                   Unsigned64,
    cucsAdaptorEthPortStatsHistId                                    Unsigned64,
    cucsAdaptorEthPortStatsHistMostRecent                            TruthValue,
    cucsAdaptorEthPortStatsHistPausePackets                          Unsigned64,
    cucsAdaptorEthPortStatsHistPausePacketsDelta                     Unsigned64,
    cucsAdaptorEthPortStatsHistPausePacketsDeltaAvg                  Unsigned64,
    cucsAdaptorEthPortStatsHistPausePacketsDeltaMax                  Unsigned64,
    cucsAdaptorEthPortStatsHistPausePacketsDeltaMin                  Unsigned64,
    cucsAdaptorEthPortStatsHistPerPriorityPausePackets               Unsigned64,
    cucsAdaptorEthPortStatsHistPerPriorityPausePacketsDelta          Unsigned64,
    cucsAdaptorEthPortStatsHistPerPriorityPausePacketsDeltaAvg       Unsigned64,
    cucsAdaptorEthPortStatsHistPerPriorityPausePacketsDeltaMax       Unsigned64,
    cucsAdaptorEthPortStatsHistPerPriorityPausePacketsDeltaMin       Unsigned64,
    cucsAdaptorEthPortStatsHistPppPackets                            Unsigned64,
    cucsAdaptorEthPortStatsHistPppPacketsDelta                       Unsigned64,
    cucsAdaptorEthPortStatsHistPppPacketsDeltaAvg                    Unsigned64,
    cucsAdaptorEthPortStatsHistPppPacketsDeltaMax                    Unsigned64,
    cucsAdaptorEthPortStatsHistPppPacketsDeltaMin                    Unsigned64,
    cucsAdaptorEthPortStatsHistSuspect                               TruthValue,
    cucsAdaptorEthPortStatsHistThresholded                           CucsAdaptorEthPortStatsHistThresholded,
    cucsAdaptorEthPortStatsHistTimeCollected                         DateAndTime,
    cucsAdaptorEthPortStatsHistTotalPackets                          Unsigned64,
    cucsAdaptorEthPortStatsHistTotalPacketsDelta                     Unsigned64,
    cucsAdaptorEthPortStatsHistTotalPacketsDeltaAvg                  Unsigned64,
    cucsAdaptorEthPortStatsHistTotalPacketsDeltaMax                  Unsigned64,
    cucsAdaptorEthPortStatsHistTotalPacketsDeltaMin                  Unsigned64,
    cucsAdaptorEthPortStatsHistVlanPackets                           Unsigned64,
    cucsAdaptorEthPortStatsHistVlanPacketsDelta                      Unsigned64,
    cucsAdaptorEthPortStatsHistVlanPacketsDeltaAvg                   Unsigned64,
    cucsAdaptorEthPortStatsHistVlanPacketsDeltaMax                   Unsigned64,
    cucsAdaptorEthPortStatsHistVlanPacketsDeltaMin                   Unsigned64
}

cucsAdaptorEthPortStatsHistInstanceId OBJECT-TYPE
    SYNTAX       CucsManagedObjectId
    MAX-ACCESS   not-accessible
    STATUS       current
    DESCRIPTION
        "Instance identifier of the managed object."
    ::= { cucsAdaptorEthPortStatsHistEntry 1 }

cucsAdaptorEthPortStatsHistDn OBJECT-TYPE
    SYNTAX       CucsManagedObjectDn
    MAX-ACCESS   read-only
    STATUS       current
    DESCRIPTION
        "Cisco UCS adaptor:EthPortStatsHist:dn managed object property"
    ::= { cucsAdaptorEthPortStatsHistEntry 2 }

cucsAdaptorEthPortStatsHistRn OBJECT-TYPE
    SYNTAX       SnmpAdminString
    MAX-ACCESS   read-only
    STATUS       current
    DESCRIPTION
        "Cisco UCS adaptor:EthPortStatsHist:rn managed object property"
    ::= { cucsAdaptorEthPortStatsHistEntry 3 }

cucsAdaptorEthPortStatsHistGoodPackets OBJECT-TYPE
    SYNTAX       Unsigned64
    MAX-ACCESS   read-only
    STATUS       current
    DESCRIPTION
        "Cisco UCS adaptor:EthPortStatsHist:goodPackets
        managed object property"
    ::= { cucsAdaptorEthPortStatsHistEntry 4 }

cucsAdaptorEthPortStatsHistGoodPacketsDelta OBJECT-TYPE
    SYNTAX       Unsigned64
    MAX-ACCESS   read-only
    STATUS       current
    DESCRIPTION
        "Cisco UCS adaptor:EthPortStatsHist:goodPacketsDelta
        managed object property"
    ::= { cucsAdaptorEthPortStatsHistEntry 5 }

cucsAdaptorEthPortStatsHistGoodPacketsDeltaAvg OBJECT-TYPE
    SYNTAX       Unsigned64
    MAX-ACCESS   read-only
    STATUS       current
    DESCRIPTION
        "Cisco UCS adaptor:EthPortStatsHist:goodPacketsDeltaAvg
        managed object property"
    ::= { cucsAdaptorEthPortStatsHistEntry 6 }

cucsAdaptorEthPortStatsHistGoodPacketsDeltaMax OBJECT-TYPE
    SYNTAX       Unsigned64
    MAX-ACCESS   read-only
    STATUS       current
    DESCRIPTION
        "Cisco UCS adaptor:EthPortStatsHist:goodPacketsDeltaMax
        managed object property"
    ::= { cucsAdaptorEthPortStatsHistEntry 7 }

cucsAdaptorEthPortStatsHistGoodPacketsDeltaMin OBJECT-TYPE
    SYNTAX       Unsigned64
    MAX-ACCESS   read-only
    STATUS       current
    DESCRIPTION
        "Cisco UCS adaptor:EthPortStatsHist:goodPacketsDeltaMin
        managed object property"
    ::= { cucsAdaptorEthPortStatsHistEntry 8 }

cucsAdaptorEthPortStatsHistId OBJECT-TYPE
    SYNTAX       Unsigned64
    MAX-ACCESS   read-only
    STATUS       current
    DESCRIPTION
        "Cisco UCS adaptor:EthPortStatsHist:id managed object property"
    ::= { cucsAdaptorEthPortStatsHistEntry 9 }

cucsAdaptorEthPortStatsHistMostRecent OBJECT-TYPE
    SYNTAX       TruthValue
    MAX-ACCESS   read-only
    STATUS       current
    DESCRIPTION
        "Cisco UCS adaptor:EthPortStatsHist:mostRecent
        managed object property"
    ::= { cucsAdaptorEthPortStatsHistEntry 10 }

cucsAdaptorEthPortStatsHistPausePackets OBJECT-TYPE
    SYNTAX       Unsigned64
    MAX-ACCESS   read-only
    STATUS       current
    DESCRIPTION
        "Cisco UCS adaptor:EthPortStatsHist:pausePackets
        managed object property"
    ::= { cucsAdaptorEthPortStatsHistEntry 11 }

cucsAdaptorEthPortStatsHistPausePacketsDelta OBJECT-TYPE
    SYNTAX       Unsigned64
    MAX-ACCESS   read-only
    STATUS       current
    DESCRIPTION
        "Cisco UCS adaptor:EthPortStatsHist:pausePacketsDelta
        managed object property"
    ::= { cucsAdaptorEthPortStatsHistEntry 12 }

cucsAdaptorEthPortStatsHistPausePacketsDeltaAvg OBJECT-TYPE
    SYNTAX       Unsigned64
    MAX-ACCESS   read-only
    STATUS       current
    DESCRIPTION
        "Cisco UCS adaptor:EthPortStatsHist:pausePacketsDeltaAvg
        managed object property"
    ::= { cucsAdaptorEthPortStatsHistEntry 13 }

cucsAdaptorEthPortStatsHistPausePacketsDeltaMax OBJECT-TYPE
    SYNTAX       Unsigned64
    MAX-ACCESS   read-only
    STATUS       current
    DESCRIPTION
        "Cisco UCS adaptor:EthPortStatsHist:pausePacketsDeltaMax
        managed object property"
    ::= { cucsAdaptorEthPortStatsHistEntry 14 }

cucsAdaptorEthPortStatsHistPausePacketsDeltaMin OBJECT-TYPE
    SYNTAX       Unsigned64
    MAX-ACCESS   read-only
    STATUS       current
    DESCRIPTION
        "Cisco UCS adaptor:EthPortStatsHist:pausePacketsDeltaMin
        managed object property"
    ::= { cucsAdaptorEthPortStatsHistEntry 15 }

cucsAdaptorEthPortStatsHistPerPriorityPausePackets OBJECT-TYPE
    SYNTAX       Unsigned64
    MAX-ACCESS   read-only
    STATUS       current
    DESCRIPTION
        "Cisco UCS adaptor:EthPortStatsHist:perPriorityPausePackets
        managed object property"
    ::= { cucsAdaptorEthPortStatsHistEntry 16 }

cucsAdaptorEthPortStatsHistPerPriorityPausePacketsDelta OBJECT-TYPE
    SYNTAX       Unsigned64
    MAX-ACCESS   read-only
    STATUS       current
    DESCRIPTION
        "Cisco UCS adaptor:EthPortStatsHist:perPriorityPausePacketsDelta
        managed object property"
    ::= { cucsAdaptorEthPortStatsHistEntry 17 }

cucsAdaptorEthPortStatsHistPerPriorityPausePacketsDeltaAvg OBJECT-TYPE
    SYNTAX       Unsigned64
    MAX-ACCESS   read-only
    STATUS       current
    DESCRIPTION
        "Cisco UCS adaptor:EthPortStatsHist:perPriorityPausePacketsDeltaAv
        g managed object property"
    ::= { cucsAdaptorEthPortStatsHistEntry 18 }

cucsAdaptorEthPortStatsHistPerPriorityPausePacketsDeltaMax OBJECT-TYPE
    SYNTAX       Unsigned64
    MAX-ACCESS   read-only
    STATUS       current
    DESCRIPTION
        "Cisco UCS adaptor:EthPortStatsHist:perPriorityPausePacketsDeltaMa
        x managed object property"
    ::= { cucsAdaptorEthPortStatsHistEntry 19 }

cucsAdaptorEthPortStatsHistPerPriorityPausePacketsDeltaMin OBJECT-TYPE
    SYNTAX       Unsigned64
    MAX-ACCESS   read-only
    STATUS       current
    DESCRIPTION
        "Cisco UCS adaptor:EthPortStatsHist:perPriorityPausePacketsDeltaMi
        n managed object property"
    ::= { cucsAdaptorEthPortStatsHistEntry 20 }

cucsAdaptorEthPortStatsHistPppPackets OBJECT-TYPE
    SYNTAX       Unsigned64
    MAX-ACCESS   read-only
    STATUS       current
    DESCRIPTION
        "Cisco UCS adaptor:EthPortStatsHist:pppPackets
        managed object property"
    ::= { cucsAdaptorEthPortStatsHistEntry 21 }

cucsAdaptorEthPortStatsHistPppPacketsDelta OBJECT-TYPE
    SYNTAX       Unsigned64
    MAX-ACCESS   read-only
    STATUS       current
    DESCRIPTION
        "Cisco UCS adaptor:EthPortStatsHist:pppPacketsDelta
        managed object property"
    ::= { cucsAdaptorEthPortStatsHistEntry 22 }

cucsAdaptorEthPortStatsHistPppPacketsDeltaAvg OBJECT-TYPE
    SYNTAX       Unsigned64
    MAX-ACCESS   read-only
    STATUS       current
    DESCRIPTION
        "Cisco UCS adaptor:EthPortStatsHist:pppPacketsDeltaAvg
        managed object property"
    ::= { cucsAdaptorEthPortStatsHistEntry 23 }

cucsAdaptorEthPortStatsHistPppPacketsDeltaMax OBJECT-TYPE
    SYNTAX       Unsigned64
    MAX-ACCESS   read-only
    STATUS       current
    DESCRIPTION
        "Cisco UCS adaptor:EthPortStatsHist:pppPacketsDeltaMax
        managed object property"
    ::= { cucsAdaptorEthPortStatsHistEntry 24 }

cucsAdaptorEthPortStatsHistPppPacketsDeltaMin OBJECT-TYPE
    SYNTAX       Unsigned64
    MAX-ACCESS   read-only
    STATUS       current
    DESCRIPTION
        "Cisco UCS adaptor:EthPortStatsHist:pppPacketsDeltaMin
        managed object property"
    ::= { cucsAdaptorEthPortStatsHistEntry 25 }

cucsAdaptorEthPortStatsHistSuspect OBJECT-TYPE
    SYNTAX       TruthValue
    MAX-ACCESS   read-only
    STATUS       current
    DESCRIPTION
        "Cisco UCS adaptor:EthPortStatsHist:suspect managed
        object property"
    ::= { cucsAdaptorEthPortStatsHistEntry 26 }

cucsAdaptorEthPortStatsHistThresholded OBJECT-TYPE
    SYNTAX       CucsAdaptorEthPortStatsHistThresholded
    MAX-ACCESS   read-only
    STATUS       current
    DESCRIPTION
        "Cisco UCS adaptor:EthPortStatsHist:thresholded
        managed object property"
    ::= { cucsAdaptorEthPortStatsHistEntry 27 }

cucsAdaptorEthPortStatsHistTimeCollected OBJECT-TYPE
    SYNTAX       DateAndTime
    MAX-ACCESS   read-only
    STATUS       current
    DESCRIPTION
        "Cisco UCS adaptor:EthPortStatsHist:timeCollected
        managed object property"
    ::= { cucsAdaptorEthPortStatsHistEntry 28 }

cucsAdaptorEthPortStatsHistTotalPackets OBJECT-TYPE
    SYNTAX       Unsigned64
    MAX-ACCESS   read-only
    STATUS       current
    DESCRIPTION
        "Cisco UCS adaptor:EthPortStatsHist:totalPackets
        managed object property"
    ::= { cucsAdaptorEthPortStatsHistEntry 29 }

cucsAdaptorEthPortStatsHistTotalPacketsDelta OBJECT-TYPE
    SYNTAX       Unsigned64
    MAX-ACCESS   read-only
    STATUS       current
    DESCRIPTION
        "Cisco UCS adaptor:EthPortStatsHist:totalPacketsDelta
        managed object property"
    ::= { cucsAdaptorEthPortStatsHistEntry 30 }

cucsAdaptorEthPortStatsHistTotalPacketsDeltaAvg OBJECT-TYPE
    SYNTAX       Unsigned64
    MAX-ACCESS   read-only
    STATUS       current
    DESCRIPTION
        "Cisco UCS adaptor:EthPortStatsHist:totalPacketsDeltaAvg
        managed object property"
    ::= { cucsAdaptorEthPortStatsHistEntry 31 }

cucsAdaptorEthPortStatsHistTotalPacketsDeltaMax OBJECT-TYPE
    SYNTAX       Unsigned64
    MAX-ACCESS   read-only
    STATUS       current
    DESCRIPTION
        "Cisco UCS adaptor:EthPortStatsHist:totalPacketsDeltaMax
        managed object property"
    ::= { cucsAdaptorEthPortStatsHistEntry 32 }

cucsAdaptorEthPortStatsHistTotalPacketsDeltaMin OBJECT-TYPE
    SYNTAX       Unsigned64
    MAX-ACCESS   read-only
    STATUS       current
    DESCRIPTION
        "Cisco UCS adaptor:EthPortStatsHist:totalPacketsDeltaMin
        managed object property"
    ::= { cucsAdaptorEthPortStatsHistEntry 33 }

cucsAdaptorEthPortStatsHistVlanPackets OBJECT-TYPE
    SYNTAX       Unsigned64
    MAX-ACCESS   read-only
    STATUS       current
    DESCRIPTION
        "Cisco UCS adaptor:EthPortStatsHist:vlanPackets
        managed object property"
    ::= { cucsAdaptorEthPortStatsHistEntry 34 }

cucsAdaptorEthPortStatsHistVlanPacketsDelta OBJECT-TYPE
    SYNTAX       Unsigned64
    MAX-ACCESS   read-only
    STATUS       current
    DESCRIPTION
        "Cisco UCS adaptor:EthPortStatsHist:vlanPacketsDelta
        managed object property"
    ::= { cucsAdaptorEthPortStatsHistEntry 35 }

cucsAdaptorEthPortStatsHistVlanPacketsDeltaAvg OBJECT-TYPE
    SYNTAX       Unsigned64
    MAX-ACCESS   read-only
    STATUS       current
    DESCRIPTION
        "Cisco UCS adaptor:EthPortStatsHist:vlanPacketsDeltaAvg
        managed object property"
    ::= { cucsAdaptorEthPortStatsHistEntry 36 }

cucsAdaptorEthPortStatsHistVlanPacketsDeltaMax OBJECT-TYPE
    SYNTAX       Unsigned64
    MAX-ACCESS   read-only
    STATUS       current
    DESCRIPTION
        "Cisco UCS adaptor:EthPortStatsHist:vlanPacketsDeltaMax
        managed object property"
    ::= { cucsAdaptorEthPortStatsHistEntry 37 }

cucsAdaptorEthPortStatsHistVlanPacketsDeltaMin OBJECT-TYPE
    SYNTAX       Unsigned64
    MAX-ACCESS   read-only
    STATUS       current
    DESCRIPTION
        "Cisco UCS adaptor:EthPortStatsHist:vlanPacketsDeltaMin
        managed object property"
    ::= { cucsAdaptorEthPortStatsHistEntry 38 }

cucsAdaptorEthRecvQueueProfileTable OBJECT-TYPE
    SYNTAX           SEQUENCE OF CucsAdaptorEthRecvQueueProfileEntry
    MAX-ACCESS       not-accessible
    STATUS           current
    DESCRIPTION
        "Cisco UCS adaptor:EthRecvQueueProfile managed object table"
    ::= { cucsAdaptorObjects 19 }

cucsAdaptorEthRecvQueueProfileEntry OBJECT-TYPE
    SYNTAX           CucsAdaptorEthRecvQueueProfileEntry
    MAX-ACCESS       not-accessible
    STATUS           current
    DESCRIPTION
        "Entry for the cucsAdaptorEthRecvQueueProfileTable table."
    INDEX { cucsAdaptorEthRecvQueueProfileInstanceId }
    ::= { cucsAdaptorEthRecvQueueProfileTable 1 }

CucsAdaptorEthRecvQueueProfileEntry ::= SEQUENCE {
    cucsAdaptorEthRecvQueueProfileInstanceId                         CucsManagedObjectId,
    cucsAdaptorEthRecvQueueProfileDn                                 CucsManagedObjectDn,
    cucsAdaptorEthRecvQueueProfileRn                                 SnmpAdminString,
    cucsAdaptorEthRecvQueueProfileCount                              Gauge32,
    cucsAdaptorEthRecvQueueProfileRingSize                           Gauge32
}

cucsAdaptorEthRecvQueueProfileInstanceId OBJECT-TYPE
    SYNTAX       CucsManagedObjectId
    MAX-ACCESS   not-accessible
    STATUS       current
    DESCRIPTION
        "Instance identifier of the managed object."
    ::= { cucsAdaptorEthRecvQueueProfileEntry 1 }

cucsAdaptorEthRecvQueueProfileDn OBJECT-TYPE
    SYNTAX       CucsManagedObjectDn
    MAX-ACCESS   read-only
    STATUS       current
    DESCRIPTION
        "Cisco UCS adaptor:EthRecvQueueProfile:dn managed object property"
    ::= { cucsAdaptorEthRecvQueueProfileEntry 2 }

cucsAdaptorEthRecvQueueProfileRn OBJECT-TYPE
    SYNTAX       SnmpAdminString
    MAX-ACCESS   read-only
    STATUS       current
    DESCRIPTION
        "Cisco UCS adaptor:EthRecvQueueProfile:rn managed object property"
    ::= { cucsAdaptorEthRecvQueueProfileEntry 3 }

cucsAdaptorEthRecvQueueProfileCount OBJECT-TYPE
    SYNTAX       Gauge32
    MAX-ACCESS   read-only
    STATUS       current
    DESCRIPTION
        "Cisco UCS adaptor:EthRecvQueueProfile:count managed
        object property"
    ::= { cucsAdaptorEthRecvQueueProfileEntry 4 }

cucsAdaptorEthRecvQueueProfileRingSize OBJECT-TYPE
    SYNTAX       Gauge32
    MAX-ACCESS   read-only
    STATUS       current
    DESCRIPTION
        "Cisco UCS adaptor:EthRecvQueueProfile:ringSize
        managed object property"
    ::= { cucsAdaptorEthRecvQueueProfileEntry 5 }

cucsAdaptorEthRoCEProfileTable OBJECT-TYPE
    SYNTAX           SEQUENCE OF CucsAdaptorEthRoCEProfileEntry
    MAX-ACCESS       not-accessible
    STATUS           current
    DESCRIPTION
        "Cisco UCS adaptor:EthRoCEProfile managed object table"
    ::= { cucsAdaptorObjects 118 }

cucsAdaptorEthRoCEProfileEntry OBJECT-TYPE
    SYNTAX           CucsAdaptorEthRoCEProfileEntry
    MAX-ACCESS       not-accessible
    STATUS           current
    DESCRIPTION
        "Entry for the cucsAdaptorEthRoCEProfileTable table."
    INDEX { cucsAdaptorEthRoCEProfileInstanceId }
    ::= { cucsAdaptorEthRoCEProfileTable 1 }

CucsAdaptorEthRoCEProfileEntry ::= SEQUENCE {
    cucsAdaptorEthRoCEProfileInstanceId                              CucsManagedObjectId,
    cucsAdaptorEthRoCEProfileDn                                      CucsManagedObjectDn,
    cucsAdaptorEthRoCEProfileRn                                      SnmpAdminString,
    cucsAdaptorEthRoCEProfileAdminState                              CucsAdaptorEthRoCEProfileAdminState,
    cucsAdaptorEthRoCEProfileMemoryRegions                           Gauge32,
    cucsAdaptorEthRoCEProfileQueuePairs                              Gauge32,
    cucsAdaptorEthRoCEProfileResourceGroups                          Gauge32
}

cucsAdaptorEthRoCEProfileInstanceId OBJECT-TYPE
    SYNTAX       CucsManagedObjectId
    MAX-ACCESS   not-accessible
    STATUS       current
    DESCRIPTION
        "Instance identifier of the managed object."
    ::= { cucsAdaptorEthRoCEProfileEntry 1 }

cucsAdaptorEthRoCEProfileDn OBJECT-TYPE
    SYNTAX       CucsManagedObjectDn
    MAX-ACCESS   read-only
    STATUS       current
    DESCRIPTION
        "Cisco UCS adaptor:EthRoCEProfile:dn managed object property"
    ::= { cucsAdaptorEthRoCEProfileEntry 2 }

cucsAdaptorEthRoCEProfileRn OBJECT-TYPE
    SYNTAX       SnmpAdminString
    MAX-ACCESS   read-only
    STATUS       current
    DESCRIPTION
        "Cisco UCS adaptor:EthRoCEProfile:rn managed object property"
    ::= { cucsAdaptorEthRoCEProfileEntry 3 }

cucsAdaptorEthRoCEProfileAdminState OBJECT-TYPE
    SYNTAX       CucsAdaptorEthRoCEProfileAdminState
    MAX-ACCESS   read-only
    STATUS       current
    DESCRIPTION
        "Cisco UCS adaptor:EthRoCEProfile:adminState managed
        object property"
    ::= { cucsAdaptorEthRoCEProfileEntry 4 }

cucsAdaptorEthRoCEProfileMemoryRegions OBJECT-TYPE
    SYNTAX       Gauge32
    MAX-ACCESS   read-only
    STATUS       current
    DESCRIPTION
        "Cisco UCS adaptor:EthRoCEProfile:memoryRegions
        managed object property"
    ::= { cucsAdaptorEthRoCEProfileEntry 5 }

cucsAdaptorEthRoCEProfileQueuePairs OBJECT-TYPE
    SYNTAX       Gauge32
    MAX-ACCESS   read-only
    STATUS       current
    DESCRIPTION
        "Cisco UCS adaptor:EthRoCEProfile:queuePairs managed
        object property"
    ::= { cucsAdaptorEthRoCEProfileEntry 6 }

cucsAdaptorEthRoCEProfileResourceGroups OBJECT-TYPE
    SYNTAX       Gauge32
    MAX-ACCESS   read-only
    STATUS       current
    DESCRIPTION
        "Cisco UCS adaptor:EthRoCEProfile:resourceGroups
        managed object property"
    ::= { cucsAdaptorEthRoCEProfileEntry 7 }

cucsAdaptorEthVxLANProfileTable OBJECT-TYPE
    SYNTAX           SEQUENCE OF CucsAdaptorEthVxLANProfileEntry
    MAX-ACCESS       not-accessible
    STATUS           current
    DESCRIPTION
        "Cisco UCS adaptor:EthVxLANProfile managed object table"
    ::= { cucsAdaptorObjects 119 }

cucsAdaptorEthVxLANProfileEntry OBJECT-TYPE
    SYNTAX           CucsAdaptorEthVxLANProfileEntry
    MAX-ACCESS       not-accessible
    STATUS           current
    DESCRIPTION
        "Entry for the cucsAdaptorEthVxLANProfileTable table."
    INDEX { cucsAdaptorEthVxLANProfileInstanceId }
    ::= { cucsAdaptorEthVxLANProfileTable 1 }

CucsAdaptorEthVxLANProfileEntry ::= SEQUENCE {
    cucsAdaptorEthVxLANProfileInstanceId                             CucsManagedObjectId,
    cucsAdaptorEthVxLANProfileDn                                     CucsManagedObjectDn,
    cucsAdaptorEthVxLANProfileRn                                     SnmpAdminString,
    cucsAdaptorEthVxLANProfileAdminState                             CucsAdaptorEthVxLANProfileAdminState
}

cucsAdaptorEthVxLANProfileInstanceId OBJECT-TYPE
    SYNTAX       CucsManagedObjectId
    MAX-ACCESS   not-accessible
    STATUS       current
    DESCRIPTION
        "Instance identifier of the managed object."
    ::= { cucsAdaptorEthVxLANProfileEntry 1 }

cucsAdaptorEthVxLANProfileDn OBJECT-TYPE
    SYNTAX       CucsManagedObjectDn
    MAX-ACCESS   read-only
    STATUS       current
    DESCRIPTION
        "Cisco UCS adaptor:EthVxLANProfile:dn managed object property"
    ::= { cucsAdaptorEthVxLANProfileEntry 2 }

cucsAdaptorEthVxLANProfileRn OBJECT-TYPE
    SYNTAX       SnmpAdminString
    MAX-ACCESS   read-only
    STATUS       current
    DESCRIPTION
        "Cisco UCS adaptor:EthVxLANProfile:rn managed object property"
    ::= { cucsAdaptorEthVxLANProfileEntry 3 }

cucsAdaptorEthVxLANProfileAdminState OBJECT-TYPE
    SYNTAX       CucsAdaptorEthVxLANProfileAdminState
    MAX-ACCESS   read-only
    STATUS       current
    DESCRIPTION
        "Cisco UCS adaptor:EthVxLANProfile:adminState managed
        object property"
    ::= { cucsAdaptorEthVxLANProfileEntry 4 }

cucsAdaptorEthWorkQueueProfileTable OBJECT-TYPE
    SYNTAX           SEQUENCE OF CucsAdaptorEthWorkQueueProfileEntry
    MAX-ACCESS       not-accessible
    STATUS           current
    DESCRIPTION
        "Cisco UCS adaptor:EthWorkQueueProfile managed object table"
    ::= { cucsAdaptorObjects 20 }

cucsAdaptorEthWorkQueueProfileEntry OBJECT-TYPE
    SYNTAX           CucsAdaptorEthWorkQueueProfileEntry
    MAX-ACCESS       not-accessible
    STATUS           current
    DESCRIPTION
        "Entry for the cucsAdaptorEthWorkQueueProfileTable table."
    INDEX { cucsAdaptorEthWorkQueueProfileInstanceId }
    ::= { cucsAdaptorEthWorkQueueProfileTable 1 }

CucsAdaptorEthWorkQueueProfileEntry ::= SEQUENCE {
    cucsAdaptorEthWorkQueueProfileInstanceId                         CucsManagedObjectId,
    cucsAdaptorEthWorkQueueProfileDn                                 CucsManagedObjectDn,
    cucsAdaptorEthWorkQueueProfileRn                                 SnmpAdminString,
    cucsAdaptorEthWorkQueueProfileCount                              Gauge32,
    cucsAdaptorEthWorkQueueProfileRingSize                           Gauge32
}

cucsAdaptorEthWorkQueueProfileInstanceId OBJECT-TYPE
    SYNTAX       CucsManagedObjectId
    MAX-ACCESS   not-accessible
    STATUS       current
    DESCRIPTION
        "Instance identifier of the managed object."
    ::= { cucsAdaptorEthWorkQueueProfileEntry 1 }

cucsAdaptorEthWorkQueueProfileDn OBJECT-TYPE
    SYNTAX       CucsManagedObjectDn
    MAX-ACCESS   read-only
    STATUS       current
    DESCRIPTION
        "Cisco UCS adaptor:EthWorkQueueProfile:dn managed object property"
    ::= { cucsAdaptorEthWorkQueueProfileEntry 2 }

cucsAdaptorEthWorkQueueProfileRn OBJECT-TYPE
    SYNTAX       SnmpAdminString
    MAX-ACCESS   read-only
    STATUS       current
    DESCRIPTION
        "Cisco UCS adaptor:EthWorkQueueProfile:rn managed object property"
    ::= { cucsAdaptorEthWorkQueueProfileEntry 3 }

cucsAdaptorEthWorkQueueProfileCount OBJECT-TYPE
    SYNTAX       Gauge32
    MAX-ACCESS   read-only
    STATUS       current
    DESCRIPTION
        "Cisco UCS adaptor:EthWorkQueueProfile:count managed
        object property"
    ::= { cucsAdaptorEthWorkQueueProfileEntry 4 }

cucsAdaptorEthWorkQueueProfileRingSize OBJECT-TYPE
    SYNTAX       Gauge32
    MAX-ACCESS   read-only
    STATUS       current
    DESCRIPTION
        "Cisco UCS adaptor:EthWorkQueueProfile:ringSize
        managed object property"
    ::= { cucsAdaptorEthWorkQueueProfileEntry 5 }

cucsAdaptorEtherIfStatsTable OBJECT-TYPE
    SYNTAX           SEQUENCE OF CucsAdaptorEtherIfStatsEntry
    MAX-ACCESS       not-accessible
    STATUS           current
    DESCRIPTION
        "Cisco UCS adaptor:EtherIfStats managed object table"
    ::= { cucsAdaptorObjects 21 }

cucsAdaptorEtherIfStatsEntry OBJECT-TYPE
    SYNTAX           CucsAdaptorEtherIfStatsEntry
    MAX-ACCESS       not-accessible
    STATUS           current
    DESCRIPTION
        "Entry for the cucsAdaptorEtherIfStatsTable table."
    INDEX { cucsAdaptorEtherIfStatsInstanceId }
    ::= { cucsAdaptorEtherIfStatsTable 1 }

CucsAdaptorEtherIfStatsEntry ::= SEQUENCE {
    cucsAdaptorEtherIfStatsInstanceId                                CucsManagedObjectId,
    cucsAdaptorEtherIfStatsDn                                        CucsManagedObjectDn,
    cucsAdaptorEtherIfStatsRn                                        SnmpAdminString,
    cucsAdaptorEtherIfStatsIntervals                                 Gauge32,
    cucsAdaptorEtherIfStatsRxBytes                                   Gauge32,
    cucsAdaptorEtherIfStatsRxBytesDelta                              Counter32,
    cucsAdaptorEtherIfStatsRxBytesDeltaAvg                           Gauge32,
    cucsAdaptorEtherIfStatsRxBytesDeltaMax                           Gauge32,
    cucsAdaptorEtherIfStatsRxBytesDeltaMin                           Gauge32,
    cucsAdaptorEtherIfStatsRxDropped                                 Gauge32,
    cucsAdaptorEtherIfStatsRxDroppedDelta                            Counter32,
    cucsAdaptorEtherIfStatsRxDroppedDeltaAvg                         Gauge32,
    cucsAdaptorEtherIfStatsRxDroppedDeltaMax                         Gauge32,
    cucsAdaptorEtherIfStatsRxDroppedDeltaMin                         Gauge32,
    cucsAdaptorEtherIfStatsRxErrors                                  Gauge32,
    cucsAdaptorEtherIfStatsRxErrorsDelta                             Counter32,
    cucsAdaptorEtherIfStatsRxErrorsDeltaAvg                          Gauge32,
    cucsAdaptorEtherIfStatsRxErrorsDeltaMax                          Gauge32,
    cucsAdaptorEtherIfStatsRxErrorsDeltaMin                          Gauge32,
    cucsAdaptorEtherIfStatsRxPackets                                 Gauge32,
    cucsAdaptorEtherIfStatsRxPacketsDelta                            Counter32,
    cucsAdaptorEtherIfStatsRxPacketsDeltaAvg                         Gauge32,
    cucsAdaptorEtherIfStatsRxPacketsDeltaMax                         Gauge32,
    cucsAdaptorEtherIfStatsRxPacketsDeltaMin                         Gauge32,
    cucsAdaptorEtherIfStatsSuspect                                   TruthValue,
    cucsAdaptorEtherIfStatsThresholded                               CucsAdaptorEtherIfStatsThresholded,
    cucsAdaptorEtherIfStatsTimeCollected                             DateAndTime,
    cucsAdaptorEtherIfStatsTxBytes                                   Gauge32,
    cucsAdaptorEtherIfStatsTxBytesDelta                              Counter32,
    cucsAdaptorEtherIfStatsTxBytesDeltaAvg                           Gauge32,
    cucsAdaptorEtherIfStatsTxBytesDeltaMax                           Gauge32,
    cucsAdaptorEtherIfStatsTxBytesDeltaMin                           Gauge32,
    cucsAdaptorEtherIfStatsTxDropped                                 Gauge32,
    cucsAdaptorEtherIfStatsTxDroppedDelta                            Counter32,
    cucsAdaptorEtherIfStatsTxDroppedDeltaAvg                         Gauge32,
    cucsAdaptorEtherIfStatsTxDroppedDeltaMax                         Gauge32,
    cucsAdaptorEtherIfStatsTxDroppedDeltaMin                         Gauge32,
    cucsAdaptorEtherIfStatsTxErrors                                  Gauge32,
    cucsAdaptorEtherIfStatsTxErrorsDelta                             Counter32,
    cucsAdaptorEtherIfStatsTxErrorsDeltaAvg                          Gauge32,
    cucsAdaptorEtherIfStatsTxErrorsDeltaMax                          Gauge32,
    cucsAdaptorEtherIfStatsTxErrorsDeltaMin                          Gauge32,
    cucsAdaptorEtherIfStatsTxPackets                                 Gauge32,
    cucsAdaptorEtherIfStatsTxPacketsDelta                            Counter32,
    cucsAdaptorEtherIfStatsTxPacketsDeltaAvg                         Gauge32,
    cucsAdaptorEtherIfStatsTxPacketsDeltaMax                         Gauge32,
    cucsAdaptorEtherIfStatsTxPacketsDeltaMin                         Gauge32,
    cucsAdaptorEtherIfStatsUpdate                                    Gauge32
}

cucsAdaptorEtherIfStatsInstanceId OBJECT-TYPE
    SYNTAX       CucsManagedObjectId
    MAX-ACCESS   not-accessible
    STATUS       current
    DESCRIPTION
        "Instance identifier of the managed object."
    ::= { cucsAdaptorEtherIfStatsEntry 1 }

cucsAdaptorEtherIfStatsDn OBJECT-TYPE
    SYNTAX       CucsManagedObjectDn
    MAX-ACCESS   read-only
    STATUS       current
    DESCRIPTION
        "Cisco UCS adaptor:EtherIfStats:dn managed object property"
    ::= { cucsAdaptorEtherIfStatsEntry 2 }

cucsAdaptorEtherIfStatsRn OBJECT-TYPE
    SYNTAX       SnmpAdminString
    MAX-ACCESS   read-only
    STATUS       current
    DESCRIPTION
        "Cisco UCS adaptor:EtherIfStats:rn managed object property"
    ::= { cucsAdaptorEtherIfStatsEntry 3 }

cucsAdaptorEtherIfStatsIntervals OBJECT-TYPE
    SYNTAX       Gauge32
    MAX-ACCESS   read-only
    STATUS       current
    DESCRIPTION
        "Cisco UCS adaptor:EtherIfStats:intervals managed object property"
    ::= { cucsAdaptorEtherIfStatsEntry 4 }

cucsAdaptorEtherIfStatsRxBytes OBJECT-TYPE
    SYNTAX       Gauge32
    MAX-ACCESS   read-only
    STATUS       current
    DESCRIPTION
        "Cisco UCS adaptor:EtherIfStats:rxBytes managed object property"
    ::= { cucsAdaptorEtherIfStatsEntry 5 }

cucsAdaptorEtherIfStatsRxBytesDelta OBJECT-TYPE
    SYNTAX       Counter32
    MAX-ACCESS   read-only
    STATUS       current
    DESCRIPTION
        "Cisco UCS adaptor:EtherIfStats:rxBytesDelta managed
        object property"
    ::= { cucsAdaptorEtherIfStatsEntry 6 }

cucsAdaptorEtherIfStatsRxBytesDeltaAvg OBJECT-TYPE
    SYNTAX       Gauge32
    MAX-ACCESS   read-only
    STATUS       current
    DESCRIPTION
        "Cisco UCS adaptor:EtherIfStats:rxBytesDeltaAvg
        managed object property"
    ::= { cucsAdaptorEtherIfStatsEntry 7 }

cucsAdaptorEtherIfStatsRxBytesDeltaMax OBJECT-TYPE
    SYNTAX       Gauge32
    MAX-ACCESS   read-only
    STATUS       current
    DESCRIPTION
        "Cisco UCS adaptor:EtherIfStats:rxBytesDeltaMax
        managed object property"
    ::= { cucsAdaptorEtherIfStatsEntry 8 }

cucsAdaptorEtherIfStatsRxBytesDeltaMin OBJECT-TYPE
    SYNTAX       Gauge32
    MAX-ACCESS   read-only
    STATUS       current
    DESCRIPTION
        "Cisco UCS adaptor:EtherIfStats:rxBytesDeltaMin
        managed object property"
    ::= { cucsAdaptorEtherIfStatsEntry 9 }

cucsAdaptorEtherIfStatsRxDropped OBJECT-TYPE
    SYNTAX       Gauge32
    MAX-ACCESS   read-only
    STATUS       current
    DESCRIPTION
        "Cisco UCS adaptor:EtherIfStats:rxDropped managed object property"
    ::= { cucsAdaptorEtherIfStatsEntry 10 }

cucsAdaptorEtherIfStatsRxDroppedDelta OBJECT-TYPE
    SYNTAX       Counter32
    MAX-ACCESS   read-only
    STATUS       current
    DESCRIPTION
        "Cisco UCS adaptor:EtherIfStats:rxDroppedDelta
        managed object property"
    ::= { cucsAdaptorEtherIfStatsEntry 11 }

cucsAdaptorEtherIfStatsRxDroppedDeltaAvg OBJECT-TYPE
    SYNTAX       Gauge32
    MAX-ACCESS   read-only
    STATUS       current
    DESCRIPTION
        "Cisco UCS adaptor:EtherIfStats:rxDroppedDeltaAvg
        managed object property"
    ::= { cucsAdaptorEtherIfStatsEntry 12 }

cucsAdaptorEtherIfStatsRxDroppedDeltaMax OBJECT-TYPE
    SYNTAX       Gauge32
    MAX-ACCESS   read-only
    STATUS       current
    DESCRIPTION
        "Cisco UCS adaptor:EtherIfStats:rxDroppedDeltaMax
        managed object property"
    ::= { cucsAdaptorEtherIfStatsEntry 13 }

cucsAdaptorEtherIfStatsRxDroppedDeltaMin OBJECT-TYPE
    SYNTAX       Gauge32
    MAX-ACCESS   read-only
    STATUS       current
    DESCRIPTION
        "Cisco UCS adaptor:EtherIfStats:rxDroppedDeltaMin
        managed object property"
    ::= { cucsAdaptorEtherIfStatsEntry 14 }

cucsAdaptorEtherIfStatsRxErrors OBJECT-TYPE
    SYNTAX       Gauge32
    MAX-ACCESS   read-only
    STATUS       current
    DESCRIPTION
        "Cisco UCS adaptor:EtherIfStats:rxErrors managed object property"
    ::= { cucsAdaptorEtherIfStatsEntry 15 }

cucsAdaptorEtherIfStatsRxErrorsDelta OBJECT-TYPE
    SYNTAX       Counter32
    MAX-ACCESS   read-only
    STATUS       current
    DESCRIPTION
        "Cisco UCS adaptor:EtherIfStats:rxErrorsDelta managed
        object property"
    ::= { cucsAdaptorEtherIfStatsEntry 16 }

cucsAdaptorEtherIfStatsRxErrorsDeltaAvg OBJECT-TYPE
    SYNTAX       Gauge32
    MAX-ACCESS   read-only
    STATUS       current
    DESCRIPTION
        "Cisco UCS adaptor:EtherIfStats:rxErrorsDeltaAvg
        managed object property"
    ::= { cucsAdaptorEtherIfStatsEntry 17 }

cucsAdaptorEtherIfStatsRxErrorsDeltaMax OBJECT-TYPE
    SYNTAX       Gauge32
    MAX-ACCESS   read-only
    STATUS       current
    DESCRIPTION
        "Cisco UCS adaptor:EtherIfStats:rxErrorsDeltaMax
        managed object property"
    ::= { cucsAdaptorEtherIfStatsEntry 18 }

cucsAdaptorEtherIfStatsRxErrorsDeltaMin OBJECT-TYPE
    SYNTAX       Gauge32
    MAX-ACCESS   read-only
    STATUS       current
    DESCRIPTION
        "Cisco UCS adaptor:EtherIfStats:rxErrorsDeltaMin
        managed object property"
    ::= { cucsAdaptorEtherIfStatsEntry 19 }

cucsAdaptorEtherIfStatsRxPackets OBJECT-TYPE
    SYNTAX       Gauge32
    MAX-ACCESS   read-only
    STATUS       current
    DESCRIPTION
        "Cisco UCS adaptor:EtherIfStats:rxPackets managed object property"
    ::= { cucsAdaptorEtherIfStatsEntry 20 }

cucsAdaptorEtherIfStatsRxPacketsDelta OBJECT-TYPE
    SYNTAX       Counter32
    MAX-ACCESS   read-only
    STATUS       current
    DESCRIPTION
        "Cisco UCS adaptor:EtherIfStats:rxPacketsDelta
        managed object property"
    ::= { cucsAdaptorEtherIfStatsEntry 21 }

cucsAdaptorEtherIfStatsRxPacketsDeltaAvg OBJECT-TYPE
    SYNTAX       Gauge32
    MAX-ACCESS   read-only
    STATUS       current
    DESCRIPTION
        "Cisco UCS adaptor:EtherIfStats:rxPacketsDeltaAvg
        managed object property"
    ::= { cucsAdaptorEtherIfStatsEntry 22 }

cucsAdaptorEtherIfStatsRxPacketsDeltaMax OBJECT-TYPE
    SYNTAX       Gauge32
    MAX-ACCESS   read-only
    STATUS       current
    DESCRIPTION
        "Cisco UCS adaptor:EtherIfStats:rxPacketsDeltaMax
        managed object property"
    ::= { cucsAdaptorEtherIfStatsEntry 23 }

cucsAdaptorEtherIfStatsRxPacketsDeltaMin OBJECT-TYPE
    SYNTAX       Gauge32
    MAX-ACCESS   read-only
    STATUS       current
    DESCRIPTION
        "Cisco UCS adaptor:EtherIfStats:rxPacketsDeltaMin
        managed object property"
    ::= { cucsAdaptorEtherIfStatsEntry 24 }

cucsAdaptorEtherIfStatsSuspect OBJECT-TYPE
    SYNTAX       TruthValue
    MAX-ACCESS   read-only
    STATUS       current
    DESCRIPTION
        "Cisco UCS adaptor:EtherIfStats:suspect managed object property"
    ::= { cucsAdaptorEtherIfStatsEntry 25 }

cucsAdaptorEtherIfStatsThresholded OBJECT-TYPE
    SYNTAX       CucsAdaptorEtherIfStatsThresholded
    MAX-ACCESS   read-only
    STATUS       current
    DESCRIPTION
        "Cisco UCS adaptor:EtherIfStats:thresholded managed
        object property"
    ::= { cucsAdaptorEtherIfStatsEntry 26 }

cucsAdaptorEtherIfStatsTimeCollected OBJECT-TYPE
    SYNTAX       DateAndTime
    MAX-ACCESS   read-only
    STATUS       current
    DESCRIPTION
        "Cisco UCS adaptor:EtherIfStats:timeCollected managed
        object property"
    ::= { cucsAdaptorEtherIfStatsEntry 27 }

cucsAdaptorEtherIfStatsTxBytes OBJECT-TYPE
    SYNTAX       Gauge32
    MAX-ACCESS   read-only
    STATUS       current
    DESCRIPTION
        "Cisco UCS adaptor:EtherIfStats:txBytes managed object property"
    ::= { cucsAdaptorEtherIfStatsEntry 28 }

cucsAdaptorEtherIfStatsTxBytesDelta OBJECT-TYPE
    SYNTAX       Counter32
    MAX-ACCESS   read-only
    STATUS       current
    DESCRIPTION
        "Cisco UCS adaptor:EtherIfStats:txBytesDelta managed
        object property"
    ::= { cucsAdaptorEtherIfStatsEntry 29 }

cucsAdaptorEtherIfStatsTxBytesDeltaAvg OBJECT-TYPE
    SYNTAX       Gauge32
    MAX-ACCESS   read-only
    STATUS       current
    DESCRIPTION
        "Cisco UCS adaptor:EtherIfStats:txBytesDeltaAvg
        managed object property"
    ::= { cucsAdaptorEtherIfStatsEntry 30 }

cucsAdaptorEtherIfStatsTxBytesDeltaMax OBJECT-TYPE
    SYNTAX       Gauge32
    MAX-ACCESS   read-only
    STATUS       current
    DESCRIPTION
        "Cisco UCS adaptor:EtherIfStats:txBytesDeltaMax
        managed object property"
    ::= { cucsAdaptorEtherIfStatsEntry 31 }

cucsAdaptorEtherIfStatsTxBytesDeltaMin OBJECT-TYPE
    SYNTAX       Gauge32
    MAX-ACCESS   read-only
    STATUS       current
    DESCRIPTION
        "Cisco UCS adaptor:EtherIfStats:txBytesDeltaMin
        managed object property"
    ::= { cucsAdaptorEtherIfStatsEntry 32 }

cucsAdaptorEtherIfStatsTxDropped OBJECT-TYPE
    SYNTAX       Gauge32
    MAX-ACCESS   read-only
    STATUS       current
    DESCRIPTION
        "Cisco UCS adaptor:EtherIfStats:txDropped managed object property"
    ::= { cucsAdaptorEtherIfStatsEntry 33 }

cucsAdaptorEtherIfStatsTxDroppedDelta OBJECT-TYPE
    SYNTAX       Counter32
    MAX-ACCESS   read-only
    STATUS       current
    DESCRIPTION
        "Cisco UCS adaptor:EtherIfStats:txDroppedDelta
        managed object property"
    ::= { cucsAdaptorEtherIfStatsEntry 34 }

cucsAdaptorEtherIfStatsTxDroppedDeltaAvg OBJECT-TYPE
    SYNTAX       Gauge32
    MAX-ACCESS   read-only
    STATUS       current
    DESCRIPTION
        "Cisco UCS adaptor:EtherIfStats:txDroppedDeltaAvg
        managed object property"
    ::= { cucsAdaptorEtherIfStatsEntry 35 }

cucsAdaptorEtherIfStatsTxDroppedDeltaMax OBJECT-TYPE
    SYNTAX       Gauge32
    MAX-ACCESS   read-only
    STATUS       current
    DESCRIPTION
        "Cisco UCS adaptor:EtherIfStats:txDroppedDeltaMax
        managed object property"
    ::= { cucsAdaptorEtherIfStatsEntry 36 }

cucsAdaptorEtherIfStatsTxDroppedDeltaMin OBJECT-TYPE
    SYNTAX       Gauge32
    MAX-ACCESS   read-only
    STATUS       current
    DESCRIPTION
        "Cisco UCS adaptor:EtherIfStats:txDroppedDeltaMin
        managed object property"
    ::= { cucsAdaptorEtherIfStatsEntry 37 }

cucsAdaptorEtherIfStatsTxErrors OBJECT-TYPE
    SYNTAX       Gauge32
    MAX-ACCESS   read-only
    STATUS       current
    DESCRIPTION
        "Cisco UCS adaptor:EtherIfStats:txErrors managed object property"
    ::= { cucsAdaptorEtherIfStatsEntry 38 }

cucsAdaptorEtherIfStatsTxErrorsDelta OBJECT-TYPE
    SYNTAX       Counter32
    MAX-ACCESS   read-only
    STATUS       current
    DESCRIPTION
        "Cisco UCS adaptor:EtherIfStats:txErrorsDelta managed
        object property"
    ::= { cucsAdaptorEtherIfStatsEntry 39 }

cucsAdaptorEtherIfStatsTxErrorsDeltaAvg OBJECT-TYPE
    SYNTAX       Gauge32
    MAX-ACCESS   read-only
    STATUS       current
    DESCRIPTION
        "Cisco UCS adaptor:EtherIfStats:txErrorsDeltaAvg
        managed object property"
    ::= { cucsAdaptorEtherIfStatsEntry 40 }

cucsAdaptorEtherIfStatsTxErrorsDeltaMax OBJECT-TYPE
    SYNTAX       Gauge32
    MAX-ACCESS   read-only
    STATUS       current
    DESCRIPTION
        "Cisco UCS adaptor:EtherIfStats:txErrorsDeltaMax
        managed object property"
    ::= { cucsAdaptorEtherIfStatsEntry 41 }

cucsAdaptorEtherIfStatsTxErrorsDeltaMin OBJECT-TYPE
    SYNTAX       Gauge32
    MAX-ACCESS   read-only
    STATUS       current
    DESCRIPTION
        "Cisco UCS adaptor:EtherIfStats:txErrorsDeltaMin
        managed object property"
    ::= { cucsAdaptorEtherIfStatsEntry 42 }

cucsAdaptorEtherIfStatsTxPackets OBJECT-TYPE
    SYNTAX       Gauge32
    MAX-ACCESS   read-only
    STATUS       current
    DESCRIPTION
        "Cisco UCS adaptor:EtherIfStats:txPackets managed object property"
    ::= { cucsAdaptorEtherIfStatsEntry 43 }

cucsAdaptorEtherIfStatsTxPacketsDelta OBJECT-TYPE
    SYNTAX       Counter32
    MAX-ACCESS   read-only
    STATUS       current
    DESCRIPTION
        "Cisco UCS adaptor:EtherIfStats:txPacketsDelta
        managed object property"
    ::= { cucsAdaptorEtherIfStatsEntry 44 }

cucsAdaptorEtherIfStatsTxPacketsDeltaAvg OBJECT-TYPE
    SYNTAX       Gauge32
    MAX-ACCESS   read-only
    STATUS       current
    DESCRIPTION
        "Cisco UCS adaptor:EtherIfStats:txPacketsDeltaAvg
        managed object property"
    ::= { cucsAdaptorEtherIfStatsEntry 45 }

cucsAdaptorEtherIfStatsTxPacketsDeltaMax OBJECT-TYPE
    SYNTAX       Gauge32
    MAX-ACCESS   read-only
    STATUS       current
    DESCRIPTION
        "Cisco UCS adaptor:EtherIfStats:txPacketsDeltaMax
        managed object property"
    ::= { cucsAdaptorEtherIfStatsEntry 46 }

cucsAdaptorEtherIfStatsTxPacketsDeltaMin OBJECT-TYPE
    SYNTAX       Gauge32
    MAX-ACCESS   read-only
    STATUS       current
    DESCRIPTION
        "Cisco UCS adaptor:EtherIfStats:txPacketsDeltaMin
        managed object property"
    ::= { cucsAdaptorEtherIfStatsEntry 47 }

cucsAdaptorEtherIfStatsUpdate OBJECT-TYPE
    SYNTAX       Gauge32
    MAX-ACCESS   read-only
    STATUS       current
    DESCRIPTION
        "Cisco UCS adaptor:EtherIfStats:update managed object property"
    ::= { cucsAdaptorEtherIfStatsEntry 48 }

cucsAdaptorEtherIfStatsHistTable OBJECT-TYPE
    SYNTAX           SEQUENCE OF CucsAdaptorEtherIfStatsHistEntry
    MAX-ACCESS       not-accessible
    STATUS           current
    DESCRIPTION
        "Cisco UCS adaptor:EtherIfStatsHist managed object table"
    ::= { cucsAdaptorObjects 22 }

cucsAdaptorEtherIfStatsHistEntry OBJECT-TYPE
    SYNTAX           CucsAdaptorEtherIfStatsHistEntry
    MAX-ACCESS       not-accessible
    STATUS           current
    DESCRIPTION
        "Entry for the cucsAdaptorEtherIfStatsHistTable table."
    INDEX { cucsAdaptorEtherIfStatsHistInstanceId }
    ::= { cucsAdaptorEtherIfStatsHistTable 1 }

CucsAdaptorEtherIfStatsHistEntry ::= SEQUENCE {
    cucsAdaptorEtherIfStatsHistInstanceId                            CucsManagedObjectId,
    cucsAdaptorEtherIfStatsHistDn                                    CucsManagedObjectDn,
    cucsAdaptorEtherIfStatsHistRn                                    SnmpAdminString,
    cucsAdaptorEtherIfStatsHistId                                    Unsigned64,
    cucsAdaptorEtherIfStatsHistMostRecent                            TruthValue,
    cucsAdaptorEtherIfStatsHistRxBytes                               Gauge32,
    cucsAdaptorEtherIfStatsHistRxBytesDelta                          Gauge32,
    cucsAdaptorEtherIfStatsHistRxBytesDeltaAvg                       Gauge32,
    cucsAdaptorEtherIfStatsHistRxBytesDeltaMax                       Gauge32,
    cucsAdaptorEtherIfStatsHistRxBytesDeltaMin                       Gauge32,
    cucsAdaptorEtherIfStatsHistRxDropped                             Gauge32,
    cucsAdaptorEtherIfStatsHistRxDroppedDelta                        Gauge32,
    cucsAdaptorEtherIfStatsHistRxDroppedDeltaAvg                     Gauge32,
    cucsAdaptorEtherIfStatsHistRxDroppedDeltaMax                     Gauge32,
    cucsAdaptorEtherIfStatsHistRxDroppedDeltaMin                     Gauge32,
    cucsAdaptorEtherIfStatsHistRxErrors                              Gauge32,
    cucsAdaptorEtherIfStatsHistRxErrorsDelta                         Gauge32,
    cucsAdaptorEtherIfStatsHistRxErrorsDeltaAvg                      Gauge32,
    cucsAdaptorEtherIfStatsHistRxErrorsDeltaMax                      Gauge32,
    cucsAdaptorEtherIfStatsHistRxErrorsDeltaMin                      Gauge32,
    cucsAdaptorEtherIfStatsHistRxPackets                             Gauge32,
    cucsAdaptorEtherIfStatsHistRxPacketsDelta                        Gauge32,
    cucsAdaptorEtherIfStatsHistRxPacketsDeltaAvg                     Gauge32,
    cucsAdaptorEtherIfStatsHistRxPacketsDeltaMax                     Gauge32,
    cucsAdaptorEtherIfStatsHistRxPacketsDeltaMin                     Gauge32,
    cucsAdaptorEtherIfStatsHistSuspect                               TruthValue,
    cucsAdaptorEtherIfStatsHistThresholded                           CucsAdaptorEtherIfStatsHistThresholded,
    cucsAdaptorEtherIfStatsHistTimeCollected                         DateAndTime,
    cucsAdaptorEtherIfStatsHistTxBytes                               Gauge32,
    cucsAdaptorEtherIfStatsHistTxBytesDelta                          Gauge32,
    cucsAdaptorEtherIfStatsHistTxBytesDeltaAvg                       Gauge32,
    cucsAdaptorEtherIfStatsHistTxBytesDeltaMax                       Gauge32,
    cucsAdaptorEtherIfStatsHistTxBytesDeltaMin                       Gauge32,
    cucsAdaptorEtherIfStatsHistTxDropped                             Gauge32,
    cucsAdaptorEtherIfStatsHistTxDroppedDelta                        Gauge32,
    cucsAdaptorEtherIfStatsHistTxDroppedDeltaAvg                     Gauge32,
    cucsAdaptorEtherIfStatsHistTxDroppedDeltaMax                     Gauge32,
    cucsAdaptorEtherIfStatsHistTxDroppedDeltaMin                     Gauge32,
    cucsAdaptorEtherIfStatsHistTxErrors                              Gauge32,
    cucsAdaptorEtherIfStatsHistTxErrorsDelta                         Gauge32,
    cucsAdaptorEtherIfStatsHistTxErrorsDeltaAvg                      Gauge32,
    cucsAdaptorEtherIfStatsHistTxErrorsDeltaMax                      Gauge32,
    cucsAdaptorEtherIfStatsHistTxErrorsDeltaMin                      Gauge32,
    cucsAdaptorEtherIfStatsHistTxPackets                             Gauge32,
    cucsAdaptorEtherIfStatsHistTxPacketsDelta                        Gauge32,
    cucsAdaptorEtherIfStatsHistTxPacketsDeltaAvg                     Gauge32,
    cucsAdaptorEtherIfStatsHistTxPacketsDeltaMax                     Gauge32,
    cucsAdaptorEtherIfStatsHistTxPacketsDeltaMin                     Gauge32
}

cucsAdaptorEtherIfStatsHistInstanceId OBJECT-TYPE
    SYNTAX       CucsManagedObjectId
    MAX-ACCESS   not-accessible
    STATUS       current
    DESCRIPTION
        "Instance identifier of the managed object."
    ::= { cucsAdaptorEtherIfStatsHistEntry 1 }

cucsAdaptorEtherIfStatsHistDn OBJECT-TYPE
    SYNTAX       CucsManagedObjectDn
    MAX-ACCESS   read-only
    STATUS       current
    DESCRIPTION
        "Cisco UCS adaptor:EtherIfStatsHist:dn managed object property"
    ::= { cucsAdaptorEtherIfStatsHistEntry 2 }

cucsAdaptorEtherIfStatsHistRn OBJECT-TYPE
    SYNTAX       SnmpAdminString
    MAX-ACCESS   read-only
    STATUS       current
    DESCRIPTION
        "Cisco UCS adaptor:EtherIfStatsHist:rn managed object property"
    ::= { cucsAdaptorEtherIfStatsHistEntry 3 }

cucsAdaptorEtherIfStatsHistId OBJECT-TYPE
    SYNTAX       Unsigned64
    MAX-ACCESS   read-only
    STATUS       current
    DESCRIPTION
        "Cisco UCS adaptor:EtherIfStatsHist:id managed object property"
    ::= { cucsAdaptorEtherIfStatsHistEntry 4 }

cucsAdaptorEtherIfStatsHistMostRecent OBJECT-TYPE
    SYNTAX       TruthValue
    MAX-ACCESS   read-only
    STATUS       current
    DESCRIPTION
        "Cisco UCS adaptor:EtherIfStatsHist:mostRecent
        managed object property"
    ::= { cucsAdaptorEtherIfStatsHistEntry 5 }

cucsAdaptorEtherIfStatsHistRxBytes OBJECT-TYPE
    SYNTAX       Gauge32
    MAX-ACCESS   read-only
    STATUS       current
    DESCRIPTION
        "Cisco UCS adaptor:EtherIfStatsHist:rxBytes managed
        object property"
    ::= { cucsAdaptorEtherIfStatsHistEntry 6 }

cucsAdaptorEtherIfStatsHistRxBytesDelta OBJECT-TYPE
    SYNTAX       Gauge32
    MAX-ACCESS   read-only
    STATUS       current
    DESCRIPTION
        "Cisco UCS adaptor:EtherIfStatsHist:rxBytesDelta
        managed object property"
    ::= { cucsAdaptorEtherIfStatsHistEntry 7 }

cucsAdaptorEtherIfStatsHistRxBytesDeltaAvg OBJECT-TYPE
    SYNTAX       Gauge32
    MAX-ACCESS   read-only
    STATUS       current
    DESCRIPTION
        "Cisco UCS adaptor:EtherIfStatsHist:rxBytesDeltaAvg
        managed object property"
    ::= { cucsAdaptorEtherIfStatsHistEntry 8 }

cucsAdaptorEtherIfStatsHistRxBytesDeltaMax OBJECT-TYPE
    SYNTAX       Gauge32
    MAX-ACCESS   read-only
    STATUS       current
    DESCRIPTION
        "Cisco UCS adaptor:EtherIfStatsHist:rxBytesDeltaMax
        managed object property"
    ::= { cucsAdaptorEtherIfStatsHistEntry 9 }

cucsAdaptorEtherIfStatsHistRxBytesDeltaMin OBJECT-TYPE
    SYNTAX       Gauge32
    MAX-ACCESS   read-only
    STATUS       current
    DESCRIPTION
        "Cisco UCS adaptor:EtherIfStatsHist:rxBytesDeltaMin
        managed object property"
    ::= { cucsAdaptorEtherIfStatsHistEntry 10 }

cucsAdaptorEtherIfStatsHistRxDropped OBJECT-TYPE
    SYNTAX       Gauge32
    MAX-ACCESS   read-only
    STATUS       current
    DESCRIPTION
        "Cisco UCS adaptor:EtherIfStatsHist:rxDropped managed
        object property"
    ::= { cucsAdaptorEtherIfStatsHistEntry 11 }

cucsAdaptorEtherIfStatsHistRxDroppedDelta OBJECT-TYPE
    SYNTAX       Gauge32
    MAX-ACCESS   read-only
    STATUS       current
    DESCRIPTION
        "Cisco UCS adaptor:EtherIfStatsHist:rxDroppedDelta
        managed object property"
    ::= { cucsAdaptorEtherIfStatsHistEntry 12 }

cucsAdaptorEtherIfStatsHistRxDroppedDeltaAvg OBJECT-TYPE
    SYNTAX       Gauge32
    MAX-ACCESS   read-only
    STATUS       current
    DESCRIPTION
        "Cisco UCS adaptor:EtherIfStatsHist:rxDroppedDeltaAvg
        managed object property"
    ::= { cucsAdaptorEtherIfStatsHistEntry 13 }

cucsAdaptorEtherIfStatsHistRxDroppedDeltaMax OBJECT-TYPE
    SYNTAX       Gauge32
    MAX-ACCESS   read-only
    STATUS       current
    DESCRIPTION
        "Cisco UCS adaptor:EtherIfStatsHist:rxDroppedDeltaMax
        managed object property"
    ::= { cucsAdaptorEtherIfStatsHistEntry 14 }

cucsAdaptorEtherIfStatsHistRxDroppedDeltaMin OBJECT-TYPE
    SYNTAX       Gauge32
    MAX-ACCESS   read-only
    STATUS       current
    DESCRIPTION
        "Cisco UCS adaptor:EtherIfStatsHist:rxDroppedDeltaMin
        managed object property"
    ::= { cucsAdaptorEtherIfStatsHistEntry 15 }

cucsAdaptorEtherIfStatsHistRxErrors OBJECT-TYPE
    SYNTAX       Gauge32
    MAX-ACCESS   read-only
    STATUS       current
    DESCRIPTION
        "Cisco UCS adaptor:EtherIfStatsHist:rxErrors managed
        object property"
    ::= { cucsAdaptorEtherIfStatsHistEntry 16 }

cucsAdaptorEtherIfStatsHistRxErrorsDelta OBJECT-TYPE
    SYNTAX       Gauge32
    MAX-ACCESS   read-only
    STATUS       current
    DESCRIPTION
        "Cisco UCS adaptor:EtherIfStatsHist:rxErrorsDelta
        managed object property"
    ::= { cucsAdaptorEtherIfStatsHistEntry 17 }

cucsAdaptorEtherIfStatsHistRxErrorsDeltaAvg OBJECT-TYPE
    SYNTAX       Gauge32
    MAX-ACCESS   read-only
    STATUS       current
    DESCRIPTION
        "Cisco UCS adaptor:EtherIfStatsHist:rxErrorsDeltaAvg
        managed object property"
    ::= { cucsAdaptorEtherIfStatsHistEntry 18 }

cucsAdaptorEtherIfStatsHistRxErrorsDeltaMax OBJECT-TYPE
    SYNTAX       Gauge32
    MAX-ACCESS   read-only
    STATUS       current
    DESCRIPTION
        "Cisco UCS adaptor:EtherIfStatsHist:rxErrorsDeltaMax
        managed object property"
    ::= { cucsAdaptorEtherIfStatsHistEntry 19 }

cucsAdaptorEtherIfStatsHistRxErrorsDeltaMin OBJECT-TYPE
    SYNTAX       Gauge32
    MAX-ACCESS   read-only
    STATUS       current
    DESCRIPTION
        "Cisco UCS adaptor:EtherIfStatsHist:rxErrorsDeltaMin
        managed object property"
    ::= { cucsAdaptorEtherIfStatsHistEntry 20 }

cucsAdaptorEtherIfStatsHistRxPackets OBJECT-TYPE
    SYNTAX       Gauge32
    MAX-ACCESS   read-only
    STATUS       current
    DESCRIPTION
        "Cisco UCS adaptor:EtherIfStatsHist:rxPackets managed
        object property"
    ::= { cucsAdaptorEtherIfStatsHistEntry 21 }

cucsAdaptorEtherIfStatsHistRxPacketsDelta OBJECT-TYPE
    SYNTAX       Gauge32
    MAX-ACCESS   read-only
    STATUS       current
    DESCRIPTION
        "Cisco UCS adaptor:EtherIfStatsHist:rxPacketsDelta
        managed object property"
    ::= { cucsAdaptorEtherIfStatsHistEntry 22 }

cucsAdaptorEtherIfStatsHistRxPacketsDeltaAvg OBJECT-TYPE
    SYNTAX       Gauge32
    MAX-ACCESS   read-only
    STATUS       current
    DESCRIPTION
        "Cisco UCS adaptor:EtherIfStatsHist:rxPacketsDeltaAvg
        managed object property"
    ::= { cucsAdaptorEtherIfStatsHistEntry 23 }

cucsAdaptorEtherIfStatsHistRxPacketsDeltaMax OBJECT-TYPE
    SYNTAX       Gauge32
    MAX-ACCESS   read-only
    STATUS       current
    DESCRIPTION
        "Cisco UCS adaptor:EtherIfStatsHist:rxPacketsDeltaMax
        managed object property"
    ::= { cucsAdaptorEtherIfStatsHistEntry 24 }

cucsAdaptorEtherIfStatsHistRxPacketsDeltaMin OBJECT-TYPE
    SYNTAX       Gauge32
    MAX-ACCESS   read-only
    STATUS       current
    DESCRIPTION
        "Cisco UCS adaptor:EtherIfStatsHist:rxPacketsDeltaMin
        managed object property"
    ::= { cucsAdaptorEtherIfStatsHistEntry 25 }

cucsAdaptorEtherIfStatsHistSuspect OBJECT-TYPE
    SYNTAX       TruthValue
    MAX-ACCESS   read-only
    STATUS       current
    DESCRIPTION
        "Cisco UCS adaptor:EtherIfStatsHist:suspect managed
        object property"
    ::= { cucsAdaptorEtherIfStatsHistEntry 26 }

cucsAdaptorEtherIfStatsHistThresholded OBJECT-TYPE
    SYNTAX       CucsAdaptorEtherIfStatsHistThresholded
    MAX-ACCESS   read-only
    STATUS       current
    DESCRIPTION
        "Cisco UCS adaptor:EtherIfStatsHist:thresholded
        managed object property"
    ::= { cucsAdaptorEtherIfStatsHistEntry 27 }

cucsAdaptorEtherIfStatsHistTimeCollected OBJECT-TYPE
    SYNTAX       DateAndTime
    MAX-ACCESS   read-only
    STATUS       current
    DESCRIPTION
        "Cisco UCS adaptor:EtherIfStatsHist:timeCollected
        managed object property"
    ::= { cucsAdaptorEtherIfStatsHistEntry 28 }

cucsAdaptorEtherIfStatsHistTxBytes OBJECT-TYPE
    SYNTAX       Gauge32
    MAX-ACCESS   read-only
    STATUS       current
    DESCRIPTION
        "Cisco UCS adaptor:EtherIfStatsHist:txBytes managed
        object property"
    ::= { cucsAdaptorEtherIfStatsHistEntry 29 }

cucsAdaptorEtherIfStatsHistTxBytesDelta OBJECT-TYPE
    SYNTAX       Gauge32
    MAX-ACCESS   read-only
    STATUS       current
    DESCRIPTION
        "Cisco UCS adaptor:EtherIfStatsHist:txBytesDelta
        managed object property"
    ::= { cucsAdaptorEtherIfStatsHistEntry 30 }

cucsAdaptorEtherIfStatsHistTxBytesDeltaAvg OBJECT-TYPE
    SYNTAX       Gauge32
    MAX-ACCESS   read-only
    STATUS       current
    DESCRIPTION
        "Cisco UCS adaptor:EtherIfStatsHist:txBytesDeltaAvg
        managed object property"
    ::= { cucsAdaptorEtherIfStatsHistEntry 31 }

cucsAdaptorEtherIfStatsHistTxBytesDeltaMax OBJECT-TYPE
    SYNTAX       Gauge32
    MAX-ACCESS   read-only
    STATUS       current
    DESCRIPTION
        "Cisco UCS adaptor:EtherIfStatsHist:txBytesDeltaMax
        managed object property"
    ::= { cucsAdaptorEtherIfStatsHistEntry 32 }

cucsAdaptorEtherIfStatsHistTxBytesDeltaMin OBJECT-TYPE
    SYNTAX       Gauge32
    MAX-ACCESS   read-only
    STATUS       current
    DESCRIPTION
        "Cisco UCS adaptor:EtherIfStatsHist:txBytesDeltaMin
        managed object property"
    ::= { cucsAdaptorEtherIfStatsHistEntry 33 }

cucsAdaptorEtherIfStatsHistTxDropped OBJECT-TYPE
    SYNTAX       Gauge32
    MAX-ACCESS   read-only
    STATUS       current
    DESCRIPTION
        "Cisco UCS adaptor:EtherIfStatsHist:txDropped managed
        object property"
    ::= { cucsAdaptorEtherIfStatsHistEntry 34 }

cucsAdaptorEtherIfStatsHistTxDroppedDelta OBJECT-TYPE
    SYNTAX       Gauge32
    MAX-ACCESS   read-only
    STATUS       current
    DESCRIPTION
        "Cisco UCS adaptor:EtherIfStatsHist:txDroppedDelta
        managed object property"
    ::= { cucsAdaptorEtherIfStatsHistEntry 35 }

cucsAdaptorEtherIfStatsHistTxDroppedDeltaAvg OBJECT-TYPE
    SYNTAX       Gauge32
    MAX-ACCESS   read-only
    STATUS       current
    DESCRIPTION
        "Cisco UCS adaptor:EtherIfStatsHist:txDroppedDeltaAvg
        managed object property"
    ::= { cucsAdaptorEtherIfStatsHistEntry 36 }

cucsAdaptorEtherIfStatsHistTxDroppedDeltaMax OBJECT-TYPE
    SYNTAX       Gauge32
    MAX-ACCESS   read-only
    STATUS       current
    DESCRIPTION
        "Cisco UCS adaptor:EtherIfStatsHist:txDroppedDeltaMax
        managed object property"
    ::= { cucsAdaptorEtherIfStatsHistEntry 37 }

cucsAdaptorEtherIfStatsHistTxDroppedDeltaMin OBJECT-TYPE
    SYNTAX       Gauge32
    MAX-ACCESS   read-only
    STATUS       current
    DESCRIPTION
        "Cisco UCS adaptor:EtherIfStatsHist:txDroppedDeltaMin
        managed object property"
    ::= { cucsAdaptorEtherIfStatsHistEntry 38 }

cucsAdaptorEtherIfStatsHistTxErrors OBJECT-TYPE
    SYNTAX       Gauge32
    MAX-ACCESS   read-only
    STATUS       current
    DESCRIPTION
        "Cisco UCS adaptor:EtherIfStatsHist:txErrors managed
        object property"
    ::= { cucsAdaptorEtherIfStatsHistEntry 39 }

cucsAdaptorEtherIfStatsHistTxErrorsDelta OBJECT-TYPE
    SYNTAX       Gauge32
    MAX-ACCESS   read-only
    STATUS       current
    DESCRIPTION
        "Cisco UCS adaptor:EtherIfStatsHist:txErrorsDelta
        managed object property"
    ::= { cucsAdaptorEtherIfStatsHistEntry 40 }

cucsAdaptorEtherIfStatsHistTxErrorsDeltaAvg OBJECT-TYPE
    SYNTAX       Gauge32
    MAX-ACCESS   read-only
    STATUS       current
    DESCRIPTION
        "Cisco UCS adaptor:EtherIfStatsHist:txErrorsDeltaAvg
        managed object property"
    ::= { cucsAdaptorEtherIfStatsHistEntry 41 }

cucsAdaptorEtherIfStatsHistTxErrorsDeltaMax OBJECT-TYPE
    SYNTAX       Gauge32
    MAX-ACCESS   read-only
    STATUS       current
    DESCRIPTION
        "Cisco UCS adaptor:EtherIfStatsHist:txErrorsDeltaMax
        managed object property"
    ::= { cucsAdaptorEtherIfStatsHistEntry 42 }

cucsAdaptorEtherIfStatsHistTxErrorsDeltaMin OBJECT-TYPE
    SYNTAX       Gauge32
    MAX-ACCESS   read-only
    STATUS       current
    DESCRIPTION
        "Cisco UCS adaptor:EtherIfStatsHist:txErrorsDeltaMin
        managed object property"
    ::= { cucsAdaptorEtherIfStatsHistEntry 43 }

cucsAdaptorEtherIfStatsHistTxPackets OBJECT-TYPE
    SYNTAX       Gauge32
    MAX-ACCESS   read-only
    STATUS       current
    DESCRIPTION
        "Cisco UCS adaptor:EtherIfStatsHist:txPackets managed
        object property"
    ::= { cucsAdaptorEtherIfStatsHistEntry 44 }

cucsAdaptorEtherIfStatsHistTxPacketsDelta OBJECT-TYPE
    SYNTAX       Gauge32
    MAX-ACCESS   read-only
    STATUS       current
    DESCRIPTION
        "Cisco UCS adaptor:EtherIfStatsHist:txPacketsDelta
        managed object property"
    ::= { cucsAdaptorEtherIfStatsHistEntry 45 }

cucsAdaptorEtherIfStatsHistTxPacketsDeltaAvg OBJECT-TYPE
    SYNTAX       Gauge32
    MAX-ACCESS   read-only
    STATUS       current
    DESCRIPTION
        "Cisco UCS adaptor:EtherIfStatsHist:txPacketsDeltaAvg
        managed object property"
    ::= { cucsAdaptorEtherIfStatsHistEntry 46 }

cucsAdaptorEtherIfStatsHistTxPacketsDeltaMax OBJECT-TYPE
    SYNTAX       Gauge32
    MAX-ACCESS   read-only
    STATUS       current
    DESCRIPTION
        "Cisco UCS adaptor:EtherIfStatsHist:txPacketsDeltaMax
        managed object property"
    ::= { cucsAdaptorEtherIfStatsHistEntry 47 }

cucsAdaptorEtherIfStatsHistTxPacketsDeltaMin OBJECT-TYPE
    SYNTAX       Gauge32
    MAX-ACCESS   read-only
    STATUS       current
    DESCRIPTION
        "Cisco UCS adaptor:EtherIfStatsHist:txPacketsDeltaMin
        managed object property"
    ::= { cucsAdaptorEtherIfStatsHistEntry 48 }

cucsAdaptorExtEthIfTable OBJECT-TYPE
    SYNTAX           SEQUENCE OF CucsAdaptorExtEthIfEntry
    MAX-ACCESS       not-accessible
    STATUS           current
    DESCRIPTION
        "Cisco UCS adaptor:ExtEthIf managed object table"
    ::= { cucsAdaptorObjects 23 }

cucsAdaptorExtEthIfEntry OBJECT-TYPE
    SYNTAX           CucsAdaptorExtEthIfEntry
    MAX-ACCESS       not-accessible
    STATUS           current
    DESCRIPTION
        "Entry for the cucsAdaptorExtEthIfTable table."
    INDEX { cucsAdaptorExtEthIfInstanceId }
    ::= { cucsAdaptorExtEthIfTable 1 }

CucsAdaptorExtEthIfEntry ::= SEQUENCE {
    cucsAdaptorExtEthIfInstanceId                                    CucsManagedObjectId,
    cucsAdaptorExtEthIfDn                                            CucsManagedObjectDn,
    cucsAdaptorExtEthIfRn                                            SnmpAdminString,
    cucsAdaptorExtEthIfAdapterId                                     Gauge32,
    cucsAdaptorExtEthIfAdminState                                    CucsAdaptorExtIfAdminState,
    cucsAdaptorExtEthIfChassisId                                     Gauge32,
    cucsAdaptorExtEthIfDiscovery                                     CucsEtherSatelliteConnectionDisc,
    cucsAdaptorExtEthIfEpDn                                          SnmpAdminString,
    cucsAdaptorExtEthIfFsmDescr                                      SnmpAdminString,
    cucsAdaptorExtEthIfFsmPrev                                       SnmpAdminString,
    cucsAdaptorExtEthIfFsmProgr                                      Gauge32,
    cucsAdaptorExtEthIfFsmRmtInvErrCode                              Gauge32,
    cucsAdaptorExtEthIfFsmRmtInvErrDescr                             SnmpAdminString,
    cucsAdaptorExtEthIfFsmRmtInvRslt                                 CucsConditionRemoteInvRslt,
    cucsAdaptorExtEthIfFsmStageDescr                                 SnmpAdminString,
    cucsAdaptorExtEthIfFsmStamp                                      DateAndTime,
    cucsAdaptorExtEthIfFsmStatus                                     SnmpAdminString,
    cucsAdaptorExtEthIfFsmTry                                        Gauge32,
    cucsAdaptorExtEthIfId                                            Gauge32,
    cucsAdaptorExtEthIfIfRole                                        CucsNetworkPortRole,
    cucsAdaptorExtEthIfIfType                                        CucsNetworkPhysEpIfType,
    cucsAdaptorExtEthIfLinkState                                     CucsAdaptorLinkState,
    cucsAdaptorExtEthIfLocale                                        CucsNetworkLocale,
    cucsAdaptorExtEthIfMac                                           MacAddress,
    cucsAdaptorExtEthIfName                                          SnmpAdminString,
    cucsAdaptorExtEthIfOperState                                     CucsNetworkPortOperState,
    cucsAdaptorExtEthIfOperStateDesc                                 SnmpAdminString,
    cucsAdaptorExtEthIfPeerDn                                        SnmpAdminString,
    cucsAdaptorExtEthIfPeerPortId                                    Gauge32,
    cucsAdaptorExtEthIfPeerSlotId                                    Gauge32,
    cucsAdaptorExtEthIfPhysEpDn                                      SnmpAdminString,
    cucsAdaptorExtEthIfPortId                                        Gauge32,
    cucsAdaptorExtEthIfPurpose                                       CucsAdaptorPurpose,
    cucsAdaptorExtEthIfSide                                          CucsNetworkSide,
    cucsAdaptorExtEthIfSlotId                                        Gauge32,
    cucsAdaptorExtEthIfSwitchId                                      CucsNetworkSwitchId,
    cucsAdaptorExtEthIfTransport                                     CucsNetworkTransport,
    cucsAdaptorExtEthIfType                                          CucsNetworkConnectionType,
    cucsAdaptorExtEthIfPeerChassisId                                 Gauge32,
    cucsAdaptorExtEthIfMacAddrType                                   CucsAddressType,
    cucsAdaptorExtEthIfLldpMac                                       MacAddress,
    cucsAdaptorExtEthIfAggrPortId                                    Gauge32,
    cucsAdaptorExtEthIfPeerAggrPortId                                Gauge32
}

cucsAdaptorExtEthIfInstanceId OBJECT-TYPE
    SYNTAX       CucsManagedObjectId
    MAX-ACCESS   not-accessible
    STATUS       current
    DESCRIPTION
        "Instance identifier of the managed object."
    ::= { cucsAdaptorExtEthIfEntry 1 }

cucsAdaptorExtEthIfDn OBJECT-TYPE
    SYNTAX       CucsManagedObjectDn
    MAX-ACCESS   read-only
    STATUS       current
    DESCRIPTION
        "Cisco UCS adaptor:ExtEthIf:dn managed object property"
    ::= { cucsAdaptorExtEthIfEntry 2 }

cucsAdaptorExtEthIfRn OBJECT-TYPE
    SYNTAX       SnmpAdminString
    MAX-ACCESS   read-only
    STATUS       current
    DESCRIPTION
        "Cisco UCS adaptor:ExtEthIf:rn managed object property"
    ::= { cucsAdaptorExtEthIfEntry 3 }

cucsAdaptorExtEthIfAdapterId OBJECT-TYPE
    SYNTAX       Gauge32
    MAX-ACCESS   read-only
    STATUS       current
    DESCRIPTION
        "Cisco UCS adaptor:ExtEthIf:adapterId managed object property"
    ::= { cucsAdaptorExtEthIfEntry 4 }

cucsAdaptorExtEthIfAdminState OBJECT-TYPE
    SYNTAX       CucsAdaptorExtIfAdminState
    MAX-ACCESS   read-only
    STATUS       current
    DESCRIPTION
        "Cisco UCS adaptor:ExtEthIf:adminState managed object property"
    ::= { cucsAdaptorExtEthIfEntry 5 }

cucsAdaptorExtEthIfChassisId OBJECT-TYPE
    SYNTAX       Gauge32
    MAX-ACCESS   read-only
    STATUS       current
    DESCRIPTION
        "Cisco UCS adaptor:ExtEthIf:chassisId managed object property"
    ::= { cucsAdaptorExtEthIfEntry 6 }

cucsAdaptorExtEthIfDiscovery OBJECT-TYPE
    SYNTAX       CucsEtherSatelliteConnectionDisc
    MAX-ACCESS   read-only
    STATUS       current
    DESCRIPTION
        "Cisco UCS adaptor:ExtEthIf:discovery managed object property"
    ::= { cucsAdaptorExtEthIfEntry 7 }

cucsAdaptorExtEthIfEpDn OBJECT-TYPE
    SYNTAX       SnmpAdminString
    MAX-ACCESS   read-only
    STATUS       current
    DESCRIPTION
        "Cisco UCS adaptor:ExtEthIf:epDn managed object property"
    ::= { cucsAdaptorExtEthIfEntry 8 }

cucsAdaptorExtEthIfFsmDescr OBJECT-TYPE
    SYNTAX       SnmpAdminString
    MAX-ACCESS   read-only
    STATUS       current
    DESCRIPTION
        "Cisco UCS adaptor:ExtEthIf:fsmDescr managed object property"
    ::= { cucsAdaptorExtEthIfEntry 9 }

cucsAdaptorExtEthIfFsmPrev OBJECT-TYPE
    SYNTAX       SnmpAdminString
    MAX-ACCESS   read-only
    STATUS       current
    DESCRIPTION
        "Cisco UCS adaptor:ExtEthIf:fsmPrev managed object property"
    ::= { cucsAdaptorExtEthIfEntry 10 }

cucsAdaptorExtEthIfFsmProgr OBJECT-TYPE
    SYNTAX       Gauge32
    MAX-ACCESS   read-only
    STATUS       current
    DESCRIPTION
        "Cisco UCS adaptor:ExtEthIf:fsmProgr managed object property"
    ::= { cucsAdaptorExtEthIfEntry 11 }

cucsAdaptorExtEthIfFsmRmtInvErrCode OBJECT-TYPE
    SYNTAX       Gauge32
    MAX-ACCESS   read-only
    STATUS       current
    DESCRIPTION
        "Cisco UCS adaptor:ExtEthIf:fsmRmtInvErrCode managed
        object property"
    ::= { cucsAdaptorExtEthIfEntry 12 }

cucsAdaptorExtEthIfFsmRmtInvErrDescr OBJECT-TYPE
    SYNTAX       SnmpAdminString
    MAX-ACCESS   read-only
    STATUS       current
    DESCRIPTION
        "Cisco UCS adaptor:ExtEthIf:fsmRmtInvErrDescr managed
        object property"
    ::= { cucsAdaptorExtEthIfEntry 13 }

cucsAdaptorExtEthIfFsmRmtInvRslt OBJECT-TYPE
    SYNTAX       CucsConditionRemoteInvRslt
    MAX-ACCESS   read-only
    STATUS       current
    DESCRIPTION
        "Cisco UCS adaptor:ExtEthIf:fsmRmtInvRslt managed object property"
    ::= { cucsAdaptorExtEthIfEntry 14 }

cucsAdaptorExtEthIfFsmStageDescr OBJECT-TYPE
    SYNTAX       SnmpAdminString
    MAX-ACCESS   read-only
    STATUS       current
    DESCRIPTION
        "Cisco UCS adaptor:ExtEthIf:fsmStageDescr managed object property"
    ::= { cucsAdaptorExtEthIfEntry 15 }

cucsAdaptorExtEthIfFsmStamp OBJECT-TYPE
    SYNTAX       DateAndTime
    MAX-ACCESS   read-only
    STATUS       current
    DESCRIPTION
        "Cisco UCS adaptor:ExtEthIf:fsmStamp managed object property"
    ::= { cucsAdaptorExtEthIfEntry 16 }

cucsAdaptorExtEthIfFsmStatus OBJECT-TYPE
    SYNTAX       SnmpAdminString
    MAX-ACCESS   read-only
    STATUS       current
    DESCRIPTION
        "Cisco UCS adaptor:ExtEthIf:fsmStatus managed object property"
    ::= { cucsAdaptorExtEthIfEntry 17 }

cucsAdaptorExtEthIfFsmTry OBJECT-TYPE
    SYNTAX       Gauge32
    MAX-ACCESS   read-only
    STATUS       current
    DESCRIPTION
        "Cisco UCS adaptor:ExtEthIf:fsmTry managed object property"
    ::= { cucsAdaptorExtEthIfEntry 18 }

cucsAdaptorExtEthIfId OBJECT-TYPE
    SYNTAX       Gauge32
    MAX-ACCESS   read-only
    STATUS       current
    DESCRIPTION
        "Cisco UCS adaptor:ExtEthIf:id managed object property"
    ::= { cucsAdaptorExtEthIfEntry 19 }

cucsAdaptorExtEthIfIfRole OBJECT-TYPE
    SYNTAX       CucsNetworkPortRole
    MAX-ACCESS   read-only
    STATUS       current
    DESCRIPTION
        "Cisco UCS adaptor:ExtEthIf:ifRole managed object property"
    ::= { cucsAdaptorExtEthIfEntry 20 }

cucsAdaptorExtEthIfIfType OBJECT-TYPE
    SYNTAX       CucsNetworkPhysEpIfType
    MAX-ACCESS   read-only
    STATUS       current
    DESCRIPTION
        "Cisco UCS adaptor:ExtEthIf:ifType managed object property"
    ::= { cucsAdaptorExtEthIfEntry 21 }

cucsAdaptorExtEthIfLinkState OBJECT-TYPE
    SYNTAX       CucsAdaptorLinkState
    MAX-ACCESS   read-only
    STATUS       current
    DESCRIPTION
        "Cisco UCS adaptor:ExtEthIf:linkState managed object property"
    ::= { cucsAdaptorExtEthIfEntry 22 }

cucsAdaptorExtEthIfLocale OBJECT-TYPE
    SYNTAX       CucsNetworkLocale
    MAX-ACCESS   read-only
    STATUS       current
    DESCRIPTION
        "Cisco UCS adaptor:ExtEthIf:locale managed object property"
    ::= { cucsAdaptorExtEthIfEntry 23 }

cucsAdaptorExtEthIfMac OBJECT-TYPE
    SYNTAX       MacAddress
    MAX-ACCESS   read-only
    STATUS       current
    DESCRIPTION
        "Cisco UCS adaptor:ExtEthIf:mac managed object property"
    ::= { cucsAdaptorExtEthIfEntry 24 }

cucsAdaptorExtEthIfName OBJECT-TYPE
    SYNTAX       SnmpAdminString
    MAX-ACCESS   read-only
    STATUS       current
    DESCRIPTION
        "Cisco UCS adaptor:ExtEthIf:name managed object property"
    ::= { cucsAdaptorExtEthIfEntry 25 }

cucsAdaptorExtEthIfOperState OBJECT-TYPE
    SYNTAX       CucsNetworkPortOperState
    MAX-ACCESS   read-only
    STATUS       current
    DESCRIPTION
        "Cisco UCS adaptor:ExtEthIf:operState managed object property"
    ::= { cucsAdaptorExtEthIfEntry 26 }

cucsAdaptorExtEthIfOperStateDesc OBJECT-TYPE
    SYNTAX       SnmpAdminString
    MAX-ACCESS   read-only
    STATUS       current
    DESCRIPTION
        "Cisco UCS adaptor:ExtEthIf:operStateDesc managed object property"
    ::= { cucsAdaptorExtEthIfEntry 27 }

cucsAdaptorExtEthIfPeerDn OBJECT-TYPE
    SYNTAX       SnmpAdminString
    MAX-ACCESS   read-only
    STATUS       current
    DESCRIPTION
        "Cisco UCS adaptor:ExtEthIf:peerDn managed object property"
    ::= { cucsAdaptorExtEthIfEntry 28 }

cucsAdaptorExtEthIfPeerPortId OBJECT-TYPE
    SYNTAX       Gauge32
    MAX-ACCESS   read-only
    STATUS       current
    DESCRIPTION
        "Cisco UCS adaptor:ExtEthIf:peerPortId managed object property"
    ::= { cucsAdaptorExtEthIfEntry 29 }

cucsAdaptorExtEthIfPeerSlotId OBJECT-TYPE
    SYNTAX       Gauge32
    MAX-ACCESS   read-only
    STATUS       current
    DESCRIPTION
        "Cisco UCS adaptor:ExtEthIf:peerSlotId managed object property"
    ::= { cucsAdaptorExtEthIfEntry 30 }

cucsAdaptorExtEthIfPhysEpDn OBJECT-TYPE
    SYNTAX       SnmpAdminString
    MAX-ACCESS   read-only
    STATUS       current
    DESCRIPTION
        "Cisco UCS adaptor:ExtEthIf:physEpDn managed object property"
    ::= { cucsAdaptorExtEthIfEntry 31 }

cucsAdaptorExtEthIfPortId OBJECT-TYPE
    SYNTAX       Gauge32
    MAX-ACCESS   read-only
    STATUS       current
    DESCRIPTION
        "Cisco UCS adaptor:ExtEthIf:portId managed object property"
    ::= { cucsAdaptorExtEthIfEntry 32 }

cucsAdaptorExtEthIfPurpose OBJECT-TYPE
    SYNTAX       CucsAdaptorPurpose
    MAX-ACCESS   read-only
    STATUS       current
    DESCRIPTION
        "Cisco UCS adaptor:ExtEthIf:purpose managed object property"
    ::= { cucsAdaptorExtEthIfEntry 33 }

cucsAdaptorExtEthIfSide OBJECT-TYPE
    SYNTAX       CucsNetworkSide
    MAX-ACCESS   read-only
    STATUS       current
    DESCRIPTION
        "Cisco UCS adaptor:ExtEthIf:side managed object property"
    ::= { cucsAdaptorExtEthIfEntry 34 }

cucsAdaptorExtEthIfSlotId OBJECT-TYPE
    SYNTAX       Gauge32
    MAX-ACCESS   read-only
    STATUS       current
    DESCRIPTION
        "Cisco UCS adaptor:ExtEthIf:slotId managed object property"
    ::= { cucsAdaptorExtEthIfEntry 35 }

cucsAdaptorExtEthIfSwitchId OBJECT-TYPE
    SYNTAX       CucsNetworkSwitchId
    MAX-ACCESS   read-only
    STATUS       current
    DESCRIPTION
        "Cisco UCS adaptor:ExtEthIf:switchId managed object property"
    ::= { cucsAdaptorExtEthIfEntry 36 }

cucsAdaptorExtEthIfTransport OBJECT-TYPE
    SYNTAX       CucsNetworkTransport
    MAX-ACCESS   read-only
    STATUS       current
    DESCRIPTION
        "Cisco UCS adaptor:ExtEthIf:transport managed object property"
    ::= { cucsAdaptorExtEthIfEntry 37 }

cucsAdaptorExtEthIfType OBJECT-TYPE
    SYNTAX       CucsNetworkConnectionType
    MAX-ACCESS   read-only
    STATUS       current
    DESCRIPTION
        "Cisco UCS adaptor:ExtEthIf:type managed object property"
    ::= { cucsAdaptorExtEthIfEntry 38 }

cucsAdaptorExtEthIfPeerChassisId OBJECT-TYPE
    SYNTAX       Gauge32
    MAX-ACCESS   read-only
    STATUS       current
    DESCRIPTION
        "Cisco UCS adaptor:ExtEthIf:peerChassisId managed object property"
    ::= { cucsAdaptorExtEthIfEntry 39 }

cucsAdaptorExtEthIfMacAddrType OBJECT-TYPE
    SYNTAX       CucsAddressType
    MAX-ACCESS   read-only
    STATUS       current
    DESCRIPTION
        "Cisco UCS adaptor:ExtEthIf:macAddrType managed object property"
    ::= { cucsAdaptorExtEthIfEntry 40 }

cucsAdaptorExtEthIfLldpMac OBJECT-TYPE
    SYNTAX       MacAddress
    MAX-ACCESS   read-only
    STATUS       current
    DESCRIPTION
        "Cisco UCS adaptor:ExtEthIf:lldpMac managed object property"
    ::= { cucsAdaptorExtEthIfEntry 41 }

cucsAdaptorExtEthIfAggrPortId OBJECT-TYPE
    SYNTAX       Gauge32
    MAX-ACCESS   read-only
    STATUS       current
    DESCRIPTION
        "Cisco UCS adaptor:ExtEthIf:aggrPortId managed object property"
    ::= { cucsAdaptorExtEthIfEntry 42 }

cucsAdaptorExtEthIfPeerAggrPortId OBJECT-TYPE
    SYNTAX       Gauge32
    MAX-ACCESS   read-only
    STATUS       current
    DESCRIPTION
        "Cisco UCS adaptor:ExtEthIf:peerAggrPortId managed
        object property"
    ::= { cucsAdaptorExtEthIfEntry 43 }

cucsAdaptorExtEthIfFsmTable OBJECT-TYPE
    SYNTAX           SEQUENCE OF CucsAdaptorExtEthIfFsmEntry
    MAX-ACCESS       not-accessible
    STATUS           current
    DESCRIPTION
        "Cisco UCS adaptor:ExtEthIfFsm managed object table"
    ::= { cucsAdaptorObjects 108 }

cucsAdaptorExtEthIfFsmEntry OBJECT-TYPE
    SYNTAX           CucsAdaptorExtEthIfFsmEntry
    MAX-ACCESS       not-accessible
    STATUS           current
    DESCRIPTION
        "Entry for the cucsAdaptorExtEthIfFsmTable table."
    INDEX { cucsAdaptorExtEthIfFsmInstanceId }
    ::= { cucsAdaptorExtEthIfFsmTable 1 }

CucsAdaptorExtEthIfFsmEntry ::= SEQUENCE {
    cucsAdaptorExtEthIfFsmInstanceId                                 CucsManagedObjectId,
    cucsAdaptorExtEthIfFsmDn                                         CucsManagedObjectDn,
    cucsAdaptorExtEthIfFsmRn                                         SnmpAdminString,
    cucsAdaptorExtEthIfFsmCompletionTime                             DateAndTime,
    cucsAdaptorExtEthIfFsmCurrentFsm                                 CucsAdaptorExtEthIfFsmCurrentFsm,
    cucsAdaptorExtEthIfFsmDescrData                                  SnmpAdminString,
    cucsAdaptorExtEthIfFsmFsmStatus                                  CucsFsmFsmStageStatus,
    cucsAdaptorExtEthIfFsmProgress                                   Gauge32,
    cucsAdaptorExtEthIfFsmRmtErrCode                                 Gauge32,
    cucsAdaptorExtEthIfFsmRmtErrDescr                                SnmpAdminString,
    cucsAdaptorExtEthIfFsmRmtRslt                                    CucsConditionRemoteInvRslt
}

cucsAdaptorExtEthIfFsmInstanceId OBJECT-TYPE
    SYNTAX       CucsManagedObjectId
    MAX-ACCESS   not-accessible
    STATUS       current
    DESCRIPTION
        "Instance identifier of the managed object."
    ::= { cucsAdaptorExtEthIfFsmEntry 1 }

cucsAdaptorExtEthIfFsmDn OBJECT-TYPE
    SYNTAX       CucsManagedObjectDn
    MAX-ACCESS   read-only
    STATUS       current
    DESCRIPTION
        "Cisco UCS adaptor:ExtEthIfFsm:dn managed object property"
    ::= { cucsAdaptorExtEthIfFsmEntry 2 }

cucsAdaptorExtEthIfFsmRn OBJECT-TYPE
    SYNTAX       SnmpAdminString
    MAX-ACCESS   read-only
    STATUS       current
    DESCRIPTION
        "Cisco UCS adaptor:ExtEthIfFsm:rn managed object property"
    ::= { cucsAdaptorExtEthIfFsmEntry 3 }

cucsAdaptorExtEthIfFsmCompletionTime OBJECT-TYPE
    SYNTAX       DateAndTime
    MAX-ACCESS   read-only
    STATUS       current
    DESCRIPTION
        "Cisco UCS adaptor:ExtEthIfFsm:completionTime managed
        object property"
    ::= { cucsAdaptorExtEthIfFsmEntry 4 }

cucsAdaptorExtEthIfFsmCurrentFsm OBJECT-TYPE
    SYNTAX       CucsAdaptorExtEthIfFsmCurrentFsm
    MAX-ACCESS   read-only
    STATUS       current
    DESCRIPTION
        "Cisco UCS adaptor:ExtEthIfFsm:currentFsm managed object property"
    ::= { cucsAdaptorExtEthIfFsmEntry 5 }

cucsAdaptorExtEthIfFsmDescrData OBJECT-TYPE
    SYNTAX       SnmpAdminString
    MAX-ACCESS   read-only
    STATUS       current
    DESCRIPTION
        "Cisco UCS adaptor:ExtEthIfFsm:descr managed object property"
    ::= { cucsAdaptorExtEthIfFsmEntry 6 }

cucsAdaptorExtEthIfFsmFsmStatus OBJECT-TYPE
    SYNTAX       CucsFsmFsmStageStatus
    MAX-ACCESS   read-only
    STATUS       current
    DESCRIPTION
        "Cisco UCS adaptor:ExtEthIfFsm:fsmStatus managed object property"
    ::= { cucsAdaptorExtEthIfFsmEntry 7 }

cucsAdaptorExtEthIfFsmProgress OBJECT-TYPE
    SYNTAX       Gauge32
    MAX-ACCESS   read-only
    STATUS       current
    DESCRIPTION
        "Cisco UCS adaptor:ExtEthIfFsm:progress managed object property"
    ::= { cucsAdaptorExtEthIfFsmEntry 8 }

cucsAdaptorExtEthIfFsmRmtErrCode OBJECT-TYPE
    SYNTAX       Gauge32
    MAX-ACCESS   read-only
    STATUS       current
    DESCRIPTION
        "Cisco UCS adaptor:ExtEthIfFsm:rmtErrCode managed object property"
    ::= { cucsAdaptorExtEthIfFsmEntry 9 }

cucsAdaptorExtEthIfFsmRmtErrDescr OBJECT-TYPE
    SYNTAX       SnmpAdminString
    MAX-ACCESS   read-only
    STATUS       current
    DESCRIPTION
        "Cisco UCS adaptor:ExtEthIfFsm:rmtErrDescr managed
        object property"
    ::= { cucsAdaptorExtEthIfFsmEntry 10 }

cucsAdaptorExtEthIfFsmRmtRslt OBJECT-TYPE
    SYNTAX       CucsConditionRemoteInvRslt
    MAX-ACCESS   read-only
    STATUS       current
    DESCRIPTION
        "Cisco UCS adaptor:ExtEthIfFsm:rmtRslt managed object property"
    ::= { cucsAdaptorExtEthIfFsmEntry 11 }

cucsAdaptorExtEthIfFsmStageTable OBJECT-TYPE
    SYNTAX           SEQUENCE OF CucsAdaptorExtEthIfFsmStageEntry
    MAX-ACCESS       not-accessible
    STATUS           current
    DESCRIPTION
        "Cisco UCS adaptor:ExtEthIfFsmStage managed object table"
    ::= { cucsAdaptorObjects 109 }

cucsAdaptorExtEthIfFsmStageEntry OBJECT-TYPE
    SYNTAX           CucsAdaptorExtEthIfFsmStageEntry
    MAX-ACCESS       not-accessible
    STATUS           current
    DESCRIPTION
        "Entry for the cucsAdaptorExtEthIfFsmStageTable table."
    INDEX { cucsAdaptorExtEthIfFsmStageInstanceId }
    ::= { cucsAdaptorExtEthIfFsmStageTable 1 }

CucsAdaptorExtEthIfFsmStageEntry ::= SEQUENCE {
    cucsAdaptorExtEthIfFsmStageInstanceId                            CucsManagedObjectId,
    cucsAdaptorExtEthIfFsmStageDn                                    CucsManagedObjectDn,
    cucsAdaptorExtEthIfFsmStageRn                                    SnmpAdminString,
    cucsAdaptorExtEthIfFsmStageDescrData                             SnmpAdminString,
    cucsAdaptorExtEthIfFsmStageLastUpdateTime                        DateAndTime,
    cucsAdaptorExtEthIfFsmStageName                                  CucsAdaptorExtEthIfFsmStageName,
    cucsAdaptorExtEthIfFsmStageOrder                                 Gauge32,
    cucsAdaptorExtEthIfFsmStageRetry                                 Gauge32,
    cucsAdaptorExtEthIfFsmStageStageStatus                           CucsFsmFsmStageStatus
}

cucsAdaptorExtEthIfFsmStageInstanceId OBJECT-TYPE
    SYNTAX       CucsManagedObjectId
    MAX-ACCESS   not-accessible
    STATUS       current
    DESCRIPTION
        "Instance identifier of the managed object."
    ::= { cucsAdaptorExtEthIfFsmStageEntry 1 }

cucsAdaptorExtEthIfFsmStageDn OBJECT-TYPE
    SYNTAX       CucsManagedObjectDn
    MAX-ACCESS   read-only
    STATUS       current
    DESCRIPTION
        "Cisco UCS adaptor:ExtEthIfFsmStage:dn managed object property"
    ::= { cucsAdaptorExtEthIfFsmStageEntry 2 }

cucsAdaptorExtEthIfFsmStageRn OBJECT-TYPE
    SYNTAX       SnmpAdminString
    MAX-ACCESS   read-only
    STATUS       current
    DESCRIPTION
        "Cisco UCS adaptor:ExtEthIfFsmStage:rn managed object property"
    ::= { cucsAdaptorExtEthIfFsmStageEntry 3 }

cucsAdaptorExtEthIfFsmStageDescrData OBJECT-TYPE
    SYNTAX       SnmpAdminString
    MAX-ACCESS   read-only
    STATUS       current
    DESCRIPTION
        "Cisco UCS adaptor:ExtEthIfFsmStage:descr managed object property"
    ::= { cucsAdaptorExtEthIfFsmStageEntry 4 }

cucsAdaptorExtEthIfFsmStageLastUpdateTime OBJECT-TYPE
    SYNTAX       DateAndTime
    MAX-ACCESS   read-only
    STATUS       current
    DESCRIPTION
        "Cisco UCS adaptor:ExtEthIfFsmStage:lastUpdateTime
        managed object property"
    ::= { cucsAdaptorExtEthIfFsmStageEntry 5 }

cucsAdaptorExtEthIfFsmStageName OBJECT-TYPE
    SYNTAX       CucsAdaptorExtEthIfFsmStageName
    MAX-ACCESS   read-only
    STATUS       current
    DESCRIPTION
        "Cisco UCS adaptor:ExtEthIfFsmStage:name managed object property"
    ::= { cucsAdaptorExtEthIfFsmStageEntry 6 }

cucsAdaptorExtEthIfFsmStageOrder OBJECT-TYPE
    SYNTAX       Gauge32
    MAX-ACCESS   read-only
    STATUS       current
    DESCRIPTION
        "Cisco UCS adaptor:ExtEthIfFsmStage:order managed object property"
    ::= { cucsAdaptorExtEthIfFsmStageEntry 7 }

cucsAdaptorExtEthIfFsmStageRetry OBJECT-TYPE
    SYNTAX       Gauge32
    MAX-ACCESS   read-only
    STATUS       current
    DESCRIPTION
        "Cisco UCS adaptor:ExtEthIfFsmStage:retry managed object property"
    ::= { cucsAdaptorExtEthIfFsmStageEntry 8 }

cucsAdaptorExtEthIfFsmStageStageStatus OBJECT-TYPE
    SYNTAX       CucsFsmFsmStageStatus
    MAX-ACCESS   read-only
    STATUS       current
    DESCRIPTION
        "Cisco UCS adaptor:ExtEthIfFsmStage:stageStatus
        managed object property"
    ::= { cucsAdaptorExtEthIfFsmStageEntry 9 }

cucsAdaptorExtEthIfFsmTaskTable OBJECT-TYPE
    SYNTAX           SEQUENCE OF CucsAdaptorExtEthIfFsmTaskEntry
    MAX-ACCESS       not-accessible
    STATUS           current
    DESCRIPTION
        "Cisco UCS adaptor:ExtEthIfFsmTask managed object table"
    ::= { cucsAdaptorObjects 24 }

cucsAdaptorExtEthIfFsmTaskEntry OBJECT-TYPE
    SYNTAX           CucsAdaptorExtEthIfFsmTaskEntry
    MAX-ACCESS       not-accessible
    STATUS           current
    DESCRIPTION
        "Entry for the cucsAdaptorExtEthIfFsmTaskTable table."
    INDEX { cucsAdaptorExtEthIfFsmTaskInstanceId }
    ::= { cucsAdaptorExtEthIfFsmTaskTable 1 }

CucsAdaptorExtEthIfFsmTaskEntry ::= SEQUENCE {
    cucsAdaptorExtEthIfFsmTaskInstanceId                             CucsManagedObjectId,
    cucsAdaptorExtEthIfFsmTaskDn                                     CucsManagedObjectDn,
    cucsAdaptorExtEthIfFsmTaskRn                                     SnmpAdminString,
    cucsAdaptorExtEthIfFsmTaskCompletion                             CucsFsmCompletion,
    cucsAdaptorExtEthIfFsmTaskFlags                                  CucsFsmFlags,
    cucsAdaptorExtEthIfFsmTaskItem                                   CucsAdaptorExtEthIfFsmTaskItem,
    cucsAdaptorExtEthIfFsmTaskSeqId                                  Gauge32
}

cucsAdaptorExtEthIfFsmTaskInstanceId OBJECT-TYPE
    SYNTAX       CucsManagedObjectId
    MAX-ACCESS   not-accessible
    STATUS       current
    DESCRIPTION
        "Instance identifier of the managed object."
    ::= { cucsAdaptorExtEthIfFsmTaskEntry 1 }

cucsAdaptorExtEthIfFsmTaskDn OBJECT-TYPE
    SYNTAX       CucsManagedObjectDn
    MAX-ACCESS   read-only
    STATUS       current
    DESCRIPTION
        "Cisco UCS adaptor:ExtEthIfFsmTask:dn managed object property"
    ::= { cucsAdaptorExtEthIfFsmTaskEntry 2 }

cucsAdaptorExtEthIfFsmTaskRn OBJECT-TYPE
    SYNTAX       SnmpAdminString
    MAX-ACCESS   read-only
    STATUS       current
    DESCRIPTION
        "Cisco UCS adaptor:ExtEthIfFsmTask:rn managed object property"
    ::= { cucsAdaptorExtEthIfFsmTaskEntry 3 }

cucsAdaptorExtEthIfFsmTaskCompletion OBJECT-TYPE
    SYNTAX       CucsFsmCompletion
    MAX-ACCESS   read-only
    STATUS       current
    DESCRIPTION
        "Cisco UCS adaptor:ExtEthIfFsmTask:completion managed
        object property"
    ::= { cucsAdaptorExtEthIfFsmTaskEntry 4 }

cucsAdaptorExtEthIfFsmTaskFlags OBJECT-TYPE
    SYNTAX       CucsFsmFlags
    MAX-ACCESS   read-only
    STATUS       current
    DESCRIPTION
        "Cisco UCS adaptor:ExtEthIfFsmTask:flags managed object property"
    ::= { cucsAdaptorExtEthIfFsmTaskEntry 5 }

cucsAdaptorExtEthIfFsmTaskItem OBJECT-TYPE
    SYNTAX       CucsAdaptorExtEthIfFsmTaskItem
    MAX-ACCESS   read-only
    STATUS       current
    DESCRIPTION
        "Cisco UCS adaptor:ExtEthIfFsmTask:item managed object property"
    ::= { cucsAdaptorExtEthIfFsmTaskEntry 6 }

cucsAdaptorExtEthIfFsmTaskSeqId OBJECT-TYPE
    SYNTAX       Gauge32
    MAX-ACCESS   read-only
    STATUS       current
    DESCRIPTION
        "Cisco UCS adaptor:ExtEthIfFsmTask:seqId managed object property"
    ::= { cucsAdaptorExtEthIfFsmTaskEntry 7 }

cucsAdaptorExtEthIfPcTable OBJECT-TYPE
    SYNTAX           SEQUENCE OF CucsAdaptorExtEthIfPcEntry
    MAX-ACCESS       not-accessible
    STATUS           current
    DESCRIPTION
        "Cisco UCS adaptor:ExtEthIfPc managed object table"
    ::= { cucsAdaptorObjects 97 }

cucsAdaptorExtEthIfPcEntry OBJECT-TYPE
    SYNTAX           CucsAdaptorExtEthIfPcEntry
    MAX-ACCESS       not-accessible
    STATUS           current
    DESCRIPTION
        "Entry for the cucsAdaptorExtEthIfPcTable table."
    INDEX { cucsAdaptorExtEthIfPcInstanceId }
    ::= { cucsAdaptorExtEthIfPcTable 1 }

CucsAdaptorExtEthIfPcEntry ::= SEQUENCE {
    cucsAdaptorExtEthIfPcInstanceId                                  CucsManagedObjectId,
    cucsAdaptorExtEthIfPcDn                                          CucsManagedObjectDn,
    cucsAdaptorExtEthIfPcRn                                          SnmpAdminString,
    cucsAdaptorExtEthIfPcEpDn                                        SnmpAdminString,
    cucsAdaptorExtEthIfPcFltAggr                                     Unsigned64,
    cucsAdaptorExtEthIfPcIfRole                                      CucsAdaptorExtIfPcIfRole,
    cucsAdaptorExtEthIfPcIfType                                      CucsAdaptorCIoEpIfType,
    cucsAdaptorExtEthIfPcLocale                                      CucsAdaptorExternalPcLocale,
    cucsAdaptorExtEthIfPcMac                                         MacAddress,
    cucsAdaptorExtEthIfPcName                                        SnmpAdminString,
    cucsAdaptorExtEthIfPcOperSpeed                                   CucsPortEthSpeed,
    cucsAdaptorExtEthIfPcOperState                                   CucsNetworkPortOperState,
    cucsAdaptorExtEthIfPcPeerDn                                      SnmpAdminString,
    cucsAdaptorExtEthIfPcPortId                                      CucsAdaptorExtEthIfPcPortId,
    cucsAdaptorExtEthIfPcStateQual                                   SnmpAdminString,
    cucsAdaptorExtEthIfPcSwitchId                                    CucsNetworkSwitchId,
    cucsAdaptorExtEthIfPcTransport                                   CucsAdaptorExtEthIfPcTransport,
    cucsAdaptorExtEthIfPcType                                        CucsAdaptorExtIfPcType
}

cucsAdaptorExtEthIfPcInstanceId OBJECT-TYPE
    SYNTAX       CucsManagedObjectId
    MAX-ACCESS   not-accessible
    STATUS       current
    DESCRIPTION
        "Instance identifier of the managed object."
    ::= { cucsAdaptorExtEthIfPcEntry 1 }

cucsAdaptorExtEthIfPcDn OBJECT-TYPE
    SYNTAX       CucsManagedObjectDn
    MAX-ACCESS   read-only
    STATUS       current
    DESCRIPTION
        "Cisco UCS adaptor:ExtEthIfPc:dn managed object property"
    ::= { cucsAdaptorExtEthIfPcEntry 2 }

cucsAdaptorExtEthIfPcRn OBJECT-TYPE
    SYNTAX       SnmpAdminString
    MAX-ACCESS   read-only
    STATUS       current
    DESCRIPTION
        "Cisco UCS adaptor:ExtEthIfPc:rn managed object property"
    ::= { cucsAdaptorExtEthIfPcEntry 3 }

cucsAdaptorExtEthIfPcEpDn OBJECT-TYPE
    SYNTAX       SnmpAdminString
    MAX-ACCESS   read-only
    STATUS       current
    DESCRIPTION
        "Cisco UCS adaptor:ExtEthIfPc:epDn managed object property"
    ::= { cucsAdaptorExtEthIfPcEntry 4 }

cucsAdaptorExtEthIfPcFltAggr OBJECT-TYPE
    SYNTAX       Unsigned64
    MAX-ACCESS   read-only
    STATUS       current
    DESCRIPTION
        "Cisco UCS adaptor:ExtEthIfPc:fltAggr managed object property"
    ::= { cucsAdaptorExtEthIfPcEntry 5 }

cucsAdaptorExtEthIfPcIfRole OBJECT-TYPE
    SYNTAX       CucsAdaptorExtIfPcIfRole
    MAX-ACCESS   read-only
    STATUS       current
    DESCRIPTION
        "Cisco UCS adaptor:ExtEthIfPc:ifRole managed object property"
    ::= { cucsAdaptorExtEthIfPcEntry 6 }

cucsAdaptorExtEthIfPcIfType OBJECT-TYPE
    SYNTAX       CucsAdaptorCIoEpIfType
    MAX-ACCESS   read-only
    STATUS       current
    DESCRIPTION
        "Cisco UCS adaptor:ExtEthIfPc:ifType managed object property"
    ::= { cucsAdaptorExtEthIfPcEntry 7 }

cucsAdaptorExtEthIfPcLocale OBJECT-TYPE
    SYNTAX       CucsAdaptorExternalPcLocale
    MAX-ACCESS   read-only
    STATUS       current
    DESCRIPTION
        "Cisco UCS adaptor:ExtEthIfPc:locale managed object property"
    ::= { cucsAdaptorExtEthIfPcEntry 8 }

cucsAdaptorExtEthIfPcMac OBJECT-TYPE
    SYNTAX       MacAddress
    MAX-ACCESS   read-only
    STATUS       current
    DESCRIPTION
        "Cisco UCS adaptor:ExtEthIfPc:mac managed object property"
    ::= { cucsAdaptorExtEthIfPcEntry 9 }

cucsAdaptorExtEthIfPcName OBJECT-TYPE
    SYNTAX       SnmpAdminString
    MAX-ACCESS   read-only
    STATUS       current
    DESCRIPTION
        "Cisco UCS adaptor:ExtEthIfPc:name managed object property"
    ::= { cucsAdaptorExtEthIfPcEntry 10 }

cucsAdaptorExtEthIfPcOperSpeed OBJECT-TYPE
    SYNTAX       CucsPortEthSpeed
    MAX-ACCESS   read-only
    STATUS       current
    DESCRIPTION
        "Cisco UCS adaptor:ExtEthIfPc:operSpeed managed object property"
    ::= { cucsAdaptorExtEthIfPcEntry 11 }

cucsAdaptorExtEthIfPcOperState OBJECT-TYPE
    SYNTAX       CucsNetworkPortOperState
    MAX-ACCESS   read-only
    STATUS       current
    DESCRIPTION
        "Cisco UCS adaptor:ExtEthIfPc:operState managed object property"
    ::= { cucsAdaptorExtEthIfPcEntry 12 }

cucsAdaptorExtEthIfPcPeerDn OBJECT-TYPE
    SYNTAX       SnmpAdminString
    MAX-ACCESS   read-only
    STATUS       current
    DESCRIPTION
        "Cisco UCS adaptor:ExtEthIfPc:peerDn managed object property"
    ::= { cucsAdaptorExtEthIfPcEntry 13 }

cucsAdaptorExtEthIfPcPortId OBJECT-TYPE
    SYNTAX       CucsAdaptorExtEthIfPcPortId
    MAX-ACCESS   read-only
    STATUS       current
    DESCRIPTION
        "Cisco UCS adaptor:ExtEthIfPc:portId managed object property"
    ::= { cucsAdaptorExtEthIfPcEntry 14 }

cucsAdaptorExtEthIfPcStateQual OBJECT-TYPE
    SYNTAX       SnmpAdminString
    MAX-ACCESS   read-only
    STATUS       current
    DESCRIPTION
        "Cisco UCS adaptor:ExtEthIfPc:stateQual managed object property"
    ::= { cucsAdaptorExtEthIfPcEntry 15 }

cucsAdaptorExtEthIfPcSwitchId OBJECT-TYPE
    SYNTAX       CucsNetworkSwitchId
    MAX-ACCESS   read-only
    STATUS       current
    DESCRIPTION
        "Cisco UCS adaptor:ExtEthIfPc:switchId managed object property"
    ::= { cucsAdaptorExtEthIfPcEntry 16 }

cucsAdaptorExtEthIfPcTransport OBJECT-TYPE
    SYNTAX       CucsAdaptorExtEthIfPcTransport
    MAX-ACCESS   read-only
    STATUS       current
    DESCRIPTION
        "Cisco UCS adaptor:ExtEthIfPc:transport managed object property"
    ::= { cucsAdaptorExtEthIfPcEntry 17 }

cucsAdaptorExtEthIfPcType OBJECT-TYPE
    SYNTAX       CucsAdaptorExtIfPcType
    MAX-ACCESS   read-only
    STATUS       current
    DESCRIPTION
        "Cisco UCS adaptor:ExtEthIfPc:type managed object property"
    ::= { cucsAdaptorExtEthIfPcEntry 18 }

cucsAdaptorExtEthIfPcEpTable OBJECT-TYPE
    SYNTAX           SEQUENCE OF CucsAdaptorExtEthIfPcEpEntry
    MAX-ACCESS       not-accessible
    STATUS           current
    DESCRIPTION
        "Cisco UCS adaptor:ExtEthIfPcEp managed object table"
    ::= { cucsAdaptorObjects 98 }

cucsAdaptorExtEthIfPcEpEntry OBJECT-TYPE
    SYNTAX           CucsAdaptorExtEthIfPcEpEntry
    MAX-ACCESS       not-accessible
    STATUS           current
    DESCRIPTION
        "Entry for the cucsAdaptorExtEthIfPcEpTable table."
    INDEX { cucsAdaptorExtEthIfPcEpInstanceId }
    ::= { cucsAdaptorExtEthIfPcEpTable 1 }

CucsAdaptorExtEthIfPcEpEntry ::= SEQUENCE {
    cucsAdaptorExtEthIfPcEpInstanceId                                CucsManagedObjectId,
    cucsAdaptorExtEthIfPcEpDnData                                    CucsManagedObjectDn,
    cucsAdaptorExtEthIfPcEpRn                                        SnmpAdminString,
    cucsAdaptorExtEthIfPcEpChassisId                                 Gauge32,
    cucsAdaptorExtEthIfPcEpEpDn                                      SnmpAdminString,
    cucsAdaptorExtEthIfPcEpIfRole                                    CucsAdaptorExtIfEpIfRole,
    cucsAdaptorExtEthIfPcEpIfType                                    CucsAdaptorPIoEpIfType,
    cucsAdaptorExtEthIfPcEpLocale                                    CucsAdaptorExternalEpLocale,
    cucsAdaptorExtEthIfPcEpMembership                                CucsFabricMembershipStatus,
    cucsAdaptorExtEthIfPcEpName                                      SnmpAdminString,
    cucsAdaptorExtEthIfPcEpPeerChassisId                             Gauge32,
    cucsAdaptorExtEthIfPcEpPeerDn                                    SnmpAdminString,
    cucsAdaptorExtEthIfPcEpPeerPortId                                Gauge32,
    cucsAdaptorExtEthIfPcEpPeerSlotId                                Gauge32,
    cucsAdaptorExtEthIfPcEpPortId                                    CucsAdaptorExtEthIfPcEpPortId,
    cucsAdaptorExtEthIfPcEpSlotId                                    CucsAdaptorExtEthIfPcEpSlotId,
    cucsAdaptorExtEthIfPcEpSwitchId                                  CucsNetworkSwitchId,
    cucsAdaptorExtEthIfPcEpTransport                                 CucsNetworkTransport,
    cucsAdaptorExtEthIfPcEpType                                      CucsAdaptorExtIfEpType,
    cucsAdaptorExtEthIfPcEpAggrPortId                                Gauge32,
    cucsAdaptorExtEthIfPcEpPeerAggrPortId                            Gauge32
}

cucsAdaptorExtEthIfPcEpInstanceId OBJECT-TYPE
    SYNTAX       CucsManagedObjectId
    MAX-ACCESS   not-accessible
    STATUS       current
    DESCRIPTION
        "Instance identifier of the managed object."
    ::= { cucsAdaptorExtEthIfPcEpEntry 1 }

cucsAdaptorExtEthIfPcEpDnData OBJECT-TYPE
    SYNTAX       CucsManagedObjectDn
    MAX-ACCESS   read-only
    STATUS       current
    DESCRIPTION
        "Cisco UCS adaptor:ExtEthIfPcEp:dn managed object property"
    ::= { cucsAdaptorExtEthIfPcEpEntry 2 }

cucsAdaptorExtEthIfPcEpRn OBJECT-TYPE
    SYNTAX       SnmpAdminString
    MAX-ACCESS   read-only
    STATUS       current
    DESCRIPTION
        "Cisco UCS adaptor:ExtEthIfPcEp:rn managed object property"
    ::= { cucsAdaptorExtEthIfPcEpEntry 3 }

cucsAdaptorExtEthIfPcEpChassisId OBJECT-TYPE
    SYNTAX       Gauge32
    MAX-ACCESS   read-only
    STATUS       current
    DESCRIPTION
        "Cisco UCS adaptor:ExtEthIfPcEp:chassisId managed object property"
    ::= { cucsAdaptorExtEthIfPcEpEntry 4 }

cucsAdaptorExtEthIfPcEpEpDn OBJECT-TYPE
    SYNTAX       SnmpAdminString
    MAX-ACCESS   read-only
    STATUS       current
    DESCRIPTION
        "Cisco UCS adaptor:ExtEthIfPcEp:epDn managed object property"
    ::= { cucsAdaptorExtEthIfPcEpEntry 5 }

cucsAdaptorExtEthIfPcEpIfRole OBJECT-TYPE
    SYNTAX       CucsAdaptorExtIfEpIfRole
    MAX-ACCESS   read-only
    STATUS       current
    DESCRIPTION
        "Cisco UCS adaptor:ExtEthIfPcEp:ifRole managed object property"
    ::= { cucsAdaptorExtEthIfPcEpEntry 6 }

cucsAdaptorExtEthIfPcEpIfType OBJECT-TYPE
    SYNTAX       CucsAdaptorPIoEpIfType
    MAX-ACCESS   read-only
    STATUS       current
    DESCRIPTION
        "Cisco UCS adaptor:ExtEthIfPcEp:ifType managed object property"
    ::= { cucsAdaptorExtEthIfPcEpEntry 7 }

cucsAdaptorExtEthIfPcEpLocale OBJECT-TYPE
    SYNTAX       CucsAdaptorExternalEpLocale
    MAX-ACCESS   read-only
    STATUS       current
    DESCRIPTION
        "Cisco UCS adaptor:ExtEthIfPcEp:locale managed object property"
    ::= { cucsAdaptorExtEthIfPcEpEntry 8 }

cucsAdaptorExtEthIfPcEpMembership OBJECT-TYPE
    SYNTAX       CucsFabricMembershipStatus
    MAX-ACCESS   read-only
    STATUS       current
    DESCRIPTION
        "Cisco UCS adaptor:ExtEthIfPcEp:membership managed
        object property"
    ::= { cucsAdaptorExtEthIfPcEpEntry 9 }

cucsAdaptorExtEthIfPcEpName OBJECT-TYPE
    SYNTAX       SnmpAdminString
    MAX-ACCESS   read-only
    STATUS       current
    DESCRIPTION
        "Cisco UCS adaptor:ExtEthIfPcEp:name managed object property"
    ::= { cucsAdaptorExtEthIfPcEpEntry 10 }

cucsAdaptorExtEthIfPcEpPeerChassisId OBJECT-TYPE
    SYNTAX       Gauge32
    MAX-ACCESS   read-only
    STATUS       current
    DESCRIPTION
        "Cisco UCS adaptor:ExtEthIfPcEp:peerChassisId managed
        object property"
    ::= { cucsAdaptorExtEthIfPcEpEntry 11 }

cucsAdaptorExtEthIfPcEpPeerDn OBJECT-TYPE
    SYNTAX       SnmpAdminString
    MAX-ACCESS   read-only
    STATUS       current
    DESCRIPTION
        "Cisco UCS adaptor:ExtEthIfPcEp:peerDn managed object property"
    ::= { cucsAdaptorExtEthIfPcEpEntry 12 }

cucsAdaptorExtEthIfPcEpPeerPortId OBJECT-TYPE
    SYNTAX       Gauge32
    MAX-ACCESS   read-only
    STATUS       current
    DESCRIPTION
        "Cisco UCS adaptor:ExtEthIfPcEp:peerPortId managed
        object property"
    ::= { cucsAdaptorExtEthIfPcEpEntry 13 }

cucsAdaptorExtEthIfPcEpPeerSlotId OBJECT-TYPE
    SYNTAX       Gauge32
    MAX-ACCESS   read-only
    STATUS       current
    DESCRIPTION
        "Cisco UCS adaptor:ExtEthIfPcEp:peerSlotId managed
        object property"
    ::= { cucsAdaptorExtEthIfPcEpEntry 14 }

cucsAdaptorExtEthIfPcEpPortId OBJECT-TYPE
    SYNTAX       CucsAdaptorExtEthIfPcEpPortId
    MAX-ACCESS   read-only
    STATUS       current
    DESCRIPTION
        "Cisco UCS adaptor:ExtEthIfPcEp:portId managed object property"
    ::= { cucsAdaptorExtEthIfPcEpEntry 15 }

cucsAdaptorExtEthIfPcEpSlotId OBJECT-TYPE
    SYNTAX       CucsAdaptorExtEthIfPcEpSlotId
    MAX-ACCESS   read-only
    STATUS       current
    DESCRIPTION
        "Cisco UCS adaptor:ExtEthIfPcEp:slotId managed object property"
    ::= { cucsAdaptorExtEthIfPcEpEntry 16 }

cucsAdaptorExtEthIfPcEpSwitchId OBJECT-TYPE
    SYNTAX       CucsNetworkSwitchId
    MAX-ACCESS   read-only
    STATUS       current
    DESCRIPTION
        "Cisco UCS adaptor:ExtEthIfPcEp:switchId managed object property"
    ::= { cucsAdaptorExtEthIfPcEpEntry 17 }

cucsAdaptorExtEthIfPcEpTransport OBJECT-TYPE
    SYNTAX       CucsNetworkTransport
    MAX-ACCESS   read-only
    STATUS       current
    DESCRIPTION
        "Cisco UCS adaptor:ExtEthIfPcEp:transport managed object property"
    ::= { cucsAdaptorExtEthIfPcEpEntry 18 }

cucsAdaptorExtEthIfPcEpType OBJECT-TYPE
    SYNTAX       CucsAdaptorExtIfEpType
    MAX-ACCESS   read-only
    STATUS       current
    DESCRIPTION
        "Cisco UCS adaptor:ExtEthIfPcEp:type managed object property"
    ::= { cucsAdaptorExtEthIfPcEpEntry 19 }

cucsAdaptorExtEthIfPcEpAggrPortId OBJECT-TYPE
    SYNTAX       Gauge32
    MAX-ACCESS   read-only
    STATUS       current
    DESCRIPTION
        "Cisco UCS adaptor:ExtEthIfPcEp:aggrPortId managed
        object property"
    ::= { cucsAdaptorExtEthIfPcEpEntry 20 }

cucsAdaptorExtEthIfPcEpPeerAggrPortId OBJECT-TYPE
    SYNTAX       Gauge32
    MAX-ACCESS   read-only
    STATUS       current
    DESCRIPTION
        "Cisco UCS adaptor:ExtEthIfPcEp:peerAggrPortId
        managed object property"
    ::= { cucsAdaptorExtEthIfPcEpEntry 21 }

cucsAdaptorExtIpV6RssHashProfileTable OBJECT-TYPE
    SYNTAX           SEQUENCE OF CucsAdaptorExtIpV6RssHashProfileEntry
    MAX-ACCESS       not-accessible
    STATUS           current
    DESCRIPTION
        "Cisco UCS adaptor:ExtIpV6RssHashProfile managed object table"
    ::= { cucsAdaptorObjects 25 }

cucsAdaptorExtIpV6RssHashProfileEntry OBJECT-TYPE
    SYNTAX           CucsAdaptorExtIpV6RssHashProfileEntry
    MAX-ACCESS       not-accessible
    STATUS           current
    DESCRIPTION
        "Entry for the cucsAdaptorExtIpV6RssHashProfileTable table."
    INDEX { cucsAdaptorExtIpV6RssHashProfileInstanceId }
    ::= { cucsAdaptorExtIpV6RssHashProfileTable 1 }

CucsAdaptorExtIpV6RssHashProfileEntry ::= SEQUENCE {
    cucsAdaptorExtIpV6RssHashProfileInstanceId                       CucsManagedObjectId,
    cucsAdaptorExtIpV6RssHashProfileDn                               CucsManagedObjectDn,
    cucsAdaptorExtIpV6RssHashProfileRn                               SnmpAdminString,
    cucsAdaptorExtIpV6RssHashProfileIpHash                           CucsAdaptorExtIpV6RssHashProfileIpHash,
    cucsAdaptorExtIpV6RssHashProfileTcpHash                          CucsAdaptorExtIpV6RssHashProfileTcpHash
}

cucsAdaptorExtIpV6RssHashProfileInstanceId OBJECT-TYPE
    SYNTAX       CucsManagedObjectId
    MAX-ACCESS   not-accessible
    STATUS       current
    DESCRIPTION
        "Instance identifier of the managed object."
    ::= { cucsAdaptorExtIpV6RssHashProfileEntry 1 }

cucsAdaptorExtIpV6RssHashProfileDn OBJECT-TYPE
    SYNTAX       CucsManagedObjectDn
    MAX-ACCESS   read-only
    STATUS       current
    DESCRIPTION
        "Cisco UCS adaptor:ExtIpV6RssHashProfile:dn managed
        object property"
    ::= { cucsAdaptorExtIpV6RssHashProfileEntry 2 }

cucsAdaptorExtIpV6RssHashProfileRn OBJECT-TYPE
    SYNTAX       SnmpAdminString
    MAX-ACCESS   read-only
    STATUS       current
    DESCRIPTION
        "Cisco UCS adaptor:ExtIpV6RssHashProfile:rn managed
        object property"
    ::= { cucsAdaptorExtIpV6RssHashProfileEntry 3 }

cucsAdaptorExtIpV6RssHashProfileIpHash OBJECT-TYPE
    SYNTAX       CucsAdaptorExtIpV6RssHashProfileIpHash
    MAX-ACCESS   read-only
    STATUS       current
    DESCRIPTION
        "Cisco UCS adaptor:ExtIpV6RssHashProfile:ipHash
        managed object property"
    ::= { cucsAdaptorExtIpV6RssHashProfileEntry 4 }

cucsAdaptorExtIpV6RssHashProfileTcpHash OBJECT-TYPE
    SYNTAX       CucsAdaptorExtIpV6RssHashProfileTcpHash
    MAX-ACCESS   read-only
    STATUS       current
    DESCRIPTION
        "Cisco UCS adaptor:ExtIpV6RssHashProfile:tcpHash
        managed object property"
    ::= { cucsAdaptorExtIpV6RssHashProfileEntry 5 }

cucsAdaptorFamilyTypeDefTable OBJECT-TYPE
    SYNTAX           SEQUENCE OF CucsAdaptorFamilyTypeDefEntry
    MAX-ACCESS       not-accessible
    STATUS           current
    DESCRIPTION
        "Cisco UCS adaptor:FamilyTypeDef managed object table"
    ::= { cucsAdaptorObjects 106 }

cucsAdaptorFamilyTypeDefEntry OBJECT-TYPE
    SYNTAX           CucsAdaptorFamilyTypeDefEntry
    MAX-ACCESS       not-accessible
    STATUS           current
    DESCRIPTION
        "Entry for the cucsAdaptorFamilyTypeDefTable table."
    INDEX { cucsAdaptorFamilyTypeDefInstanceId }
    ::= { cucsAdaptorFamilyTypeDefTable 1 }

CucsAdaptorFamilyTypeDefEntry ::= SEQUENCE {
    cucsAdaptorFamilyTypeDefInstanceId                               CucsManagedObjectId,
    cucsAdaptorFamilyTypeDefDn                                       CucsManagedObjectDn,
    cucsAdaptorFamilyTypeDefRn                                       SnmpAdminString,
    cucsAdaptorFamilyTypeDefIsPassthrough                            TruthValue,
    cucsAdaptorFamilyTypeDefNumDcePorts                              Gauge32,
    cucsAdaptorFamilyTypeDefPortFamily                               SnmpAdminString,
    cucsAdaptorFamilyTypeDefType                                     SnmpAdminString,
    cucsAdaptorFamilyTypeDefIsMultiPort                              TruthValue,
    cucsAdaptorFamilyTypeDefIsRetimerRequired                        TruthValue
}

cucsAdaptorFamilyTypeDefInstanceId OBJECT-TYPE
    SYNTAX       CucsManagedObjectId
    MAX-ACCESS   not-accessible
    STATUS       current
    DESCRIPTION
        "Instance identifier of the managed object."
    ::= { cucsAdaptorFamilyTypeDefEntry 1 }

cucsAdaptorFamilyTypeDefDn OBJECT-TYPE
    SYNTAX       CucsManagedObjectDn
    MAX-ACCESS   read-only
    STATUS       current
    DESCRIPTION
        "Cisco UCS adaptor:FamilyTypeDef:dn managed object property"
    ::= { cucsAdaptorFamilyTypeDefEntry 2 }

cucsAdaptorFamilyTypeDefRn OBJECT-TYPE
    SYNTAX       SnmpAdminString
    MAX-ACCESS   read-only
    STATUS       current
    DESCRIPTION
        "Cisco UCS adaptor:FamilyTypeDef:rn managed object property"
    ::= { cucsAdaptorFamilyTypeDefEntry 3 }

cucsAdaptorFamilyTypeDefIsPassthrough OBJECT-TYPE
    SYNTAX       TruthValue
    MAX-ACCESS   read-only
    STATUS       current
    DESCRIPTION
        "Cisco UCS adaptor:FamilyTypeDef:isPassthrough
        managed object property"
    ::= { cucsAdaptorFamilyTypeDefEntry 4 }

cucsAdaptorFamilyTypeDefNumDcePorts OBJECT-TYPE
    SYNTAX       Gauge32
    MAX-ACCESS   read-only
    STATUS       current
    DESCRIPTION
        "Cisco UCS adaptor:FamilyTypeDef:numDcePorts managed
        object property"
    ::= { cucsAdaptorFamilyTypeDefEntry 5 }

cucsAdaptorFamilyTypeDefPortFamily OBJECT-TYPE
    SYNTAX       SnmpAdminString
    MAX-ACCESS   read-only
    STATUS       current
    DESCRIPTION
        "Cisco UCS adaptor:FamilyTypeDef:portFamily managed
        object property"
    ::= { cucsAdaptorFamilyTypeDefEntry 6 }

cucsAdaptorFamilyTypeDefType OBJECT-TYPE
    SYNTAX       SnmpAdminString
    MAX-ACCESS   read-only
    STATUS       current
    DESCRIPTION
        "Cisco UCS adaptor:FamilyTypeDef:type managed object property"
    ::= { cucsAdaptorFamilyTypeDefEntry 7 }

cucsAdaptorFamilyTypeDefIsMultiPort OBJECT-TYPE
    SYNTAX       TruthValue
    MAX-ACCESS   read-only
    STATUS       current
    DESCRIPTION
        "Cisco UCS adaptor:FamilyTypeDef:isMultiPort managed
        object property"
    ::= { cucsAdaptorFamilyTypeDefEntry 8 }

cucsAdaptorFamilyTypeDefIsRetimerRequired OBJECT-TYPE
    SYNTAX       TruthValue
    MAX-ACCESS   read-only
    STATUS       current
    DESCRIPTION
        "Cisco UCS adaptor:FamilyTypeDef:isRetimerRequired
        managed object property"
    ::= { cucsAdaptorFamilyTypeDefEntry 9 }

cucsAdaptorFcCdbWorkQueueProfileTable OBJECT-TYPE
    SYNTAX           SEQUENCE OF CucsAdaptorFcCdbWorkQueueProfileEntry
    MAX-ACCESS       not-accessible
    STATUS           current
    DESCRIPTION
        "Cisco UCS adaptor:FcCdbWorkQueueProfile managed object table"
    ::= { cucsAdaptorObjects 26 }

cucsAdaptorFcCdbWorkQueueProfileEntry OBJECT-TYPE
    SYNTAX           CucsAdaptorFcCdbWorkQueueProfileEntry
    MAX-ACCESS       not-accessible
    STATUS           current
    DESCRIPTION
        "Entry for the cucsAdaptorFcCdbWorkQueueProfileTable table."
    INDEX { cucsAdaptorFcCdbWorkQueueProfileInstanceId }
    ::= { cucsAdaptorFcCdbWorkQueueProfileTable 1 }

CucsAdaptorFcCdbWorkQueueProfileEntry ::= SEQUENCE {
    cucsAdaptorFcCdbWorkQueueProfileInstanceId                       CucsManagedObjectId,
    cucsAdaptorFcCdbWorkQueueProfileDn                               CucsManagedObjectDn,
    cucsAdaptorFcCdbWorkQueueProfileRn                               SnmpAdminString,
    cucsAdaptorFcCdbWorkQueueProfileCount                            Gauge32,
    cucsAdaptorFcCdbWorkQueueProfileRingSize                         Gauge32
}

cucsAdaptorFcCdbWorkQueueProfileInstanceId OBJECT-TYPE
    SYNTAX       CucsManagedObjectId
    MAX-ACCESS   not-accessible
    STATUS       current
    DESCRIPTION
        "Instance identifier of the managed object."
    ::= { cucsAdaptorFcCdbWorkQueueProfileEntry 1 }

cucsAdaptorFcCdbWorkQueueProfileDn OBJECT-TYPE
    SYNTAX       CucsManagedObjectDn
    MAX-ACCESS   read-only
    STATUS       current
    DESCRIPTION
        "Cisco UCS adaptor:FcCdbWorkQueueProfile:dn managed
        object property"
    ::= { cucsAdaptorFcCdbWorkQueueProfileEntry 2 }

cucsAdaptorFcCdbWorkQueueProfileRn OBJECT-TYPE
    SYNTAX       SnmpAdminString
    MAX-ACCESS   read-only
    STATUS       current
    DESCRIPTION
        "Cisco UCS adaptor:FcCdbWorkQueueProfile:rn managed
        object property"
    ::= { cucsAdaptorFcCdbWorkQueueProfileEntry 3 }

cucsAdaptorFcCdbWorkQueueProfileCount OBJECT-TYPE
    SYNTAX       Gauge32
    MAX-ACCESS   read-only
    STATUS       current
    DESCRIPTION
        "Cisco UCS adaptor:FcCdbWorkQueueProfile:count
        managed object property"
    ::= { cucsAdaptorFcCdbWorkQueueProfileEntry 4 }

cucsAdaptorFcCdbWorkQueueProfileRingSize OBJECT-TYPE
    SYNTAX       Gauge32
    MAX-ACCESS   read-only
    STATUS       current
    DESCRIPTION
        "Cisco UCS adaptor:FcCdbWorkQueueProfile:ringSize
        managed object property"
    ::= { cucsAdaptorFcCdbWorkQueueProfileEntry 5 }

cucsAdaptorFcErrorRecoveryProfileTable OBJECT-TYPE
    SYNTAX           SEQUENCE OF CucsAdaptorFcErrorRecoveryProfileEntry
    MAX-ACCESS       not-accessible
    STATUS           current
    DESCRIPTION
        "Cisco UCS adaptor:FcErrorRecoveryProfile managed object table"
    ::= { cucsAdaptorObjects 27 }

cucsAdaptorFcErrorRecoveryProfileEntry OBJECT-TYPE
    SYNTAX           CucsAdaptorFcErrorRecoveryProfileEntry
    MAX-ACCESS       not-accessible
    STATUS           current
    DESCRIPTION
        "Entry for the cucsAdaptorFcErrorRecoveryProfileTable table."
    INDEX { cucsAdaptorFcErrorRecoveryProfileInstanceId }
    ::= { cucsAdaptorFcErrorRecoveryProfileTable 1 }

CucsAdaptorFcErrorRecoveryProfileEntry ::= SEQUENCE {
    cucsAdaptorFcErrorRecoveryProfileInstanceId                      CucsManagedObjectId,
    cucsAdaptorFcErrorRecoveryProfileDn                              CucsManagedObjectDn,
    cucsAdaptorFcErrorRecoveryProfileRn                              SnmpAdminString,
    cucsAdaptorFcErrorRecoveryProfileErrorDetectTimeout              Gauge32,
    cucsAdaptorFcErrorRecoveryProfileFcpErrorRecovery                CucsAdaptorFcErrorRecoveryProfileFcpErrorRecovery,
    cucsAdaptorFcErrorRecoveryProfileLinkDownTimeout                 Gauge32,
    cucsAdaptorFcErrorRecoveryProfilePortDownIoRetryCount            Gauge32,
    cucsAdaptorFcErrorRecoveryProfilePortDownTimeout                 Gauge32,
    cucsAdaptorFcErrorRecoveryProfileResourceAllocationTimeout       Gauge32
}

cucsAdaptorFcErrorRecoveryProfileInstanceId OBJECT-TYPE
    SYNTAX       CucsManagedObjectId
    MAX-ACCESS   not-accessible
    STATUS       current
    DESCRIPTION
        "Instance identifier of the managed object."
    ::= { cucsAdaptorFcErrorRecoveryProfileEntry 1 }

cucsAdaptorFcErrorRecoveryProfileDn OBJECT-TYPE
    SYNTAX       CucsManagedObjectDn
    MAX-ACCESS   read-only
    STATUS       current
    DESCRIPTION
        "Cisco UCS adaptor:FcErrorRecoveryProfile:dn managed
        object property"
    ::= { cucsAdaptorFcErrorRecoveryProfileEntry 2 }

cucsAdaptorFcErrorRecoveryProfileRn OBJECT-TYPE
    SYNTAX       SnmpAdminString
    MAX-ACCESS   read-only
    STATUS       current
    DESCRIPTION
        "Cisco UCS adaptor:FcErrorRecoveryProfile:rn managed
        object property"
    ::= { cucsAdaptorFcErrorRecoveryProfileEntry 3 }

cucsAdaptorFcErrorRecoveryProfileErrorDetectTimeout OBJECT-TYPE
    SYNTAX       Gauge32
    MAX-ACCESS   read-only
    STATUS       current
    DESCRIPTION
        "Cisco UCS adaptor:FcErrorRecoveryProfile:errorDetectTimeout
        managed object property"
    ::= { cucsAdaptorFcErrorRecoveryProfileEntry 4 }

cucsAdaptorFcErrorRecoveryProfileFcpErrorRecovery OBJECT-TYPE
    SYNTAX       CucsAdaptorFcErrorRecoveryProfileFcpErrorRecovery
    MAX-ACCESS   read-only
    STATUS       current
    DESCRIPTION
        "Cisco UCS adaptor:FcErrorRecoveryProfile:fcpErrorRecovery
        managed object property"
    ::= { cucsAdaptorFcErrorRecoveryProfileEntry 5 }

cucsAdaptorFcErrorRecoveryProfileLinkDownTimeout OBJECT-TYPE
    SYNTAX       Gauge32
    MAX-ACCESS   read-only
    STATUS       current
    DESCRIPTION
        "Cisco UCS adaptor:FcErrorRecoveryProfile:linkDownTimeout
        managed object property"
    ::= { cucsAdaptorFcErrorRecoveryProfileEntry 6 }

cucsAdaptorFcErrorRecoveryProfilePortDownIoRetryCount OBJECT-TYPE
    SYNTAX       Gauge32
    MAX-ACCESS   read-only
    STATUS       current
    DESCRIPTION
        "Cisco UCS adaptor:FcErrorRecoveryProfile:portDownIoRetryCount
        managed object property"
    ::= { cucsAdaptorFcErrorRecoveryProfileEntry 7 }

cucsAdaptorFcErrorRecoveryProfilePortDownTimeout OBJECT-TYPE
    SYNTAX       Gauge32
    MAX-ACCESS   read-only
    STATUS       current
    DESCRIPTION
        "Cisco UCS adaptor:FcErrorRecoveryProfile:portDownTimeout
        managed object property"
    ::= { cucsAdaptorFcErrorRecoveryProfileEntry 8 }

cucsAdaptorFcErrorRecoveryProfileResourceAllocationTimeout OBJECT-TYPE
    SYNTAX       Gauge32
    MAX-ACCESS   read-only
    STATUS       current
    DESCRIPTION
        "Cisco UCS adaptor:FcErrorRecoveryProfile:resourceAllocationTimeou
        t managed object property"
    ::= { cucsAdaptorFcErrorRecoveryProfileEntry 9 }

cucsAdaptorFcFnicProfileTable OBJECT-TYPE
    SYNTAX           SEQUENCE OF CucsAdaptorFcFnicProfileEntry
    MAX-ACCESS       not-accessible
    STATUS           current
    DESCRIPTION
        "Cisco UCS adaptor:FcFnicProfile managed object table"
    ::= { cucsAdaptorObjects 137 }

cucsAdaptorFcFnicProfileEntry OBJECT-TYPE
    SYNTAX           CucsAdaptorFcFnicProfileEntry
    MAX-ACCESS       not-accessible
    STATUS           current
    DESCRIPTION
        "Entry for the cucsAdaptorFcFnicProfileTable table."
    INDEX { cucsAdaptorFcFnicProfileInstanceId }
    ::= { cucsAdaptorFcFnicProfileTable 1 }

CucsAdaptorFcFnicProfileEntry ::= SEQUENCE {
    cucsAdaptorFcFnicProfileInstanceId                               CucsManagedObjectId,
    cucsAdaptorFcFnicProfileDn                                       CucsManagedObjectDn,
    cucsAdaptorFcFnicProfileRn                                       SnmpAdminString,
    cucsAdaptorFcFnicProfileIoRetryTimeout                           Gauge32,
    cucsAdaptorFcFnicProfileLunQueueDepth                            Gauge32
}

cucsAdaptorFcFnicProfileInstanceId OBJECT-TYPE
    SYNTAX       CucsManagedObjectId
    MAX-ACCESS   not-accessible
    STATUS       current
    DESCRIPTION
        "Instance identifier of the managed object."
    ::= { cucsAdaptorFcFnicProfileEntry 1 }

cucsAdaptorFcFnicProfileDn OBJECT-TYPE
    SYNTAX       CucsManagedObjectDn
    MAX-ACCESS   read-only
    STATUS       current
    DESCRIPTION
        "Cisco UCS adaptor:FcFnicProfile:dn managed object property"
    ::= { cucsAdaptorFcFnicProfileEntry 2 }

cucsAdaptorFcFnicProfileRn OBJECT-TYPE
    SYNTAX       SnmpAdminString
    MAX-ACCESS   read-only
    STATUS       current
    DESCRIPTION
        "Cisco UCS adaptor:FcFnicProfile:rn managed object property"
    ::= { cucsAdaptorFcFnicProfileEntry 3 }

cucsAdaptorFcFnicProfileIoRetryTimeout OBJECT-TYPE
    SYNTAX       Gauge32
    MAX-ACCESS   read-only
    STATUS       current
    DESCRIPTION
        "Cisco UCS adaptor:FcFnicProfile:ioRetryTimeout
        managed object property"
    ::= { cucsAdaptorFcFnicProfileEntry 4 }

cucsAdaptorFcFnicProfileLunQueueDepth OBJECT-TYPE
    SYNTAX       Gauge32
    MAX-ACCESS   read-only
    STATUS       current
    DESCRIPTION
        "Cisco UCS adaptor:FcFnicProfile:lunQueueDepth
        managed object property"
    ::= { cucsAdaptorFcFnicProfileEntry 5 }

cucsAdaptorFcIfEventStatsTable OBJECT-TYPE
    SYNTAX           SEQUENCE OF CucsAdaptorFcIfEventStatsEntry
    MAX-ACCESS       not-accessible
    STATUS           current
    DESCRIPTION
        "Cisco UCS adaptor:FcIfEventStats managed object table"
    ::= { cucsAdaptorObjects 28 }

cucsAdaptorFcIfEventStatsEntry OBJECT-TYPE
    SYNTAX           CucsAdaptorFcIfEventStatsEntry
    MAX-ACCESS       not-accessible
    STATUS           current
    DESCRIPTION
        "Entry for the cucsAdaptorFcIfEventStatsTable table."
    INDEX { cucsAdaptorFcIfEventStatsInstanceId }
    ::= { cucsAdaptorFcIfEventStatsTable 1 }

CucsAdaptorFcIfEventStatsEntry ::= SEQUENCE {
    cucsAdaptorFcIfEventStatsInstanceId                              CucsManagedObjectId,
    cucsAdaptorFcIfEventStatsDn                                      CucsManagedObjectDn,
    cucsAdaptorFcIfEventStatsRn                                      SnmpAdminString,
    cucsAdaptorFcIfEventStatsIntervals                               Gauge32,
    cucsAdaptorFcIfEventStatsInvalidCRCCount                         Unsigned64,
    cucsAdaptorFcIfEventStatsInvalidCRCCountDelta                    Counter64,
    cucsAdaptorFcIfEventStatsInvalidCRCCountDeltaAvg                 Unsigned64,
    cucsAdaptorFcIfEventStatsInvalidCRCCountDeltaMax                 Unsigned64,
    cucsAdaptorFcIfEventStatsInvalidCRCCountDeltaMin                 Unsigned64,
    cucsAdaptorFcIfEventStatsLinkFailureCount                        Unsigned64,
    cucsAdaptorFcIfEventStatsLinkFailureCountDelta                   Counter64,
    cucsAdaptorFcIfEventStatsLinkFailureCountDeltaAvg                Unsigned64,
    cucsAdaptorFcIfEventStatsLinkFailureCountDeltaMax                Unsigned64,
    cucsAdaptorFcIfEventStatsLinkFailureCountDeltaMin                Unsigned64,
    cucsAdaptorFcIfEventStatsLipCount                                Unsigned64,
    cucsAdaptorFcIfEventStatsLipCountDelta                           Counter64,
    cucsAdaptorFcIfEventStatsLipCountDeltaAvg                        Unsigned64,
    cucsAdaptorFcIfEventStatsLipCountDeltaMax                        Unsigned64,
    cucsAdaptorFcIfEventStatsLipCountDeltaMin                        Unsigned64,
    cucsAdaptorFcIfEventStatsLossOfSignalCount                       Unsigned64,
    cucsAdaptorFcIfEventStatsLossOfSignalCountDelta                  Counter64,
    cucsAdaptorFcIfEventStatsLossOfSignalCountDeltaAvg               Unsigned64,
    cucsAdaptorFcIfEventStatsLossOfSignalCountDeltaMax               Unsigned64,
    cucsAdaptorFcIfEventStatsLossOfSignalCountDeltaMin               Unsigned64,
    cucsAdaptorFcIfEventStatsLossOfSyncCount                         Unsigned64,
    cucsAdaptorFcIfEventStatsLossOfSyncCountDelta                    Counter64,
    cucsAdaptorFcIfEventStatsLossOfSyncCountDeltaAvg                 Unsigned64,
    cucsAdaptorFcIfEventStatsLossOfSyncCountDeltaMax                 Unsigned64,
    cucsAdaptorFcIfEventStatsLossOfSyncCountDeltaMin                 Unsigned64,
    cucsAdaptorFcIfEventStatsNOSCount                                Unsigned64,
    cucsAdaptorFcIfEventStatsNOSCountDelta                           Counter64,
    cucsAdaptorFcIfEventStatsNOSCountDeltaAvg                        Unsigned64,
    cucsAdaptorFcIfEventStatsNOSCountDeltaMax                        Unsigned64,
    cucsAdaptorFcIfEventStatsNOSCountDeltaMin                        Unsigned64,
    cucsAdaptorFcIfEventStatsSecondsSinceLastReset                   Unsigned64,
    cucsAdaptorFcIfEventStatsSecondsSinceLastResetDelta              Counter64,
    cucsAdaptorFcIfEventStatsSecondsSinceLastResetDeltaAvg           Unsigned64,
    cucsAdaptorFcIfEventStatsSecondsSinceLastResetDeltaMax           Unsigned64,
    cucsAdaptorFcIfEventStatsSecondsSinceLastResetDeltaMin           Unsigned64,
    cucsAdaptorFcIfEventStatsSeqProtocolErrCount                     Unsigned64,
    cucsAdaptorFcIfEventStatsSeqProtocolErrCountDelta                Counter64,
    cucsAdaptorFcIfEventStatsSeqProtocolErrCountDeltaAvg             Unsigned64,
    cucsAdaptorFcIfEventStatsSeqProtocolErrCountDeltaMax             Unsigned64,
    cucsAdaptorFcIfEventStatsSeqProtocolErrCountDeltaMin             Unsigned64,
    cucsAdaptorFcIfEventStatsSuspect                                 TruthValue,
    cucsAdaptorFcIfEventStatsThresholded                             CucsAdaptorFcIfEventStatsThresholded,
    cucsAdaptorFcIfEventStatsTimeCollected                           DateAndTime,
    cucsAdaptorFcIfEventStatsUpdate                                  Gauge32
}

cucsAdaptorFcIfEventStatsInstanceId OBJECT-TYPE
    SYNTAX       CucsManagedObjectId
    MAX-ACCESS   not-accessible
    STATUS       current
    DESCRIPTION
        "Instance identifier of the managed object."
    ::= { cucsAdaptorFcIfEventStatsEntry 1 }

cucsAdaptorFcIfEventStatsDn OBJECT-TYPE
    SYNTAX       CucsManagedObjectDn
    MAX-ACCESS   read-only
    STATUS       current
    DESCRIPTION
        "Cisco UCS adaptor:FcIfEventStats:dn managed object property"
    ::= { cucsAdaptorFcIfEventStatsEntry 2 }

cucsAdaptorFcIfEventStatsRn OBJECT-TYPE
    SYNTAX       SnmpAdminString
    MAX-ACCESS   read-only
    STATUS       current
    DESCRIPTION
        "Cisco UCS adaptor:FcIfEventStats:rn managed object property"
    ::= { cucsAdaptorFcIfEventStatsEntry 3 }

cucsAdaptorFcIfEventStatsIntervals OBJECT-TYPE
    SYNTAX       Gauge32
    MAX-ACCESS   read-only
    STATUS       current
    DESCRIPTION
        "Cisco UCS adaptor:FcIfEventStats:intervals managed
        object property"
    ::= { cucsAdaptorFcIfEventStatsEntry 4 }

cucsAdaptorFcIfEventStatsInvalidCRCCount OBJECT-TYPE
    SYNTAX       Unsigned64
    MAX-ACCESS   read-only
    STATUS       current
    DESCRIPTION
        "Cisco UCS adaptor:FcIfEventStats:invalidCRCCount
        managed object property"
    ::= { cucsAdaptorFcIfEventStatsEntry 5 }

cucsAdaptorFcIfEventStatsInvalidCRCCountDelta OBJECT-TYPE
    SYNTAX       Counter64
    MAX-ACCESS   read-only
    STATUS       current
    DESCRIPTION
        "Cisco UCS adaptor:FcIfEventStats:invalidCRCCountDelta
        managed object property"
    ::= { cucsAdaptorFcIfEventStatsEntry 6 }

cucsAdaptorFcIfEventStatsInvalidCRCCountDeltaAvg OBJECT-TYPE
    SYNTAX       Unsigned64
    MAX-ACCESS   read-only
    STATUS       current
    DESCRIPTION
        "Cisco UCS adaptor:FcIfEventStats:invalidCRCCountDeltaAvg
        managed object property"
    ::= { cucsAdaptorFcIfEventStatsEntry 7 }

cucsAdaptorFcIfEventStatsInvalidCRCCountDeltaMax OBJECT-TYPE
    SYNTAX       Unsigned64
    MAX-ACCESS   read-only
    STATUS       current
    DESCRIPTION
        "Cisco UCS adaptor:FcIfEventStats:invalidCRCCountDeltaMax
        managed object property"
    ::= { cucsAdaptorFcIfEventStatsEntry 8 }

cucsAdaptorFcIfEventStatsInvalidCRCCountDeltaMin OBJECT-TYPE
    SYNTAX       Unsigned64
    MAX-ACCESS   read-only
    STATUS       current
    DESCRIPTION
        "Cisco UCS adaptor:FcIfEventStats:invalidCRCCountDeltaMin
        managed object property"
    ::= { cucsAdaptorFcIfEventStatsEntry 9 }

cucsAdaptorFcIfEventStatsLinkFailureCount OBJECT-TYPE
    SYNTAX       Unsigned64
    MAX-ACCESS   read-only
    STATUS       current
    DESCRIPTION
        "Cisco UCS adaptor:FcIfEventStats:linkFailureCount
        managed object property"
    ::= { cucsAdaptorFcIfEventStatsEntry 10 }

cucsAdaptorFcIfEventStatsLinkFailureCountDelta OBJECT-TYPE
    SYNTAX       Counter64
    MAX-ACCESS   read-only
    STATUS       current
    DESCRIPTION
        "Cisco UCS adaptor:FcIfEventStats:linkFailureCountDelta
        managed object property"
    ::= { cucsAdaptorFcIfEventStatsEntry 11 }

cucsAdaptorFcIfEventStatsLinkFailureCountDeltaAvg OBJECT-TYPE
    SYNTAX       Unsigned64
    MAX-ACCESS   read-only
    STATUS       current
    DESCRIPTION
        "Cisco UCS adaptor:FcIfEventStats:linkFailureCountDeltaAvg
        managed object property"
    ::= { cucsAdaptorFcIfEventStatsEntry 12 }

cucsAdaptorFcIfEventStatsLinkFailureCountDeltaMax OBJECT-TYPE
    SYNTAX       Unsigned64
    MAX-ACCESS   read-only
    STATUS       current
    DESCRIPTION
        "Cisco UCS adaptor:FcIfEventStats:linkFailureCountDeltaMax
        managed object property"
    ::= { cucsAdaptorFcIfEventStatsEntry 13 }

cucsAdaptorFcIfEventStatsLinkFailureCountDeltaMin OBJECT-TYPE
    SYNTAX       Unsigned64
    MAX-ACCESS   read-only
    STATUS       current
    DESCRIPTION
        "Cisco UCS adaptor:FcIfEventStats:linkFailureCountDeltaMin
        managed object property"
    ::= { cucsAdaptorFcIfEventStatsEntry 14 }

cucsAdaptorFcIfEventStatsLipCount OBJECT-TYPE
    SYNTAX       Unsigned64
    MAX-ACCESS   read-only
    STATUS       current
    DESCRIPTION
        "Cisco UCS adaptor:FcIfEventStats:lipCount managed
        object property"
    ::= { cucsAdaptorFcIfEventStatsEntry 15 }

cucsAdaptorFcIfEventStatsLipCountDelta OBJECT-TYPE
    SYNTAX       Counter64
    MAX-ACCESS   read-only
    STATUS       current
    DESCRIPTION
        "Cisco UCS adaptor:FcIfEventStats:lipCountDelta
        managed object property"
    ::= { cucsAdaptorFcIfEventStatsEntry 16 }

cucsAdaptorFcIfEventStatsLipCountDeltaAvg OBJECT-TYPE
    SYNTAX       Unsigned64
    MAX-ACCESS   read-only
    STATUS       current
    DESCRIPTION
        "Cisco UCS adaptor:FcIfEventStats:lipCountDeltaAvg
        managed object property"
    ::= { cucsAdaptorFcIfEventStatsEntry 17 }

cucsAdaptorFcIfEventStatsLipCountDeltaMax OBJECT-TYPE
    SYNTAX       Unsigned64
    MAX-ACCESS   read-only
    STATUS       current
    DESCRIPTION
        "Cisco UCS adaptor:FcIfEventStats:lipCountDeltaMax
        managed object property"
    ::= { cucsAdaptorFcIfEventStatsEntry 18 }

cucsAdaptorFcIfEventStatsLipCountDeltaMin OBJECT-TYPE
    SYNTAX       Unsigned64
    MAX-ACCESS   read-only
    STATUS       current
    DESCRIPTION
        "Cisco UCS adaptor:FcIfEventStats:lipCountDeltaMin
        managed object property"
    ::= { cucsAdaptorFcIfEventStatsEntry 19 }

cucsAdaptorFcIfEventStatsLossOfSignalCount OBJECT-TYPE
    SYNTAX       Unsigned64
    MAX-ACCESS   read-only
    STATUS       current
    DESCRIPTION
        "Cisco UCS adaptor:FcIfEventStats:lossOfSignalCount
        managed object property"
    ::= { cucsAdaptorFcIfEventStatsEntry 20 }

cucsAdaptorFcIfEventStatsLossOfSignalCountDelta OBJECT-TYPE
    SYNTAX       Counter64
    MAX-ACCESS   read-only
    STATUS       current
    DESCRIPTION
        "Cisco UCS adaptor:FcIfEventStats:lossOfSignalCountDelta
        managed object property"
    ::= { cucsAdaptorFcIfEventStatsEntry 21 }

cucsAdaptorFcIfEventStatsLossOfSignalCountDeltaAvg OBJECT-TYPE
    SYNTAX       Unsigned64
    MAX-ACCESS   read-only
    STATUS       current
    DESCRIPTION
        "Cisco UCS adaptor:FcIfEventStats:lossOfSignalCountDeltaAvg
        managed object property"
    ::= { cucsAdaptorFcIfEventStatsEntry 22 }

cucsAdaptorFcIfEventStatsLossOfSignalCountDeltaMax OBJECT-TYPE
    SYNTAX       Unsigned64
    MAX-ACCESS   read-only
    STATUS       current
    DESCRIPTION
        "Cisco UCS adaptor:FcIfEventStats:lossOfSignalCountDeltaMax
        managed object property"
    ::= { cucsAdaptorFcIfEventStatsEntry 23 }

cucsAdaptorFcIfEventStatsLossOfSignalCountDeltaMin OBJECT-TYPE
    SYNTAX       Unsigned64
    MAX-ACCESS   read-only
    STATUS       current
    DESCRIPTION
        "Cisco UCS adaptor:FcIfEventStats:lossOfSignalCountDeltaMin
        managed object property"
    ::= { cucsAdaptorFcIfEventStatsEntry 24 }

cucsAdaptorFcIfEventStatsLossOfSyncCount OBJECT-TYPE
    SYNTAX       Unsigned64
    MAX-ACCESS   read-only
    STATUS       current
    DESCRIPTION
        "Cisco UCS adaptor:FcIfEventStats:lossOfSyncCount
        managed object property"
    ::= { cucsAdaptorFcIfEventStatsEntry 25 }

cucsAdaptorFcIfEventStatsLossOfSyncCountDelta OBJECT-TYPE
    SYNTAX       Counter64
    MAX-ACCESS   read-only
    STATUS       current
    DESCRIPTION
        "Cisco UCS adaptor:FcIfEventStats:lossOfSyncCountDelta
        managed object property"
    ::= { cucsAdaptorFcIfEventStatsEntry 26 }

cucsAdaptorFcIfEventStatsLossOfSyncCountDeltaAvg OBJECT-TYPE
    SYNTAX       Unsigned64
    MAX-ACCESS   read-only
    STATUS       current
    DESCRIPTION
        "Cisco UCS adaptor:FcIfEventStats:lossOfSyncCountDeltaAvg
        managed object property"
    ::= { cucsAdaptorFcIfEventStatsEntry 27 }

cucsAdaptorFcIfEventStatsLossOfSyncCountDeltaMax OBJECT-TYPE
    SYNTAX       Unsigned64
    MAX-ACCESS   read-only
    STATUS       current
    DESCRIPTION
        "Cisco UCS adaptor:FcIfEventStats:lossOfSyncCountDeltaMax
        managed object property"
    ::= { cucsAdaptorFcIfEventStatsEntry 28 }

cucsAdaptorFcIfEventStatsLossOfSyncCountDeltaMin OBJECT-TYPE
    SYNTAX       Unsigned64
    MAX-ACCESS   read-only
    STATUS       current
    DESCRIPTION
        "Cisco UCS adaptor:FcIfEventStats:lossOfSyncCountDeltaMin
        managed object property"
    ::= { cucsAdaptorFcIfEventStatsEntry 29 }

cucsAdaptorFcIfEventStatsNOSCount OBJECT-TYPE
    SYNTAX       Unsigned64
    MAX-ACCESS   read-only
    STATUS       current
    DESCRIPTION
        "Cisco UCS adaptor:FcIfEventStats:nOSCount managed
        object property"
    ::= { cucsAdaptorFcIfEventStatsEntry 30 }

cucsAdaptorFcIfEventStatsNOSCountDelta OBJECT-TYPE
    SYNTAX       Counter64
    MAX-ACCESS   read-only
    STATUS       current
    DESCRIPTION
        "Cisco UCS adaptor:FcIfEventStats:nOSCountDelta
        managed object property"
    ::= { cucsAdaptorFcIfEventStatsEntry 31 }

cucsAdaptorFcIfEventStatsNOSCountDeltaAvg OBJECT-TYPE
    SYNTAX       Unsigned64
    MAX-ACCESS   read-only
    STATUS       current
    DESCRIPTION
        "Cisco UCS adaptor:FcIfEventStats:nOSCountDeltaAvg
        managed object property"
    ::= { cucsAdaptorFcIfEventStatsEntry 32 }

cucsAdaptorFcIfEventStatsNOSCountDeltaMax OBJECT-TYPE
    SYNTAX       Unsigned64
    MAX-ACCESS   read-only
    STATUS       current
    DESCRIPTION
        "Cisco UCS adaptor:FcIfEventStats:nOSCountDeltaMax
        managed object property"
    ::= { cucsAdaptorFcIfEventStatsEntry 33 }

cucsAdaptorFcIfEventStatsNOSCountDeltaMin OBJECT-TYPE
    SYNTAX       Unsigned64
    MAX-ACCESS   read-only
    STATUS       current
    DESCRIPTION
        "Cisco UCS adaptor:FcIfEventStats:nOSCountDeltaMin
        managed object property"
    ::= { cucsAdaptorFcIfEventStatsEntry 34 }

cucsAdaptorFcIfEventStatsSecondsSinceLastReset OBJECT-TYPE
    SYNTAX       Unsigned64
    MAX-ACCESS   read-only
    STATUS       current
    DESCRIPTION
        "Cisco UCS adaptor:FcIfEventStats:secondsSinceLastReset
        managed object property"
    ::= { cucsAdaptorFcIfEventStatsEntry 35 }

cucsAdaptorFcIfEventStatsSecondsSinceLastResetDelta OBJECT-TYPE
    SYNTAX       Counter64
    MAX-ACCESS   read-only
    STATUS       current
    DESCRIPTION
        "Cisco UCS adaptor:FcIfEventStats:secondsSinceLastResetDelta
        managed object property"
    ::= { cucsAdaptorFcIfEventStatsEntry 36 }

cucsAdaptorFcIfEventStatsSecondsSinceLastResetDeltaAvg OBJECT-TYPE
    SYNTAX       Unsigned64
    MAX-ACCESS   read-only
    STATUS       current
    DESCRIPTION
        "Cisco UCS adaptor:FcIfEventStats:secondsSinceLastResetDeltaAvg
        managed object property"
    ::= { cucsAdaptorFcIfEventStatsEntry 37 }

cucsAdaptorFcIfEventStatsSecondsSinceLastResetDeltaMax OBJECT-TYPE
    SYNTAX       Unsigned64
    MAX-ACCESS   read-only
    STATUS       current
    DESCRIPTION
        "Cisco UCS adaptor:FcIfEventStats:secondsSinceLastResetDeltaMax
        managed object property"
    ::= { cucsAdaptorFcIfEventStatsEntry 38 }

cucsAdaptorFcIfEventStatsSecondsSinceLastResetDeltaMin OBJECT-TYPE
    SYNTAX       Unsigned64
    MAX-ACCESS   read-only
    STATUS       current
    DESCRIPTION
        "Cisco UCS adaptor:FcIfEventStats:secondsSinceLastResetDeltaMin
        managed object property"
    ::= { cucsAdaptorFcIfEventStatsEntry 39 }

cucsAdaptorFcIfEventStatsSeqProtocolErrCount OBJECT-TYPE
    SYNTAX       Unsigned64
    MAX-ACCESS   read-only
    STATUS       current
    DESCRIPTION
        "Cisco UCS adaptor:FcIfEventStats:seqProtocolErrCount
        managed object property"
    ::= { cucsAdaptorFcIfEventStatsEntry 40 }

cucsAdaptorFcIfEventStatsSeqProtocolErrCountDelta OBJECT-TYPE
    SYNTAX       Counter64
    MAX-ACCESS   read-only
    STATUS       current
    DESCRIPTION
        "Cisco UCS adaptor:FcIfEventStats:seqProtocolErrCountDelta
        managed object property"
    ::= { cucsAdaptorFcIfEventStatsEntry 41 }

cucsAdaptorFcIfEventStatsSeqProtocolErrCountDeltaAvg OBJECT-TYPE
    SYNTAX       Unsigned64
    MAX-ACCESS   read-only
    STATUS       current
    DESCRIPTION
        "Cisco UCS adaptor:FcIfEventStats:seqProtocolErrCountDeltaAvg
        managed object property"
    ::= { cucsAdaptorFcIfEventStatsEntry 42 }

cucsAdaptorFcIfEventStatsSeqProtocolErrCountDeltaMax OBJECT-TYPE
    SYNTAX       Unsigned64
    MAX-ACCESS   read-only
    STATUS       current
    DESCRIPTION
        "Cisco UCS adaptor:FcIfEventStats:seqProtocolErrCountDeltaMax
        managed object property"
    ::= { cucsAdaptorFcIfEventStatsEntry 43 }

cucsAdaptorFcIfEventStatsSeqProtocolErrCountDeltaMin OBJECT-TYPE
    SYNTAX       Unsigned64
    MAX-ACCESS   read-only
    STATUS       current
    DESCRIPTION
        "Cisco UCS adaptor:FcIfEventStats:seqProtocolErrCountDeltaMin
        managed object property"
    ::= { cucsAdaptorFcIfEventStatsEntry 44 }

cucsAdaptorFcIfEventStatsSuspect OBJECT-TYPE
    SYNTAX       TruthValue
    MAX-ACCESS   read-only
    STATUS       current
    DESCRIPTION
        "Cisco UCS adaptor:FcIfEventStats:suspect managed object property"
    ::= { cucsAdaptorFcIfEventStatsEntry 45 }

cucsAdaptorFcIfEventStatsThresholded OBJECT-TYPE
    SYNTAX       CucsAdaptorFcIfEventStatsThresholded
    MAX-ACCESS   read-only
    STATUS       current
    DESCRIPTION
        "Cisco UCS adaptor:FcIfEventStats:thresholded managed
        object property"
    ::= { cucsAdaptorFcIfEventStatsEntry 46 }

cucsAdaptorFcIfEventStatsTimeCollected OBJECT-TYPE
    SYNTAX       DateAndTime
    MAX-ACCESS   read-only
    STATUS       current
    DESCRIPTION
        "Cisco UCS adaptor:FcIfEventStats:timeCollected
        managed object property"
    ::= { cucsAdaptorFcIfEventStatsEntry 47 }

cucsAdaptorFcIfEventStatsUpdate OBJECT-TYPE
    SYNTAX       Gauge32
    MAX-ACCESS   read-only
    STATUS       current
    DESCRIPTION
        "Cisco UCS adaptor:FcIfEventStats:update managed object property"
    ::= { cucsAdaptorFcIfEventStatsEntry 48 }

cucsAdaptorFcIfEventStatsHistTable OBJECT-TYPE
    SYNTAX           SEQUENCE OF CucsAdaptorFcIfEventStatsHistEntry
    MAX-ACCESS       not-accessible
    STATUS           current
    DESCRIPTION
        "Cisco UCS adaptor:FcIfEventStatsHist managed object table"
    ::= { cucsAdaptorObjects 29 }

cucsAdaptorFcIfEventStatsHistEntry OBJECT-TYPE
    SYNTAX           CucsAdaptorFcIfEventStatsHistEntry
    MAX-ACCESS       not-accessible
    STATUS           current
    DESCRIPTION
        "Entry for the cucsAdaptorFcIfEventStatsHistTable table."
    INDEX { cucsAdaptorFcIfEventStatsHistInstanceId }
    ::= { cucsAdaptorFcIfEventStatsHistTable 1 }

CucsAdaptorFcIfEventStatsHistEntry ::= SEQUENCE {
    cucsAdaptorFcIfEventStatsHistInstanceId                          CucsManagedObjectId,
    cucsAdaptorFcIfEventStatsHistDn                                  CucsManagedObjectDn,
    cucsAdaptorFcIfEventStatsHistRn                                  SnmpAdminString,
    cucsAdaptorFcIfEventStatsHistId                                  Unsigned64,
    cucsAdaptorFcIfEventStatsHistInvalidCRCCount                     Unsigned64,
    cucsAdaptorFcIfEventStatsHistInvalidCRCCountDelta                Unsigned64,
    cucsAdaptorFcIfEventStatsHistInvalidCRCCountDeltaAvg             Unsigned64,
    cucsAdaptorFcIfEventStatsHistInvalidCRCCountDeltaMax             Unsigned64,
    cucsAdaptorFcIfEventStatsHistInvalidCRCCountDeltaMin             Unsigned64,
    cucsAdaptorFcIfEventStatsHistLinkFailureCount                    Unsigned64,
    cucsAdaptorFcIfEventStatsHistLinkFailureCountDelta               Unsigned64,
    cucsAdaptorFcIfEventStatsHistLinkFailureCountDeltaAvg            Unsigned64,
    cucsAdaptorFcIfEventStatsHistLinkFailureCountDeltaMax            Unsigned64,
    cucsAdaptorFcIfEventStatsHistLinkFailureCountDeltaMin            Unsigned64,
    cucsAdaptorFcIfEventStatsHistLipCount                            Unsigned64,
    cucsAdaptorFcIfEventStatsHistLipCountDelta                       Unsigned64,
    cucsAdaptorFcIfEventStatsHistLipCountDeltaAvg                    Unsigned64,
    cucsAdaptorFcIfEventStatsHistLipCountDeltaMax                    Unsigned64,
    cucsAdaptorFcIfEventStatsHistLipCountDeltaMin                    Unsigned64,
    cucsAdaptorFcIfEventStatsHistLossOfSignalCount                   Unsigned64,
    cucsAdaptorFcIfEventStatsHistLossOfSignalCountDelta              Unsigned64,
    cucsAdaptorFcIfEventStatsHistLossOfSignalCountDeltaAvg           Unsigned64,
    cucsAdaptorFcIfEventStatsHistLossOfSignalCountDeltaMax           Unsigned64,
    cucsAdaptorFcIfEventStatsHistLossOfSignalCountDeltaMin           Unsigned64,
    cucsAdaptorFcIfEventStatsHistLossOfSyncCount                     Unsigned64,
    cucsAdaptorFcIfEventStatsHistLossOfSyncCountDelta                Unsigned64,
    cucsAdaptorFcIfEventStatsHistLossOfSyncCountDeltaAvg             Unsigned64,
    cucsAdaptorFcIfEventStatsHistLossOfSyncCountDeltaMax             Unsigned64,
    cucsAdaptorFcIfEventStatsHistLossOfSyncCountDeltaMin             Unsigned64,
    cucsAdaptorFcIfEventStatsHistMostRecent                          TruthValue,
    cucsAdaptorFcIfEventStatsHistNOSCount                            Unsigned64,
    cucsAdaptorFcIfEventStatsHistNOSCountDelta                       Unsigned64,
    cucsAdaptorFcIfEventStatsHistNOSCountDeltaAvg                    Unsigned64,
    cucsAdaptorFcIfEventStatsHistNOSCountDeltaMax                    Unsigned64,
    cucsAdaptorFcIfEventStatsHistNOSCountDeltaMin                    Unsigned64,
    cucsAdaptorFcIfEventStatsHistSecondsSinceLastReset               Unsigned64,
    cucsAdaptorFcIfEventStatsHistSecondsSinceLastResetDelta          Unsigned64,
    cucsAdaptorFcIfEventStatsHistSecondsSinceLastResetDeltaAvg       Unsigned64,
    cucsAdaptorFcIfEventStatsHistSecondsSinceLastResetDeltaMax       Unsigned64,
    cucsAdaptorFcIfEventStatsHistSecondsSinceLastResetDeltaMin       Unsigned64,
    cucsAdaptorFcIfEventStatsHistSeqProtocolErrCount                 Unsigned64,
    cucsAdaptorFcIfEventStatsHistSeqProtocolErrCountDelta            Unsigned64,
    cucsAdaptorFcIfEventStatsHistSeqProtocolErrCountDeltaAvg         Unsigned64,
    cucsAdaptorFcIfEventStatsHistSeqProtocolErrCountDeltaMax         Unsigned64,
    cucsAdaptorFcIfEventStatsHistSeqProtocolErrCountDeltaMin         Unsigned64,
    cucsAdaptorFcIfEventStatsHistSuspect                             TruthValue,
    cucsAdaptorFcIfEventStatsHistThresholded                         CucsAdaptorFcIfEventStatsHistThresholded,
    cucsAdaptorFcIfEventStatsHistTimeCollected                       DateAndTime
}

cucsAdaptorFcIfEventStatsHistInstanceId OBJECT-TYPE
    SYNTAX       CucsManagedObjectId
    MAX-ACCESS   not-accessible
    STATUS       current
    DESCRIPTION
        "Instance identifier of the managed object."
    ::= { cucsAdaptorFcIfEventStatsHistEntry 1 }

cucsAdaptorFcIfEventStatsHistDn OBJECT-TYPE
    SYNTAX       CucsManagedObjectDn
    MAX-ACCESS   read-only
    STATUS       current
    DESCRIPTION
        "Cisco UCS adaptor:FcIfEventStatsHist:dn managed object property"
    ::= { cucsAdaptorFcIfEventStatsHistEntry 2 }

cucsAdaptorFcIfEventStatsHistRn OBJECT-TYPE
    SYNTAX       SnmpAdminString
    MAX-ACCESS   read-only
    STATUS       current
    DESCRIPTION
        "Cisco UCS adaptor:FcIfEventStatsHist:rn managed object property"
    ::= { cucsAdaptorFcIfEventStatsHistEntry 3 }

cucsAdaptorFcIfEventStatsHistId OBJECT-TYPE
    SYNTAX       Unsigned64
    MAX-ACCESS   read-only
    STATUS       current
    DESCRIPTION
        "Cisco UCS adaptor:FcIfEventStatsHist:id managed object property"
    ::= { cucsAdaptorFcIfEventStatsHistEntry 4 }

cucsAdaptorFcIfEventStatsHistInvalidCRCCount OBJECT-TYPE
    SYNTAX       Unsigned64
    MAX-ACCESS   read-only
    STATUS       current
    DESCRIPTION
        "Cisco UCS adaptor:FcIfEventStatsHist:invalidCRCCount
        managed object property"
    ::= { cucsAdaptorFcIfEventStatsHistEntry 5 }

cucsAdaptorFcIfEventStatsHistInvalidCRCCountDelta OBJECT-TYPE
    SYNTAX       Unsigned64
    MAX-ACCESS   read-only
    STATUS       current
    DESCRIPTION
        "Cisco UCS adaptor:FcIfEventStatsHist:invalidCRCCountDelta
        managed object property"
    ::= { cucsAdaptorFcIfEventStatsHistEntry 6 }

cucsAdaptorFcIfEventStatsHistInvalidCRCCountDeltaAvg OBJECT-TYPE
    SYNTAX       Unsigned64
    MAX-ACCESS   read-only
    STATUS       current
    DESCRIPTION
        "Cisco UCS adaptor:FcIfEventStatsHist:invalidCRCCountDeltaAvg
        managed object property"
    ::= { cucsAdaptorFcIfEventStatsHistEntry 7 }

cucsAdaptorFcIfEventStatsHistInvalidCRCCountDeltaMax OBJECT-TYPE
    SYNTAX       Unsigned64
    MAX-ACCESS   read-only
    STATUS       current
    DESCRIPTION
        "Cisco UCS adaptor:FcIfEventStatsHist:invalidCRCCountDeltaMax
        managed object property"
    ::= { cucsAdaptorFcIfEventStatsHistEntry 8 }

cucsAdaptorFcIfEventStatsHistInvalidCRCCountDeltaMin OBJECT-TYPE
    SYNTAX       Unsigned64
    MAX-ACCESS   read-only
    STATUS       current
    DESCRIPTION
        "Cisco UCS adaptor:FcIfEventStatsHist:invalidCRCCountDeltaMin
        managed object property"
    ::= { cucsAdaptorFcIfEventStatsHistEntry 9 }

cucsAdaptorFcIfEventStatsHistLinkFailureCount OBJECT-TYPE
    SYNTAX       Unsigned64
    MAX-ACCESS   read-only
    STATUS       current
    DESCRIPTION
        "Cisco UCS adaptor:FcIfEventStatsHist:linkFailureCount
        managed object property"
    ::= { cucsAdaptorFcIfEventStatsHistEntry 10 }

cucsAdaptorFcIfEventStatsHistLinkFailureCountDelta OBJECT-TYPE
    SYNTAX       Unsigned64
    MAX-ACCESS   read-only
    STATUS       current
    DESCRIPTION
        "Cisco UCS adaptor:FcIfEventStatsHist:linkFailureCountDelta
        managed object property"
    ::= { cucsAdaptorFcIfEventStatsHistEntry 11 }

cucsAdaptorFcIfEventStatsHistLinkFailureCountDeltaAvg OBJECT-TYPE
    SYNTAX       Unsigned64
    MAX-ACCESS   read-only
    STATUS       current
    DESCRIPTION
        "Cisco UCS adaptor:FcIfEventStatsHist:linkFailureCountDeltaAvg
        managed object property"
    ::= { cucsAdaptorFcIfEventStatsHistEntry 12 }

cucsAdaptorFcIfEventStatsHistLinkFailureCountDeltaMax OBJECT-TYPE
    SYNTAX       Unsigned64
    MAX-ACCESS   read-only
    STATUS       current
    DESCRIPTION
        "Cisco UCS adaptor:FcIfEventStatsHist:linkFailureCountDeltaMax
        managed object property"
    ::= { cucsAdaptorFcIfEventStatsHistEntry 13 }

cucsAdaptorFcIfEventStatsHistLinkFailureCountDeltaMin OBJECT-TYPE
    SYNTAX       Unsigned64
    MAX-ACCESS   read-only
    STATUS       current
    DESCRIPTION
        "Cisco UCS adaptor:FcIfEventStatsHist:linkFailureCountDeltaMin
        managed object property"
    ::= { cucsAdaptorFcIfEventStatsHistEntry 14 }

cucsAdaptorFcIfEventStatsHistLipCount OBJECT-TYPE
    SYNTAX       Unsigned64
    MAX-ACCESS   read-only
    STATUS       current
    DESCRIPTION
        "Cisco UCS adaptor:FcIfEventStatsHist:lipCount
        managed object property"
    ::= { cucsAdaptorFcIfEventStatsHistEntry 15 }

cucsAdaptorFcIfEventStatsHistLipCountDelta OBJECT-TYPE
    SYNTAX       Unsigned64
    MAX-ACCESS   read-only
    STATUS       current
    DESCRIPTION
        "Cisco UCS adaptor:FcIfEventStatsHist:lipCountDelta
        managed object property"
    ::= { cucsAdaptorFcIfEventStatsHistEntry 16 }

cucsAdaptorFcIfEventStatsHistLipCountDeltaAvg OBJECT-TYPE
    SYNTAX       Unsigned64
    MAX-ACCESS   read-only
    STATUS       current
    DESCRIPTION
        "Cisco UCS adaptor:FcIfEventStatsHist:lipCountDeltaAvg
        managed object property"
    ::= { cucsAdaptorFcIfEventStatsHistEntry 17 }

cucsAdaptorFcIfEventStatsHistLipCountDeltaMax OBJECT-TYPE
    SYNTAX       Unsigned64
    MAX-ACCESS   read-only
    STATUS       current
    DESCRIPTION
        "Cisco UCS adaptor:FcIfEventStatsHist:lipCountDeltaMax
        managed object property"
    ::= { cucsAdaptorFcIfEventStatsHistEntry 18 }

cucsAdaptorFcIfEventStatsHistLipCountDeltaMin OBJECT-TYPE
    SYNTAX       Unsigned64
    MAX-ACCESS   read-only
    STATUS       current
    DESCRIPTION
        "Cisco UCS adaptor:FcIfEventStatsHist:lipCountDeltaMin
        managed object property"
    ::= { cucsAdaptorFcIfEventStatsHistEntry 19 }

cucsAdaptorFcIfEventStatsHistLossOfSignalCount OBJECT-TYPE
    SYNTAX       Unsigned64
    MAX-ACCESS   read-only
    STATUS       current
    DESCRIPTION
        "Cisco UCS adaptor:FcIfEventStatsHist:lossOfSignalCount
        managed object property"
    ::= { cucsAdaptorFcIfEventStatsHistEntry 20 }

cucsAdaptorFcIfEventStatsHistLossOfSignalCountDelta OBJECT-TYPE
    SYNTAX       Unsigned64
    MAX-ACCESS   read-only
    STATUS       current
    DESCRIPTION
        "Cisco UCS adaptor:FcIfEventStatsHist:lossOfSignalCountDelta
        managed object property"
    ::= { cucsAdaptorFcIfEventStatsHistEntry 21 }

cucsAdaptorFcIfEventStatsHistLossOfSignalCountDeltaAvg OBJECT-TYPE
    SYNTAX       Unsigned64
    MAX-ACCESS   read-only
    STATUS       current
    DESCRIPTION
        "Cisco UCS adaptor:FcIfEventStatsHist:lossOfSignalCountDeltaAvg
        managed object property"
    ::= { cucsAdaptorFcIfEventStatsHistEntry 22 }

cucsAdaptorFcIfEventStatsHistLossOfSignalCountDeltaMax OBJECT-TYPE
    SYNTAX       Unsigned64
    MAX-ACCESS   read-only
    STATUS       current
    DESCRIPTION
        "Cisco UCS adaptor:FcIfEventStatsHist:lossOfSignalCountDeltaMax
        managed object property"
    ::= { cucsAdaptorFcIfEventStatsHistEntry 23 }

cucsAdaptorFcIfEventStatsHistLossOfSignalCountDeltaMin OBJECT-TYPE
    SYNTAX       Unsigned64
    MAX-ACCESS   read-only
    STATUS       current
    DESCRIPTION
        "Cisco UCS adaptor:FcIfEventStatsHist:lossOfSignalCountDeltaMin
        managed object property"
    ::= { cucsAdaptorFcIfEventStatsHistEntry 24 }

cucsAdaptorFcIfEventStatsHistLossOfSyncCount OBJECT-TYPE
    SYNTAX       Unsigned64
    MAX-ACCESS   read-only
    STATUS       current
    DESCRIPTION
        "Cisco UCS adaptor:FcIfEventStatsHist:lossOfSyncCount
        managed object property"
    ::= { cucsAdaptorFcIfEventStatsHistEntry 25 }

cucsAdaptorFcIfEventStatsHistLossOfSyncCountDelta OBJECT-TYPE
    SYNTAX       Unsigned64
    MAX-ACCESS   read-only
    STATUS       current
    DESCRIPTION
        "Cisco UCS adaptor:FcIfEventStatsHist:lossOfSyncCountDelta
        managed object property"
    ::= { cucsAdaptorFcIfEventStatsHistEntry 26 }

cucsAdaptorFcIfEventStatsHistLossOfSyncCountDeltaAvg OBJECT-TYPE
    SYNTAX       Unsigned64
    MAX-ACCESS   read-only
    STATUS       current
    DESCRIPTION
        "Cisco UCS adaptor:FcIfEventStatsHist:lossOfSyncCountDeltaAvg
        managed object property"
    ::= { cucsAdaptorFcIfEventStatsHistEntry 27 }

cucsAdaptorFcIfEventStatsHistLossOfSyncCountDeltaMax OBJECT-TYPE
    SYNTAX       Unsigned64
    MAX-ACCESS   read-only
    STATUS       current
    DESCRIPTION
        "Cisco UCS adaptor:FcIfEventStatsHist:lossOfSyncCountDeltaMax
        managed object property"
    ::= { cucsAdaptorFcIfEventStatsHistEntry 28 }

cucsAdaptorFcIfEventStatsHistLossOfSyncCountDeltaMin OBJECT-TYPE
    SYNTAX       Unsigned64
    MAX-ACCESS   read-only
    STATUS       current
    DESCRIPTION
        "Cisco UCS adaptor:FcIfEventStatsHist:lossOfSyncCountDeltaMin
        managed object property"
    ::= { cucsAdaptorFcIfEventStatsHistEntry 29 }

cucsAdaptorFcIfEventStatsHistMostRecent OBJECT-TYPE
    SYNTAX       TruthValue
    MAX-ACCESS   read-only
    STATUS       current
    DESCRIPTION
        "Cisco UCS adaptor:FcIfEventStatsHist:mostRecent
        managed object property"
    ::= { cucsAdaptorFcIfEventStatsHistEntry 30 }

cucsAdaptorFcIfEventStatsHistNOSCount OBJECT-TYPE
    SYNTAX       Unsigned64
    MAX-ACCESS   read-only
    STATUS       current
    DESCRIPTION
        "Cisco UCS adaptor:FcIfEventStatsHist:nOSCount
        managed object property"
    ::= { cucsAdaptorFcIfEventStatsHistEntry 31 }

cucsAdaptorFcIfEventStatsHistNOSCountDelta OBJECT-TYPE
    SYNTAX       Unsigned64
    MAX-ACCESS   read-only
    STATUS       current
    DESCRIPTION
        "Cisco UCS adaptor:FcIfEventStatsHist:nOSCountDelta
        managed object property"
    ::= { cucsAdaptorFcIfEventStatsHistEntry 32 }

cucsAdaptorFcIfEventStatsHistNOSCountDeltaAvg OBJECT-TYPE
    SYNTAX       Unsigned64
    MAX-ACCESS   read-only
    STATUS       current
    DESCRIPTION
        "Cisco UCS adaptor:FcIfEventStatsHist:nOSCountDeltaAvg
        managed object property"
    ::= { cucsAdaptorFcIfEventStatsHistEntry 33 }

cucsAdaptorFcIfEventStatsHistNOSCountDeltaMax OBJECT-TYPE
    SYNTAX       Unsigned64
    MAX-ACCESS   read-only
    STATUS       current
    DESCRIPTION
        "Cisco UCS adaptor:FcIfEventStatsHist:nOSCountDeltaMax
        managed object property"
    ::= { cucsAdaptorFcIfEventStatsHistEntry 34 }

cucsAdaptorFcIfEventStatsHistNOSCountDeltaMin OBJECT-TYPE
    SYNTAX       Unsigned64
    MAX-ACCESS   read-only
    STATUS       current
    DESCRIPTION
        "Cisco UCS adaptor:FcIfEventStatsHist:nOSCountDeltaMin
        managed object property"
    ::= { cucsAdaptorFcIfEventStatsHistEntry 35 }

cucsAdaptorFcIfEventStatsHistSecondsSinceLastReset OBJECT-TYPE
    SYNTAX       Unsigned64
    MAX-ACCESS   read-only
    STATUS       current
    DESCRIPTION
        "Cisco UCS adaptor:FcIfEventStatsHist:secondsSinceLastReset
        managed object property"
    ::= { cucsAdaptorFcIfEventStatsHistEntry 36 }

cucsAdaptorFcIfEventStatsHistSecondsSinceLastResetDelta OBJECT-TYPE
    SYNTAX       Unsigned64
    MAX-ACCESS   read-only
    STATUS       current
    DESCRIPTION
        "Cisco UCS adaptor:FcIfEventStatsHist:secondsSinceLastResetDelta
        managed object property"
    ::= { cucsAdaptorFcIfEventStatsHistEntry 37 }

cucsAdaptorFcIfEventStatsHistSecondsSinceLastResetDeltaAvg OBJECT-TYPE
    SYNTAX       Unsigned64
    MAX-ACCESS   read-only
    STATUS       current
    DESCRIPTION
        "Cisco UCS adaptor:FcIfEventStatsHist:secondsSinceLastResetDeltaAv
        g managed object property"
    ::= { cucsAdaptorFcIfEventStatsHistEntry 38 }

cucsAdaptorFcIfEventStatsHistSecondsSinceLastResetDeltaMax OBJECT-TYPE
    SYNTAX       Unsigned64
    MAX-ACCESS   read-only
    STATUS       current
    DESCRIPTION
        "Cisco UCS adaptor:FcIfEventStatsHist:secondsSinceLastResetDeltaMa
        x managed object property"
    ::= { cucsAdaptorFcIfEventStatsHistEntry 39 }

cucsAdaptorFcIfEventStatsHistSecondsSinceLastResetDeltaMin OBJECT-TYPE
    SYNTAX       Unsigned64
    MAX-ACCESS   read-only
    STATUS       current
    DESCRIPTION
        "Cisco UCS adaptor:FcIfEventStatsHist:secondsSinceLastResetDeltaMi
        n managed object property"
    ::= { cucsAdaptorFcIfEventStatsHistEntry 40 }

cucsAdaptorFcIfEventStatsHistSeqProtocolErrCount OBJECT-TYPE
    SYNTAX       Unsigned64
    MAX-ACCESS   read-only
    STATUS       current
    DESCRIPTION
        "Cisco UCS adaptor:FcIfEventStatsHist:seqProtocolErrCount
        managed object property"
    ::= { cucsAdaptorFcIfEventStatsHistEntry 41 }

cucsAdaptorFcIfEventStatsHistSeqProtocolErrCountDelta OBJECT-TYPE
    SYNTAX       Unsigned64
    MAX-ACCESS   read-only
    STATUS       current
    DESCRIPTION
        "Cisco UCS adaptor:FcIfEventStatsHist:seqProtocolErrCountDelta
        managed object property"
    ::= { cucsAdaptorFcIfEventStatsHistEntry 42 }

cucsAdaptorFcIfEventStatsHistSeqProtocolErrCountDeltaAvg OBJECT-TYPE
    SYNTAX       Unsigned64
    MAX-ACCESS   read-only
    STATUS       current
    DESCRIPTION
        "Cisco UCS adaptor:FcIfEventStatsHist:seqProtocolErrCountDeltaAvg
        managed object property"
    ::= { cucsAdaptorFcIfEventStatsHistEntry 43 }

cucsAdaptorFcIfEventStatsHistSeqProtocolErrCountDeltaMax OBJECT-TYPE
    SYNTAX       Unsigned64
    MAX-ACCESS   read-only
    STATUS       current
    DESCRIPTION
        "Cisco UCS adaptor:FcIfEventStatsHist:seqProtocolErrCountDeltaMax
        managed object property"
    ::= { cucsAdaptorFcIfEventStatsHistEntry 44 }

cucsAdaptorFcIfEventStatsHistSeqProtocolErrCountDeltaMin OBJECT-TYPE
    SYNTAX       Unsigned64
    MAX-ACCESS   read-only
    STATUS       current
    DESCRIPTION
        "Cisco UCS adaptor:FcIfEventStatsHist:seqProtocolErrCountDeltaMin
        managed object property"
    ::= { cucsAdaptorFcIfEventStatsHistEntry 45 }

cucsAdaptorFcIfEventStatsHistSuspect OBJECT-TYPE
    SYNTAX       TruthValue
    MAX-ACCESS   read-only
    STATUS       current
    DESCRIPTION
        "Cisco UCS adaptor:FcIfEventStatsHist:suspect managed
        object property"
    ::= { cucsAdaptorFcIfEventStatsHistEntry 46 }

cucsAdaptorFcIfEventStatsHistThresholded OBJECT-TYPE
    SYNTAX       CucsAdaptorFcIfEventStatsHistThresholded
    MAX-ACCESS   read-only
    STATUS       current
    DESCRIPTION
        "Cisco UCS adaptor:FcIfEventStatsHist:thresholded
        managed object property"
    ::= { cucsAdaptorFcIfEventStatsHistEntry 47 }

cucsAdaptorFcIfEventStatsHistTimeCollected OBJECT-TYPE
    SYNTAX       DateAndTime
    MAX-ACCESS   read-only
    STATUS       current
    DESCRIPTION
        "Cisco UCS adaptor:FcIfEventStatsHist:timeCollected
        managed object property"
    ::= { cucsAdaptorFcIfEventStatsHistEntry 48 }

cucsAdaptorFcIfFC4StatsTable OBJECT-TYPE
    SYNTAX           SEQUENCE OF CucsAdaptorFcIfFC4StatsEntry
    MAX-ACCESS       not-accessible
    STATUS           current
    DESCRIPTION
        "Cisco UCS adaptor:FcIfFC4Stats managed object table"
    ::= { cucsAdaptorObjects 30 }

cucsAdaptorFcIfFC4StatsEntry OBJECT-TYPE
    SYNTAX           CucsAdaptorFcIfFC4StatsEntry
    MAX-ACCESS       not-accessible
    STATUS           current
    DESCRIPTION
        "Entry for the cucsAdaptorFcIfFC4StatsTable table."
    INDEX { cucsAdaptorFcIfFC4StatsInstanceId }
    ::= { cucsAdaptorFcIfFC4StatsTable 1 }

CucsAdaptorFcIfFC4StatsEntry ::= SEQUENCE {
    cucsAdaptorFcIfFC4StatsInstanceId                                CucsManagedObjectId,
    cucsAdaptorFcIfFC4StatsDn                                        CucsManagedObjectDn,
    cucsAdaptorFcIfFC4StatsRn                                        SnmpAdminString,
    cucsAdaptorFcIfFC4StatsControlRequests                           Unsigned64,
    cucsAdaptorFcIfFC4StatsControlRequestsDelta                      Counter64,
    cucsAdaptorFcIfFC4StatsControlRequestsDeltaAvg                   Unsigned64,
    cucsAdaptorFcIfFC4StatsControlRequestsDeltaMax                   Unsigned64,
    cucsAdaptorFcIfFC4StatsControlRequestsDeltaMin                   Unsigned64,
    cucsAdaptorFcIfFC4StatsInputMegabytes                            Unsigned64,
    cucsAdaptorFcIfFC4StatsInputMegabytesDelta                       Counter64,
    cucsAdaptorFcIfFC4StatsInputMegabytesDeltaAvg                    Unsigned64,
    cucsAdaptorFcIfFC4StatsInputMegabytesDeltaMax                    Unsigned64,
    cucsAdaptorFcIfFC4StatsInputMegabytesDeltaMin                    Unsigned64,
    cucsAdaptorFcIfFC4StatsInputRequests                             Unsigned64,
    cucsAdaptorFcIfFC4StatsInputRequestsDelta                        Counter64,
    cucsAdaptorFcIfFC4StatsInputRequestsDeltaAvg                     Unsigned64,
    cucsAdaptorFcIfFC4StatsInputRequestsDeltaMax                     Unsigned64,
    cucsAdaptorFcIfFC4StatsInputRequestsDeltaMin                     Unsigned64,
    cucsAdaptorFcIfFC4StatsIntervals                                 Gauge32,
    cucsAdaptorFcIfFC4StatsOutputMegabytes                           Unsigned64,
    cucsAdaptorFcIfFC4StatsOutputMegabytesDelta                      Counter64,
    cucsAdaptorFcIfFC4StatsOutputMegabytesDeltaAvg                   Unsigned64,
    cucsAdaptorFcIfFC4StatsOutputMegabytesDeltaMax                   Unsigned64,
    cucsAdaptorFcIfFC4StatsOutputMegabytesDeltaMin                   Unsigned64,
    cucsAdaptorFcIfFC4StatsOutputRequests                            Unsigned64,
    cucsAdaptorFcIfFC4StatsOutputRequestsDelta                       Counter64,
    cucsAdaptorFcIfFC4StatsOutputRequestsDeltaAvg                    Unsigned64,
    cucsAdaptorFcIfFC4StatsOutputRequestsDeltaMax                    Unsigned64,
    cucsAdaptorFcIfFC4StatsOutputRequestsDeltaMin                    Unsigned64,
    cucsAdaptorFcIfFC4StatsSuspect                                   TruthValue,
    cucsAdaptorFcIfFC4StatsThresholded                               CucsAdaptorFcIfFC4StatsThresholded,
    cucsAdaptorFcIfFC4StatsTimeCollected                             DateAndTime,
    cucsAdaptorFcIfFC4StatsUpdate                                    Gauge32
}

cucsAdaptorFcIfFC4StatsInstanceId OBJECT-TYPE
    SYNTAX       CucsManagedObjectId
    MAX-ACCESS   not-accessible
    STATUS       current
    DESCRIPTION
        "Instance identifier of the managed object."
    ::= { cucsAdaptorFcIfFC4StatsEntry 1 }

cucsAdaptorFcIfFC4StatsDn OBJECT-TYPE
    SYNTAX       CucsManagedObjectDn
    MAX-ACCESS   read-only
    STATUS       current
    DESCRIPTION
        "Cisco UCS adaptor:FcIfFC4Stats:dn managed object property"
    ::= { cucsAdaptorFcIfFC4StatsEntry 2 }

cucsAdaptorFcIfFC4StatsRn OBJECT-TYPE
    SYNTAX       SnmpAdminString
    MAX-ACCESS   read-only
    STATUS       current
    DESCRIPTION
        "Cisco UCS adaptor:FcIfFC4Stats:rn managed object property"
    ::= { cucsAdaptorFcIfFC4StatsEntry 3 }

cucsAdaptorFcIfFC4StatsControlRequests OBJECT-TYPE
    SYNTAX       Unsigned64
    MAX-ACCESS   read-only
    STATUS       current
    DESCRIPTION
        "Cisco UCS adaptor:FcIfFC4Stats:controlRequests
        managed object property"
    ::= { cucsAdaptorFcIfFC4StatsEntry 4 }

cucsAdaptorFcIfFC4StatsControlRequestsDelta OBJECT-TYPE
    SYNTAX       Counter64
    MAX-ACCESS   read-only
    STATUS       current
    DESCRIPTION
        "Cisco UCS adaptor:FcIfFC4Stats:controlRequestsDelta
        managed object property"
    ::= { cucsAdaptorFcIfFC4StatsEntry 5 }

cucsAdaptorFcIfFC4StatsControlRequestsDeltaAvg OBJECT-TYPE
    SYNTAX       Unsigned64
    MAX-ACCESS   read-only
    STATUS       current
    DESCRIPTION
        "Cisco UCS adaptor:FcIfFC4Stats:controlRequestsDeltaAvg
        managed object property"
    ::= { cucsAdaptorFcIfFC4StatsEntry 6 }

cucsAdaptorFcIfFC4StatsControlRequestsDeltaMax OBJECT-TYPE
    SYNTAX       Unsigned64
    MAX-ACCESS   read-only
    STATUS       current
    DESCRIPTION
        "Cisco UCS adaptor:FcIfFC4Stats:controlRequestsDeltaMax
        managed object property"
    ::= { cucsAdaptorFcIfFC4StatsEntry 7 }

cucsAdaptorFcIfFC4StatsControlRequestsDeltaMin OBJECT-TYPE
    SYNTAX       Unsigned64
    MAX-ACCESS   read-only
    STATUS       current
    DESCRIPTION
        "Cisco UCS adaptor:FcIfFC4Stats:controlRequestsDeltaMin
        managed object property"
    ::= { cucsAdaptorFcIfFC4StatsEntry 8 }

cucsAdaptorFcIfFC4StatsInputMegabytes OBJECT-TYPE
    SYNTAX       Unsigned64
    MAX-ACCESS   read-only
    STATUS       current
    DESCRIPTION
        "Cisco UCS adaptor:FcIfFC4Stats:inputMegabytes
        managed object property"
    ::= { cucsAdaptorFcIfFC4StatsEntry 9 }

cucsAdaptorFcIfFC4StatsInputMegabytesDelta OBJECT-TYPE
    SYNTAX       Counter64
    MAX-ACCESS   read-only
    STATUS       current
    DESCRIPTION
        "Cisco UCS adaptor:FcIfFC4Stats:inputMegabytesDelta
        managed object property"
    ::= { cucsAdaptorFcIfFC4StatsEntry 10 }

cucsAdaptorFcIfFC4StatsInputMegabytesDeltaAvg OBJECT-TYPE
    SYNTAX       Unsigned64
    MAX-ACCESS   read-only
    STATUS       current
    DESCRIPTION
        "Cisco UCS adaptor:FcIfFC4Stats:inputMegabytesDeltaAvg
        managed object property"
    ::= { cucsAdaptorFcIfFC4StatsEntry 11 }

cucsAdaptorFcIfFC4StatsInputMegabytesDeltaMax OBJECT-TYPE
    SYNTAX       Unsigned64
    MAX-ACCESS   read-only
    STATUS       current
    DESCRIPTION
        "Cisco UCS adaptor:FcIfFC4Stats:inputMegabytesDeltaMax
        managed object property"
    ::= { cucsAdaptorFcIfFC4StatsEntry 12 }

cucsAdaptorFcIfFC4StatsInputMegabytesDeltaMin OBJECT-TYPE
    SYNTAX       Unsigned64
    MAX-ACCESS   read-only
    STATUS       current
    DESCRIPTION
        "Cisco UCS adaptor:FcIfFC4Stats:inputMegabytesDeltaMin
        managed object property"
    ::= { cucsAdaptorFcIfFC4StatsEntry 13 }

cucsAdaptorFcIfFC4StatsInputRequests OBJECT-TYPE
    SYNTAX       Unsigned64
    MAX-ACCESS   read-only
    STATUS       current
    DESCRIPTION
        "Cisco UCS adaptor:FcIfFC4Stats:inputRequests managed
        object property"
    ::= { cucsAdaptorFcIfFC4StatsEntry 14 }

cucsAdaptorFcIfFC4StatsInputRequestsDelta OBJECT-TYPE
    SYNTAX       Counter64
    MAX-ACCESS   read-only
    STATUS       current
    DESCRIPTION
        "Cisco UCS adaptor:FcIfFC4Stats:inputRequestsDelta
        managed object property"
    ::= { cucsAdaptorFcIfFC4StatsEntry 15 }

cucsAdaptorFcIfFC4StatsInputRequestsDeltaAvg OBJECT-TYPE
    SYNTAX       Unsigned64
    MAX-ACCESS   read-only
    STATUS       current
    DESCRIPTION
        "Cisco UCS adaptor:FcIfFC4Stats:inputRequestsDeltaAvg
        managed object property"
    ::= { cucsAdaptorFcIfFC4StatsEntry 16 }

cucsAdaptorFcIfFC4StatsInputRequestsDeltaMax OBJECT-TYPE
    SYNTAX       Unsigned64
    MAX-ACCESS   read-only
    STATUS       current
    DESCRIPTION
        "Cisco UCS adaptor:FcIfFC4Stats:inputRequestsDeltaMax
        managed object property"
    ::= { cucsAdaptorFcIfFC4StatsEntry 17 }

cucsAdaptorFcIfFC4StatsInputRequestsDeltaMin OBJECT-TYPE
    SYNTAX       Unsigned64
    MAX-ACCESS   read-only
    STATUS       current
    DESCRIPTION
        "Cisco UCS adaptor:FcIfFC4Stats:inputRequestsDeltaMin
        managed object property"
    ::= { cucsAdaptorFcIfFC4StatsEntry 18 }

cucsAdaptorFcIfFC4StatsIntervals OBJECT-TYPE
    SYNTAX       Gauge32
    MAX-ACCESS   read-only
    STATUS       current
    DESCRIPTION
        "Cisco UCS adaptor:FcIfFC4Stats:intervals managed object property"
    ::= { cucsAdaptorFcIfFC4StatsEntry 19 }

cucsAdaptorFcIfFC4StatsOutputMegabytes OBJECT-TYPE
    SYNTAX       Unsigned64
    MAX-ACCESS   read-only
    STATUS       current
    DESCRIPTION
        "Cisco UCS adaptor:FcIfFC4Stats:outputMegabytes
        managed object property"
    ::= { cucsAdaptorFcIfFC4StatsEntry 20 }

cucsAdaptorFcIfFC4StatsOutputMegabytesDelta OBJECT-TYPE
    SYNTAX       Counter64
    MAX-ACCESS   read-only
    STATUS       current
    DESCRIPTION
        "Cisco UCS adaptor:FcIfFC4Stats:outputMegabytesDelta
        managed object property"
    ::= { cucsAdaptorFcIfFC4StatsEntry 21 }

cucsAdaptorFcIfFC4StatsOutputMegabytesDeltaAvg OBJECT-TYPE
    SYNTAX       Unsigned64
    MAX-ACCESS   read-only
    STATUS       current
    DESCRIPTION
        "Cisco UCS adaptor:FcIfFC4Stats:outputMegabytesDeltaAvg
        managed object property"
    ::= { cucsAdaptorFcIfFC4StatsEntry 22 }

cucsAdaptorFcIfFC4StatsOutputMegabytesDeltaMax OBJECT-TYPE
    SYNTAX       Unsigned64
    MAX-ACCESS   read-only
    STATUS       current
    DESCRIPTION
        "Cisco UCS adaptor:FcIfFC4Stats:outputMegabytesDeltaMax
        managed object property"
    ::= { cucsAdaptorFcIfFC4StatsEntry 23 }

cucsAdaptorFcIfFC4StatsOutputMegabytesDeltaMin OBJECT-TYPE
    SYNTAX       Unsigned64
    MAX-ACCESS   read-only
    STATUS       current
    DESCRIPTION
        "Cisco UCS adaptor:FcIfFC4Stats:outputMegabytesDeltaMin
        managed object property"
    ::= { cucsAdaptorFcIfFC4StatsEntry 24 }

cucsAdaptorFcIfFC4StatsOutputRequests OBJECT-TYPE
    SYNTAX       Unsigned64
    MAX-ACCESS   read-only
    STATUS       current
    DESCRIPTION
        "Cisco UCS adaptor:FcIfFC4Stats:outputRequests
        managed object property"
    ::= { cucsAdaptorFcIfFC4StatsEntry 25 }

cucsAdaptorFcIfFC4StatsOutputRequestsDelta OBJECT-TYPE
    SYNTAX       Counter64
    MAX-ACCESS   read-only
    STATUS       current
    DESCRIPTION
        "Cisco UCS adaptor:FcIfFC4Stats:outputRequestsDelta
        managed object property"
    ::= { cucsAdaptorFcIfFC4StatsEntry 26 }

cucsAdaptorFcIfFC4StatsOutputRequestsDeltaAvg OBJECT-TYPE
    SYNTAX       Unsigned64
    MAX-ACCESS   read-only
    STATUS       current
    DESCRIPTION
        "Cisco UCS adaptor:FcIfFC4Stats:outputRequestsDeltaAvg
        managed object property"
    ::= { cucsAdaptorFcIfFC4StatsEntry 27 }

cucsAdaptorFcIfFC4StatsOutputRequestsDeltaMax OBJECT-TYPE
    SYNTAX       Unsigned64
    MAX-ACCESS   read-only
    STATUS       current
    DESCRIPTION
        "Cisco UCS adaptor:FcIfFC4Stats:outputRequestsDeltaMax
        managed object property"
    ::= { cucsAdaptorFcIfFC4StatsEntry 28 }

cucsAdaptorFcIfFC4StatsOutputRequestsDeltaMin OBJECT-TYPE
    SYNTAX       Unsigned64
    MAX-ACCESS   read-only
    STATUS       current
    DESCRIPTION
        "Cisco UCS adaptor:FcIfFC4Stats:outputRequestsDeltaMin
        managed object property"
    ::= { cucsAdaptorFcIfFC4StatsEntry 29 }

cucsAdaptorFcIfFC4StatsSuspect OBJECT-TYPE
    SYNTAX       TruthValue
    MAX-ACCESS   read-only
    STATUS       current
    DESCRIPTION
        "Cisco UCS adaptor:FcIfFC4Stats:suspect managed object property"
    ::= { cucsAdaptorFcIfFC4StatsEntry 30 }

cucsAdaptorFcIfFC4StatsThresholded OBJECT-TYPE
    SYNTAX       CucsAdaptorFcIfFC4StatsThresholded
    MAX-ACCESS   read-only
    STATUS       current
    DESCRIPTION
        "Cisco UCS adaptor:FcIfFC4Stats:thresholded managed
        object property"
    ::= { cucsAdaptorFcIfFC4StatsEntry 31 }

cucsAdaptorFcIfFC4StatsTimeCollected OBJECT-TYPE
    SYNTAX       DateAndTime
    MAX-ACCESS   read-only
    STATUS       current
    DESCRIPTION
        "Cisco UCS adaptor:FcIfFC4Stats:timeCollected managed
        object property"
    ::= { cucsAdaptorFcIfFC4StatsEntry 32 }

cucsAdaptorFcIfFC4StatsUpdate OBJECT-TYPE
    SYNTAX       Gauge32
    MAX-ACCESS   read-only
    STATUS       current
    DESCRIPTION
        "Cisco UCS adaptor:FcIfFC4Stats:update managed object property"
    ::= { cucsAdaptorFcIfFC4StatsEntry 33 }

cucsAdaptorFcIfFC4StatsHistTable OBJECT-TYPE
    SYNTAX           SEQUENCE OF CucsAdaptorFcIfFC4StatsHistEntry
    MAX-ACCESS       not-accessible
    STATUS           current
    DESCRIPTION
        "Cisco UCS adaptor:FcIfFC4StatsHist managed object table"
    ::= { cucsAdaptorObjects 31 }

cucsAdaptorFcIfFC4StatsHistEntry OBJECT-TYPE
    SYNTAX           CucsAdaptorFcIfFC4StatsHistEntry
    MAX-ACCESS       not-accessible
    STATUS           current
    DESCRIPTION
        "Entry for the cucsAdaptorFcIfFC4StatsHistTable table."
    INDEX { cucsAdaptorFcIfFC4StatsHistInstanceId }
    ::= { cucsAdaptorFcIfFC4StatsHistTable 1 }

CucsAdaptorFcIfFC4StatsHistEntry ::= SEQUENCE {
    cucsAdaptorFcIfFC4StatsHistInstanceId                            CucsManagedObjectId,
    cucsAdaptorFcIfFC4StatsHistDn                                    CucsManagedObjectDn,
    cucsAdaptorFcIfFC4StatsHistRn                                    SnmpAdminString,
    cucsAdaptorFcIfFC4StatsHistControlRequests                       Unsigned64,
    cucsAdaptorFcIfFC4StatsHistControlRequestsDelta                  Unsigned64,
    cucsAdaptorFcIfFC4StatsHistControlRequestsDeltaAvg               Unsigned64,
    cucsAdaptorFcIfFC4StatsHistControlRequestsDeltaMax               Unsigned64,
    cucsAdaptorFcIfFC4StatsHistControlRequestsDeltaMin               Unsigned64,
    cucsAdaptorFcIfFC4StatsHistId                                    Unsigned64,
    cucsAdaptorFcIfFC4StatsHistInputMegabytes                        Unsigned64,
    cucsAdaptorFcIfFC4StatsHistInputMegabytesDelta                   Unsigned64,
    cucsAdaptorFcIfFC4StatsHistInputMegabytesDeltaAvg                Unsigned64,
    cucsAdaptorFcIfFC4StatsHistInputMegabytesDeltaMax                Unsigned64,
    cucsAdaptorFcIfFC4StatsHistInputMegabytesDeltaMin                Unsigned64,
    cucsAdaptorFcIfFC4StatsHistInputRequests                         Unsigned64,
    cucsAdaptorFcIfFC4StatsHistInputRequestsDelta                    Unsigned64,
    cucsAdaptorFcIfFC4StatsHistInputRequestsDeltaAvg                 Unsigned64,
    cucsAdaptorFcIfFC4StatsHistInputRequestsDeltaMax                 Unsigned64,
    cucsAdaptorFcIfFC4StatsHistInputRequestsDeltaMin                 Unsigned64,
    cucsAdaptorFcIfFC4StatsHistMostRecent                            TruthValue,
    cucsAdaptorFcIfFC4StatsHistOutputMegabytes                       Unsigned64,
    cucsAdaptorFcIfFC4StatsHistOutputMegabytesDelta                  Unsigned64,
    cucsAdaptorFcIfFC4StatsHistOutputMegabytesDeltaAvg               Unsigned64,
    cucsAdaptorFcIfFC4StatsHistOutputMegabytesDeltaMax               Unsigned64,
    cucsAdaptorFcIfFC4StatsHistOutputMegabytesDeltaMin               Unsigned64,
    cucsAdaptorFcIfFC4StatsHistOutputRequests                        Unsigned64,
    cucsAdaptorFcIfFC4StatsHistOutputRequestsDelta                   Unsigned64,
    cucsAdaptorFcIfFC4StatsHistOutputRequestsDeltaAvg                Unsigned64,
    cucsAdaptorFcIfFC4StatsHistOutputRequestsDeltaMax                Unsigned64,
    cucsAdaptorFcIfFC4StatsHistOutputRequestsDeltaMin                Unsigned64,
    cucsAdaptorFcIfFC4StatsHistSuspect                               TruthValue,
    cucsAdaptorFcIfFC4StatsHistThresholded                           CucsAdaptorFcIfFC4StatsHistThresholded,
    cucsAdaptorFcIfFC4StatsHistTimeCollected                         DateAndTime
}

cucsAdaptorFcIfFC4StatsHistInstanceId OBJECT-TYPE
    SYNTAX       CucsManagedObjectId
    MAX-ACCESS   not-accessible
    STATUS       current
    DESCRIPTION
        "Instance identifier of the managed object."
    ::= { cucsAdaptorFcIfFC4StatsHistEntry 1 }

cucsAdaptorFcIfFC4StatsHistDn OBJECT-TYPE
    SYNTAX       CucsManagedObjectDn
    MAX-ACCESS   read-only
    STATUS       current
    DESCRIPTION
        "Cisco UCS adaptor:FcIfFC4StatsHist:dn managed object property"
    ::= { cucsAdaptorFcIfFC4StatsHistEntry 2 }

cucsAdaptorFcIfFC4StatsHistRn OBJECT-TYPE
    SYNTAX       SnmpAdminString
    MAX-ACCESS   read-only
    STATUS       current
    DESCRIPTION
        "Cisco UCS adaptor:FcIfFC4StatsHist:rn managed object property"
    ::= { cucsAdaptorFcIfFC4StatsHistEntry 3 }

cucsAdaptorFcIfFC4StatsHistControlRequests OBJECT-TYPE
    SYNTAX       Unsigned64
    MAX-ACCESS   read-only
    STATUS       current
    DESCRIPTION
        "Cisco UCS adaptor:FcIfFC4StatsHist:controlRequests
        managed object property"
    ::= { cucsAdaptorFcIfFC4StatsHistEntry 4 }

cucsAdaptorFcIfFC4StatsHistControlRequestsDelta OBJECT-TYPE
    SYNTAX       Unsigned64
    MAX-ACCESS   read-only
    STATUS       current
    DESCRIPTION
        "Cisco UCS adaptor:FcIfFC4StatsHist:controlRequestsDelta
        managed object property"
    ::= { cucsAdaptorFcIfFC4StatsHistEntry 5 }

cucsAdaptorFcIfFC4StatsHistControlRequestsDeltaAvg OBJECT-TYPE
    SYNTAX       Unsigned64
    MAX-ACCESS   read-only
    STATUS       current
    DESCRIPTION
        "Cisco UCS adaptor:FcIfFC4StatsHist:controlRequestsDeltaAvg
        managed object property"
    ::= { cucsAdaptorFcIfFC4StatsHistEntry 6 }

cucsAdaptorFcIfFC4StatsHistControlRequestsDeltaMax OBJECT-TYPE
    SYNTAX       Unsigned64
    MAX-ACCESS   read-only
    STATUS       current
    DESCRIPTION
        "Cisco UCS adaptor:FcIfFC4StatsHist:controlRequestsDeltaMax
        managed object property"
    ::= { cucsAdaptorFcIfFC4StatsHistEntry 7 }

cucsAdaptorFcIfFC4StatsHistControlRequestsDeltaMin OBJECT-TYPE
    SYNTAX       Unsigned64
    MAX-ACCESS   read-only
    STATUS       current
    DESCRIPTION
        "Cisco UCS adaptor:FcIfFC4StatsHist:controlRequestsDeltaMin
        managed object property"
    ::= { cucsAdaptorFcIfFC4StatsHistEntry 8 }

cucsAdaptorFcIfFC4StatsHistId OBJECT-TYPE
    SYNTAX       Unsigned64
    MAX-ACCESS   read-only
    STATUS       current
    DESCRIPTION
        "Cisco UCS adaptor:FcIfFC4StatsHist:id managed object property"
    ::= { cucsAdaptorFcIfFC4StatsHistEntry 9 }

cucsAdaptorFcIfFC4StatsHistInputMegabytes OBJECT-TYPE
    SYNTAX       Unsigned64
    MAX-ACCESS   read-only
    STATUS       current
    DESCRIPTION
        "Cisco UCS adaptor:FcIfFC4StatsHist:inputMegabytes
        managed object property"
    ::= { cucsAdaptorFcIfFC4StatsHistEntry 10 }

cucsAdaptorFcIfFC4StatsHistInputMegabytesDelta OBJECT-TYPE
    SYNTAX       Unsigned64
    MAX-ACCESS   read-only
    STATUS       current
    DESCRIPTION
        "Cisco UCS adaptor:FcIfFC4StatsHist:inputMegabytesDelta
        managed object property"
    ::= { cucsAdaptorFcIfFC4StatsHistEntry 11 }

cucsAdaptorFcIfFC4StatsHistInputMegabytesDeltaAvg OBJECT-TYPE
    SYNTAX       Unsigned64
    MAX-ACCESS   read-only
    STATUS       current
    DESCRIPTION
        "Cisco UCS adaptor:FcIfFC4StatsHist:inputMegabytesDeltaAvg
        managed object property"
    ::= { cucsAdaptorFcIfFC4StatsHistEntry 12 }

cucsAdaptorFcIfFC4StatsHistInputMegabytesDeltaMax OBJECT-TYPE
    SYNTAX       Unsigned64
    MAX-ACCESS   read-only
    STATUS       current
    DESCRIPTION
        "Cisco UCS adaptor:FcIfFC4StatsHist:inputMegabytesDeltaMax
        managed object property"
    ::= { cucsAdaptorFcIfFC4StatsHistEntry 13 }

cucsAdaptorFcIfFC4StatsHistInputMegabytesDeltaMin OBJECT-TYPE
    SYNTAX       Unsigned64
    MAX-ACCESS   read-only
    STATUS       current
    DESCRIPTION
        "Cisco UCS adaptor:FcIfFC4StatsHist:inputMegabytesDeltaMin
        managed object property"
    ::= { cucsAdaptorFcIfFC4StatsHistEntry 14 }

cucsAdaptorFcIfFC4StatsHistInputRequests OBJECT-TYPE
    SYNTAX       Unsigned64
    MAX-ACCESS   read-only
    STATUS       current
    DESCRIPTION
        "Cisco UCS adaptor:FcIfFC4StatsHist:inputRequests
        managed object property"
    ::= { cucsAdaptorFcIfFC4StatsHistEntry 15 }

cucsAdaptorFcIfFC4StatsHistInputRequestsDelta OBJECT-TYPE
    SYNTAX       Unsigned64
    MAX-ACCESS   read-only
    STATUS       current
    DESCRIPTION
        "Cisco UCS adaptor:FcIfFC4StatsHist:inputRequestsDelta
        managed object property"
    ::= { cucsAdaptorFcIfFC4StatsHistEntry 16 }

cucsAdaptorFcIfFC4StatsHistInputRequestsDeltaAvg OBJECT-TYPE
    SYNTAX       Unsigned64
    MAX-ACCESS   read-only
    STATUS       current
    DESCRIPTION
        "Cisco UCS adaptor:FcIfFC4StatsHist:inputRequestsDeltaAvg
        managed object property"
    ::= { cucsAdaptorFcIfFC4StatsHistEntry 17 }

cucsAdaptorFcIfFC4StatsHistInputRequestsDeltaMax OBJECT-TYPE
    SYNTAX       Unsigned64
    MAX-ACCESS   read-only
    STATUS       current
    DESCRIPTION
        "Cisco UCS adaptor:FcIfFC4StatsHist:inputRequestsDeltaMax
        managed object property"
    ::= { cucsAdaptorFcIfFC4StatsHistEntry 18 }

cucsAdaptorFcIfFC4StatsHistInputRequestsDeltaMin OBJECT-TYPE
    SYNTAX       Unsigned64
    MAX-ACCESS   read-only
    STATUS       current
    DESCRIPTION
        "Cisco UCS adaptor:FcIfFC4StatsHist:inputRequestsDeltaMin
        managed object property"
    ::= { cucsAdaptorFcIfFC4StatsHistEntry 19 }

cucsAdaptorFcIfFC4StatsHistMostRecent OBJECT-TYPE
    SYNTAX       TruthValue
    MAX-ACCESS   read-only
    STATUS       current
    DESCRIPTION
        "Cisco UCS adaptor:FcIfFC4StatsHist:mostRecent
        managed object property"
    ::= { cucsAdaptorFcIfFC4StatsHistEntry 20 }

cucsAdaptorFcIfFC4StatsHistOutputMegabytes OBJECT-TYPE
    SYNTAX       Unsigned64
    MAX-ACCESS   read-only
    STATUS       current
    DESCRIPTION
        "Cisco UCS adaptor:FcIfFC4StatsHist:outputMegabytes
        managed object property"
    ::= { cucsAdaptorFcIfFC4StatsHistEntry 21 }

cucsAdaptorFcIfFC4StatsHistOutputMegabytesDelta OBJECT-TYPE
    SYNTAX       Unsigned64
    MAX-ACCESS   read-only
    STATUS       current
    DESCRIPTION
        "Cisco UCS adaptor:FcIfFC4StatsHist:outputMegabytesDelta
        managed object property"
    ::= { cucsAdaptorFcIfFC4StatsHistEntry 22 }

cucsAdaptorFcIfFC4StatsHistOutputMegabytesDeltaAvg OBJECT-TYPE
    SYNTAX       Unsigned64
    MAX-ACCESS   read-only
    STATUS       current
    DESCRIPTION
        "Cisco UCS adaptor:FcIfFC4StatsHist:outputMegabytesDeltaAvg
        managed object property"
    ::= { cucsAdaptorFcIfFC4StatsHistEntry 23 }

cucsAdaptorFcIfFC4StatsHistOutputMegabytesDeltaMax OBJECT-TYPE
    SYNTAX       Unsigned64
    MAX-ACCESS   read-only
    STATUS       current
    DESCRIPTION
        "Cisco UCS adaptor:FcIfFC4StatsHist:outputMegabytesDeltaMax
        managed object property"
    ::= { cucsAdaptorFcIfFC4StatsHistEntry 24 }

cucsAdaptorFcIfFC4StatsHistOutputMegabytesDeltaMin OBJECT-TYPE
    SYNTAX       Unsigned64
    MAX-ACCESS   read-only
    STATUS       current
    DESCRIPTION
        "Cisco UCS adaptor:FcIfFC4StatsHist:outputMegabytesDeltaMin
        managed object property"
    ::= { cucsAdaptorFcIfFC4StatsHistEntry 25 }

cucsAdaptorFcIfFC4StatsHistOutputRequests OBJECT-TYPE
    SYNTAX       Unsigned64
    MAX-ACCESS   read-only
    STATUS       current
    DESCRIPTION
        "Cisco UCS adaptor:FcIfFC4StatsHist:outputRequests
        managed object property"
    ::= { cucsAdaptorFcIfFC4StatsHistEntry 26 }

cucsAdaptorFcIfFC4StatsHistOutputRequestsDelta OBJECT-TYPE
    SYNTAX       Unsigned64
    MAX-ACCESS   read-only
    STATUS       current
    DESCRIPTION
        "Cisco UCS adaptor:FcIfFC4StatsHist:outputRequestsDelta
        managed object property"
    ::= { cucsAdaptorFcIfFC4StatsHistEntry 27 }

cucsAdaptorFcIfFC4StatsHistOutputRequestsDeltaAvg OBJECT-TYPE
    SYNTAX       Unsigned64
    MAX-ACCESS   read-only
    STATUS       current
    DESCRIPTION
        "Cisco UCS adaptor:FcIfFC4StatsHist:outputRequestsDeltaAvg
        managed object property"
    ::= { cucsAdaptorFcIfFC4StatsHistEntry 28 }

cucsAdaptorFcIfFC4StatsHistOutputRequestsDeltaMax OBJECT-TYPE
    SYNTAX       Unsigned64
    MAX-ACCESS   read-only
    STATUS       current
    DESCRIPTION
        "Cisco UCS adaptor:FcIfFC4StatsHist:outputRequestsDeltaMax
        managed object property"
    ::= { cucsAdaptorFcIfFC4StatsHistEntry 29 }

cucsAdaptorFcIfFC4StatsHistOutputRequestsDeltaMin OBJECT-TYPE
    SYNTAX       Unsigned64
    MAX-ACCESS   read-only
    STATUS       current
    DESCRIPTION
        "Cisco UCS adaptor:FcIfFC4StatsHist:outputRequestsDeltaMin
        managed object property"
    ::= { cucsAdaptorFcIfFC4StatsHistEntry 30 }

cucsAdaptorFcIfFC4StatsHistSuspect OBJECT-TYPE
    SYNTAX       TruthValue
    MAX-ACCESS   read-only
    STATUS       current
    DESCRIPTION
        "Cisco UCS adaptor:FcIfFC4StatsHist:suspect managed
        object property"
    ::= { cucsAdaptorFcIfFC4StatsHistEntry 31 }

cucsAdaptorFcIfFC4StatsHistThresholded OBJECT-TYPE
    SYNTAX       CucsAdaptorFcIfFC4StatsHistThresholded
    MAX-ACCESS   read-only
    STATUS       current
    DESCRIPTION
        "Cisco UCS adaptor:FcIfFC4StatsHist:thresholded
        managed object property"
    ::= { cucsAdaptorFcIfFC4StatsHistEntry 32 }

cucsAdaptorFcIfFC4StatsHistTimeCollected OBJECT-TYPE
    SYNTAX       DateAndTime
    MAX-ACCESS   read-only
    STATUS       current
    DESCRIPTION
        "Cisco UCS adaptor:FcIfFC4StatsHist:timeCollected
        managed object property"
    ::= { cucsAdaptorFcIfFC4StatsHistEntry 33 }

cucsAdaptorFcIfFrameStatsTable OBJECT-TYPE
    SYNTAX           SEQUENCE OF CucsAdaptorFcIfFrameStatsEntry
    MAX-ACCESS       not-accessible
    STATUS           current
    DESCRIPTION
        "Cisco UCS adaptor:FcIfFrameStats managed object table"
    ::= { cucsAdaptorObjects 32 }

cucsAdaptorFcIfFrameStatsEntry OBJECT-TYPE
    SYNTAX           CucsAdaptorFcIfFrameStatsEntry
    MAX-ACCESS       not-accessible
    STATUS           current
    DESCRIPTION
        "Entry for the cucsAdaptorFcIfFrameStatsTable table."
    INDEX { cucsAdaptorFcIfFrameStatsInstanceId }
    ::= { cucsAdaptorFcIfFrameStatsTable 1 }

CucsAdaptorFcIfFrameStatsEntry ::= SEQUENCE {
    cucsAdaptorFcIfFrameStatsInstanceId                              CucsManagedObjectId,
    cucsAdaptorFcIfFrameStatsDn                                      CucsManagedObjectDn,
    cucsAdaptorFcIfFrameStatsRn                                      SnmpAdminString,
    cucsAdaptorFcIfFrameStatsDumpedFrames                            Unsigned64,
    cucsAdaptorFcIfFrameStatsDumpedFramesDelta                       Counter64,
    cucsAdaptorFcIfFrameStatsDumpedFramesDeltaAvg                    Unsigned64,
    cucsAdaptorFcIfFrameStatsDumpedFramesDeltaMax                    Unsigned64,
    cucsAdaptorFcIfFrameStatsDumpedFramesDeltaMin                    Unsigned64,
    cucsAdaptorFcIfFrameStatsErrorFrames                             Unsigned64,
    cucsAdaptorFcIfFrameStatsErrorFramesDelta                        Counter64,
    cucsAdaptorFcIfFrameStatsErrorFramesDeltaAvg                     Unsigned64,
    cucsAdaptorFcIfFrameStatsErrorFramesDeltaMax                     Unsigned64,
    cucsAdaptorFcIfFrameStatsErrorFramesDeltaMin                     Unsigned64,
    cucsAdaptorFcIfFrameStatsIntervals                               Gauge32,
    cucsAdaptorFcIfFrameStatsRxFrames                                Unsigned64,
    cucsAdaptorFcIfFrameStatsRxFramesDelta                           Counter64,
    cucsAdaptorFcIfFrameStatsRxFramesDeltaAvg                        Unsigned64,
    cucsAdaptorFcIfFrameStatsRxFramesDeltaMax                        Unsigned64,
    cucsAdaptorFcIfFrameStatsRxFramesDeltaMin                        Unsigned64,
    cucsAdaptorFcIfFrameStatsSuspect                                 TruthValue,
    cucsAdaptorFcIfFrameStatsThresholded                             CucsAdaptorFcIfFrameStatsThresholded,
    cucsAdaptorFcIfFrameStatsTimeCollected                           DateAndTime,
    cucsAdaptorFcIfFrameStatsTxFrames                                Unsigned64,
    cucsAdaptorFcIfFrameStatsTxFramesDelta                           Counter64,
    cucsAdaptorFcIfFrameStatsTxFramesDeltaAvg                        Unsigned64,
    cucsAdaptorFcIfFrameStatsTxFramesDeltaMax                        Unsigned64,
    cucsAdaptorFcIfFrameStatsTxFramesDeltaMin                        Unsigned64,
    cucsAdaptorFcIfFrameStatsUpdate                                  Gauge32
}

cucsAdaptorFcIfFrameStatsInstanceId OBJECT-TYPE
    SYNTAX       CucsManagedObjectId
    MAX-ACCESS   not-accessible
    STATUS       current
    DESCRIPTION
        "Instance identifier of the managed object."
    ::= { cucsAdaptorFcIfFrameStatsEntry 1 }

cucsAdaptorFcIfFrameStatsDn OBJECT-TYPE
    SYNTAX       CucsManagedObjectDn
    MAX-ACCESS   read-only
    STATUS       current
    DESCRIPTION
        "Cisco UCS adaptor:FcIfFrameStats:dn managed object property"
    ::= { cucsAdaptorFcIfFrameStatsEntry 2 }

cucsAdaptorFcIfFrameStatsRn OBJECT-TYPE
    SYNTAX       SnmpAdminString
    MAX-ACCESS   read-only
    STATUS       current
    DESCRIPTION
        "Cisco UCS adaptor:FcIfFrameStats:rn managed object property"
    ::= { cucsAdaptorFcIfFrameStatsEntry 3 }

cucsAdaptorFcIfFrameStatsDumpedFrames OBJECT-TYPE
    SYNTAX       Unsigned64
    MAX-ACCESS   read-only
    STATUS       current
    DESCRIPTION
        "Cisco UCS adaptor:FcIfFrameStats:dumpedFrames
        managed object property"
    ::= { cucsAdaptorFcIfFrameStatsEntry 4 }

cucsAdaptorFcIfFrameStatsDumpedFramesDelta OBJECT-TYPE
    SYNTAX       Counter64
    MAX-ACCESS   read-only
    STATUS       current
    DESCRIPTION
        "Cisco UCS adaptor:FcIfFrameStats:dumpedFramesDelta
        managed object property"
    ::= { cucsAdaptorFcIfFrameStatsEntry 5 }

cucsAdaptorFcIfFrameStatsDumpedFramesDeltaAvg OBJECT-TYPE
    SYNTAX       Unsigned64
    MAX-ACCESS   read-only
    STATUS       current
    DESCRIPTION
        "Cisco UCS adaptor:FcIfFrameStats:dumpedFramesDeltaAvg
        managed object property"
    ::= { cucsAdaptorFcIfFrameStatsEntry 6 }

cucsAdaptorFcIfFrameStatsDumpedFramesDeltaMax OBJECT-TYPE
    SYNTAX       Unsigned64
    MAX-ACCESS   read-only
    STATUS       current
    DESCRIPTION
        "Cisco UCS adaptor:FcIfFrameStats:dumpedFramesDeltaMax
        managed object property"
    ::= { cucsAdaptorFcIfFrameStatsEntry 7 }

cucsAdaptorFcIfFrameStatsDumpedFramesDeltaMin OBJECT-TYPE
    SYNTAX       Unsigned64
    MAX-ACCESS   read-only
    STATUS       current
    DESCRIPTION
        "Cisco UCS adaptor:FcIfFrameStats:dumpedFramesDeltaMin
        managed object property"
    ::= { cucsAdaptorFcIfFrameStatsEntry 8 }

cucsAdaptorFcIfFrameStatsErrorFrames OBJECT-TYPE
    SYNTAX       Unsigned64
    MAX-ACCESS   read-only
    STATUS       current
    DESCRIPTION
        "Cisco UCS adaptor:FcIfFrameStats:errorFrames managed
        object property"
    ::= { cucsAdaptorFcIfFrameStatsEntry 9 }

cucsAdaptorFcIfFrameStatsErrorFramesDelta OBJECT-TYPE
    SYNTAX       Counter64
    MAX-ACCESS   read-only
    STATUS       current
    DESCRIPTION
        "Cisco UCS adaptor:FcIfFrameStats:errorFramesDelta
        managed object property"
    ::= { cucsAdaptorFcIfFrameStatsEntry 10 }

cucsAdaptorFcIfFrameStatsErrorFramesDeltaAvg OBJECT-TYPE
    SYNTAX       Unsigned64
    MAX-ACCESS   read-only
    STATUS       current
    DESCRIPTION
        "Cisco UCS adaptor:FcIfFrameStats:errorFramesDeltaAvg
        managed object property"
    ::= { cucsAdaptorFcIfFrameStatsEntry 11 }

cucsAdaptorFcIfFrameStatsErrorFramesDeltaMax OBJECT-TYPE
    SYNTAX       Unsigned64
    MAX-ACCESS   read-only
    STATUS       current
    DESCRIPTION
        "Cisco UCS adaptor:FcIfFrameStats:errorFramesDeltaMax
        managed object property"
    ::= { cucsAdaptorFcIfFrameStatsEntry 12 }

cucsAdaptorFcIfFrameStatsErrorFramesDeltaMin OBJECT-TYPE
    SYNTAX       Unsigned64
    MAX-ACCESS   read-only
    STATUS       current
    DESCRIPTION
        "Cisco UCS adaptor:FcIfFrameStats:errorFramesDeltaMin
        managed object property"
    ::= { cucsAdaptorFcIfFrameStatsEntry 13 }

cucsAdaptorFcIfFrameStatsIntervals OBJECT-TYPE
    SYNTAX       Gauge32
    MAX-ACCESS   read-only
    STATUS       current
    DESCRIPTION
        "Cisco UCS adaptor:FcIfFrameStats:intervals managed
        object property"
    ::= { cucsAdaptorFcIfFrameStatsEntry 14 }

cucsAdaptorFcIfFrameStatsRxFrames OBJECT-TYPE
    SYNTAX       Unsigned64
    MAX-ACCESS   read-only
    STATUS       current
    DESCRIPTION
        "Cisco UCS adaptor:FcIfFrameStats:rxFrames managed
        object property"
    ::= { cucsAdaptorFcIfFrameStatsEntry 15 }

cucsAdaptorFcIfFrameStatsRxFramesDelta OBJECT-TYPE
    SYNTAX       Counter64
    MAX-ACCESS   read-only
    STATUS       current
    DESCRIPTION
        "Cisco UCS adaptor:FcIfFrameStats:rxFramesDelta
        managed object property"
    ::= { cucsAdaptorFcIfFrameStatsEntry 16 }

cucsAdaptorFcIfFrameStatsRxFramesDeltaAvg OBJECT-TYPE
    SYNTAX       Unsigned64
    MAX-ACCESS   read-only
    STATUS       current
    DESCRIPTION
        "Cisco UCS adaptor:FcIfFrameStats:rxFramesDeltaAvg
        managed object property"
    ::= { cucsAdaptorFcIfFrameStatsEntry 17 }

cucsAdaptorFcIfFrameStatsRxFramesDeltaMax OBJECT-TYPE
    SYNTAX       Unsigned64
    MAX-ACCESS   read-only
    STATUS       current
    DESCRIPTION
        "Cisco UCS adaptor:FcIfFrameStats:rxFramesDeltaMax
        managed object property"
    ::= { cucsAdaptorFcIfFrameStatsEntry 18 }

cucsAdaptorFcIfFrameStatsRxFramesDeltaMin OBJECT-TYPE
    SYNTAX       Unsigned64
    MAX-ACCESS   read-only
    STATUS       current
    DESCRIPTION
        "Cisco UCS adaptor:FcIfFrameStats:rxFramesDeltaMin
        managed object property"
    ::= { cucsAdaptorFcIfFrameStatsEntry 19 }

cucsAdaptorFcIfFrameStatsSuspect OBJECT-TYPE
    SYNTAX       TruthValue
    MAX-ACCESS   read-only
    STATUS       current
    DESCRIPTION
        "Cisco UCS adaptor:FcIfFrameStats:suspect managed object property"
    ::= { cucsAdaptorFcIfFrameStatsEntry 20 }

cucsAdaptorFcIfFrameStatsThresholded OBJECT-TYPE
    SYNTAX       CucsAdaptorFcIfFrameStatsThresholded
    MAX-ACCESS   read-only
    STATUS       current
    DESCRIPTION
        "Cisco UCS adaptor:FcIfFrameStats:thresholded managed
        object property"
    ::= { cucsAdaptorFcIfFrameStatsEntry 21 }

cucsAdaptorFcIfFrameStatsTimeCollected OBJECT-TYPE
    SYNTAX       DateAndTime
    MAX-ACCESS   read-only
    STATUS       current
    DESCRIPTION
        "Cisco UCS adaptor:FcIfFrameStats:timeCollected
        managed object property"
    ::= { cucsAdaptorFcIfFrameStatsEntry 22 }

cucsAdaptorFcIfFrameStatsTxFrames OBJECT-TYPE
    SYNTAX       Unsigned64
    MAX-ACCESS   read-only
    STATUS       current
    DESCRIPTION
        "Cisco UCS adaptor:FcIfFrameStats:txFrames managed
        object property"
    ::= { cucsAdaptorFcIfFrameStatsEntry 23 }

cucsAdaptorFcIfFrameStatsTxFramesDelta OBJECT-TYPE
    SYNTAX       Counter64
    MAX-ACCESS   read-only
    STATUS       current
    DESCRIPTION
        "Cisco UCS adaptor:FcIfFrameStats:txFramesDelta
        managed object property"
    ::= { cucsAdaptorFcIfFrameStatsEntry 24 }

cucsAdaptorFcIfFrameStatsTxFramesDeltaAvg OBJECT-TYPE
    SYNTAX       Unsigned64
    MAX-ACCESS   read-only
    STATUS       current
    DESCRIPTION
        "Cisco UCS adaptor:FcIfFrameStats:txFramesDeltaAvg
        managed object property"
    ::= { cucsAdaptorFcIfFrameStatsEntry 25 }

cucsAdaptorFcIfFrameStatsTxFramesDeltaMax OBJECT-TYPE
    SYNTAX       Unsigned64
    MAX-ACCESS   read-only
    STATUS       current
    DESCRIPTION
        "Cisco UCS adaptor:FcIfFrameStats:txFramesDeltaMax
        managed object property"
    ::= { cucsAdaptorFcIfFrameStatsEntry 26 }

cucsAdaptorFcIfFrameStatsTxFramesDeltaMin OBJECT-TYPE
    SYNTAX       Unsigned64
    MAX-ACCESS   read-only
    STATUS       current
    DESCRIPTION
        "Cisco UCS adaptor:FcIfFrameStats:txFramesDeltaMin
        managed object property"
    ::= { cucsAdaptorFcIfFrameStatsEntry 27 }

cucsAdaptorFcIfFrameStatsUpdate OBJECT-TYPE
    SYNTAX       Gauge32
    MAX-ACCESS   read-only
    STATUS       current
    DESCRIPTION
        "Cisco UCS adaptor:FcIfFrameStats:update managed object property"
    ::= { cucsAdaptorFcIfFrameStatsEntry 28 }

cucsAdaptorFcIfFrameStatsHistTable OBJECT-TYPE
    SYNTAX           SEQUENCE OF CucsAdaptorFcIfFrameStatsHistEntry
    MAX-ACCESS       not-accessible
    STATUS           current
    DESCRIPTION
        "Cisco UCS adaptor:FcIfFrameStatsHist managed object table"
    ::= { cucsAdaptorObjects 33 }

cucsAdaptorFcIfFrameStatsHistEntry OBJECT-TYPE
    SYNTAX           CucsAdaptorFcIfFrameStatsHistEntry
    MAX-ACCESS       not-accessible
    STATUS           current
    DESCRIPTION
        "Entry for the cucsAdaptorFcIfFrameStatsHistTable table."
    INDEX { cucsAdaptorFcIfFrameStatsHistInstanceId }
    ::= { cucsAdaptorFcIfFrameStatsHistTable 1 }

CucsAdaptorFcIfFrameStatsHistEntry ::= SEQUENCE {
    cucsAdaptorFcIfFrameStatsHistInstanceId                          CucsManagedObjectId,
    cucsAdaptorFcIfFrameStatsHistDn                                  CucsManagedObjectDn,
    cucsAdaptorFcIfFrameStatsHistRn                                  SnmpAdminString,
    cucsAdaptorFcIfFrameStatsHistDumpedFrames                        Unsigned64,
    cucsAdaptorFcIfFrameStatsHistDumpedFramesDelta                   Unsigned64,
    cucsAdaptorFcIfFrameStatsHistDumpedFramesDeltaAvg                Unsigned64,
    cucsAdaptorFcIfFrameStatsHistDumpedFramesDeltaMax                Unsigned64,
    cucsAdaptorFcIfFrameStatsHistDumpedFramesDeltaMin                Unsigned64,
    cucsAdaptorFcIfFrameStatsHistErrorFrames                         Unsigned64,
    cucsAdaptorFcIfFrameStatsHistErrorFramesDelta                    Unsigned64,
    cucsAdaptorFcIfFrameStatsHistErrorFramesDeltaAvg                 Unsigned64,
    cucsAdaptorFcIfFrameStatsHistErrorFramesDeltaMax                 Unsigned64,
    cucsAdaptorFcIfFrameStatsHistErrorFramesDeltaMin                 Unsigned64,
    cucsAdaptorFcIfFrameStatsHistId                                  Unsigned64,
    cucsAdaptorFcIfFrameStatsHistMostRecent                          TruthValue,
    cucsAdaptorFcIfFrameStatsHistRxFrames                            Unsigned64,
    cucsAdaptorFcIfFrameStatsHistRxFramesDelta                       Unsigned64,
    cucsAdaptorFcIfFrameStatsHistRxFramesDeltaAvg                    Unsigned64,
    cucsAdaptorFcIfFrameStatsHistRxFramesDeltaMax                    Unsigned64,
    cucsAdaptorFcIfFrameStatsHistRxFramesDeltaMin                    Unsigned64,
    cucsAdaptorFcIfFrameStatsHistSuspect                             TruthValue,
    cucsAdaptorFcIfFrameStatsHistThresholded                         CucsAdaptorFcIfFrameStatsHistThresholded,
    cucsAdaptorFcIfFrameStatsHistTimeCollected                       DateAndTime,
    cucsAdaptorFcIfFrameStatsHistTxFrames                            Unsigned64,
    cucsAdaptorFcIfFrameStatsHistTxFramesDelta                       Unsigned64,
    cucsAdaptorFcIfFrameStatsHistTxFramesDeltaAvg                    Unsigned64,
    cucsAdaptorFcIfFrameStatsHistTxFramesDeltaMax                    Unsigned64,
    cucsAdaptorFcIfFrameStatsHistTxFramesDeltaMin                    Unsigned64
}

cucsAdaptorFcIfFrameStatsHistInstanceId OBJECT-TYPE
    SYNTAX       CucsManagedObjectId
    MAX-ACCESS   not-accessible
    STATUS       current
    DESCRIPTION
        "Instance identifier of the managed object."
    ::= { cucsAdaptorFcIfFrameStatsHistEntry 1 }

cucsAdaptorFcIfFrameStatsHistDn OBJECT-TYPE
    SYNTAX       CucsManagedObjectDn
    MAX-ACCESS   read-only
    STATUS       current
    DESCRIPTION
        "Cisco UCS adaptor:FcIfFrameStatsHist:dn managed object property"
    ::= { cucsAdaptorFcIfFrameStatsHistEntry 2 }

cucsAdaptorFcIfFrameStatsHistRn OBJECT-TYPE
    SYNTAX       SnmpAdminString
    MAX-ACCESS   read-only
    STATUS       current
    DESCRIPTION
        "Cisco UCS adaptor:FcIfFrameStatsHist:rn managed object property"
    ::= { cucsAdaptorFcIfFrameStatsHistEntry 3 }

cucsAdaptorFcIfFrameStatsHistDumpedFrames OBJECT-TYPE
    SYNTAX       Unsigned64
    MAX-ACCESS   read-only
    STATUS       current
    DESCRIPTION
        "Cisco UCS adaptor:FcIfFrameStatsHist:dumpedFrames
        managed object property"
    ::= { cucsAdaptorFcIfFrameStatsHistEntry 4 }

cucsAdaptorFcIfFrameStatsHistDumpedFramesDelta OBJECT-TYPE
    SYNTAX       Unsigned64
    MAX-ACCESS   read-only
    STATUS       current
    DESCRIPTION
        "Cisco UCS adaptor:FcIfFrameStatsHist:dumpedFramesDelta
        managed object property"
    ::= { cucsAdaptorFcIfFrameStatsHistEntry 5 }

cucsAdaptorFcIfFrameStatsHistDumpedFramesDeltaAvg OBJECT-TYPE
    SYNTAX       Unsigned64
    MAX-ACCESS   read-only
    STATUS       current
    DESCRIPTION
        "Cisco UCS adaptor:FcIfFrameStatsHist:dumpedFramesDeltaAvg
        managed object property"
    ::= { cucsAdaptorFcIfFrameStatsHistEntry 6 }

cucsAdaptorFcIfFrameStatsHistDumpedFramesDeltaMax OBJECT-TYPE
    SYNTAX       Unsigned64
    MAX-ACCESS   read-only
    STATUS       current
    DESCRIPTION
        "Cisco UCS adaptor:FcIfFrameStatsHist:dumpedFramesDeltaMax
        managed object property"
    ::= { cucsAdaptorFcIfFrameStatsHistEntry 7 }

cucsAdaptorFcIfFrameStatsHistDumpedFramesDeltaMin OBJECT-TYPE
    SYNTAX       Unsigned64
    MAX-ACCESS   read-only
    STATUS       current
    DESCRIPTION
        "Cisco UCS adaptor:FcIfFrameStatsHist:dumpedFramesDeltaMin
        managed object property"
    ::= { cucsAdaptorFcIfFrameStatsHistEntry 8 }

cucsAdaptorFcIfFrameStatsHistErrorFrames OBJECT-TYPE
    SYNTAX       Unsigned64
    MAX-ACCESS   read-only
    STATUS       current
    DESCRIPTION
        "Cisco UCS adaptor:FcIfFrameStatsHist:errorFrames
        managed object property"
    ::= { cucsAdaptorFcIfFrameStatsHistEntry 9 }

cucsAdaptorFcIfFrameStatsHistErrorFramesDelta OBJECT-TYPE
    SYNTAX       Unsigned64
    MAX-ACCESS   read-only
    STATUS       current
    DESCRIPTION
        "Cisco UCS adaptor:FcIfFrameStatsHist:errorFramesDelta
        managed object property"
    ::= { cucsAdaptorFcIfFrameStatsHistEntry 10 }

cucsAdaptorFcIfFrameStatsHistErrorFramesDeltaAvg OBJECT-TYPE
    SYNTAX       Unsigned64
    MAX-ACCESS   read-only
    STATUS       current
    DESCRIPTION
        "Cisco UCS adaptor:FcIfFrameStatsHist:errorFramesDeltaAvg
        managed object property"
    ::= { cucsAdaptorFcIfFrameStatsHistEntry 11 }

cucsAdaptorFcIfFrameStatsHistErrorFramesDeltaMax OBJECT-TYPE
    SYNTAX       Unsigned64
    MAX-ACCESS   read-only
    STATUS       current
    DESCRIPTION
        "Cisco UCS adaptor:FcIfFrameStatsHist:errorFramesDeltaMax
        managed object property"
    ::= { cucsAdaptorFcIfFrameStatsHistEntry 12 }

cucsAdaptorFcIfFrameStatsHistErrorFramesDeltaMin OBJECT-TYPE
    SYNTAX       Unsigned64
    MAX-ACCESS   read-only
    STATUS       current
    DESCRIPTION
        "Cisco UCS adaptor:FcIfFrameStatsHist:errorFramesDeltaMin
        managed object property"
    ::= { cucsAdaptorFcIfFrameStatsHistEntry 13 }

cucsAdaptorFcIfFrameStatsHistId OBJECT-TYPE
    SYNTAX       Unsigned64
    MAX-ACCESS   read-only
    STATUS       current
    DESCRIPTION
        "Cisco UCS adaptor:FcIfFrameStatsHist:id managed object property"
    ::= { cucsAdaptorFcIfFrameStatsHistEntry 14 }

cucsAdaptorFcIfFrameStatsHistMostRecent OBJECT-TYPE
    SYNTAX       TruthValue
    MAX-ACCESS   read-only
    STATUS       current
    DESCRIPTION
        "Cisco UCS adaptor:FcIfFrameStatsHist:mostRecent
        managed object property"
    ::= { cucsAdaptorFcIfFrameStatsHistEntry 15 }

cucsAdaptorFcIfFrameStatsHistRxFrames OBJECT-TYPE
    SYNTAX       Unsigned64
    MAX-ACCESS   read-only
    STATUS       current
    DESCRIPTION
        "Cisco UCS adaptor:FcIfFrameStatsHist:rxFrames
        managed object property"
    ::= { cucsAdaptorFcIfFrameStatsHistEntry 16 }

cucsAdaptorFcIfFrameStatsHistRxFramesDelta OBJECT-TYPE
    SYNTAX       Unsigned64
    MAX-ACCESS   read-only
    STATUS       current
    DESCRIPTION
        "Cisco UCS adaptor:FcIfFrameStatsHist:rxFramesDelta
        managed object property"
    ::= { cucsAdaptorFcIfFrameStatsHistEntry 17 }

cucsAdaptorFcIfFrameStatsHistRxFramesDeltaAvg OBJECT-TYPE
    SYNTAX       Unsigned64
    MAX-ACCESS   read-only
    STATUS       current
    DESCRIPTION
        "Cisco UCS adaptor:FcIfFrameStatsHist:rxFramesDeltaAvg
        managed object property"
    ::= { cucsAdaptorFcIfFrameStatsHistEntry 18 }

cucsAdaptorFcIfFrameStatsHistRxFramesDeltaMax OBJECT-TYPE
    SYNTAX       Unsigned64
    MAX-ACCESS   read-only
    STATUS       current
    DESCRIPTION
        "Cisco UCS adaptor:FcIfFrameStatsHist:rxFramesDeltaMax
        managed object property"
    ::= { cucsAdaptorFcIfFrameStatsHistEntry 19 }

cucsAdaptorFcIfFrameStatsHistRxFramesDeltaMin OBJECT-TYPE
    SYNTAX       Unsigned64
    MAX-ACCESS   read-only
    STATUS       current
    DESCRIPTION
        "Cisco UCS adaptor:FcIfFrameStatsHist:rxFramesDeltaMin
        managed object property"
    ::= { cucsAdaptorFcIfFrameStatsHistEntry 20 }

cucsAdaptorFcIfFrameStatsHistSuspect OBJECT-TYPE
    SYNTAX       TruthValue
    MAX-ACCESS   read-only
    STATUS       current
    DESCRIPTION
        "Cisco UCS adaptor:FcIfFrameStatsHist:suspect managed
        object property"
    ::= { cucsAdaptorFcIfFrameStatsHistEntry 21 }

cucsAdaptorFcIfFrameStatsHistThresholded OBJECT-TYPE
    SYNTAX       CucsAdaptorFcIfFrameStatsHistThresholded
    MAX-ACCESS   read-only
    STATUS       current
    DESCRIPTION
        "Cisco UCS adaptor:FcIfFrameStatsHist:thresholded
        managed object property"
    ::= { cucsAdaptorFcIfFrameStatsHistEntry 22 }

cucsAdaptorFcIfFrameStatsHistTimeCollected OBJECT-TYPE
    SYNTAX       DateAndTime
    MAX-ACCESS   read-only
    STATUS       current
    DESCRIPTION
        "Cisco UCS adaptor:FcIfFrameStatsHist:timeCollected
        managed object property"
    ::= { cucsAdaptorFcIfFrameStatsHistEntry 23 }

cucsAdaptorFcIfFrameStatsHistTxFrames OBJECT-TYPE
    SYNTAX       Unsigned64
    MAX-ACCESS   read-only
    STATUS       current
    DESCRIPTION
        "Cisco UCS adaptor:FcIfFrameStatsHist:txFrames
        managed object property"
    ::= { cucsAdaptorFcIfFrameStatsHistEntry 24 }

cucsAdaptorFcIfFrameStatsHistTxFramesDelta OBJECT-TYPE
    SYNTAX       Unsigned64
    MAX-ACCESS   read-only
    STATUS       current
    DESCRIPTION
        "Cisco UCS adaptor:FcIfFrameStatsHist:txFramesDelta
        managed object property"
    ::= { cucsAdaptorFcIfFrameStatsHistEntry 25 }

cucsAdaptorFcIfFrameStatsHistTxFramesDeltaAvg OBJECT-TYPE
    SYNTAX       Unsigned64
    MAX-ACCESS   read-only
    STATUS       current
    DESCRIPTION
        "Cisco UCS adaptor:FcIfFrameStatsHist:txFramesDeltaAvg
        managed object property"
    ::= { cucsAdaptorFcIfFrameStatsHistEntry 26 }

cucsAdaptorFcIfFrameStatsHistTxFramesDeltaMax OBJECT-TYPE
    SYNTAX       Unsigned64
    MAX-ACCESS   read-only
    STATUS       current
    DESCRIPTION
        "Cisco UCS adaptor:FcIfFrameStatsHist:txFramesDeltaMax
        managed object property"
    ::= { cucsAdaptorFcIfFrameStatsHistEntry 27 }

cucsAdaptorFcIfFrameStatsHistTxFramesDeltaMin OBJECT-TYPE
    SYNTAX       Unsigned64
    MAX-ACCESS   read-only
    STATUS       current
    DESCRIPTION
        "Cisco UCS adaptor:FcIfFrameStatsHist:txFramesDeltaMin
        managed object property"
    ::= { cucsAdaptorFcIfFrameStatsHistEntry 28 }

cucsAdaptorFcInterruptProfileTable OBJECT-TYPE
    SYNTAX           SEQUENCE OF CucsAdaptorFcInterruptProfileEntry
    MAX-ACCESS       not-accessible
    STATUS           current
    DESCRIPTION
        "Cisco UCS adaptor:FcInterruptProfile managed object table"
    ::= { cucsAdaptorObjects 34 }

cucsAdaptorFcInterruptProfileEntry OBJECT-TYPE
    SYNTAX           CucsAdaptorFcInterruptProfileEntry
    MAX-ACCESS       not-accessible
    STATUS           current
    DESCRIPTION
        "Entry for the cucsAdaptorFcInterruptProfileTable table."
    INDEX { cucsAdaptorFcInterruptProfileInstanceId }
    ::= { cucsAdaptorFcInterruptProfileTable 1 }

CucsAdaptorFcInterruptProfileEntry ::= SEQUENCE {
    cucsAdaptorFcInterruptProfileInstanceId                          CucsManagedObjectId,
    cucsAdaptorFcInterruptProfileDn                                  CucsManagedObjectDn,
    cucsAdaptorFcInterruptProfileRn                                  SnmpAdminString,
    cucsAdaptorFcInterruptProfileMode                                CucsAdaptorInterruptMode
}

cucsAdaptorFcInterruptProfileInstanceId OBJECT-TYPE
    SYNTAX       CucsManagedObjectId
    MAX-ACCESS   not-accessible
    STATUS       current
    DESCRIPTION
        "Instance identifier of the managed object."
    ::= { cucsAdaptorFcInterruptProfileEntry 1 }

cucsAdaptorFcInterruptProfileDn OBJECT-TYPE
    SYNTAX       CucsManagedObjectDn
    MAX-ACCESS   read-only
    STATUS       current
    DESCRIPTION
        "Cisco UCS adaptor:FcInterruptProfile:dn managed object property"
    ::= { cucsAdaptorFcInterruptProfileEntry 2 }

cucsAdaptorFcInterruptProfileRn OBJECT-TYPE
    SYNTAX       SnmpAdminString
    MAX-ACCESS   read-only
    STATUS       current
    DESCRIPTION
        "Cisco UCS adaptor:FcInterruptProfile:rn managed object property"
    ::= { cucsAdaptorFcInterruptProfileEntry 3 }

cucsAdaptorFcInterruptProfileMode OBJECT-TYPE
    SYNTAX       CucsAdaptorInterruptMode
    MAX-ACCESS   read-only
    STATUS       current
    DESCRIPTION
        "Cisco UCS adaptor:FcInterruptProfile:mode managed
        object property"
    ::= { cucsAdaptorFcInterruptProfileEntry 4 }

cucsAdaptorFcOEIfTable OBJECT-TYPE
    SYNTAX           SEQUENCE OF CucsAdaptorFcOEIfEntry
    MAX-ACCESS       not-accessible
    STATUS           current
    DESCRIPTION
        "Cisco UCS adaptor:FcOEIf managed object table"
    ::= { cucsAdaptorObjects 35 }

cucsAdaptorFcOEIfEntry OBJECT-TYPE
    SYNTAX           CucsAdaptorFcOEIfEntry
    MAX-ACCESS       not-accessible
    STATUS           current
    DESCRIPTION
        "Entry for the cucsAdaptorFcOEIfTable table."
    INDEX { cucsAdaptorFcOEIfInstanceId }
    ::= { cucsAdaptorFcOEIfTable 1 }

CucsAdaptorFcOEIfEntry ::= SEQUENCE {
    cucsAdaptorFcOEIfInstanceId                                      CucsManagedObjectId,
    cucsAdaptorFcOEIfDn                                              CucsManagedObjectDn,
    cucsAdaptorFcOEIfRn                                              SnmpAdminString,
    cucsAdaptorFcOEIfEpDn                                            SnmpAdminString,
    cucsAdaptorFcOEIfFcoeVlan                                        Gauge32,
    cucsAdaptorFcOEIfId                                              Gauge32,
    cucsAdaptorFcOEIfIfRole                                          CucsFabricVnetEpIfRole,
    cucsAdaptorFcOEIfIfType                                          CucsNetworkVnetEpIfType,
    cucsAdaptorFcOEIfLc                                              CucsFsmLifecycle,
    cucsAdaptorFcOEIfLocale                                          CucsFabricVnetEpLocale,
    cucsAdaptorFcOEIfMac                                             MacAddress,
    cucsAdaptorFcOEIfName                                            SnmpAdminString,
    cucsAdaptorFcOEIfPeerDn                                          SnmpAdminString,
    cucsAdaptorFcOEIfSwitchId                                        CucsNetworkSwitchId,
    cucsAdaptorFcOEIfTransport                                       CucsFabricAVsanTransport,
    cucsAdaptorFcOEIfType                                            CucsFabricAVsanType,
    cucsAdaptorFcOEIfOperState                                       CucsFabricVsanOperState,
    cucsAdaptorFcOEIfZoningState                                     CucsFabricZoningState,
    cucsAdaptorFcOEIfPolicyOwner                                     CucsFabricVnetEpPolicyOwner
}

cucsAdaptorFcOEIfInstanceId OBJECT-TYPE
    SYNTAX       CucsManagedObjectId
    MAX-ACCESS   not-accessible
    STATUS       current
    DESCRIPTION
        "Instance identifier of the managed object."
    ::= { cucsAdaptorFcOEIfEntry 1 }

cucsAdaptorFcOEIfDn OBJECT-TYPE
    SYNTAX       CucsManagedObjectDn
    MAX-ACCESS   read-only
    STATUS       current
    DESCRIPTION
        "Cisco UCS adaptor:FcOEIf:dn managed object property"
    ::= { cucsAdaptorFcOEIfEntry 2 }

cucsAdaptorFcOEIfRn OBJECT-TYPE
    SYNTAX       SnmpAdminString
    MAX-ACCESS   read-only
    STATUS       current
    DESCRIPTION
        "Cisco UCS adaptor:FcOEIf:rn managed object property"
    ::= { cucsAdaptorFcOEIfEntry 3 }

cucsAdaptorFcOEIfEpDn OBJECT-TYPE
    SYNTAX       SnmpAdminString
    MAX-ACCESS   read-only
    STATUS       current
    DESCRIPTION
        "Cisco UCS adaptor:FcOEIf:epDn managed object property"
    ::= { cucsAdaptorFcOEIfEntry 4 }

cucsAdaptorFcOEIfFcoeVlan OBJECT-TYPE
    SYNTAX       Gauge32
    MAX-ACCESS   read-only
    STATUS       current
    DESCRIPTION
        "Cisco UCS adaptor:FcOEIf:fcoeVlan managed object property"
    ::= { cucsAdaptorFcOEIfEntry 5 }

cucsAdaptorFcOEIfId OBJECT-TYPE
    SYNTAX       Gauge32
    MAX-ACCESS   read-only
    STATUS       current
    DESCRIPTION
        "Cisco UCS adaptor:FcOEIf:id managed object property"
    ::= { cucsAdaptorFcOEIfEntry 6 }

cucsAdaptorFcOEIfIfRole OBJECT-TYPE
    SYNTAX       CucsFabricVnetEpIfRole
    MAX-ACCESS   read-only
    STATUS       current
    DESCRIPTION
        "Cisco UCS adaptor:FcOEIf:ifRole managed object property"
    ::= { cucsAdaptorFcOEIfEntry 7 }

cucsAdaptorFcOEIfIfType OBJECT-TYPE
    SYNTAX       CucsNetworkVnetEpIfType
    MAX-ACCESS   read-only
    STATUS       current
    DESCRIPTION
        "Cisco UCS adaptor:FcOEIf:ifType managed object property"
    ::= { cucsAdaptorFcOEIfEntry 8 }

cucsAdaptorFcOEIfLc OBJECT-TYPE
    SYNTAX       CucsFsmLifecycle
    MAX-ACCESS   read-only
    STATUS       current
    DESCRIPTION
        "Cisco UCS adaptor:FcOEIf:lc managed object property"
    ::= { cucsAdaptorFcOEIfEntry 9 }

cucsAdaptorFcOEIfLocale OBJECT-TYPE
    SYNTAX       CucsFabricVnetEpLocale
    MAX-ACCESS   read-only
    STATUS       current
    DESCRIPTION
        "Cisco UCS adaptor:FcOEIf:locale managed object property"
    ::= { cucsAdaptorFcOEIfEntry 10 }

cucsAdaptorFcOEIfMac OBJECT-TYPE
    SYNTAX       MacAddress
    MAX-ACCESS   read-only
    STATUS       current
    DESCRIPTION
        "Cisco UCS adaptor:FcOEIf:mac managed object property"
    ::= { cucsAdaptorFcOEIfEntry 11 }

cucsAdaptorFcOEIfName OBJECT-TYPE
    SYNTAX       SnmpAdminString
    MAX-ACCESS   read-only
    STATUS       current
    DESCRIPTION
        "Cisco UCS adaptor:FcOEIf:name managed object property"
    ::= { cucsAdaptorFcOEIfEntry 12 }

cucsAdaptorFcOEIfPeerDn OBJECT-TYPE
    SYNTAX       SnmpAdminString
    MAX-ACCESS   read-only
    STATUS       current
    DESCRIPTION
        "Cisco UCS adaptor:FcOEIf:peerDn managed object property"
    ::= { cucsAdaptorFcOEIfEntry 13 }

cucsAdaptorFcOEIfSwitchId OBJECT-TYPE
    SYNTAX       CucsNetworkSwitchId
    MAX-ACCESS   read-only
    STATUS       current
    DESCRIPTION
        "Cisco UCS adaptor:FcOEIf:switchId managed object property"
    ::= { cucsAdaptorFcOEIfEntry 14 }

cucsAdaptorFcOEIfTransport OBJECT-TYPE
    SYNTAX       CucsFabricAVsanTransport
    MAX-ACCESS   read-only
    STATUS       current
    DESCRIPTION
        "Cisco UCS adaptor:FcOEIf:transport managed object property"
    ::= { cucsAdaptorFcOEIfEntry 15 }

cucsAdaptorFcOEIfType OBJECT-TYPE
    SYNTAX       CucsFabricAVsanType
    MAX-ACCESS   read-only
    STATUS       current
    DESCRIPTION
        "Cisco UCS adaptor:FcOEIf:type managed object property"
    ::= { cucsAdaptorFcOEIfEntry 16 }

cucsAdaptorFcOEIfOperState OBJECT-TYPE
    SYNTAX       CucsFabricVsanOperState
    MAX-ACCESS   read-only
    STATUS       current
    DESCRIPTION
        "Cisco UCS adaptor:FcOEIf:operState managed object property"
    ::= { cucsAdaptorFcOEIfEntry 17 }

cucsAdaptorFcOEIfZoningState OBJECT-TYPE
    SYNTAX       CucsFabricZoningState
    MAX-ACCESS   read-only
    STATUS       current
    DESCRIPTION
        "Cisco UCS adaptor:FcOEIf:zoningState managed object property"
    ::= { cucsAdaptorFcOEIfEntry 18 }

cucsAdaptorFcOEIfPolicyOwner OBJECT-TYPE
    SYNTAX       CucsFabricVnetEpPolicyOwner
    MAX-ACCESS   read-only
    STATUS       current
    DESCRIPTION
        "Cisco UCS adaptor:FcOEIf:policyOwner managed object property"
    ::= { cucsAdaptorFcOEIfEntry 20 }

cucsAdaptorFcPortFLogiProfileTable OBJECT-TYPE
    SYNTAX           SEQUENCE OF CucsAdaptorFcPortFLogiProfileEntry
    MAX-ACCESS       not-accessible
    STATUS           current
    DESCRIPTION
        "Cisco UCS adaptor:FcPortFLogiProfile managed object table"
    ::= { cucsAdaptorObjects 36 }

cucsAdaptorFcPortFLogiProfileEntry OBJECT-TYPE
    SYNTAX           CucsAdaptorFcPortFLogiProfileEntry
    MAX-ACCESS       not-accessible
    STATUS           current
    DESCRIPTION
        "Entry for the cucsAdaptorFcPortFLogiProfileTable table."
    INDEX { cucsAdaptorFcPortFLogiProfileInstanceId }
    ::= { cucsAdaptorFcPortFLogiProfileTable 1 }

CucsAdaptorFcPortFLogiProfileEntry ::= SEQUENCE {
    cucsAdaptorFcPortFLogiProfileInstanceId                          CucsManagedObjectId,
    cucsAdaptorFcPortFLogiProfileDn                                  CucsManagedObjectDn,
    cucsAdaptorFcPortFLogiProfileRn                                  SnmpAdminString,
    cucsAdaptorFcPortFLogiProfileRetries                             Gauge32,
    cucsAdaptorFcPortFLogiProfileTimeout                             Gauge32
}

cucsAdaptorFcPortFLogiProfileInstanceId OBJECT-TYPE
    SYNTAX       CucsManagedObjectId
    MAX-ACCESS   not-accessible
    STATUS       current
    DESCRIPTION
        "Instance identifier of the managed object."
    ::= { cucsAdaptorFcPortFLogiProfileEntry 1 }

cucsAdaptorFcPortFLogiProfileDn OBJECT-TYPE
    SYNTAX       CucsManagedObjectDn
    MAX-ACCESS   read-only
    STATUS       current
    DESCRIPTION
        "Cisco UCS adaptor:FcPortFLogiProfile:dn managed object property"
    ::= { cucsAdaptorFcPortFLogiProfileEntry 2 }

cucsAdaptorFcPortFLogiProfileRn OBJECT-TYPE
    SYNTAX       SnmpAdminString
    MAX-ACCESS   read-only
    STATUS       current
    DESCRIPTION
        "Cisco UCS adaptor:FcPortFLogiProfile:rn managed object property"
    ::= { cucsAdaptorFcPortFLogiProfileEntry 3 }

cucsAdaptorFcPortFLogiProfileRetries OBJECT-TYPE
    SYNTAX       Gauge32
    MAX-ACCESS   read-only
    STATUS       current
    DESCRIPTION
        "Cisco UCS adaptor:FcPortFLogiProfile:retries managed
        object property"
    ::= { cucsAdaptorFcPortFLogiProfileEntry 4 }

cucsAdaptorFcPortFLogiProfileTimeout OBJECT-TYPE
    SYNTAX       Gauge32
    MAX-ACCESS   read-only
    STATUS       current
    DESCRIPTION
        "Cisco UCS adaptor:FcPortFLogiProfile:timeout managed
        object property"
    ::= { cucsAdaptorFcPortFLogiProfileEntry 5 }

cucsAdaptorFcPortPLogiProfileTable OBJECT-TYPE
    SYNTAX           SEQUENCE OF CucsAdaptorFcPortPLogiProfileEntry
    MAX-ACCESS       not-accessible
    STATUS           current
    DESCRIPTION
        "Cisco UCS adaptor:FcPortPLogiProfile managed object table"
    ::= { cucsAdaptorObjects 37 }

cucsAdaptorFcPortPLogiProfileEntry OBJECT-TYPE
    SYNTAX           CucsAdaptorFcPortPLogiProfileEntry
    MAX-ACCESS       not-accessible
    STATUS           current
    DESCRIPTION
        "Entry for the cucsAdaptorFcPortPLogiProfileTable table."
    INDEX { cucsAdaptorFcPortPLogiProfileInstanceId }
    ::= { cucsAdaptorFcPortPLogiProfileTable 1 }

CucsAdaptorFcPortPLogiProfileEntry ::= SEQUENCE {
    cucsAdaptorFcPortPLogiProfileInstanceId                          CucsManagedObjectId,
    cucsAdaptorFcPortPLogiProfileDn                                  CucsManagedObjectDn,
    cucsAdaptorFcPortPLogiProfileRn                                  SnmpAdminString,
    cucsAdaptorFcPortPLogiProfileRetries                             Gauge32,
    cucsAdaptorFcPortPLogiProfileTimeout                             Gauge32
}

cucsAdaptorFcPortPLogiProfileInstanceId OBJECT-TYPE
    SYNTAX       CucsManagedObjectId
    MAX-ACCESS   not-accessible
    STATUS       current
    DESCRIPTION
        "Instance identifier of the managed object."
    ::= { cucsAdaptorFcPortPLogiProfileEntry 1 }

cucsAdaptorFcPortPLogiProfileDn OBJECT-TYPE
    SYNTAX       CucsManagedObjectDn
    MAX-ACCESS   read-only
    STATUS       current
    DESCRIPTION
        "Cisco UCS adaptor:FcPortPLogiProfile:dn managed object property"
    ::= { cucsAdaptorFcPortPLogiProfileEntry 2 }

cucsAdaptorFcPortPLogiProfileRn OBJECT-TYPE
    SYNTAX       SnmpAdminString
    MAX-ACCESS   read-only
    STATUS       current
    DESCRIPTION
        "Cisco UCS adaptor:FcPortPLogiProfile:rn managed object property"
    ::= { cucsAdaptorFcPortPLogiProfileEntry 3 }

cucsAdaptorFcPortPLogiProfileRetries OBJECT-TYPE
    SYNTAX       Gauge32
    MAX-ACCESS   read-only
    STATUS       current
    DESCRIPTION
        "Cisco UCS adaptor:FcPortPLogiProfile:retries managed
        object property"
    ::= { cucsAdaptorFcPortPLogiProfileEntry 4 }

cucsAdaptorFcPortPLogiProfileTimeout OBJECT-TYPE
    SYNTAX       Gauge32
    MAX-ACCESS   read-only
    STATUS       current
    DESCRIPTION
        "Cisco UCS adaptor:FcPortPLogiProfile:timeout managed
        object property"
    ::= { cucsAdaptorFcPortPLogiProfileEntry 5 }

cucsAdaptorFcPortProfileTable OBJECT-TYPE
    SYNTAX           SEQUENCE OF CucsAdaptorFcPortProfileEntry
    MAX-ACCESS       not-accessible
    STATUS           current
    DESCRIPTION
        "Cisco UCS adaptor:FcPortProfile managed object table"
    ::= { cucsAdaptorObjects 38 }

cucsAdaptorFcPortProfileEntry OBJECT-TYPE
    SYNTAX           CucsAdaptorFcPortProfileEntry
    MAX-ACCESS       not-accessible
    STATUS           current
    DESCRIPTION
        "Entry for the cucsAdaptorFcPortProfileTable table."
    INDEX { cucsAdaptorFcPortProfileInstanceId }
    ::= { cucsAdaptorFcPortProfileTable 1 }

CucsAdaptorFcPortProfileEntry ::= SEQUENCE {
    cucsAdaptorFcPortProfileInstanceId                               CucsManagedObjectId,
    cucsAdaptorFcPortProfileDn                                       CucsManagedObjectDn,
    cucsAdaptorFcPortProfileRn                                       SnmpAdminString,
    cucsAdaptorFcPortProfileIoThrottleCount                          Gauge32,
    cucsAdaptorFcPortProfileLunsPerTarget                            Gauge32
}

cucsAdaptorFcPortProfileInstanceId OBJECT-TYPE
    SYNTAX       CucsManagedObjectId
    MAX-ACCESS   not-accessible
    STATUS       current
    DESCRIPTION
        "Instance identifier of the managed object."
    ::= { cucsAdaptorFcPortProfileEntry 1 }

cucsAdaptorFcPortProfileDn OBJECT-TYPE
    SYNTAX       CucsManagedObjectDn
    MAX-ACCESS   read-only
    STATUS       current
    DESCRIPTION
        "Cisco UCS adaptor:FcPortProfile:dn managed object property"
    ::= { cucsAdaptorFcPortProfileEntry 2 }

cucsAdaptorFcPortProfileRn OBJECT-TYPE
    SYNTAX       SnmpAdminString
    MAX-ACCESS   read-only
    STATUS       current
    DESCRIPTION
        "Cisco UCS adaptor:FcPortProfile:rn managed object property"
    ::= { cucsAdaptorFcPortProfileEntry 3 }

cucsAdaptorFcPortProfileIoThrottleCount OBJECT-TYPE
    SYNTAX       Gauge32
    MAX-ACCESS   read-only
    STATUS       current
    DESCRIPTION
        "Cisco UCS adaptor:FcPortProfile:ioThrottleCount
        managed object property"
    ::= { cucsAdaptorFcPortProfileEntry 4 }

cucsAdaptorFcPortProfileLunsPerTarget OBJECT-TYPE
    SYNTAX       Gauge32
    MAX-ACCESS   read-only
    STATUS       current
    DESCRIPTION
        "Cisco UCS adaptor:FcPortProfile:lunsPerTarget
        managed object property"
    ::= { cucsAdaptorFcPortProfileEntry 5 }

cucsAdaptorFcPortStatsTable OBJECT-TYPE
    SYNTAX           SEQUENCE OF CucsAdaptorFcPortStatsEntry
    MAX-ACCESS       not-accessible
    STATUS           current
    DESCRIPTION
        "Cisco UCS adaptor:FcPortStats managed object table"
    ::= { cucsAdaptorObjects 39 }

cucsAdaptorFcPortStatsEntry OBJECT-TYPE
    SYNTAX           CucsAdaptorFcPortStatsEntry
    MAX-ACCESS       not-accessible
    STATUS           current
    DESCRIPTION
        "Entry for the cucsAdaptorFcPortStatsTable table."
    INDEX { cucsAdaptorFcPortStatsInstanceId }
    ::= { cucsAdaptorFcPortStatsTable 1 }

CucsAdaptorFcPortStatsEntry ::= SEQUENCE {
    cucsAdaptorFcPortStatsInstanceId                                 CucsManagedObjectId,
    cucsAdaptorFcPortStatsDn                                         CucsManagedObjectDn,
    cucsAdaptorFcPortStatsRn                                         SnmpAdminString,
    cucsAdaptorFcPortStatsIntervals                                  Gauge32,
    cucsAdaptorFcPortStatsRxBadFrames                                Unsigned64,
    cucsAdaptorFcPortStatsRxBadFramesDelta                           Counter64,
    cucsAdaptorFcPortStatsRxBadFramesDeltaAvg                        Unsigned64,
    cucsAdaptorFcPortStatsRxBadFramesDeltaMax                        Unsigned64,
    cucsAdaptorFcPortStatsRxBadFramesDeltaMin                        Unsigned64,
    cucsAdaptorFcPortStatsRxFrames                                   Unsigned64,
    cucsAdaptorFcPortStatsRxFramesDelta                              Counter64,
    cucsAdaptorFcPortStatsRxFramesDeltaAvg                           Unsigned64,
    cucsAdaptorFcPortStatsRxFramesDeltaMax                           Unsigned64,
    cucsAdaptorFcPortStatsRxFramesDeltaMin                           Unsigned64,
    cucsAdaptorFcPortStatsSuspect                                    TruthValue,
    cucsAdaptorFcPortStatsThresholded                                CucsAdaptorFcPortStatsThresholded,
    cucsAdaptorFcPortStatsTimeCollected                              DateAndTime,
    cucsAdaptorFcPortStatsTxBadFrames                                Unsigned64,
    cucsAdaptorFcPortStatsTxBadFramesDelta                           Counter64,
    cucsAdaptorFcPortStatsTxBadFramesDeltaAvg                        Unsigned64,
    cucsAdaptorFcPortStatsTxBadFramesDeltaMax                        Unsigned64,
    cucsAdaptorFcPortStatsTxBadFramesDeltaMin                        Unsigned64,
    cucsAdaptorFcPortStatsTxFrames                                   Unsigned64,
    cucsAdaptorFcPortStatsTxFramesDelta                              Counter64,
    cucsAdaptorFcPortStatsTxFramesDeltaAvg                           Unsigned64,
    cucsAdaptorFcPortStatsTxFramesDeltaMax                           Unsigned64,
    cucsAdaptorFcPortStatsTxFramesDeltaMin                           Unsigned64,
    cucsAdaptorFcPortStatsUpdate                                     Gauge32
}

cucsAdaptorFcPortStatsInstanceId OBJECT-TYPE
    SYNTAX       CucsManagedObjectId
    MAX-ACCESS   not-accessible
    STATUS       current
    DESCRIPTION
        "Instance identifier of the managed object."
    ::= { cucsAdaptorFcPortStatsEntry 1 }

cucsAdaptorFcPortStatsDn OBJECT-TYPE
    SYNTAX       CucsManagedObjectDn
    MAX-ACCESS   read-only
    STATUS       current
    DESCRIPTION
        "Cisco UCS adaptor:FcPortStats:dn managed object property"
    ::= { cucsAdaptorFcPortStatsEntry 2 }

cucsAdaptorFcPortStatsRn OBJECT-TYPE
    SYNTAX       SnmpAdminString
    MAX-ACCESS   read-only
    STATUS       current
    DESCRIPTION
        "Cisco UCS adaptor:FcPortStats:rn managed object property"
    ::= { cucsAdaptorFcPortStatsEntry 3 }

cucsAdaptorFcPortStatsIntervals OBJECT-TYPE
    SYNTAX       Gauge32
    MAX-ACCESS   read-only
    STATUS       current
    DESCRIPTION
        "Cisco UCS adaptor:FcPortStats:intervals managed object property"
    ::= { cucsAdaptorFcPortStatsEntry 4 }

cucsAdaptorFcPortStatsRxBadFrames OBJECT-TYPE
    SYNTAX       Unsigned64
    MAX-ACCESS   read-only
    STATUS       current
    DESCRIPTION
        "Cisco UCS adaptor:FcPortStats:rxBadFrames managed
        object property"
    ::= { cucsAdaptorFcPortStatsEntry 5 }

cucsAdaptorFcPortStatsRxBadFramesDelta OBJECT-TYPE
    SYNTAX       Counter64
    MAX-ACCESS   read-only
    STATUS       current
    DESCRIPTION
        "Cisco UCS adaptor:FcPortStats:rxBadFramesDelta
        managed object property"
    ::= { cucsAdaptorFcPortStatsEntry 6 }

cucsAdaptorFcPortStatsRxBadFramesDeltaAvg OBJECT-TYPE
    SYNTAX       Unsigned64
    MAX-ACCESS   read-only
    STATUS       current
    DESCRIPTION
        "Cisco UCS adaptor:FcPortStats:rxBadFramesDeltaAvg
        managed object property"
    ::= { cucsAdaptorFcPortStatsEntry 7 }

cucsAdaptorFcPortStatsRxBadFramesDeltaMax OBJECT-TYPE
    SYNTAX       Unsigned64
    MAX-ACCESS   read-only
    STATUS       current
    DESCRIPTION
        "Cisco UCS adaptor:FcPortStats:rxBadFramesDeltaMax
        managed object property"
    ::= { cucsAdaptorFcPortStatsEntry 8 }

cucsAdaptorFcPortStatsRxBadFramesDeltaMin OBJECT-TYPE
    SYNTAX       Unsigned64
    MAX-ACCESS   read-only
    STATUS       current
    DESCRIPTION
        "Cisco UCS adaptor:FcPortStats:rxBadFramesDeltaMin
        managed object property"
    ::= { cucsAdaptorFcPortStatsEntry 9 }

cucsAdaptorFcPortStatsRxFrames OBJECT-TYPE
    SYNTAX       Unsigned64
    MAX-ACCESS   read-only
    STATUS       current
    DESCRIPTION
        "Cisco UCS adaptor:FcPortStats:rxFrames managed object property"
    ::= { cucsAdaptorFcPortStatsEntry 10 }

cucsAdaptorFcPortStatsRxFramesDelta OBJECT-TYPE
    SYNTAX       Counter64
    MAX-ACCESS   read-only
    STATUS       current
    DESCRIPTION
        "Cisco UCS adaptor:FcPortStats:rxFramesDelta managed
        object property"
    ::= { cucsAdaptorFcPortStatsEntry 11 }

cucsAdaptorFcPortStatsRxFramesDeltaAvg OBJECT-TYPE
    SYNTAX       Unsigned64
    MAX-ACCESS   read-only
    STATUS       current
    DESCRIPTION
        "Cisco UCS adaptor:FcPortStats:rxFramesDeltaAvg
        managed object property"
    ::= { cucsAdaptorFcPortStatsEntry 12 }

cucsAdaptorFcPortStatsRxFramesDeltaMax OBJECT-TYPE
    SYNTAX       Unsigned64
    MAX-ACCESS   read-only
    STATUS       current
    DESCRIPTION
        "Cisco UCS adaptor:FcPortStats:rxFramesDeltaMax
        managed object property"
    ::= { cucsAdaptorFcPortStatsEntry 13 }

cucsAdaptorFcPortStatsRxFramesDeltaMin OBJECT-TYPE
    SYNTAX       Unsigned64
    MAX-ACCESS   read-only
    STATUS       current
    DESCRIPTION
        "Cisco UCS adaptor:FcPortStats:rxFramesDeltaMin
        managed object property"
    ::= { cucsAdaptorFcPortStatsEntry 14 }

cucsAdaptorFcPortStatsSuspect OBJECT-TYPE
    SYNTAX       TruthValue
    MAX-ACCESS   read-only
    STATUS       current
    DESCRIPTION
        "Cisco UCS adaptor:FcPortStats:suspect managed object property"
    ::= { cucsAdaptorFcPortStatsEntry 15 }

cucsAdaptorFcPortStatsThresholded OBJECT-TYPE
    SYNTAX       CucsAdaptorFcPortStatsThresholded
    MAX-ACCESS   read-only
    STATUS       current
    DESCRIPTION
        "Cisco UCS adaptor:FcPortStats:thresholded managed
        object property"
    ::= { cucsAdaptorFcPortStatsEntry 16 }

cucsAdaptorFcPortStatsTimeCollected OBJECT-TYPE
    SYNTAX       DateAndTime
    MAX-ACCESS   read-only
    STATUS       current
    DESCRIPTION
        "Cisco UCS adaptor:FcPortStats:timeCollected managed
        object property"
    ::= { cucsAdaptorFcPortStatsEntry 17 }

cucsAdaptorFcPortStatsTxBadFrames OBJECT-TYPE
    SYNTAX       Unsigned64
    MAX-ACCESS   read-only
    STATUS       current
    DESCRIPTION
        "Cisco UCS adaptor:FcPortStats:txBadFrames managed
        object property"
    ::= { cucsAdaptorFcPortStatsEntry 18 }

cucsAdaptorFcPortStatsTxBadFramesDelta OBJECT-TYPE
    SYNTAX       Counter64
    MAX-ACCESS   read-only
    STATUS       current
    DESCRIPTION
        "Cisco UCS adaptor:FcPortStats:txBadFramesDelta
        managed object property"
    ::= { cucsAdaptorFcPortStatsEntry 19 }

cucsAdaptorFcPortStatsTxBadFramesDeltaAvg OBJECT-TYPE
    SYNTAX       Unsigned64
    MAX-ACCESS   read-only
    STATUS       current
    DESCRIPTION
        "Cisco UCS adaptor:FcPortStats:txBadFramesDeltaAvg
        managed object property"
    ::= { cucsAdaptorFcPortStatsEntry 20 }

cucsAdaptorFcPortStatsTxBadFramesDeltaMax OBJECT-TYPE
    SYNTAX       Unsigned64
    MAX-ACCESS   read-only
    STATUS       current
    DESCRIPTION
        "Cisco UCS adaptor:FcPortStats:txBadFramesDeltaMax
        managed object property"
    ::= { cucsAdaptorFcPortStatsEntry 21 }

cucsAdaptorFcPortStatsTxBadFramesDeltaMin OBJECT-TYPE
    SYNTAX       Unsigned64
    MAX-ACCESS   read-only
    STATUS       current
    DESCRIPTION
        "Cisco UCS adaptor:FcPortStats:txBadFramesDeltaMin
        managed object property"
    ::= { cucsAdaptorFcPortStatsEntry 22 }

cucsAdaptorFcPortStatsTxFrames OBJECT-TYPE
    SYNTAX       Unsigned64
    MAX-ACCESS   read-only
    STATUS       current
    DESCRIPTION
        "Cisco UCS adaptor:FcPortStats:txFrames managed object property"
    ::= { cucsAdaptorFcPortStatsEntry 23 }

cucsAdaptorFcPortStatsTxFramesDelta OBJECT-TYPE
    SYNTAX       Counter64
    MAX-ACCESS   read-only
    STATUS       current
    DESCRIPTION
        "Cisco UCS adaptor:FcPortStats:txFramesDelta managed
        object property"
    ::= { cucsAdaptorFcPortStatsEntry 24 }

cucsAdaptorFcPortStatsTxFramesDeltaAvg OBJECT-TYPE
    SYNTAX       Unsigned64
    MAX-ACCESS   read-only
    STATUS       current
    DESCRIPTION
        "Cisco UCS adaptor:FcPortStats:txFramesDeltaAvg
        managed object property"
    ::= { cucsAdaptorFcPortStatsEntry 25 }

cucsAdaptorFcPortStatsTxFramesDeltaMax OBJECT-TYPE
    SYNTAX       Unsigned64
    MAX-ACCESS   read-only
    STATUS       current
    DESCRIPTION
        "Cisco UCS adaptor:FcPortStats:txFramesDeltaMax
        managed object property"
    ::= { cucsAdaptorFcPortStatsEntry 26 }

cucsAdaptorFcPortStatsTxFramesDeltaMin OBJECT-TYPE
    SYNTAX       Unsigned64
    MAX-ACCESS   read-only
    STATUS       current
    DESCRIPTION
        "Cisco UCS adaptor:FcPortStats:txFramesDeltaMin
        managed object property"
    ::= { cucsAdaptorFcPortStatsEntry 27 }

cucsAdaptorFcPortStatsUpdate OBJECT-TYPE
    SYNTAX       Gauge32
    MAX-ACCESS   read-only
    STATUS       current
    DESCRIPTION
        "Cisco UCS adaptor:FcPortStats:update managed object property"
    ::= { cucsAdaptorFcPortStatsEntry 28 }

cucsAdaptorFcPortStatsHistTable OBJECT-TYPE
    SYNTAX           SEQUENCE OF CucsAdaptorFcPortStatsHistEntry
    MAX-ACCESS       not-accessible
    STATUS           current
    DESCRIPTION
        "Cisco UCS adaptor:FcPortStatsHist managed object table"
    ::= { cucsAdaptorObjects 40 }

cucsAdaptorFcPortStatsHistEntry OBJECT-TYPE
    SYNTAX           CucsAdaptorFcPortStatsHistEntry
    MAX-ACCESS       not-accessible
    STATUS           current
    DESCRIPTION
        "Entry for the cucsAdaptorFcPortStatsHistTable table."
    INDEX { cucsAdaptorFcPortStatsHistInstanceId }
    ::= { cucsAdaptorFcPortStatsHistTable 1 }

CucsAdaptorFcPortStatsHistEntry ::= SEQUENCE {
    cucsAdaptorFcPortStatsHistInstanceId                             CucsManagedObjectId,
    cucsAdaptorFcPortStatsHistDn                                     CucsManagedObjectDn,
    cucsAdaptorFcPortStatsHistRn                                     SnmpAdminString,
    cucsAdaptorFcPortStatsHistId                                     Unsigned64,
    cucsAdaptorFcPortStatsHistMostRecent                             TruthValue,
    cucsAdaptorFcPortStatsHistRxBadFrames                            Unsigned64,
    cucsAdaptorFcPortStatsHistRxBadFramesDelta                       Unsigned64,
    cucsAdaptorFcPortStatsHistRxBadFramesDeltaAvg                    Unsigned64,
    cucsAdaptorFcPortStatsHistRxBadFramesDeltaMax                    Unsigned64,
    cucsAdaptorFcPortStatsHistRxBadFramesDeltaMin                    Unsigned64,
    cucsAdaptorFcPortStatsHistRxFrames                               Unsigned64,
    cucsAdaptorFcPortStatsHistRxFramesDelta                          Unsigned64,
    cucsAdaptorFcPortStatsHistRxFramesDeltaAvg                       Unsigned64,
    cucsAdaptorFcPortStatsHistRxFramesDeltaMax                       Unsigned64,
    cucsAdaptorFcPortStatsHistRxFramesDeltaMin                       Unsigned64,
    cucsAdaptorFcPortStatsHistSuspect                                TruthValue,
    cucsAdaptorFcPortStatsHistThresholded                            CucsAdaptorFcPortStatsHistThresholded,
    cucsAdaptorFcPortStatsHistTimeCollected                          DateAndTime,
    cucsAdaptorFcPortStatsHistTxBadFrames                            Unsigned64,
    cucsAdaptorFcPortStatsHistTxBadFramesDelta                       Unsigned64,
    cucsAdaptorFcPortStatsHistTxBadFramesDeltaAvg                    Unsigned64,
    cucsAdaptorFcPortStatsHistTxBadFramesDeltaMax                    Unsigned64,
    cucsAdaptorFcPortStatsHistTxBadFramesDeltaMin                    Unsigned64,
    cucsAdaptorFcPortStatsHistTxFrames                               Unsigned64,
    cucsAdaptorFcPortStatsHistTxFramesDelta                          Unsigned64,
    cucsAdaptorFcPortStatsHistTxFramesDeltaAvg                       Unsigned64,
    cucsAdaptorFcPortStatsHistTxFramesDeltaMax                       Unsigned64,
    cucsAdaptorFcPortStatsHistTxFramesDeltaMin                       Unsigned64
}

cucsAdaptorFcPortStatsHistInstanceId OBJECT-TYPE
    SYNTAX       CucsManagedObjectId
    MAX-ACCESS   not-accessible
    STATUS       current
    DESCRIPTION
        "Instance identifier of the managed object."
    ::= { cucsAdaptorFcPortStatsHistEntry 1 }

cucsAdaptorFcPortStatsHistDn OBJECT-TYPE
    SYNTAX       CucsManagedObjectDn
    MAX-ACCESS   read-only
    STATUS       current
    DESCRIPTION
        "Cisco UCS adaptor:FcPortStatsHist:dn managed object property"
    ::= { cucsAdaptorFcPortStatsHistEntry 2 }

cucsAdaptorFcPortStatsHistRn OBJECT-TYPE
    SYNTAX       SnmpAdminString
    MAX-ACCESS   read-only
    STATUS       current
    DESCRIPTION
        "Cisco UCS adaptor:FcPortStatsHist:rn managed object property"
    ::= { cucsAdaptorFcPortStatsHistEntry 3 }

cucsAdaptorFcPortStatsHistId OBJECT-TYPE
    SYNTAX       Unsigned64
    MAX-ACCESS   read-only
    STATUS       current
    DESCRIPTION
        "Cisco UCS adaptor:FcPortStatsHist:id managed object property"
    ::= { cucsAdaptorFcPortStatsHistEntry 4 }

cucsAdaptorFcPortStatsHistMostRecent OBJECT-TYPE
    SYNTAX       TruthValue
    MAX-ACCESS   read-only
    STATUS       current
    DESCRIPTION
        "Cisco UCS adaptor:FcPortStatsHist:mostRecent managed
        object property"
    ::= { cucsAdaptorFcPortStatsHistEntry 5 }

cucsAdaptorFcPortStatsHistRxBadFrames OBJECT-TYPE
    SYNTAX       Unsigned64
    MAX-ACCESS   read-only
    STATUS       current
    DESCRIPTION
        "Cisco UCS adaptor:FcPortStatsHist:rxBadFrames
        managed object property"
    ::= { cucsAdaptorFcPortStatsHistEntry 6 }

cucsAdaptorFcPortStatsHistRxBadFramesDelta OBJECT-TYPE
    SYNTAX       Unsigned64
    MAX-ACCESS   read-only
    STATUS       current
    DESCRIPTION
        "Cisco UCS adaptor:FcPortStatsHist:rxBadFramesDelta
        managed object property"
    ::= { cucsAdaptorFcPortStatsHistEntry 7 }

cucsAdaptorFcPortStatsHistRxBadFramesDeltaAvg OBJECT-TYPE
    SYNTAX       Unsigned64
    MAX-ACCESS   read-only
    STATUS       current
    DESCRIPTION
        "Cisco UCS adaptor:FcPortStatsHist:rxBadFramesDeltaAvg
        managed object property"
    ::= { cucsAdaptorFcPortStatsHistEntry 8 }

cucsAdaptorFcPortStatsHistRxBadFramesDeltaMax OBJECT-TYPE
    SYNTAX       Unsigned64
    MAX-ACCESS   read-only
    STATUS       current
    DESCRIPTION
        "Cisco UCS adaptor:FcPortStatsHist:rxBadFramesDeltaMax
        managed object property"
    ::= { cucsAdaptorFcPortStatsHistEntry 9 }

cucsAdaptorFcPortStatsHistRxBadFramesDeltaMin OBJECT-TYPE
    SYNTAX       Unsigned64
    MAX-ACCESS   read-only
    STATUS       current
    DESCRIPTION
        "Cisco UCS adaptor:FcPortStatsHist:rxBadFramesDeltaMin
        managed object property"
    ::= { cucsAdaptorFcPortStatsHistEntry 10 }

cucsAdaptorFcPortStatsHistRxFrames OBJECT-TYPE
    SYNTAX       Unsigned64
    MAX-ACCESS   read-only
    STATUS       current
    DESCRIPTION
        "Cisco UCS adaptor:FcPortStatsHist:rxFrames managed
        object property"
    ::= { cucsAdaptorFcPortStatsHistEntry 11 }

cucsAdaptorFcPortStatsHistRxFramesDelta OBJECT-TYPE
    SYNTAX       Unsigned64
    MAX-ACCESS   read-only
    STATUS       current
    DESCRIPTION
        "Cisco UCS adaptor:FcPortStatsHist:rxFramesDelta
        managed object property"
    ::= { cucsAdaptorFcPortStatsHistEntry 12 }

cucsAdaptorFcPortStatsHistRxFramesDeltaAvg OBJECT-TYPE
    SYNTAX       Unsigned64
    MAX-ACCESS   read-only
    STATUS       current
    DESCRIPTION
        "Cisco UCS adaptor:FcPortStatsHist:rxFramesDeltaAvg
        managed object property"
    ::= { cucsAdaptorFcPortStatsHistEntry 13 }

cucsAdaptorFcPortStatsHistRxFramesDeltaMax OBJECT-TYPE
    SYNTAX       Unsigned64
    MAX-ACCESS   read-only
    STATUS       current
    DESCRIPTION
        "Cisco UCS adaptor:FcPortStatsHist:rxFramesDeltaMax
        managed object property"
    ::= { cucsAdaptorFcPortStatsHistEntry 14 }

cucsAdaptorFcPortStatsHistRxFramesDeltaMin OBJECT-TYPE
    SYNTAX       Unsigned64
    MAX-ACCESS   read-only
    STATUS       current
    DESCRIPTION
        "Cisco UCS adaptor:FcPortStatsHist:rxFramesDeltaMin
        managed object property"
    ::= { cucsAdaptorFcPortStatsHistEntry 15 }

cucsAdaptorFcPortStatsHistSuspect OBJECT-TYPE
    SYNTAX       TruthValue
    MAX-ACCESS   read-only
    STATUS       current
    DESCRIPTION
        "Cisco UCS adaptor:FcPortStatsHist:suspect managed
        object property"
    ::= { cucsAdaptorFcPortStatsHistEntry 16 }

cucsAdaptorFcPortStatsHistThresholded OBJECT-TYPE
    SYNTAX       CucsAdaptorFcPortStatsHistThresholded
    MAX-ACCESS   read-only
    STATUS       current
    DESCRIPTION
        "Cisco UCS adaptor:FcPortStatsHist:thresholded
        managed object property"
    ::= { cucsAdaptorFcPortStatsHistEntry 17 }

cucsAdaptorFcPortStatsHistTimeCollected OBJECT-TYPE
    SYNTAX       DateAndTime
    MAX-ACCESS   read-only
    STATUS       current
    DESCRIPTION
        "Cisco UCS adaptor:FcPortStatsHist:timeCollected
        managed object property"
    ::= { cucsAdaptorFcPortStatsHistEntry 18 }

cucsAdaptorFcPortStatsHistTxBadFrames OBJECT-TYPE
    SYNTAX       Unsigned64
    MAX-ACCESS   read-only
    STATUS       current
    DESCRIPTION
        "Cisco UCS adaptor:FcPortStatsHist:txBadFrames
        managed object property"
    ::= { cucsAdaptorFcPortStatsHistEntry 19 }

cucsAdaptorFcPortStatsHistTxBadFramesDelta OBJECT-TYPE
    SYNTAX       Unsigned64
    MAX-ACCESS   read-only
    STATUS       current
    DESCRIPTION
        "Cisco UCS adaptor:FcPortStatsHist:txBadFramesDelta
        managed object property"
    ::= { cucsAdaptorFcPortStatsHistEntry 20 }

cucsAdaptorFcPortStatsHistTxBadFramesDeltaAvg OBJECT-TYPE
    SYNTAX       Unsigned64
    MAX-ACCESS   read-only
    STATUS       current
    DESCRIPTION
        "Cisco UCS adaptor:FcPortStatsHist:txBadFramesDeltaAvg
        managed object property"
    ::= { cucsAdaptorFcPortStatsHistEntry 21 }

cucsAdaptorFcPortStatsHistTxBadFramesDeltaMax OBJECT-TYPE
    SYNTAX       Unsigned64
    MAX-ACCESS   read-only
    STATUS       current
    DESCRIPTION
        "Cisco UCS adaptor:FcPortStatsHist:txBadFramesDeltaMax
        managed object property"
    ::= { cucsAdaptorFcPortStatsHistEntry 22 }

cucsAdaptorFcPortStatsHistTxBadFramesDeltaMin OBJECT-TYPE
    SYNTAX       Unsigned64
    MAX-ACCESS   read-only
    STATUS       current
    DESCRIPTION
        "Cisco UCS adaptor:FcPortStatsHist:txBadFramesDeltaMin
        managed object property"
    ::= { cucsAdaptorFcPortStatsHistEntry 23 }

cucsAdaptorFcPortStatsHistTxFrames OBJECT-TYPE
    SYNTAX       Unsigned64
    MAX-ACCESS   read-only
    STATUS       current
    DESCRIPTION
        "Cisco UCS adaptor:FcPortStatsHist:txFrames managed
        object property"
    ::= { cucsAdaptorFcPortStatsHistEntry 24 }

cucsAdaptorFcPortStatsHistTxFramesDelta OBJECT-TYPE
    SYNTAX       Unsigned64
    MAX-ACCESS   read-only
    STATUS       current
    DESCRIPTION
        "Cisco UCS adaptor:FcPortStatsHist:txFramesDelta
        managed object property"
    ::= { cucsAdaptorFcPortStatsHistEntry 25 }

cucsAdaptorFcPortStatsHistTxFramesDeltaAvg OBJECT-TYPE
    SYNTAX       Unsigned64
    MAX-ACCESS   read-only
    STATUS       current
    DESCRIPTION
        "Cisco UCS adaptor:FcPortStatsHist:txFramesDeltaAvg
        managed object property"
    ::= { cucsAdaptorFcPortStatsHistEntry 26 }

cucsAdaptorFcPortStatsHistTxFramesDeltaMax OBJECT-TYPE
    SYNTAX       Unsigned64
    MAX-ACCESS   read-only
    STATUS       current
    DESCRIPTION
        "Cisco UCS adaptor:FcPortStatsHist:txFramesDeltaMax
        managed object property"
    ::= { cucsAdaptorFcPortStatsHistEntry 27 }

cucsAdaptorFcPortStatsHistTxFramesDeltaMin OBJECT-TYPE
    SYNTAX       Unsigned64
    MAX-ACCESS   read-only
    STATUS       current
    DESCRIPTION
        "Cisco UCS adaptor:FcPortStatsHist:txFramesDeltaMin
        managed object property"
    ::= { cucsAdaptorFcPortStatsHistEntry 28 }

cucsAdaptorFcRecvQueueProfileTable OBJECT-TYPE
    SYNTAX           SEQUENCE OF CucsAdaptorFcRecvQueueProfileEntry
    MAX-ACCESS       not-accessible
    STATUS           current
    DESCRIPTION
        "Cisco UCS adaptor:FcRecvQueueProfile managed object table"
    ::= { cucsAdaptorObjects 41 }

cucsAdaptorFcRecvQueueProfileEntry OBJECT-TYPE
    SYNTAX           CucsAdaptorFcRecvQueueProfileEntry
    MAX-ACCESS       not-accessible
    STATUS           current
    DESCRIPTION
        "Entry for the cucsAdaptorFcRecvQueueProfileTable table."
    INDEX { cucsAdaptorFcRecvQueueProfileInstanceId }
    ::= { cucsAdaptorFcRecvQueueProfileTable 1 }

CucsAdaptorFcRecvQueueProfileEntry ::= SEQUENCE {
    cucsAdaptorFcRecvQueueProfileInstanceId                          CucsManagedObjectId,
    cucsAdaptorFcRecvQueueProfileDn                                  CucsManagedObjectDn,
    cucsAdaptorFcRecvQueueProfileRn                                  SnmpAdminString,
    cucsAdaptorFcRecvQueueProfileCount                               Gauge32,
    cucsAdaptorFcRecvQueueProfileRingSize                            Gauge32
}

cucsAdaptorFcRecvQueueProfileInstanceId OBJECT-TYPE
    SYNTAX       CucsManagedObjectId
    MAX-ACCESS   not-accessible
    STATUS       current
    DESCRIPTION
        "Instance identifier of the managed object."
    ::= { cucsAdaptorFcRecvQueueProfileEntry 1 }

cucsAdaptorFcRecvQueueProfileDn OBJECT-TYPE
    SYNTAX       CucsManagedObjectDn
    MAX-ACCESS   read-only
    STATUS       current
    DESCRIPTION
        "Cisco UCS adaptor:FcRecvQueueProfile:dn managed object property"
    ::= { cucsAdaptorFcRecvQueueProfileEntry 2 }

cucsAdaptorFcRecvQueueProfileRn OBJECT-TYPE
    SYNTAX       SnmpAdminString
    MAX-ACCESS   read-only
    STATUS       current
    DESCRIPTION
        "Cisco UCS adaptor:FcRecvQueueProfile:rn managed object property"
    ::= { cucsAdaptorFcRecvQueueProfileEntry 3 }

cucsAdaptorFcRecvQueueProfileCount OBJECT-TYPE
    SYNTAX       Gauge32
    MAX-ACCESS   read-only
    STATUS       current
    DESCRIPTION
        "Cisco UCS adaptor:FcRecvQueueProfile:count managed
        object property"
    ::= { cucsAdaptorFcRecvQueueProfileEntry 4 }

cucsAdaptorFcRecvQueueProfileRingSize OBJECT-TYPE
    SYNTAX       Gauge32
    MAX-ACCESS   read-only
    STATUS       current
    DESCRIPTION
        "Cisco UCS adaptor:FcRecvQueueProfile:ringSize
        managed object property"
    ::= { cucsAdaptorFcRecvQueueProfileEntry 5 }

cucsAdaptorFcWorkQueueProfileTable OBJECT-TYPE
    SYNTAX           SEQUENCE OF CucsAdaptorFcWorkQueueProfileEntry
    MAX-ACCESS       not-accessible
    STATUS           current
    DESCRIPTION
        "Cisco UCS adaptor:FcWorkQueueProfile managed object table"
    ::= { cucsAdaptorObjects 42 }

cucsAdaptorFcWorkQueueProfileEntry OBJECT-TYPE
    SYNTAX           CucsAdaptorFcWorkQueueProfileEntry
    MAX-ACCESS       not-accessible
    STATUS           current
    DESCRIPTION
        "Entry for the cucsAdaptorFcWorkQueueProfileTable table."
    INDEX { cucsAdaptorFcWorkQueueProfileInstanceId }
    ::= { cucsAdaptorFcWorkQueueProfileTable 1 }

CucsAdaptorFcWorkQueueProfileEntry ::= SEQUENCE {
    cucsAdaptorFcWorkQueueProfileInstanceId                          CucsManagedObjectId,
    cucsAdaptorFcWorkQueueProfileDn                                  CucsManagedObjectDn,
    cucsAdaptorFcWorkQueueProfileRn                                  SnmpAdminString,
    cucsAdaptorFcWorkQueueProfileCount                               Gauge32,
    cucsAdaptorFcWorkQueueProfileRingSize                            Gauge32
}

cucsAdaptorFcWorkQueueProfileInstanceId OBJECT-TYPE
    SYNTAX       CucsManagedObjectId
    MAX-ACCESS   not-accessible
    STATUS       current
    DESCRIPTION
        "Instance identifier of the managed object."
    ::= { cucsAdaptorFcWorkQueueProfileEntry 1 }

cucsAdaptorFcWorkQueueProfileDn OBJECT-TYPE
    SYNTAX       CucsManagedObjectDn
    MAX-ACCESS   read-only
    STATUS       current
    DESCRIPTION
        "Cisco UCS adaptor:FcWorkQueueProfile:dn managed object property"
    ::= { cucsAdaptorFcWorkQueueProfileEntry 2 }

cucsAdaptorFcWorkQueueProfileRn OBJECT-TYPE
    SYNTAX       SnmpAdminString
    MAX-ACCESS   read-only
    STATUS       current
    DESCRIPTION
        "Cisco UCS adaptor:FcWorkQueueProfile:rn managed object property"
    ::= { cucsAdaptorFcWorkQueueProfileEntry 3 }

cucsAdaptorFcWorkQueueProfileCount OBJECT-TYPE
    SYNTAX       Gauge32
    MAX-ACCESS   read-only
    STATUS       current
    DESCRIPTION
        "Cisco UCS adaptor:FcWorkQueueProfile:count managed
        object property"
    ::= { cucsAdaptorFcWorkQueueProfileEntry 4 }

cucsAdaptorFcWorkQueueProfileRingSize OBJECT-TYPE
    SYNTAX       Gauge32
    MAX-ACCESS   read-only
    STATUS       current
    DESCRIPTION
        "Cisco UCS adaptor:FcWorkQueueProfile:ringSize
        managed object property"
    ::= { cucsAdaptorFcWorkQueueProfileEntry 5 }

cucsAdaptorFruCapProviderTable OBJECT-TYPE
    SYNTAX           SEQUENCE OF CucsAdaptorFruCapProviderEntry
    MAX-ACCESS       not-accessible
    STATUS           current
    DESCRIPTION
        "Cisco UCS adaptor:FruCapProvider managed object table"
    ::= { cucsAdaptorObjects 43 }

cucsAdaptorFruCapProviderEntry OBJECT-TYPE
    SYNTAX           CucsAdaptorFruCapProviderEntry
    MAX-ACCESS       not-accessible
    STATUS           current
    DESCRIPTION
        "Entry for the cucsAdaptorFruCapProviderTable table."
    INDEX { cucsAdaptorFruCapProviderInstanceId }
    ::= { cucsAdaptorFruCapProviderTable 1 }

CucsAdaptorFruCapProviderEntry ::= SEQUENCE {
    cucsAdaptorFruCapProviderInstanceId                              CucsManagedObjectId,
    cucsAdaptorFruCapProviderDn                                      CucsManagedObjectDn,
    cucsAdaptorFruCapProviderRn                                      SnmpAdminString,
    cucsAdaptorFruCapProviderDeprecated                              TruthValue,
    cucsAdaptorFruCapProviderGencount                                Gauge32,
    cucsAdaptorFruCapProviderMgmtPlaneVer                            SnmpAdminString,
    cucsAdaptorFruCapProviderModel                                   SnmpAdminString,
    cucsAdaptorFruCapProviderRevision                                SnmpAdminString,
    cucsAdaptorFruCapProviderVendor                                  SnmpAdminString,
    cucsAdaptorFruCapProviderPromCardType                            Gauge32,
    cucsAdaptorFruCapProviderDeleted                                 TruthValue,
    cucsAdaptorFruCapProviderElementLoadFailures                     Gauge32,
    cucsAdaptorFruCapProviderElementsLoaded                          Gauge32,
    cucsAdaptorFruCapProviderLoadErrors                              Gauge32,
    cucsAdaptorFruCapProviderLoadWarnings                            Gauge32
}

cucsAdaptorFruCapProviderInstanceId OBJECT-TYPE
    SYNTAX       CucsManagedObjectId
    MAX-ACCESS   not-accessible
    STATUS       current
    DESCRIPTION
        "Instance identifier of the managed object."
    ::= { cucsAdaptorFruCapProviderEntry 1 }

cucsAdaptorFruCapProviderDn OBJECT-TYPE
    SYNTAX       CucsManagedObjectDn
    MAX-ACCESS   read-only
    STATUS       current
    DESCRIPTION
        "Cisco UCS adaptor:FruCapProvider:dn managed object property"
    ::= { cucsAdaptorFruCapProviderEntry 2 }

cucsAdaptorFruCapProviderRn OBJECT-TYPE
    SYNTAX       SnmpAdminString
    MAX-ACCESS   read-only
    STATUS       current
    DESCRIPTION
        "Cisco UCS adaptor:FruCapProvider:rn managed object property"
    ::= { cucsAdaptorFruCapProviderEntry 3 }

cucsAdaptorFruCapProviderDeprecated OBJECT-TYPE
    SYNTAX       TruthValue
    MAX-ACCESS   read-only
    STATUS       current
    DESCRIPTION
        "Cisco UCS adaptor:FruCapProvider:deprecated managed
        object property"
    ::= { cucsAdaptorFruCapProviderEntry 4 }

cucsAdaptorFruCapProviderGencount OBJECT-TYPE
    SYNTAX       Gauge32
    MAX-ACCESS   read-only
    STATUS       current
    DESCRIPTION
        "Cisco UCS adaptor:FruCapProvider:gencount managed
        object property"
    ::= { cucsAdaptorFruCapProviderEntry 5 }

cucsAdaptorFruCapProviderMgmtPlaneVer OBJECT-TYPE
    SYNTAX       SnmpAdminString
    MAX-ACCESS   read-only
    STATUS       current
    DESCRIPTION
        "Cisco UCS adaptor:FruCapProvider:mgmtPlaneVer
        managed object property"
    ::= { cucsAdaptorFruCapProviderEntry 6 }

cucsAdaptorFruCapProviderModel OBJECT-TYPE
    SYNTAX       SnmpAdminString
    MAX-ACCESS   read-only
    STATUS       current
    DESCRIPTION
        "Cisco UCS adaptor:FruCapProvider:model managed object property"
    ::= { cucsAdaptorFruCapProviderEntry 7 }

cucsAdaptorFruCapProviderRevision OBJECT-TYPE
    SYNTAX       SnmpAdminString
    MAX-ACCESS   read-only
    STATUS       current
    DESCRIPTION
        "Cisco UCS adaptor:FruCapProvider:revision managed
        object property"
    ::= { cucsAdaptorFruCapProviderEntry 8 }

cucsAdaptorFruCapProviderVendor OBJECT-TYPE
    SYNTAX       SnmpAdminString
    MAX-ACCESS   read-only
    STATUS       current
    DESCRIPTION
        "Cisco UCS adaptor:FruCapProvider:vendor managed object property"
    ::= { cucsAdaptorFruCapProviderEntry 9 }

cucsAdaptorFruCapProviderPromCardType OBJECT-TYPE
    SYNTAX       Gauge32
    MAX-ACCESS   read-only
    STATUS       current
    DESCRIPTION
        "Cisco UCS adaptor:FruCapProvider:promCardType
        managed object property"
    ::= { cucsAdaptorFruCapProviderEntry 10 }

cucsAdaptorFruCapProviderDeleted OBJECT-TYPE
    SYNTAX       TruthValue
    MAX-ACCESS   read-only
    STATUS       current
    DESCRIPTION
        "Cisco UCS adaptor:FruCapProvider:deleted managed object property"
    ::= { cucsAdaptorFruCapProviderEntry 11 }

cucsAdaptorFruCapProviderElementLoadFailures OBJECT-TYPE
    SYNTAX       Gauge32
    MAX-ACCESS   read-only
    STATUS       current
    DESCRIPTION
        "Cisco UCS adaptor:FruCapProvider:elementLoadFailures
        managed object property"
    ::= { cucsAdaptorFruCapProviderEntry 12 }

cucsAdaptorFruCapProviderElementsLoaded OBJECT-TYPE
    SYNTAX       Gauge32
    MAX-ACCESS   read-only
    STATUS       current
    DESCRIPTION
        "Cisco UCS adaptor:FruCapProvider:elementsLoaded
        managed object property"
    ::= { cucsAdaptorFruCapProviderEntry 13 }

cucsAdaptorFruCapProviderLoadErrors OBJECT-TYPE
    SYNTAX       Gauge32
    MAX-ACCESS   read-only
    STATUS       current
    DESCRIPTION
        "Cisco UCS adaptor:FruCapProvider:loadErrors managed
        object property"
    ::= { cucsAdaptorFruCapProviderEntry 14 }

cucsAdaptorFruCapProviderLoadWarnings OBJECT-TYPE
    SYNTAX       Gauge32
    MAX-ACCESS   read-only
    STATUS       current
    DESCRIPTION
        "Cisco UCS adaptor:FruCapProvider:loadWarnings
        managed object property"
    ::= { cucsAdaptorFruCapProviderEntry 15 }

cucsAdaptorFruCapRefTable OBJECT-TYPE
    SYNTAX           SEQUENCE OF CucsAdaptorFruCapRefEntry
    MAX-ACCESS       not-accessible
    STATUS           current
    DESCRIPTION
        "Cisco UCS adaptor:FruCapRef managed object table"
    ::= { cucsAdaptorObjects 95 }

cucsAdaptorFruCapRefEntry OBJECT-TYPE
    SYNTAX           CucsAdaptorFruCapRefEntry
    MAX-ACCESS       not-accessible
    STATUS           current
    DESCRIPTION
        "Entry for the cucsAdaptorFruCapRefTable table."
    INDEX { cucsAdaptorFruCapRefInstanceId }
    ::= { cucsAdaptorFruCapRefTable 1 }

CucsAdaptorFruCapRefEntry ::= SEQUENCE {
    cucsAdaptorFruCapRefInstanceId                                   CucsManagedObjectId,
    cucsAdaptorFruCapRefDn                                           CucsManagedObjectDn,
    cucsAdaptorFruCapRefRn                                           SnmpAdminString,
    cucsAdaptorFruCapRefIsSupported                                  CucsAdaptorDefaultAction,
    cucsAdaptorFruCapRefModel                                        SnmpAdminString,
    cucsAdaptorFruCapRefRevision                                     SnmpAdminString,
    cucsAdaptorFruCapRefVendor                                       SnmpAdminString
}

cucsAdaptorFruCapRefInstanceId OBJECT-TYPE
    SYNTAX       CucsManagedObjectId
    MAX-ACCESS   not-accessible
    STATUS       current
    DESCRIPTION
        "Instance identifier of the managed object."
    ::= { cucsAdaptorFruCapRefEntry 1 }

cucsAdaptorFruCapRefDn OBJECT-TYPE
    SYNTAX       CucsManagedObjectDn
    MAX-ACCESS   read-only
    STATUS       current
    DESCRIPTION
        "Cisco UCS adaptor:FruCapRef:dn managed object property"
    ::= { cucsAdaptorFruCapRefEntry 2 }

cucsAdaptorFruCapRefRn OBJECT-TYPE
    SYNTAX       SnmpAdminString
    MAX-ACCESS   read-only
    STATUS       current
    DESCRIPTION
        "Cisco UCS adaptor:FruCapRef:rn managed object property"
    ::= { cucsAdaptorFruCapRefEntry 3 }

cucsAdaptorFruCapRefIsSupported OBJECT-TYPE
    SYNTAX       CucsAdaptorDefaultAction
    MAX-ACCESS   read-only
    STATUS       current
    DESCRIPTION
        "Cisco UCS adaptor:FruCapRef:isSupported managed object property"
    ::= { cucsAdaptorFruCapRefEntry 4 }

cucsAdaptorFruCapRefModel OBJECT-TYPE
    SYNTAX       SnmpAdminString
    MAX-ACCESS   read-only
    STATUS       current
    DESCRIPTION
        "Cisco UCS adaptor:FruCapRef:model managed object property"
    ::= { cucsAdaptorFruCapRefEntry 5 }

cucsAdaptorFruCapRefRevision OBJECT-TYPE
    SYNTAX       SnmpAdminString
    MAX-ACCESS   read-only
    STATUS       current
    DESCRIPTION
        "Cisco UCS adaptor:FruCapRef:revision managed object property"
    ::= { cucsAdaptorFruCapRefEntry 6 }

cucsAdaptorFruCapRefVendor OBJECT-TYPE
    SYNTAX       SnmpAdminString
    MAX-ACCESS   read-only
    STATUS       current
    DESCRIPTION
        "Cisco UCS adaptor:FruCapRef:vendor managed object property"
    ::= { cucsAdaptorFruCapRefEntry 7 }

cucsAdaptorFwCapProviderTable OBJECT-TYPE
    SYNTAX           SEQUENCE OF CucsAdaptorFwCapProviderEntry
    MAX-ACCESS       not-accessible
    STATUS           current
    DESCRIPTION
        "Cisco UCS adaptor:FwCapProvider managed object table"
    ::= { cucsAdaptorObjects 44 }

cucsAdaptorFwCapProviderEntry OBJECT-TYPE
    SYNTAX           CucsAdaptorFwCapProviderEntry
    MAX-ACCESS       not-accessible
    STATUS           current
    DESCRIPTION
        "Entry for the cucsAdaptorFwCapProviderTable table."
    INDEX { cucsAdaptorFwCapProviderInstanceId }
    ::= { cucsAdaptorFwCapProviderTable 1 }

CucsAdaptorFwCapProviderEntry ::= SEQUENCE {
    cucsAdaptorFwCapProviderInstanceId                               CucsManagedObjectId,
    cucsAdaptorFwCapProviderDn                                       CucsManagedObjectDn,
    cucsAdaptorFwCapProviderRn                                       SnmpAdminString,
    cucsAdaptorFwCapProviderDeprecated                               TruthValue,
    cucsAdaptorFwCapProviderGencount                                 Gauge32,
    cucsAdaptorFwCapProviderMgmtPlaneVer                             SnmpAdminString,
    cucsAdaptorFwCapProviderModel                                    SnmpAdminString,
    cucsAdaptorFwCapProviderVendor                                   SnmpAdminString,
    cucsAdaptorFwCapProviderVersion                                  SnmpAdminString,
    cucsAdaptorFwCapProviderDeleted                                  TruthValue,
    cucsAdaptorFwCapProviderElementLoadFailures                      Gauge32,
    cucsAdaptorFwCapProviderElementsLoaded                           Gauge32,
    cucsAdaptorFwCapProviderLoadErrors                               Gauge32,
    cucsAdaptorFwCapProviderLoadWarnings                             Gauge32
}

cucsAdaptorFwCapProviderInstanceId OBJECT-TYPE
    SYNTAX       CucsManagedObjectId
    MAX-ACCESS   not-accessible
    STATUS       current
    DESCRIPTION
        "Instance identifier of the managed object."
    ::= { cucsAdaptorFwCapProviderEntry 1 }

cucsAdaptorFwCapProviderDn OBJECT-TYPE
    SYNTAX       CucsManagedObjectDn
    MAX-ACCESS   read-only
    STATUS       current
    DESCRIPTION
        "Cisco UCS adaptor:FwCapProvider:dn managed object property"
    ::= { cucsAdaptorFwCapProviderEntry 2 }

cucsAdaptorFwCapProviderRn OBJECT-TYPE
    SYNTAX       SnmpAdminString
    MAX-ACCESS   read-only
    STATUS       current
    DESCRIPTION
        "Cisco UCS adaptor:FwCapProvider:rn managed object property"
    ::= { cucsAdaptorFwCapProviderEntry 3 }

cucsAdaptorFwCapProviderDeprecated OBJECT-TYPE
    SYNTAX       TruthValue
    MAX-ACCESS   read-only
    STATUS       current
    DESCRIPTION
        "Cisco UCS adaptor:FwCapProvider:deprecated managed
        object property"
    ::= { cucsAdaptorFwCapProviderEntry 4 }

cucsAdaptorFwCapProviderGencount OBJECT-TYPE
    SYNTAX       Gauge32
    MAX-ACCESS   read-only
    STATUS       current
    DESCRIPTION
        "Cisco UCS adaptor:FwCapProvider:gencount managed object property"
    ::= { cucsAdaptorFwCapProviderEntry 5 }

cucsAdaptorFwCapProviderMgmtPlaneVer OBJECT-TYPE
    SYNTAX       SnmpAdminString
    MAX-ACCESS   read-only
    STATUS       current
    DESCRIPTION
        "Cisco UCS adaptor:FwCapProvider:mgmtPlaneVer managed
        object property"
    ::= { cucsAdaptorFwCapProviderEntry 6 }

cucsAdaptorFwCapProviderModel OBJECT-TYPE
    SYNTAX       SnmpAdminString
    MAX-ACCESS   read-only
    STATUS       current
    DESCRIPTION
        "Cisco UCS adaptor:FwCapProvider:model managed object property"
    ::= { cucsAdaptorFwCapProviderEntry 7 }

cucsAdaptorFwCapProviderVendor OBJECT-TYPE
    SYNTAX       SnmpAdminString
    MAX-ACCESS   read-only
    STATUS       current
    DESCRIPTION
        "Cisco UCS adaptor:FwCapProvider:vendor managed object property"
    ::= { cucsAdaptorFwCapProviderEntry 8 }

cucsAdaptorFwCapProviderVersion OBJECT-TYPE
    SYNTAX       SnmpAdminString
    MAX-ACCESS   read-only
    STATUS       current
    DESCRIPTION
        "Cisco UCS adaptor:FwCapProvider:version managed object property"
    ::= { cucsAdaptorFwCapProviderEntry 9 }

cucsAdaptorFwCapProviderDeleted OBJECT-TYPE
    SYNTAX       TruthValue
    MAX-ACCESS   read-only
    STATUS       current
    DESCRIPTION
        "Cisco UCS adaptor:FwCapProvider:deleted managed object property"
    ::= { cucsAdaptorFwCapProviderEntry 10 }

cucsAdaptorFwCapProviderElementLoadFailures OBJECT-TYPE
    SYNTAX       Gauge32
    MAX-ACCESS   read-only
    STATUS       current
    DESCRIPTION
        "Cisco UCS adaptor:FwCapProvider:elementLoadFailures
        managed object property"
    ::= { cucsAdaptorFwCapProviderEntry 11 }

cucsAdaptorFwCapProviderElementsLoaded OBJECT-TYPE
    SYNTAX       Gauge32
    MAX-ACCESS   read-only
    STATUS       current
    DESCRIPTION
        "Cisco UCS adaptor:FwCapProvider:elementsLoaded
        managed object property"
    ::= { cucsAdaptorFwCapProviderEntry 12 }

cucsAdaptorFwCapProviderLoadErrors OBJECT-TYPE
    SYNTAX       Gauge32
    MAX-ACCESS   read-only
    STATUS       current
    DESCRIPTION
        "Cisco UCS adaptor:FwCapProvider:loadErrors managed
        object property"
    ::= { cucsAdaptorFwCapProviderEntry 13 }

cucsAdaptorFwCapProviderLoadWarnings OBJECT-TYPE
    SYNTAX       Gauge32
    MAX-ACCESS   read-only
    STATUS       current
    DESCRIPTION
        "Cisco UCS adaptor:FwCapProvider:loadWarnings managed
        object property"
    ::= { cucsAdaptorFwCapProviderEntry 14 }

cucsAdaptorHostEthIfTable OBJECT-TYPE
    SYNTAX           SEQUENCE OF CucsAdaptorHostEthIfEntry
    MAX-ACCESS       not-accessible
    STATUS           current
    DESCRIPTION
        "Cisco UCS adaptor:HostEthIf managed object table"
    ::= { cucsAdaptorObjects 45 }

cucsAdaptorHostEthIfEntry OBJECT-TYPE
    SYNTAX           CucsAdaptorHostEthIfEntry
    MAX-ACCESS       not-accessible
    STATUS           current
    DESCRIPTION
        "Entry for the cucsAdaptorHostEthIfTable table."
    INDEX { cucsAdaptorHostEthIfInstanceId }
    ::= { cucsAdaptorHostEthIfTable 1 }

CucsAdaptorHostEthIfEntry ::= SEQUENCE {
    cucsAdaptorHostEthIfInstanceId                                   CucsManagedObjectId,
    cucsAdaptorHostEthIfDn                                           CucsManagedObjectDn,
    cucsAdaptorHostEthIfRn                                           SnmpAdminString,
    cucsAdaptorHostEthIfAdminState                                   CucsAdaptorHostIfAdminState,
    cucsAdaptorHostEthIfBootDev                                      CucsAdaptorHostIfBootDev,
    cucsAdaptorHostEthIfChassisId                                    Gauge32,
    cucsAdaptorHostEthIfDiscovery                                    CucsEtherSatelliteConnectionDisc,
    cucsAdaptorHostEthIfEpDn                                         SnmpAdminString,
    cucsAdaptorHostEthIfFltAggr                                      Unsigned64,
    cucsAdaptorHostEthIfFsmDescr                                     SnmpAdminString,
    cucsAdaptorHostEthIfFsmPrev                                      SnmpAdminString,
    cucsAdaptorHostEthIfFsmProgr                                     Gauge32,
    cucsAdaptorHostEthIfFsmRmtInvErrCode                             Gauge32,
    cucsAdaptorHostEthIfFsmRmtInvErrDescr                            SnmpAdminString,
    cucsAdaptorHostEthIfFsmRmtInvRslt                                CucsConditionRemoteInvRslt,
    cucsAdaptorHostEthIfFsmStageDescr                                SnmpAdminString,
    cucsAdaptorHostEthIfFsmStamp                                     DateAndTime,
    cucsAdaptorHostEthIfFsmStatus                                    SnmpAdminString,
    cucsAdaptorHostEthIfFsmTry                                       Gauge32,
    cucsAdaptorHostEthIfId                                           Gauge32,
    cucsAdaptorHostEthIfIfRole                                       CucsNetworkPortRole,
    cucsAdaptorHostEthIfIfType                                       CucsNetworkPhysEpIfType,
    cucsAdaptorHostEthIfLc                                           CucsFsmLifecycle,
    cucsAdaptorHostEthIfLinkState                                    CucsAdaptorLinkState,
    cucsAdaptorHostEthIfLocale                                       CucsNetworkLocale,
    cucsAdaptorHostEthIfMac                                          MacAddress,
    cucsAdaptorHostEthIfModel                                        SnmpAdminString,
    cucsAdaptorHostEthIfMtu                                          Gauge32,
    cucsAdaptorHostEthIfName                                         SnmpAdminString,
    cucsAdaptorHostEthIfOperState                                    CucsEquipmentOperability,
    cucsAdaptorHostEthIfOperability                                  CucsEquipmentOperability,
    cucsAdaptorHostEthIfOrder                                        Gauge32,
    cucsAdaptorHostEthIfOriginalMac                                  MacAddress,
    cucsAdaptorHostEthIfPciAddr                                      SnmpAdminString,
    cucsAdaptorHostEthIfPeerDn                                       SnmpAdminString,
    cucsAdaptorHostEthIfPeerPortId                                   Gauge32,
    cucsAdaptorHostEthIfPeerSlotId                                   Gauge32,
    cucsAdaptorHostEthIfPerf                                         CucsEquipmentSensorThresholdStatus,
    cucsAdaptorHostEthIfPortId                                       Gauge32,
    cucsAdaptorHostEthIfPower                                        CucsEquipmentPowerState,
    cucsAdaptorHostEthIfPresence                                     CucsEquipmentPresence,
    cucsAdaptorHostEthIfPurpose                                      CucsAdaptorPurpose,
    cucsAdaptorHostEthIfRevision                                     SnmpAdminString,
    cucsAdaptorHostEthIfSerial                                       SnmpAdminString,
    cucsAdaptorHostEthIfSide                                         CucsNetworkSide,
    cucsAdaptorHostEthIfSlotId                                       Gauge32,
    cucsAdaptorHostEthIfSwitchId                                     CucsNetworkSwitchId,
    cucsAdaptorHostEthIfThermal                                      CucsEquipmentSensorThresholdStatus,
    cucsAdaptorHostEthIfTransport                                    CucsAdaptorHostEthIfTransport,
    cucsAdaptorHostEthIfType                                         CucsNetworkConnectionType,
    cucsAdaptorHostEthIfVendor                                       SnmpAdminString,
    cucsAdaptorHostEthIfVnicDn                                       SnmpAdminString,
    cucsAdaptorHostEthIfVoltage                                      CucsEquipmentSensorThresholdStatus,
    cucsAdaptorHostEthIfPeerChassisId                                Gauge32,
    cucsAdaptorHostEthIfPciFunc                                      Gauge32,
    cucsAdaptorHostEthIfPciSlot                                      Gauge32,
    cucsAdaptorHostEthIfOperQualifierReason                          SnmpAdminString,
    cucsAdaptorHostEthIfPfDn                                         SnmpAdminString,
    cucsAdaptorHostEthIfVirtualizationPreference                     CucsVnicVirtualizationPreferenceType,
    cucsAdaptorHostEthIfHostPort                                     CucsAdaptorHostEthIfHostPort,
    cucsAdaptorHostEthIfCdnName                                      SnmpAdminString
}

cucsAdaptorHostEthIfInstanceId OBJECT-TYPE
    SYNTAX       CucsManagedObjectId
    MAX-ACCESS   not-accessible
    STATUS       current
    DESCRIPTION
        "Instance identifier of the managed object."
    ::= { cucsAdaptorHostEthIfEntry 1 }

cucsAdaptorHostEthIfDn OBJECT-TYPE
    SYNTAX       CucsManagedObjectDn
    MAX-ACCESS   read-only
    STATUS       current
    DESCRIPTION
        "Cisco UCS adaptor:HostEthIf:dn managed object property"
    ::= { cucsAdaptorHostEthIfEntry 2 }

cucsAdaptorHostEthIfRn OBJECT-TYPE
    SYNTAX       SnmpAdminString
    MAX-ACCESS   read-only
    STATUS       current
    DESCRIPTION
        "Cisco UCS adaptor:HostEthIf:rn managed object property"
    ::= { cucsAdaptorHostEthIfEntry 3 }

cucsAdaptorHostEthIfAdminState OBJECT-TYPE
    SYNTAX       CucsAdaptorHostIfAdminState
    MAX-ACCESS   read-only
    STATUS       current
    DESCRIPTION
        "Cisco UCS adaptor:HostEthIf:adminState managed object property"
    ::= { cucsAdaptorHostEthIfEntry 4 }

cucsAdaptorHostEthIfBootDev OBJECT-TYPE
    SYNTAX       CucsAdaptorHostIfBootDev
    MAX-ACCESS   read-only
    STATUS       current
    DESCRIPTION
        "Cisco UCS adaptor:HostEthIf:bootDev managed object property"
    ::= { cucsAdaptorHostEthIfEntry 5 }

cucsAdaptorHostEthIfChassisId OBJECT-TYPE
    SYNTAX       Gauge32
    MAX-ACCESS   read-only
    STATUS       current
    DESCRIPTION
        "Cisco UCS adaptor:HostEthIf:chassisId managed object property"
    ::= { cucsAdaptorHostEthIfEntry 6 }

cucsAdaptorHostEthIfDiscovery OBJECT-TYPE
    SYNTAX       CucsEtherSatelliteConnectionDisc
    MAX-ACCESS   read-only
    STATUS       current
    DESCRIPTION
        "Cisco UCS adaptor:HostEthIf:discovery managed object property"
    ::= { cucsAdaptorHostEthIfEntry 7 }

cucsAdaptorHostEthIfEpDn OBJECT-TYPE
    SYNTAX       SnmpAdminString
    MAX-ACCESS   read-only
    STATUS       current
    DESCRIPTION
        "Cisco UCS adaptor:HostEthIf:epDn managed object property"
    ::= { cucsAdaptorHostEthIfEntry 8 }

cucsAdaptorHostEthIfFltAggr OBJECT-TYPE
    SYNTAX       Unsigned64
    MAX-ACCESS   read-only
    STATUS       current
    DESCRIPTION
        "Cisco UCS adaptor:HostEthIf:fltAggr managed object property"
    ::= { cucsAdaptorHostEthIfEntry 9 }

cucsAdaptorHostEthIfFsmDescr OBJECT-TYPE
    SYNTAX       SnmpAdminString
    MAX-ACCESS   read-only
    STATUS       current
    DESCRIPTION
        "Cisco UCS adaptor:HostEthIf:fsmDescr managed object property"
    ::= { cucsAdaptorHostEthIfEntry 10 }

cucsAdaptorHostEthIfFsmPrev OBJECT-TYPE
    SYNTAX       SnmpAdminString
    MAX-ACCESS   read-only
    STATUS       current
    DESCRIPTION
        "Cisco UCS adaptor:HostEthIf:fsmPrev managed object property"
    ::= { cucsAdaptorHostEthIfEntry 11 }

cucsAdaptorHostEthIfFsmProgr OBJECT-TYPE
    SYNTAX       Gauge32
    MAX-ACCESS   read-only
    STATUS       current
    DESCRIPTION
        "Cisco UCS adaptor:HostEthIf:fsmProgr managed object property"
    ::= { cucsAdaptorHostEthIfEntry 12 }

cucsAdaptorHostEthIfFsmRmtInvErrCode OBJECT-TYPE
    SYNTAX       Gauge32
    MAX-ACCESS   read-only
    STATUS       current
    DESCRIPTION
        "Cisco UCS adaptor:HostEthIf:fsmRmtInvErrCode managed
        object property"
    ::= { cucsAdaptorHostEthIfEntry 13 }

cucsAdaptorHostEthIfFsmRmtInvErrDescr OBJECT-TYPE
    SYNTAX       SnmpAdminString
    MAX-ACCESS   read-only
    STATUS       current
    DESCRIPTION
        "Cisco UCS adaptor:HostEthIf:fsmRmtInvErrDescr
        managed object property"
    ::= { cucsAdaptorHostEthIfEntry 14 }

cucsAdaptorHostEthIfFsmRmtInvRslt OBJECT-TYPE
    SYNTAX       CucsConditionRemoteInvRslt
    MAX-ACCESS   read-only
    STATUS       current
    DESCRIPTION
        "Cisco UCS adaptor:HostEthIf:fsmRmtInvRslt managed
        object property"
    ::= { cucsAdaptorHostEthIfEntry 15 }

cucsAdaptorHostEthIfFsmStageDescr OBJECT-TYPE
    SYNTAX       SnmpAdminString
    MAX-ACCESS   read-only
    STATUS       current
    DESCRIPTION
        "Cisco UCS adaptor:HostEthIf:fsmStageDescr managed
        object property"
    ::= { cucsAdaptorHostEthIfEntry 16 }

cucsAdaptorHostEthIfFsmStamp OBJECT-TYPE
    SYNTAX       DateAndTime
    MAX-ACCESS   read-only
    STATUS       current
    DESCRIPTION
        "Cisco UCS adaptor:HostEthIf:fsmStamp managed object property"
    ::= { cucsAdaptorHostEthIfEntry 17 }

cucsAdaptorHostEthIfFsmStatus OBJECT-TYPE
    SYNTAX       SnmpAdminString
    MAX-ACCESS   read-only
    STATUS       current
    DESCRIPTION
        "Cisco UCS adaptor:HostEthIf:fsmStatus managed object property"
    ::= { cucsAdaptorHostEthIfEntry 18 }

cucsAdaptorHostEthIfFsmTry OBJECT-TYPE
    SYNTAX       Gauge32
    MAX-ACCESS   read-only
    STATUS       current
    DESCRIPTION
        "Cisco UCS adaptor:HostEthIf:fsmTry managed object property"
    ::= { cucsAdaptorHostEthIfEntry 19 }

cucsAdaptorHostEthIfId OBJECT-TYPE
    SYNTAX       Gauge32
    MAX-ACCESS   read-only
    STATUS       current
    DESCRIPTION
        "Cisco UCS adaptor:HostEthIf:id managed object property"
    ::= { cucsAdaptorHostEthIfEntry 20 }

cucsAdaptorHostEthIfIfRole OBJECT-TYPE
    SYNTAX       CucsNetworkPortRole
    MAX-ACCESS   read-only
    STATUS       current
    DESCRIPTION
        "Cisco UCS adaptor:HostEthIf:ifRole managed object property"
    ::= { cucsAdaptorHostEthIfEntry 21 }

cucsAdaptorHostEthIfIfType OBJECT-TYPE
    SYNTAX       CucsNetworkPhysEpIfType
    MAX-ACCESS   read-only
    STATUS       current
    DESCRIPTION
        "Cisco UCS adaptor:HostEthIf:ifType managed object property"
    ::= { cucsAdaptorHostEthIfEntry 22 }

cucsAdaptorHostEthIfLc OBJECT-TYPE
    SYNTAX       CucsFsmLifecycle
    MAX-ACCESS   read-only
    STATUS       current
    DESCRIPTION
        "Cisco UCS adaptor:HostEthIf:lc managed object property"
    ::= { cucsAdaptorHostEthIfEntry 23 }

cucsAdaptorHostEthIfLinkState OBJECT-TYPE
    SYNTAX       CucsAdaptorLinkState
    MAX-ACCESS   read-only
    STATUS       current
    DESCRIPTION
        "Cisco UCS adaptor:HostEthIf:linkState managed object property"
    ::= { cucsAdaptorHostEthIfEntry 24 }

cucsAdaptorHostEthIfLocale OBJECT-TYPE
    SYNTAX       CucsNetworkLocale
    MAX-ACCESS   read-only
    STATUS       current
    DESCRIPTION
        "Cisco UCS adaptor:HostEthIf:locale managed object property"
    ::= { cucsAdaptorHostEthIfEntry 25 }

cucsAdaptorHostEthIfMac OBJECT-TYPE
    SYNTAX       MacAddress
    MAX-ACCESS   read-only
    STATUS       current
    DESCRIPTION
        "Cisco UCS adaptor:HostEthIf:mac managed object property"
    ::= { cucsAdaptorHostEthIfEntry 26 }

cucsAdaptorHostEthIfModel OBJECT-TYPE
    SYNTAX       SnmpAdminString
    MAX-ACCESS   read-only
    STATUS       current
    DESCRIPTION
        "Cisco UCS adaptor:HostEthIf:model managed object property"
    ::= { cucsAdaptorHostEthIfEntry 27 }

cucsAdaptorHostEthIfMtu OBJECT-TYPE
    SYNTAX       Gauge32
    MAX-ACCESS   read-only
    STATUS       current
    DESCRIPTION
        "Cisco UCS adaptor:HostEthIf:mtu managed object property"
    ::= { cucsAdaptorHostEthIfEntry 28 }

cucsAdaptorHostEthIfName OBJECT-TYPE
    SYNTAX       SnmpAdminString
    MAX-ACCESS   read-only
    STATUS       current
    DESCRIPTION
        "Cisco UCS adaptor:HostEthIf:name managed object property"
    ::= { cucsAdaptorHostEthIfEntry 29 }

cucsAdaptorHostEthIfOperState OBJECT-TYPE
    SYNTAX       CucsEquipmentOperability
    MAX-ACCESS   read-only
    STATUS       current
    DESCRIPTION
        "Cisco UCS adaptor:HostEthIf:operState managed object property"
    ::= { cucsAdaptorHostEthIfEntry 30 }

cucsAdaptorHostEthIfOperability OBJECT-TYPE
    SYNTAX       CucsEquipmentOperability
    MAX-ACCESS   read-only
    STATUS       current
    DESCRIPTION
        "Cisco UCS adaptor:HostEthIf:operability managed object property"
    ::= { cucsAdaptorHostEthIfEntry 31 }

cucsAdaptorHostEthIfOrder OBJECT-TYPE
    SYNTAX       Gauge32
    MAX-ACCESS   read-only
    STATUS       current
    DESCRIPTION
        "Cisco UCS adaptor:HostEthIf:order managed object property"
    ::= { cucsAdaptorHostEthIfEntry 32 }

cucsAdaptorHostEthIfOriginalMac OBJECT-TYPE
    SYNTAX       MacAddress
    MAX-ACCESS   read-only
    STATUS       current
    DESCRIPTION
        "Cisco UCS adaptor:HostEthIf:originalMac managed object property"
    ::= { cucsAdaptorHostEthIfEntry 33 }

cucsAdaptorHostEthIfPciAddr OBJECT-TYPE
    SYNTAX       SnmpAdminString
    MAX-ACCESS   read-only
    STATUS       current
    DESCRIPTION
        "Cisco UCS adaptor:HostEthIf:pciAddr managed object property"
    ::= { cucsAdaptorHostEthIfEntry 34 }

cucsAdaptorHostEthIfPeerDn OBJECT-TYPE
    SYNTAX       SnmpAdminString
    MAX-ACCESS   read-only
    STATUS       current
    DESCRIPTION
        "Cisco UCS adaptor:HostEthIf:peerDn managed object property"
    ::= { cucsAdaptorHostEthIfEntry 35 }

cucsAdaptorHostEthIfPeerPortId OBJECT-TYPE
    SYNTAX       Gauge32
    MAX-ACCESS   read-only
    STATUS       current
    DESCRIPTION
        "Cisco UCS adaptor:HostEthIf:peerPortId managed object property"
    ::= { cucsAdaptorHostEthIfEntry 36 }

cucsAdaptorHostEthIfPeerSlotId OBJECT-TYPE
    SYNTAX       Gauge32
    MAX-ACCESS   read-only
    STATUS       current
    DESCRIPTION
        "Cisco UCS adaptor:HostEthIf:peerSlotId managed object property"
    ::= { cucsAdaptorHostEthIfEntry 37 }

cucsAdaptorHostEthIfPerf OBJECT-TYPE
    SYNTAX       CucsEquipmentSensorThresholdStatus
    MAX-ACCESS   read-only
    STATUS       current
    DESCRIPTION
        "Cisco UCS adaptor:HostEthIf:perf managed object property"
    ::= { cucsAdaptorHostEthIfEntry 38 }

cucsAdaptorHostEthIfPortId OBJECT-TYPE
    SYNTAX       Gauge32
    MAX-ACCESS   read-only
    STATUS       current
    DESCRIPTION
        "Cisco UCS adaptor:HostEthIf:portId managed object property"
    ::= { cucsAdaptorHostEthIfEntry 39 }

cucsAdaptorHostEthIfPower OBJECT-TYPE
    SYNTAX       CucsEquipmentPowerState
    MAX-ACCESS   read-only
    STATUS       current
    DESCRIPTION
        "Cisco UCS adaptor:HostEthIf:power managed object property"
    ::= { cucsAdaptorHostEthIfEntry 40 }

cucsAdaptorHostEthIfPresence OBJECT-TYPE
    SYNTAX       CucsEquipmentPresence
    MAX-ACCESS   read-only
    STATUS       current
    DESCRIPTION
        "Cisco UCS adaptor:HostEthIf:presence managed object property"
    ::= { cucsAdaptorHostEthIfEntry 41 }

cucsAdaptorHostEthIfPurpose OBJECT-TYPE
    SYNTAX       CucsAdaptorPurpose
    MAX-ACCESS   read-only
    STATUS       current
    DESCRIPTION
        "Cisco UCS adaptor:HostEthIf:purpose managed object property"
    ::= { cucsAdaptorHostEthIfEntry 42 }

cucsAdaptorHostEthIfRevision OBJECT-TYPE
    SYNTAX       SnmpAdminString
    MAX-ACCESS   read-only
    STATUS       current
    DESCRIPTION
        "Cisco UCS adaptor:HostEthIf:revision managed object property"
    ::= { cucsAdaptorHostEthIfEntry 43 }

cucsAdaptorHostEthIfSerial OBJECT-TYPE
    SYNTAX       SnmpAdminString
    MAX-ACCESS   read-only
    STATUS       current
    DESCRIPTION
        "Cisco UCS adaptor:HostEthIf:serial managed object property"
    ::= { cucsAdaptorHostEthIfEntry 44 }

cucsAdaptorHostEthIfSide OBJECT-TYPE
    SYNTAX       CucsNetworkSide
    MAX-ACCESS   read-only
    STATUS       current
    DESCRIPTION
        "Cisco UCS adaptor:HostEthIf:side managed object property"
    ::= { cucsAdaptorHostEthIfEntry 45 }

cucsAdaptorHostEthIfSlotId OBJECT-TYPE
    SYNTAX       Gauge32
    MAX-ACCESS   read-only
    STATUS       current
    DESCRIPTION
        "Cisco UCS adaptor:HostEthIf:slotId managed object property"
    ::= { cucsAdaptorHostEthIfEntry 46 }

cucsAdaptorHostEthIfSwitchId OBJECT-TYPE
    SYNTAX       CucsNetworkSwitchId
    MAX-ACCESS   read-only
    STATUS       current
    DESCRIPTION
        "Cisco UCS adaptor:HostEthIf:switchId managed object property"
    ::= { cucsAdaptorHostEthIfEntry 47 }

cucsAdaptorHostEthIfThermal OBJECT-TYPE
    SYNTAX       CucsEquipmentSensorThresholdStatus
    MAX-ACCESS   read-only
    STATUS       current
    DESCRIPTION
        "Cisco UCS adaptor:HostEthIf:thermal managed object property"
    ::= { cucsAdaptorHostEthIfEntry 48 }

cucsAdaptorHostEthIfTransport OBJECT-TYPE
    SYNTAX       CucsAdaptorHostEthIfTransport
    MAX-ACCESS   read-only
    STATUS       current
    DESCRIPTION
        "Cisco UCS adaptor:HostEthIf:transport managed object property"
    ::= { cucsAdaptorHostEthIfEntry 49 }

cucsAdaptorHostEthIfType OBJECT-TYPE
    SYNTAX       CucsNetworkConnectionType
    MAX-ACCESS   read-only
    STATUS       current
    DESCRIPTION
        "Cisco UCS adaptor:HostEthIf:type managed object property"
    ::= { cucsAdaptorHostEthIfEntry 50 }

cucsAdaptorHostEthIfVendor OBJECT-TYPE
    SYNTAX       SnmpAdminString
    MAX-ACCESS   read-only
    STATUS       current
    DESCRIPTION
        "Cisco UCS adaptor:HostEthIf:vendor managed object property"
    ::= { cucsAdaptorHostEthIfEntry 51 }

cucsAdaptorHostEthIfVnicDn OBJECT-TYPE
    SYNTAX       SnmpAdminString
    MAX-ACCESS   read-only
    STATUS       current
    DESCRIPTION
        "Cisco UCS adaptor:HostEthIf:vnicDn managed object property"
    ::= { cucsAdaptorHostEthIfEntry 52 }

cucsAdaptorHostEthIfVoltage OBJECT-TYPE
    SYNTAX       CucsEquipmentSensorThresholdStatus
    MAX-ACCESS   read-only
    STATUS       current
    DESCRIPTION
        "Cisco UCS adaptor:HostEthIf:voltage managed object property"
    ::= { cucsAdaptorHostEthIfEntry 53 }

cucsAdaptorHostEthIfPeerChassisId OBJECT-TYPE
    SYNTAX       Gauge32
    MAX-ACCESS   read-only
    STATUS       current
    DESCRIPTION
        "Cisco UCS adaptor:HostEthIf:peerChassisId managed
        object property"
    ::= { cucsAdaptorHostEthIfEntry 54 }

cucsAdaptorHostEthIfPciFunc OBJECT-TYPE
    SYNTAX       Gauge32
    MAX-ACCESS   read-only
    STATUS       current
    DESCRIPTION
        "Cisco UCS adaptor:HostEthIf:pciFunc managed object property"
    ::= { cucsAdaptorHostEthIfEntry 55 }

cucsAdaptorHostEthIfPciSlot OBJECT-TYPE
    SYNTAX       Gauge32
    MAX-ACCESS   read-only
    STATUS       current
    DESCRIPTION
        "Cisco UCS adaptor:HostEthIf:pciSlot managed object property"
    ::= { cucsAdaptorHostEthIfEntry 56 }

cucsAdaptorHostEthIfOperQualifierReason OBJECT-TYPE
    SYNTAX       SnmpAdminString
    MAX-ACCESS   read-only
    STATUS       current
    DESCRIPTION
        "Cisco UCS adaptor:HostEthIf:operQualifierReason
        managed object property"
    ::= { cucsAdaptorHostEthIfEntry 57 }

cucsAdaptorHostEthIfPfDn OBJECT-TYPE
    SYNTAX       SnmpAdminString
    MAX-ACCESS   read-only
    STATUS       current
    DESCRIPTION
        "Cisco UCS adaptor:HostEthIf:pfDn managed object property"
    ::= { cucsAdaptorHostEthIfEntry 58 }

cucsAdaptorHostEthIfVirtualizationPreference OBJECT-TYPE
    SYNTAX       CucsVnicVirtualizationPreferenceType
    MAX-ACCESS   read-only
    STATUS       current
    DESCRIPTION
        "Cisco UCS adaptor:HostEthIf:virtualizationPreference
        managed object property"
    ::= { cucsAdaptorHostEthIfEntry 59 }

cucsAdaptorHostEthIfHostPort OBJECT-TYPE
    SYNTAX       CucsAdaptorHostEthIfHostPort
    MAX-ACCESS   read-only
    STATUS       current
    DESCRIPTION
        "Cisco UCS adaptor:HostEthIf:hostPort managed object property"
    ::= { cucsAdaptorHostEthIfEntry 60 }

cucsAdaptorHostEthIfCdnName OBJECT-TYPE
    SYNTAX       SnmpAdminString
    MAX-ACCESS   read-only
    STATUS       current
    DESCRIPTION
        "Cisco UCS adaptor:HostEthIf:cdnName managed object property"
    ::= { cucsAdaptorHostEthIfEntry 61 }

cucsAdaptorHostEthIfFsmTable OBJECT-TYPE
    SYNTAX           SEQUENCE OF CucsAdaptorHostEthIfFsmEntry
    MAX-ACCESS       not-accessible
    STATUS           current
    DESCRIPTION
        "Cisco UCS adaptor:HostEthIfFsm managed object table"
    ::= { cucsAdaptorObjects 110 }

cucsAdaptorHostEthIfFsmEntry OBJECT-TYPE
    SYNTAX           CucsAdaptorHostEthIfFsmEntry
    MAX-ACCESS       not-accessible
    STATUS           current
    DESCRIPTION
        "Entry for the cucsAdaptorHostEthIfFsmTable table."
    INDEX { cucsAdaptorHostEthIfFsmInstanceId }
    ::= { cucsAdaptorHostEthIfFsmTable 1 }

CucsAdaptorHostEthIfFsmEntry ::= SEQUENCE {
    cucsAdaptorHostEthIfFsmInstanceId                                CucsManagedObjectId,
    cucsAdaptorHostEthIfFsmDn                                        CucsManagedObjectDn,
    cucsAdaptorHostEthIfFsmRn                                        SnmpAdminString,
    cucsAdaptorHostEthIfFsmCompletionTime                            DateAndTime,
    cucsAdaptorHostEthIfFsmCurrentFsm                                CucsAdaptorHostEthIfFsmCurrentFsm,
    cucsAdaptorHostEthIfFsmDescrData                                 SnmpAdminString,
    cucsAdaptorHostEthIfFsmFsmStatus                                 CucsFsmFsmStageStatus,
    cucsAdaptorHostEthIfFsmProgress                                  Gauge32,
    cucsAdaptorHostEthIfFsmRmtErrCode                                Gauge32,
    cucsAdaptorHostEthIfFsmRmtErrDescr                               SnmpAdminString,
    cucsAdaptorHostEthIfFsmRmtRslt                                   CucsConditionRemoteInvRslt
}

cucsAdaptorHostEthIfFsmInstanceId OBJECT-TYPE
    SYNTAX       CucsManagedObjectId
    MAX-ACCESS   not-accessible
    STATUS       current
    DESCRIPTION
        "Instance identifier of the managed object."
    ::= { cucsAdaptorHostEthIfFsmEntry 1 }

cucsAdaptorHostEthIfFsmDn OBJECT-TYPE
    SYNTAX       CucsManagedObjectDn
    MAX-ACCESS   read-only
    STATUS       current
    DESCRIPTION
        "Cisco UCS adaptor:HostEthIfFsm:dn managed object property"
    ::= { cucsAdaptorHostEthIfFsmEntry 2 }

cucsAdaptorHostEthIfFsmRn OBJECT-TYPE
    SYNTAX       SnmpAdminString
    MAX-ACCESS   read-only
    STATUS       current
    DESCRIPTION
        "Cisco UCS adaptor:HostEthIfFsm:rn managed object property"
    ::= { cucsAdaptorHostEthIfFsmEntry 3 }

cucsAdaptorHostEthIfFsmCompletionTime OBJECT-TYPE
    SYNTAX       DateAndTime
    MAX-ACCESS   read-only
    STATUS       current
    DESCRIPTION
        "Cisco UCS adaptor:HostEthIfFsm:completionTime
        managed object property"
    ::= { cucsAdaptorHostEthIfFsmEntry 4 }

cucsAdaptorHostEthIfFsmCurrentFsm OBJECT-TYPE
    SYNTAX       CucsAdaptorHostEthIfFsmCurrentFsm
    MAX-ACCESS   read-only
    STATUS       current
    DESCRIPTION
        "Cisco UCS adaptor:HostEthIfFsm:currentFsm managed
        object property"
    ::= { cucsAdaptorHostEthIfFsmEntry 5 }

cucsAdaptorHostEthIfFsmDescrData OBJECT-TYPE
    SYNTAX       SnmpAdminString
    MAX-ACCESS   read-only
    STATUS       current
    DESCRIPTION
        "Cisco UCS adaptor:HostEthIfFsm:descr managed object property"
    ::= { cucsAdaptorHostEthIfFsmEntry 6 }

cucsAdaptorHostEthIfFsmFsmStatus OBJECT-TYPE
    SYNTAX       CucsFsmFsmStageStatus
    MAX-ACCESS   read-only
    STATUS       current
    DESCRIPTION
        "Cisco UCS adaptor:HostEthIfFsm:fsmStatus managed object property"
    ::= { cucsAdaptorHostEthIfFsmEntry 7 }

cucsAdaptorHostEthIfFsmProgress OBJECT-TYPE
    SYNTAX       Gauge32
    MAX-ACCESS   read-only
    STATUS       current
    DESCRIPTION
        "Cisco UCS adaptor:HostEthIfFsm:progress managed object property"
    ::= { cucsAdaptorHostEthIfFsmEntry 8 }

cucsAdaptorHostEthIfFsmRmtErrCode OBJECT-TYPE
    SYNTAX       Gauge32
    MAX-ACCESS   read-only
    STATUS       current
    DESCRIPTION
        "Cisco UCS adaptor:HostEthIfFsm:rmtErrCode managed
        object property"
    ::= { cucsAdaptorHostEthIfFsmEntry 9 }

cucsAdaptorHostEthIfFsmRmtErrDescr OBJECT-TYPE
    SYNTAX       SnmpAdminString
    MAX-ACCESS   read-only
    STATUS       current
    DESCRIPTION
        "Cisco UCS adaptor:HostEthIfFsm:rmtErrDescr managed
        object property"
    ::= { cucsAdaptorHostEthIfFsmEntry 10 }

cucsAdaptorHostEthIfFsmRmtRslt OBJECT-TYPE
    SYNTAX       CucsConditionRemoteInvRslt
    MAX-ACCESS   read-only
    STATUS       current
    DESCRIPTION
        "Cisco UCS adaptor:HostEthIfFsm:rmtRslt managed object property"
    ::= { cucsAdaptorHostEthIfFsmEntry 11 }

cucsAdaptorHostEthIfFsmStageTable OBJECT-TYPE
    SYNTAX           SEQUENCE OF CucsAdaptorHostEthIfFsmStageEntry
    MAX-ACCESS       not-accessible
    STATUS           current
    DESCRIPTION
        "Cisco UCS adaptor:HostEthIfFsmStage managed object table"
    ::= { cucsAdaptorObjects 111 }

cucsAdaptorHostEthIfFsmStageEntry OBJECT-TYPE
    SYNTAX           CucsAdaptorHostEthIfFsmStageEntry
    MAX-ACCESS       not-accessible
    STATUS           current
    DESCRIPTION
        "Entry for the cucsAdaptorHostEthIfFsmStageTable table."
    INDEX { cucsAdaptorHostEthIfFsmStageInstanceId }
    ::= { cucsAdaptorHostEthIfFsmStageTable 1 }

CucsAdaptorHostEthIfFsmStageEntry ::= SEQUENCE {
    cucsAdaptorHostEthIfFsmStageInstanceId                           CucsManagedObjectId,
    cucsAdaptorHostEthIfFsmStageDn                                   CucsManagedObjectDn,
    cucsAdaptorHostEthIfFsmStageRn                                   SnmpAdminString,
    cucsAdaptorHostEthIfFsmStageDescrData                            SnmpAdminString,
    cucsAdaptorHostEthIfFsmStageLastUpdateTime                       DateAndTime,
    cucsAdaptorHostEthIfFsmStageName                                 CucsAdaptorHostEthIfFsmStageName,
    cucsAdaptorHostEthIfFsmStageOrder                                Gauge32,
    cucsAdaptorHostEthIfFsmStageRetry                                Gauge32,
    cucsAdaptorHostEthIfFsmStageStageStatus                          CucsFsmFsmStageStatus
}

cucsAdaptorHostEthIfFsmStageInstanceId OBJECT-TYPE
    SYNTAX       CucsManagedObjectId
    MAX-ACCESS   not-accessible
    STATUS       current
    DESCRIPTION
        "Instance identifier of the managed object."
    ::= { cucsAdaptorHostEthIfFsmStageEntry 1 }

cucsAdaptorHostEthIfFsmStageDn OBJECT-TYPE
    SYNTAX       CucsManagedObjectDn
    MAX-ACCESS   read-only
    STATUS       current
    DESCRIPTION
        "Cisco UCS adaptor:HostEthIfFsmStage:dn managed object property"
    ::= { cucsAdaptorHostEthIfFsmStageEntry 2 }

cucsAdaptorHostEthIfFsmStageRn OBJECT-TYPE
    SYNTAX       SnmpAdminString
    MAX-ACCESS   read-only
    STATUS       current
    DESCRIPTION
        "Cisco UCS adaptor:HostEthIfFsmStage:rn managed object property"
    ::= { cucsAdaptorHostEthIfFsmStageEntry 3 }

cucsAdaptorHostEthIfFsmStageDescrData OBJECT-TYPE
    SYNTAX       SnmpAdminString
    MAX-ACCESS   read-only
    STATUS       current
    DESCRIPTION
        "Cisco UCS adaptor:HostEthIfFsmStage:descr managed
        object property"
    ::= { cucsAdaptorHostEthIfFsmStageEntry 4 }

cucsAdaptorHostEthIfFsmStageLastUpdateTime OBJECT-TYPE
    SYNTAX       DateAndTime
    MAX-ACCESS   read-only
    STATUS       current
    DESCRIPTION
        "Cisco UCS adaptor:HostEthIfFsmStage:lastUpdateTime
        managed object property"
    ::= { cucsAdaptorHostEthIfFsmStageEntry 5 }

cucsAdaptorHostEthIfFsmStageName OBJECT-TYPE
    SYNTAX       CucsAdaptorHostEthIfFsmStageName
    MAX-ACCESS   read-only
    STATUS       current
    DESCRIPTION
        "Cisco UCS adaptor:HostEthIfFsmStage:name managed object property"
    ::= { cucsAdaptorHostEthIfFsmStageEntry 6 }

cucsAdaptorHostEthIfFsmStageOrder OBJECT-TYPE
    SYNTAX       Gauge32
    MAX-ACCESS   read-only
    STATUS       current
    DESCRIPTION
        "Cisco UCS adaptor:HostEthIfFsmStage:order managed
        object property"
    ::= { cucsAdaptorHostEthIfFsmStageEntry 7 }

cucsAdaptorHostEthIfFsmStageRetry OBJECT-TYPE
    SYNTAX       Gauge32
    MAX-ACCESS   read-only
    STATUS       current
    DESCRIPTION
        "Cisco UCS adaptor:HostEthIfFsmStage:retry managed
        object property"
    ::= { cucsAdaptorHostEthIfFsmStageEntry 8 }

cucsAdaptorHostEthIfFsmStageStageStatus OBJECT-TYPE
    SYNTAX       CucsFsmFsmStageStatus
    MAX-ACCESS   read-only
    STATUS       current
    DESCRIPTION
        "Cisco UCS adaptor:HostEthIfFsmStage:stageStatus
        managed object property"
    ::= { cucsAdaptorHostEthIfFsmStageEntry 9 }

cucsAdaptorHostEthIfFsmTaskTable OBJECT-TYPE
    SYNTAX           SEQUENCE OF CucsAdaptorHostEthIfFsmTaskEntry
    MAX-ACCESS       not-accessible
    STATUS           current
    DESCRIPTION
        "Cisco UCS adaptor:HostEthIfFsmTask managed object table"
    ::= { cucsAdaptorObjects 46 }

cucsAdaptorHostEthIfFsmTaskEntry OBJECT-TYPE
    SYNTAX           CucsAdaptorHostEthIfFsmTaskEntry
    MAX-ACCESS       not-accessible
    STATUS           current
    DESCRIPTION
        "Entry for the cucsAdaptorHostEthIfFsmTaskTable table."
    INDEX { cucsAdaptorHostEthIfFsmTaskInstanceId }
    ::= { cucsAdaptorHostEthIfFsmTaskTable 1 }

CucsAdaptorHostEthIfFsmTaskEntry ::= SEQUENCE {
    cucsAdaptorHostEthIfFsmTaskInstanceId                            CucsManagedObjectId,
    cucsAdaptorHostEthIfFsmTaskDn                                    CucsManagedObjectDn,
    cucsAdaptorHostEthIfFsmTaskRn                                    SnmpAdminString,
    cucsAdaptorHostEthIfFsmTaskCompletion                            CucsFsmCompletion,
    cucsAdaptorHostEthIfFsmTaskFlags                                 CucsFsmFlags,
    cucsAdaptorHostEthIfFsmTaskItem                                  CucsAdaptorHostEthIfFsmTaskItem,
    cucsAdaptorHostEthIfFsmTaskSeqId                                 Gauge32
}

cucsAdaptorHostEthIfFsmTaskInstanceId OBJECT-TYPE
    SYNTAX       CucsManagedObjectId
    MAX-ACCESS   not-accessible
    STATUS       current
    DESCRIPTION
        "Instance identifier of the managed object."
    ::= { cucsAdaptorHostEthIfFsmTaskEntry 1 }

cucsAdaptorHostEthIfFsmTaskDn OBJECT-TYPE
    SYNTAX       CucsManagedObjectDn
    MAX-ACCESS   read-only
    STATUS       current
    DESCRIPTION
        "Cisco UCS adaptor:HostEthIfFsmTask:dn managed object property"
    ::= { cucsAdaptorHostEthIfFsmTaskEntry 2 }

cucsAdaptorHostEthIfFsmTaskRn OBJECT-TYPE
    SYNTAX       SnmpAdminString
    MAX-ACCESS   read-only
    STATUS       current
    DESCRIPTION
        "Cisco UCS adaptor:HostEthIfFsmTask:rn managed object property"
    ::= { cucsAdaptorHostEthIfFsmTaskEntry 3 }

cucsAdaptorHostEthIfFsmTaskCompletion OBJECT-TYPE
    SYNTAX       CucsFsmCompletion
    MAX-ACCESS   read-only
    STATUS       current
    DESCRIPTION
        "Cisco UCS adaptor:HostEthIfFsmTask:completion
        managed object property"
    ::= { cucsAdaptorHostEthIfFsmTaskEntry 4 }

cucsAdaptorHostEthIfFsmTaskFlags OBJECT-TYPE
    SYNTAX       CucsFsmFlags
    MAX-ACCESS   read-only
    STATUS       current
    DESCRIPTION
        "Cisco UCS adaptor:HostEthIfFsmTask:flags managed object property"
    ::= { cucsAdaptorHostEthIfFsmTaskEntry 5 }

cucsAdaptorHostEthIfFsmTaskItem OBJECT-TYPE
    SYNTAX       CucsAdaptorHostEthIfFsmTaskItem
    MAX-ACCESS   read-only
    STATUS       current
    DESCRIPTION
        "Cisco UCS adaptor:HostEthIfFsmTask:item managed object property"
    ::= { cucsAdaptorHostEthIfFsmTaskEntry 6 }

cucsAdaptorHostEthIfFsmTaskSeqId OBJECT-TYPE
    SYNTAX       Gauge32
    MAX-ACCESS   read-only
    STATUS       current
    DESCRIPTION
        "Cisco UCS adaptor:HostEthIfFsmTask:seqId managed object property"
    ::= { cucsAdaptorHostEthIfFsmTaskEntry 7 }

cucsAdaptorHostEthIfProfileTable OBJECT-TYPE
    SYNTAX           SEQUENCE OF CucsAdaptorHostEthIfProfileEntry
    MAX-ACCESS       not-accessible
    STATUS           current
    DESCRIPTION
        "Cisco UCS adaptor:HostEthIfProfile managed object table"
    ::= { cucsAdaptorObjects 47 }

cucsAdaptorHostEthIfProfileEntry OBJECT-TYPE
    SYNTAX           CucsAdaptorHostEthIfProfileEntry
    MAX-ACCESS       not-accessible
    STATUS           current
    DESCRIPTION
        "Entry for the cucsAdaptorHostEthIfProfileTable table."
    INDEX { cucsAdaptorHostEthIfProfileInstanceId }
    ::= { cucsAdaptorHostEthIfProfileTable 1 }

CucsAdaptorHostEthIfProfileEntry ::= SEQUENCE {
    cucsAdaptorHostEthIfProfileInstanceId                            CucsManagedObjectId,
    cucsAdaptorHostEthIfProfileDn                                    CucsManagedObjectDn,
    cucsAdaptorHostEthIfProfileRn                                    SnmpAdminString,
    cucsAdaptorHostEthIfProfileDescr                                 SnmpAdminString,
    cucsAdaptorHostEthIfProfileIntId                                 SnmpAdminString,
    cucsAdaptorHostEthIfProfileName                                  SnmpAdminString,
    cucsAdaptorHostEthIfProfilePolicyLevel                           Gauge32,
    cucsAdaptorHostEthIfProfilePolicyOwner                           CucsPolicyPolicyOwner
}

cucsAdaptorHostEthIfProfileInstanceId OBJECT-TYPE
    SYNTAX       CucsManagedObjectId
    MAX-ACCESS   not-accessible
    STATUS       current
    DESCRIPTION
        "Instance identifier of the managed object."
    ::= { cucsAdaptorHostEthIfProfileEntry 1 }

cucsAdaptorHostEthIfProfileDn OBJECT-TYPE
    SYNTAX       CucsManagedObjectDn
    MAX-ACCESS   read-only
    STATUS       current
    DESCRIPTION
        "Cisco UCS adaptor:HostEthIfProfile:dn managed object property"
    ::= { cucsAdaptorHostEthIfProfileEntry 2 }

cucsAdaptorHostEthIfProfileRn OBJECT-TYPE
    SYNTAX       SnmpAdminString
    MAX-ACCESS   read-only
    STATUS       current
    DESCRIPTION
        "Cisco UCS adaptor:HostEthIfProfile:rn managed object property"
    ::= { cucsAdaptorHostEthIfProfileEntry 3 }

cucsAdaptorHostEthIfProfileDescr OBJECT-TYPE
    SYNTAX       SnmpAdminString
    MAX-ACCESS   read-only
    STATUS       current
    DESCRIPTION
        "Cisco UCS adaptor:HostEthIfProfile:descr managed object property"
    ::= { cucsAdaptorHostEthIfProfileEntry 4 }

cucsAdaptorHostEthIfProfileIntId OBJECT-TYPE
    SYNTAX       SnmpAdminString
    MAX-ACCESS   read-only
    STATUS       current
    DESCRIPTION
        "Cisco UCS adaptor:HostEthIfProfile:intId managed object property"
    ::= { cucsAdaptorHostEthIfProfileEntry 5 }

cucsAdaptorHostEthIfProfileName OBJECT-TYPE
    SYNTAX       SnmpAdminString
    MAX-ACCESS   read-only
    STATUS       current
    DESCRIPTION
        "Cisco UCS adaptor:HostEthIfProfile:name managed object property"
    ::= { cucsAdaptorHostEthIfProfileEntry 6 }

cucsAdaptorHostEthIfProfilePolicyLevel OBJECT-TYPE
    SYNTAX       Gauge32
    MAX-ACCESS   read-only
    STATUS       current
    DESCRIPTION
        "Cisco UCS adaptor:HostEthIfProfile:policyLevel
        managed object property"
    ::= { cucsAdaptorHostEthIfProfileEntry 7 }

cucsAdaptorHostEthIfProfilePolicyOwner OBJECT-TYPE
    SYNTAX       CucsPolicyPolicyOwner
    MAX-ACCESS   read-only
    STATUS       current
    DESCRIPTION
        "Cisco UCS adaptor:HostEthIfProfile:policyOwner
        managed object property"
    ::= { cucsAdaptorHostEthIfProfileEntry 8 }

cucsAdaptorHostFcIfTable OBJECT-TYPE
    SYNTAX           SEQUENCE OF CucsAdaptorHostFcIfEntry
    MAX-ACCESS       not-accessible
    STATUS           current
    DESCRIPTION
        "Cisco UCS adaptor:HostFcIf managed object table"
    ::= { cucsAdaptorObjects 48 }

cucsAdaptorHostFcIfEntry OBJECT-TYPE
    SYNTAX           CucsAdaptorHostFcIfEntry
    MAX-ACCESS       not-accessible
    STATUS           current
    DESCRIPTION
        "Entry for the cucsAdaptorHostFcIfTable table."
    INDEX { cucsAdaptorHostFcIfInstanceId }
    ::= { cucsAdaptorHostFcIfTable 1 }

CucsAdaptorHostFcIfEntry ::= SEQUENCE {
    cucsAdaptorHostFcIfInstanceId                                    CucsManagedObjectId,
    cucsAdaptorHostFcIfDn                                            CucsManagedObjectDn,
    cucsAdaptorHostFcIfRn                                            SnmpAdminString,
    cucsAdaptorHostFcIfAdminState                                    CucsAdaptorHostFcIfAdminState,
    cucsAdaptorHostFcIfBootDev                                       CucsAdaptorHostIfBootDev,
    cucsAdaptorHostFcIfChassisId                                     Gauge32,
    cucsAdaptorHostFcIfDiscovery                                     CucsEtherSatelliteConnectionDisc,
    cucsAdaptorHostFcIfEpDn                                          SnmpAdminString,
    cucsAdaptorHostFcIfFltAggr                                       Unsigned64,
    cucsAdaptorHostFcIfFsmDescr                                      SnmpAdminString,
    cucsAdaptorHostFcIfFsmPrev                                       SnmpAdminString,
    cucsAdaptorHostFcIfFsmProgr                                      Gauge32,
    cucsAdaptorHostFcIfFsmRmtInvErrCode                              Gauge32,
    cucsAdaptorHostFcIfFsmRmtInvErrDescr                             SnmpAdminString,
    cucsAdaptorHostFcIfFsmRmtInvRslt                                 CucsConditionRemoteInvRslt,
    cucsAdaptorHostFcIfFsmStageDescr                                 SnmpAdminString,
    cucsAdaptorHostFcIfFsmStamp                                      DateAndTime,
    cucsAdaptorHostFcIfFsmStatus                                     SnmpAdminString,
    cucsAdaptorHostFcIfFsmTry                                        Gauge32,
    cucsAdaptorHostFcIfId                                            Gauge32,
    cucsAdaptorHostFcIfIfRole                                        CucsNetworkPortRole,
    cucsAdaptorHostFcIfIfType                                        CucsNetworkPhysEpIfType,
    cucsAdaptorHostFcIfLc                                            CucsFsmLifecycle,
    cucsAdaptorHostFcIfLinkState                                     CucsAdaptorLinkState,
    cucsAdaptorHostFcIfLocale                                        CucsNetworkLocale,
    cucsAdaptorHostFcIfMaxDataFieldSize                              Gauge32,
    cucsAdaptorHostFcIfModel                                         SnmpAdminString,
    cucsAdaptorHostFcIfName                                          SnmpAdminString,
    cucsAdaptorHostFcIfNodeWwn                                       Unsigned64,
    cucsAdaptorHostFcIfOperState                                     CucsEquipmentOperability,
    cucsAdaptorHostFcIfOperability                                   CucsEquipmentOperability,
    cucsAdaptorHostFcIfOrder                                         Gauge32,
    cucsAdaptorHostFcIfOriginalNodeWwn                               Unsigned64,
    cucsAdaptorHostFcIfOriginalWwn                                   Unsigned64,
    cucsAdaptorHostFcIfPciAddr                                       SnmpAdminString,
    cucsAdaptorHostFcIfPeerDn                                        SnmpAdminString,
    cucsAdaptorHostFcIfPeerPortId                                    Gauge32,
    cucsAdaptorHostFcIfPeerSlotId                                    Gauge32,
    cucsAdaptorHostFcIfPerf                                          CucsEquipmentSensorThresholdStatus,
    cucsAdaptorHostFcIfPersBind                                      CucsAdaptorHostFcIfPersBind,
    cucsAdaptorHostFcIfPortId                                        Gauge32,
    cucsAdaptorHostFcIfPower                                         CucsEquipmentPowerState,
    cucsAdaptorHostFcIfPresence                                      CucsEquipmentPresence,
    cucsAdaptorHostFcIfPurpose                                       CucsAdaptorPurpose,
    cucsAdaptorHostFcIfRevision                                      SnmpAdminString,
    cucsAdaptorHostFcIfSerial                                        SnmpAdminString,
    cucsAdaptorHostFcIfSide                                          CucsNetworkSide,
    cucsAdaptorHostFcIfSlotId                                        Gauge32,
    cucsAdaptorHostFcIfSwitchId                                      CucsNetworkSwitchId,
    cucsAdaptorHostFcIfThermal                                       CucsEquipmentSensorThresholdStatus,
    cucsAdaptorHostFcIfTransport                                     CucsAdaptorHostFcIfTransport,
    cucsAdaptorHostFcIfType                                          CucsNetworkConnectionType,
    cucsAdaptorHostFcIfVendor                                        SnmpAdminString,
    cucsAdaptorHostFcIfVnicDn                                        SnmpAdminString,
    cucsAdaptorHostFcIfVoltage                                       CucsEquipmentSensorThresholdStatus,
    cucsAdaptorHostFcIfWwn                                           Unsigned64,
    cucsAdaptorHostFcIfPeerChassisId                                 Gauge32,
    cucsAdaptorHostFcIfPciFunc                                       Gauge32,
    cucsAdaptorHostFcIfPciSlot                                       Gauge32,
    cucsAdaptorHostFcIfOperQualifierReason                           SnmpAdminString,
    cucsAdaptorHostFcIfHostPort                                      CucsAdaptorHostFcIfHostPort,
    cucsAdaptorHostFcIfCdnName                                       SnmpAdminString
}

cucsAdaptorHostFcIfInstanceId OBJECT-TYPE
    SYNTAX       CucsManagedObjectId
    MAX-ACCESS   not-accessible
    STATUS       current
    DESCRIPTION
        "Instance identifier of the managed object."
    ::= { cucsAdaptorHostFcIfEntry 1 }

cucsAdaptorHostFcIfDn OBJECT-TYPE
    SYNTAX       CucsManagedObjectDn
    MAX-ACCESS   read-only
    STATUS       current
    DESCRIPTION
        "Cisco UCS adaptor:HostFcIf:dn managed object property"
    ::= { cucsAdaptorHostFcIfEntry 2 }

cucsAdaptorHostFcIfRn OBJECT-TYPE
    SYNTAX       SnmpAdminString
    MAX-ACCESS   read-only
    STATUS       current
    DESCRIPTION
        "Cisco UCS adaptor:HostFcIf:rn managed object property"
    ::= { cucsAdaptorHostFcIfEntry 3 }

cucsAdaptorHostFcIfAdminState OBJECT-TYPE
    SYNTAX       CucsAdaptorHostFcIfAdminState
    MAX-ACCESS   read-only
    STATUS       current
    DESCRIPTION
        "Cisco UCS adaptor:HostFcIf:adminState managed object property"
    ::= { cucsAdaptorHostFcIfEntry 4 }

cucsAdaptorHostFcIfBootDev OBJECT-TYPE
    SYNTAX       CucsAdaptorHostIfBootDev
    MAX-ACCESS   read-only
    STATUS       current
    DESCRIPTION
        "Cisco UCS adaptor:HostFcIf:bootDev managed object property"
    ::= { cucsAdaptorHostFcIfEntry 5 }

cucsAdaptorHostFcIfChassisId OBJECT-TYPE
    SYNTAX       Gauge32
    MAX-ACCESS   read-only
    STATUS       current
    DESCRIPTION
        "Cisco UCS adaptor:HostFcIf:chassisId managed object property"
    ::= { cucsAdaptorHostFcIfEntry 6 }

cucsAdaptorHostFcIfDiscovery OBJECT-TYPE
    SYNTAX       CucsEtherSatelliteConnectionDisc
    MAX-ACCESS   read-only
    STATUS       current
    DESCRIPTION
        "Cisco UCS adaptor:HostFcIf:discovery managed object property"
    ::= { cucsAdaptorHostFcIfEntry 7 }

cucsAdaptorHostFcIfEpDn OBJECT-TYPE
    SYNTAX       SnmpAdminString
    MAX-ACCESS   read-only
    STATUS       current
    DESCRIPTION
        "Cisco UCS adaptor:HostFcIf:epDn managed object property"
    ::= { cucsAdaptorHostFcIfEntry 8 }

cucsAdaptorHostFcIfFltAggr OBJECT-TYPE
    SYNTAX       Unsigned64
    MAX-ACCESS   read-only
    STATUS       current
    DESCRIPTION
        "Cisco UCS adaptor:HostFcIf:fltAggr managed object property"
    ::= { cucsAdaptorHostFcIfEntry 9 }

cucsAdaptorHostFcIfFsmDescr OBJECT-TYPE
    SYNTAX       SnmpAdminString
    MAX-ACCESS   read-only
    STATUS       current
    DESCRIPTION
        "Cisco UCS adaptor:HostFcIf:fsmDescr managed object property"
    ::= { cucsAdaptorHostFcIfEntry 10 }

cucsAdaptorHostFcIfFsmPrev OBJECT-TYPE
    SYNTAX       SnmpAdminString
    MAX-ACCESS   read-only
    STATUS       current
    DESCRIPTION
        "Cisco UCS adaptor:HostFcIf:fsmPrev managed object property"
    ::= { cucsAdaptorHostFcIfEntry 11 }

cucsAdaptorHostFcIfFsmProgr OBJECT-TYPE
    SYNTAX       Gauge32
    MAX-ACCESS   read-only
    STATUS       current
    DESCRIPTION
        "Cisco UCS adaptor:HostFcIf:fsmProgr managed object property"
    ::= { cucsAdaptorHostFcIfEntry 12 }

cucsAdaptorHostFcIfFsmRmtInvErrCode OBJECT-TYPE
    SYNTAX       Gauge32
    MAX-ACCESS   read-only
    STATUS       current
    DESCRIPTION
        "Cisco UCS adaptor:HostFcIf:fsmRmtInvErrCode managed
        object property"
    ::= { cucsAdaptorHostFcIfEntry 13 }

cucsAdaptorHostFcIfFsmRmtInvErrDescr OBJECT-TYPE
    SYNTAX       SnmpAdminString
    MAX-ACCESS   read-only
    STATUS       current
    DESCRIPTION
        "Cisco UCS adaptor:HostFcIf:fsmRmtInvErrDescr managed
        object property"
    ::= { cucsAdaptorHostFcIfEntry 14 }

cucsAdaptorHostFcIfFsmRmtInvRslt OBJECT-TYPE
    SYNTAX       CucsConditionRemoteInvRslt
    MAX-ACCESS   read-only
    STATUS       current
    DESCRIPTION
        "Cisco UCS adaptor:HostFcIf:fsmRmtInvRslt managed object property"
    ::= { cucsAdaptorHostFcIfEntry 15 }

cucsAdaptorHostFcIfFsmStageDescr OBJECT-TYPE
    SYNTAX       SnmpAdminString
    MAX-ACCESS   read-only
    STATUS       current
    DESCRIPTION
        "Cisco UCS adaptor:HostFcIf:fsmStageDescr managed object property"
    ::= { cucsAdaptorHostFcIfEntry 16 }

cucsAdaptorHostFcIfFsmStamp OBJECT-TYPE
    SYNTAX       DateAndTime
    MAX-ACCESS   read-only
    STATUS       current
    DESCRIPTION
        "Cisco UCS adaptor:HostFcIf:fsmStamp managed object property"
    ::= { cucsAdaptorHostFcIfEntry 17 }

cucsAdaptorHostFcIfFsmStatus OBJECT-TYPE
    SYNTAX       SnmpAdminString
    MAX-ACCESS   read-only
    STATUS       current
    DESCRIPTION
        "Cisco UCS adaptor:HostFcIf:fsmStatus managed object property"
    ::= { cucsAdaptorHostFcIfEntry 18 }

cucsAdaptorHostFcIfFsmTry OBJECT-TYPE
    SYNTAX       Gauge32
    MAX-ACCESS   read-only
    STATUS       current
    DESCRIPTION
        "Cisco UCS adaptor:HostFcIf:fsmTry managed object property"
    ::= { cucsAdaptorHostFcIfEntry 19 }

cucsAdaptorHostFcIfId OBJECT-TYPE
    SYNTAX       Gauge32
    MAX-ACCESS   read-only
    STATUS       current
    DESCRIPTION
        "Cisco UCS adaptor:HostFcIf:id managed object property"
    ::= { cucsAdaptorHostFcIfEntry 20 }

cucsAdaptorHostFcIfIfRole OBJECT-TYPE
    SYNTAX       CucsNetworkPortRole
    MAX-ACCESS   read-only
    STATUS       current
    DESCRIPTION
        "Cisco UCS adaptor:HostFcIf:ifRole managed object property"
    ::= { cucsAdaptorHostFcIfEntry 21 }

cucsAdaptorHostFcIfIfType OBJECT-TYPE
    SYNTAX       CucsNetworkPhysEpIfType
    MAX-ACCESS   read-only
    STATUS       current
    DESCRIPTION
        "Cisco UCS adaptor:HostFcIf:ifType managed object property"
    ::= { cucsAdaptorHostFcIfEntry 22 }

cucsAdaptorHostFcIfLc OBJECT-TYPE
    SYNTAX       CucsFsmLifecycle
    MAX-ACCESS   read-only
    STATUS       current
    DESCRIPTION
        "Cisco UCS adaptor:HostFcIf:lc managed object property"
    ::= { cucsAdaptorHostFcIfEntry 23 }

cucsAdaptorHostFcIfLinkState OBJECT-TYPE
    SYNTAX       CucsAdaptorLinkState
    MAX-ACCESS   read-only
    STATUS       current
    DESCRIPTION
        "Cisco UCS adaptor:HostFcIf:linkState managed object property"
    ::= { cucsAdaptorHostFcIfEntry 24 }

cucsAdaptorHostFcIfLocale OBJECT-TYPE
    SYNTAX       CucsNetworkLocale
    MAX-ACCESS   read-only
    STATUS       current
    DESCRIPTION
        "Cisco UCS adaptor:HostFcIf:locale managed object property"
    ::= { cucsAdaptorHostFcIfEntry 25 }

cucsAdaptorHostFcIfMaxDataFieldSize OBJECT-TYPE
    SYNTAX       Gauge32
    MAX-ACCESS   read-only
    STATUS       current
    DESCRIPTION
        "Cisco UCS adaptor:HostFcIf:maxDataFieldSize managed
        object property"
    ::= { cucsAdaptorHostFcIfEntry 26 }

cucsAdaptorHostFcIfModel OBJECT-TYPE
    SYNTAX       SnmpAdminString
    MAX-ACCESS   read-only
    STATUS       current
    DESCRIPTION
        "Cisco UCS adaptor:HostFcIf:model managed object property"
    ::= { cucsAdaptorHostFcIfEntry 27 }

cucsAdaptorHostFcIfName OBJECT-TYPE
    SYNTAX       SnmpAdminString
    MAX-ACCESS   read-only
    STATUS       current
    DESCRIPTION
        "Cisco UCS adaptor:HostFcIf:name managed object property"
    ::= { cucsAdaptorHostFcIfEntry 28 }

cucsAdaptorHostFcIfNodeWwn OBJECT-TYPE
    SYNTAX       Unsigned64
    MAX-ACCESS   read-only
    STATUS       current
    DESCRIPTION
        "Cisco UCS adaptor:HostFcIf:nodeWwn managed object property"
    ::= { cucsAdaptorHostFcIfEntry 29 }

cucsAdaptorHostFcIfOperState OBJECT-TYPE
    SYNTAX       CucsEquipmentOperability
    MAX-ACCESS   read-only
    STATUS       current
    DESCRIPTION
        "Cisco UCS adaptor:HostFcIf:operState managed object property"
    ::= { cucsAdaptorHostFcIfEntry 30 }

cucsAdaptorHostFcIfOperability OBJECT-TYPE
    SYNTAX       CucsEquipmentOperability
    MAX-ACCESS   read-only
    STATUS       current
    DESCRIPTION
        "Cisco UCS adaptor:HostFcIf:operability managed object property"
    ::= { cucsAdaptorHostFcIfEntry 31 }

cucsAdaptorHostFcIfOrder OBJECT-TYPE
    SYNTAX       Gauge32
    MAX-ACCESS   read-only
    STATUS       current
    DESCRIPTION
        "Cisco UCS adaptor:HostFcIf:order managed object property"
    ::= { cucsAdaptorHostFcIfEntry 32 }

cucsAdaptorHostFcIfOriginalNodeWwn OBJECT-TYPE
    SYNTAX       Unsigned64
    MAX-ACCESS   read-only
    STATUS       current
    DESCRIPTION
        "Cisco UCS adaptor:HostFcIf:originalNodeWwn managed
        object property"
    ::= { cucsAdaptorHostFcIfEntry 33 }

cucsAdaptorHostFcIfOriginalWwn OBJECT-TYPE
    SYNTAX       Unsigned64
    MAX-ACCESS   read-only
    STATUS       current
    DESCRIPTION
        "Cisco UCS adaptor:HostFcIf:originalWwn managed object property"
    ::= { cucsAdaptorHostFcIfEntry 34 }

cucsAdaptorHostFcIfPciAddr OBJECT-TYPE
    SYNTAX       SnmpAdminString
    MAX-ACCESS   read-only
    STATUS       current
    DESCRIPTION
        "Cisco UCS adaptor:HostFcIf:pciAddr managed object property"
    ::= { cucsAdaptorHostFcIfEntry 35 }

cucsAdaptorHostFcIfPeerDn OBJECT-TYPE
    SYNTAX       SnmpAdminString
    MAX-ACCESS   read-only
    STATUS       current
    DESCRIPTION
        "Cisco UCS adaptor:HostFcIf:peerDn managed object property"
    ::= { cucsAdaptorHostFcIfEntry 36 }

cucsAdaptorHostFcIfPeerPortId OBJECT-TYPE
    SYNTAX       Gauge32
    MAX-ACCESS   read-only
    STATUS       current
    DESCRIPTION
        "Cisco UCS adaptor:HostFcIf:peerPortId managed object property"
    ::= { cucsAdaptorHostFcIfEntry 37 }

cucsAdaptorHostFcIfPeerSlotId OBJECT-TYPE
    SYNTAX       Gauge32
    MAX-ACCESS   read-only
    STATUS       current
    DESCRIPTION
        "Cisco UCS adaptor:HostFcIf:peerSlotId managed object property"
    ::= { cucsAdaptorHostFcIfEntry 38 }

cucsAdaptorHostFcIfPerf OBJECT-TYPE
    SYNTAX       CucsEquipmentSensorThresholdStatus
    MAX-ACCESS   read-only
    STATUS       current
    DESCRIPTION
        "Cisco UCS adaptor:HostFcIf:perf managed object property"
    ::= { cucsAdaptorHostFcIfEntry 39 }

cucsAdaptorHostFcIfPersBind OBJECT-TYPE
    SYNTAX       CucsAdaptorHostFcIfPersBind
    MAX-ACCESS   read-only
    STATUS       current
    DESCRIPTION
        "Cisco UCS adaptor:HostFcIf:persBind managed object property"
    ::= { cucsAdaptorHostFcIfEntry 40 }

cucsAdaptorHostFcIfPortId OBJECT-TYPE
    SYNTAX       Gauge32
    MAX-ACCESS   read-only
    STATUS       current
    DESCRIPTION
        "Cisco UCS adaptor:HostFcIf:portId managed object property"
    ::= { cucsAdaptorHostFcIfEntry 41 }

cucsAdaptorHostFcIfPower OBJECT-TYPE
    SYNTAX       CucsEquipmentPowerState
    MAX-ACCESS   read-only
    STATUS       current
    DESCRIPTION
        "Cisco UCS adaptor:HostFcIf:power managed object property"
    ::= { cucsAdaptorHostFcIfEntry 42 }

cucsAdaptorHostFcIfPresence OBJECT-TYPE
    SYNTAX       CucsEquipmentPresence
    MAX-ACCESS   read-only
    STATUS       current
    DESCRIPTION
        "Cisco UCS adaptor:HostFcIf:presence managed object property"
    ::= { cucsAdaptorHostFcIfEntry 43 }

cucsAdaptorHostFcIfPurpose OBJECT-TYPE
    SYNTAX       CucsAdaptorPurpose
    MAX-ACCESS   read-only
    STATUS       current
    DESCRIPTION
        "Cisco UCS adaptor:HostFcIf:purpose managed object property"
    ::= { cucsAdaptorHostFcIfEntry 44 }

cucsAdaptorHostFcIfRevision OBJECT-TYPE
    SYNTAX       SnmpAdminString
    MAX-ACCESS   read-only
    STATUS       current
    DESCRIPTION
        "Cisco UCS adaptor:HostFcIf:revision managed object property"
    ::= { cucsAdaptorHostFcIfEntry 45 }

cucsAdaptorHostFcIfSerial OBJECT-TYPE
    SYNTAX       SnmpAdminString
    MAX-ACCESS   read-only
    STATUS       current
    DESCRIPTION
        "Cisco UCS adaptor:HostFcIf:serial managed object property"
    ::= { cucsAdaptorHostFcIfEntry 46 }

cucsAdaptorHostFcIfSide OBJECT-TYPE
    SYNTAX       CucsNetworkSide
    MAX-ACCESS   read-only
    STATUS       current
    DESCRIPTION
        "Cisco UCS adaptor:HostFcIf:side managed object property"
    ::= { cucsAdaptorHostFcIfEntry 47 }

cucsAdaptorHostFcIfSlotId OBJECT-TYPE
    SYNTAX       Gauge32
    MAX-ACCESS   read-only
    STATUS       current
    DESCRIPTION
        "Cisco UCS adaptor:HostFcIf:slotId managed object property"
    ::= { cucsAdaptorHostFcIfEntry 48 }

cucsAdaptorHostFcIfSwitchId OBJECT-TYPE
    SYNTAX       CucsNetworkSwitchId
    MAX-ACCESS   read-only
    STATUS       current
    DESCRIPTION
        "Cisco UCS adaptor:HostFcIf:switchId managed object property"
    ::= { cucsAdaptorHostFcIfEntry 49 }

cucsAdaptorHostFcIfThermal OBJECT-TYPE
    SYNTAX       CucsEquipmentSensorThresholdStatus
    MAX-ACCESS   read-only
    STATUS       current
    DESCRIPTION
        "Cisco UCS adaptor:HostFcIf:thermal managed object property"
    ::= { cucsAdaptorHostFcIfEntry 50 }

cucsAdaptorHostFcIfTransport OBJECT-TYPE
    SYNTAX       CucsAdaptorHostFcIfTransport
    MAX-ACCESS   read-only
    STATUS       current
    DESCRIPTION
        "Cisco UCS adaptor:HostFcIf:transport managed object property"
    ::= { cucsAdaptorHostFcIfEntry 51 }

cucsAdaptorHostFcIfType OBJECT-TYPE
    SYNTAX       CucsNetworkConnectionType
    MAX-ACCESS   read-only
    STATUS       current
    DESCRIPTION
        "Cisco UCS adaptor:HostFcIf:type managed object property"
    ::= { cucsAdaptorHostFcIfEntry 52 }

cucsAdaptorHostFcIfVendor OBJECT-TYPE
    SYNTAX       SnmpAdminString
    MAX-ACCESS   read-only
    STATUS       current
    DESCRIPTION
        "Cisco UCS adaptor:HostFcIf:vendor managed object property"
    ::= { cucsAdaptorHostFcIfEntry 53 }

cucsAdaptorHostFcIfVnicDn OBJECT-TYPE
    SYNTAX       SnmpAdminString
    MAX-ACCESS   read-only
    STATUS       current
    DESCRIPTION
        "Cisco UCS adaptor:HostFcIf:vnicDn managed object property"
    ::= { cucsAdaptorHostFcIfEntry 54 }

cucsAdaptorHostFcIfVoltage OBJECT-TYPE
    SYNTAX       CucsEquipmentSensorThresholdStatus
    MAX-ACCESS   read-only
    STATUS       current
    DESCRIPTION
        "Cisco UCS adaptor:HostFcIf:voltage managed object property"
    ::= { cucsAdaptorHostFcIfEntry 55 }

cucsAdaptorHostFcIfWwn OBJECT-TYPE
    SYNTAX       Unsigned64
    MAX-ACCESS   read-only
    STATUS       current
    DESCRIPTION
        "Cisco UCS adaptor:HostFcIf:wwn managed object property"
    ::= { cucsAdaptorHostFcIfEntry 56 }

cucsAdaptorHostFcIfPeerChassisId OBJECT-TYPE
    SYNTAX       Gauge32
    MAX-ACCESS   read-only
    STATUS       current
    DESCRIPTION
        "Cisco UCS adaptor:HostFcIf:peerChassisId managed object property"
    ::= { cucsAdaptorHostFcIfEntry 57 }

cucsAdaptorHostFcIfPciFunc OBJECT-TYPE
    SYNTAX       Gauge32
    MAX-ACCESS   read-only
    STATUS       current
    DESCRIPTION
        "Cisco UCS adaptor:HostFcIf:pciFunc managed object property"
    ::= { cucsAdaptorHostFcIfEntry 58 }

cucsAdaptorHostFcIfPciSlot OBJECT-TYPE
    SYNTAX       Gauge32
    MAX-ACCESS   read-only
    STATUS       current
    DESCRIPTION
        "Cisco UCS adaptor:HostFcIf:pciSlot managed object property"
    ::= { cucsAdaptorHostFcIfEntry 59 }

cucsAdaptorHostFcIfOperQualifierReason OBJECT-TYPE
    SYNTAX       SnmpAdminString
    MAX-ACCESS   read-only
    STATUS       current
    DESCRIPTION
        "Cisco UCS adaptor:HostFcIf:operQualifierReason
        managed object property"
    ::= { cucsAdaptorHostFcIfEntry 60 }

cucsAdaptorHostFcIfHostPort OBJECT-TYPE
    SYNTAX       CucsAdaptorHostFcIfHostPort
    MAX-ACCESS   read-only
    STATUS       current
    DESCRIPTION
        "Cisco UCS adaptor:HostFcIf:hostPort managed object property"
    ::= { cucsAdaptorHostFcIfEntry 61 }

cucsAdaptorHostFcIfCdnName OBJECT-TYPE
    SYNTAX       SnmpAdminString
    MAX-ACCESS   read-only
    STATUS       current
    DESCRIPTION
        "Cisco UCS adaptor:HostFcIf:cdnName managed object property"
    ::= { cucsAdaptorHostFcIfEntry 62 }

cucsAdaptorHostFcIfFsmTable OBJECT-TYPE
    SYNTAX           SEQUENCE OF CucsAdaptorHostFcIfFsmEntry
    MAX-ACCESS       not-accessible
    STATUS           current
    DESCRIPTION
        "Cisco UCS adaptor:HostFcIfFsm managed object table"
    ::= { cucsAdaptorObjects 112 }

cucsAdaptorHostFcIfFsmEntry OBJECT-TYPE
    SYNTAX           CucsAdaptorHostFcIfFsmEntry
    MAX-ACCESS       not-accessible
    STATUS           current
    DESCRIPTION
        "Entry for the cucsAdaptorHostFcIfFsmTable table."
    INDEX { cucsAdaptorHostFcIfFsmInstanceId }
    ::= { cucsAdaptorHostFcIfFsmTable 1 }

CucsAdaptorHostFcIfFsmEntry ::= SEQUENCE {
    cucsAdaptorHostFcIfFsmInstanceId                                 CucsManagedObjectId,
    cucsAdaptorHostFcIfFsmDn                                         CucsManagedObjectDn,
    cucsAdaptorHostFcIfFsmRn                                         SnmpAdminString,
    cucsAdaptorHostFcIfFsmCompletionTime                             DateAndTime,
    cucsAdaptorHostFcIfFsmCurrentFsm                                 CucsAdaptorHostFcIfFsmCurrentFsm,
    cucsAdaptorHostFcIfFsmDescrData                                  SnmpAdminString,
    cucsAdaptorHostFcIfFsmFsmStatus                                  CucsFsmFsmStageStatus,
    cucsAdaptorHostFcIfFsmProgress                                   Gauge32,
    cucsAdaptorHostFcIfFsmRmtErrCode                                 Gauge32,
    cucsAdaptorHostFcIfFsmRmtErrDescr                                SnmpAdminString,
    cucsAdaptorHostFcIfFsmRmtRslt                                    CucsConditionRemoteInvRslt
}

cucsAdaptorHostFcIfFsmInstanceId OBJECT-TYPE
    SYNTAX       CucsManagedObjectId
    MAX-ACCESS   not-accessible
    STATUS       current
    DESCRIPTION
        "Instance identifier of the managed object."
    ::= { cucsAdaptorHostFcIfFsmEntry 1 }

cucsAdaptorHostFcIfFsmDn OBJECT-TYPE
    SYNTAX       CucsManagedObjectDn
    MAX-ACCESS   read-only
    STATUS       current
    DESCRIPTION
        "Cisco UCS adaptor:HostFcIfFsm:dn managed object property"
    ::= { cucsAdaptorHostFcIfFsmEntry 2 }

cucsAdaptorHostFcIfFsmRn OBJECT-TYPE
    SYNTAX       SnmpAdminString
    MAX-ACCESS   read-only
    STATUS       current
    DESCRIPTION
        "Cisco UCS adaptor:HostFcIfFsm:rn managed object property"
    ::= { cucsAdaptorHostFcIfFsmEntry 3 }

cucsAdaptorHostFcIfFsmCompletionTime OBJECT-TYPE
    SYNTAX       DateAndTime
    MAX-ACCESS   read-only
    STATUS       current
    DESCRIPTION
        "Cisco UCS adaptor:HostFcIfFsm:completionTime managed
        object property"
    ::= { cucsAdaptorHostFcIfFsmEntry 4 }

cucsAdaptorHostFcIfFsmCurrentFsm OBJECT-TYPE
    SYNTAX       CucsAdaptorHostFcIfFsmCurrentFsm
    MAX-ACCESS   read-only
    STATUS       current
    DESCRIPTION
        "Cisco UCS adaptor:HostFcIfFsm:currentFsm managed object property"
    ::= { cucsAdaptorHostFcIfFsmEntry 5 }

cucsAdaptorHostFcIfFsmDescrData OBJECT-TYPE
    SYNTAX       SnmpAdminString
    MAX-ACCESS   read-only
    STATUS       current
    DESCRIPTION
        "Cisco UCS adaptor:HostFcIfFsm:descr managed object property"
    ::= { cucsAdaptorHostFcIfFsmEntry 6 }

cucsAdaptorHostFcIfFsmFsmStatus OBJECT-TYPE
    SYNTAX       CucsFsmFsmStageStatus
    MAX-ACCESS   read-only
    STATUS       current
    DESCRIPTION
        "Cisco UCS adaptor:HostFcIfFsm:fsmStatus managed object property"
    ::= { cucsAdaptorHostFcIfFsmEntry 7 }

cucsAdaptorHostFcIfFsmProgress OBJECT-TYPE
    SYNTAX       Gauge32
    MAX-ACCESS   read-only
    STATUS       current
    DESCRIPTION
        "Cisco UCS adaptor:HostFcIfFsm:progress managed object property"
    ::= { cucsAdaptorHostFcIfFsmEntry 8 }

cucsAdaptorHostFcIfFsmRmtErrCode OBJECT-TYPE
    SYNTAX       Gauge32
    MAX-ACCESS   read-only
    STATUS       current
    DESCRIPTION
        "Cisco UCS adaptor:HostFcIfFsm:rmtErrCode managed object property"
    ::= { cucsAdaptorHostFcIfFsmEntry 9 }

cucsAdaptorHostFcIfFsmRmtErrDescr OBJECT-TYPE
    SYNTAX       SnmpAdminString
    MAX-ACCESS   read-only
    STATUS       current
    DESCRIPTION
        "Cisco UCS adaptor:HostFcIfFsm:rmtErrDescr managed
        object property"
    ::= { cucsAdaptorHostFcIfFsmEntry 10 }

cucsAdaptorHostFcIfFsmRmtRslt OBJECT-TYPE
    SYNTAX       CucsConditionRemoteInvRslt
    MAX-ACCESS   read-only
    STATUS       current
    DESCRIPTION
        "Cisco UCS adaptor:HostFcIfFsm:rmtRslt managed object property"
    ::= { cucsAdaptorHostFcIfFsmEntry 11 }

cucsAdaptorHostFcIfFsmStageTable OBJECT-TYPE
    SYNTAX           SEQUENCE OF CucsAdaptorHostFcIfFsmStageEntry
    MAX-ACCESS       not-accessible
    STATUS           current
    DESCRIPTION
        "Cisco UCS adaptor:HostFcIfFsmStage managed object table"
    ::= { cucsAdaptorObjects 113 }

cucsAdaptorHostFcIfFsmStageEntry OBJECT-TYPE
    SYNTAX           CucsAdaptorHostFcIfFsmStageEntry
    MAX-ACCESS       not-accessible
    STATUS           current
    DESCRIPTION
        "Entry for the cucsAdaptorHostFcIfFsmStageTable table."
    INDEX { cucsAdaptorHostFcIfFsmStageInstanceId }
    ::= { cucsAdaptorHostFcIfFsmStageTable 1 }

CucsAdaptorHostFcIfFsmStageEntry ::= SEQUENCE {
    cucsAdaptorHostFcIfFsmStageInstanceId                            CucsManagedObjectId,
    cucsAdaptorHostFcIfFsmStageDn                                    CucsManagedObjectDn,
    cucsAdaptorHostFcIfFsmStageRn                                    SnmpAdminString,
    cucsAdaptorHostFcIfFsmStageDescrData                             SnmpAdminString,
    cucsAdaptorHostFcIfFsmStageLastUpdateTime                        DateAndTime,
    cucsAdaptorHostFcIfFsmStageName                                  CucsAdaptorHostFcIfFsmStageName,
    cucsAdaptorHostFcIfFsmStageOrder                                 Gauge32,
    cucsAdaptorHostFcIfFsmStageRetry                                 Gauge32,
    cucsAdaptorHostFcIfFsmStageStageStatus                           CucsFsmFsmStageStatus
}

cucsAdaptorHostFcIfFsmStageInstanceId OBJECT-TYPE
    SYNTAX       CucsManagedObjectId
    MAX-ACCESS   not-accessible
    STATUS       current
    DESCRIPTION
        "Instance identifier of the managed object."
    ::= { cucsAdaptorHostFcIfFsmStageEntry 1 }

cucsAdaptorHostFcIfFsmStageDn OBJECT-TYPE
    SYNTAX       CucsManagedObjectDn
    MAX-ACCESS   read-only
    STATUS       current
    DESCRIPTION
        "Cisco UCS adaptor:HostFcIfFsmStage:dn managed object property"
    ::= { cucsAdaptorHostFcIfFsmStageEntry 2 }

cucsAdaptorHostFcIfFsmStageRn OBJECT-TYPE
    SYNTAX       SnmpAdminString
    MAX-ACCESS   read-only
    STATUS       current
    DESCRIPTION
        "Cisco UCS adaptor:HostFcIfFsmStage:rn managed object property"
    ::= { cucsAdaptorHostFcIfFsmStageEntry 3 }

cucsAdaptorHostFcIfFsmStageDescrData OBJECT-TYPE
    SYNTAX       SnmpAdminString
    MAX-ACCESS   read-only
    STATUS       current
    DESCRIPTION
        "Cisco UCS adaptor:HostFcIfFsmStage:descr managed object property"
    ::= { cucsAdaptorHostFcIfFsmStageEntry 4 }

cucsAdaptorHostFcIfFsmStageLastUpdateTime OBJECT-TYPE
    SYNTAX       DateAndTime
    MAX-ACCESS   read-only
    STATUS       current
    DESCRIPTION
        "Cisco UCS adaptor:HostFcIfFsmStage:lastUpdateTime
        managed object property"
    ::= { cucsAdaptorHostFcIfFsmStageEntry 5 }

cucsAdaptorHostFcIfFsmStageName OBJECT-TYPE
    SYNTAX       CucsAdaptorHostFcIfFsmStageName
    MAX-ACCESS   read-only
    STATUS       current
    DESCRIPTION
        "Cisco UCS adaptor:HostFcIfFsmStage:name managed object property"
    ::= { cucsAdaptorHostFcIfFsmStageEntry 6 }

cucsAdaptorHostFcIfFsmStageOrder OBJECT-TYPE
    SYNTAX       Gauge32
    MAX-ACCESS   read-only
    STATUS       current
    DESCRIPTION
        "Cisco UCS adaptor:HostFcIfFsmStage:order managed object property"
    ::= { cucsAdaptorHostFcIfFsmStageEntry 7 }

cucsAdaptorHostFcIfFsmStageRetry OBJECT-TYPE
    SYNTAX       Gauge32
    MAX-ACCESS   read-only
    STATUS       current
    DESCRIPTION
        "Cisco UCS adaptor:HostFcIfFsmStage:retry managed object property"
    ::= { cucsAdaptorHostFcIfFsmStageEntry 8 }

cucsAdaptorHostFcIfFsmStageStageStatus OBJECT-TYPE
    SYNTAX       CucsFsmFsmStageStatus
    MAX-ACCESS   read-only
    STATUS       current
    DESCRIPTION
        "Cisco UCS adaptor:HostFcIfFsmStage:stageStatus
        managed object property"
    ::= { cucsAdaptorHostFcIfFsmStageEntry 9 }

cucsAdaptorHostFcIfFsmTaskTable OBJECT-TYPE
    SYNTAX           SEQUENCE OF CucsAdaptorHostFcIfFsmTaskEntry
    MAX-ACCESS       not-accessible
    STATUS           current
    DESCRIPTION
        "Cisco UCS adaptor:HostFcIfFsmTask managed object table"
    ::= { cucsAdaptorObjects 49 }

cucsAdaptorHostFcIfFsmTaskEntry OBJECT-TYPE
    SYNTAX           CucsAdaptorHostFcIfFsmTaskEntry
    MAX-ACCESS       not-accessible
    STATUS           current
    DESCRIPTION
        "Entry for the cucsAdaptorHostFcIfFsmTaskTable table."
    INDEX { cucsAdaptorHostFcIfFsmTaskInstanceId }
    ::= { cucsAdaptorHostFcIfFsmTaskTable 1 }

CucsAdaptorHostFcIfFsmTaskEntry ::= SEQUENCE {
    cucsAdaptorHostFcIfFsmTaskInstanceId                             CucsManagedObjectId,
    cucsAdaptorHostFcIfFsmTaskDn                                     CucsManagedObjectDn,
    cucsAdaptorHostFcIfFsmTaskRn                                     SnmpAdminString,
    cucsAdaptorHostFcIfFsmTaskCompletion                             CucsFsmCompletion,
    cucsAdaptorHostFcIfFsmTaskFlags                                  CucsFsmFlags,
    cucsAdaptorHostFcIfFsmTaskItem                                   CucsAdaptorHostFcIfFsmTaskItem,
    cucsAdaptorHostFcIfFsmTaskSeqId                                  Gauge32
}

cucsAdaptorHostFcIfFsmTaskInstanceId OBJECT-TYPE
    SYNTAX       CucsManagedObjectId
    MAX-ACCESS   not-accessible
    STATUS       current
    DESCRIPTION
        "Instance identifier of the managed object."
    ::= { cucsAdaptorHostFcIfFsmTaskEntry 1 }

cucsAdaptorHostFcIfFsmTaskDn OBJECT-TYPE
    SYNTAX       CucsManagedObjectDn
    MAX-ACCESS   read-only
    STATUS       current
    DESCRIPTION
        "Cisco UCS adaptor:HostFcIfFsmTask:dn managed object property"
    ::= { cucsAdaptorHostFcIfFsmTaskEntry 2 }

cucsAdaptorHostFcIfFsmTaskRn OBJECT-TYPE
    SYNTAX       SnmpAdminString
    MAX-ACCESS   read-only
    STATUS       current
    DESCRIPTION
        "Cisco UCS adaptor:HostFcIfFsmTask:rn managed object property"
    ::= { cucsAdaptorHostFcIfFsmTaskEntry 3 }

cucsAdaptorHostFcIfFsmTaskCompletion OBJECT-TYPE
    SYNTAX       CucsFsmCompletion
    MAX-ACCESS   read-only
    STATUS       current
    DESCRIPTION
        "Cisco UCS adaptor:HostFcIfFsmTask:completion managed
        object property"
    ::= { cucsAdaptorHostFcIfFsmTaskEntry 4 }

cucsAdaptorHostFcIfFsmTaskFlags OBJECT-TYPE
    SYNTAX       CucsFsmFlags
    MAX-ACCESS   read-only
    STATUS       current
    DESCRIPTION
        "Cisco UCS adaptor:HostFcIfFsmTask:flags managed object property"
    ::= { cucsAdaptorHostFcIfFsmTaskEntry 5 }

cucsAdaptorHostFcIfFsmTaskItem OBJECT-TYPE
    SYNTAX       CucsAdaptorHostFcIfFsmTaskItem
    MAX-ACCESS   read-only
    STATUS       current
    DESCRIPTION
        "Cisco UCS adaptor:HostFcIfFsmTask:item managed object property"
    ::= { cucsAdaptorHostFcIfFsmTaskEntry 6 }

cucsAdaptorHostFcIfFsmTaskSeqId OBJECT-TYPE
    SYNTAX       Gauge32
    MAX-ACCESS   read-only
    STATUS       current
    DESCRIPTION
        "Cisco UCS adaptor:HostFcIfFsmTask:seqId managed object property"
    ::= { cucsAdaptorHostFcIfFsmTaskEntry 7 }

cucsAdaptorHostFcIfProfileTable OBJECT-TYPE
    SYNTAX           SEQUENCE OF CucsAdaptorHostFcIfProfileEntry
    MAX-ACCESS       not-accessible
    STATUS           current
    DESCRIPTION
        "Cisco UCS adaptor:HostFcIfProfile managed object table"
    ::= { cucsAdaptorObjects 50 }

cucsAdaptorHostFcIfProfileEntry OBJECT-TYPE
    SYNTAX           CucsAdaptorHostFcIfProfileEntry
    MAX-ACCESS       not-accessible
    STATUS           current
    DESCRIPTION
        "Entry for the cucsAdaptorHostFcIfProfileTable table."
    INDEX { cucsAdaptorHostFcIfProfileInstanceId }
    ::= { cucsAdaptorHostFcIfProfileTable 1 }

CucsAdaptorHostFcIfProfileEntry ::= SEQUENCE {
    cucsAdaptorHostFcIfProfileInstanceId                             CucsManagedObjectId,
    cucsAdaptorHostFcIfProfileDn                                     CucsManagedObjectDn,
    cucsAdaptorHostFcIfProfileRn                                     SnmpAdminString,
    cucsAdaptorHostFcIfProfileDescr                                  SnmpAdminString,
    cucsAdaptorHostFcIfProfileIntId                                  SnmpAdminString,
    cucsAdaptorHostFcIfProfileName                                   SnmpAdminString,
    cucsAdaptorHostFcIfProfilePolicyLevel                            Gauge32,
    cucsAdaptorHostFcIfProfilePolicyOwner                            CucsPolicyPolicyOwner
}

cucsAdaptorHostFcIfProfileInstanceId OBJECT-TYPE
    SYNTAX       CucsManagedObjectId
    MAX-ACCESS   not-accessible
    STATUS       current
    DESCRIPTION
        "Instance identifier of the managed object."
    ::= { cucsAdaptorHostFcIfProfileEntry 1 }

cucsAdaptorHostFcIfProfileDn OBJECT-TYPE
    SYNTAX       CucsManagedObjectDn
    MAX-ACCESS   read-only
    STATUS       current
    DESCRIPTION
        "Cisco UCS adaptor:HostFcIfProfile:dn managed object property"
    ::= { cucsAdaptorHostFcIfProfileEntry 2 }

cucsAdaptorHostFcIfProfileRn OBJECT-TYPE
    SYNTAX       SnmpAdminString
    MAX-ACCESS   read-only
    STATUS       current
    DESCRIPTION
        "Cisco UCS adaptor:HostFcIfProfile:rn managed object property"
    ::= { cucsAdaptorHostFcIfProfileEntry 3 }

cucsAdaptorHostFcIfProfileDescr OBJECT-TYPE
    SYNTAX       SnmpAdminString
    MAX-ACCESS   read-only
    STATUS       current
    DESCRIPTION
        "Cisco UCS adaptor:HostFcIfProfile:descr managed object property"
    ::= { cucsAdaptorHostFcIfProfileEntry 4 }

cucsAdaptorHostFcIfProfileIntId OBJECT-TYPE
    SYNTAX       SnmpAdminString
    MAX-ACCESS   read-only
    STATUS       current
    DESCRIPTION
        "Cisco UCS adaptor:HostFcIfProfile:intId managed object property"
    ::= { cucsAdaptorHostFcIfProfileEntry 5 }

cucsAdaptorHostFcIfProfileName OBJECT-TYPE
    SYNTAX       SnmpAdminString
    MAX-ACCESS   read-only
    STATUS       current
    DESCRIPTION
        "Cisco UCS adaptor:HostFcIfProfile:name managed object property"
    ::= { cucsAdaptorHostFcIfProfileEntry 6 }

cucsAdaptorHostFcIfProfilePolicyLevel OBJECT-TYPE
    SYNTAX       Gauge32
    MAX-ACCESS   read-only
    STATUS       current
    DESCRIPTION
        "Cisco UCS adaptor:HostFcIfProfile:policyLevel
        managed object property"
    ::= { cucsAdaptorHostFcIfProfileEntry 7 }

cucsAdaptorHostFcIfProfilePolicyOwner OBJECT-TYPE
    SYNTAX       CucsPolicyPolicyOwner
    MAX-ACCESS   read-only
    STATUS       current
    DESCRIPTION
        "Cisco UCS adaptor:HostFcIfProfile:policyOwner
        managed object property"
    ::= { cucsAdaptorHostFcIfProfileEntry 8 }

cucsAdaptorHostIfConfigTable OBJECT-TYPE
    SYNTAX           SEQUENCE OF CucsAdaptorHostIfConfigEntry
    MAX-ACCESS       not-accessible
    STATUS           current
    DESCRIPTION
        "Cisco UCS adaptor:HostIfConfig managed object table"
    ::= { cucsAdaptorObjects 134 }

cucsAdaptorHostIfConfigEntry OBJECT-TYPE
    SYNTAX           CucsAdaptorHostIfConfigEntry
    MAX-ACCESS       not-accessible
    STATUS           current
    DESCRIPTION
        "Entry for the cucsAdaptorHostIfConfigTable table."
    INDEX { cucsAdaptorHostIfConfigInstanceId }
    ::= { cucsAdaptorHostIfConfigTable 1 }

CucsAdaptorHostIfConfigEntry ::= SEQUENCE {
    cucsAdaptorHostIfConfigInstanceId                                CucsManagedObjectId,
    cucsAdaptorHostIfConfigDn                                        CucsManagedObjectDn,
    cucsAdaptorHostIfConfigRn                                        SnmpAdminString,
    cucsAdaptorHostIfConfigAdminState                                CucsAdaptorAdminState,
    cucsAdaptorHostIfConfigId                                        Gauge32,
    cucsAdaptorHostIfConfigName                                      SnmpAdminString,
    cucsAdaptorHostIfConfigTransport                                 CucsNetworkTransport
}

cucsAdaptorHostIfConfigInstanceId OBJECT-TYPE
    SYNTAX       CucsManagedObjectId
    MAX-ACCESS   not-accessible
    STATUS       current
    DESCRIPTION
        "Instance identifier of the managed object."
    ::= { cucsAdaptorHostIfConfigEntry 1 }

cucsAdaptorHostIfConfigDn OBJECT-TYPE
    SYNTAX       CucsManagedObjectDn
    MAX-ACCESS   read-only
    STATUS       current
    DESCRIPTION
        "Cisco UCS adaptor:HostIfConfig:dn managed object property"
    ::= { cucsAdaptorHostIfConfigEntry 2 }

cucsAdaptorHostIfConfigRn OBJECT-TYPE
    SYNTAX       SnmpAdminString
    MAX-ACCESS   read-only
    STATUS       current
    DESCRIPTION
        "Cisco UCS adaptor:HostIfConfig:rn managed object property"
    ::= { cucsAdaptorHostIfConfigEntry 3 }

cucsAdaptorHostIfConfigAdminState OBJECT-TYPE
    SYNTAX       CucsAdaptorAdminState
    MAX-ACCESS   read-only
    STATUS       current
    DESCRIPTION
        "Cisco UCS adaptor:HostIfConfig:adminState managed
        object property"
    ::= { cucsAdaptorHostIfConfigEntry 4 }

cucsAdaptorHostIfConfigId OBJECT-TYPE
    SYNTAX       Gauge32
    MAX-ACCESS   read-only
    STATUS       current
    DESCRIPTION
        "Cisco UCS adaptor:HostIfConfig:id managed object property"
    ::= { cucsAdaptorHostIfConfigEntry 5 }

cucsAdaptorHostIfConfigName OBJECT-TYPE
    SYNTAX       SnmpAdminString
    MAX-ACCESS   read-only
    STATUS       current
    DESCRIPTION
        "Cisco UCS adaptor:HostIfConfig:name managed object property"
    ::= { cucsAdaptorHostIfConfigEntry 6 }

cucsAdaptorHostIfConfigTransport OBJECT-TYPE
    SYNTAX       CucsNetworkTransport
    MAX-ACCESS   read-only
    STATUS       current
    DESCRIPTION
        "Cisco UCS adaptor:HostIfConfig:transport managed object property"
    ::= { cucsAdaptorHostIfConfigEntry 7 }

cucsAdaptorHostIscsiIfTable OBJECT-TYPE
    SYNTAX           SEQUENCE OF CucsAdaptorHostIscsiIfEntry
    MAX-ACCESS       not-accessible
    STATUS           current
    DESCRIPTION
        "Cisco UCS adaptor:HostIscsiIf managed object table"
    ::= { cucsAdaptorObjects 99 }

cucsAdaptorHostIscsiIfEntry OBJECT-TYPE
    SYNTAX           CucsAdaptorHostIscsiIfEntry
    MAX-ACCESS       not-accessible
    STATUS           current
    DESCRIPTION
        "Entry for the cucsAdaptorHostIscsiIfTable table."
    INDEX { cucsAdaptorHostIscsiIfInstanceId }
    ::= { cucsAdaptorHostIscsiIfTable 1 }

CucsAdaptorHostIscsiIfEntry ::= SEQUENCE {
    cucsAdaptorHostIscsiIfInstanceId                                 CucsManagedObjectId,
    cucsAdaptorHostIscsiIfDn                                         CucsManagedObjectDn,
    cucsAdaptorHostIscsiIfRn                                         SnmpAdminString,
    cucsAdaptorHostIscsiIfAdminState                                 CucsAdaptorHostIfAdminState,
    cucsAdaptorHostIscsiIfBootDev                                    CucsAdaptorHostIfBootDev,
    cucsAdaptorHostIscsiIfChassisId                                  Gauge32,
    cucsAdaptorHostIscsiIfDiscovery                                  CucsEtherSatelliteConnectionDisc,
    cucsAdaptorHostIscsiIfEpDn                                       SnmpAdminString,
    cucsAdaptorHostIscsiIfEthEpDn                                    SnmpAdminString,
    cucsAdaptorHostIscsiIfFltAggr                                    Unsigned64,
    cucsAdaptorHostIscsiIfHostVisible                                CucsAdaptorHostVisibility,
    cucsAdaptorHostIscsiIfId                                         Gauge32,
    cucsAdaptorHostIscsiIfIfRole                                     CucsNetworkPortRole,
    cucsAdaptorHostIscsiIfIfType                                     CucsNetworkPhysEpIfType,
    cucsAdaptorHostIscsiIfInitiatorName                              SnmpAdminString,
    cucsAdaptorHostIscsiIfLc                                         CucsFsmLifecycle,
    cucsAdaptorHostIscsiIfLinkState                                  CucsAdaptorLinkState,
    cucsAdaptorHostIscsiIfLocale                                     CucsNetworkLocale,
    cucsAdaptorHostIscsiIfMac                                        MacAddress,
    cucsAdaptorHostIscsiIfModel                                      SnmpAdminString,
    cucsAdaptorHostIscsiIfName                                       SnmpAdminString,
    cucsAdaptorHostIscsiIfOperState                                  CucsEquipmentOperability,
    cucsAdaptorHostIscsiIfOperability                                CucsEquipmentOperability,
    cucsAdaptorHostIscsiIfOrder                                      Gauge32,
    cucsAdaptorHostIscsiIfOriginalMac                                MacAddress,
    cucsAdaptorHostIscsiIfPciAddr                                    SnmpAdminString,
    cucsAdaptorHostIscsiIfPciFunc                                    Gauge32,
    cucsAdaptorHostIscsiIfPciSlot                                    Gauge32,
    cucsAdaptorHostIscsiIfPeerChassisId                              Gauge32,
    cucsAdaptorHostIscsiIfPeerDn                                     SnmpAdminString,
    cucsAdaptorHostIscsiIfPeerPortId                                 Gauge32,
    cucsAdaptorHostIscsiIfPeerSlotId                                 Gauge32,
    cucsAdaptorHostIscsiIfPerf                                       CucsEquipmentSensorThresholdStatus,
    cucsAdaptorHostIscsiIfPortId                                     Gauge32,
    cucsAdaptorHostIscsiIfPower                                      CucsEquipmentPowerState,
    cucsAdaptorHostIscsiIfPresence                                   CucsEquipmentPresence,
    cucsAdaptorHostIscsiIfPurpose                                    CucsAdaptorPurpose,
    cucsAdaptorHostIscsiIfRevision                                   SnmpAdminString,
    cucsAdaptorHostIscsiIfSerial                                     SnmpAdminString,
    cucsAdaptorHostIscsiIfSide                                       CucsNetworkSide,
    cucsAdaptorHostIscsiIfSlotId                                     Gauge32,
    cucsAdaptorHostIscsiIfSwitchId                                   CucsNetworkSwitchId,
    cucsAdaptorHostIscsiIfThermal                                    CucsEquipmentSensorThresholdStatus,
    cucsAdaptorHostIscsiIfTransport                                  CucsNetworkTransport,
    cucsAdaptorHostIscsiIfType                                       CucsNetworkConnectionType,
    cucsAdaptorHostIscsiIfVendor                                     SnmpAdminString,
    cucsAdaptorHostIscsiIfVnicDn                                     SnmpAdminString,
    cucsAdaptorHostIscsiIfVnicName                                   SnmpAdminString,
    cucsAdaptorHostIscsiIfVoltage                                    CucsEquipmentSensorThresholdStatus,
    cucsAdaptorHostIscsiIfOperQualifierReason                        SnmpAdminString,
    cucsAdaptorHostIscsiIfCdnName                                    SnmpAdminString
}

cucsAdaptorHostIscsiIfInstanceId OBJECT-TYPE
    SYNTAX       CucsManagedObjectId
    MAX-ACCESS   not-accessible
    STATUS       current
    DESCRIPTION
        "Instance identifier of the managed object."
    ::= { cucsAdaptorHostIscsiIfEntry 1 }

cucsAdaptorHostIscsiIfDn OBJECT-TYPE
    SYNTAX       CucsManagedObjectDn
    MAX-ACCESS   read-only
    STATUS       current
    DESCRIPTION
        "Cisco UCS adaptor:HostIscsiIf:dn managed object property"
    ::= { cucsAdaptorHostIscsiIfEntry 2 }

cucsAdaptorHostIscsiIfRn OBJECT-TYPE
    SYNTAX       SnmpAdminString
    MAX-ACCESS   read-only
    STATUS       current
    DESCRIPTION
        "Cisco UCS adaptor:HostIscsiIf:rn managed object property"
    ::= { cucsAdaptorHostIscsiIfEntry 3 }

cucsAdaptorHostIscsiIfAdminState OBJECT-TYPE
    SYNTAX       CucsAdaptorHostIfAdminState
    MAX-ACCESS   read-only
    STATUS       current
    DESCRIPTION
        "Cisco UCS adaptor:HostIscsiIf:adminState managed object property"
    ::= { cucsAdaptorHostIscsiIfEntry 4 }

cucsAdaptorHostIscsiIfBootDev OBJECT-TYPE
    SYNTAX       CucsAdaptorHostIfBootDev
    MAX-ACCESS   read-only
    STATUS       current
    DESCRIPTION
        "Cisco UCS adaptor:HostIscsiIf:bootDev managed object property"
    ::= { cucsAdaptorHostIscsiIfEntry 5 }

cucsAdaptorHostIscsiIfChassisId OBJECT-TYPE
    SYNTAX       Gauge32
    MAX-ACCESS   read-only
    STATUS       current
    DESCRIPTION
        "Cisco UCS adaptor:HostIscsiIf:chassisId managed object property"
    ::= { cucsAdaptorHostIscsiIfEntry 6 }

cucsAdaptorHostIscsiIfDiscovery OBJECT-TYPE
    SYNTAX       CucsEtherSatelliteConnectionDisc
    MAX-ACCESS   read-only
    STATUS       current
    DESCRIPTION
        "Cisco UCS adaptor:HostIscsiIf:discovery managed object property"
    ::= { cucsAdaptorHostIscsiIfEntry 7 }

cucsAdaptorHostIscsiIfEpDn OBJECT-TYPE
    SYNTAX       SnmpAdminString
    MAX-ACCESS   read-only
    STATUS       current
    DESCRIPTION
        "Cisco UCS adaptor:HostIscsiIf:epDn managed object property"
    ::= { cucsAdaptorHostIscsiIfEntry 8 }

cucsAdaptorHostIscsiIfEthEpDn OBJECT-TYPE
    SYNTAX       SnmpAdminString
    MAX-ACCESS   read-only
    STATUS       current
    DESCRIPTION
        "Cisco UCS adaptor:HostIscsiIf:ethEpDn managed object property"
    ::= { cucsAdaptorHostIscsiIfEntry 9 }

cucsAdaptorHostIscsiIfFltAggr OBJECT-TYPE
    SYNTAX       Unsigned64
    MAX-ACCESS   read-only
    STATUS       current
    DESCRIPTION
        "Cisco UCS adaptor:HostIscsiIf:fltAggr managed object property"
    ::= { cucsAdaptorHostIscsiIfEntry 10 }

cucsAdaptorHostIscsiIfHostVisible OBJECT-TYPE
    SYNTAX       CucsAdaptorHostVisibility
    MAX-ACCESS   read-only
    STATUS       current
    DESCRIPTION
        "Cisco UCS adaptor:HostIscsiIf:hostVisible managed
        object property"
    ::= { cucsAdaptorHostIscsiIfEntry 11 }

cucsAdaptorHostIscsiIfId OBJECT-TYPE
    SYNTAX       Gauge32
    MAX-ACCESS   read-only
    STATUS       current
    DESCRIPTION
        "Cisco UCS adaptor:HostIscsiIf:id managed object property"
    ::= { cucsAdaptorHostIscsiIfEntry 12 }

cucsAdaptorHostIscsiIfIfRole OBJECT-TYPE
    SYNTAX       CucsNetworkPortRole
    MAX-ACCESS   read-only
    STATUS       current
    DESCRIPTION
        "Cisco UCS adaptor:HostIscsiIf:ifRole managed object property"
    ::= { cucsAdaptorHostIscsiIfEntry 13 }

cucsAdaptorHostIscsiIfIfType OBJECT-TYPE
    SYNTAX       CucsNetworkPhysEpIfType
    MAX-ACCESS   read-only
    STATUS       current
    DESCRIPTION
        "Cisco UCS adaptor:HostIscsiIf:ifType managed object property"
    ::= { cucsAdaptorHostIscsiIfEntry 14 }

cucsAdaptorHostIscsiIfInitiatorName OBJECT-TYPE
    SYNTAX       SnmpAdminString
    MAX-ACCESS   read-only
    STATUS       current
    DESCRIPTION
        "Cisco UCS adaptor:HostIscsiIf:initiatorName managed
        object property"
    ::= { cucsAdaptorHostIscsiIfEntry 15 }

cucsAdaptorHostIscsiIfLc OBJECT-TYPE
    SYNTAX       CucsFsmLifecycle
    MAX-ACCESS   read-only
    STATUS       current
    DESCRIPTION
        "Cisco UCS adaptor:HostIscsiIf:lc managed object property"
    ::= { cucsAdaptorHostIscsiIfEntry 16 }

cucsAdaptorHostIscsiIfLinkState OBJECT-TYPE
    SYNTAX       CucsAdaptorLinkState
    MAX-ACCESS   read-only
    STATUS       current
    DESCRIPTION
        "Cisco UCS adaptor:HostIscsiIf:linkState managed object property"
    ::= { cucsAdaptorHostIscsiIfEntry 17 }

cucsAdaptorHostIscsiIfLocale OBJECT-TYPE
    SYNTAX       CucsNetworkLocale
    MAX-ACCESS   read-only
    STATUS       current
    DESCRIPTION
        "Cisco UCS adaptor:HostIscsiIf:locale managed object property"
    ::= { cucsAdaptorHostIscsiIfEntry 18 }

cucsAdaptorHostIscsiIfMac OBJECT-TYPE
    SYNTAX       MacAddress
    MAX-ACCESS   read-only
    STATUS       current
    DESCRIPTION
        "Cisco UCS adaptor:HostIscsiIf:mac managed object property"
    ::= { cucsAdaptorHostIscsiIfEntry 19 }

cucsAdaptorHostIscsiIfModel OBJECT-TYPE
    SYNTAX       SnmpAdminString
    MAX-ACCESS   read-only
    STATUS       current
    DESCRIPTION
        "Cisco UCS adaptor:HostIscsiIf:model managed object property"
    ::= { cucsAdaptorHostIscsiIfEntry 20 }

cucsAdaptorHostIscsiIfName OBJECT-TYPE
    SYNTAX       SnmpAdminString
    MAX-ACCESS   read-only
    STATUS       current
    DESCRIPTION
        "Cisco UCS adaptor:HostIscsiIf:name managed object property"
    ::= { cucsAdaptorHostIscsiIfEntry 21 }

cucsAdaptorHostIscsiIfOperState OBJECT-TYPE
    SYNTAX       CucsEquipmentOperability
    MAX-ACCESS   read-only
    STATUS       current
    DESCRIPTION
        "Cisco UCS adaptor:HostIscsiIf:operState managed object property"
    ::= { cucsAdaptorHostIscsiIfEntry 22 }

cucsAdaptorHostIscsiIfOperability OBJECT-TYPE
    SYNTAX       CucsEquipmentOperability
    MAX-ACCESS   read-only
    STATUS       current
    DESCRIPTION
        "Cisco UCS adaptor:HostIscsiIf:operability managed
        object property"
    ::= { cucsAdaptorHostIscsiIfEntry 23 }

cucsAdaptorHostIscsiIfOrder OBJECT-TYPE
    SYNTAX       Gauge32
    MAX-ACCESS   read-only
    STATUS       current
    DESCRIPTION
        "Cisco UCS adaptor:HostIscsiIf:order managed object property"
    ::= { cucsAdaptorHostIscsiIfEntry 24 }

cucsAdaptorHostIscsiIfOriginalMac OBJECT-TYPE
    SYNTAX       MacAddress
    MAX-ACCESS   read-only
    STATUS       current
    DESCRIPTION
        "Cisco UCS adaptor:HostIscsiIf:originalMac managed
        object property"
    ::= { cucsAdaptorHostIscsiIfEntry 25 }

cucsAdaptorHostIscsiIfPciAddr OBJECT-TYPE
    SYNTAX       SnmpAdminString
    MAX-ACCESS   read-only
    STATUS       current
    DESCRIPTION
        "Cisco UCS adaptor:HostIscsiIf:pciAddr managed object property"
    ::= { cucsAdaptorHostIscsiIfEntry 26 }

cucsAdaptorHostIscsiIfPciFunc OBJECT-TYPE
    SYNTAX       Gauge32
    MAX-ACCESS   read-only
    STATUS       current
    DESCRIPTION
        "Cisco UCS adaptor:HostIscsiIf:pciFunc managed object property"
    ::= { cucsAdaptorHostIscsiIfEntry 27 }

cucsAdaptorHostIscsiIfPciSlot OBJECT-TYPE
    SYNTAX       Gauge32
    MAX-ACCESS   read-only
    STATUS       current
    DESCRIPTION
        "Cisco UCS adaptor:HostIscsiIf:pciSlot managed object property"
    ::= { cucsAdaptorHostIscsiIfEntry 28 }

cucsAdaptorHostIscsiIfPeerChassisId OBJECT-TYPE
    SYNTAX       Gauge32
    MAX-ACCESS   read-only
    STATUS       current
    DESCRIPTION
        "Cisco UCS adaptor:HostIscsiIf:peerChassisId managed
        object property"
    ::= { cucsAdaptorHostIscsiIfEntry 29 }

cucsAdaptorHostIscsiIfPeerDn OBJECT-TYPE
    SYNTAX       SnmpAdminString
    MAX-ACCESS   read-only
    STATUS       current
    DESCRIPTION
        "Cisco UCS adaptor:HostIscsiIf:peerDn managed object property"
    ::= { cucsAdaptorHostIscsiIfEntry 30 }

cucsAdaptorHostIscsiIfPeerPortId OBJECT-TYPE
    SYNTAX       Gauge32
    MAX-ACCESS   read-only
    STATUS       current
    DESCRIPTION
        "Cisco UCS adaptor:HostIscsiIf:peerPortId managed object property"
    ::= { cucsAdaptorHostIscsiIfEntry 31 }

cucsAdaptorHostIscsiIfPeerSlotId OBJECT-TYPE
    SYNTAX       Gauge32
    MAX-ACCESS   read-only
    STATUS       current
    DESCRIPTION
        "Cisco UCS adaptor:HostIscsiIf:peerSlotId managed object property"
    ::= { cucsAdaptorHostIscsiIfEntry 32 }

cucsAdaptorHostIscsiIfPerf OBJECT-TYPE
    SYNTAX       CucsEquipmentSensorThresholdStatus
    MAX-ACCESS   read-only
    STATUS       current
    DESCRIPTION
        "Cisco UCS adaptor:HostIscsiIf:perf managed object property"
    ::= { cucsAdaptorHostIscsiIfEntry 33 }

cucsAdaptorHostIscsiIfPortId OBJECT-TYPE
    SYNTAX       Gauge32
    MAX-ACCESS   read-only
    STATUS       current
    DESCRIPTION
        "Cisco UCS adaptor:HostIscsiIf:portId managed object property"
    ::= { cucsAdaptorHostIscsiIfEntry 34 }

cucsAdaptorHostIscsiIfPower OBJECT-TYPE
    SYNTAX       CucsEquipmentPowerState
    MAX-ACCESS   read-only
    STATUS       current
    DESCRIPTION
        "Cisco UCS adaptor:HostIscsiIf:power managed object property"
    ::= { cucsAdaptorHostIscsiIfEntry 35 }

cucsAdaptorHostIscsiIfPresence OBJECT-TYPE
    SYNTAX       CucsEquipmentPresence
    MAX-ACCESS   read-only
    STATUS       current
    DESCRIPTION
        "Cisco UCS adaptor:HostIscsiIf:presence managed object property"
    ::= { cucsAdaptorHostIscsiIfEntry 36 }

cucsAdaptorHostIscsiIfPurpose OBJECT-TYPE
    SYNTAX       CucsAdaptorPurpose
    MAX-ACCESS   read-only
    STATUS       current
    DESCRIPTION
        "Cisco UCS adaptor:HostIscsiIf:purpose managed object property"
    ::= { cucsAdaptorHostIscsiIfEntry 37 }

cucsAdaptorHostIscsiIfRevision OBJECT-TYPE
    SYNTAX       SnmpAdminString
    MAX-ACCESS   read-only
    STATUS       current
    DESCRIPTION
        "Cisco UCS adaptor:HostIscsiIf:revision managed object property"
    ::= { cucsAdaptorHostIscsiIfEntry 38 }

cucsAdaptorHostIscsiIfSerial OBJECT-TYPE
    SYNTAX       SnmpAdminString
    MAX-ACCESS   read-only
    STATUS       current
    DESCRIPTION
        "Cisco UCS adaptor:HostIscsiIf:serial managed object property"
    ::= { cucsAdaptorHostIscsiIfEntry 39 }

cucsAdaptorHostIscsiIfSide OBJECT-TYPE
    SYNTAX       CucsNetworkSide
    MAX-ACCESS   read-only
    STATUS       current
    DESCRIPTION
        "Cisco UCS adaptor:HostIscsiIf:side managed object property"
    ::= { cucsAdaptorHostIscsiIfEntry 40 }

cucsAdaptorHostIscsiIfSlotId OBJECT-TYPE
    SYNTAX       Gauge32
    MAX-ACCESS   read-only
    STATUS       current
    DESCRIPTION
        "Cisco UCS adaptor:HostIscsiIf:slotId managed object property"
    ::= { cucsAdaptorHostIscsiIfEntry 41 }

cucsAdaptorHostIscsiIfSwitchId OBJECT-TYPE
    SYNTAX       CucsNetworkSwitchId
    MAX-ACCESS   read-only
    STATUS       current
    DESCRIPTION
        "Cisco UCS adaptor:HostIscsiIf:switchId managed object property"
    ::= { cucsAdaptorHostIscsiIfEntry 42 }

cucsAdaptorHostIscsiIfThermal OBJECT-TYPE
    SYNTAX       CucsEquipmentSensorThresholdStatus
    MAX-ACCESS   read-only
    STATUS       current
    DESCRIPTION
        "Cisco UCS adaptor:HostIscsiIf:thermal managed object property"
    ::= { cucsAdaptorHostIscsiIfEntry 43 }

cucsAdaptorHostIscsiIfTransport OBJECT-TYPE
    SYNTAX       CucsNetworkTransport
    MAX-ACCESS   read-only
    STATUS       current
    DESCRIPTION
        "Cisco UCS adaptor:HostIscsiIf:transport managed object property"
    ::= { cucsAdaptorHostIscsiIfEntry 44 }

cucsAdaptorHostIscsiIfType OBJECT-TYPE
    SYNTAX       CucsNetworkConnectionType
    MAX-ACCESS   read-only
    STATUS       current
    DESCRIPTION
        "Cisco UCS adaptor:HostIscsiIf:type managed object property"
    ::= { cucsAdaptorHostIscsiIfEntry 45 }

cucsAdaptorHostIscsiIfVendor OBJECT-TYPE
    SYNTAX       SnmpAdminString
    MAX-ACCESS   read-only
    STATUS       current
    DESCRIPTION
        "Cisco UCS adaptor:HostIscsiIf:vendor managed object property"
    ::= { cucsAdaptorHostIscsiIfEntry 46 }

cucsAdaptorHostIscsiIfVnicDn OBJECT-TYPE
    SYNTAX       SnmpAdminString
    MAX-ACCESS   read-only
    STATUS       current
    DESCRIPTION
        "Cisco UCS adaptor:HostIscsiIf:vnicDn managed object property"
    ::= { cucsAdaptorHostIscsiIfEntry 47 }

cucsAdaptorHostIscsiIfVnicName OBJECT-TYPE
    SYNTAX       SnmpAdminString
    MAX-ACCESS   read-only
    STATUS       current
    DESCRIPTION
        "Cisco UCS adaptor:HostIscsiIf:vnicName managed object property"
    ::= { cucsAdaptorHostIscsiIfEntry 48 }

cucsAdaptorHostIscsiIfVoltage OBJECT-TYPE
    SYNTAX       CucsEquipmentSensorThresholdStatus
    MAX-ACCESS   read-only
    STATUS       current
    DESCRIPTION
        "Cisco UCS adaptor:HostIscsiIf:voltage managed object property"
    ::= { cucsAdaptorHostIscsiIfEntry 49 }

cucsAdaptorHostIscsiIfOperQualifierReason OBJECT-TYPE
    SYNTAX       SnmpAdminString
    MAX-ACCESS   read-only
    STATUS       current
    DESCRIPTION
        "Cisco UCS adaptor:HostIscsiIf:operQualifierReason
        managed object property"
    ::= { cucsAdaptorHostIscsiIfEntry 50 }

cucsAdaptorHostIscsiIfCdnName OBJECT-TYPE
    SYNTAX       SnmpAdminString
    MAX-ACCESS   read-only
    STATUS       current
    DESCRIPTION
        "Cisco UCS adaptor:HostIscsiIf:cdnName managed object property"
    ::= { cucsAdaptorHostIscsiIfEntry 51 }

cucsAdaptorHostIscsiIfProfileTable OBJECT-TYPE
    SYNTAX           SEQUENCE OF CucsAdaptorHostIscsiIfProfileEntry
    MAX-ACCESS       not-accessible
    STATUS           current
    DESCRIPTION
        "Cisco UCS adaptor:HostIscsiIfProfile managed object table"
    ::= { cucsAdaptorObjects 100 }

cucsAdaptorHostIscsiIfProfileEntry OBJECT-TYPE
    SYNTAX           CucsAdaptorHostIscsiIfProfileEntry
    MAX-ACCESS       not-accessible
    STATUS           current
    DESCRIPTION
        "Entry for the cucsAdaptorHostIscsiIfProfileTable table."
    INDEX { cucsAdaptorHostIscsiIfProfileInstanceId }
    ::= { cucsAdaptorHostIscsiIfProfileTable 1 }

CucsAdaptorHostIscsiIfProfileEntry ::= SEQUENCE {
    cucsAdaptorHostIscsiIfProfileInstanceId                          CucsManagedObjectId,
    cucsAdaptorHostIscsiIfProfileDn                                  CucsManagedObjectDn,
    cucsAdaptorHostIscsiIfProfileRn                                  SnmpAdminString,
    cucsAdaptorHostIscsiIfProfileDescr                               SnmpAdminString,
    cucsAdaptorHostIscsiIfProfileIntId                               SnmpAdminString,
    cucsAdaptorHostIscsiIfProfileName                                SnmpAdminString,
    cucsAdaptorHostIscsiIfProfilePolicyLevel                         Gauge32,
    cucsAdaptorHostIscsiIfProfilePolicyOwner                         CucsPolicyPolicyOwner
}

cucsAdaptorHostIscsiIfProfileInstanceId OBJECT-TYPE
    SYNTAX       CucsManagedObjectId
    MAX-ACCESS   not-accessible
    STATUS       current
    DESCRIPTION
        "Instance identifier of the managed object."
    ::= { cucsAdaptorHostIscsiIfProfileEntry 1 }

cucsAdaptorHostIscsiIfProfileDn OBJECT-TYPE
    SYNTAX       CucsManagedObjectDn
    MAX-ACCESS   read-only
    STATUS       current
    DESCRIPTION
        "Cisco UCS adaptor:HostIscsiIfProfile:dn managed object property"
    ::= { cucsAdaptorHostIscsiIfProfileEntry 2 }

cucsAdaptorHostIscsiIfProfileRn OBJECT-TYPE
    SYNTAX       SnmpAdminString
    MAX-ACCESS   read-only
    STATUS       current
    DESCRIPTION
        "Cisco UCS adaptor:HostIscsiIfProfile:rn managed object property"
    ::= { cucsAdaptorHostIscsiIfProfileEntry 3 }

cucsAdaptorHostIscsiIfProfileDescr OBJECT-TYPE
    SYNTAX       SnmpAdminString
    MAX-ACCESS   read-only
    STATUS       current
    DESCRIPTION
        "Cisco UCS adaptor:HostIscsiIfProfile:descr managed
        object property"
    ::= { cucsAdaptorHostIscsiIfProfileEntry 4 }

cucsAdaptorHostIscsiIfProfileIntId OBJECT-TYPE
    SYNTAX       SnmpAdminString
    MAX-ACCESS   read-only
    STATUS       current
    DESCRIPTION
        "Cisco UCS adaptor:HostIscsiIfProfile:intId managed
        object property"
    ::= { cucsAdaptorHostIscsiIfProfileEntry 5 }

cucsAdaptorHostIscsiIfProfileName OBJECT-TYPE
    SYNTAX       SnmpAdminString
    MAX-ACCESS   read-only
    STATUS       current
    DESCRIPTION
        "Cisco UCS adaptor:HostIscsiIfProfile:name managed
        object property"
    ::= { cucsAdaptorHostIscsiIfProfileEntry 6 }

cucsAdaptorHostIscsiIfProfilePolicyLevel OBJECT-TYPE
    SYNTAX       Gauge32
    MAX-ACCESS   read-only
    STATUS       current
    DESCRIPTION
        "Cisco UCS adaptor:HostIscsiIfProfile:policyLevel
        managed object property"
    ::= { cucsAdaptorHostIscsiIfProfileEntry 7 }

cucsAdaptorHostIscsiIfProfilePolicyOwner OBJECT-TYPE
    SYNTAX       CucsPolicyPolicyOwner
    MAX-ACCESS   read-only
    STATUS       current
    DESCRIPTION
        "Cisco UCS adaptor:HostIscsiIfProfile:policyOwner
        managed object property"
    ::= { cucsAdaptorHostIscsiIfProfileEntry 8 }

cucsAdaptorHostMgmtCapTable OBJECT-TYPE
    SYNTAX           SEQUENCE OF CucsAdaptorHostMgmtCapEntry
    MAX-ACCESS       not-accessible
    STATUS           current
    DESCRIPTION
        "Cisco UCS adaptor:HostMgmtCap managed object table"
    ::= { cucsAdaptorObjects 51 }

cucsAdaptorHostMgmtCapEntry OBJECT-TYPE
    SYNTAX           CucsAdaptorHostMgmtCapEntry
    MAX-ACCESS       not-accessible
    STATUS           current
    DESCRIPTION
        "Entry for the cucsAdaptorHostMgmtCapTable table."
    INDEX { cucsAdaptorHostMgmtCapInstanceId }
    ::= { cucsAdaptorHostMgmtCapTable 1 }

CucsAdaptorHostMgmtCapEntry ::= SEQUENCE {
    cucsAdaptorHostMgmtCapInstanceId                                 CucsManagedObjectId,
    cucsAdaptorHostMgmtCapDn                                         CucsManagedObjectDn,
    cucsAdaptorHostMgmtCapRn                                         SnmpAdminString,
    cucsAdaptorHostMgmtCapMode                                       CucsAdaptorMgmtCapMode,
    cucsAdaptorHostMgmtCapOperPowerRequirement                       CucsAdaptorMgmtCapOperPowerRequirement,
    cucsAdaptorHostMgmtCapPreboot                                    CucsAdaptorHostMgmtCapPreboot,
    cucsAdaptorHostMgmtCapRebootActionOnDestructive                  CucsAdaptorMgmtCapRebootActionOnDestructive,
    cucsAdaptorHostMgmtCapPresence                                   CucsAdaptorHostMgmtCapPresence
}

cucsAdaptorHostMgmtCapInstanceId OBJECT-TYPE
    SYNTAX       CucsManagedObjectId
    MAX-ACCESS   not-accessible
    STATUS       current
    DESCRIPTION
        "Instance identifier of the managed object."
    ::= { cucsAdaptorHostMgmtCapEntry 1 }

cucsAdaptorHostMgmtCapDn OBJECT-TYPE
    SYNTAX       CucsManagedObjectDn
    MAX-ACCESS   read-only
    STATUS       current
    DESCRIPTION
        "Cisco UCS adaptor:HostMgmtCap:dn managed object property"
    ::= { cucsAdaptorHostMgmtCapEntry 2 }

cucsAdaptorHostMgmtCapRn OBJECT-TYPE
    SYNTAX       SnmpAdminString
    MAX-ACCESS   read-only
    STATUS       current
    DESCRIPTION
        "Cisco UCS adaptor:HostMgmtCap:rn managed object property"
    ::= { cucsAdaptorHostMgmtCapEntry 3 }

cucsAdaptorHostMgmtCapMode OBJECT-TYPE
    SYNTAX       CucsAdaptorMgmtCapMode
    MAX-ACCESS   read-only
    STATUS       current
    DESCRIPTION
        "Cisco UCS adaptor:HostMgmtCap:mode managed object property"
    ::= { cucsAdaptorHostMgmtCapEntry 4 }

cucsAdaptorHostMgmtCapOperPowerRequirement OBJECT-TYPE
    SYNTAX       CucsAdaptorMgmtCapOperPowerRequirement
    MAX-ACCESS   read-only
    STATUS       current
    DESCRIPTION
        "Cisco UCS adaptor:HostMgmtCap:operPowerRequirement
        managed object property"
    ::= { cucsAdaptorHostMgmtCapEntry 5 }

cucsAdaptorHostMgmtCapPreboot OBJECT-TYPE
    SYNTAX       CucsAdaptorHostMgmtCapPreboot
    MAX-ACCESS   read-only
    STATUS       current
    DESCRIPTION
        "Cisco UCS adaptor:HostMgmtCap:preboot managed object property"
    ::= { cucsAdaptorHostMgmtCapEntry 6 }

cucsAdaptorHostMgmtCapRebootActionOnDestructive OBJECT-TYPE
    SYNTAX       CucsAdaptorMgmtCapRebootActionOnDestructive
    MAX-ACCESS   read-only
    STATUS       current
    DESCRIPTION
        "Cisco UCS adaptor:HostMgmtCap:rebootActionOnDestructive
        managed object property"
    ::= { cucsAdaptorHostMgmtCapEntry 7 }

cucsAdaptorHostMgmtCapPresence OBJECT-TYPE
    SYNTAX       CucsAdaptorHostMgmtCapPresence
    MAX-ACCESS   read-only
    STATUS       current
    DESCRIPTION
        "Cisco UCS adaptor:HostMgmtCap:presence managed object property"
    ::= { cucsAdaptorHostMgmtCapEntry 8 }

cucsAdaptorHostPortTable OBJECT-TYPE
    SYNTAX           SEQUENCE OF CucsAdaptorHostPortEntry
    MAX-ACCESS       not-accessible
    STATUS           current
    DESCRIPTION
        "Cisco UCS adaptor:HostPort managed object table"
    ::= { cucsAdaptorObjects 120 }

cucsAdaptorHostPortEntry OBJECT-TYPE
    SYNTAX           CucsAdaptorHostPortEntry
    MAX-ACCESS       not-accessible
    STATUS           current
    DESCRIPTION
        "Entry for the cucsAdaptorHostPortTable table."
    INDEX { cucsAdaptorHostPortInstanceId }
    ::= { cucsAdaptorHostPortTable 1 }

CucsAdaptorHostPortEntry ::= SEQUENCE {
    cucsAdaptorHostPortInstanceId                                    CucsManagedObjectId,
    cucsAdaptorHostPortDn                                            CucsManagedObjectDn,
    cucsAdaptorHostPortRn                                            SnmpAdminString,
    cucsAdaptorHostPortFltAggr                                       Unsigned64,
    cucsAdaptorHostPortId                                            CucsAdaptorHostPortId,
    cucsAdaptorHostPortLocationDn                                    SnmpAdminString,
    cucsAdaptorHostPortModel                                         SnmpAdminString,
    cucsAdaptorHostPortOperQualifierReason                           SnmpAdminString,
    cucsAdaptorHostPortOperState                                     CucsEquipmentOperability,
    cucsAdaptorHostPortOperability                                   CucsEquipmentOperability,
    cucsAdaptorHostPortPerf                                          CucsEquipmentSensorThresholdStatus,
    cucsAdaptorHostPortPower                                         CucsEquipmentPowerState,
    cucsAdaptorHostPortPresence                                      CucsEquipmentPresence,
    cucsAdaptorHostPortRevision                                      SnmpAdminString,
    cucsAdaptorHostPortSerial                                        SnmpAdminString,
    cucsAdaptorHostPortThermal                                       CucsEquipmentSensorThresholdStatus,
    cucsAdaptorHostPortVendor                                        SnmpAdminString,
    cucsAdaptorHostPortVoltage                                       CucsEquipmentSensorThresholdStatus
}

cucsAdaptorHostPortInstanceId OBJECT-TYPE
    SYNTAX       CucsManagedObjectId
    MAX-ACCESS   not-accessible
    STATUS       current
    DESCRIPTION
        "Instance identifier of the managed object."
    ::= { cucsAdaptorHostPortEntry 1 }

cucsAdaptorHostPortDn OBJECT-TYPE
    SYNTAX       CucsManagedObjectDn
    MAX-ACCESS   read-only
    STATUS       current
    DESCRIPTION
        "Cisco UCS adaptor:HostPort:dn managed object property"
    ::= { cucsAdaptorHostPortEntry 2 }

cucsAdaptorHostPortRn OBJECT-TYPE
    SYNTAX       SnmpAdminString
    MAX-ACCESS   read-only
    STATUS       current
    DESCRIPTION
        "Cisco UCS adaptor:HostPort:rn managed object property"
    ::= { cucsAdaptorHostPortEntry 3 }

cucsAdaptorHostPortFltAggr OBJECT-TYPE
    SYNTAX       Unsigned64
    MAX-ACCESS   read-only
    STATUS       current
    DESCRIPTION
        "Cisco UCS adaptor:HostPort:fltAggr managed object property"
    ::= { cucsAdaptorHostPortEntry 4 }

cucsAdaptorHostPortId OBJECT-TYPE
    SYNTAX       CucsAdaptorHostPortId
    MAX-ACCESS   read-only
    STATUS       current
    DESCRIPTION
        "Cisco UCS adaptor:HostPort:id managed object property"
    ::= { cucsAdaptorHostPortEntry 5 }

cucsAdaptorHostPortLocationDn OBJECT-TYPE
    SYNTAX       SnmpAdminString
    MAX-ACCESS   read-only
    STATUS       current
    DESCRIPTION
        "Cisco UCS adaptor:HostPort:locationDn managed object property"
    ::= { cucsAdaptorHostPortEntry 6 }

cucsAdaptorHostPortModel OBJECT-TYPE
    SYNTAX       SnmpAdminString
    MAX-ACCESS   read-only
    STATUS       current
    DESCRIPTION
        "Cisco UCS adaptor:HostPort:model managed object property"
    ::= { cucsAdaptorHostPortEntry 7 }

cucsAdaptorHostPortOperQualifierReason OBJECT-TYPE
    SYNTAX       SnmpAdminString
    MAX-ACCESS   read-only
    STATUS       current
    DESCRIPTION
        "Cisco UCS adaptor:HostPort:operQualifierReason
        managed object property"
    ::= { cucsAdaptorHostPortEntry 8 }

cucsAdaptorHostPortOperState OBJECT-TYPE
    SYNTAX       CucsEquipmentOperability
    MAX-ACCESS   read-only
    STATUS       current
    DESCRIPTION
        "Cisco UCS adaptor:HostPort:operState managed object property"
    ::= { cucsAdaptorHostPortEntry 9 }

cucsAdaptorHostPortOperability OBJECT-TYPE
    SYNTAX       CucsEquipmentOperability
    MAX-ACCESS   read-only
    STATUS       current
    DESCRIPTION
        "Cisco UCS adaptor:HostPort:operability managed object property"
    ::= { cucsAdaptorHostPortEntry 10 }

cucsAdaptorHostPortPerf OBJECT-TYPE
    SYNTAX       CucsEquipmentSensorThresholdStatus
    MAX-ACCESS   read-only
    STATUS       current
    DESCRIPTION
        "Cisco UCS adaptor:HostPort:perf managed object property"
    ::= { cucsAdaptorHostPortEntry 11 }

cucsAdaptorHostPortPower OBJECT-TYPE
    SYNTAX       CucsEquipmentPowerState
    MAX-ACCESS   read-only
    STATUS       current
    DESCRIPTION
        "Cisco UCS adaptor:HostPort:power managed object property"
    ::= { cucsAdaptorHostPortEntry 12 }

cucsAdaptorHostPortPresence OBJECT-TYPE
    SYNTAX       CucsEquipmentPresence
    MAX-ACCESS   read-only
    STATUS       current
    DESCRIPTION
        "Cisco UCS adaptor:HostPort:presence managed object property"
    ::= { cucsAdaptorHostPortEntry 13 }

cucsAdaptorHostPortRevision OBJECT-TYPE
    SYNTAX       SnmpAdminString
    MAX-ACCESS   read-only
    STATUS       current
    DESCRIPTION
        "Cisco UCS adaptor:HostPort:revision managed object property"
    ::= { cucsAdaptorHostPortEntry 14 }

cucsAdaptorHostPortSerial OBJECT-TYPE
    SYNTAX       SnmpAdminString
    MAX-ACCESS   read-only
    STATUS       current
    DESCRIPTION
        "Cisco UCS adaptor:HostPort:serial managed object property"
    ::= { cucsAdaptorHostPortEntry 15 }

cucsAdaptorHostPortThermal OBJECT-TYPE
    SYNTAX       CucsEquipmentSensorThresholdStatus
    MAX-ACCESS   read-only
    STATUS       current
    DESCRIPTION
        "Cisco UCS adaptor:HostPort:thermal managed object property"
    ::= { cucsAdaptorHostPortEntry 16 }

cucsAdaptorHostPortVendor OBJECT-TYPE
    SYNTAX       SnmpAdminString
    MAX-ACCESS   read-only
    STATUS       current
    DESCRIPTION
        "Cisco UCS adaptor:HostPort:vendor managed object property"
    ::= { cucsAdaptorHostPortEntry 17 }

cucsAdaptorHostPortVoltage OBJECT-TYPE
    SYNTAX       CucsEquipmentSensorThresholdStatus
    MAX-ACCESS   read-only
    STATUS       current
    DESCRIPTION
        "Cisco UCS adaptor:HostPort:voltage managed object property"
    ::= { cucsAdaptorHostPortEntry 18 }

cucsAdaptorHostPortCapTable OBJECT-TYPE
    SYNTAX           SEQUENCE OF CucsAdaptorHostPortCapEntry
    MAX-ACCESS       not-accessible
    STATUS           current
    DESCRIPTION
        "Cisco UCS adaptor:HostPortCap managed object table"
    ::= { cucsAdaptorObjects 121 }

cucsAdaptorHostPortCapEntry OBJECT-TYPE
    SYNTAX           CucsAdaptorHostPortCapEntry
    MAX-ACCESS       not-accessible
    STATUS           current
    DESCRIPTION
        "Entry for the cucsAdaptorHostPortCapTable table."
    INDEX { cucsAdaptorHostPortCapInstanceId }
    ::= { cucsAdaptorHostPortCapTable 1 }

CucsAdaptorHostPortCapEntry ::= SEQUENCE {
    cucsAdaptorHostPortCapInstanceId                                 CucsManagedObjectId,
    cucsAdaptorHostPortCapDn                                         CucsManagedObjectDn,
    cucsAdaptorHostPortCapRn                                         SnmpAdminString,
    cucsAdaptorHostPortCapMaxPorts                                   Gauge32
}

cucsAdaptorHostPortCapInstanceId OBJECT-TYPE
    SYNTAX       CucsManagedObjectId
    MAX-ACCESS   not-accessible
    STATUS       current
    DESCRIPTION
        "Instance identifier of the managed object."
    ::= { cucsAdaptorHostPortCapEntry 1 }

cucsAdaptorHostPortCapDn OBJECT-TYPE
    SYNTAX       CucsManagedObjectDn
    MAX-ACCESS   read-only
    STATUS       current
    DESCRIPTION
        "Cisco UCS adaptor:HostPortCap:dn managed object property"
    ::= { cucsAdaptorHostPortCapEntry 2 }

cucsAdaptorHostPortCapRn OBJECT-TYPE
    SYNTAX       SnmpAdminString
    MAX-ACCESS   read-only
    STATUS       current
    DESCRIPTION
        "Cisco UCS adaptor:HostPortCap:rn managed object property"
    ::= { cucsAdaptorHostPortCapEntry 3 }

cucsAdaptorHostPortCapMaxPorts OBJECT-TYPE
    SYNTAX       Gauge32
    MAX-ACCESS   read-only
    STATUS       current
    DESCRIPTION
        "Cisco UCS adaptor:HostPortCap:maxPorts managed object property"
    ::= { cucsAdaptorHostPortCapEntry 4 }

cucsAdaptorHostScsiIfTable OBJECT-TYPE
    SYNTAX           SEQUENCE OF CucsAdaptorHostScsiIfEntry
    MAX-ACCESS       not-accessible
    STATUS           current
    DESCRIPTION
        "Cisco UCS adaptor:HostScsiIf managed object table"
    ::= { cucsAdaptorObjects 125 }

cucsAdaptorHostScsiIfEntry OBJECT-TYPE
    SYNTAX           CucsAdaptorHostScsiIfEntry
    MAX-ACCESS       not-accessible
    STATUS           current
    DESCRIPTION
        "Entry for the cucsAdaptorHostScsiIfTable table."
    INDEX { cucsAdaptorHostScsiIfInstanceId }
    ::= { cucsAdaptorHostScsiIfTable 1 }

CucsAdaptorHostScsiIfEntry ::= SEQUENCE {
    cucsAdaptorHostScsiIfInstanceId                                  CucsManagedObjectId,
    cucsAdaptorHostScsiIfDn                                          CucsManagedObjectDn,
    cucsAdaptorHostScsiIfRn                                          SnmpAdminString,
    cucsAdaptorHostScsiIfAdminState                                  CucsAdaptorHostIfAdminState,
    cucsAdaptorHostScsiIfBootDev                                     CucsAdaptorHostIfBootDev,
    cucsAdaptorHostScsiIfChassisId                                   Gauge32,
    cucsAdaptorHostScsiIfDiscovery                                   CucsEtherSatelliteConnectionDisc,
    cucsAdaptorHostScsiIfEpDn                                        SnmpAdminString,
    cucsAdaptorHostScsiIfFltAggr                                     Unsigned64,
    cucsAdaptorHostScsiIfId                                          Gauge32,
    cucsAdaptorHostScsiIfIfRole                                      CucsNetworkPortRole,
    cucsAdaptorHostScsiIfIfType                                      CucsNetworkPhysEpIfType,
    cucsAdaptorHostScsiIfLc                                          CucsFsmLifecycle,
    cucsAdaptorHostScsiIfLinkState                                   CucsAdaptorLinkState,
    cucsAdaptorHostScsiIfLocale                                      CucsNetworkLocale,
    cucsAdaptorHostScsiIfModel                                       SnmpAdminString,
    cucsAdaptorHostScsiIfName                                        SnmpAdminString,
    cucsAdaptorHostScsiIfOperQualifierReason                         SnmpAdminString,
    cucsAdaptorHostScsiIfOperState                                   CucsEquipmentOperability,
    cucsAdaptorHostScsiIfOperability                                 CucsEquipmentOperability,
    cucsAdaptorHostScsiIfOrder                                       Gauge32,
    cucsAdaptorHostScsiIfPciAddr                                     SnmpAdminString,
    cucsAdaptorHostScsiIfPciFunc                                     Gauge32,
    cucsAdaptorHostScsiIfPciSlot                                     Gauge32,
    cucsAdaptorHostScsiIfPeerChassisId                               Gauge32,
    cucsAdaptorHostScsiIfPeerDn                                      SnmpAdminString,
    cucsAdaptorHostScsiIfPeerPortId                                  Gauge32,
    cucsAdaptorHostScsiIfPeerSlotId                                  Gauge32,
    cucsAdaptorHostScsiIfPerf                                        CucsEquipmentSensorThresholdStatus,
    cucsAdaptorHostScsiIfPortId                                      Gauge32,
    cucsAdaptorHostScsiIfPower                                       CucsEquipmentPowerState,
    cucsAdaptorHostScsiIfPresence                                    CucsEquipmentPresence,
    cucsAdaptorHostScsiIfPurpose                                     CucsAdaptorPurpose,
    cucsAdaptorHostScsiIfRevision                                    SnmpAdminString,
    cucsAdaptorHostScsiIfSerial                                      SnmpAdminString,
    cucsAdaptorHostScsiIfSide                                        CucsNetworkSide,
    cucsAdaptorHostScsiIfSlotId                                      Gauge32,
    cucsAdaptorHostScsiIfSwitchId                                    CucsNetworkSwitchId,
    cucsAdaptorHostScsiIfThermal                                     CucsEquipmentSensorThresholdStatus,
    cucsAdaptorHostScsiIfTransport                                   CucsNetworkTransport,
    cucsAdaptorHostScsiIfType                                        CucsNetworkConnectionType,
    cucsAdaptorHostScsiIfVendor                                      SnmpAdminString,
    cucsAdaptorHostScsiIfVnicDn                                      SnmpAdminString,
    cucsAdaptorHostScsiIfVoltage                                     CucsEquipmentSensorThresholdStatus,
    cucsAdaptorHostScsiIfCdnName                                     SnmpAdminString
}

cucsAdaptorHostScsiIfInstanceId OBJECT-TYPE
    SYNTAX       CucsManagedObjectId
    MAX-ACCESS   not-accessible
    STATUS       current
    DESCRIPTION
        "Instance identifier of the managed object."
    ::= { cucsAdaptorHostScsiIfEntry 1 }

cucsAdaptorHostScsiIfDn OBJECT-TYPE
    SYNTAX       CucsManagedObjectDn
    MAX-ACCESS   read-only
    STATUS       current
    DESCRIPTION
        "Cisco UCS adaptor:HostScsiIf:dn managed object property"
    ::= { cucsAdaptorHostScsiIfEntry 2 }

cucsAdaptorHostScsiIfRn OBJECT-TYPE
    SYNTAX       SnmpAdminString
    MAX-ACCESS   read-only
    STATUS       current
    DESCRIPTION
        "Cisco UCS adaptor:HostScsiIf:rn managed object property"
    ::= { cucsAdaptorHostScsiIfEntry 3 }

cucsAdaptorHostScsiIfAdminState OBJECT-TYPE
    SYNTAX       CucsAdaptorHostIfAdminState
    MAX-ACCESS   read-only
    STATUS       current
    DESCRIPTION
        "Cisco UCS adaptor:HostScsiIf:adminState managed object property"
    ::= { cucsAdaptorHostScsiIfEntry 4 }

cucsAdaptorHostScsiIfBootDev OBJECT-TYPE
    SYNTAX       CucsAdaptorHostIfBootDev
    MAX-ACCESS   read-only
    STATUS       current
    DESCRIPTION
        "Cisco UCS adaptor:HostScsiIf:bootDev managed object property"
    ::= { cucsAdaptorHostScsiIfEntry 5 }

cucsAdaptorHostScsiIfChassisId OBJECT-TYPE
    SYNTAX       Gauge32
    MAX-ACCESS   read-only
    STATUS       current
    DESCRIPTION
        "Cisco UCS adaptor:HostScsiIf:chassisId managed object property"
    ::= { cucsAdaptorHostScsiIfEntry 6 }

cucsAdaptorHostScsiIfDiscovery OBJECT-TYPE
    SYNTAX       CucsEtherSatelliteConnectionDisc
    MAX-ACCESS   read-only
    STATUS       current
    DESCRIPTION
        "Cisco UCS adaptor:HostScsiIf:discovery managed object property"
    ::= { cucsAdaptorHostScsiIfEntry 7 }

cucsAdaptorHostScsiIfEpDn OBJECT-TYPE
    SYNTAX       SnmpAdminString
    MAX-ACCESS   read-only
    STATUS       current
    DESCRIPTION
        "Cisco UCS adaptor:HostScsiIf:epDn managed object property"
    ::= { cucsAdaptorHostScsiIfEntry 8 }

cucsAdaptorHostScsiIfFltAggr OBJECT-TYPE
    SYNTAX       Unsigned64
    MAX-ACCESS   read-only
    STATUS       current
    DESCRIPTION
        "Cisco UCS adaptor:HostScsiIf:fltAggr managed object property"
    ::= { cucsAdaptorHostScsiIfEntry 9 }

cucsAdaptorHostScsiIfId OBJECT-TYPE
    SYNTAX       Gauge32
    MAX-ACCESS   read-only
    STATUS       current
    DESCRIPTION
        "Cisco UCS adaptor:HostScsiIf:id managed object property"
    ::= { cucsAdaptorHostScsiIfEntry 10 }

cucsAdaptorHostScsiIfIfRole OBJECT-TYPE
    SYNTAX       CucsNetworkPortRole
    MAX-ACCESS   read-only
    STATUS       current
    DESCRIPTION
        "Cisco UCS adaptor:HostScsiIf:ifRole managed object property"
    ::= { cucsAdaptorHostScsiIfEntry 11 }

cucsAdaptorHostScsiIfIfType OBJECT-TYPE
    SYNTAX       CucsNetworkPhysEpIfType
    MAX-ACCESS   read-only
    STATUS       current
    DESCRIPTION
        "Cisco UCS adaptor:HostScsiIf:ifType managed object property"
    ::= { cucsAdaptorHostScsiIfEntry 12 }

cucsAdaptorHostScsiIfLc OBJECT-TYPE
    SYNTAX       CucsFsmLifecycle
    MAX-ACCESS   read-only
    STATUS       current
    DESCRIPTION
        "Cisco UCS adaptor:HostScsiIf:lc managed object property"
    ::= { cucsAdaptorHostScsiIfEntry 13 }

cucsAdaptorHostScsiIfLinkState OBJECT-TYPE
    SYNTAX       CucsAdaptorLinkState
    MAX-ACCESS   read-only
    STATUS       current
    DESCRIPTION
        "Cisco UCS adaptor:HostScsiIf:linkState managed object property"
    ::= { cucsAdaptorHostScsiIfEntry 14 }

cucsAdaptorHostScsiIfLocale OBJECT-TYPE
    SYNTAX       CucsNetworkLocale
    MAX-ACCESS   read-only
    STATUS       current
    DESCRIPTION
        "Cisco UCS adaptor:HostScsiIf:locale managed object property"
    ::= { cucsAdaptorHostScsiIfEntry 15 }

cucsAdaptorHostScsiIfModel OBJECT-TYPE
    SYNTAX       SnmpAdminString
    MAX-ACCESS   read-only
    STATUS       current
    DESCRIPTION
        "Cisco UCS adaptor:HostScsiIf:model managed object property"
    ::= { cucsAdaptorHostScsiIfEntry 16 }

cucsAdaptorHostScsiIfName OBJECT-TYPE
    SYNTAX       SnmpAdminString
    MAX-ACCESS   read-only
    STATUS       current
    DESCRIPTION
        "Cisco UCS adaptor:HostScsiIf:name managed object property"
    ::= { cucsAdaptorHostScsiIfEntry 17 }

cucsAdaptorHostScsiIfOperQualifierReason OBJECT-TYPE
    SYNTAX       SnmpAdminString
    MAX-ACCESS   read-only
    STATUS       current
    DESCRIPTION
        "Cisco UCS adaptor:HostScsiIf:operQualifierReason
        managed object property"
    ::= { cucsAdaptorHostScsiIfEntry 18 }

cucsAdaptorHostScsiIfOperState OBJECT-TYPE
    SYNTAX       CucsEquipmentOperability
    MAX-ACCESS   read-only
    STATUS       current
    DESCRIPTION
        "Cisco UCS adaptor:HostScsiIf:operState managed object property"
    ::= { cucsAdaptorHostScsiIfEntry 19 }

cucsAdaptorHostScsiIfOperability OBJECT-TYPE
    SYNTAX       CucsEquipmentOperability
    MAX-ACCESS   read-only
    STATUS       current
    DESCRIPTION
        "Cisco UCS adaptor:HostScsiIf:operability managed object property"
    ::= { cucsAdaptorHostScsiIfEntry 20 }

cucsAdaptorHostScsiIfOrder OBJECT-TYPE
    SYNTAX       Gauge32
    MAX-ACCESS   read-only
    STATUS       current
    DESCRIPTION
        "Cisco UCS adaptor:HostScsiIf:order managed object property"
    ::= { cucsAdaptorHostScsiIfEntry 21 }

cucsAdaptorHostScsiIfPciAddr OBJECT-TYPE
    SYNTAX       SnmpAdminString
    MAX-ACCESS   read-only
    STATUS       current
    DESCRIPTION
        "Cisco UCS adaptor:HostScsiIf:pciAddr managed object property"
    ::= { cucsAdaptorHostScsiIfEntry 22 }

cucsAdaptorHostScsiIfPciFunc OBJECT-TYPE
    SYNTAX       Gauge32
    MAX-ACCESS   read-only
    STATUS       current
    DESCRIPTION
        "Cisco UCS adaptor:HostScsiIf:pciFunc managed object property"
    ::= { cucsAdaptorHostScsiIfEntry 23 }

cucsAdaptorHostScsiIfPciSlot OBJECT-TYPE
    SYNTAX       Gauge32
    MAX-ACCESS   read-only
    STATUS       current
    DESCRIPTION
        "Cisco UCS adaptor:HostScsiIf:pciSlot managed object property"
    ::= { cucsAdaptorHostScsiIfEntry 24 }

cucsAdaptorHostScsiIfPeerChassisId OBJECT-TYPE
    SYNTAX       Gauge32
    MAX-ACCESS   read-only
    STATUS       current
    DESCRIPTION
        "Cisco UCS adaptor:HostScsiIf:peerChassisId managed
        object property"
    ::= { cucsAdaptorHostScsiIfEntry 25 }

cucsAdaptorHostScsiIfPeerDn OBJECT-TYPE
    SYNTAX       SnmpAdminString
    MAX-ACCESS   read-only
    STATUS       current
    DESCRIPTION
        "Cisco UCS adaptor:HostScsiIf:peerDn managed object property"
    ::= { cucsAdaptorHostScsiIfEntry 26 }

cucsAdaptorHostScsiIfPeerPortId OBJECT-TYPE
    SYNTAX       Gauge32
    MAX-ACCESS   read-only
    STATUS       current
    DESCRIPTION
        "Cisco UCS adaptor:HostScsiIf:peerPortId managed object property"
    ::= { cucsAdaptorHostScsiIfEntry 27 }

cucsAdaptorHostScsiIfPeerSlotId OBJECT-TYPE
    SYNTAX       Gauge32
    MAX-ACCESS   read-only
    STATUS       current
    DESCRIPTION
        "Cisco UCS adaptor:HostScsiIf:peerSlotId managed object property"
    ::= { cucsAdaptorHostScsiIfEntry 28 }

cucsAdaptorHostScsiIfPerf OBJECT-TYPE
    SYNTAX       CucsEquipmentSensorThresholdStatus
    MAX-ACCESS   read-only
    STATUS       current
    DESCRIPTION
        "Cisco UCS adaptor:HostScsiIf:perf managed object property"
    ::= { cucsAdaptorHostScsiIfEntry 29 }

cucsAdaptorHostScsiIfPortId OBJECT-TYPE
    SYNTAX       Gauge32
    MAX-ACCESS   read-only
    STATUS       current
    DESCRIPTION
        "Cisco UCS adaptor:HostScsiIf:portId managed object property"
    ::= { cucsAdaptorHostScsiIfEntry 30 }

cucsAdaptorHostScsiIfPower OBJECT-TYPE
    SYNTAX       CucsEquipmentPowerState
    MAX-ACCESS   read-only
    STATUS       current
    DESCRIPTION
        "Cisco UCS adaptor:HostScsiIf:power managed object property"
    ::= { cucsAdaptorHostScsiIfEntry 31 }

cucsAdaptorHostScsiIfPresence OBJECT-TYPE
    SYNTAX       CucsEquipmentPresence
    MAX-ACCESS   read-only
    STATUS       current
    DESCRIPTION
        "Cisco UCS adaptor:HostScsiIf:presence managed object property"
    ::= { cucsAdaptorHostScsiIfEntry 32 }

cucsAdaptorHostScsiIfPurpose OBJECT-TYPE
    SYNTAX       CucsAdaptorPurpose
    MAX-ACCESS   read-only
    STATUS       current
    DESCRIPTION
        "Cisco UCS adaptor:HostScsiIf:purpose managed object property"
    ::= { cucsAdaptorHostScsiIfEntry 33 }

cucsAdaptorHostScsiIfRevision OBJECT-TYPE
    SYNTAX       SnmpAdminString
    MAX-ACCESS   read-only
    STATUS       current
    DESCRIPTION
        "Cisco UCS adaptor:HostScsiIf:revision managed object property"
    ::= { cucsAdaptorHostScsiIfEntry 34 }

cucsAdaptorHostScsiIfSerial OBJECT-TYPE
    SYNTAX       SnmpAdminString
    MAX-ACCESS   read-only
    STATUS       current
    DESCRIPTION
        "Cisco UCS adaptor:HostScsiIf:serial managed object property"
    ::= { cucsAdaptorHostScsiIfEntry 35 }

cucsAdaptorHostScsiIfSide OBJECT-TYPE
    SYNTAX       CucsNetworkSide
    MAX-ACCESS   read-only
    STATUS       current
    DESCRIPTION
        "Cisco UCS adaptor:HostScsiIf:side managed object property"
    ::= { cucsAdaptorHostScsiIfEntry 36 }

cucsAdaptorHostScsiIfSlotId OBJECT-TYPE
    SYNTAX       Gauge32
    MAX-ACCESS   read-only
    STATUS       current
    DESCRIPTION
        "Cisco UCS adaptor:HostScsiIf:slotId managed object property"
    ::= { cucsAdaptorHostScsiIfEntry 37 }

cucsAdaptorHostScsiIfSwitchId OBJECT-TYPE
    SYNTAX       CucsNetworkSwitchId
    MAX-ACCESS   read-only
    STATUS       current
    DESCRIPTION
        "Cisco UCS adaptor:HostScsiIf:switchId managed object property"
    ::= { cucsAdaptorHostScsiIfEntry 38 }

cucsAdaptorHostScsiIfThermal OBJECT-TYPE
    SYNTAX       CucsEquipmentSensorThresholdStatus
    MAX-ACCESS   read-only
    STATUS       current
    DESCRIPTION
        "Cisco UCS adaptor:HostScsiIf:thermal managed object property"
    ::= { cucsAdaptorHostScsiIfEntry 39 }

cucsAdaptorHostScsiIfTransport OBJECT-TYPE
    SYNTAX       CucsNetworkTransport
    MAX-ACCESS   read-only
    STATUS       current
    DESCRIPTION
        "Cisco UCS adaptor:HostScsiIf:transport managed object property"
    ::= { cucsAdaptorHostScsiIfEntry 40 }

cucsAdaptorHostScsiIfType OBJECT-TYPE
    SYNTAX       CucsNetworkConnectionType
    MAX-ACCESS   read-only
    STATUS       current
    DESCRIPTION
        "Cisco UCS adaptor:HostScsiIf:type managed object property"
    ::= { cucsAdaptorHostScsiIfEntry 41 }

cucsAdaptorHostScsiIfVendor OBJECT-TYPE
    SYNTAX       SnmpAdminString
    MAX-ACCESS   read-only
    STATUS       current
    DESCRIPTION
        "Cisco UCS adaptor:HostScsiIf:vendor managed object property"
    ::= { cucsAdaptorHostScsiIfEntry 42 }

cucsAdaptorHostScsiIfVnicDn OBJECT-TYPE
    SYNTAX       SnmpAdminString
    MAX-ACCESS   read-only
    STATUS       current
    DESCRIPTION
        "Cisco UCS adaptor:HostScsiIf:vnicDn managed object property"
    ::= { cucsAdaptorHostScsiIfEntry 43 }

cucsAdaptorHostScsiIfVoltage OBJECT-TYPE
    SYNTAX       CucsEquipmentSensorThresholdStatus
    MAX-ACCESS   read-only
    STATUS       current
    DESCRIPTION
        "Cisco UCS adaptor:HostScsiIf:voltage managed object property"
    ::= { cucsAdaptorHostScsiIfEntry 44 }

cucsAdaptorHostScsiIfCdnName OBJECT-TYPE
    SYNTAX       SnmpAdminString
    MAX-ACCESS   read-only
    STATUS       current
    DESCRIPTION
        "Cisco UCS adaptor:HostScsiIf:cdnName managed object property"
    ::= { cucsAdaptorHostScsiIfEntry 45 }

cucsAdaptorHostScsiLunRefTable OBJECT-TYPE
    SYNTAX           SEQUENCE OF CucsAdaptorHostScsiLunRefEntry
    MAX-ACCESS       not-accessible
    STATUS           current
    DESCRIPTION
        "Cisco UCS adaptor:HostScsiLunRef managed object table"
    ::= { cucsAdaptorObjects 126 }

cucsAdaptorHostScsiLunRefEntry OBJECT-TYPE
    SYNTAX           CucsAdaptorHostScsiLunRefEntry
    MAX-ACCESS       not-accessible
    STATUS           current
    DESCRIPTION
        "Entry for the cucsAdaptorHostScsiLunRefTable table."
    INDEX { cucsAdaptorHostScsiLunRefInstanceId }
    ::= { cucsAdaptorHostScsiLunRefTable 1 }

CucsAdaptorHostScsiLunRefEntry ::= SEQUENCE {
    cucsAdaptorHostScsiLunRefInstanceId                              CucsManagedObjectId,
    cucsAdaptorHostScsiLunRefDn                                      CucsManagedObjectDn,
    cucsAdaptorHostScsiLunRefRn                                      SnmpAdminString,
    cucsAdaptorHostScsiLunRefBootDev                                 CucsLstorageBootDevice,
    cucsAdaptorHostScsiLunRefFltAggr                                 Unsigned64,
    cucsAdaptorHostScsiLunRefLunDn                                   SnmpAdminString,
    cucsAdaptorHostScsiLunRefLunId                                   Gauge32,
    cucsAdaptorHostScsiLunRefLunName                                 SnmpAdminString,
    cucsAdaptorHostScsiLunRefLunOrder                                Gauge32,
    cucsAdaptorHostScsiLunRefOperLunId                               Gauge32,
    cucsAdaptorHostScsiLunRefOperLunOrder                            Gauge32
}

cucsAdaptorHostScsiLunRefInstanceId OBJECT-TYPE
    SYNTAX       CucsManagedObjectId
    MAX-ACCESS   not-accessible
    STATUS       current
    DESCRIPTION
        "Instance identifier of the managed object."
    ::= { cucsAdaptorHostScsiLunRefEntry 1 }

cucsAdaptorHostScsiLunRefDn OBJECT-TYPE
    SYNTAX       CucsManagedObjectDn
    MAX-ACCESS   read-only
    STATUS       current
    DESCRIPTION
        "Cisco UCS adaptor:HostScsiLunRef:dn managed object property"
    ::= { cucsAdaptorHostScsiLunRefEntry 2 }

cucsAdaptorHostScsiLunRefRn OBJECT-TYPE
    SYNTAX       SnmpAdminString
    MAX-ACCESS   read-only
    STATUS       current
    DESCRIPTION
        "Cisco UCS adaptor:HostScsiLunRef:rn managed object property"
    ::= { cucsAdaptorHostScsiLunRefEntry 3 }

cucsAdaptorHostScsiLunRefBootDev OBJECT-TYPE
    SYNTAX       CucsLstorageBootDevice
    MAX-ACCESS   read-only
    STATUS       current
    DESCRIPTION
        "Cisco UCS adaptor:HostScsiLunRef:bootDev managed object property"
    ::= { cucsAdaptorHostScsiLunRefEntry 4 }

cucsAdaptorHostScsiLunRefFltAggr OBJECT-TYPE
    SYNTAX       Unsigned64
    MAX-ACCESS   read-only
    STATUS       current
    DESCRIPTION
        "Cisco UCS adaptor:HostScsiLunRef:fltAggr managed object property"
    ::= { cucsAdaptorHostScsiLunRefEntry 5 }

cucsAdaptorHostScsiLunRefLunDn OBJECT-TYPE
    SYNTAX       SnmpAdminString
    MAX-ACCESS   read-only
    STATUS       current
    DESCRIPTION
        "Cisco UCS adaptor:HostScsiLunRef:lunDn managed object property"
    ::= { cucsAdaptorHostScsiLunRefEntry 6 }

cucsAdaptorHostScsiLunRefLunId OBJECT-TYPE
    SYNTAX       Gauge32
    MAX-ACCESS   read-only
    STATUS       current
    DESCRIPTION
        "Cisco UCS adaptor:HostScsiLunRef:lunId managed object property"
    ::= { cucsAdaptorHostScsiLunRefEntry 7 }

cucsAdaptorHostScsiLunRefLunName OBJECT-TYPE
    SYNTAX       SnmpAdminString
    MAX-ACCESS   read-only
    STATUS       current
    DESCRIPTION
        "Cisco UCS adaptor:HostScsiLunRef:lunName managed object property"
    ::= { cucsAdaptorHostScsiLunRefEntry 8 }

cucsAdaptorHostScsiLunRefLunOrder OBJECT-TYPE
    SYNTAX       Gauge32
    MAX-ACCESS   read-only
    STATUS       current
    DESCRIPTION
        "Cisco UCS adaptor:HostScsiLunRef:lunOrder managed
        object property"
    ::= { cucsAdaptorHostScsiLunRefEntry 9 }

cucsAdaptorHostScsiLunRefOperLunId OBJECT-TYPE
    SYNTAX       Gauge32
    MAX-ACCESS   read-only
    STATUS       current
    DESCRIPTION
        "Cisco UCS adaptor:HostScsiLunRef:operLunId managed
        object property"
    ::= { cucsAdaptorHostScsiLunRefEntry 10 }

cucsAdaptorHostScsiLunRefOperLunOrder OBJECT-TYPE
    SYNTAX       Gauge32
    MAX-ACCESS   read-only
    STATUS       current
    DESCRIPTION
        "Cisco UCS adaptor:HostScsiLunRef:operLunOrder
        managed object property"
    ::= { cucsAdaptorHostScsiLunRefEntry 11 }

cucsAdaptorHostServiceEthIfTable OBJECT-TYPE
    SYNTAX           SEQUENCE OF CucsAdaptorHostServiceEthIfEntry
    MAX-ACCESS       not-accessible
    STATUS           current
    DESCRIPTION
        "Cisco UCS adaptor:HostServiceEthIf managed object table"
    ::= { cucsAdaptorObjects 114 }

cucsAdaptorHostServiceEthIfEntry OBJECT-TYPE
    SYNTAX           CucsAdaptorHostServiceEthIfEntry
    MAX-ACCESS       not-accessible
    STATUS           current
    DESCRIPTION
        "Entry for the cucsAdaptorHostServiceEthIfTable table."
    INDEX { cucsAdaptorHostServiceEthIfInstanceId }
    ::= { cucsAdaptorHostServiceEthIfTable 1 }

CucsAdaptorHostServiceEthIfEntry ::= SEQUENCE {
    cucsAdaptorHostServiceEthIfInstanceId                            CucsManagedObjectId,
    cucsAdaptorHostServiceEthIfDn                                    CucsManagedObjectDn,
    cucsAdaptorHostServiceEthIfRn                                    SnmpAdminString,
    cucsAdaptorHostServiceEthIfAdminState                            CucsAdaptorHostIfAdminState,
    cucsAdaptorHostServiceEthIfBootDev                               CucsAdaptorHostIfBootDev,
    cucsAdaptorHostServiceEthIfChassisId                             Gauge32,
    cucsAdaptorHostServiceEthIfDiscovery                             CucsEtherSatelliteConnectionDisc,
    cucsAdaptorHostServiceEthIfEpDn                                  SnmpAdminString,
    cucsAdaptorHostServiceEthIfFltAggr                               Unsigned64,
    cucsAdaptorHostServiceEthIfId                                    Gauge32,
    cucsAdaptorHostServiceEthIfIfRole                                CucsAdaptorHostServiceEthIfIfRole,
    cucsAdaptorHostServiceEthIfIfType                                CucsNetworkPhysEpIfType,
    cucsAdaptorHostServiceEthIfLc                                    CucsFsmLifecycle,
    cucsAdaptorHostServiceEthIfLinkState                             CucsAdaptorLinkState,
    cucsAdaptorHostServiceEthIfLocale                                CucsNetworkLocale,
    cucsAdaptorHostServiceEthIfMac                                   MacAddress,
    cucsAdaptorHostServiceEthIfModel                                 SnmpAdminString,
    cucsAdaptorHostServiceEthIfMtu                                   Gauge32,
    cucsAdaptorHostServiceEthIfName                                  SnmpAdminString,
    cucsAdaptorHostServiceEthIfOperQualifierReason                   SnmpAdminString,
    cucsAdaptorHostServiceEthIfOperState                             CucsEquipmentOperability,
    cucsAdaptorHostServiceEthIfOperability                           CucsEquipmentOperability,
    cucsAdaptorHostServiceEthIfOrder                                 Gauge32,
    cucsAdaptorHostServiceEthIfOriginalMac                           MacAddress,
    cucsAdaptorHostServiceEthIfPciAddr                               SnmpAdminString,
    cucsAdaptorHostServiceEthIfPciFunc                               Gauge32,
    cucsAdaptorHostServiceEthIfPciSlot                               Gauge32,
    cucsAdaptorHostServiceEthIfPeerChassisId                         Gauge32,
    cucsAdaptorHostServiceEthIfPeerDn                                SnmpAdminString,
    cucsAdaptorHostServiceEthIfPeerPortId                            Gauge32,
    cucsAdaptorHostServiceEthIfPeerSlotId                            Gauge32,
    cucsAdaptorHostServiceEthIfPerf                                  CucsEquipmentSensorThresholdStatus,
    cucsAdaptorHostServiceEthIfPortId                                Gauge32,
    cucsAdaptorHostServiceEthIfPower                                 CucsEquipmentPowerState,
    cucsAdaptorHostServiceEthIfPresence                              CucsEquipmentPresence,
    cucsAdaptorHostServiceEthIfPurpose                               CucsAdaptorPurpose,
    cucsAdaptorHostServiceEthIfRevision                              SnmpAdminString,
    cucsAdaptorHostServiceEthIfSerial                                SnmpAdminString,
    cucsAdaptorHostServiceEthIfSide                                  CucsNetworkSide,
    cucsAdaptorHostServiceEthIfSlotId                                Gauge32,
    cucsAdaptorHostServiceEthIfSwitchId                              CucsNetworkSwitchId,
    cucsAdaptorHostServiceEthIfThermal                               CucsEquipmentSensorThresholdStatus,
    cucsAdaptorHostServiceEthIfTransport                             CucsNetworkTransport,
    cucsAdaptorHostServiceEthIfType                                  CucsNetworkConnectionType,
    cucsAdaptorHostServiceEthIfVendor                                SnmpAdminString,
    cucsAdaptorHostServiceEthIfVnicDn                                SnmpAdminString,
    cucsAdaptorHostServiceEthIfVoltage                               CucsEquipmentSensorThresholdStatus,
    cucsAdaptorHostServiceEthIfCdnName                               SnmpAdminString
}

cucsAdaptorHostServiceEthIfInstanceId OBJECT-TYPE
    SYNTAX       CucsManagedObjectId
    MAX-ACCESS   not-accessible
    STATUS       current
    DESCRIPTION
        "Instance identifier of the managed object."
    ::= { cucsAdaptorHostServiceEthIfEntry 1 }

cucsAdaptorHostServiceEthIfDn OBJECT-TYPE
    SYNTAX       CucsManagedObjectDn
    MAX-ACCESS   read-only
    STATUS       current
    DESCRIPTION
        "Cisco UCS adaptor:HostServiceEthIf:dn managed object property"
    ::= { cucsAdaptorHostServiceEthIfEntry 2 }

cucsAdaptorHostServiceEthIfRn OBJECT-TYPE
    SYNTAX       SnmpAdminString
    MAX-ACCESS   read-only
    STATUS       current
    DESCRIPTION
        "Cisco UCS adaptor:HostServiceEthIf:rn managed object property"
    ::= { cucsAdaptorHostServiceEthIfEntry 3 }

cucsAdaptorHostServiceEthIfAdminState OBJECT-TYPE
    SYNTAX       CucsAdaptorHostIfAdminState
    MAX-ACCESS   read-only
    STATUS       current
    DESCRIPTION
        "Cisco UCS adaptor:HostServiceEthIf:adminState
        managed object property"
    ::= { cucsAdaptorHostServiceEthIfEntry 4 }

cucsAdaptorHostServiceEthIfBootDev OBJECT-TYPE
    SYNTAX       CucsAdaptorHostIfBootDev
    MAX-ACCESS   read-only
    STATUS       current
    DESCRIPTION
        "Cisco UCS adaptor:HostServiceEthIf:bootDev managed
        object property"
    ::= { cucsAdaptorHostServiceEthIfEntry 5 }

cucsAdaptorHostServiceEthIfChassisId OBJECT-TYPE
    SYNTAX       Gauge32
    MAX-ACCESS   read-only
    STATUS       current
    DESCRIPTION
        "Cisco UCS adaptor:HostServiceEthIf:chassisId managed
        object property"
    ::= { cucsAdaptorHostServiceEthIfEntry 6 }

cucsAdaptorHostServiceEthIfDiscovery OBJECT-TYPE
    SYNTAX       CucsEtherSatelliteConnectionDisc
    MAX-ACCESS   read-only
    STATUS       current
    DESCRIPTION
        "Cisco UCS adaptor:HostServiceEthIf:discovery managed
        object property"
    ::= { cucsAdaptorHostServiceEthIfEntry 7 }

cucsAdaptorHostServiceEthIfEpDn OBJECT-TYPE
    SYNTAX       SnmpAdminString
    MAX-ACCESS   read-only
    STATUS       current
    DESCRIPTION
        "Cisco UCS adaptor:HostServiceEthIf:epDn managed object property"
    ::= { cucsAdaptorHostServiceEthIfEntry 8 }

cucsAdaptorHostServiceEthIfFltAggr OBJECT-TYPE
    SYNTAX       Unsigned64
    MAX-ACCESS   read-only
    STATUS       current
    DESCRIPTION
        "Cisco UCS adaptor:HostServiceEthIf:fltAggr managed
        object property"
    ::= { cucsAdaptorHostServiceEthIfEntry 9 }

cucsAdaptorHostServiceEthIfId OBJECT-TYPE
    SYNTAX       Gauge32
    MAX-ACCESS   read-only
    STATUS       current
    DESCRIPTION
        "Cisco UCS adaptor:HostServiceEthIf:id managed object property"
    ::= { cucsAdaptorHostServiceEthIfEntry 10 }

cucsAdaptorHostServiceEthIfIfRole OBJECT-TYPE
    SYNTAX       CucsAdaptorHostServiceEthIfIfRole
    MAX-ACCESS   read-only
    STATUS       current
    DESCRIPTION
        "Cisco UCS adaptor:HostServiceEthIf:ifRole managed
        object property"
    ::= { cucsAdaptorHostServiceEthIfEntry 11 }

cucsAdaptorHostServiceEthIfIfType OBJECT-TYPE
    SYNTAX       CucsNetworkPhysEpIfType
    MAX-ACCESS   read-only
    STATUS       current
    DESCRIPTION
        "Cisco UCS adaptor:HostServiceEthIf:ifType managed
        object property"
    ::= { cucsAdaptorHostServiceEthIfEntry 12 }

cucsAdaptorHostServiceEthIfLc OBJECT-TYPE
    SYNTAX       CucsFsmLifecycle
    MAX-ACCESS   read-only
    STATUS       current
    DESCRIPTION
        "Cisco UCS adaptor:HostServiceEthIf:lc managed object property"
    ::= { cucsAdaptorHostServiceEthIfEntry 13 }

cucsAdaptorHostServiceEthIfLinkState OBJECT-TYPE
    SYNTAX       CucsAdaptorLinkState
    MAX-ACCESS   read-only
    STATUS       current
    DESCRIPTION
        "Cisco UCS adaptor:HostServiceEthIf:linkState managed
        object property"
    ::= { cucsAdaptorHostServiceEthIfEntry 14 }

cucsAdaptorHostServiceEthIfLocale OBJECT-TYPE
    SYNTAX       CucsNetworkLocale
    MAX-ACCESS   read-only
    STATUS       current
    DESCRIPTION
        "Cisco UCS adaptor:HostServiceEthIf:locale managed
        object property"
    ::= { cucsAdaptorHostServiceEthIfEntry 15 }

cucsAdaptorHostServiceEthIfMac OBJECT-TYPE
    SYNTAX       MacAddress
    MAX-ACCESS   read-only
    STATUS       current
    DESCRIPTION
        "Cisco UCS adaptor:HostServiceEthIf:mac managed object property"
    ::= { cucsAdaptorHostServiceEthIfEntry 16 }

cucsAdaptorHostServiceEthIfModel OBJECT-TYPE
    SYNTAX       SnmpAdminString
    MAX-ACCESS   read-only
    STATUS       current
    DESCRIPTION
        "Cisco UCS adaptor:HostServiceEthIf:model managed object property"
    ::= { cucsAdaptorHostServiceEthIfEntry 17 }

cucsAdaptorHostServiceEthIfMtu OBJECT-TYPE
    SYNTAX       Gauge32
    MAX-ACCESS   read-only
    STATUS       current
    DESCRIPTION
        "Cisco UCS adaptor:HostServiceEthIf:mtu managed object property"
    ::= { cucsAdaptorHostServiceEthIfEntry 18 }

cucsAdaptorHostServiceEthIfName OBJECT-TYPE
    SYNTAX       SnmpAdminString
    MAX-ACCESS   read-only
    STATUS       current
    DESCRIPTION
        "Cisco UCS adaptor:HostServiceEthIf:name managed object property"
    ::= { cucsAdaptorHostServiceEthIfEntry 19 }

cucsAdaptorHostServiceEthIfOperQualifierReason OBJECT-TYPE
    SYNTAX       SnmpAdminString
    MAX-ACCESS   read-only
    STATUS       current
    DESCRIPTION
        "Cisco UCS adaptor:HostServiceEthIf:operQualifierReason
        managed object property"
    ::= { cucsAdaptorHostServiceEthIfEntry 20 }

cucsAdaptorHostServiceEthIfOperState OBJECT-TYPE
    SYNTAX       CucsEquipmentOperability
    MAX-ACCESS   read-only
    STATUS       current
    DESCRIPTION
        "Cisco UCS adaptor:HostServiceEthIf:operState managed
        object property"
    ::= { cucsAdaptorHostServiceEthIfEntry 21 }

cucsAdaptorHostServiceEthIfOperability OBJECT-TYPE
    SYNTAX       CucsEquipmentOperability
    MAX-ACCESS   read-only
    STATUS       current
    DESCRIPTION
        "Cisco UCS adaptor:HostServiceEthIf:operability
        managed object property"
    ::= { cucsAdaptorHostServiceEthIfEntry 22 }

cucsAdaptorHostServiceEthIfOrder OBJECT-TYPE
    SYNTAX       Gauge32
    MAX-ACCESS   read-only
    STATUS       current
    DESCRIPTION
        "Cisco UCS adaptor:HostServiceEthIf:order managed object property"
    ::= { cucsAdaptorHostServiceEthIfEntry 23 }

cucsAdaptorHostServiceEthIfOriginalMac OBJECT-TYPE
    SYNTAX       MacAddress
    MAX-ACCESS   read-only
    STATUS       current
    DESCRIPTION
        "Cisco UCS adaptor:HostServiceEthIf:originalMac
        managed object property"
    ::= { cucsAdaptorHostServiceEthIfEntry 24 }

cucsAdaptorHostServiceEthIfPciAddr OBJECT-TYPE
    SYNTAX       SnmpAdminString
    MAX-ACCESS   read-only
    STATUS       current
    DESCRIPTION
        "Cisco UCS adaptor:HostServiceEthIf:pciAddr managed
        object property"
    ::= { cucsAdaptorHostServiceEthIfEntry 25 }

cucsAdaptorHostServiceEthIfPciFunc OBJECT-TYPE
    SYNTAX       Gauge32
    MAX-ACCESS   read-only
    STATUS       current
    DESCRIPTION
        "Cisco UCS adaptor:HostServiceEthIf:pciFunc managed
        object property"
    ::= { cucsAdaptorHostServiceEthIfEntry 26 }

cucsAdaptorHostServiceEthIfPciSlot OBJECT-TYPE
    SYNTAX       Gauge32
    MAX-ACCESS   read-only
    STATUS       current
    DESCRIPTION
        "Cisco UCS adaptor:HostServiceEthIf:pciSlot managed
        object property"
    ::= { cucsAdaptorHostServiceEthIfEntry 27 }

cucsAdaptorHostServiceEthIfPeerChassisId OBJECT-TYPE
    SYNTAX       Gauge32
    MAX-ACCESS   read-only
    STATUS       current
    DESCRIPTION
        "Cisco UCS adaptor:HostServiceEthIf:peerChassisId
        managed object property"
    ::= { cucsAdaptorHostServiceEthIfEntry 28 }

cucsAdaptorHostServiceEthIfPeerDn OBJECT-TYPE
    SYNTAX       SnmpAdminString
    MAX-ACCESS   read-only
    STATUS       current
    DESCRIPTION
        "Cisco UCS adaptor:HostServiceEthIf:peerDn managed
        object property"
    ::= { cucsAdaptorHostServiceEthIfEntry 29 }

cucsAdaptorHostServiceEthIfPeerPortId OBJECT-TYPE
    SYNTAX       Gauge32
    MAX-ACCESS   read-only
    STATUS       current
    DESCRIPTION
        "Cisco UCS adaptor:HostServiceEthIf:peerPortId
        managed object property"
    ::= { cucsAdaptorHostServiceEthIfEntry 30 }

cucsAdaptorHostServiceEthIfPeerSlotId OBJECT-TYPE
    SYNTAX       Gauge32
    MAX-ACCESS   read-only
    STATUS       current
    DESCRIPTION
        "Cisco UCS adaptor:HostServiceEthIf:peerSlotId
        managed object property"
    ::= { cucsAdaptorHostServiceEthIfEntry 31 }

cucsAdaptorHostServiceEthIfPerf OBJECT-TYPE
    SYNTAX       CucsEquipmentSensorThresholdStatus
    MAX-ACCESS   read-only
    STATUS       current
    DESCRIPTION
        "Cisco UCS adaptor:HostServiceEthIf:perf managed object property"
    ::= { cucsAdaptorHostServiceEthIfEntry 32 }

cucsAdaptorHostServiceEthIfPortId OBJECT-TYPE
    SYNTAX       Gauge32
    MAX-ACCESS   read-only
    STATUS       current
    DESCRIPTION
        "Cisco UCS adaptor:HostServiceEthIf:portId managed
        object property"
    ::= { cucsAdaptorHostServiceEthIfEntry 33 }

cucsAdaptorHostServiceEthIfPower OBJECT-TYPE
    SYNTAX       CucsEquipmentPowerState
    MAX-ACCESS   read-only
    STATUS       current
    DESCRIPTION
        "Cisco UCS adaptor:HostServiceEthIf:power managed object property"
    ::= { cucsAdaptorHostServiceEthIfEntry 34 }

cucsAdaptorHostServiceEthIfPresence OBJECT-TYPE
    SYNTAX       CucsEquipmentPresence
    MAX-ACCESS   read-only
    STATUS       current
    DESCRIPTION
        "Cisco UCS adaptor:HostServiceEthIf:presence managed
        object property"
    ::= { cucsAdaptorHostServiceEthIfEntry 35 }

cucsAdaptorHostServiceEthIfPurpose OBJECT-TYPE
    SYNTAX       CucsAdaptorPurpose
    MAX-ACCESS   read-only
    STATUS       current
    DESCRIPTION
        "Cisco UCS adaptor:HostServiceEthIf:purpose managed
        object property"
    ::= { cucsAdaptorHostServiceEthIfEntry 36 }

cucsAdaptorHostServiceEthIfRevision OBJECT-TYPE
    SYNTAX       SnmpAdminString
    MAX-ACCESS   read-only
    STATUS       current
    DESCRIPTION
        "Cisco UCS adaptor:HostServiceEthIf:revision managed
        object property"
    ::= { cucsAdaptorHostServiceEthIfEntry 37 }

cucsAdaptorHostServiceEthIfSerial OBJECT-TYPE
    SYNTAX       SnmpAdminString
    MAX-ACCESS   read-only
    STATUS       current
    DESCRIPTION
        "Cisco UCS adaptor:HostServiceEthIf:serial managed
        object property"
    ::= { cucsAdaptorHostServiceEthIfEntry 38 }

cucsAdaptorHostServiceEthIfSide OBJECT-TYPE
    SYNTAX       CucsNetworkSide
    MAX-ACCESS   read-only
    STATUS       current
    DESCRIPTION
        "Cisco UCS adaptor:HostServiceEthIf:side managed object property"
    ::= { cucsAdaptorHostServiceEthIfEntry 39 }

cucsAdaptorHostServiceEthIfSlotId OBJECT-TYPE
    SYNTAX       Gauge32
    MAX-ACCESS   read-only
    STATUS       current
    DESCRIPTION
        "Cisco UCS adaptor:HostServiceEthIf:slotId managed
        object property"
    ::= { cucsAdaptorHostServiceEthIfEntry 40 }

cucsAdaptorHostServiceEthIfSwitchId OBJECT-TYPE
    SYNTAX       CucsNetworkSwitchId
    MAX-ACCESS   read-only
    STATUS       current
    DESCRIPTION
        "Cisco UCS adaptor:HostServiceEthIf:switchId managed
        object property"
    ::= { cucsAdaptorHostServiceEthIfEntry 41 }

cucsAdaptorHostServiceEthIfThermal OBJECT-TYPE
    SYNTAX       CucsEquipmentSensorThresholdStatus
    MAX-ACCESS   read-only
    STATUS       current
    DESCRIPTION
        "Cisco UCS adaptor:HostServiceEthIf:thermal managed
        object property"
    ::= { cucsAdaptorHostServiceEthIfEntry 42 }

cucsAdaptorHostServiceEthIfTransport OBJECT-TYPE
    SYNTAX       CucsNetworkTransport
    MAX-ACCESS   read-only
    STATUS       current
    DESCRIPTION
        "Cisco UCS adaptor:HostServiceEthIf:transport managed
        object property"
    ::= { cucsAdaptorHostServiceEthIfEntry 43 }

cucsAdaptorHostServiceEthIfType OBJECT-TYPE
    SYNTAX       CucsNetworkConnectionType
    MAX-ACCESS   read-only
    STATUS       current
    DESCRIPTION
        "Cisco UCS adaptor:HostServiceEthIf:type managed object property"
    ::= { cucsAdaptorHostServiceEthIfEntry 44 }

cucsAdaptorHostServiceEthIfVendor OBJECT-TYPE
    SYNTAX       SnmpAdminString
    MAX-ACCESS   read-only
    STATUS       current
    DESCRIPTION
        "Cisco UCS adaptor:HostServiceEthIf:vendor managed
        object property"
    ::= { cucsAdaptorHostServiceEthIfEntry 45 }

cucsAdaptorHostServiceEthIfVnicDn OBJECT-TYPE
    SYNTAX       SnmpAdminString
    MAX-ACCESS   read-only
    STATUS       current
    DESCRIPTION
        "Cisco UCS adaptor:HostServiceEthIf:vnicDn managed
        object property"
    ::= { cucsAdaptorHostServiceEthIfEntry 46 }

cucsAdaptorHostServiceEthIfVoltage OBJECT-TYPE
    SYNTAX       CucsEquipmentSensorThresholdStatus
    MAX-ACCESS   read-only
    STATUS       current
    DESCRIPTION
        "Cisco UCS adaptor:HostServiceEthIf:voltage managed
        object property"
    ::= { cucsAdaptorHostServiceEthIfEntry 47 }

cucsAdaptorHostServiceEthIfCdnName OBJECT-TYPE
    SYNTAX       SnmpAdminString
    MAX-ACCESS   read-only
    STATUS       current
    DESCRIPTION
        "Cisco UCS adaptor:HostServiceEthIf:cdnName managed
        object property"
    ::= { cucsAdaptorHostServiceEthIfEntry 48 }

cucsAdaptorHostVnicHwAddrCapTable OBJECT-TYPE
    SYNTAX           SEQUENCE OF CucsAdaptorHostVnicHwAddrCapEntry
    MAX-ACCESS       not-accessible
    STATUS           current
    DESCRIPTION
        "Cisco UCS adaptor:HostVnicHwAddrCap managed object table"
    ::= { cucsAdaptorObjects 123 }

cucsAdaptorHostVnicHwAddrCapEntry OBJECT-TYPE
    SYNTAX           CucsAdaptorHostVnicHwAddrCapEntry
    MAX-ACCESS       not-accessible
    STATUS           current
    DESCRIPTION
        "Entry for the cucsAdaptorHostVnicHwAddrCapTable table."
    INDEX { cucsAdaptorHostVnicHwAddrCapInstanceId }
    ::= { cucsAdaptorHostVnicHwAddrCapTable 1 }

CucsAdaptorHostVnicHwAddrCapEntry ::= SEQUENCE {
    cucsAdaptorHostVnicHwAddrCapInstanceId                           CucsManagedObjectId,
    cucsAdaptorHostVnicHwAddrCapDn                                   CucsManagedObjectDn,
    cucsAdaptorHostVnicHwAddrCapRn                                   SnmpAdminString,
    cucsAdaptorHostVnicHwAddrCapMacOffset1                           Gauge32,
    cucsAdaptorHostVnicHwAddrCapMacOffset2                           Gauge32,
    cucsAdaptorHostVnicHwAddrCapMacOffsetVnicFrom                    Gauge32,
    cucsAdaptorHostVnicHwAddrCapMacOffsetVnicTo                      Gauge32
}

cucsAdaptorHostVnicHwAddrCapInstanceId OBJECT-TYPE
    SYNTAX       CucsManagedObjectId
    MAX-ACCESS   not-accessible
    STATUS       current
    DESCRIPTION
        "Instance identifier of the managed object."
    ::= { cucsAdaptorHostVnicHwAddrCapEntry 1 }

cucsAdaptorHostVnicHwAddrCapDn OBJECT-TYPE
    SYNTAX       CucsManagedObjectDn
    MAX-ACCESS   read-only
    STATUS       current
    DESCRIPTION
        "Cisco UCS adaptor:HostVnicHwAddrCap:dn managed object property"
    ::= { cucsAdaptorHostVnicHwAddrCapEntry 2 }

cucsAdaptorHostVnicHwAddrCapRn OBJECT-TYPE
    SYNTAX       SnmpAdminString
    MAX-ACCESS   read-only
    STATUS       current
    DESCRIPTION
        "Cisco UCS adaptor:HostVnicHwAddrCap:rn managed object property"
    ::= { cucsAdaptorHostVnicHwAddrCapEntry 3 }

cucsAdaptorHostVnicHwAddrCapMacOffset1 OBJECT-TYPE
    SYNTAX       Gauge32
    MAX-ACCESS   read-only
    STATUS       current
    DESCRIPTION
        "Cisco UCS adaptor:HostVnicHwAddrCap:macOffset1
        managed object property"
    ::= { cucsAdaptorHostVnicHwAddrCapEntry 4 }

cucsAdaptorHostVnicHwAddrCapMacOffset2 OBJECT-TYPE
    SYNTAX       Gauge32
    MAX-ACCESS   read-only
    STATUS       current
    DESCRIPTION
        "Cisco UCS adaptor:HostVnicHwAddrCap:macOffset2
        managed object property"
    ::= { cucsAdaptorHostVnicHwAddrCapEntry 5 }

cucsAdaptorHostVnicHwAddrCapMacOffsetVnicFrom OBJECT-TYPE
    SYNTAX       Gauge32
    MAX-ACCESS   read-only
    STATUS       current
    DESCRIPTION
        "Cisco UCS adaptor:HostVnicHwAddrCap:macOffsetVnicFrom
        managed object property"
    ::= { cucsAdaptorHostVnicHwAddrCapEntry 6 }

cucsAdaptorHostVnicHwAddrCapMacOffsetVnicTo OBJECT-TYPE
    SYNTAX       Gauge32
    MAX-ACCESS   read-only
    STATUS       current
    DESCRIPTION
        "Cisco UCS adaptor:HostVnicHwAddrCap:macOffsetVnicTo
        managed object property"
    ::= { cucsAdaptorHostVnicHwAddrCapEntry 7 }

cucsAdaptorHostethHwAddrCapTable OBJECT-TYPE
    SYNTAX           SEQUENCE OF CucsAdaptorHostethHwAddrCapEntry
    MAX-ACCESS       not-accessible
    STATUS           current
    DESCRIPTION
        "Cisco UCS adaptor:HostethHwAddrCap managed object table"
    ::= { cucsAdaptorObjects 91 }

cucsAdaptorHostethHwAddrCapEntry OBJECT-TYPE
    SYNTAX           CucsAdaptorHostethHwAddrCapEntry
    MAX-ACCESS       not-accessible
    STATUS           current
    DESCRIPTION
        "Entry for the cucsAdaptorHostethHwAddrCapTable table."
    INDEX { cucsAdaptorHostethHwAddrCapInstanceId }
    ::= { cucsAdaptorHostethHwAddrCapTable 1 }

CucsAdaptorHostethHwAddrCapEntry ::= SEQUENCE {
    cucsAdaptorHostethHwAddrCapInstanceId                            CucsManagedObjectId,
    cucsAdaptorHostethHwAddrCapDn                                    CucsManagedObjectDn,
    cucsAdaptorHostethHwAddrCapRn                                    SnmpAdminString,
    cucsAdaptorHostethHwAddrCapMacOffset1                            Gauge32,
    cucsAdaptorHostethHwAddrCapMacOffset2                            Gauge32,
    cucsAdaptorHostethHwAddrCapLegacyMacOffset1                      Gauge32,
    cucsAdaptorHostethHwAddrCapLegacyMacOffset2                      Gauge32
}

cucsAdaptorHostethHwAddrCapInstanceId OBJECT-TYPE
    SYNTAX       CucsManagedObjectId
    MAX-ACCESS   not-accessible
    STATUS       current
    DESCRIPTION
        "Instance identifier of the managed object."
    ::= { cucsAdaptorHostethHwAddrCapEntry 1 }

cucsAdaptorHostethHwAddrCapDn OBJECT-TYPE
    SYNTAX       CucsManagedObjectDn
    MAX-ACCESS   read-only
    STATUS       current
    DESCRIPTION
        "Cisco UCS adaptor:HostethHwAddrCap:dn managed object property"
    ::= { cucsAdaptorHostethHwAddrCapEntry 2 }

cucsAdaptorHostethHwAddrCapRn OBJECT-TYPE
    SYNTAX       SnmpAdminString
    MAX-ACCESS   read-only
    STATUS       current
    DESCRIPTION
        "Cisco UCS adaptor:HostethHwAddrCap:rn managed object property"
    ::= { cucsAdaptorHostethHwAddrCapEntry 3 }

cucsAdaptorHostethHwAddrCapMacOffset1 OBJECT-TYPE
    SYNTAX       Gauge32
    MAX-ACCESS   read-only
    STATUS       current
    DESCRIPTION
        "Cisco UCS adaptor:HostethHwAddrCap:macOffset1
        managed object property"
    ::= { cucsAdaptorHostethHwAddrCapEntry 4 }

cucsAdaptorHostethHwAddrCapMacOffset2 OBJECT-TYPE
    SYNTAX       Gauge32
    MAX-ACCESS   read-only
    STATUS       current
    DESCRIPTION
        "Cisco UCS adaptor:HostethHwAddrCap:macOffset2
        managed object property"
    ::= { cucsAdaptorHostethHwAddrCapEntry 5 }

cucsAdaptorHostethHwAddrCapLegacyMacOffset1 OBJECT-TYPE
    SYNTAX       Gauge32
    MAX-ACCESS   read-only
    STATUS       current
    DESCRIPTION
        "Cisco UCS adaptor:HostethHwAddrCap:legacyMacOffset1
        managed object property"
    ::= { cucsAdaptorHostethHwAddrCapEntry 6 }

cucsAdaptorHostethHwAddrCapLegacyMacOffset2 OBJECT-TYPE
    SYNTAX       Gauge32
    MAX-ACCESS   read-only
    STATUS       current
    DESCRIPTION
        "Cisco UCS adaptor:HostethHwAddrCap:legacyMacOffset2
        managed object property"
    ::= { cucsAdaptorHostethHwAddrCapEntry 7 }

cucsAdaptorHostfcHwAddrCapTable OBJECT-TYPE
    SYNTAX           SEQUENCE OF CucsAdaptorHostfcHwAddrCapEntry
    MAX-ACCESS       not-accessible
    STATUS           current
    DESCRIPTION
        "Cisco UCS adaptor:HostfcHwAddrCap managed object table"
    ::= { cucsAdaptorObjects 92 }

cucsAdaptorHostfcHwAddrCapEntry OBJECT-TYPE
    SYNTAX           CucsAdaptorHostfcHwAddrCapEntry
    MAX-ACCESS       not-accessible
    STATUS           current
    DESCRIPTION
        "Entry for the cucsAdaptorHostfcHwAddrCapTable table."
    INDEX { cucsAdaptorHostfcHwAddrCapInstanceId }
    ::= { cucsAdaptorHostfcHwAddrCapTable 1 }

CucsAdaptorHostfcHwAddrCapEntry ::= SEQUENCE {
    cucsAdaptorHostfcHwAddrCapInstanceId                             CucsManagedObjectId,
    cucsAdaptorHostfcHwAddrCapDn                                     CucsManagedObjectDn,
    cucsAdaptorHostfcHwAddrCapRn                                     SnmpAdminString,
    cucsAdaptorHostfcHwAddrCapMacOffset1                             Gauge32,
    cucsAdaptorHostfcHwAddrCapMacOffset2                             Gauge32,
    cucsAdaptorHostfcHwAddrCapWwnReverseMaskA                        Unsigned64,
    cucsAdaptorHostfcHwAddrCapWwnReverseMaskB                        Unsigned64,
    cucsAdaptorHostfcHwAddrCapWwnnReverseMaskA                       Unsigned64,
    cucsAdaptorHostfcHwAddrCapWwnnReverseMaskB                       Unsigned64
}

cucsAdaptorHostfcHwAddrCapInstanceId OBJECT-TYPE
    SYNTAX       CucsManagedObjectId
    MAX-ACCESS   not-accessible
    STATUS       current
    DESCRIPTION
        "Instance identifier of the managed object."
    ::= { cucsAdaptorHostfcHwAddrCapEntry 1 }

cucsAdaptorHostfcHwAddrCapDn OBJECT-TYPE
    SYNTAX       CucsManagedObjectDn
    MAX-ACCESS   read-only
    STATUS       current
    DESCRIPTION
        "Cisco UCS adaptor:HostfcHwAddrCap:dn managed object property"
    ::= { cucsAdaptorHostfcHwAddrCapEntry 2 }

cucsAdaptorHostfcHwAddrCapRn OBJECT-TYPE
    SYNTAX       SnmpAdminString
    MAX-ACCESS   read-only
    STATUS       current
    DESCRIPTION
        "Cisco UCS adaptor:HostfcHwAddrCap:rn managed object property"
    ::= { cucsAdaptorHostfcHwAddrCapEntry 3 }

cucsAdaptorHostfcHwAddrCapMacOffset1 OBJECT-TYPE
    SYNTAX       Gauge32
    MAX-ACCESS   read-only
    STATUS       current
    DESCRIPTION
        "Cisco UCS adaptor:HostfcHwAddrCap:macOffset1 managed
        object property"
    ::= { cucsAdaptorHostfcHwAddrCapEntry 4 }

cucsAdaptorHostfcHwAddrCapMacOffset2 OBJECT-TYPE
    SYNTAX       Gauge32
    MAX-ACCESS   read-only
    STATUS       current
    DESCRIPTION
        "Cisco UCS adaptor:HostfcHwAddrCap:macOffset2 managed
        object property"
    ::= { cucsAdaptorHostfcHwAddrCapEntry 5 }

cucsAdaptorHostfcHwAddrCapWwnReverseMaskA OBJECT-TYPE
    SYNTAX       Unsigned64
    MAX-ACCESS   read-only
    STATUS       current
    DESCRIPTION
        "Cisco UCS adaptor:HostfcHwAddrCap:wwnReverseMaskA
        managed object property"
    ::= { cucsAdaptorHostfcHwAddrCapEntry 6 }

cucsAdaptorHostfcHwAddrCapWwnReverseMaskB OBJECT-TYPE
    SYNTAX       Unsigned64
    MAX-ACCESS   read-only
    STATUS       current
    DESCRIPTION
        "Cisco UCS adaptor:HostfcHwAddrCap:wwnReverseMaskB
        managed object property"
    ::= { cucsAdaptorHostfcHwAddrCapEntry 7 }

cucsAdaptorHostfcHwAddrCapWwnnReverseMaskA OBJECT-TYPE
    SYNTAX       Unsigned64
    MAX-ACCESS   read-only
    STATUS       current
    DESCRIPTION
        "Cisco UCS adaptor:HostfcHwAddrCap:wwnnReverseMaskA
        managed object property"
    ::= { cucsAdaptorHostfcHwAddrCapEntry 8 }

cucsAdaptorHostfcHwAddrCapWwnnReverseMaskB OBJECT-TYPE
    SYNTAX       Unsigned64
    MAX-ACCESS   read-only
    STATUS       current
    DESCRIPTION
        "Cisco UCS adaptor:HostfcHwAddrCap:wwnnReverseMaskB
        managed object property"
    ::= { cucsAdaptorHostfcHwAddrCapEntry 9 }

cucsAdaptorIScsiCapTable OBJECT-TYPE
    SYNTAX           SEQUENCE OF CucsAdaptorIScsiCapEntry
    MAX-ACCESS       not-accessible
    STATUS           current
    DESCRIPTION
        "Cisco UCS adaptor:IScsiCap managed object table"
    ::= { cucsAdaptorObjects 101 }

cucsAdaptorIScsiCapEntry OBJECT-TYPE
    SYNTAX           CucsAdaptorIScsiCapEntry
    MAX-ACCESS       not-accessible
    STATUS           current
    DESCRIPTION
        "Entry for the cucsAdaptorIScsiCapTable table."
    INDEX { cucsAdaptorIScsiCapInstanceId }
    ::= { cucsAdaptorIScsiCapTable 1 }

CucsAdaptorIScsiCapEntry ::= SEQUENCE {
    cucsAdaptorIScsiCapInstanceId                                    CucsManagedObjectId,
    cucsAdaptorIScsiCapDn                                            CucsManagedObjectDn,
    cucsAdaptorIScsiCapRn                                            SnmpAdminString,
    cucsAdaptorIScsiCapMacOffset1                                    Gauge32,
    cucsAdaptorIScsiCapMacOffset2                                    Gauge32,
    cucsAdaptorIScsiCapOffloadSupport                                TruthValue,
    cucsAdaptorIScsiCapOffloadType                                   CucsAdaptorOffloadMethod,
    cucsAdaptorIScsiCapVlanForBoot                                   TruthValue,
    cucsAdaptorIScsiCapBootOrderType                                 CucsAdaptorIScsiCapBootOrderType
}

cucsAdaptorIScsiCapInstanceId OBJECT-TYPE
    SYNTAX       CucsManagedObjectId
    MAX-ACCESS   not-accessible
    STATUS       current
    DESCRIPTION
        "Instance identifier of the managed object."
    ::= { cucsAdaptorIScsiCapEntry 1 }

cucsAdaptorIScsiCapDn OBJECT-TYPE
    SYNTAX       CucsManagedObjectDn
    MAX-ACCESS   read-only
    STATUS       current
    DESCRIPTION
        "Cisco UCS adaptor:IScsiCap:dn managed object property"
    ::= { cucsAdaptorIScsiCapEntry 2 }

cucsAdaptorIScsiCapRn OBJECT-TYPE
    SYNTAX       SnmpAdminString
    MAX-ACCESS   read-only
    STATUS       current
    DESCRIPTION
        "Cisco UCS adaptor:IScsiCap:rn managed object property"
    ::= { cucsAdaptorIScsiCapEntry 3 }

cucsAdaptorIScsiCapMacOffset1 OBJECT-TYPE
    SYNTAX       Gauge32
    MAX-ACCESS   read-only
    STATUS       current
    DESCRIPTION
        "Cisco UCS adaptor:IScsiCap:macOffset1 managed object property"
    ::= { cucsAdaptorIScsiCapEntry 4 }

cucsAdaptorIScsiCapMacOffset2 OBJECT-TYPE
    SYNTAX       Gauge32
    MAX-ACCESS   read-only
    STATUS       current
    DESCRIPTION
        "Cisco UCS adaptor:IScsiCap:macOffset2 managed object property"
    ::= { cucsAdaptorIScsiCapEntry 5 }

cucsAdaptorIScsiCapOffloadSupport OBJECT-TYPE
    SYNTAX       TruthValue
    MAX-ACCESS   read-only
    STATUS       current
    DESCRIPTION
        "Cisco UCS adaptor:IScsiCap:offloadSupport managed
        object property"
    ::= { cucsAdaptorIScsiCapEntry 6 }

cucsAdaptorIScsiCapOffloadType OBJECT-TYPE
    SYNTAX       CucsAdaptorOffloadMethod
    MAX-ACCESS   read-only
    STATUS       current
    DESCRIPTION
        "Cisco UCS adaptor:IScsiCap:offloadType managed object property"
    ::= { cucsAdaptorIScsiCapEntry 7 }

cucsAdaptorIScsiCapVlanForBoot OBJECT-TYPE
    SYNTAX       TruthValue
    MAX-ACCESS   read-only
    STATUS       current
    DESCRIPTION
        "Cisco UCS adaptor:IScsiCap:vlanForBoot managed object property"
    ::= { cucsAdaptorIScsiCapEntry 8 }

cucsAdaptorIScsiCapBootOrderType OBJECT-TYPE
    SYNTAX       CucsAdaptorIScsiCapBootOrderType
    MAX-ACCESS   read-only
    STATUS       current
    DESCRIPTION
        "Cisco UCS adaptor:IScsiCap:bootOrderType managed object property"
    ::= { cucsAdaptorIScsiCapEntry 9 }

cucsAdaptorIpV4RssHashProfileTable OBJECT-TYPE
    SYNTAX           SEQUENCE OF CucsAdaptorIpV4RssHashProfileEntry
    MAX-ACCESS       not-accessible
    STATUS           current
    DESCRIPTION
        "Cisco UCS adaptor:IpV4RssHashProfile managed object table"
    ::= { cucsAdaptorObjects 52 }

cucsAdaptorIpV4RssHashProfileEntry OBJECT-TYPE
    SYNTAX           CucsAdaptorIpV4RssHashProfileEntry
    MAX-ACCESS       not-accessible
    STATUS           current
    DESCRIPTION
        "Entry for the cucsAdaptorIpV4RssHashProfileTable table."
    INDEX { cucsAdaptorIpV4RssHashProfileInstanceId }
    ::= { cucsAdaptorIpV4RssHashProfileTable 1 }

CucsAdaptorIpV4RssHashProfileEntry ::= SEQUENCE {
    cucsAdaptorIpV4RssHashProfileInstanceId                          CucsManagedObjectId,
    cucsAdaptorIpV4RssHashProfileDn                                  CucsManagedObjectDn,
    cucsAdaptorIpV4RssHashProfileRn                                  SnmpAdminString,
    cucsAdaptorIpV4RssHashProfileIpHash                              CucsAdaptorIpV4RssHashProfileIpHash,
    cucsAdaptorIpV4RssHashProfileTcpHash                             CucsAdaptorIpV4RssHashProfileTcpHash
}

cucsAdaptorIpV4RssHashProfileInstanceId OBJECT-TYPE
    SYNTAX       CucsManagedObjectId
    MAX-ACCESS   not-accessible
    STATUS       current
    DESCRIPTION
        "Instance identifier of the managed object."
    ::= { cucsAdaptorIpV4RssHashProfileEntry 1 }

cucsAdaptorIpV4RssHashProfileDn OBJECT-TYPE
    SYNTAX       CucsManagedObjectDn
    MAX-ACCESS   read-only
    STATUS       current
    DESCRIPTION
        "Cisco UCS adaptor:IpV4RssHashProfile:dn managed object property"
    ::= { cucsAdaptorIpV4RssHashProfileEntry 2 }

cucsAdaptorIpV4RssHashProfileRn OBJECT-TYPE
    SYNTAX       SnmpAdminString
    MAX-ACCESS   read-only
    STATUS       current
    DESCRIPTION
        "Cisco UCS adaptor:IpV4RssHashProfile:rn managed object property"
    ::= { cucsAdaptorIpV4RssHashProfileEntry 3 }

cucsAdaptorIpV4RssHashProfileIpHash OBJECT-TYPE
    SYNTAX       CucsAdaptorIpV4RssHashProfileIpHash
    MAX-ACCESS   read-only
    STATUS       current
    DESCRIPTION
        "Cisco UCS adaptor:IpV4RssHashProfile:ipHash managed
        object property"
    ::= { cucsAdaptorIpV4RssHashProfileEntry 4 }

cucsAdaptorIpV4RssHashProfileTcpHash OBJECT-TYPE
    SYNTAX       CucsAdaptorIpV4RssHashProfileTcpHash
    MAX-ACCESS   read-only
    STATUS       current
    DESCRIPTION
        "Cisco UCS adaptor:IpV4RssHashProfile:tcpHash managed
        object property"
    ::= { cucsAdaptorIpV4RssHashProfileEntry 5 }

cucsAdaptorIpV6RssHashProfileTable OBJECT-TYPE
    SYNTAX           SEQUENCE OF CucsAdaptorIpV6RssHashProfileEntry
    MAX-ACCESS       not-accessible
    STATUS           current
    DESCRIPTION
        "Cisco UCS adaptor:IpV6RssHashProfile managed object table"
    ::= { cucsAdaptorObjects 53 }

cucsAdaptorIpV6RssHashProfileEntry OBJECT-TYPE
    SYNTAX           CucsAdaptorIpV6RssHashProfileEntry
    MAX-ACCESS       not-accessible
    STATUS           current
    DESCRIPTION
        "Entry for the cucsAdaptorIpV6RssHashProfileTable table."
    INDEX { cucsAdaptorIpV6RssHashProfileInstanceId }
    ::= { cucsAdaptorIpV6RssHashProfileTable 1 }

CucsAdaptorIpV6RssHashProfileEntry ::= SEQUENCE {
    cucsAdaptorIpV6RssHashProfileInstanceId                          CucsManagedObjectId,
    cucsAdaptorIpV6RssHashProfileDn                                  CucsManagedObjectDn,
    cucsAdaptorIpV6RssHashProfileRn                                  SnmpAdminString,
    cucsAdaptorIpV6RssHashProfileIpHash                              CucsAdaptorIpV6RssHashProfileIpHash,
    cucsAdaptorIpV6RssHashProfileTcpHash                             CucsAdaptorIpV6RssHashProfileTcpHash
}

cucsAdaptorIpV6RssHashProfileInstanceId OBJECT-TYPE
    SYNTAX       CucsManagedObjectId
    MAX-ACCESS   not-accessible
    STATUS       current
    DESCRIPTION
        "Instance identifier of the managed object."
    ::= { cucsAdaptorIpV6RssHashProfileEntry 1 }

cucsAdaptorIpV6RssHashProfileDn OBJECT-TYPE
    SYNTAX       CucsManagedObjectDn
    MAX-ACCESS   read-only
    STATUS       current
    DESCRIPTION
        "Cisco UCS adaptor:IpV6RssHashProfile:dn managed object property"
    ::= { cucsAdaptorIpV6RssHashProfileEntry 2 }

cucsAdaptorIpV6RssHashProfileRn OBJECT-TYPE
    SYNTAX       SnmpAdminString
    MAX-ACCESS   read-only
    STATUS       current
    DESCRIPTION
        "Cisco UCS adaptor:IpV6RssHashProfile:rn managed object property"
    ::= { cucsAdaptorIpV6RssHashProfileEntry 3 }

cucsAdaptorIpV6RssHashProfileIpHash OBJECT-TYPE
    SYNTAX       CucsAdaptorIpV6RssHashProfileIpHash
    MAX-ACCESS   read-only
    STATUS       current
    DESCRIPTION
        "Cisco UCS adaptor:IpV6RssHashProfile:ipHash managed
        object property"
    ::= { cucsAdaptorIpV6RssHashProfileEntry 4 }

cucsAdaptorIpV6RssHashProfileTcpHash OBJECT-TYPE
    SYNTAX       CucsAdaptorIpV6RssHashProfileTcpHash
    MAX-ACCESS   read-only
    STATUS       current
    DESCRIPTION
        "Cisco UCS adaptor:IpV6RssHashProfile:tcpHash managed
        object property"
    ::= { cucsAdaptorIpV6RssHashProfileEntry 5 }

cucsAdaptorIscsiAuthTable OBJECT-TYPE
    SYNTAX           SEQUENCE OF CucsAdaptorIscsiAuthEntry
    MAX-ACCESS       not-accessible
    STATUS           current
    DESCRIPTION
        "Cisco UCS adaptor:IscsiAuth managed object table"
    ::= { cucsAdaptorObjects 102 }

cucsAdaptorIscsiAuthEntry OBJECT-TYPE
    SYNTAX           CucsAdaptorIscsiAuthEntry
    MAX-ACCESS       not-accessible
    STATUS           current
    DESCRIPTION
        "Entry for the cucsAdaptorIscsiAuthTable table."
    INDEX { cucsAdaptorIscsiAuthInstanceId }
    ::= { cucsAdaptorIscsiAuthTable 1 }

CucsAdaptorIscsiAuthEntry ::= SEQUENCE {
    cucsAdaptorIscsiAuthInstanceId                                   CucsManagedObjectId,
    cucsAdaptorIscsiAuthDn                                           CucsManagedObjectDn,
    cucsAdaptorIscsiAuthRn                                           SnmpAdminString,
    cucsAdaptorIscsiAuthPassword                                     SnmpAdminString,
    cucsAdaptorIscsiAuthUserId                                       SnmpAdminString
}

cucsAdaptorIscsiAuthInstanceId OBJECT-TYPE
    SYNTAX       CucsManagedObjectId
    MAX-ACCESS   not-accessible
    STATUS       current
    DESCRIPTION
        "Instance identifier of the managed object."
    ::= { cucsAdaptorIscsiAuthEntry 1 }

cucsAdaptorIscsiAuthDn OBJECT-TYPE
    SYNTAX       CucsManagedObjectDn
    MAX-ACCESS   read-only
    STATUS       current
    DESCRIPTION
        "Cisco UCS adaptor:IscsiAuth:dn managed object property"
    ::= { cucsAdaptorIscsiAuthEntry 2 }

cucsAdaptorIscsiAuthRn OBJECT-TYPE
    SYNTAX       SnmpAdminString
    MAX-ACCESS   read-only
    STATUS       current
    DESCRIPTION
        "Cisco UCS adaptor:IscsiAuth:rn managed object property"
    ::= { cucsAdaptorIscsiAuthEntry 3 }

cucsAdaptorIscsiAuthPassword OBJECT-TYPE
    SYNTAX       SnmpAdminString
    MAX-ACCESS   read-only
    STATUS       current
    DESCRIPTION
        "Cisco UCS adaptor:IscsiAuth:password managed object property"
    ::= { cucsAdaptorIscsiAuthEntry 4 }

cucsAdaptorIscsiAuthUserId OBJECT-TYPE
    SYNTAX       SnmpAdminString
    MAX-ACCESS   read-only
    STATUS       current
    DESCRIPTION
        "Cisco UCS adaptor:IscsiAuth:userId managed object property"
    ::= { cucsAdaptorIscsiAuthEntry 5 }

cucsAdaptorIscsiProtTable OBJECT-TYPE
    SYNTAX           SEQUENCE OF CucsAdaptorIscsiProtEntry
    MAX-ACCESS       not-accessible
    STATUS           current
    DESCRIPTION
        "Cisco UCS adaptor:IscsiProt managed object table"
    ::= { cucsAdaptorObjects 103 }

cucsAdaptorIscsiProtEntry OBJECT-TYPE
    SYNTAX           CucsAdaptorIscsiProtEntry
    MAX-ACCESS       not-accessible
    STATUS           current
    DESCRIPTION
        "Entry for the cucsAdaptorIscsiProtTable table."
    INDEX { cucsAdaptorIscsiProtInstanceId }
    ::= { cucsAdaptorIscsiProtTable 1 }

CucsAdaptorIscsiProtEntry ::= SEQUENCE {
    cucsAdaptorIscsiProtInstanceId                                   CucsManagedObjectId,
    cucsAdaptorIscsiProtDn                                           CucsManagedObjectDn,
    cucsAdaptorIscsiProtRn                                           SnmpAdminString,
    cucsAdaptorIscsiProtConnectionTimeOut                            CucsAdaptorIscsiProtConnectionTimeOut,
    cucsAdaptorIscsiProtDhcpTimeOut                                  CucsAdaptorIscsiProtDhcpTimeOut,
    cucsAdaptorIscsiProtFltAggr                                      Unsigned64,
    cucsAdaptorIscsiProtInitiatorName                                SnmpAdminString,
    cucsAdaptorIscsiProtLunBusyRetryCount                            CucsAdaptorIscsiProtLunBusyRetryCount,
    cucsAdaptorIscsiProtTcpTimeStamp                                 TruthValue
}

cucsAdaptorIscsiProtInstanceId OBJECT-TYPE
    SYNTAX       CucsManagedObjectId
    MAX-ACCESS   not-accessible
    STATUS       current
    DESCRIPTION
        "Instance identifier of the managed object."
    ::= { cucsAdaptorIscsiProtEntry 1 }

cucsAdaptorIscsiProtDn OBJECT-TYPE
    SYNTAX       CucsManagedObjectDn
    MAX-ACCESS   read-only
    STATUS       current
    DESCRIPTION
        "Cisco UCS adaptor:IscsiProt:dn managed object property"
    ::= { cucsAdaptorIscsiProtEntry 2 }

cucsAdaptorIscsiProtRn OBJECT-TYPE
    SYNTAX       SnmpAdminString
    MAX-ACCESS   read-only
    STATUS       current
    DESCRIPTION
        "Cisco UCS adaptor:IscsiProt:rn managed object property"
    ::= { cucsAdaptorIscsiProtEntry 3 }

cucsAdaptorIscsiProtConnectionTimeOut OBJECT-TYPE
    SYNTAX       CucsAdaptorIscsiProtConnectionTimeOut
    MAX-ACCESS   read-only
    STATUS       current
    DESCRIPTION
        "Cisco UCS adaptor:IscsiProt:connectionTimeOut
        managed object property"
    ::= { cucsAdaptorIscsiProtEntry 4 }

cucsAdaptorIscsiProtDhcpTimeOut OBJECT-TYPE
    SYNTAX       CucsAdaptorIscsiProtDhcpTimeOut
    MAX-ACCESS   read-only
    STATUS       current
    DESCRIPTION
        "Cisco UCS adaptor:IscsiProt:dhcpTimeOut managed object property"
    ::= { cucsAdaptorIscsiProtEntry 5 }

cucsAdaptorIscsiProtFltAggr OBJECT-TYPE
    SYNTAX       Unsigned64
    MAX-ACCESS   read-only
    STATUS       current
    DESCRIPTION
        "Cisco UCS adaptor:IscsiProt:fltAggr managed object property"
    ::= { cucsAdaptorIscsiProtEntry 6 }

cucsAdaptorIscsiProtInitiatorName OBJECT-TYPE
    SYNTAX       SnmpAdminString
    MAX-ACCESS   read-only
    STATUS       current
    DESCRIPTION
        "Cisco UCS adaptor:IscsiProt:initiatorName managed
        object property"
    ::= { cucsAdaptorIscsiProtEntry 7 }

cucsAdaptorIscsiProtLunBusyRetryCount OBJECT-TYPE
    SYNTAX       CucsAdaptorIscsiProtLunBusyRetryCount
    MAX-ACCESS   read-only
    STATUS       current
    DESCRIPTION
        "Cisco UCS adaptor:IscsiProt:lunBusyRetryCount
        managed object property"
    ::= { cucsAdaptorIscsiProtEntry 8 }

cucsAdaptorIscsiProtTcpTimeStamp OBJECT-TYPE
    SYNTAX       TruthValue
    MAX-ACCESS   read-only
    STATUS       current
    DESCRIPTION
        "Cisco UCS adaptor:IscsiProt:tcpTimeStamp managed object property"
    ::= { cucsAdaptorIscsiProtEntry 9 }

cucsAdaptorIscsiTargetIfTable OBJECT-TYPE
    SYNTAX           SEQUENCE OF CucsAdaptorIscsiTargetIfEntry
    MAX-ACCESS       not-accessible
    STATUS           current
    DESCRIPTION
        "Cisco UCS adaptor:IscsiTargetIf managed object table"
    ::= { cucsAdaptorObjects 104 }

cucsAdaptorIscsiTargetIfEntry OBJECT-TYPE
    SYNTAX           CucsAdaptorIscsiTargetIfEntry
    MAX-ACCESS       not-accessible
    STATUS           current
    DESCRIPTION
        "Entry for the cucsAdaptorIscsiTargetIfTable table."
    INDEX { cucsAdaptorIscsiTargetIfInstanceId }
    ::= { cucsAdaptorIscsiTargetIfTable 1 }

CucsAdaptorIscsiTargetIfEntry ::= SEQUENCE {
    cucsAdaptorIscsiTargetIfInstanceId                               CucsManagedObjectId,
    cucsAdaptorIscsiTargetIfDn                                       CucsManagedObjectDn,
    cucsAdaptorIscsiTargetIfRn                                       SnmpAdminString,
    cucsAdaptorIscsiTargetIfDhcpVendorId                             SnmpAdminString,
    cucsAdaptorIscsiTargetIfFltAggr                                  Unsigned64,
    cucsAdaptorIscsiTargetIfIpAddress                                InetAddressIPv4,
    cucsAdaptorIscsiTargetIfLun                                      Gauge32,
    cucsAdaptorIscsiTargetIfName                                     SnmpAdminString,
    cucsAdaptorIscsiTargetIfPortNumber                               Gauge32,
    cucsAdaptorIscsiTargetIfPriority                                 Gauge32
}

cucsAdaptorIscsiTargetIfInstanceId OBJECT-TYPE
    SYNTAX       CucsManagedObjectId
    MAX-ACCESS   not-accessible
    STATUS       current
    DESCRIPTION
        "Instance identifier of the managed object."
    ::= { cucsAdaptorIscsiTargetIfEntry 1 }

cucsAdaptorIscsiTargetIfDn OBJECT-TYPE
    SYNTAX       CucsManagedObjectDn
    MAX-ACCESS   read-only
    STATUS       current
    DESCRIPTION
        "Cisco UCS adaptor:IscsiTargetIf:dn managed object property"
    ::= { cucsAdaptorIscsiTargetIfEntry 2 }

cucsAdaptorIscsiTargetIfRn OBJECT-TYPE
    SYNTAX       SnmpAdminString
    MAX-ACCESS   read-only
    STATUS       current
    DESCRIPTION
        "Cisco UCS adaptor:IscsiTargetIf:rn managed object property"
    ::= { cucsAdaptorIscsiTargetIfEntry 3 }

cucsAdaptorIscsiTargetIfDhcpVendorId OBJECT-TYPE
    SYNTAX       SnmpAdminString
    MAX-ACCESS   read-only
    STATUS       current
    DESCRIPTION
        "Cisco UCS adaptor:IscsiTargetIf:dhcpVendorId managed
        object property"
    ::= { cucsAdaptorIscsiTargetIfEntry 4 }

cucsAdaptorIscsiTargetIfFltAggr OBJECT-TYPE
    SYNTAX       Unsigned64
    MAX-ACCESS   read-only
    STATUS       current
    DESCRIPTION
        "Cisco UCS adaptor:IscsiTargetIf:fltAggr managed object property"
    ::= { cucsAdaptorIscsiTargetIfEntry 5 }

cucsAdaptorIscsiTargetIfIpAddress OBJECT-TYPE
    SYNTAX       InetAddressIPv4
    MAX-ACCESS   read-only
    STATUS       current
    DESCRIPTION
        "Cisco UCS adaptor:IscsiTargetIf:ipAddress managed
        object property"
    ::= { cucsAdaptorIscsiTargetIfEntry 6 }

cucsAdaptorIscsiTargetIfLun OBJECT-TYPE
    SYNTAX       Gauge32
    MAX-ACCESS   read-only
    STATUS       current
    DESCRIPTION
        "Cisco UCS adaptor:IscsiTargetIf:lun managed object property"
    ::= { cucsAdaptorIscsiTargetIfEntry 7 }

cucsAdaptorIscsiTargetIfName OBJECT-TYPE
    SYNTAX       SnmpAdminString
    MAX-ACCESS   read-only
    STATUS       current
    DESCRIPTION
        "Cisco UCS adaptor:IscsiTargetIf:name managed object property"
    ::= { cucsAdaptorIscsiTargetIfEntry 8 }

cucsAdaptorIscsiTargetIfPortNumber OBJECT-TYPE
    SYNTAX       Gauge32
    MAX-ACCESS   read-only
    STATUS       current
    DESCRIPTION
        "Cisco UCS adaptor:IscsiTargetIf:portNumber managed
        object property"
    ::= { cucsAdaptorIscsiTargetIfEntry 9 }

cucsAdaptorIscsiTargetIfPriority OBJECT-TYPE
    SYNTAX       Gauge32
    MAX-ACCESS   read-only
    STATUS       current
    DESCRIPTION
        "Cisco UCS adaptor:IscsiTargetIf:priority managed object property"
    ::= { cucsAdaptorIscsiTargetIfEntry 10 }

cucsAdaptorLanCapTable OBJECT-TYPE
    SYNTAX           SEQUENCE OF CucsAdaptorLanCapEntry
    MAX-ACCESS       not-accessible
    STATUS           current
    DESCRIPTION
        "Cisco UCS adaptor:LanCap managed object table"
    ::= { cucsAdaptorObjects 54 }

cucsAdaptorLanCapEntry OBJECT-TYPE
    SYNTAX           CucsAdaptorLanCapEntry
    MAX-ACCESS       not-accessible
    STATUS           current
    DESCRIPTION
        "Entry for the cucsAdaptorLanCapTable table."
    INDEX { cucsAdaptorLanCapInstanceId }
    ::= { cucsAdaptorLanCapTable 1 }

CucsAdaptorLanCapEntry ::= SEQUENCE {
    cucsAdaptorLanCapInstanceId                                      CucsManagedObjectId,
    cucsAdaptorLanCapDn                                              CucsManagedObjectDn,
    cucsAdaptorLanCapRn                                              SnmpAdminString,
    cucsAdaptorLanCapDefaultVlan                                     CucsAdaptorLanCapDefaultVlan
}

cucsAdaptorLanCapInstanceId OBJECT-TYPE
    SYNTAX       CucsManagedObjectId
    MAX-ACCESS   not-accessible
    STATUS       current
    DESCRIPTION
        "Instance identifier of the managed object."
    ::= { cucsAdaptorLanCapEntry 1 }

cucsAdaptorLanCapDn OBJECT-TYPE
    SYNTAX       CucsManagedObjectDn
    MAX-ACCESS   read-only
    STATUS       current
    DESCRIPTION
        "Cisco UCS adaptor:LanCap:dn managed object property"
    ::= { cucsAdaptorLanCapEntry 2 }

cucsAdaptorLanCapRn OBJECT-TYPE
    SYNTAX       SnmpAdminString
    MAX-ACCESS   read-only
    STATUS       current
    DESCRIPTION
        "Cisco UCS adaptor:LanCap:rn managed object property"
    ::= { cucsAdaptorLanCapEntry 3 }

cucsAdaptorLanCapDefaultVlan OBJECT-TYPE
    SYNTAX       CucsAdaptorLanCapDefaultVlan
    MAX-ACCESS   read-only
    STATUS       current
    DESCRIPTION
        "Cisco UCS adaptor:LanCap:defaultVlan managed object property"
    ::= { cucsAdaptorLanCapEntry 4 }

cucsAdaptorLldpCapTable OBJECT-TYPE
    SYNTAX           SEQUENCE OF CucsAdaptorLldpCapEntry
    MAX-ACCESS       not-accessible
    STATUS           current
    DESCRIPTION
        "Cisco UCS adaptor:LldpCap managed object table"
    ::= { cucsAdaptorObjects 96 }

cucsAdaptorLldpCapEntry OBJECT-TYPE
    SYNTAX           CucsAdaptorLldpCapEntry
    MAX-ACCESS       not-accessible
    STATUS           current
    DESCRIPTION
        "Entry for the cucsAdaptorLldpCapTable table."
    INDEX { cucsAdaptorLldpCapInstanceId }
    ::= { cucsAdaptorLldpCapTable 1 }

CucsAdaptorLldpCapEntry ::= SEQUENCE {
    cucsAdaptorLldpCapInstanceId                                     CucsManagedObjectId,
    cucsAdaptorLldpCapDn                                             CucsManagedObjectDn,
    cucsAdaptorLldpCapRn                                             SnmpAdminString,
    cucsAdaptorLldpCapSupport                                        CucsAdaptorLldpCapSupport
}

cucsAdaptorLldpCapInstanceId OBJECT-TYPE
    SYNTAX       CucsManagedObjectId
    MAX-ACCESS   not-accessible
    STATUS       current
    DESCRIPTION
        "Instance identifier of the managed object."
    ::= { cucsAdaptorLldpCapEntry 1 }

cucsAdaptorLldpCapDn OBJECT-TYPE
    SYNTAX       CucsManagedObjectDn
    MAX-ACCESS   read-only
    STATUS       current
    DESCRIPTION
        "Cisco UCS adaptor:LldpCap:dn managed object property"
    ::= { cucsAdaptorLldpCapEntry 2 }

cucsAdaptorLldpCapRn OBJECT-TYPE
    SYNTAX       SnmpAdminString
    MAX-ACCESS   read-only
    STATUS       current
    DESCRIPTION
        "Cisco UCS adaptor:LldpCap:rn managed object property"
    ::= { cucsAdaptorLldpCapEntry 3 }

cucsAdaptorLldpCapSupport OBJECT-TYPE
    SYNTAX       CucsAdaptorLldpCapSupport
    MAX-ACCESS   read-only
    STATUS       current
    DESCRIPTION
        "Cisco UCS adaptor:LldpCap:support managed object property"
    ::= { cucsAdaptorLldpCapEntry 4 }

cucsAdaptorMenloBaseErrorStatsTable OBJECT-TYPE
    SYNTAX           SEQUENCE OF CucsAdaptorMenloBaseErrorStatsEntry
    MAX-ACCESS       not-accessible
    STATUS           current
    DESCRIPTION
        "Cisco UCS adaptor:MenloBaseErrorStats managed object table"
    ::= { cucsAdaptorObjects 55 }

cucsAdaptorMenloBaseErrorStatsEntry OBJECT-TYPE
    SYNTAX           CucsAdaptorMenloBaseErrorStatsEntry
    MAX-ACCESS       not-accessible
    STATUS           current
    DESCRIPTION
        "Entry for the cucsAdaptorMenloBaseErrorStatsTable table."
    INDEX { cucsAdaptorMenloBaseErrorStatsInstanceId }
    ::= { cucsAdaptorMenloBaseErrorStatsTable 1 }

CucsAdaptorMenloBaseErrorStatsEntry ::= SEQUENCE {
    cucsAdaptorMenloBaseErrorStatsInstanceId                         CucsManagedObjectId,
    cucsAdaptorMenloBaseErrorStatsDn                                 CucsManagedObjectDn,
    cucsAdaptorMenloBaseErrorStatsRn                                 SnmpAdminString,
    cucsAdaptorMenloBaseErrorStatsCorrectableErrors                  Unsigned64,
    cucsAdaptorMenloBaseErrorStatsCorrectableErrorsDelta             Counter64,
    cucsAdaptorMenloBaseErrorStatsCorrectableErrorsDeltaAvg          Unsigned64,
    cucsAdaptorMenloBaseErrorStatsCorrectableErrorsDeltaMax          Unsigned64,
    cucsAdaptorMenloBaseErrorStatsCorrectableErrorsDeltaMin          Unsigned64,
    cucsAdaptorMenloBaseErrorStatsIntervals                          Gauge32,
    cucsAdaptorMenloBaseErrorStatsSuspect                            TruthValue,
    cucsAdaptorMenloBaseErrorStatsThresholded                        CucsAdaptorMenloBaseErrorStatsThresholded,
    cucsAdaptorMenloBaseErrorStatsTimeCollected                      DateAndTime,
    cucsAdaptorMenloBaseErrorStatsUncorrectableErrors                Unsigned64,
    cucsAdaptorMenloBaseErrorStatsUncorrectableErrorsDelta           Counter64,
    cucsAdaptorMenloBaseErrorStatsUncorrectableErrorsDeltaAvg        Unsigned64,
    cucsAdaptorMenloBaseErrorStatsUncorrectableErrorsDeltaMax        Unsigned64,
    cucsAdaptorMenloBaseErrorStatsUncorrectableErrorsDeltaMin        Unsigned64,
    cucsAdaptorMenloBaseErrorStatsUpdate                             Gauge32
}

cucsAdaptorMenloBaseErrorStatsInstanceId OBJECT-TYPE
    SYNTAX       CucsManagedObjectId
    MAX-ACCESS   not-accessible
    STATUS       current
    DESCRIPTION
        "Instance identifier of the managed object."
    ::= { cucsAdaptorMenloBaseErrorStatsEntry 1 }

cucsAdaptorMenloBaseErrorStatsDn OBJECT-TYPE
    SYNTAX       CucsManagedObjectDn
    MAX-ACCESS   read-only
    STATUS       current
    DESCRIPTION
        "Cisco UCS adaptor:MenloBaseErrorStats:dn managed object property"
    ::= { cucsAdaptorMenloBaseErrorStatsEntry 2 }

cucsAdaptorMenloBaseErrorStatsRn OBJECT-TYPE
    SYNTAX       SnmpAdminString
    MAX-ACCESS   read-only
    STATUS       current
    DESCRIPTION
        "Cisco UCS adaptor:MenloBaseErrorStats:rn managed object property"
    ::= { cucsAdaptorMenloBaseErrorStatsEntry 3 }

cucsAdaptorMenloBaseErrorStatsCorrectableErrors OBJECT-TYPE
    SYNTAX       Unsigned64
    MAX-ACCESS   read-only
    STATUS       current
    DESCRIPTION
        "Cisco UCS adaptor:MenloBaseErrorStats:correctableErrors
        managed object property"
    ::= { cucsAdaptorMenloBaseErrorStatsEntry 4 }

cucsAdaptorMenloBaseErrorStatsCorrectableErrorsDelta OBJECT-TYPE
    SYNTAX       Counter64
    MAX-ACCESS   read-only
    STATUS       current
    DESCRIPTION
        "Cisco UCS adaptor:MenloBaseErrorStats:correctableErrorsDelta
        managed object property"
    ::= { cucsAdaptorMenloBaseErrorStatsEntry 5 }

cucsAdaptorMenloBaseErrorStatsCorrectableErrorsDeltaAvg OBJECT-TYPE
    SYNTAX       Unsigned64
    MAX-ACCESS   read-only
    STATUS       current
    DESCRIPTION
        "Cisco UCS adaptor:MenloBaseErrorStats:correctableErrorsDeltaAvg
        managed object property"
    ::= { cucsAdaptorMenloBaseErrorStatsEntry 6 }

cucsAdaptorMenloBaseErrorStatsCorrectableErrorsDeltaMax OBJECT-TYPE
    SYNTAX       Unsigned64
    MAX-ACCESS   read-only
    STATUS       current
    DESCRIPTION
        "Cisco UCS adaptor:MenloBaseErrorStats:correctableErrorsDeltaMax
        managed object property"
    ::= { cucsAdaptorMenloBaseErrorStatsEntry 7 }

cucsAdaptorMenloBaseErrorStatsCorrectableErrorsDeltaMin OBJECT-TYPE
    SYNTAX       Unsigned64
    MAX-ACCESS   read-only
    STATUS       current
    DESCRIPTION
        "Cisco UCS adaptor:MenloBaseErrorStats:correctableErrorsDeltaMin
        managed object property"
    ::= { cucsAdaptorMenloBaseErrorStatsEntry 8 }

cucsAdaptorMenloBaseErrorStatsIntervals OBJECT-TYPE
    SYNTAX       Gauge32
    MAX-ACCESS   read-only
    STATUS       current
    DESCRIPTION
        "Cisco UCS adaptor:MenloBaseErrorStats:intervals
        managed object property"
    ::= { cucsAdaptorMenloBaseErrorStatsEntry 9 }

cucsAdaptorMenloBaseErrorStatsSuspect OBJECT-TYPE
    SYNTAX       TruthValue
    MAX-ACCESS   read-only
    STATUS       current
    DESCRIPTION
        "Cisco UCS adaptor:MenloBaseErrorStats:suspect
        managed object property"
    ::= { cucsAdaptorMenloBaseErrorStatsEntry 10 }

cucsAdaptorMenloBaseErrorStatsThresholded OBJECT-TYPE
    SYNTAX       CucsAdaptorMenloBaseErrorStatsThresholded
    MAX-ACCESS   read-only
    STATUS       current
    DESCRIPTION
        "Cisco UCS adaptor:MenloBaseErrorStats:thresholded
        managed object property"
    ::= { cucsAdaptorMenloBaseErrorStatsEntry 11 }

cucsAdaptorMenloBaseErrorStatsTimeCollected OBJECT-TYPE
    SYNTAX       DateAndTime
    MAX-ACCESS   read-only
    STATUS       current
    DESCRIPTION
        "Cisco UCS adaptor:MenloBaseErrorStats:timeCollected
        managed object property"
    ::= { cucsAdaptorMenloBaseErrorStatsEntry 12 }

cucsAdaptorMenloBaseErrorStatsUncorrectableErrors OBJECT-TYPE
    SYNTAX       Unsigned64
    MAX-ACCESS   read-only
    STATUS       current
    DESCRIPTION
        "Cisco UCS adaptor:MenloBaseErrorStats:uncorrectableErrors
        managed object property"
    ::= { cucsAdaptorMenloBaseErrorStatsEntry 13 }

cucsAdaptorMenloBaseErrorStatsUncorrectableErrorsDelta OBJECT-TYPE
    SYNTAX       Counter64
    MAX-ACCESS   read-only
    STATUS       current
    DESCRIPTION
        "Cisco UCS adaptor:MenloBaseErrorStats:uncorrectableErrorsDelta
        managed object property"
    ::= { cucsAdaptorMenloBaseErrorStatsEntry 14 }

cucsAdaptorMenloBaseErrorStatsUncorrectableErrorsDeltaAvg OBJECT-TYPE
    SYNTAX       Unsigned64
    MAX-ACCESS   read-only
    STATUS       current
    DESCRIPTION
        "Cisco UCS adaptor:MenloBaseErrorStats:uncorrectableErrorsDeltaAvg
         managed object property"
    ::= { cucsAdaptorMenloBaseErrorStatsEntry 15 }

cucsAdaptorMenloBaseErrorStatsUncorrectableErrorsDeltaMax OBJECT-TYPE
    SYNTAX       Unsigned64
    MAX-ACCESS   read-only
    STATUS       current
    DESCRIPTION
        "Cisco UCS adaptor:MenloBaseErrorStats:uncorrectableErrorsDeltaMax
         managed object property"
    ::= { cucsAdaptorMenloBaseErrorStatsEntry 16 }

cucsAdaptorMenloBaseErrorStatsUncorrectableErrorsDeltaMin OBJECT-TYPE
    SYNTAX       Unsigned64
    MAX-ACCESS   read-only
    STATUS       current
    DESCRIPTION
        "Cisco UCS adaptor:MenloBaseErrorStats:uncorrectableErrorsDeltaMin
         managed object property"
    ::= { cucsAdaptorMenloBaseErrorStatsEntry 17 }

cucsAdaptorMenloBaseErrorStatsUpdate OBJECT-TYPE
    SYNTAX       Gauge32
    MAX-ACCESS   read-only
    STATUS       current
    DESCRIPTION
        "Cisco UCS adaptor:MenloBaseErrorStats:update managed
        object property"
    ::= { cucsAdaptorMenloBaseErrorStatsEntry 18 }

cucsAdaptorMenloBaseErrorStatsHistTable OBJECT-TYPE
    SYNTAX           SEQUENCE OF CucsAdaptorMenloBaseErrorStatsHistEntry
    MAX-ACCESS       not-accessible
    STATUS           current
    DESCRIPTION
        "Cisco UCS adaptor:MenloBaseErrorStatsHist managed object table"
    ::= { cucsAdaptorObjects 56 }

cucsAdaptorMenloBaseErrorStatsHistEntry OBJECT-TYPE
    SYNTAX           CucsAdaptorMenloBaseErrorStatsHistEntry
    MAX-ACCESS       not-accessible
    STATUS           current
    DESCRIPTION
        "Entry for the cucsAdaptorMenloBaseErrorStatsHistTable table."
    INDEX { cucsAdaptorMenloBaseErrorStatsHistInstanceId }
    ::= { cucsAdaptorMenloBaseErrorStatsHistTable 1 }

CucsAdaptorMenloBaseErrorStatsHistEntry ::= SEQUENCE {
    cucsAdaptorMenloBaseErrorStatsHistInstanceId                     CucsManagedObjectId,
    cucsAdaptorMenloBaseErrorStatsHistDn                             CucsManagedObjectDn,
    cucsAdaptorMenloBaseErrorStatsHistRn                             SnmpAdminString,
    cucsAdaptorMenloBaseErrorStatsHistCorrectableErrors              Unsigned64,
    cucsAdaptorMenloBaseErrorStatsHistCorrectableErrorsDelta         Unsigned64,
    cucsAdaptorMenloBaseErrorStatsHistCorrectableErrorsDeltaAvg      Unsigned64,
    cucsAdaptorMenloBaseErrorStatsHistCorrectableErrorsDeltaMax      Unsigned64,
    cucsAdaptorMenloBaseErrorStatsHistCorrectableErrorsDeltaMin      Unsigned64,
    cucsAdaptorMenloBaseErrorStatsHistId                             Unsigned64,
    cucsAdaptorMenloBaseErrorStatsHistMostRecent                     TruthValue,
    cucsAdaptorMenloBaseErrorStatsHistSuspect                        TruthValue,
    cucsAdaptorMenloBaseErrorStatsHistThresholded                    CucsAdaptorMenloBaseErrorStatsHistThresholded,
    cucsAdaptorMenloBaseErrorStatsHistTimeCollected                  DateAndTime,
    cucsAdaptorMenloBaseErrorStatsHistUncorrectableErrors            Unsigned64,
    cucsAdaptorMenloBaseErrorStatsHistUncorrectableErrorsDelta       Unsigned64,
    cucsAdaptorMenloBaseErrorStatsHistUncorrectableErrorsDeltaAvg    Unsigned64,
    cucsAdaptorMenloBaseErrorStatsHistUncorrectableErrorsDeltaMax    Unsigned64,
    cucsAdaptorMenloBaseErrorStatsHistUncorrectableErrorsDeltaMin    Unsigned64
}

cucsAdaptorMenloBaseErrorStatsHistInstanceId OBJECT-TYPE
    SYNTAX       CucsManagedObjectId
    MAX-ACCESS   not-accessible
    STATUS       current
    DESCRIPTION
        "Instance identifier of the managed object."
    ::= { cucsAdaptorMenloBaseErrorStatsHistEntry 1 }

cucsAdaptorMenloBaseErrorStatsHistDn OBJECT-TYPE
    SYNTAX       CucsManagedObjectDn
    MAX-ACCESS   read-only
    STATUS       current
    DESCRIPTION
        "Cisco UCS adaptor:MenloBaseErrorStatsHist:dn managed
        object property"
    ::= { cucsAdaptorMenloBaseErrorStatsHistEntry 2 }

cucsAdaptorMenloBaseErrorStatsHistRn OBJECT-TYPE
    SYNTAX       SnmpAdminString
    MAX-ACCESS   read-only
    STATUS       current
    DESCRIPTION
        "Cisco UCS adaptor:MenloBaseErrorStatsHist:rn managed
        object property"
    ::= { cucsAdaptorMenloBaseErrorStatsHistEntry 3 }

cucsAdaptorMenloBaseErrorStatsHistCorrectableErrors OBJECT-TYPE
    SYNTAX       Unsigned64
    MAX-ACCESS   read-only
    STATUS       current
    DESCRIPTION
        "Cisco UCS adaptor:MenloBaseErrorStatsHist:correctableErrors
        managed object property"
    ::= { cucsAdaptorMenloBaseErrorStatsHistEntry 4 }

cucsAdaptorMenloBaseErrorStatsHistCorrectableErrorsDelta OBJECT-TYPE
    SYNTAX       Unsigned64
    MAX-ACCESS   read-only
    STATUS       current
    DESCRIPTION
        "Cisco UCS adaptor:MenloBaseErrorStatsHist:correctableErrorsDelta
        managed object property"
    ::= { cucsAdaptorMenloBaseErrorStatsHistEntry 5 }

cucsAdaptorMenloBaseErrorStatsHistCorrectableErrorsDeltaAvg OBJECT-TYPE
    SYNTAX       Unsigned64
    MAX-ACCESS   read-only
    STATUS       current
    DESCRIPTION
        "Cisco UCS adaptor:MenloBaseErrorStatsHist:correctableErrorsDeltaA
        vg managed object property"
    ::= { cucsAdaptorMenloBaseErrorStatsHistEntry 6 }

cucsAdaptorMenloBaseErrorStatsHistCorrectableErrorsDeltaMax OBJECT-TYPE
    SYNTAX       Unsigned64
    MAX-ACCESS   read-only
    STATUS       current
    DESCRIPTION
        "Cisco UCS adaptor:MenloBaseErrorStatsHist:correctableErrorsDeltaM
        ax managed object property"
    ::= { cucsAdaptorMenloBaseErrorStatsHistEntry 7 }

cucsAdaptorMenloBaseErrorStatsHistCorrectableErrorsDeltaMin OBJECT-TYPE
    SYNTAX       Unsigned64
    MAX-ACCESS   read-only
    STATUS       current
    DESCRIPTION
        "Cisco UCS adaptor:MenloBaseErrorStatsHist:correctableErrorsDeltaM
        in managed object property"
    ::= { cucsAdaptorMenloBaseErrorStatsHistEntry 8 }

cucsAdaptorMenloBaseErrorStatsHistId OBJECT-TYPE
    SYNTAX       Unsigned64
    MAX-ACCESS   read-only
    STATUS       current
    DESCRIPTION
        "Cisco UCS adaptor:MenloBaseErrorStatsHist:id managed
        object property"
    ::= { cucsAdaptorMenloBaseErrorStatsHistEntry 9 }

cucsAdaptorMenloBaseErrorStatsHistMostRecent OBJECT-TYPE
    SYNTAX       TruthValue
    MAX-ACCESS   read-only
    STATUS       current
    DESCRIPTION
        "Cisco UCS adaptor:MenloBaseErrorStatsHist:mostRecent
        managed object property"
    ::= { cucsAdaptorMenloBaseErrorStatsHistEntry 10 }

cucsAdaptorMenloBaseErrorStatsHistSuspect OBJECT-TYPE
    SYNTAX       TruthValue
    MAX-ACCESS   read-only
    STATUS       current
    DESCRIPTION
        "Cisco UCS adaptor:MenloBaseErrorStatsHist:suspect
        managed object property"
    ::= { cucsAdaptorMenloBaseErrorStatsHistEntry 11 }

cucsAdaptorMenloBaseErrorStatsHistThresholded OBJECT-TYPE
    SYNTAX       CucsAdaptorMenloBaseErrorStatsHistThresholded
    MAX-ACCESS   read-only
    STATUS       current
    DESCRIPTION
        "Cisco UCS adaptor:MenloBaseErrorStatsHist:thresholded
        managed object property"
    ::= { cucsAdaptorMenloBaseErrorStatsHistEntry 12 }

cucsAdaptorMenloBaseErrorStatsHistTimeCollected OBJECT-TYPE
    SYNTAX       DateAndTime
    MAX-ACCESS   read-only
    STATUS       current
    DESCRIPTION
        "Cisco UCS adaptor:MenloBaseErrorStatsHist:timeCollected
        managed object property"
    ::= { cucsAdaptorMenloBaseErrorStatsHistEntry 13 }

cucsAdaptorMenloBaseErrorStatsHistUncorrectableErrors OBJECT-TYPE
    SYNTAX       Unsigned64
    MAX-ACCESS   read-only
    STATUS       current
    DESCRIPTION
        "Cisco UCS adaptor:MenloBaseErrorStatsHist:uncorrectableErrors
        managed object property"
    ::= { cucsAdaptorMenloBaseErrorStatsHistEntry 14 }

cucsAdaptorMenloBaseErrorStatsHistUncorrectableErrorsDelta OBJECT-TYPE
    SYNTAX       Unsigned64
    MAX-ACCESS   read-only
    STATUS       current
    DESCRIPTION
        "Cisco UCS adaptor:MenloBaseErrorStatsHist:uncorrectableErrorsDelt
        a managed object property"
    ::= { cucsAdaptorMenloBaseErrorStatsHistEntry 15 }

cucsAdaptorMenloBaseErrorStatsHistUncorrectableErrorsDeltaAvg OBJECT-TYPE
    SYNTAX       Unsigned64
    MAX-ACCESS   read-only
    STATUS       current
    DESCRIPTION
        "Cisco UCS adaptor:MenloBaseErrorStatsHist:uncorrectableErrorsDelt
        aAvg managed object property"
    ::= { cucsAdaptorMenloBaseErrorStatsHistEntry 16 }

cucsAdaptorMenloBaseErrorStatsHistUncorrectableErrorsDeltaMax OBJECT-TYPE
    SYNTAX       Unsigned64
    MAX-ACCESS   read-only
    STATUS       current
    DESCRIPTION
        "Cisco UCS adaptor:MenloBaseErrorStatsHist:uncorrectableErrorsDelt
        aMax managed object property"
    ::= { cucsAdaptorMenloBaseErrorStatsHistEntry 17 }

cucsAdaptorMenloBaseErrorStatsHistUncorrectableErrorsDeltaMin OBJECT-TYPE
    SYNTAX       Unsigned64
    MAX-ACCESS   read-only
    STATUS       current
    DESCRIPTION
        "Cisco UCS adaptor:MenloBaseErrorStatsHist:uncorrectableErrorsDelt
        aMin managed object property"
    ::= { cucsAdaptorMenloBaseErrorStatsHistEntry 18 }

cucsAdaptorMenloDcePortStatsTable OBJECT-TYPE
    SYNTAX           SEQUENCE OF CucsAdaptorMenloDcePortStatsEntry
    MAX-ACCESS       not-accessible
    STATUS           current
    DESCRIPTION
        "Cisco UCS adaptor:MenloDcePortStats managed object table"
    ::= { cucsAdaptorObjects 57 }

cucsAdaptorMenloDcePortStatsEntry OBJECT-TYPE
    SYNTAX           CucsAdaptorMenloDcePortStatsEntry
    MAX-ACCESS       not-accessible
    STATUS           current
    DESCRIPTION
        "Entry for the cucsAdaptorMenloDcePortStatsTable table."
    INDEX { cucsAdaptorMenloDcePortStatsInstanceId }
    ::= { cucsAdaptorMenloDcePortStatsTable 1 }

CucsAdaptorMenloDcePortStatsEntry ::= SEQUENCE {
    cucsAdaptorMenloDcePortStatsInstanceId                           CucsManagedObjectId,
    cucsAdaptorMenloDcePortStatsDn                                   CucsManagedObjectDn,
    cucsAdaptorMenloDcePortStatsRn                                   SnmpAdminString,
    cucsAdaptorMenloDcePortStatsIntervals                            Gauge32,
    cucsAdaptorMenloDcePortStatsMenloPortIndex                       CucsAdaptorMenloStatsIndex,
    cucsAdaptorMenloDcePortStatsRxPauseCFC                           Unsigned64,
    cucsAdaptorMenloDcePortStatsRxPauseCFCDelta                      Counter64,
    cucsAdaptorMenloDcePortStatsRxPauseCFCDeltaAvg                   Unsigned64,
    cucsAdaptorMenloDcePortStatsRxPauseCFCDeltaMax                   Unsigned64,
    cucsAdaptorMenloDcePortStatsRxPauseCFCDeltaMin                   Unsigned64,
    cucsAdaptorMenloDcePortStatsRxPausePFC                           Unsigned64,
    cucsAdaptorMenloDcePortStatsRxPausePFCDelta                      Counter64,
    cucsAdaptorMenloDcePortStatsRxPausePFCDeltaAvg                   Unsigned64,
    cucsAdaptorMenloDcePortStatsRxPausePFCDeltaMax                   Unsigned64,
    cucsAdaptorMenloDcePortStatsRxPausePFCDeltaMin                   Unsigned64,
    cucsAdaptorMenloDcePortStatsSuspect                              TruthValue,
    cucsAdaptorMenloDcePortStatsThresholded                          CucsAdaptorMenloDcePortStatsThresholded,
    cucsAdaptorMenloDcePortStatsTimeCollected                        DateAndTime,
    cucsAdaptorMenloDcePortStatsTxPauseCFC                           Unsigned64,
    cucsAdaptorMenloDcePortStatsTxPauseCFCDelta                      Counter64,
    cucsAdaptorMenloDcePortStatsTxPauseCFCDeltaAvg                   Unsigned64,
    cucsAdaptorMenloDcePortStatsTxPauseCFCDeltaMax                   Unsigned64,
    cucsAdaptorMenloDcePortStatsTxPauseCFCDeltaMin                   Unsigned64,
    cucsAdaptorMenloDcePortStatsTxPausePFC                           Unsigned64,
    cucsAdaptorMenloDcePortStatsTxPausePFCDelta                      Counter64,
    cucsAdaptorMenloDcePortStatsTxPausePFCDeltaAvg                   Unsigned64,
    cucsAdaptorMenloDcePortStatsTxPausePFCDeltaMax                   Unsigned64,
    cucsAdaptorMenloDcePortStatsTxPausePFCDeltaMin                   Unsigned64,
    cucsAdaptorMenloDcePortStatsUpdate                               Gauge32
}

cucsAdaptorMenloDcePortStatsInstanceId OBJECT-TYPE
    SYNTAX       CucsManagedObjectId
    MAX-ACCESS   not-accessible
    STATUS       current
    DESCRIPTION
        "Instance identifier of the managed object."
    ::= { cucsAdaptorMenloDcePortStatsEntry 1 }

cucsAdaptorMenloDcePortStatsDn OBJECT-TYPE
    SYNTAX       CucsManagedObjectDn
    MAX-ACCESS   read-only
    STATUS       current
    DESCRIPTION
        "Cisco UCS adaptor:MenloDcePortStats:dn managed object property"
    ::= { cucsAdaptorMenloDcePortStatsEntry 2 }

cucsAdaptorMenloDcePortStatsRn OBJECT-TYPE
    SYNTAX       SnmpAdminString
    MAX-ACCESS   read-only
    STATUS       current
    DESCRIPTION
        "Cisco UCS adaptor:MenloDcePortStats:rn managed object property"
    ::= { cucsAdaptorMenloDcePortStatsEntry 3 }

cucsAdaptorMenloDcePortStatsIntervals OBJECT-TYPE
    SYNTAX       Gauge32
    MAX-ACCESS   read-only
    STATUS       current
    DESCRIPTION
        "Cisco UCS adaptor:MenloDcePortStats:intervals
        managed object property"
    ::= { cucsAdaptorMenloDcePortStatsEntry 4 }

cucsAdaptorMenloDcePortStatsMenloPortIndex OBJECT-TYPE
    SYNTAX       CucsAdaptorMenloStatsIndex
    MAX-ACCESS   read-only
    STATUS       current
    DESCRIPTION
        "Cisco UCS adaptor:MenloDcePortStats:menloPortIndex
        managed object property"
    ::= { cucsAdaptorMenloDcePortStatsEntry 5 }

cucsAdaptorMenloDcePortStatsRxPauseCFC OBJECT-TYPE
    SYNTAX       Unsigned64
    MAX-ACCESS   read-only
    STATUS       current
    DESCRIPTION
        "Cisco UCS adaptor:MenloDcePortStats:rxPauseCFC
        managed object property"
    ::= { cucsAdaptorMenloDcePortStatsEntry 6 }

cucsAdaptorMenloDcePortStatsRxPauseCFCDelta OBJECT-TYPE
    SYNTAX       Counter64
    MAX-ACCESS   read-only
    STATUS       current
    DESCRIPTION
        "Cisco UCS adaptor:MenloDcePortStats:rxPauseCFCDelta
        managed object property"
    ::= { cucsAdaptorMenloDcePortStatsEntry 7 }

cucsAdaptorMenloDcePortStatsRxPauseCFCDeltaAvg OBJECT-TYPE
    SYNTAX       Unsigned64
    MAX-ACCESS   read-only
    STATUS       current
    DESCRIPTION
        "Cisco UCS adaptor:MenloDcePortStats:rxPauseCFCDeltaAvg
        managed object property"
    ::= { cucsAdaptorMenloDcePortStatsEntry 8 }

cucsAdaptorMenloDcePortStatsRxPauseCFCDeltaMax OBJECT-TYPE
    SYNTAX       Unsigned64
    MAX-ACCESS   read-only
    STATUS       current
    DESCRIPTION
        "Cisco UCS adaptor:MenloDcePortStats:rxPauseCFCDeltaMax
        managed object property"
    ::= { cucsAdaptorMenloDcePortStatsEntry 9 }

cucsAdaptorMenloDcePortStatsRxPauseCFCDeltaMin OBJECT-TYPE
    SYNTAX       Unsigned64
    MAX-ACCESS   read-only
    STATUS       current
    DESCRIPTION
        "Cisco UCS adaptor:MenloDcePortStats:rxPauseCFCDeltaMin
        managed object property"
    ::= { cucsAdaptorMenloDcePortStatsEntry 10 }

cucsAdaptorMenloDcePortStatsRxPausePFC OBJECT-TYPE
    SYNTAX       Unsigned64
    MAX-ACCESS   read-only
    STATUS       current
    DESCRIPTION
        "Cisco UCS adaptor:MenloDcePortStats:rxPausePFC
        managed object property"
    ::= { cucsAdaptorMenloDcePortStatsEntry 11 }

cucsAdaptorMenloDcePortStatsRxPausePFCDelta OBJECT-TYPE
    SYNTAX       Counter64
    MAX-ACCESS   read-only
    STATUS       current
    DESCRIPTION
        "Cisco UCS adaptor:MenloDcePortStats:rxPausePFCDelta
        managed object property"
    ::= { cucsAdaptorMenloDcePortStatsEntry 12 }

cucsAdaptorMenloDcePortStatsRxPausePFCDeltaAvg OBJECT-TYPE
    SYNTAX       Unsigned64
    MAX-ACCESS   read-only
    STATUS       current
    DESCRIPTION
        "Cisco UCS adaptor:MenloDcePortStats:rxPausePFCDeltaAvg
        managed object property"
    ::= { cucsAdaptorMenloDcePortStatsEntry 13 }

cucsAdaptorMenloDcePortStatsRxPausePFCDeltaMax OBJECT-TYPE
    SYNTAX       Unsigned64
    MAX-ACCESS   read-only
    STATUS       current
    DESCRIPTION
        "Cisco UCS adaptor:MenloDcePortStats:rxPausePFCDeltaMax
        managed object property"
    ::= { cucsAdaptorMenloDcePortStatsEntry 14 }

cucsAdaptorMenloDcePortStatsRxPausePFCDeltaMin OBJECT-TYPE
    SYNTAX       Unsigned64
    MAX-ACCESS   read-only
    STATUS       current
    DESCRIPTION
        "Cisco UCS adaptor:MenloDcePortStats:rxPausePFCDeltaMin
        managed object property"
    ::= { cucsAdaptorMenloDcePortStatsEntry 15 }

cucsAdaptorMenloDcePortStatsSuspect OBJECT-TYPE
    SYNTAX       TruthValue
    MAX-ACCESS   read-only
    STATUS       current
    DESCRIPTION
        "Cisco UCS adaptor:MenloDcePortStats:suspect managed
        object property"
    ::= { cucsAdaptorMenloDcePortStatsEntry 16 }

cucsAdaptorMenloDcePortStatsThresholded OBJECT-TYPE
    SYNTAX       CucsAdaptorMenloDcePortStatsThresholded
    MAX-ACCESS   read-only
    STATUS       current
    DESCRIPTION
        "Cisco UCS adaptor:MenloDcePortStats:thresholded
        managed object property"
    ::= { cucsAdaptorMenloDcePortStatsEntry 17 }

cucsAdaptorMenloDcePortStatsTimeCollected OBJECT-TYPE
    SYNTAX       DateAndTime
    MAX-ACCESS   read-only
    STATUS       current
    DESCRIPTION
        "Cisco UCS adaptor:MenloDcePortStats:timeCollected
        managed object property"
    ::= { cucsAdaptorMenloDcePortStatsEntry 18 }

cucsAdaptorMenloDcePortStatsTxPauseCFC OBJECT-TYPE
    SYNTAX       Unsigned64
    MAX-ACCESS   read-only
    STATUS       current
    DESCRIPTION
        "Cisco UCS adaptor:MenloDcePortStats:txPauseCFC
        managed object property"
    ::= { cucsAdaptorMenloDcePortStatsEntry 19 }

cucsAdaptorMenloDcePortStatsTxPauseCFCDelta OBJECT-TYPE
    SYNTAX       Counter64
    MAX-ACCESS   read-only
    STATUS       current
    DESCRIPTION
        "Cisco UCS adaptor:MenloDcePortStats:txPauseCFCDelta
        managed object property"
    ::= { cucsAdaptorMenloDcePortStatsEntry 20 }

cucsAdaptorMenloDcePortStatsTxPauseCFCDeltaAvg OBJECT-TYPE
    SYNTAX       Unsigned64
    MAX-ACCESS   read-only
    STATUS       current
    DESCRIPTION
        "Cisco UCS adaptor:MenloDcePortStats:txPauseCFCDeltaAvg
        managed object property"
    ::= { cucsAdaptorMenloDcePortStatsEntry 21 }

cucsAdaptorMenloDcePortStatsTxPauseCFCDeltaMax OBJECT-TYPE
    SYNTAX       Unsigned64
    MAX-ACCESS   read-only
    STATUS       current
    DESCRIPTION
        "Cisco UCS adaptor:MenloDcePortStats:txPauseCFCDeltaMax
        managed object property"
    ::= { cucsAdaptorMenloDcePortStatsEntry 22 }

cucsAdaptorMenloDcePortStatsTxPauseCFCDeltaMin OBJECT-TYPE
    SYNTAX       Unsigned64
    MAX-ACCESS   read-only
    STATUS       current
    DESCRIPTION
        "Cisco UCS adaptor:MenloDcePortStats:txPauseCFCDeltaMin
        managed object property"
    ::= { cucsAdaptorMenloDcePortStatsEntry 23 }

cucsAdaptorMenloDcePortStatsTxPausePFC OBJECT-TYPE
    SYNTAX       Unsigned64
    MAX-ACCESS   read-only
    STATUS       current
    DESCRIPTION
        "Cisco UCS adaptor:MenloDcePortStats:txPausePFC
        managed object property"
    ::= { cucsAdaptorMenloDcePortStatsEntry 24 }

cucsAdaptorMenloDcePortStatsTxPausePFCDelta OBJECT-TYPE
    SYNTAX       Counter64
    MAX-ACCESS   read-only
    STATUS       current
    DESCRIPTION
        "Cisco UCS adaptor:MenloDcePortStats:txPausePFCDelta
        managed object property"
    ::= { cucsAdaptorMenloDcePortStatsEntry 25 }

cucsAdaptorMenloDcePortStatsTxPausePFCDeltaAvg OBJECT-TYPE
    SYNTAX       Unsigned64
    MAX-ACCESS   read-only
    STATUS       current
    DESCRIPTION
        "Cisco UCS adaptor:MenloDcePortStats:txPausePFCDeltaAvg
        managed object property"
    ::= { cucsAdaptorMenloDcePortStatsEntry 26 }

cucsAdaptorMenloDcePortStatsTxPausePFCDeltaMax OBJECT-TYPE
    SYNTAX       Unsigned64
    MAX-ACCESS   read-only
    STATUS       current
    DESCRIPTION
        "Cisco UCS adaptor:MenloDcePortStats:txPausePFCDeltaMax
        managed object property"
    ::= { cucsAdaptorMenloDcePortStatsEntry 27 }

cucsAdaptorMenloDcePortStatsTxPausePFCDeltaMin OBJECT-TYPE
    SYNTAX       Unsigned64
    MAX-ACCESS   read-only
    STATUS       current
    DESCRIPTION
        "Cisco UCS adaptor:MenloDcePortStats:txPausePFCDeltaMin
        managed object property"
    ::= { cucsAdaptorMenloDcePortStatsEntry 28 }

cucsAdaptorMenloDcePortStatsUpdate OBJECT-TYPE
    SYNTAX       Gauge32
    MAX-ACCESS   read-only
    STATUS       current
    DESCRIPTION
        "Cisco UCS adaptor:MenloDcePortStats:update managed
        object property"
    ::= { cucsAdaptorMenloDcePortStatsEntry 29 }

cucsAdaptorMenloDcePortStatsHistTable OBJECT-TYPE
    SYNTAX           SEQUENCE OF CucsAdaptorMenloDcePortStatsHistEntry
    MAX-ACCESS       not-accessible
    STATUS           current
    DESCRIPTION
        "Cisco UCS adaptor:MenloDcePortStatsHist managed object table"
    ::= { cucsAdaptorObjects 58 }

cucsAdaptorMenloDcePortStatsHistEntry OBJECT-TYPE
    SYNTAX           CucsAdaptorMenloDcePortStatsHistEntry
    MAX-ACCESS       not-accessible
    STATUS           current
    DESCRIPTION
        "Entry for the cucsAdaptorMenloDcePortStatsHistTable table."
    INDEX { cucsAdaptorMenloDcePortStatsHistInstanceId }
    ::= { cucsAdaptorMenloDcePortStatsHistTable 1 }

CucsAdaptorMenloDcePortStatsHistEntry ::= SEQUENCE {
    cucsAdaptorMenloDcePortStatsHistInstanceId                       CucsManagedObjectId,
    cucsAdaptorMenloDcePortStatsHistDn                               CucsManagedObjectDn,
    cucsAdaptorMenloDcePortStatsHistRn                               SnmpAdminString,
    cucsAdaptorMenloDcePortStatsHistId                               Unsigned64,
    cucsAdaptorMenloDcePortStatsHistMostRecent                       TruthValue,
    cucsAdaptorMenloDcePortStatsHistRxPauseCFC                       Unsigned64,
    cucsAdaptorMenloDcePortStatsHistRxPauseCFCDelta                  Unsigned64,
    cucsAdaptorMenloDcePortStatsHistRxPauseCFCDeltaAvg               Unsigned64,
    cucsAdaptorMenloDcePortStatsHistRxPauseCFCDeltaMax               Unsigned64,
    cucsAdaptorMenloDcePortStatsHistRxPauseCFCDeltaMin               Unsigned64,
    cucsAdaptorMenloDcePortStatsHistRxPausePFC                       Unsigned64,
    cucsAdaptorMenloDcePortStatsHistRxPausePFCDelta                  Unsigned64,
    cucsAdaptorMenloDcePortStatsHistRxPausePFCDeltaAvg               Unsigned64,
    cucsAdaptorMenloDcePortStatsHistRxPausePFCDeltaMax               Unsigned64,
    cucsAdaptorMenloDcePortStatsHistRxPausePFCDeltaMin               Unsigned64,
    cucsAdaptorMenloDcePortStatsHistSuspect                          TruthValue,
    cucsAdaptorMenloDcePortStatsHistThresholded                      CucsAdaptorMenloDcePortStatsHistThresholded,
    cucsAdaptorMenloDcePortStatsHistTimeCollected                    DateAndTime,
    cucsAdaptorMenloDcePortStatsHistTxPauseCFC                       Unsigned64,
    cucsAdaptorMenloDcePortStatsHistTxPauseCFCDelta                  Unsigned64,
    cucsAdaptorMenloDcePortStatsHistTxPauseCFCDeltaAvg               Unsigned64,
    cucsAdaptorMenloDcePortStatsHistTxPauseCFCDeltaMax               Unsigned64,
    cucsAdaptorMenloDcePortStatsHistTxPauseCFCDeltaMin               Unsigned64,
    cucsAdaptorMenloDcePortStatsHistTxPausePFC                       Unsigned64,
    cucsAdaptorMenloDcePortStatsHistTxPausePFCDelta                  Unsigned64,
    cucsAdaptorMenloDcePortStatsHistTxPausePFCDeltaAvg               Unsigned64,
    cucsAdaptorMenloDcePortStatsHistTxPausePFCDeltaMax               Unsigned64,
    cucsAdaptorMenloDcePortStatsHistTxPausePFCDeltaMin               Unsigned64
}

cucsAdaptorMenloDcePortStatsHistInstanceId OBJECT-TYPE
    SYNTAX       CucsManagedObjectId
    MAX-ACCESS   not-accessible
    STATUS       current
    DESCRIPTION
        "Instance identifier of the managed object."
    ::= { cucsAdaptorMenloDcePortStatsHistEntry 1 }

cucsAdaptorMenloDcePortStatsHistDn OBJECT-TYPE
    SYNTAX       CucsManagedObjectDn
    MAX-ACCESS   read-only
    STATUS       current
    DESCRIPTION
        "Cisco UCS adaptor:MenloDcePortStatsHist:dn managed
        object property"
    ::= { cucsAdaptorMenloDcePortStatsHistEntry 2 }

cucsAdaptorMenloDcePortStatsHistRn OBJECT-TYPE
    SYNTAX       SnmpAdminString
    MAX-ACCESS   read-only
    STATUS       current
    DESCRIPTION
        "Cisco UCS adaptor:MenloDcePortStatsHist:rn managed
        object property"
    ::= { cucsAdaptorMenloDcePortStatsHistEntry 3 }

cucsAdaptorMenloDcePortStatsHistId OBJECT-TYPE
    SYNTAX       Unsigned64
    MAX-ACCESS   read-only
    STATUS       current
    DESCRIPTION
        "Cisco UCS adaptor:MenloDcePortStatsHist:id managed
        object property"
    ::= { cucsAdaptorMenloDcePortStatsHistEntry 4 }

cucsAdaptorMenloDcePortStatsHistMostRecent OBJECT-TYPE
    SYNTAX       TruthValue
    MAX-ACCESS   read-only
    STATUS       current
    DESCRIPTION
        "Cisco UCS adaptor:MenloDcePortStatsHist:mostRecent
        managed object property"
    ::= { cucsAdaptorMenloDcePortStatsHistEntry 5 }

cucsAdaptorMenloDcePortStatsHistRxPauseCFC OBJECT-TYPE
    SYNTAX       Unsigned64
    MAX-ACCESS   read-only
    STATUS       current
    DESCRIPTION
        "Cisco UCS adaptor:MenloDcePortStatsHist:rxPauseCFC
        managed object property"
    ::= { cucsAdaptorMenloDcePortStatsHistEntry 6 }

cucsAdaptorMenloDcePortStatsHistRxPauseCFCDelta OBJECT-TYPE
    SYNTAX       Unsigned64
    MAX-ACCESS   read-only
    STATUS       current
    DESCRIPTION
        "Cisco UCS adaptor:MenloDcePortStatsHist:rxPauseCFCDelta
        managed object property"
    ::= { cucsAdaptorMenloDcePortStatsHistEntry 7 }

cucsAdaptorMenloDcePortStatsHistRxPauseCFCDeltaAvg OBJECT-TYPE
    SYNTAX       Unsigned64
    MAX-ACCESS   read-only
    STATUS       current
    DESCRIPTION
        "Cisco UCS adaptor:MenloDcePortStatsHist:rxPauseCFCDeltaAvg
        managed object property"
    ::= { cucsAdaptorMenloDcePortStatsHistEntry 8 }

cucsAdaptorMenloDcePortStatsHistRxPauseCFCDeltaMax OBJECT-TYPE
    SYNTAX       Unsigned64
    MAX-ACCESS   read-only
    STATUS       current
    DESCRIPTION
        "Cisco UCS adaptor:MenloDcePortStatsHist:rxPauseCFCDeltaMax
        managed object property"
    ::= { cucsAdaptorMenloDcePortStatsHistEntry 9 }

cucsAdaptorMenloDcePortStatsHistRxPauseCFCDeltaMin OBJECT-TYPE
    SYNTAX       Unsigned64
    MAX-ACCESS   read-only
    STATUS       current
    DESCRIPTION
        "Cisco UCS adaptor:MenloDcePortStatsHist:rxPauseCFCDeltaMin
        managed object property"
    ::= { cucsAdaptorMenloDcePortStatsHistEntry 10 }

cucsAdaptorMenloDcePortStatsHistRxPausePFC OBJECT-TYPE
    SYNTAX       Unsigned64
    MAX-ACCESS   read-only
    STATUS       current
    DESCRIPTION
        "Cisco UCS adaptor:MenloDcePortStatsHist:rxPausePFC
        managed object property"
    ::= { cucsAdaptorMenloDcePortStatsHistEntry 11 }

cucsAdaptorMenloDcePortStatsHistRxPausePFCDelta OBJECT-TYPE
    SYNTAX       Unsigned64
    MAX-ACCESS   read-only
    STATUS       current
    DESCRIPTION
        "Cisco UCS adaptor:MenloDcePortStatsHist:rxPausePFCDelta
        managed object property"
    ::= { cucsAdaptorMenloDcePortStatsHistEntry 12 }

cucsAdaptorMenloDcePortStatsHistRxPausePFCDeltaAvg OBJECT-TYPE
    SYNTAX       Unsigned64
    MAX-ACCESS   read-only
    STATUS       current
    DESCRIPTION
        "Cisco UCS adaptor:MenloDcePortStatsHist:rxPausePFCDeltaAvg
        managed object property"
    ::= { cucsAdaptorMenloDcePortStatsHistEntry 13 }

cucsAdaptorMenloDcePortStatsHistRxPausePFCDeltaMax OBJECT-TYPE
    SYNTAX       Unsigned64
    MAX-ACCESS   read-only
    STATUS       current
    DESCRIPTION
        "Cisco UCS adaptor:MenloDcePortStatsHist:rxPausePFCDeltaMax
        managed object property"
    ::= { cucsAdaptorMenloDcePortStatsHistEntry 14 }

cucsAdaptorMenloDcePortStatsHistRxPausePFCDeltaMin OBJECT-TYPE
    SYNTAX       Unsigned64
    MAX-ACCESS   read-only
    STATUS       current
    DESCRIPTION
        "Cisco UCS adaptor:MenloDcePortStatsHist:rxPausePFCDeltaMin
        managed object property"
    ::= { cucsAdaptorMenloDcePortStatsHistEntry 15 }

cucsAdaptorMenloDcePortStatsHistSuspect OBJECT-TYPE
    SYNTAX       TruthValue
    MAX-ACCESS   read-only
    STATUS       current
    DESCRIPTION
        "Cisco UCS adaptor:MenloDcePortStatsHist:suspect
        managed object property"
    ::= { cucsAdaptorMenloDcePortStatsHistEntry 16 }

cucsAdaptorMenloDcePortStatsHistThresholded OBJECT-TYPE
    SYNTAX       CucsAdaptorMenloDcePortStatsHistThresholded
    MAX-ACCESS   read-only
    STATUS       current
    DESCRIPTION
        "Cisco UCS adaptor:MenloDcePortStatsHist:thresholded
        managed object property"
    ::= { cucsAdaptorMenloDcePortStatsHistEntry 17 }

cucsAdaptorMenloDcePortStatsHistTimeCollected OBJECT-TYPE
    SYNTAX       DateAndTime
    MAX-ACCESS   read-only
    STATUS       current
    DESCRIPTION
        "Cisco UCS adaptor:MenloDcePortStatsHist:timeCollected
        managed object property"
    ::= { cucsAdaptorMenloDcePortStatsHistEntry 18 }

cucsAdaptorMenloDcePortStatsHistTxPauseCFC OBJECT-TYPE
    SYNTAX       Unsigned64
    MAX-ACCESS   read-only
    STATUS       current
    DESCRIPTION
        "Cisco UCS adaptor:MenloDcePortStatsHist:txPauseCFC
        managed object property"
    ::= { cucsAdaptorMenloDcePortStatsHistEntry 19 }

cucsAdaptorMenloDcePortStatsHistTxPauseCFCDelta OBJECT-TYPE
    SYNTAX       Unsigned64
    MAX-ACCESS   read-only
    STATUS       current
    DESCRIPTION
        "Cisco UCS adaptor:MenloDcePortStatsHist:txPauseCFCDelta
        managed object property"
    ::= { cucsAdaptorMenloDcePortStatsHistEntry 20 }

cucsAdaptorMenloDcePortStatsHistTxPauseCFCDeltaAvg OBJECT-TYPE
    SYNTAX       Unsigned64
    MAX-ACCESS   read-only
    STATUS       current
    DESCRIPTION
        "Cisco UCS adaptor:MenloDcePortStatsHist:txPauseCFCDeltaAvg
        managed object property"
    ::= { cucsAdaptorMenloDcePortStatsHistEntry 21 }

cucsAdaptorMenloDcePortStatsHistTxPauseCFCDeltaMax OBJECT-TYPE
    SYNTAX       Unsigned64
    MAX-ACCESS   read-only
    STATUS       current
    DESCRIPTION
        "Cisco UCS adaptor:MenloDcePortStatsHist:txPauseCFCDeltaMax
        managed object property"
    ::= { cucsAdaptorMenloDcePortStatsHistEntry 22 }

cucsAdaptorMenloDcePortStatsHistTxPauseCFCDeltaMin OBJECT-TYPE
    SYNTAX       Unsigned64
    MAX-ACCESS   read-only
    STATUS       current
    DESCRIPTION
        "Cisco UCS adaptor:MenloDcePortStatsHist:txPauseCFCDeltaMin
        managed object property"
    ::= { cucsAdaptorMenloDcePortStatsHistEntry 23 }

cucsAdaptorMenloDcePortStatsHistTxPausePFC OBJECT-TYPE
    SYNTAX       Unsigned64
    MAX-ACCESS   read-only
    STATUS       current
    DESCRIPTION
        "Cisco UCS adaptor:MenloDcePortStatsHist:txPausePFC
        managed object property"
    ::= { cucsAdaptorMenloDcePortStatsHistEntry 24 }

cucsAdaptorMenloDcePortStatsHistTxPausePFCDelta OBJECT-TYPE
    SYNTAX       Unsigned64
    MAX-ACCESS   read-only
    STATUS       current
    DESCRIPTION
        "Cisco UCS adaptor:MenloDcePortStatsHist:txPausePFCDelta
        managed object property"
    ::= { cucsAdaptorMenloDcePortStatsHistEntry 25 }

cucsAdaptorMenloDcePortStatsHistTxPausePFCDeltaAvg OBJECT-TYPE
    SYNTAX       Unsigned64
    MAX-ACCESS   read-only
    STATUS       current
    DESCRIPTION
        "Cisco UCS adaptor:MenloDcePortStatsHist:txPausePFCDeltaAvg
        managed object property"
    ::= { cucsAdaptorMenloDcePortStatsHistEntry 26 }

cucsAdaptorMenloDcePortStatsHistTxPausePFCDeltaMax OBJECT-TYPE
    SYNTAX       Unsigned64
    MAX-ACCESS   read-only
    STATUS       current
    DESCRIPTION
        "Cisco UCS adaptor:MenloDcePortStatsHist:txPausePFCDeltaMax
        managed object property"
    ::= { cucsAdaptorMenloDcePortStatsHistEntry 27 }

cucsAdaptorMenloDcePortStatsHistTxPausePFCDeltaMin OBJECT-TYPE
    SYNTAX       Unsigned64
    MAX-ACCESS   read-only
    STATUS       current
    DESCRIPTION
        "Cisco UCS adaptor:MenloDcePortStatsHist:txPausePFCDeltaMin
        managed object property"
    ::= { cucsAdaptorMenloDcePortStatsHistEntry 28 }

cucsAdaptorMenloEthErrorStatsTable OBJECT-TYPE
    SYNTAX           SEQUENCE OF CucsAdaptorMenloEthErrorStatsEntry
    MAX-ACCESS       not-accessible
    STATUS           current
    DESCRIPTION
        "Cisco UCS adaptor:MenloEthErrorStats managed object table"
    ::= { cucsAdaptorObjects 59 }

cucsAdaptorMenloEthErrorStatsEntry OBJECT-TYPE
    SYNTAX           CucsAdaptorMenloEthErrorStatsEntry
    MAX-ACCESS       not-accessible
    STATUS           current
    DESCRIPTION
        "Entry for the cucsAdaptorMenloEthErrorStatsTable table."
    INDEX { cucsAdaptorMenloEthErrorStatsInstanceId }
    ::= { cucsAdaptorMenloEthErrorStatsTable 1 }

CucsAdaptorMenloEthErrorStatsEntry ::= SEQUENCE {
    cucsAdaptorMenloEthErrorStatsInstanceId                          CucsManagedObjectId,
    cucsAdaptorMenloEthErrorStatsDn                                  CucsManagedObjectDn,
    cucsAdaptorMenloEthErrorStatsRn                                  SnmpAdminString,
    cucsAdaptorMenloEthErrorStatsCorrectableErrors                   Unsigned64,
    cucsAdaptorMenloEthErrorStatsCorrectableErrorsDelta              Counter64,
    cucsAdaptorMenloEthErrorStatsCorrectableErrorsDeltaAvg           Unsigned64,
    cucsAdaptorMenloEthErrorStatsCorrectableErrorsDeltaMax           Unsigned64,
    cucsAdaptorMenloEthErrorStatsCorrectableErrorsDeltaMin           Unsigned64,
    cucsAdaptorMenloEthErrorStatsDropAcl                             Unsigned64,
    cucsAdaptorMenloEthErrorStatsDropAclDelta                        Counter64,
    cucsAdaptorMenloEthErrorStatsDropAclDeltaAvg                     Unsigned64,
    cucsAdaptorMenloEthErrorStatsDropAclDeltaMax                     Unsigned64,
    cucsAdaptorMenloEthErrorStatsDropAclDeltaMin                     Unsigned64,
    cucsAdaptorMenloEthErrorStatsIntervals                           Gauge32,
    cucsAdaptorMenloEthErrorStatsMenloEthIndex                       CucsAdaptorMenloStatsIndex,
    cucsAdaptorMenloEthErrorStatsPopErrors                           Unsigned64,
    cucsAdaptorMenloEthErrorStatsPopErrorsDelta                      Counter64,
    cucsAdaptorMenloEthErrorStatsPopErrorsDeltaAvg                   Unsigned64,
    cucsAdaptorMenloEthErrorStatsPopErrorsDeltaMax                   Unsigned64,
    cucsAdaptorMenloEthErrorStatsPopErrorsDeltaMin                   Unsigned64,
    cucsAdaptorMenloEthErrorStatsPushErrors                          Unsigned64,
    cucsAdaptorMenloEthErrorStatsPushErrorsDelta                     Counter64,
    cucsAdaptorMenloEthErrorStatsPushErrorsDeltaAvg                  Unsigned64,
    cucsAdaptorMenloEthErrorStatsPushErrorsDeltaMax                  Unsigned64,
    cucsAdaptorMenloEthErrorStatsPushErrorsDeltaMin                  Unsigned64,
    cucsAdaptorMenloEthErrorStatsSuspect                             TruthValue,
    cucsAdaptorMenloEthErrorStatsThresholded                         CucsAdaptorMenloEthErrorStatsThresholded,
    cucsAdaptorMenloEthErrorStatsTimeCollected                       DateAndTime,
    cucsAdaptorMenloEthErrorStatsUncorrectableErrors                 Unsigned64,
    cucsAdaptorMenloEthErrorStatsUncorrectableErrorsDelta            Counter64,
    cucsAdaptorMenloEthErrorStatsUncorrectableErrorsDeltaAvg         Unsigned64,
    cucsAdaptorMenloEthErrorStatsUncorrectableErrorsDeltaMax         Unsigned64,
    cucsAdaptorMenloEthErrorStatsUncorrectableErrorsDeltaMin         Unsigned64,
    cucsAdaptorMenloEthErrorStatsUpdate                              Gauge32
}

cucsAdaptorMenloEthErrorStatsInstanceId OBJECT-TYPE
    SYNTAX       CucsManagedObjectId
    MAX-ACCESS   not-accessible
    STATUS       current
    DESCRIPTION
        "Instance identifier of the managed object."
    ::= { cucsAdaptorMenloEthErrorStatsEntry 1 }

cucsAdaptorMenloEthErrorStatsDn OBJECT-TYPE
    SYNTAX       CucsManagedObjectDn
    MAX-ACCESS   read-only
    STATUS       current
    DESCRIPTION
        "Cisco UCS adaptor:MenloEthErrorStats:dn managed object property"
    ::= { cucsAdaptorMenloEthErrorStatsEntry 2 }

cucsAdaptorMenloEthErrorStatsRn OBJECT-TYPE
    SYNTAX       SnmpAdminString
    MAX-ACCESS   read-only
    STATUS       current
    DESCRIPTION
        "Cisco UCS adaptor:MenloEthErrorStats:rn managed object property"
    ::= { cucsAdaptorMenloEthErrorStatsEntry 3 }

cucsAdaptorMenloEthErrorStatsCorrectableErrors OBJECT-TYPE
    SYNTAX       Unsigned64
    MAX-ACCESS   read-only
    STATUS       current
    DESCRIPTION
        "Cisco UCS adaptor:MenloEthErrorStats:correctableErrors
        managed object property"
    ::= { cucsAdaptorMenloEthErrorStatsEntry 4 }

cucsAdaptorMenloEthErrorStatsCorrectableErrorsDelta OBJECT-TYPE
    SYNTAX       Counter64
    MAX-ACCESS   read-only
    STATUS       current
    DESCRIPTION
        "Cisco UCS adaptor:MenloEthErrorStats:correctableErrorsDelta
        managed object property"
    ::= { cucsAdaptorMenloEthErrorStatsEntry 5 }

cucsAdaptorMenloEthErrorStatsCorrectableErrorsDeltaAvg OBJECT-TYPE
    SYNTAX       Unsigned64
    MAX-ACCESS   read-only
    STATUS       current
    DESCRIPTION
        "Cisco UCS adaptor:MenloEthErrorStats:correctableErrorsDeltaAvg
        managed object property"
    ::= { cucsAdaptorMenloEthErrorStatsEntry 6 }

cucsAdaptorMenloEthErrorStatsCorrectableErrorsDeltaMax OBJECT-TYPE
    SYNTAX       Unsigned64
    MAX-ACCESS   read-only
    STATUS       current
    DESCRIPTION
        "Cisco UCS adaptor:MenloEthErrorStats:correctableErrorsDeltaMax
        managed object property"
    ::= { cucsAdaptorMenloEthErrorStatsEntry 7 }

cucsAdaptorMenloEthErrorStatsCorrectableErrorsDeltaMin OBJECT-TYPE
    SYNTAX       Unsigned64
    MAX-ACCESS   read-only
    STATUS       current
    DESCRIPTION
        "Cisco UCS adaptor:MenloEthErrorStats:correctableErrorsDeltaMin
        managed object property"
    ::= { cucsAdaptorMenloEthErrorStatsEntry 8 }

cucsAdaptorMenloEthErrorStatsDropAcl OBJECT-TYPE
    SYNTAX       Unsigned64
    MAX-ACCESS   read-only
    STATUS       current
    DESCRIPTION
        "Cisco UCS adaptor:MenloEthErrorStats:dropAcl managed
        object property"
    ::= { cucsAdaptorMenloEthErrorStatsEntry 9 }

cucsAdaptorMenloEthErrorStatsDropAclDelta OBJECT-TYPE
    SYNTAX       Counter64
    MAX-ACCESS   read-only
    STATUS       current
    DESCRIPTION
        "Cisco UCS adaptor:MenloEthErrorStats:dropAclDelta
        managed object property"
    ::= { cucsAdaptorMenloEthErrorStatsEntry 10 }

cucsAdaptorMenloEthErrorStatsDropAclDeltaAvg OBJECT-TYPE
    SYNTAX       Unsigned64
    MAX-ACCESS   read-only
    STATUS       current
    DESCRIPTION
        "Cisco UCS adaptor:MenloEthErrorStats:dropAclDeltaAvg
        managed object property"
    ::= { cucsAdaptorMenloEthErrorStatsEntry 11 }

cucsAdaptorMenloEthErrorStatsDropAclDeltaMax OBJECT-TYPE
    SYNTAX       Unsigned64
    MAX-ACCESS   read-only
    STATUS       current
    DESCRIPTION
        "Cisco UCS adaptor:MenloEthErrorStats:dropAclDeltaMax
        managed object property"
    ::= { cucsAdaptorMenloEthErrorStatsEntry 12 }

cucsAdaptorMenloEthErrorStatsDropAclDeltaMin OBJECT-TYPE
    SYNTAX       Unsigned64
    MAX-ACCESS   read-only
    STATUS       current
    DESCRIPTION
        "Cisco UCS adaptor:MenloEthErrorStats:dropAclDeltaMin
        managed object property"
    ::= { cucsAdaptorMenloEthErrorStatsEntry 13 }

cucsAdaptorMenloEthErrorStatsIntervals OBJECT-TYPE
    SYNTAX       Gauge32
    MAX-ACCESS   read-only
    STATUS       current
    DESCRIPTION
        "Cisco UCS adaptor:MenloEthErrorStats:intervals
        managed object property"
    ::= { cucsAdaptorMenloEthErrorStatsEntry 14 }

cucsAdaptorMenloEthErrorStatsMenloEthIndex OBJECT-TYPE
    SYNTAX       CucsAdaptorMenloStatsIndex
    MAX-ACCESS   read-only
    STATUS       current
    DESCRIPTION
        "Cisco UCS adaptor:MenloEthErrorStats:menloEthIndex
        managed object property"
    ::= { cucsAdaptorMenloEthErrorStatsEntry 15 }

cucsAdaptorMenloEthErrorStatsPopErrors OBJECT-TYPE
    SYNTAX       Unsigned64
    MAX-ACCESS   read-only
    STATUS       current
    DESCRIPTION
        "Cisco UCS adaptor:MenloEthErrorStats:popErrors
        managed object property"
    ::= { cucsAdaptorMenloEthErrorStatsEntry 16 }

cucsAdaptorMenloEthErrorStatsPopErrorsDelta OBJECT-TYPE
    SYNTAX       Counter64
    MAX-ACCESS   read-only
    STATUS       current
    DESCRIPTION
        "Cisco UCS adaptor:MenloEthErrorStats:popErrorsDelta
        managed object property"
    ::= { cucsAdaptorMenloEthErrorStatsEntry 17 }

cucsAdaptorMenloEthErrorStatsPopErrorsDeltaAvg OBJECT-TYPE
    SYNTAX       Unsigned64
    MAX-ACCESS   read-only
    STATUS       current
    DESCRIPTION
        "Cisco UCS adaptor:MenloEthErrorStats:popErrorsDeltaAvg
        managed object property"
    ::= { cucsAdaptorMenloEthErrorStatsEntry 18 }

cucsAdaptorMenloEthErrorStatsPopErrorsDeltaMax OBJECT-TYPE
    SYNTAX       Unsigned64
    MAX-ACCESS   read-only
    STATUS       current
    DESCRIPTION
        "Cisco UCS adaptor:MenloEthErrorStats:popErrorsDeltaMax
        managed object property"
    ::= { cucsAdaptorMenloEthErrorStatsEntry 19 }

cucsAdaptorMenloEthErrorStatsPopErrorsDeltaMin OBJECT-TYPE
    SYNTAX       Unsigned64
    MAX-ACCESS   read-only
    STATUS       current
    DESCRIPTION
        "Cisco UCS adaptor:MenloEthErrorStats:popErrorsDeltaMin
        managed object property"
    ::= { cucsAdaptorMenloEthErrorStatsEntry 20 }

cucsAdaptorMenloEthErrorStatsPushErrors OBJECT-TYPE
    SYNTAX       Unsigned64
    MAX-ACCESS   read-only
    STATUS       current
    DESCRIPTION
        "Cisco UCS adaptor:MenloEthErrorStats:pushErrors
        managed object property"
    ::= { cucsAdaptorMenloEthErrorStatsEntry 21 }

cucsAdaptorMenloEthErrorStatsPushErrorsDelta OBJECT-TYPE
    SYNTAX       Counter64
    MAX-ACCESS   read-only
    STATUS       current
    DESCRIPTION
        "Cisco UCS adaptor:MenloEthErrorStats:pushErrorsDelta
        managed object property"
    ::= { cucsAdaptorMenloEthErrorStatsEntry 22 }

cucsAdaptorMenloEthErrorStatsPushErrorsDeltaAvg OBJECT-TYPE
    SYNTAX       Unsigned64
    MAX-ACCESS   read-only
    STATUS       current
    DESCRIPTION
        "Cisco UCS adaptor:MenloEthErrorStats:pushErrorsDeltaAvg
        managed object property"
    ::= { cucsAdaptorMenloEthErrorStatsEntry 23 }

cucsAdaptorMenloEthErrorStatsPushErrorsDeltaMax OBJECT-TYPE
    SYNTAX       Unsigned64
    MAX-ACCESS   read-only
    STATUS       current
    DESCRIPTION
        "Cisco UCS adaptor:MenloEthErrorStats:pushErrorsDeltaMax
        managed object property"
    ::= { cucsAdaptorMenloEthErrorStatsEntry 24 }

cucsAdaptorMenloEthErrorStatsPushErrorsDeltaMin OBJECT-TYPE
    SYNTAX       Unsigned64
    MAX-ACCESS   read-only
    STATUS       current
    DESCRIPTION
        "Cisco UCS adaptor:MenloEthErrorStats:pushErrorsDeltaMin
        managed object property"
    ::= { cucsAdaptorMenloEthErrorStatsEntry 25 }

cucsAdaptorMenloEthErrorStatsSuspect OBJECT-TYPE
    SYNTAX       TruthValue
    MAX-ACCESS   read-only
    STATUS       current
    DESCRIPTION
        "Cisco UCS adaptor:MenloEthErrorStats:suspect managed
        object property"
    ::= { cucsAdaptorMenloEthErrorStatsEntry 26 }

cucsAdaptorMenloEthErrorStatsThresholded OBJECT-TYPE
    SYNTAX       CucsAdaptorMenloEthErrorStatsThresholded
    MAX-ACCESS   read-only
    STATUS       current
    DESCRIPTION
        "Cisco UCS adaptor:MenloEthErrorStats:thresholded
        managed object property"
    ::= { cucsAdaptorMenloEthErrorStatsEntry 27 }

cucsAdaptorMenloEthErrorStatsTimeCollected OBJECT-TYPE
    SYNTAX       DateAndTime
    MAX-ACCESS   read-only
    STATUS       current
    DESCRIPTION
        "Cisco UCS adaptor:MenloEthErrorStats:timeCollected
        managed object property"
    ::= { cucsAdaptorMenloEthErrorStatsEntry 28 }

cucsAdaptorMenloEthErrorStatsUncorrectableErrors OBJECT-TYPE
    SYNTAX       Unsigned64
    MAX-ACCESS   read-only
    STATUS       current
    DESCRIPTION
        "Cisco UCS adaptor:MenloEthErrorStats:uncorrectableErrors
        managed object property"
    ::= { cucsAdaptorMenloEthErrorStatsEntry 29 }

cucsAdaptorMenloEthErrorStatsUncorrectableErrorsDelta OBJECT-TYPE
    SYNTAX       Counter64
    MAX-ACCESS   read-only
    STATUS       current
    DESCRIPTION
        "Cisco UCS adaptor:MenloEthErrorStats:uncorrectableErrorsDelta
        managed object property"
    ::= { cucsAdaptorMenloEthErrorStatsEntry 30 }

cucsAdaptorMenloEthErrorStatsUncorrectableErrorsDeltaAvg OBJECT-TYPE
    SYNTAX       Unsigned64
    MAX-ACCESS   read-only
    STATUS       current
    DESCRIPTION
        "Cisco UCS adaptor:MenloEthErrorStats:uncorrectableErrorsDeltaAvg
        managed object property"
    ::= { cucsAdaptorMenloEthErrorStatsEntry 31 }

cucsAdaptorMenloEthErrorStatsUncorrectableErrorsDeltaMax OBJECT-TYPE
    SYNTAX       Unsigned64
    MAX-ACCESS   read-only
    STATUS       current
    DESCRIPTION
        "Cisco UCS adaptor:MenloEthErrorStats:uncorrectableErrorsDeltaMax
        managed object property"
    ::= { cucsAdaptorMenloEthErrorStatsEntry 32 }

cucsAdaptorMenloEthErrorStatsUncorrectableErrorsDeltaMin OBJECT-TYPE
    SYNTAX       Unsigned64
    MAX-ACCESS   read-only
    STATUS       current
    DESCRIPTION
        "Cisco UCS adaptor:MenloEthErrorStats:uncorrectableErrorsDeltaMin
        managed object property"
    ::= { cucsAdaptorMenloEthErrorStatsEntry 33 }

cucsAdaptorMenloEthErrorStatsUpdate OBJECT-TYPE
    SYNTAX       Gauge32
    MAX-ACCESS   read-only
    STATUS       current
    DESCRIPTION
        "Cisco UCS adaptor:MenloEthErrorStats:update managed
        object property"
    ::= { cucsAdaptorMenloEthErrorStatsEntry 34 }

cucsAdaptorMenloEthErrorStatsHistTable OBJECT-TYPE
    SYNTAX           SEQUENCE OF CucsAdaptorMenloEthErrorStatsHistEntry
    MAX-ACCESS       not-accessible
    STATUS           current
    DESCRIPTION
        "Cisco UCS adaptor:MenloEthErrorStatsHist managed object table"
    ::= { cucsAdaptorObjects 60 }

cucsAdaptorMenloEthErrorStatsHistEntry OBJECT-TYPE
    SYNTAX           CucsAdaptorMenloEthErrorStatsHistEntry
    MAX-ACCESS       not-accessible
    STATUS           current
    DESCRIPTION
        "Entry for the cucsAdaptorMenloEthErrorStatsHistTable table."
    INDEX { cucsAdaptorMenloEthErrorStatsHistInstanceId }
    ::= { cucsAdaptorMenloEthErrorStatsHistTable 1 }

CucsAdaptorMenloEthErrorStatsHistEntry ::= SEQUENCE {
    cucsAdaptorMenloEthErrorStatsHistInstanceId                      CucsManagedObjectId,
    cucsAdaptorMenloEthErrorStatsHistDn                              CucsManagedObjectDn,
    cucsAdaptorMenloEthErrorStatsHistRn                              SnmpAdminString,
    cucsAdaptorMenloEthErrorStatsHistCorrectableErrors               Unsigned64,
    cucsAdaptorMenloEthErrorStatsHistCorrectableErrorsDelta          Unsigned64,
    cucsAdaptorMenloEthErrorStatsHistCorrectableErrorsDeltaAvg       Unsigned64,
    cucsAdaptorMenloEthErrorStatsHistCorrectableErrorsDeltaMax       Unsigned64,
    cucsAdaptorMenloEthErrorStatsHistCorrectableErrorsDeltaMin       Unsigned64,
    cucsAdaptorMenloEthErrorStatsHistDropAcl                         Unsigned64,
    cucsAdaptorMenloEthErrorStatsHistDropAclDelta                    Unsigned64,
    cucsAdaptorMenloEthErrorStatsHistDropAclDeltaAvg                 Unsigned64,
    cucsAdaptorMenloEthErrorStatsHistDropAclDeltaMax                 Unsigned64,
    cucsAdaptorMenloEthErrorStatsHistDropAclDeltaMin                 Unsigned64,
    cucsAdaptorMenloEthErrorStatsHistId                              Unsigned64,
    cucsAdaptorMenloEthErrorStatsHistMostRecent                      TruthValue,
    cucsAdaptorMenloEthErrorStatsHistPopErrors                       Unsigned64,
    cucsAdaptorMenloEthErrorStatsHistPopErrorsDelta                  Unsigned64,
    cucsAdaptorMenloEthErrorStatsHistPopErrorsDeltaAvg               Unsigned64,
    cucsAdaptorMenloEthErrorStatsHistPopErrorsDeltaMax               Unsigned64,
    cucsAdaptorMenloEthErrorStatsHistPopErrorsDeltaMin               Unsigned64,
    cucsAdaptorMenloEthErrorStatsHistPushErrors                      Unsigned64,
    cucsAdaptorMenloEthErrorStatsHistPushErrorsDelta                 Unsigned64,
    cucsAdaptorMenloEthErrorStatsHistPushErrorsDeltaAvg              Unsigned64,
    cucsAdaptorMenloEthErrorStatsHistPushErrorsDeltaMax              Unsigned64,
    cucsAdaptorMenloEthErrorStatsHistPushErrorsDeltaMin              Unsigned64,
    cucsAdaptorMenloEthErrorStatsHistSuspect                         TruthValue,
    cucsAdaptorMenloEthErrorStatsHistThresholded                     CucsAdaptorMenloEthErrorStatsHistThresholded,
    cucsAdaptorMenloEthErrorStatsHistTimeCollected                   DateAndTime,
    cucsAdaptorMenloEthErrorStatsHistUncorrectableErrors             Unsigned64,
    cucsAdaptorMenloEthErrorStatsHistUncorrectableErrorsDelta        Unsigned64,
    cucsAdaptorMenloEthErrorStatsHistUncorrectableErrorsDeltaAvg     Unsigned64,
    cucsAdaptorMenloEthErrorStatsHistUncorrectableErrorsDeltaMax     Unsigned64,
    cucsAdaptorMenloEthErrorStatsHistUncorrectableErrorsDeltaMin     Unsigned64
}

cucsAdaptorMenloEthErrorStatsHistInstanceId OBJECT-TYPE
    SYNTAX       CucsManagedObjectId
    MAX-ACCESS   not-accessible
    STATUS       current
    DESCRIPTION
        "Instance identifier of the managed object."
    ::= { cucsAdaptorMenloEthErrorStatsHistEntry 1 }

cucsAdaptorMenloEthErrorStatsHistDn OBJECT-TYPE
    SYNTAX       CucsManagedObjectDn
    MAX-ACCESS   read-only
    STATUS       current
    DESCRIPTION
        "Cisco UCS adaptor:MenloEthErrorStatsHist:dn managed
        object property"
    ::= { cucsAdaptorMenloEthErrorStatsHistEntry 2 }

cucsAdaptorMenloEthErrorStatsHistRn OBJECT-TYPE
    SYNTAX       SnmpAdminString
    MAX-ACCESS   read-only
    STATUS       current
    DESCRIPTION
        "Cisco UCS adaptor:MenloEthErrorStatsHist:rn managed
        object property"
    ::= { cucsAdaptorMenloEthErrorStatsHistEntry 3 }

cucsAdaptorMenloEthErrorStatsHistCorrectableErrors OBJECT-TYPE
    SYNTAX       Unsigned64
    MAX-ACCESS   read-only
    STATUS       current
    DESCRIPTION
        "Cisco UCS adaptor:MenloEthErrorStatsHist:correctableErrors
        managed object property"
    ::= { cucsAdaptorMenloEthErrorStatsHistEntry 4 }

cucsAdaptorMenloEthErrorStatsHistCorrectableErrorsDelta OBJECT-TYPE
    SYNTAX       Unsigned64
    MAX-ACCESS   read-only
    STATUS       current
    DESCRIPTION
        "Cisco UCS adaptor:MenloEthErrorStatsHist:correctableErrorsDelta
        managed object property"
    ::= { cucsAdaptorMenloEthErrorStatsHistEntry 5 }

cucsAdaptorMenloEthErrorStatsHistCorrectableErrorsDeltaAvg OBJECT-TYPE
    SYNTAX       Unsigned64
    MAX-ACCESS   read-only
    STATUS       current
    DESCRIPTION
        "Cisco UCS adaptor:MenloEthErrorStatsHist:correctableErrorsDeltaAv
        g managed object property"
    ::= { cucsAdaptorMenloEthErrorStatsHistEntry 6 }

cucsAdaptorMenloEthErrorStatsHistCorrectableErrorsDeltaMax OBJECT-TYPE
    SYNTAX       Unsigned64
    MAX-ACCESS   read-only
    STATUS       current
    DESCRIPTION
        "Cisco UCS adaptor:MenloEthErrorStatsHist:correctableErrorsDeltaMa
        x managed object property"
    ::= { cucsAdaptorMenloEthErrorStatsHistEntry 7 }

cucsAdaptorMenloEthErrorStatsHistCorrectableErrorsDeltaMin OBJECT-TYPE
    SYNTAX       Unsigned64
    MAX-ACCESS   read-only
    STATUS       current
    DESCRIPTION
        "Cisco UCS adaptor:MenloEthErrorStatsHist:correctableErrorsDeltaMi
        n managed object property"
    ::= { cucsAdaptorMenloEthErrorStatsHistEntry 8 }

cucsAdaptorMenloEthErrorStatsHistDropAcl OBJECT-TYPE
    SYNTAX       Unsigned64
    MAX-ACCESS   read-only
    STATUS       current
    DESCRIPTION
        "Cisco UCS adaptor:MenloEthErrorStatsHist:dropAcl
        managed object property"
    ::= { cucsAdaptorMenloEthErrorStatsHistEntry 9 }

cucsAdaptorMenloEthErrorStatsHistDropAclDelta OBJECT-TYPE
    SYNTAX       Unsigned64
    MAX-ACCESS   read-only
    STATUS       current
    DESCRIPTION
        "Cisco UCS adaptor:MenloEthErrorStatsHist:dropAclDelta
        managed object property"
    ::= { cucsAdaptorMenloEthErrorStatsHistEntry 10 }

cucsAdaptorMenloEthErrorStatsHistDropAclDeltaAvg OBJECT-TYPE
    SYNTAX       Unsigned64
    MAX-ACCESS   read-only
    STATUS       current
    DESCRIPTION
        "Cisco UCS adaptor:MenloEthErrorStatsHist:dropAclDeltaAvg
        managed object property"
    ::= { cucsAdaptorMenloEthErrorStatsHistEntry 11 }

cucsAdaptorMenloEthErrorStatsHistDropAclDeltaMax OBJECT-TYPE
    SYNTAX       Unsigned64
    MAX-ACCESS   read-only
    STATUS       current
    DESCRIPTION
        "Cisco UCS adaptor:MenloEthErrorStatsHist:dropAclDeltaMax
        managed object property"
    ::= { cucsAdaptorMenloEthErrorStatsHistEntry 12 }

cucsAdaptorMenloEthErrorStatsHistDropAclDeltaMin OBJECT-TYPE
    SYNTAX       Unsigned64
    MAX-ACCESS   read-only
    STATUS       current
    DESCRIPTION
        "Cisco UCS adaptor:MenloEthErrorStatsHist:dropAclDeltaMin
        managed object property"
    ::= { cucsAdaptorMenloEthErrorStatsHistEntry 13 }

cucsAdaptorMenloEthErrorStatsHistId OBJECT-TYPE
    SYNTAX       Unsigned64
    MAX-ACCESS   read-only
    STATUS       current
    DESCRIPTION
        "Cisco UCS adaptor:MenloEthErrorStatsHist:id managed
        object property"
    ::= { cucsAdaptorMenloEthErrorStatsHistEntry 14 }

cucsAdaptorMenloEthErrorStatsHistMostRecent OBJECT-TYPE
    SYNTAX       TruthValue
    MAX-ACCESS   read-only
    STATUS       current
    DESCRIPTION
        "Cisco UCS adaptor:MenloEthErrorStatsHist:mostRecent
        managed object property"
    ::= { cucsAdaptorMenloEthErrorStatsHistEntry 15 }

cucsAdaptorMenloEthErrorStatsHistPopErrors OBJECT-TYPE
    SYNTAX       Unsigned64
    MAX-ACCESS   read-only
    STATUS       current
    DESCRIPTION
        "Cisco UCS adaptor:MenloEthErrorStatsHist:popErrors
        managed object property"
    ::= { cucsAdaptorMenloEthErrorStatsHistEntry 16 }

cucsAdaptorMenloEthErrorStatsHistPopErrorsDelta OBJECT-TYPE
    SYNTAX       Unsigned64
    MAX-ACCESS   read-only
    STATUS       current
    DESCRIPTION
        "Cisco UCS adaptor:MenloEthErrorStatsHist:popErrorsDelta
        managed object property"
    ::= { cucsAdaptorMenloEthErrorStatsHistEntry 17 }

cucsAdaptorMenloEthErrorStatsHistPopErrorsDeltaAvg OBJECT-TYPE
    SYNTAX       Unsigned64
    MAX-ACCESS   read-only
    STATUS       current
    DESCRIPTION
        "Cisco UCS adaptor:MenloEthErrorStatsHist:popErrorsDeltaAvg
        managed object property"
    ::= { cucsAdaptorMenloEthErrorStatsHistEntry 18 }

cucsAdaptorMenloEthErrorStatsHistPopErrorsDeltaMax OBJECT-TYPE
    SYNTAX       Unsigned64
    MAX-ACCESS   read-only
    STATUS       current
    DESCRIPTION
        "Cisco UCS adaptor:MenloEthErrorStatsHist:popErrorsDeltaMax
        managed object property"
    ::= { cucsAdaptorMenloEthErrorStatsHistEntry 19 }

cucsAdaptorMenloEthErrorStatsHistPopErrorsDeltaMin OBJECT-TYPE
    SYNTAX       Unsigned64
    MAX-ACCESS   read-only
    STATUS       current
    DESCRIPTION
        "Cisco UCS adaptor:MenloEthErrorStatsHist:popErrorsDeltaMin
        managed object property"
    ::= { cucsAdaptorMenloEthErrorStatsHistEntry 20 }

cucsAdaptorMenloEthErrorStatsHistPushErrors OBJECT-TYPE
    SYNTAX       Unsigned64
    MAX-ACCESS   read-only
    STATUS       current
    DESCRIPTION
        "Cisco UCS adaptor:MenloEthErrorStatsHist:pushErrors
        managed object property"
    ::= { cucsAdaptorMenloEthErrorStatsHistEntry 21 }

cucsAdaptorMenloEthErrorStatsHistPushErrorsDelta OBJECT-TYPE
    SYNTAX       Unsigned64
    MAX-ACCESS   read-only
    STATUS       current
    DESCRIPTION
        "Cisco UCS adaptor:MenloEthErrorStatsHist:pushErrorsDelta
        managed object property"
    ::= { cucsAdaptorMenloEthErrorStatsHistEntry 22 }

cucsAdaptorMenloEthErrorStatsHistPushErrorsDeltaAvg OBJECT-TYPE
    SYNTAX       Unsigned64
    MAX-ACCESS   read-only
    STATUS       current
    DESCRIPTION
        "Cisco UCS adaptor:MenloEthErrorStatsHist:pushErrorsDeltaAvg
        managed object property"
    ::= { cucsAdaptorMenloEthErrorStatsHistEntry 23 }

cucsAdaptorMenloEthErrorStatsHistPushErrorsDeltaMax OBJECT-TYPE
    SYNTAX       Unsigned64
    MAX-ACCESS   read-only
    STATUS       current
    DESCRIPTION
        "Cisco UCS adaptor:MenloEthErrorStatsHist:pushErrorsDeltaMax
        managed object property"
    ::= { cucsAdaptorMenloEthErrorStatsHistEntry 24 }

cucsAdaptorMenloEthErrorStatsHistPushErrorsDeltaMin OBJECT-TYPE
    SYNTAX       Unsigned64
    MAX-ACCESS   read-only
    STATUS       current
    DESCRIPTION
        "Cisco UCS adaptor:MenloEthErrorStatsHist:pushErrorsDeltaMin
        managed object property"
    ::= { cucsAdaptorMenloEthErrorStatsHistEntry 25 }

cucsAdaptorMenloEthErrorStatsHistSuspect OBJECT-TYPE
    SYNTAX       TruthValue
    MAX-ACCESS   read-only
    STATUS       current
    DESCRIPTION
        "Cisco UCS adaptor:MenloEthErrorStatsHist:suspect
        managed object property"
    ::= { cucsAdaptorMenloEthErrorStatsHistEntry 26 }

cucsAdaptorMenloEthErrorStatsHistThresholded OBJECT-TYPE
    SYNTAX       CucsAdaptorMenloEthErrorStatsHistThresholded
    MAX-ACCESS   read-only
    STATUS       current
    DESCRIPTION
        "Cisco UCS adaptor:MenloEthErrorStatsHist:thresholded
        managed object property"
    ::= { cucsAdaptorMenloEthErrorStatsHistEntry 27 }

cucsAdaptorMenloEthErrorStatsHistTimeCollected OBJECT-TYPE
    SYNTAX       DateAndTime
    MAX-ACCESS   read-only
    STATUS       current
    DESCRIPTION
        "Cisco UCS adaptor:MenloEthErrorStatsHist:timeCollected
        managed object property"
    ::= { cucsAdaptorMenloEthErrorStatsHistEntry 28 }

cucsAdaptorMenloEthErrorStatsHistUncorrectableErrors OBJECT-TYPE
    SYNTAX       Unsigned64
    MAX-ACCESS   read-only
    STATUS       current
    DESCRIPTION
        "Cisco UCS adaptor:MenloEthErrorStatsHist:uncorrectableErrors
        managed object property"
    ::= { cucsAdaptorMenloEthErrorStatsHistEntry 29 }

cucsAdaptorMenloEthErrorStatsHistUncorrectableErrorsDelta OBJECT-TYPE
    SYNTAX       Unsigned64
    MAX-ACCESS   read-only
    STATUS       current
    DESCRIPTION
        "Cisco UCS adaptor:MenloEthErrorStatsHist:uncorrectableErrorsDelta
         managed object property"
    ::= { cucsAdaptorMenloEthErrorStatsHistEntry 30 }

cucsAdaptorMenloEthErrorStatsHistUncorrectableErrorsDeltaAvg OBJECT-TYPE
    SYNTAX       Unsigned64
    MAX-ACCESS   read-only
    STATUS       current
    DESCRIPTION
        "Cisco UCS adaptor:MenloEthErrorStatsHist:uncorrectableErrorsDelta
        Avg managed object property"
    ::= { cucsAdaptorMenloEthErrorStatsHistEntry 31 }

cucsAdaptorMenloEthErrorStatsHistUncorrectableErrorsDeltaMax OBJECT-TYPE
    SYNTAX       Unsigned64
    MAX-ACCESS   read-only
    STATUS       current
    DESCRIPTION
        "Cisco UCS adaptor:MenloEthErrorStatsHist:uncorrectableErrorsDelta
        Max managed object property"
    ::= { cucsAdaptorMenloEthErrorStatsHistEntry 32 }

cucsAdaptorMenloEthErrorStatsHistUncorrectableErrorsDeltaMin OBJECT-TYPE
    SYNTAX       Unsigned64
    MAX-ACCESS   read-only
    STATUS       current
    DESCRIPTION
        "Cisco UCS adaptor:MenloEthErrorStatsHist:uncorrectableErrorsDelta
        Min managed object property"
    ::= { cucsAdaptorMenloEthErrorStatsHistEntry 33 }

cucsAdaptorMenloEthStatsTable OBJECT-TYPE
    SYNTAX           SEQUENCE OF CucsAdaptorMenloEthStatsEntry
    MAX-ACCESS       not-accessible
    STATUS           current
    DESCRIPTION
        "Cisco UCS adaptor:MenloEthStats managed object table"
    ::= { cucsAdaptorObjects 61 }

cucsAdaptorMenloEthStatsEntry OBJECT-TYPE
    SYNTAX           CucsAdaptorMenloEthStatsEntry
    MAX-ACCESS       not-accessible
    STATUS           current
    DESCRIPTION
        "Entry for the cucsAdaptorMenloEthStatsTable table."
    INDEX { cucsAdaptorMenloEthStatsInstanceId }
    ::= { cucsAdaptorMenloEthStatsTable 1 }

CucsAdaptorMenloEthStatsEntry ::= SEQUENCE {
    cucsAdaptorMenloEthStatsInstanceId                               CucsManagedObjectId,
    cucsAdaptorMenloEthStatsDn                                       CucsManagedObjectDn,
    cucsAdaptorMenloEthStatsRn                                       SnmpAdminString,
    cucsAdaptorMenloEthStatsDropOverrun                              Unsigned64,
    cucsAdaptorMenloEthStatsDropOverrunDelta                         Counter64,
    cucsAdaptorMenloEthStatsDropOverrunDeltaAvg                      Unsigned64,
    cucsAdaptorMenloEthStatsDropOverrunDeltaMax                      Unsigned64,
    cucsAdaptorMenloEthStatsDropOverrunDeltaMin                      Unsigned64,
    cucsAdaptorMenloEthStatsDropRunt                                 Unsigned64,
    cucsAdaptorMenloEthStatsDropRuntDelta                            Counter64,
    cucsAdaptorMenloEthStatsDropRuntDeltaAvg                         Unsigned64,
    cucsAdaptorMenloEthStatsDropRuntDeltaMax                         Unsigned64,
    cucsAdaptorMenloEthStatsDropRuntDeltaMin                         Unsigned64,
    cucsAdaptorMenloEthStatsIntervals                                Gauge32,
    cucsAdaptorMenloEthStatsMenloEthIndex                            CucsAdaptorMenloStatsIndex,
    cucsAdaptorMenloEthStatsSuspect                                  TruthValue,
    cucsAdaptorMenloEthStatsThresholded                              CucsAdaptorMenloEthStatsThresholded,
    cucsAdaptorMenloEthStatsTimeCollected                            DateAndTime,
    cucsAdaptorMenloEthStatsTruncateOverrun                          Unsigned64,
    cucsAdaptorMenloEthStatsTruncateOverrunDelta                     Counter64,
    cucsAdaptorMenloEthStatsTruncateOverrunDeltaAvg                  Unsigned64,
    cucsAdaptorMenloEthStatsTruncateOverrunDeltaMax                  Unsigned64,
    cucsAdaptorMenloEthStatsTruncateOverrunDeltaMin                  Unsigned64,
    cucsAdaptorMenloEthStatsUpdate                                   Gauge32
}

cucsAdaptorMenloEthStatsInstanceId OBJECT-TYPE
    SYNTAX       CucsManagedObjectId
    MAX-ACCESS   not-accessible
    STATUS       current
    DESCRIPTION
        "Instance identifier of the managed object."
    ::= { cucsAdaptorMenloEthStatsEntry 1 }

cucsAdaptorMenloEthStatsDn OBJECT-TYPE
    SYNTAX       CucsManagedObjectDn
    MAX-ACCESS   read-only
    STATUS       current
    DESCRIPTION
        "Cisco UCS adaptor:MenloEthStats:dn managed object property"
    ::= { cucsAdaptorMenloEthStatsEntry 2 }

cucsAdaptorMenloEthStatsRn OBJECT-TYPE
    SYNTAX       SnmpAdminString
    MAX-ACCESS   read-only
    STATUS       current
    DESCRIPTION
        "Cisco UCS adaptor:MenloEthStats:rn managed object property"
    ::= { cucsAdaptorMenloEthStatsEntry 3 }

cucsAdaptorMenloEthStatsDropOverrun OBJECT-TYPE
    SYNTAX       Unsigned64
    MAX-ACCESS   read-only
    STATUS       current
    DESCRIPTION
        "Cisco UCS adaptor:MenloEthStats:dropOverrun managed
        object property"
    ::= { cucsAdaptorMenloEthStatsEntry 4 }

cucsAdaptorMenloEthStatsDropOverrunDelta OBJECT-TYPE
    SYNTAX       Counter64
    MAX-ACCESS   read-only
    STATUS       current
    DESCRIPTION
        "Cisco UCS adaptor:MenloEthStats:dropOverrunDelta
        managed object property"
    ::= { cucsAdaptorMenloEthStatsEntry 5 }

cucsAdaptorMenloEthStatsDropOverrunDeltaAvg OBJECT-TYPE
    SYNTAX       Unsigned64
    MAX-ACCESS   read-only
    STATUS       current
    DESCRIPTION
        "Cisco UCS adaptor:MenloEthStats:dropOverrunDeltaAvg
        managed object property"
    ::= { cucsAdaptorMenloEthStatsEntry 6 }

cucsAdaptorMenloEthStatsDropOverrunDeltaMax OBJECT-TYPE
    SYNTAX       Unsigned64
    MAX-ACCESS   read-only
    STATUS       current
    DESCRIPTION
        "Cisco UCS adaptor:MenloEthStats:dropOverrunDeltaMax
        managed object property"
    ::= { cucsAdaptorMenloEthStatsEntry 7 }

cucsAdaptorMenloEthStatsDropOverrunDeltaMin OBJECT-TYPE
    SYNTAX       Unsigned64
    MAX-ACCESS   read-only
    STATUS       current
    DESCRIPTION
        "Cisco UCS adaptor:MenloEthStats:dropOverrunDeltaMin
        managed object property"
    ::= { cucsAdaptorMenloEthStatsEntry 8 }

cucsAdaptorMenloEthStatsDropRunt OBJECT-TYPE
    SYNTAX       Unsigned64
    MAX-ACCESS   read-only
    STATUS       current
    DESCRIPTION
        "Cisco UCS adaptor:MenloEthStats:dropRunt managed object property"
    ::= { cucsAdaptorMenloEthStatsEntry 9 }

cucsAdaptorMenloEthStatsDropRuntDelta OBJECT-TYPE
    SYNTAX       Counter64
    MAX-ACCESS   read-only
    STATUS       current
    DESCRIPTION
        "Cisco UCS adaptor:MenloEthStats:dropRuntDelta
        managed object property"
    ::= { cucsAdaptorMenloEthStatsEntry 10 }

cucsAdaptorMenloEthStatsDropRuntDeltaAvg OBJECT-TYPE
    SYNTAX       Unsigned64
    MAX-ACCESS   read-only
    STATUS       current
    DESCRIPTION
        "Cisco UCS adaptor:MenloEthStats:dropRuntDeltaAvg
        managed object property"
    ::= { cucsAdaptorMenloEthStatsEntry 11 }

cucsAdaptorMenloEthStatsDropRuntDeltaMax OBJECT-TYPE
    SYNTAX       Unsigned64
    MAX-ACCESS   read-only
    STATUS       current
    DESCRIPTION
        "Cisco UCS adaptor:MenloEthStats:dropRuntDeltaMax
        managed object property"
    ::= { cucsAdaptorMenloEthStatsEntry 12 }

cucsAdaptorMenloEthStatsDropRuntDeltaMin OBJECT-TYPE
    SYNTAX       Unsigned64
    MAX-ACCESS   read-only
    STATUS       current
    DESCRIPTION
        "Cisco UCS adaptor:MenloEthStats:dropRuntDeltaMin
        managed object property"
    ::= { cucsAdaptorMenloEthStatsEntry 13 }

cucsAdaptorMenloEthStatsIntervals OBJECT-TYPE
    SYNTAX       Gauge32
    MAX-ACCESS   read-only
    STATUS       current
    DESCRIPTION
        "Cisco UCS adaptor:MenloEthStats:intervals managed
        object property"
    ::= { cucsAdaptorMenloEthStatsEntry 14 }

cucsAdaptorMenloEthStatsMenloEthIndex OBJECT-TYPE
    SYNTAX       CucsAdaptorMenloStatsIndex
    MAX-ACCESS   read-only
    STATUS       current
    DESCRIPTION
        "Cisco UCS adaptor:MenloEthStats:menloEthIndex
        managed object property"
    ::= { cucsAdaptorMenloEthStatsEntry 15 }

cucsAdaptorMenloEthStatsSuspect OBJECT-TYPE
    SYNTAX       TruthValue
    MAX-ACCESS   read-only
    STATUS       current
    DESCRIPTION
        "Cisco UCS adaptor:MenloEthStats:suspect managed object property"
    ::= { cucsAdaptorMenloEthStatsEntry 16 }

cucsAdaptorMenloEthStatsThresholded OBJECT-TYPE
    SYNTAX       CucsAdaptorMenloEthStatsThresholded
    MAX-ACCESS   read-only
    STATUS       current
    DESCRIPTION
        "Cisco UCS adaptor:MenloEthStats:thresholded managed
        object property"
    ::= { cucsAdaptorMenloEthStatsEntry 17 }

cucsAdaptorMenloEthStatsTimeCollected OBJECT-TYPE
    SYNTAX       DateAndTime
    MAX-ACCESS   read-only
    STATUS       current
    DESCRIPTION
        "Cisco UCS adaptor:MenloEthStats:timeCollected
        managed object property"
    ::= { cucsAdaptorMenloEthStatsEntry 18 }

cucsAdaptorMenloEthStatsTruncateOverrun OBJECT-TYPE
    SYNTAX       Unsigned64
    MAX-ACCESS   read-only
    STATUS       current
    DESCRIPTION
        "Cisco UCS adaptor:MenloEthStats:truncateOverrun
        managed object property"
    ::= { cucsAdaptorMenloEthStatsEntry 19 }

cucsAdaptorMenloEthStatsTruncateOverrunDelta OBJECT-TYPE
    SYNTAX       Counter64
    MAX-ACCESS   read-only
    STATUS       current
    DESCRIPTION
        "Cisco UCS adaptor:MenloEthStats:truncateOverrunDelta
        managed object property"
    ::= { cucsAdaptorMenloEthStatsEntry 20 }

cucsAdaptorMenloEthStatsTruncateOverrunDeltaAvg OBJECT-TYPE
    SYNTAX       Unsigned64
    MAX-ACCESS   read-only
    STATUS       current
    DESCRIPTION
        "Cisco UCS adaptor:MenloEthStats:truncateOverrunDeltaAvg
        managed object property"
    ::= { cucsAdaptorMenloEthStatsEntry 21 }

cucsAdaptorMenloEthStatsTruncateOverrunDeltaMax OBJECT-TYPE
    SYNTAX       Unsigned64
    MAX-ACCESS   read-only
    STATUS       current
    DESCRIPTION
        "Cisco UCS adaptor:MenloEthStats:truncateOverrunDeltaMax
        managed object property"
    ::= { cucsAdaptorMenloEthStatsEntry 22 }

cucsAdaptorMenloEthStatsTruncateOverrunDeltaMin OBJECT-TYPE
    SYNTAX       Unsigned64
    MAX-ACCESS   read-only
    STATUS       current
    DESCRIPTION
        "Cisco UCS adaptor:MenloEthStats:truncateOverrunDeltaMin
        managed object property"
    ::= { cucsAdaptorMenloEthStatsEntry 23 }

cucsAdaptorMenloEthStatsUpdate OBJECT-TYPE
    SYNTAX       Gauge32
    MAX-ACCESS   read-only
    STATUS       current
    DESCRIPTION
        "Cisco UCS adaptor:MenloEthStats:update managed object property"
    ::= { cucsAdaptorMenloEthStatsEntry 24 }

cucsAdaptorMenloEthStatsHistTable OBJECT-TYPE
    SYNTAX           SEQUENCE OF CucsAdaptorMenloEthStatsHistEntry
    MAX-ACCESS       not-accessible
    STATUS           current
    DESCRIPTION
        "Cisco UCS adaptor:MenloEthStatsHist managed object table"
    ::= { cucsAdaptorObjects 62 }

cucsAdaptorMenloEthStatsHistEntry OBJECT-TYPE
    SYNTAX           CucsAdaptorMenloEthStatsHistEntry
    MAX-ACCESS       not-accessible
    STATUS           current
    DESCRIPTION
        "Entry for the cucsAdaptorMenloEthStatsHistTable table."
    INDEX { cucsAdaptorMenloEthStatsHistInstanceId }
    ::= { cucsAdaptorMenloEthStatsHistTable 1 }

CucsAdaptorMenloEthStatsHistEntry ::= SEQUENCE {
    cucsAdaptorMenloEthStatsHistInstanceId                           CucsManagedObjectId,
    cucsAdaptorMenloEthStatsHistDn                                   CucsManagedObjectDn,
    cucsAdaptorMenloEthStatsHistRn                                   SnmpAdminString,
    cucsAdaptorMenloEthStatsHistDropOverrun                          Unsigned64,
    cucsAdaptorMenloEthStatsHistDropOverrunDelta                     Unsigned64,
    cucsAdaptorMenloEthStatsHistDropOverrunDeltaAvg                  Unsigned64,
    cucsAdaptorMenloEthStatsHistDropOverrunDeltaMax                  Unsigned64,
    cucsAdaptorMenloEthStatsHistDropOverrunDeltaMin                  Unsigned64,
    cucsAdaptorMenloEthStatsHistDropRunt                             Unsigned64,
    cucsAdaptorMenloEthStatsHistDropRuntDelta                        Unsigned64,
    cucsAdaptorMenloEthStatsHistDropRuntDeltaAvg                     Unsigned64,
    cucsAdaptorMenloEthStatsHistDropRuntDeltaMax                     Unsigned64,
    cucsAdaptorMenloEthStatsHistDropRuntDeltaMin                     Unsigned64,
    cucsAdaptorMenloEthStatsHistId                                   Unsigned64,
    cucsAdaptorMenloEthStatsHistMostRecent                           TruthValue,
    cucsAdaptorMenloEthStatsHistSuspect                              TruthValue,
    cucsAdaptorMenloEthStatsHistThresholded                          CucsAdaptorMenloEthStatsHistThresholded,
    cucsAdaptorMenloEthStatsHistTimeCollected                        DateAndTime,
    cucsAdaptorMenloEthStatsHistTruncateOverrun                      Unsigned64,
    cucsAdaptorMenloEthStatsHistTruncateOverrunDelta                 Unsigned64,
    cucsAdaptorMenloEthStatsHistTruncateOverrunDeltaAvg              Unsigned64,
    cucsAdaptorMenloEthStatsHistTruncateOverrunDeltaMax              Unsigned64,
    cucsAdaptorMenloEthStatsHistTruncateOverrunDeltaMin              Unsigned64
}

cucsAdaptorMenloEthStatsHistInstanceId OBJECT-TYPE
    SYNTAX       CucsManagedObjectId
    MAX-ACCESS   not-accessible
    STATUS       current
    DESCRIPTION
        "Instance identifier of the managed object."
    ::= { cucsAdaptorMenloEthStatsHistEntry 1 }

cucsAdaptorMenloEthStatsHistDn OBJECT-TYPE
    SYNTAX       CucsManagedObjectDn
    MAX-ACCESS   read-only
    STATUS       current
    DESCRIPTION
        "Cisco UCS adaptor:MenloEthStatsHist:dn managed object property"
    ::= { cucsAdaptorMenloEthStatsHistEntry 2 }

cucsAdaptorMenloEthStatsHistRn OBJECT-TYPE
    SYNTAX       SnmpAdminString
    MAX-ACCESS   read-only
    STATUS       current
    DESCRIPTION
        "Cisco UCS adaptor:MenloEthStatsHist:rn managed object property"
    ::= { cucsAdaptorMenloEthStatsHistEntry 3 }

cucsAdaptorMenloEthStatsHistDropOverrun OBJECT-TYPE
    SYNTAX       Unsigned64
    MAX-ACCESS   read-only
    STATUS       current
    DESCRIPTION
        "Cisco UCS adaptor:MenloEthStatsHist:dropOverrun
        managed object property"
    ::= { cucsAdaptorMenloEthStatsHistEntry 4 }

cucsAdaptorMenloEthStatsHistDropOverrunDelta OBJECT-TYPE
    SYNTAX       Unsigned64
    MAX-ACCESS   read-only
    STATUS       current
    DESCRIPTION
        "Cisco UCS adaptor:MenloEthStatsHist:dropOverrunDelta
        managed object property"
    ::= { cucsAdaptorMenloEthStatsHistEntry 5 }

cucsAdaptorMenloEthStatsHistDropOverrunDeltaAvg OBJECT-TYPE
    SYNTAX       Unsigned64
    MAX-ACCESS   read-only
    STATUS       current
    DESCRIPTION
        "Cisco UCS adaptor:MenloEthStatsHist:dropOverrunDeltaAvg
        managed object property"
    ::= { cucsAdaptorMenloEthStatsHistEntry 6 }

cucsAdaptorMenloEthStatsHistDropOverrunDeltaMax OBJECT-TYPE
    SYNTAX       Unsigned64
    MAX-ACCESS   read-only
    STATUS       current
    DESCRIPTION
        "Cisco UCS adaptor:MenloEthStatsHist:dropOverrunDeltaMax
        managed object property"
    ::= { cucsAdaptorMenloEthStatsHistEntry 7 }

cucsAdaptorMenloEthStatsHistDropOverrunDeltaMin OBJECT-TYPE
    SYNTAX       Unsigned64
    MAX-ACCESS   read-only
    STATUS       current
    DESCRIPTION
        "Cisco UCS adaptor:MenloEthStatsHist:dropOverrunDeltaMin
        managed object property"
    ::= { cucsAdaptorMenloEthStatsHistEntry 8 }

cucsAdaptorMenloEthStatsHistDropRunt OBJECT-TYPE
    SYNTAX       Unsigned64
    MAX-ACCESS   read-only
    STATUS       current
    DESCRIPTION
        "Cisco UCS adaptor:MenloEthStatsHist:dropRunt managed
        object property"
    ::= { cucsAdaptorMenloEthStatsHistEntry 9 }

cucsAdaptorMenloEthStatsHistDropRuntDelta OBJECT-TYPE
    SYNTAX       Unsigned64
    MAX-ACCESS   read-only
    STATUS       current
    DESCRIPTION
        "Cisco UCS adaptor:MenloEthStatsHist:dropRuntDelta
        managed object property"
    ::= { cucsAdaptorMenloEthStatsHistEntry 10 }

cucsAdaptorMenloEthStatsHistDropRuntDeltaAvg OBJECT-TYPE
    SYNTAX       Unsigned64
    MAX-ACCESS   read-only
    STATUS       current
    DESCRIPTION
        "Cisco UCS adaptor:MenloEthStatsHist:dropRuntDeltaAvg
        managed object property"
    ::= { cucsAdaptorMenloEthStatsHistEntry 11 }

cucsAdaptorMenloEthStatsHistDropRuntDeltaMax OBJECT-TYPE
    SYNTAX       Unsigned64
    MAX-ACCESS   read-only
    STATUS       current
    DESCRIPTION
        "Cisco UCS adaptor:MenloEthStatsHist:dropRuntDeltaMax
        managed object property"
    ::= { cucsAdaptorMenloEthStatsHistEntry 12 }

cucsAdaptorMenloEthStatsHistDropRuntDeltaMin OBJECT-TYPE
    SYNTAX       Unsigned64
    MAX-ACCESS   read-only
    STATUS       current
    DESCRIPTION
        "Cisco UCS adaptor:MenloEthStatsHist:dropRuntDeltaMin
        managed object property"
    ::= { cucsAdaptorMenloEthStatsHistEntry 13 }

cucsAdaptorMenloEthStatsHistId OBJECT-TYPE
    SYNTAX       Unsigned64
    MAX-ACCESS   read-only
    STATUS       current
    DESCRIPTION
        "Cisco UCS adaptor:MenloEthStatsHist:id managed object property"
    ::= { cucsAdaptorMenloEthStatsHistEntry 14 }

cucsAdaptorMenloEthStatsHistMostRecent OBJECT-TYPE
    SYNTAX       TruthValue
    MAX-ACCESS   read-only
    STATUS       current
    DESCRIPTION
        "Cisco UCS adaptor:MenloEthStatsHist:mostRecent
        managed object property"
    ::= { cucsAdaptorMenloEthStatsHistEntry 15 }

cucsAdaptorMenloEthStatsHistSuspect OBJECT-TYPE
    SYNTAX       TruthValue
    MAX-ACCESS   read-only
    STATUS       current
    DESCRIPTION
        "Cisco UCS adaptor:MenloEthStatsHist:suspect managed
        object property"
    ::= { cucsAdaptorMenloEthStatsHistEntry 16 }

cucsAdaptorMenloEthStatsHistThresholded OBJECT-TYPE
    SYNTAX       CucsAdaptorMenloEthStatsHistThresholded
    MAX-ACCESS   read-only
    STATUS       current
    DESCRIPTION
        "Cisco UCS adaptor:MenloEthStatsHist:thresholded
        managed object property"
    ::= { cucsAdaptorMenloEthStatsHistEntry 17 }

cucsAdaptorMenloEthStatsHistTimeCollected OBJECT-TYPE
    SYNTAX       DateAndTime
    MAX-ACCESS   read-only
    STATUS       current
    DESCRIPTION
        "Cisco UCS adaptor:MenloEthStatsHist:timeCollected
        managed object property"
    ::= { cucsAdaptorMenloEthStatsHistEntry 18 }

cucsAdaptorMenloEthStatsHistTruncateOverrun OBJECT-TYPE
    SYNTAX       Unsigned64
    MAX-ACCESS   read-only
    STATUS       current
    DESCRIPTION
        "Cisco UCS adaptor:MenloEthStatsHist:truncateOverrun
        managed object property"
    ::= { cucsAdaptorMenloEthStatsHistEntry 19 }

cucsAdaptorMenloEthStatsHistTruncateOverrunDelta OBJECT-TYPE
    SYNTAX       Unsigned64
    MAX-ACCESS   read-only
    STATUS       current
    DESCRIPTION
        "Cisco UCS adaptor:MenloEthStatsHist:truncateOverrunDelta
        managed object property"
    ::= { cucsAdaptorMenloEthStatsHistEntry 20 }

cucsAdaptorMenloEthStatsHistTruncateOverrunDeltaAvg OBJECT-TYPE
    SYNTAX       Unsigned64
    MAX-ACCESS   read-only
    STATUS       current
    DESCRIPTION
        "Cisco UCS adaptor:MenloEthStatsHist:truncateOverrunDeltaAvg
        managed object property"
    ::= { cucsAdaptorMenloEthStatsHistEntry 21 }

cucsAdaptorMenloEthStatsHistTruncateOverrunDeltaMax OBJECT-TYPE
    SYNTAX       Unsigned64
    MAX-ACCESS   read-only
    STATUS       current
    DESCRIPTION
        "Cisco UCS adaptor:MenloEthStatsHist:truncateOverrunDeltaMax
        managed object property"
    ::= { cucsAdaptorMenloEthStatsHistEntry 22 }

cucsAdaptorMenloEthStatsHistTruncateOverrunDeltaMin OBJECT-TYPE
    SYNTAX       Unsigned64
    MAX-ACCESS   read-only
    STATUS       current
    DESCRIPTION
        "Cisco UCS adaptor:MenloEthStatsHist:truncateOverrunDeltaMin
        managed object property"
    ::= { cucsAdaptorMenloEthStatsHistEntry 23 }

cucsAdaptorMenloFcErrorStatsTable OBJECT-TYPE
    SYNTAX           SEQUENCE OF CucsAdaptorMenloFcErrorStatsEntry
    MAX-ACCESS       not-accessible
    STATUS           current
    DESCRIPTION
        "Cisco UCS adaptor:MenloFcErrorStats managed object table"
    ::= { cucsAdaptorObjects 63 }

cucsAdaptorMenloFcErrorStatsEntry OBJECT-TYPE
    SYNTAX           CucsAdaptorMenloFcErrorStatsEntry
    MAX-ACCESS       not-accessible
    STATUS           current
    DESCRIPTION
        "Entry for the cucsAdaptorMenloFcErrorStatsTable table."
    INDEX { cucsAdaptorMenloFcErrorStatsInstanceId }
    ::= { cucsAdaptorMenloFcErrorStatsTable 1 }

CucsAdaptorMenloFcErrorStatsEntry ::= SEQUENCE {
    cucsAdaptorMenloFcErrorStatsInstanceId                           CucsManagedObjectId,
    cucsAdaptorMenloFcErrorStatsDn                                   CucsManagedObjectDn,
    cucsAdaptorMenloFcErrorStatsRn                                   SnmpAdminString,
    cucsAdaptorMenloFcErrorStatsCorrectableErrors                    Unsigned64,
    cucsAdaptorMenloFcErrorStatsCorrectableErrorsDelta               Counter64,
    cucsAdaptorMenloFcErrorStatsCorrectableErrorsDeltaAvg            Unsigned64,
    cucsAdaptorMenloFcErrorStatsCorrectableErrorsDeltaMax            Unsigned64,
    cucsAdaptorMenloFcErrorStatsCorrectableErrorsDeltaMin            Unsigned64,
    cucsAdaptorMenloFcErrorStatsIntervals                            Gauge32,
    cucsAdaptorMenloFcErrorStatsMenloFcIndex                         CucsAdaptorMenloStatsIndex,
    cucsAdaptorMenloFcErrorStatsPopErrors                            Unsigned64,
    cucsAdaptorMenloFcErrorStatsPopErrorsDelta                       Counter64,
    cucsAdaptorMenloFcErrorStatsPopErrorsDeltaAvg                    Unsigned64,
    cucsAdaptorMenloFcErrorStatsPopErrorsDeltaMax                    Unsigned64,
    cucsAdaptorMenloFcErrorStatsPopErrorsDeltaMin                    Unsigned64,
    cucsAdaptorMenloFcErrorStatsPushErrors                           Unsigned64,
    cucsAdaptorMenloFcErrorStatsPushErrorsDelta                      Counter64,
    cucsAdaptorMenloFcErrorStatsPushErrorsDeltaAvg                   Unsigned64,
    cucsAdaptorMenloFcErrorStatsPushErrorsDeltaMax                   Unsigned64,
    cucsAdaptorMenloFcErrorStatsPushErrorsDeltaMin                   Unsigned64,
    cucsAdaptorMenloFcErrorStatsSuspect                              TruthValue,
    cucsAdaptorMenloFcErrorStatsThresholded                          CucsAdaptorMenloFcErrorStatsThresholded,
    cucsAdaptorMenloFcErrorStatsTimeCollected                        DateAndTime,
    cucsAdaptorMenloFcErrorStatsUncorrectableErrors                  Unsigned64,
    cucsAdaptorMenloFcErrorStatsUncorrectableErrorsDelta             Counter64,
    cucsAdaptorMenloFcErrorStatsUncorrectableErrorsDeltaAvg          Unsigned64,
    cucsAdaptorMenloFcErrorStatsUncorrectableErrorsDeltaMax          Unsigned64,
    cucsAdaptorMenloFcErrorStatsUncorrectableErrorsDeltaMin          Unsigned64,
    cucsAdaptorMenloFcErrorStatsUpdate                               Gauge32
}

cucsAdaptorMenloFcErrorStatsInstanceId OBJECT-TYPE
    SYNTAX       CucsManagedObjectId
    MAX-ACCESS   not-accessible
    STATUS       current
    DESCRIPTION
        "Instance identifier of the managed object."
    ::= { cucsAdaptorMenloFcErrorStatsEntry 1 }

cucsAdaptorMenloFcErrorStatsDn OBJECT-TYPE
    SYNTAX       CucsManagedObjectDn
    MAX-ACCESS   read-only
    STATUS       current
    DESCRIPTION
        "Cisco UCS adaptor:MenloFcErrorStats:dn managed object property"
    ::= { cucsAdaptorMenloFcErrorStatsEntry 2 }

cucsAdaptorMenloFcErrorStatsRn OBJECT-TYPE
    SYNTAX       SnmpAdminString
    MAX-ACCESS   read-only
    STATUS       current
    DESCRIPTION
        "Cisco UCS adaptor:MenloFcErrorStats:rn managed object property"
    ::= { cucsAdaptorMenloFcErrorStatsEntry 3 }

cucsAdaptorMenloFcErrorStatsCorrectableErrors OBJECT-TYPE
    SYNTAX       Unsigned64
    MAX-ACCESS   read-only
    STATUS       current
    DESCRIPTION
        "Cisco UCS adaptor:MenloFcErrorStats:correctableErrors
        managed object property"
    ::= { cucsAdaptorMenloFcErrorStatsEntry 4 }

cucsAdaptorMenloFcErrorStatsCorrectableErrorsDelta OBJECT-TYPE
    SYNTAX       Counter64
    MAX-ACCESS   read-only
    STATUS       current
    DESCRIPTION
        "Cisco UCS adaptor:MenloFcErrorStats:correctableErrorsDelta
        managed object property"
    ::= { cucsAdaptorMenloFcErrorStatsEntry 5 }

cucsAdaptorMenloFcErrorStatsCorrectableErrorsDeltaAvg OBJECT-TYPE
    SYNTAX       Unsigned64
    MAX-ACCESS   read-only
    STATUS       current
    DESCRIPTION
        "Cisco UCS adaptor:MenloFcErrorStats:correctableErrorsDeltaAvg
        managed object property"
    ::= { cucsAdaptorMenloFcErrorStatsEntry 6 }

cucsAdaptorMenloFcErrorStatsCorrectableErrorsDeltaMax OBJECT-TYPE
    SYNTAX       Unsigned64
    MAX-ACCESS   read-only
    STATUS       current
    DESCRIPTION
        "Cisco UCS adaptor:MenloFcErrorStats:correctableErrorsDeltaMax
        managed object property"
    ::= { cucsAdaptorMenloFcErrorStatsEntry 7 }

cucsAdaptorMenloFcErrorStatsCorrectableErrorsDeltaMin OBJECT-TYPE
    SYNTAX       Unsigned64
    MAX-ACCESS   read-only
    STATUS       current
    DESCRIPTION
        "Cisco UCS adaptor:MenloFcErrorStats:correctableErrorsDeltaMin
        managed object property"
    ::= { cucsAdaptorMenloFcErrorStatsEntry 8 }

cucsAdaptorMenloFcErrorStatsIntervals OBJECT-TYPE
    SYNTAX       Gauge32
    MAX-ACCESS   read-only
    STATUS       current
    DESCRIPTION
        "Cisco UCS adaptor:MenloFcErrorStats:intervals
        managed object property"
    ::= { cucsAdaptorMenloFcErrorStatsEntry 9 }

cucsAdaptorMenloFcErrorStatsMenloFcIndex OBJECT-TYPE
    SYNTAX       CucsAdaptorMenloStatsIndex
    MAX-ACCESS   read-only
    STATUS       current
    DESCRIPTION
        "Cisco UCS adaptor:MenloFcErrorStats:menloFcIndex
        managed object property"
    ::= { cucsAdaptorMenloFcErrorStatsEntry 10 }

cucsAdaptorMenloFcErrorStatsPopErrors OBJECT-TYPE
    SYNTAX       Unsigned64
    MAX-ACCESS   read-only
    STATUS       current
    DESCRIPTION
        "Cisco UCS adaptor:MenloFcErrorStats:popErrors
        managed object property"
    ::= { cucsAdaptorMenloFcErrorStatsEntry 11 }

cucsAdaptorMenloFcErrorStatsPopErrorsDelta OBJECT-TYPE
    SYNTAX       Counter64
    MAX-ACCESS   read-only
    STATUS       current
    DESCRIPTION
        "Cisco UCS adaptor:MenloFcErrorStats:popErrorsDelta
        managed object property"
    ::= { cucsAdaptorMenloFcErrorStatsEntry 12 }

cucsAdaptorMenloFcErrorStatsPopErrorsDeltaAvg OBJECT-TYPE
    SYNTAX       Unsigned64
    MAX-ACCESS   read-only
    STATUS       current
    DESCRIPTION
        "Cisco UCS adaptor:MenloFcErrorStats:popErrorsDeltaAvg
        managed object property"
    ::= { cucsAdaptorMenloFcErrorStatsEntry 13 }

cucsAdaptorMenloFcErrorStatsPopErrorsDeltaMax OBJECT-TYPE
    SYNTAX       Unsigned64
    MAX-ACCESS   read-only
    STATUS       current
    DESCRIPTION
        "Cisco UCS adaptor:MenloFcErrorStats:popErrorsDeltaMax
        managed object property"
    ::= { cucsAdaptorMenloFcErrorStatsEntry 14 }

cucsAdaptorMenloFcErrorStatsPopErrorsDeltaMin OBJECT-TYPE
    SYNTAX       Unsigned64
    MAX-ACCESS   read-only
    STATUS       current
    DESCRIPTION
        "Cisco UCS adaptor:MenloFcErrorStats:popErrorsDeltaMin
        managed object property"
    ::= { cucsAdaptorMenloFcErrorStatsEntry 15 }

cucsAdaptorMenloFcErrorStatsPushErrors OBJECT-TYPE
    SYNTAX       Unsigned64
    MAX-ACCESS   read-only
    STATUS       current
    DESCRIPTION
        "Cisco UCS adaptor:MenloFcErrorStats:pushErrors
        managed object property"
    ::= { cucsAdaptorMenloFcErrorStatsEntry 16 }

cucsAdaptorMenloFcErrorStatsPushErrorsDelta OBJECT-TYPE
    SYNTAX       Counter64
    MAX-ACCESS   read-only
    STATUS       current
    DESCRIPTION
        "Cisco UCS adaptor:MenloFcErrorStats:pushErrorsDelta
        managed object property"
    ::= { cucsAdaptorMenloFcErrorStatsEntry 17 }

cucsAdaptorMenloFcErrorStatsPushErrorsDeltaAvg OBJECT-TYPE
    SYNTAX       Unsigned64
    MAX-ACCESS   read-only
    STATUS       current
    DESCRIPTION
        "Cisco UCS adaptor:MenloFcErrorStats:pushErrorsDeltaAvg
        managed object property"
    ::= { cucsAdaptorMenloFcErrorStatsEntry 18 }

cucsAdaptorMenloFcErrorStatsPushErrorsDeltaMax OBJECT-TYPE
    SYNTAX       Unsigned64
    MAX-ACCESS   read-only
    STATUS       current
    DESCRIPTION
        "Cisco UCS adaptor:MenloFcErrorStats:pushErrorsDeltaMax
        managed object property"
    ::= { cucsAdaptorMenloFcErrorStatsEntry 19 }

cucsAdaptorMenloFcErrorStatsPushErrorsDeltaMin OBJECT-TYPE
    SYNTAX       Unsigned64
    MAX-ACCESS   read-only
    STATUS       current
    DESCRIPTION
        "Cisco UCS adaptor:MenloFcErrorStats:pushErrorsDeltaMin
        managed object property"
    ::= { cucsAdaptorMenloFcErrorStatsEntry 20 }

cucsAdaptorMenloFcErrorStatsSuspect OBJECT-TYPE
    SYNTAX       TruthValue
    MAX-ACCESS   read-only
    STATUS       current
    DESCRIPTION
        "Cisco UCS adaptor:MenloFcErrorStats:suspect managed
        object property"
    ::= { cucsAdaptorMenloFcErrorStatsEntry 21 }

cucsAdaptorMenloFcErrorStatsThresholded OBJECT-TYPE
    SYNTAX       CucsAdaptorMenloFcErrorStatsThresholded
    MAX-ACCESS   read-only
    STATUS       current
    DESCRIPTION
        "Cisco UCS adaptor:MenloFcErrorStats:thresholded
        managed object property"
    ::= { cucsAdaptorMenloFcErrorStatsEntry 22 }

cucsAdaptorMenloFcErrorStatsTimeCollected OBJECT-TYPE
    SYNTAX       DateAndTime
    MAX-ACCESS   read-only
    STATUS       current
    DESCRIPTION
        "Cisco UCS adaptor:MenloFcErrorStats:timeCollected
        managed object property"
    ::= { cucsAdaptorMenloFcErrorStatsEntry 23 }

cucsAdaptorMenloFcErrorStatsUncorrectableErrors OBJECT-TYPE
    SYNTAX       Unsigned64
    MAX-ACCESS   read-only
    STATUS       current
    DESCRIPTION
        "Cisco UCS adaptor:MenloFcErrorStats:uncorrectableErrors
        managed object property"
    ::= { cucsAdaptorMenloFcErrorStatsEntry 24 }

cucsAdaptorMenloFcErrorStatsUncorrectableErrorsDelta OBJECT-TYPE
    SYNTAX       Counter64
    MAX-ACCESS   read-only
    STATUS       current
    DESCRIPTION
        "Cisco UCS adaptor:MenloFcErrorStats:uncorrectableErrorsDelta
        managed object property"
    ::= { cucsAdaptorMenloFcErrorStatsEntry 25 }

cucsAdaptorMenloFcErrorStatsUncorrectableErrorsDeltaAvg OBJECT-TYPE
    SYNTAX       Unsigned64
    MAX-ACCESS   read-only
    STATUS       current
    DESCRIPTION
        "Cisco UCS adaptor:MenloFcErrorStats:uncorrectableErrorsDeltaAvg
        managed object property"
    ::= { cucsAdaptorMenloFcErrorStatsEntry 26 }

cucsAdaptorMenloFcErrorStatsUncorrectableErrorsDeltaMax OBJECT-TYPE
    SYNTAX       Unsigned64
    MAX-ACCESS   read-only
    STATUS       current
    DESCRIPTION
        "Cisco UCS adaptor:MenloFcErrorStats:uncorrectableErrorsDeltaMax
        managed object property"
    ::= { cucsAdaptorMenloFcErrorStatsEntry 27 }

cucsAdaptorMenloFcErrorStatsUncorrectableErrorsDeltaMin OBJECT-TYPE
    SYNTAX       Unsigned64
    MAX-ACCESS   read-only
    STATUS       current
    DESCRIPTION
        "Cisco UCS adaptor:MenloFcErrorStats:uncorrectableErrorsDeltaMin
        managed object property"
    ::= { cucsAdaptorMenloFcErrorStatsEntry 28 }

cucsAdaptorMenloFcErrorStatsUpdate OBJECT-TYPE
    SYNTAX       Gauge32
    MAX-ACCESS   read-only
    STATUS       current
    DESCRIPTION
        "Cisco UCS adaptor:MenloFcErrorStats:update managed
        object property"
    ::= { cucsAdaptorMenloFcErrorStatsEntry 29 }

cucsAdaptorMenloFcErrorStatsHistTable OBJECT-TYPE
    SYNTAX           SEQUENCE OF CucsAdaptorMenloFcErrorStatsHistEntry
    MAX-ACCESS       not-accessible
    STATUS           current
    DESCRIPTION
        "Cisco UCS adaptor:MenloFcErrorStatsHist managed object table"
    ::= { cucsAdaptorObjects 64 }

cucsAdaptorMenloFcErrorStatsHistEntry OBJECT-TYPE
    SYNTAX           CucsAdaptorMenloFcErrorStatsHistEntry
    MAX-ACCESS       not-accessible
    STATUS           current
    DESCRIPTION
        "Entry for the cucsAdaptorMenloFcErrorStatsHistTable table."
    INDEX { cucsAdaptorMenloFcErrorStatsHistInstanceId }
    ::= { cucsAdaptorMenloFcErrorStatsHistTable 1 }

CucsAdaptorMenloFcErrorStatsHistEntry ::= SEQUENCE {
    cucsAdaptorMenloFcErrorStatsHistInstanceId                       CucsManagedObjectId,
    cucsAdaptorMenloFcErrorStatsHistDn                               CucsManagedObjectDn,
    cucsAdaptorMenloFcErrorStatsHistRn                               SnmpAdminString,
    cucsAdaptorMenloFcErrorStatsHistCorrectableErrors                Unsigned64,
    cucsAdaptorMenloFcErrorStatsHistCorrectableErrorsDelta           Unsigned64,
    cucsAdaptorMenloFcErrorStatsHistCorrectableErrorsDeltaAvg        Unsigned64,
    cucsAdaptorMenloFcErrorStatsHistCorrectableErrorsDeltaMax        Unsigned64,
    cucsAdaptorMenloFcErrorStatsHistCorrectableErrorsDeltaMin        Unsigned64,
    cucsAdaptorMenloFcErrorStatsHistId                               Unsigned64,
    cucsAdaptorMenloFcErrorStatsHistMostRecent                       TruthValue,
    cucsAdaptorMenloFcErrorStatsHistPopErrors                        Unsigned64,
    cucsAdaptorMenloFcErrorStatsHistPopErrorsDelta                   Unsigned64,
    cucsAdaptorMenloFcErrorStatsHistPopErrorsDeltaAvg                Unsigned64,
    cucsAdaptorMenloFcErrorStatsHistPopErrorsDeltaMax                Unsigned64,
    cucsAdaptorMenloFcErrorStatsHistPopErrorsDeltaMin                Unsigned64,
    cucsAdaptorMenloFcErrorStatsHistPushErrors                       Unsigned64,
    cucsAdaptorMenloFcErrorStatsHistPushErrorsDelta                  Unsigned64,
    cucsAdaptorMenloFcErrorStatsHistPushErrorsDeltaAvg               Unsigned64,
    cucsAdaptorMenloFcErrorStatsHistPushErrorsDeltaMax               Unsigned64,
    cucsAdaptorMenloFcErrorStatsHistPushErrorsDeltaMin               Unsigned64,
    cucsAdaptorMenloFcErrorStatsHistSuspect                          TruthValue,
    cucsAdaptorMenloFcErrorStatsHistThresholded                      CucsAdaptorMenloFcErrorStatsHistThresholded,
    cucsAdaptorMenloFcErrorStatsHistTimeCollected                    DateAndTime,
    cucsAdaptorMenloFcErrorStatsHistUncorrectableErrors              Unsigned64,
    cucsAdaptorMenloFcErrorStatsHistUncorrectableErrorsDelta         Unsigned64,
    cucsAdaptorMenloFcErrorStatsHistUncorrectableErrorsDeltaAvg      Unsigned64,
    cucsAdaptorMenloFcErrorStatsHistUncorrectableErrorsDeltaMax      Unsigned64,
    cucsAdaptorMenloFcErrorStatsHistUncorrectableErrorsDeltaMin      Unsigned64
}

cucsAdaptorMenloFcErrorStatsHistInstanceId OBJECT-TYPE
    SYNTAX       CucsManagedObjectId
    MAX-ACCESS   not-accessible
    STATUS       current
    DESCRIPTION
        "Instance identifier of the managed object."
    ::= { cucsAdaptorMenloFcErrorStatsHistEntry 1 }

cucsAdaptorMenloFcErrorStatsHistDn OBJECT-TYPE
    SYNTAX       CucsManagedObjectDn
    MAX-ACCESS   read-only
    STATUS       current
    DESCRIPTION
        "Cisco UCS adaptor:MenloFcErrorStatsHist:dn managed
        object property"
    ::= { cucsAdaptorMenloFcErrorStatsHistEntry 2 }

cucsAdaptorMenloFcErrorStatsHistRn OBJECT-TYPE
    SYNTAX       SnmpAdminString
    MAX-ACCESS   read-only
    STATUS       current
    DESCRIPTION
        "Cisco UCS adaptor:MenloFcErrorStatsHist:rn managed
        object property"
    ::= { cucsAdaptorMenloFcErrorStatsHistEntry 3 }

cucsAdaptorMenloFcErrorStatsHistCorrectableErrors OBJECT-TYPE
    SYNTAX       Unsigned64
    MAX-ACCESS   read-only
    STATUS       current
    DESCRIPTION
        "Cisco UCS adaptor:MenloFcErrorStatsHist:correctableErrors
        managed object property"
    ::= { cucsAdaptorMenloFcErrorStatsHistEntry 4 }

cucsAdaptorMenloFcErrorStatsHistCorrectableErrorsDelta OBJECT-TYPE
    SYNTAX       Unsigned64
    MAX-ACCESS   read-only
    STATUS       current
    DESCRIPTION
        "Cisco UCS adaptor:MenloFcErrorStatsHist:correctableErrorsDelta
        managed object property"
    ::= { cucsAdaptorMenloFcErrorStatsHistEntry 5 }

cucsAdaptorMenloFcErrorStatsHistCorrectableErrorsDeltaAvg OBJECT-TYPE
    SYNTAX       Unsigned64
    MAX-ACCESS   read-only
    STATUS       current
    DESCRIPTION
        "Cisco UCS adaptor:MenloFcErrorStatsHist:correctableErrorsDeltaAvg
         managed object property"
    ::= { cucsAdaptorMenloFcErrorStatsHistEntry 6 }

cucsAdaptorMenloFcErrorStatsHistCorrectableErrorsDeltaMax OBJECT-TYPE
    SYNTAX       Unsigned64
    MAX-ACCESS   read-only
    STATUS       current
    DESCRIPTION
        "Cisco UCS adaptor:MenloFcErrorStatsHist:correctableErrorsDeltaMax
         managed object property"
    ::= { cucsAdaptorMenloFcErrorStatsHistEntry 7 }

cucsAdaptorMenloFcErrorStatsHistCorrectableErrorsDeltaMin OBJECT-TYPE
    SYNTAX       Unsigned64
    MAX-ACCESS   read-only
    STATUS       current
    DESCRIPTION
        "Cisco UCS adaptor:MenloFcErrorStatsHist:correctableErrorsDeltaMin
         managed object property"
    ::= { cucsAdaptorMenloFcErrorStatsHistEntry 8 }

cucsAdaptorMenloFcErrorStatsHistId OBJECT-TYPE
    SYNTAX       Unsigned64
    MAX-ACCESS   read-only
    STATUS       current
    DESCRIPTION
        "Cisco UCS adaptor:MenloFcErrorStatsHist:id managed
        object property"
    ::= { cucsAdaptorMenloFcErrorStatsHistEntry 9 }

cucsAdaptorMenloFcErrorStatsHistMostRecent OBJECT-TYPE
    SYNTAX       TruthValue
    MAX-ACCESS   read-only
    STATUS       current
    DESCRIPTION
        "Cisco UCS adaptor:MenloFcErrorStatsHist:mostRecent
        managed object property"
    ::= { cucsAdaptorMenloFcErrorStatsHistEntry 10 }

cucsAdaptorMenloFcErrorStatsHistPopErrors OBJECT-TYPE
    SYNTAX       Unsigned64
    MAX-ACCESS   read-only
    STATUS       current
    DESCRIPTION
        "Cisco UCS adaptor:MenloFcErrorStatsHist:popErrors
        managed object property"
    ::= { cucsAdaptorMenloFcErrorStatsHistEntry 11 }

cucsAdaptorMenloFcErrorStatsHistPopErrorsDelta OBJECT-TYPE
    SYNTAX       Unsigned64
    MAX-ACCESS   read-only
    STATUS       current
    DESCRIPTION
        "Cisco UCS adaptor:MenloFcErrorStatsHist:popErrorsDelta
        managed object property"
    ::= { cucsAdaptorMenloFcErrorStatsHistEntry 12 }

cucsAdaptorMenloFcErrorStatsHistPopErrorsDeltaAvg OBJECT-TYPE
    SYNTAX       Unsigned64
    MAX-ACCESS   read-only
    STATUS       current
    DESCRIPTION
        "Cisco UCS adaptor:MenloFcErrorStatsHist:popErrorsDeltaAvg
        managed object property"
    ::= { cucsAdaptorMenloFcErrorStatsHistEntry 13 }

cucsAdaptorMenloFcErrorStatsHistPopErrorsDeltaMax OBJECT-TYPE
    SYNTAX       Unsigned64
    MAX-ACCESS   read-only
    STATUS       current
    DESCRIPTION
        "Cisco UCS adaptor:MenloFcErrorStatsHist:popErrorsDeltaMax
        managed object property"
    ::= { cucsAdaptorMenloFcErrorStatsHistEntry 14 }

cucsAdaptorMenloFcErrorStatsHistPopErrorsDeltaMin OBJECT-TYPE
    SYNTAX       Unsigned64
    MAX-ACCESS   read-only
    STATUS       current
    DESCRIPTION
        "Cisco UCS adaptor:MenloFcErrorStatsHist:popErrorsDeltaMin
        managed object property"
    ::= { cucsAdaptorMenloFcErrorStatsHistEntry 15 }

cucsAdaptorMenloFcErrorStatsHistPushErrors OBJECT-TYPE
    SYNTAX       Unsigned64
    MAX-ACCESS   read-only
    STATUS       current
    DESCRIPTION
        "Cisco UCS adaptor:MenloFcErrorStatsHist:pushErrors
        managed object property"
    ::= { cucsAdaptorMenloFcErrorStatsHistEntry 16 }

cucsAdaptorMenloFcErrorStatsHistPushErrorsDelta OBJECT-TYPE
    SYNTAX       Unsigned64
    MAX-ACCESS   read-only
    STATUS       current
    DESCRIPTION
        "Cisco UCS adaptor:MenloFcErrorStatsHist:pushErrorsDelta
        managed object property"
    ::= { cucsAdaptorMenloFcErrorStatsHistEntry 17 }

cucsAdaptorMenloFcErrorStatsHistPushErrorsDeltaAvg OBJECT-TYPE
    SYNTAX       Unsigned64
    MAX-ACCESS   read-only
    STATUS       current
    DESCRIPTION
        "Cisco UCS adaptor:MenloFcErrorStatsHist:pushErrorsDeltaAvg
        managed object property"
    ::= { cucsAdaptorMenloFcErrorStatsHistEntry 18 }

cucsAdaptorMenloFcErrorStatsHistPushErrorsDeltaMax OBJECT-TYPE
    SYNTAX       Unsigned64
    MAX-ACCESS   read-only
    STATUS       current
    DESCRIPTION
        "Cisco UCS adaptor:MenloFcErrorStatsHist:pushErrorsDeltaMax
        managed object property"
    ::= { cucsAdaptorMenloFcErrorStatsHistEntry 19 }

cucsAdaptorMenloFcErrorStatsHistPushErrorsDeltaMin OBJECT-TYPE
    SYNTAX       Unsigned64
    MAX-ACCESS   read-only
    STATUS       current
    DESCRIPTION
        "Cisco UCS adaptor:MenloFcErrorStatsHist:pushErrorsDeltaMin
        managed object property"
    ::= { cucsAdaptorMenloFcErrorStatsHistEntry 20 }

cucsAdaptorMenloFcErrorStatsHistSuspect OBJECT-TYPE
    SYNTAX       TruthValue
    MAX-ACCESS   read-only
    STATUS       current
    DESCRIPTION
        "Cisco UCS adaptor:MenloFcErrorStatsHist:suspect
        managed object property"
    ::= { cucsAdaptorMenloFcErrorStatsHistEntry 21 }

cucsAdaptorMenloFcErrorStatsHistThresholded OBJECT-TYPE
    SYNTAX       CucsAdaptorMenloFcErrorStatsHistThresholded
    MAX-ACCESS   read-only
    STATUS       current
    DESCRIPTION
        "Cisco UCS adaptor:MenloFcErrorStatsHist:thresholded
        managed object property"
    ::= { cucsAdaptorMenloFcErrorStatsHistEntry 22 }

cucsAdaptorMenloFcErrorStatsHistTimeCollected OBJECT-TYPE
    SYNTAX       DateAndTime
    MAX-ACCESS   read-only
    STATUS       current
    DESCRIPTION
        "Cisco UCS adaptor:MenloFcErrorStatsHist:timeCollected
        managed object property"
    ::= { cucsAdaptorMenloFcErrorStatsHistEntry 23 }

cucsAdaptorMenloFcErrorStatsHistUncorrectableErrors OBJECT-TYPE
    SYNTAX       Unsigned64
    MAX-ACCESS   read-only
    STATUS       current
    DESCRIPTION
        "Cisco UCS adaptor:MenloFcErrorStatsHist:uncorrectableErrors
        managed object property"
    ::= { cucsAdaptorMenloFcErrorStatsHistEntry 24 }

cucsAdaptorMenloFcErrorStatsHistUncorrectableErrorsDelta OBJECT-TYPE
    SYNTAX       Unsigned64
    MAX-ACCESS   read-only
    STATUS       current
    DESCRIPTION
        "Cisco UCS adaptor:MenloFcErrorStatsHist:uncorrectableErrorsDelta
        managed object property"
    ::= { cucsAdaptorMenloFcErrorStatsHistEntry 25 }

cucsAdaptorMenloFcErrorStatsHistUncorrectableErrorsDeltaAvg OBJECT-TYPE
    SYNTAX       Unsigned64
    MAX-ACCESS   read-only
    STATUS       current
    DESCRIPTION
        "Cisco UCS adaptor:MenloFcErrorStatsHist:uncorrectableErrorsDeltaA
        vg managed object property"
    ::= { cucsAdaptorMenloFcErrorStatsHistEntry 26 }

cucsAdaptorMenloFcErrorStatsHistUncorrectableErrorsDeltaMax OBJECT-TYPE
    SYNTAX       Unsigned64
    MAX-ACCESS   read-only
    STATUS       current
    DESCRIPTION
        "Cisco UCS adaptor:MenloFcErrorStatsHist:uncorrectableErrorsDeltaM
        ax managed object property"
    ::= { cucsAdaptorMenloFcErrorStatsHistEntry 27 }

cucsAdaptorMenloFcErrorStatsHistUncorrectableErrorsDeltaMin OBJECT-TYPE
    SYNTAX       Unsigned64
    MAX-ACCESS   read-only
    STATUS       current
    DESCRIPTION
        "Cisco UCS adaptor:MenloFcErrorStatsHist:uncorrectableErrorsDeltaM
        in managed object property"
    ::= { cucsAdaptorMenloFcErrorStatsHistEntry 28 }

cucsAdaptorMenloFcStatsTable OBJECT-TYPE
    SYNTAX           SEQUENCE OF CucsAdaptorMenloFcStatsEntry
    MAX-ACCESS       not-accessible
    STATUS           current
    DESCRIPTION
        "Cisco UCS adaptor:MenloFcStats managed object table"
    ::= { cucsAdaptorObjects 65 }

cucsAdaptorMenloFcStatsEntry OBJECT-TYPE
    SYNTAX           CucsAdaptorMenloFcStatsEntry
    MAX-ACCESS       not-accessible
    STATUS           current
    DESCRIPTION
        "Entry for the cucsAdaptorMenloFcStatsTable table."
    INDEX { cucsAdaptorMenloFcStatsInstanceId }
    ::= { cucsAdaptorMenloFcStatsTable 1 }

CucsAdaptorMenloFcStatsEntry ::= SEQUENCE {
    cucsAdaptorMenloFcStatsInstanceId                                CucsManagedObjectId,
    cucsAdaptorMenloFcStatsDn                                        CucsManagedObjectDn,
    cucsAdaptorMenloFcStatsRn                                        SnmpAdminString,
    cucsAdaptorMenloFcStatsDropAcl                                   Unsigned64,
    cucsAdaptorMenloFcStatsDropAclDelta                              Counter64,
    cucsAdaptorMenloFcStatsDropAclDeltaAvg                           Unsigned64,
    cucsAdaptorMenloFcStatsDropAclDeltaMax                           Unsigned64,
    cucsAdaptorMenloFcStatsDropAclDeltaMin                           Unsigned64,
    cucsAdaptorMenloFcStatsDropOverrun                               Unsigned64,
    cucsAdaptorMenloFcStatsDropOverrunDelta                          Counter64,
    cucsAdaptorMenloFcStatsDropOverrunDeltaAvg                       Unsigned64,
    cucsAdaptorMenloFcStatsDropOverrunDeltaMax                       Unsigned64,
    cucsAdaptorMenloFcStatsDropOverrunDeltaMin                       Unsigned64,
    cucsAdaptorMenloFcStatsDropRunt                                  Unsigned64,
    cucsAdaptorMenloFcStatsDropRuntDelta                             Counter64,
    cucsAdaptorMenloFcStatsDropRuntDeltaAvg                          Unsigned64,
    cucsAdaptorMenloFcStatsDropRuntDeltaMax                          Unsigned64,
    cucsAdaptorMenloFcStatsDropRuntDeltaMin                          Unsigned64,
    cucsAdaptorMenloFcStatsIntervals                                 Gauge32,
    cucsAdaptorMenloFcStatsMenloFcIndex                              CucsAdaptorMenloStatsIndex,
    cucsAdaptorMenloFcStatsSuspect                                   TruthValue,
    cucsAdaptorMenloFcStatsThresholded                               CucsAdaptorMenloFcStatsThresholded,
    cucsAdaptorMenloFcStatsTimeCollected                             DateAndTime,
    cucsAdaptorMenloFcStatsTruncateOverrun                           Unsigned64,
    cucsAdaptorMenloFcStatsTruncateOverrunDelta                      Counter64,
    cucsAdaptorMenloFcStatsTruncateOverrunDeltaAvg                   Unsigned64,
    cucsAdaptorMenloFcStatsTruncateOverrunDeltaMax                   Unsigned64,
    cucsAdaptorMenloFcStatsTruncateOverrunDeltaMin                   Unsigned64,
    cucsAdaptorMenloFcStatsUpdate                                    Gauge32
}

cucsAdaptorMenloFcStatsInstanceId OBJECT-TYPE
    SYNTAX       CucsManagedObjectId
    MAX-ACCESS   not-accessible
    STATUS       current
    DESCRIPTION
        "Instance identifier of the managed object."
    ::= { cucsAdaptorMenloFcStatsEntry 1 }

cucsAdaptorMenloFcStatsDn OBJECT-TYPE
    SYNTAX       CucsManagedObjectDn
    MAX-ACCESS   read-only
    STATUS       current
    DESCRIPTION
        "Cisco UCS adaptor:MenloFcStats:dn managed object property"
    ::= { cucsAdaptorMenloFcStatsEntry 2 }

cucsAdaptorMenloFcStatsRn OBJECT-TYPE
    SYNTAX       SnmpAdminString
    MAX-ACCESS   read-only
    STATUS       current
    DESCRIPTION
        "Cisco UCS adaptor:MenloFcStats:rn managed object property"
    ::= { cucsAdaptorMenloFcStatsEntry 3 }

cucsAdaptorMenloFcStatsDropAcl OBJECT-TYPE
    SYNTAX       Unsigned64
    MAX-ACCESS   read-only
    STATUS       current
    DESCRIPTION
        "Cisco UCS adaptor:MenloFcStats:dropAcl managed object property"
    ::= { cucsAdaptorMenloFcStatsEntry 4 }

cucsAdaptorMenloFcStatsDropAclDelta OBJECT-TYPE
    SYNTAX       Counter64
    MAX-ACCESS   read-only
    STATUS       current
    DESCRIPTION
        "Cisco UCS adaptor:MenloFcStats:dropAclDelta managed
        object property"
    ::= { cucsAdaptorMenloFcStatsEntry 5 }

cucsAdaptorMenloFcStatsDropAclDeltaAvg OBJECT-TYPE
    SYNTAX       Unsigned64
    MAX-ACCESS   read-only
    STATUS       current
    DESCRIPTION
        "Cisco UCS adaptor:MenloFcStats:dropAclDeltaAvg
        managed object property"
    ::= { cucsAdaptorMenloFcStatsEntry 6 }

cucsAdaptorMenloFcStatsDropAclDeltaMax OBJECT-TYPE
    SYNTAX       Unsigned64
    MAX-ACCESS   read-only
    STATUS       current
    DESCRIPTION
        "Cisco UCS adaptor:MenloFcStats:dropAclDeltaMax
        managed object property"
    ::= { cucsAdaptorMenloFcStatsEntry 7 }

cucsAdaptorMenloFcStatsDropAclDeltaMin OBJECT-TYPE
    SYNTAX       Unsigned64
    MAX-ACCESS   read-only
    STATUS       current
    DESCRIPTION
        "Cisco UCS adaptor:MenloFcStats:dropAclDeltaMin
        managed object property"
    ::= { cucsAdaptorMenloFcStatsEntry 8 }

cucsAdaptorMenloFcStatsDropOverrun OBJECT-TYPE
    SYNTAX       Unsigned64
    MAX-ACCESS   read-only
    STATUS       current
    DESCRIPTION
        "Cisco UCS adaptor:MenloFcStats:dropOverrun managed
        object property"
    ::= { cucsAdaptorMenloFcStatsEntry 9 }

cucsAdaptorMenloFcStatsDropOverrunDelta OBJECT-TYPE
    SYNTAX       Counter64
    MAX-ACCESS   read-only
    STATUS       current
    DESCRIPTION
        "Cisco UCS adaptor:MenloFcStats:dropOverrunDelta
        managed object property"
    ::= { cucsAdaptorMenloFcStatsEntry 10 }

cucsAdaptorMenloFcStatsDropOverrunDeltaAvg OBJECT-TYPE
    SYNTAX       Unsigned64
    MAX-ACCESS   read-only
    STATUS       current
    DESCRIPTION
        "Cisco UCS adaptor:MenloFcStats:dropOverrunDeltaAvg
        managed object property"
    ::= { cucsAdaptorMenloFcStatsEntry 11 }

cucsAdaptorMenloFcStatsDropOverrunDeltaMax OBJECT-TYPE
    SYNTAX       Unsigned64
    MAX-ACCESS   read-only
    STATUS       current
    DESCRIPTION
        "Cisco UCS adaptor:MenloFcStats:dropOverrunDeltaMax
        managed object property"
    ::= { cucsAdaptorMenloFcStatsEntry 12 }

cucsAdaptorMenloFcStatsDropOverrunDeltaMin OBJECT-TYPE
    SYNTAX       Unsigned64
    MAX-ACCESS   read-only
    STATUS       current
    DESCRIPTION
        "Cisco UCS adaptor:MenloFcStats:dropOverrunDeltaMin
        managed object property"
    ::= { cucsAdaptorMenloFcStatsEntry 13 }

cucsAdaptorMenloFcStatsDropRunt OBJECT-TYPE
    SYNTAX       Unsigned64
    MAX-ACCESS   read-only
    STATUS       current
    DESCRIPTION
        "Cisco UCS adaptor:MenloFcStats:dropRunt managed object property"
    ::= { cucsAdaptorMenloFcStatsEntry 14 }

cucsAdaptorMenloFcStatsDropRuntDelta OBJECT-TYPE
    SYNTAX       Counter64
    MAX-ACCESS   read-only
    STATUS       current
    DESCRIPTION
        "Cisco UCS adaptor:MenloFcStats:dropRuntDelta managed
        object property"
    ::= { cucsAdaptorMenloFcStatsEntry 15 }

cucsAdaptorMenloFcStatsDropRuntDeltaAvg OBJECT-TYPE
    SYNTAX       Unsigned64
    MAX-ACCESS   read-only
    STATUS       current
    DESCRIPTION
        "Cisco UCS adaptor:MenloFcStats:dropRuntDeltaAvg
        managed object property"
    ::= { cucsAdaptorMenloFcStatsEntry 16 }

cucsAdaptorMenloFcStatsDropRuntDeltaMax OBJECT-TYPE
    SYNTAX       Unsigned64
    MAX-ACCESS   read-only
    STATUS       current
    DESCRIPTION
        "Cisco UCS adaptor:MenloFcStats:dropRuntDeltaMax
        managed object property"
    ::= { cucsAdaptorMenloFcStatsEntry 17 }

cucsAdaptorMenloFcStatsDropRuntDeltaMin OBJECT-TYPE
    SYNTAX       Unsigned64
    MAX-ACCESS   read-only
    STATUS       current
    DESCRIPTION
        "Cisco UCS adaptor:MenloFcStats:dropRuntDeltaMin
        managed object property"
    ::= { cucsAdaptorMenloFcStatsEntry 18 }

cucsAdaptorMenloFcStatsIntervals OBJECT-TYPE
    SYNTAX       Gauge32
    MAX-ACCESS   read-only
    STATUS       current
    DESCRIPTION
        "Cisco UCS adaptor:MenloFcStats:intervals managed object property"
    ::= { cucsAdaptorMenloFcStatsEntry 19 }

cucsAdaptorMenloFcStatsMenloFcIndex OBJECT-TYPE
    SYNTAX       CucsAdaptorMenloStatsIndex
    MAX-ACCESS   read-only
    STATUS       current
    DESCRIPTION
        "Cisco UCS adaptor:MenloFcStats:menloFcIndex managed
        object property"
    ::= { cucsAdaptorMenloFcStatsEntry 20 }

cucsAdaptorMenloFcStatsSuspect OBJECT-TYPE
    SYNTAX       TruthValue
    MAX-ACCESS   read-only
    STATUS       current
    DESCRIPTION
        "Cisco UCS adaptor:MenloFcStats:suspect managed object property"
    ::= { cucsAdaptorMenloFcStatsEntry 21 }

cucsAdaptorMenloFcStatsThresholded OBJECT-TYPE
    SYNTAX       CucsAdaptorMenloFcStatsThresholded
    MAX-ACCESS   read-only
    STATUS       current
    DESCRIPTION
        "Cisco UCS adaptor:MenloFcStats:thresholded managed
        object property"
    ::= { cucsAdaptorMenloFcStatsEntry 22 }

cucsAdaptorMenloFcStatsTimeCollected OBJECT-TYPE
    SYNTAX       DateAndTime
    MAX-ACCESS   read-only
    STATUS       current
    DESCRIPTION
        "Cisco UCS adaptor:MenloFcStats:timeCollected managed
        object property"
    ::= { cucsAdaptorMenloFcStatsEntry 23 }

cucsAdaptorMenloFcStatsTruncateOverrun OBJECT-TYPE
    SYNTAX       Unsigned64
    MAX-ACCESS   read-only
    STATUS       current
    DESCRIPTION
        "Cisco UCS adaptor:MenloFcStats:truncateOverrun
        managed object property"
    ::= { cucsAdaptorMenloFcStatsEntry 24 }

cucsAdaptorMenloFcStatsTruncateOverrunDelta OBJECT-TYPE
    SYNTAX       Counter64
    MAX-ACCESS   read-only
    STATUS       current
    DESCRIPTION
        "Cisco UCS adaptor:MenloFcStats:truncateOverrunDelta
        managed object property"
    ::= { cucsAdaptorMenloFcStatsEntry 25 }

cucsAdaptorMenloFcStatsTruncateOverrunDeltaAvg OBJECT-TYPE
    SYNTAX       Unsigned64
    MAX-ACCESS   read-only
    STATUS       current
    DESCRIPTION
        "Cisco UCS adaptor:MenloFcStats:truncateOverrunDeltaAvg
        managed object property"
    ::= { cucsAdaptorMenloFcStatsEntry 26 }

cucsAdaptorMenloFcStatsTruncateOverrunDeltaMax OBJECT-TYPE
    SYNTAX       Unsigned64
    MAX-ACCESS   read-only
    STATUS       current
    DESCRIPTION
        "Cisco UCS adaptor:MenloFcStats:truncateOverrunDeltaMax
        managed object property"
    ::= { cucsAdaptorMenloFcStatsEntry 27 }

cucsAdaptorMenloFcStatsTruncateOverrunDeltaMin OBJECT-TYPE
    SYNTAX       Unsigned64
    MAX-ACCESS   read-only
    STATUS       current
    DESCRIPTION
        "Cisco UCS adaptor:MenloFcStats:truncateOverrunDeltaMin
        managed object property"
    ::= { cucsAdaptorMenloFcStatsEntry 28 }

cucsAdaptorMenloFcStatsUpdate OBJECT-TYPE
    SYNTAX       Gauge32
    MAX-ACCESS   read-only
    STATUS       current
    DESCRIPTION
        "Cisco UCS adaptor:MenloFcStats:update managed object property"
    ::= { cucsAdaptorMenloFcStatsEntry 29 }

cucsAdaptorMenloFcStatsHistTable OBJECT-TYPE
    SYNTAX           SEQUENCE OF CucsAdaptorMenloFcStatsHistEntry
    MAX-ACCESS       not-accessible
    STATUS           current
    DESCRIPTION
        "Cisco UCS adaptor:MenloFcStatsHist managed object table"
    ::= { cucsAdaptorObjects 66 }

cucsAdaptorMenloFcStatsHistEntry OBJECT-TYPE
    SYNTAX           CucsAdaptorMenloFcStatsHistEntry
    MAX-ACCESS       not-accessible
    STATUS           current
    DESCRIPTION
        "Entry for the cucsAdaptorMenloFcStatsHistTable table."
    INDEX { cucsAdaptorMenloFcStatsHistInstanceId }
    ::= { cucsAdaptorMenloFcStatsHistTable 1 }

CucsAdaptorMenloFcStatsHistEntry ::= SEQUENCE {
    cucsAdaptorMenloFcStatsHistInstanceId                            CucsManagedObjectId,
    cucsAdaptorMenloFcStatsHistDn                                    CucsManagedObjectDn,
    cucsAdaptorMenloFcStatsHistRn                                    SnmpAdminString,
    cucsAdaptorMenloFcStatsHistDropAcl                               Unsigned64,
    cucsAdaptorMenloFcStatsHistDropAclDelta                          Unsigned64,
    cucsAdaptorMenloFcStatsHistDropAclDeltaAvg                       Unsigned64,
    cucsAdaptorMenloFcStatsHistDropAclDeltaMax                       Unsigned64,
    cucsAdaptorMenloFcStatsHistDropAclDeltaMin                       Unsigned64,
    cucsAdaptorMenloFcStatsHistDropOverrun                           Unsigned64,
    cucsAdaptorMenloFcStatsHistDropOverrunDelta                      Unsigned64,
    cucsAdaptorMenloFcStatsHistDropOverrunDeltaAvg                   Unsigned64,
    cucsAdaptorMenloFcStatsHistDropOverrunDeltaMax                   Unsigned64,
    cucsAdaptorMenloFcStatsHistDropOverrunDeltaMin                   Unsigned64,
    cucsAdaptorMenloFcStatsHistDropRunt                              Unsigned64,
    cucsAdaptorMenloFcStatsHistDropRuntDelta                         Unsigned64,
    cucsAdaptorMenloFcStatsHistDropRuntDeltaAvg                      Unsigned64,
    cucsAdaptorMenloFcStatsHistDropRuntDeltaMax                      Unsigned64,
    cucsAdaptorMenloFcStatsHistDropRuntDeltaMin                      Unsigned64,
    cucsAdaptorMenloFcStatsHistId                                    Unsigned64,
    cucsAdaptorMenloFcStatsHistMostRecent                            TruthValue,
    cucsAdaptorMenloFcStatsHistSuspect                               TruthValue,
    cucsAdaptorMenloFcStatsHistThresholded                           CucsAdaptorMenloFcStatsHistThresholded,
    cucsAdaptorMenloFcStatsHistTimeCollected                         DateAndTime,
    cucsAdaptorMenloFcStatsHistTruncateOverrun                       Unsigned64,
    cucsAdaptorMenloFcStatsHistTruncateOverrunDelta                  Unsigned64,
    cucsAdaptorMenloFcStatsHistTruncateOverrunDeltaAvg               Unsigned64,
    cucsAdaptorMenloFcStatsHistTruncateOverrunDeltaMax               Unsigned64,
    cucsAdaptorMenloFcStatsHistTruncateOverrunDeltaMin               Unsigned64
}

cucsAdaptorMenloFcStatsHistInstanceId OBJECT-TYPE
    SYNTAX       CucsManagedObjectId
    MAX-ACCESS   not-accessible
    STATUS       current
    DESCRIPTION
        "Instance identifier of the managed object."
    ::= { cucsAdaptorMenloFcStatsHistEntry 1 }

cucsAdaptorMenloFcStatsHistDn OBJECT-TYPE
    SYNTAX       CucsManagedObjectDn
    MAX-ACCESS   read-only
    STATUS       current
    DESCRIPTION
        "Cisco UCS adaptor:MenloFcStatsHist:dn managed object property"
    ::= { cucsAdaptorMenloFcStatsHistEntry 2 }

cucsAdaptorMenloFcStatsHistRn OBJECT-TYPE
    SYNTAX       SnmpAdminString
    MAX-ACCESS   read-only
    STATUS       current
    DESCRIPTION
        "Cisco UCS adaptor:MenloFcStatsHist:rn managed object property"
    ::= { cucsAdaptorMenloFcStatsHistEntry 3 }

cucsAdaptorMenloFcStatsHistDropAcl OBJECT-TYPE
    SYNTAX       Unsigned64
    MAX-ACCESS   read-only
    STATUS       current
    DESCRIPTION
        "Cisco UCS adaptor:MenloFcStatsHist:dropAcl managed
        object property"
    ::= { cucsAdaptorMenloFcStatsHistEntry 4 }

cucsAdaptorMenloFcStatsHistDropAclDelta OBJECT-TYPE
    SYNTAX       Unsigned64
    MAX-ACCESS   read-only
    STATUS       current
    DESCRIPTION
        "Cisco UCS adaptor:MenloFcStatsHist:dropAclDelta
        managed object property"
    ::= { cucsAdaptorMenloFcStatsHistEntry 5 }

cucsAdaptorMenloFcStatsHistDropAclDeltaAvg OBJECT-TYPE
    SYNTAX       Unsigned64
    MAX-ACCESS   read-only
    STATUS       current
    DESCRIPTION
        "Cisco UCS adaptor:MenloFcStatsHist:dropAclDeltaAvg
        managed object property"
    ::= { cucsAdaptorMenloFcStatsHistEntry 6 }

cucsAdaptorMenloFcStatsHistDropAclDeltaMax OBJECT-TYPE
    SYNTAX       Unsigned64
    MAX-ACCESS   read-only
    STATUS       current
    DESCRIPTION
        "Cisco UCS adaptor:MenloFcStatsHist:dropAclDeltaMax
        managed object property"
    ::= { cucsAdaptorMenloFcStatsHistEntry 7 }

cucsAdaptorMenloFcStatsHistDropAclDeltaMin OBJECT-TYPE
    SYNTAX       Unsigned64
    MAX-ACCESS   read-only
    STATUS       current
    DESCRIPTION
        "Cisco UCS adaptor:MenloFcStatsHist:dropAclDeltaMin
        managed object property"
    ::= { cucsAdaptorMenloFcStatsHistEntry 8 }

cucsAdaptorMenloFcStatsHistDropOverrun OBJECT-TYPE
    SYNTAX       Unsigned64
    MAX-ACCESS   read-only
    STATUS       current
    DESCRIPTION
        "Cisco UCS adaptor:MenloFcStatsHist:dropOverrun
        managed object property"
    ::= { cucsAdaptorMenloFcStatsHistEntry 9 }

cucsAdaptorMenloFcStatsHistDropOverrunDelta OBJECT-TYPE
    SYNTAX       Unsigned64
    MAX-ACCESS   read-only
    STATUS       current
    DESCRIPTION
        "Cisco UCS adaptor:MenloFcStatsHist:dropOverrunDelta
        managed object property"
    ::= { cucsAdaptorMenloFcStatsHistEntry 10 }

cucsAdaptorMenloFcStatsHistDropOverrunDeltaAvg OBJECT-TYPE
    SYNTAX       Unsigned64
    MAX-ACCESS   read-only
    STATUS       current
    DESCRIPTION
        "Cisco UCS adaptor:MenloFcStatsHist:dropOverrunDeltaAvg
        managed object property"
    ::= { cucsAdaptorMenloFcStatsHistEntry 11 }

cucsAdaptorMenloFcStatsHistDropOverrunDeltaMax OBJECT-TYPE
    SYNTAX       Unsigned64
    MAX-ACCESS   read-only
    STATUS       current
    DESCRIPTION
        "Cisco UCS adaptor:MenloFcStatsHist:dropOverrunDeltaMax
        managed object property"
    ::= { cucsAdaptorMenloFcStatsHistEntry 12 }

cucsAdaptorMenloFcStatsHistDropOverrunDeltaMin OBJECT-TYPE
    SYNTAX       Unsigned64
    MAX-ACCESS   read-only
    STATUS       current
    DESCRIPTION
        "Cisco UCS adaptor:MenloFcStatsHist:dropOverrunDeltaMin
        managed object property"
    ::= { cucsAdaptorMenloFcStatsHistEntry 13 }

cucsAdaptorMenloFcStatsHistDropRunt OBJECT-TYPE
    SYNTAX       Unsigned64
    MAX-ACCESS   read-only
    STATUS       current
    DESCRIPTION
        "Cisco UCS adaptor:MenloFcStatsHist:dropRunt managed
        object property"
    ::= { cucsAdaptorMenloFcStatsHistEntry 14 }

cucsAdaptorMenloFcStatsHistDropRuntDelta OBJECT-TYPE
    SYNTAX       Unsigned64
    MAX-ACCESS   read-only
    STATUS       current
    DESCRIPTION
        "Cisco UCS adaptor:MenloFcStatsHist:dropRuntDelta
        managed object property"
    ::= { cucsAdaptorMenloFcStatsHistEntry 15 }

cucsAdaptorMenloFcStatsHistDropRuntDeltaAvg OBJECT-TYPE
    SYNTAX       Unsigned64
    MAX-ACCESS   read-only
    STATUS       current
    DESCRIPTION
        "Cisco UCS adaptor:MenloFcStatsHist:dropRuntDeltaAvg
        managed object property"
    ::= { cucsAdaptorMenloFcStatsHistEntry 16 }

cucsAdaptorMenloFcStatsHistDropRuntDeltaMax OBJECT-TYPE
    SYNTAX       Unsigned64
    MAX-ACCESS   read-only
    STATUS       current
    DESCRIPTION
        "Cisco UCS adaptor:MenloFcStatsHist:dropRuntDeltaMax
        managed object property"
    ::= { cucsAdaptorMenloFcStatsHistEntry 17 }

cucsAdaptorMenloFcStatsHistDropRuntDeltaMin OBJECT-TYPE
    SYNTAX       Unsigned64
    MAX-ACCESS   read-only
    STATUS       current
    DESCRIPTION
        "Cisco UCS adaptor:MenloFcStatsHist:dropRuntDeltaMin
        managed object property"
    ::= { cucsAdaptorMenloFcStatsHistEntry 18 }

cucsAdaptorMenloFcStatsHistId OBJECT-TYPE
    SYNTAX       Unsigned64
    MAX-ACCESS   read-only
    STATUS       current
    DESCRIPTION
        "Cisco UCS adaptor:MenloFcStatsHist:id managed object property"
    ::= { cucsAdaptorMenloFcStatsHistEntry 19 }

cucsAdaptorMenloFcStatsHistMostRecent OBJECT-TYPE
    SYNTAX       TruthValue
    MAX-ACCESS   read-only
    STATUS       current
    DESCRIPTION
        "Cisco UCS adaptor:MenloFcStatsHist:mostRecent
        managed object property"
    ::= { cucsAdaptorMenloFcStatsHistEntry 20 }

cucsAdaptorMenloFcStatsHistSuspect OBJECT-TYPE
    SYNTAX       TruthValue
    MAX-ACCESS   read-only
    STATUS       current
    DESCRIPTION
        "Cisco UCS adaptor:MenloFcStatsHist:suspect managed
        object property"
    ::= { cucsAdaptorMenloFcStatsHistEntry 21 }

cucsAdaptorMenloFcStatsHistThresholded OBJECT-TYPE
    SYNTAX       CucsAdaptorMenloFcStatsHistThresholded
    MAX-ACCESS   read-only
    STATUS       current
    DESCRIPTION
        "Cisco UCS adaptor:MenloFcStatsHist:thresholded
        managed object property"
    ::= { cucsAdaptorMenloFcStatsHistEntry 22 }

cucsAdaptorMenloFcStatsHistTimeCollected OBJECT-TYPE
    SYNTAX       DateAndTime
    MAX-ACCESS   read-only
    STATUS       current
    DESCRIPTION
        "Cisco UCS adaptor:MenloFcStatsHist:timeCollected
        managed object property"
    ::= { cucsAdaptorMenloFcStatsHistEntry 23 }

cucsAdaptorMenloFcStatsHistTruncateOverrun OBJECT-TYPE
    SYNTAX       Unsigned64
    MAX-ACCESS   read-only
    STATUS       current
    DESCRIPTION
        "Cisco UCS adaptor:MenloFcStatsHist:truncateOverrun
        managed object property"
    ::= { cucsAdaptorMenloFcStatsHistEntry 24 }

cucsAdaptorMenloFcStatsHistTruncateOverrunDelta OBJECT-TYPE
    SYNTAX       Unsigned64
    MAX-ACCESS   read-only
    STATUS       current
    DESCRIPTION
        "Cisco UCS adaptor:MenloFcStatsHist:truncateOverrunDelta
        managed object property"
    ::= { cucsAdaptorMenloFcStatsHistEntry 25 }

cucsAdaptorMenloFcStatsHistTruncateOverrunDeltaAvg OBJECT-TYPE
    SYNTAX       Unsigned64
    MAX-ACCESS   read-only
    STATUS       current
    DESCRIPTION
        "Cisco UCS adaptor:MenloFcStatsHist:truncateOverrunDeltaAvg
        managed object property"
    ::= { cucsAdaptorMenloFcStatsHistEntry 26 }

cucsAdaptorMenloFcStatsHistTruncateOverrunDeltaMax OBJECT-TYPE
    SYNTAX       Unsigned64
    MAX-ACCESS   read-only
    STATUS       current
    DESCRIPTION
        "Cisco UCS adaptor:MenloFcStatsHist:truncateOverrunDeltaMax
        managed object property"
    ::= { cucsAdaptorMenloFcStatsHistEntry 27 }

cucsAdaptorMenloFcStatsHistTruncateOverrunDeltaMin OBJECT-TYPE
    SYNTAX       Unsigned64
    MAX-ACCESS   read-only
    STATUS       current
    DESCRIPTION
        "Cisco UCS adaptor:MenloFcStatsHist:truncateOverrunDeltaMin
        managed object property"
    ::= { cucsAdaptorMenloFcStatsHistEntry 28 }

cucsAdaptorMenloHostPortStatsTable OBJECT-TYPE
    SYNTAX           SEQUENCE OF CucsAdaptorMenloHostPortStatsEntry
    MAX-ACCESS       not-accessible
    STATUS           current
    DESCRIPTION
        "Cisco UCS adaptor:MenloHostPortStats managed object table"
    ::= { cucsAdaptorObjects 67 }

cucsAdaptorMenloHostPortStatsEntry OBJECT-TYPE
    SYNTAX           CucsAdaptorMenloHostPortStatsEntry
    MAX-ACCESS       not-accessible
    STATUS           current
    DESCRIPTION
        "Entry for the cucsAdaptorMenloHostPortStatsTable table."
    INDEX { cucsAdaptorMenloHostPortStatsInstanceId }
    ::= { cucsAdaptorMenloHostPortStatsTable 1 }

CucsAdaptorMenloHostPortStatsEntry ::= SEQUENCE {
    cucsAdaptorMenloHostPortStatsInstanceId                          CucsManagedObjectId,
    cucsAdaptorMenloHostPortStatsDn                                  CucsManagedObjectDn,
    cucsAdaptorMenloHostPortStatsRn                                  SnmpAdminString,
    cucsAdaptorMenloHostPortStatsIntervals                           Gauge32,
    cucsAdaptorMenloHostPortStatsMenloPortIndex                      CucsAdaptorMenloStatsIndex,
    cucsAdaptorMenloHostPortStatsRxPauseCFC                          Unsigned64,
    cucsAdaptorMenloHostPortStatsRxPauseCFCDelta                     Counter64,
    cucsAdaptorMenloHostPortStatsRxPauseCFCDeltaAvg                  Unsigned64,
    cucsAdaptorMenloHostPortStatsRxPauseCFCDeltaMax                  Unsigned64,
    cucsAdaptorMenloHostPortStatsRxPauseCFCDeltaMin                  Unsigned64,
    cucsAdaptorMenloHostPortStatsRxPausePFC                          Unsigned64,
    cucsAdaptorMenloHostPortStatsRxPausePFCDelta                     Counter64,
    cucsAdaptorMenloHostPortStatsRxPausePFCDeltaAvg                  Unsigned64,
    cucsAdaptorMenloHostPortStatsRxPausePFCDeltaMax                  Unsigned64,
    cucsAdaptorMenloHostPortStatsRxPausePFCDeltaMin                  Unsigned64,
    cucsAdaptorMenloHostPortStatsSuspect                             TruthValue,
    cucsAdaptorMenloHostPortStatsThresholded                         CucsAdaptorMenloHostPortStatsThresholded,
    cucsAdaptorMenloHostPortStatsTimeCollected                       DateAndTime,
    cucsAdaptorMenloHostPortStatsTxPauseCFC                          Unsigned64,
    cucsAdaptorMenloHostPortStatsTxPauseCFCDelta                     Counter64,
    cucsAdaptorMenloHostPortStatsTxPauseCFCDeltaAvg                  Unsigned64,
    cucsAdaptorMenloHostPortStatsTxPauseCFCDeltaMax                  Unsigned64,
    cucsAdaptorMenloHostPortStatsTxPauseCFCDeltaMin                  Unsigned64,
    cucsAdaptorMenloHostPortStatsTxPausePFC                          Unsigned64,
    cucsAdaptorMenloHostPortStatsTxPausePFCDelta                     Counter64,
    cucsAdaptorMenloHostPortStatsTxPausePFCDeltaAvg                  Unsigned64,
    cucsAdaptorMenloHostPortStatsTxPausePFCDeltaMax                  Unsigned64,
    cucsAdaptorMenloHostPortStatsTxPausePFCDeltaMin                  Unsigned64,
    cucsAdaptorMenloHostPortStatsUpdate                              Gauge32
}

cucsAdaptorMenloHostPortStatsInstanceId OBJECT-TYPE
    SYNTAX       CucsManagedObjectId
    MAX-ACCESS   not-accessible
    STATUS       current
    DESCRIPTION
        "Instance identifier of the managed object."
    ::= { cucsAdaptorMenloHostPortStatsEntry 1 }

cucsAdaptorMenloHostPortStatsDn OBJECT-TYPE
    SYNTAX       CucsManagedObjectDn
    MAX-ACCESS   read-only
    STATUS       current
    DESCRIPTION
        "Cisco UCS adaptor:MenloHostPortStats:dn managed object property"
    ::= { cucsAdaptorMenloHostPortStatsEntry 2 }

cucsAdaptorMenloHostPortStatsRn OBJECT-TYPE
    SYNTAX       SnmpAdminString
    MAX-ACCESS   read-only
    STATUS       current
    DESCRIPTION
        "Cisco UCS adaptor:MenloHostPortStats:rn managed object property"
    ::= { cucsAdaptorMenloHostPortStatsEntry 3 }

cucsAdaptorMenloHostPortStatsIntervals OBJECT-TYPE
    SYNTAX       Gauge32
    MAX-ACCESS   read-only
    STATUS       current
    DESCRIPTION
        "Cisco UCS adaptor:MenloHostPortStats:intervals
        managed object property"
    ::= { cucsAdaptorMenloHostPortStatsEntry 4 }

cucsAdaptorMenloHostPortStatsMenloPortIndex OBJECT-TYPE
    SYNTAX       CucsAdaptorMenloStatsIndex
    MAX-ACCESS   read-only
    STATUS       current
    DESCRIPTION
        "Cisco UCS adaptor:MenloHostPortStats:menloPortIndex
        managed object property"
    ::= { cucsAdaptorMenloHostPortStatsEntry 5 }

cucsAdaptorMenloHostPortStatsRxPauseCFC OBJECT-TYPE
    SYNTAX       Unsigned64
    MAX-ACCESS   read-only
    STATUS       current
    DESCRIPTION
        "Cisco UCS adaptor:MenloHostPortStats:rxPauseCFC
        managed object property"
    ::= { cucsAdaptorMenloHostPortStatsEntry 6 }

cucsAdaptorMenloHostPortStatsRxPauseCFCDelta OBJECT-TYPE
    SYNTAX       Counter64
    MAX-ACCESS   read-only
    STATUS       current
    DESCRIPTION
        "Cisco UCS adaptor:MenloHostPortStats:rxPauseCFCDelta
        managed object property"
    ::= { cucsAdaptorMenloHostPortStatsEntry 7 }

cucsAdaptorMenloHostPortStatsRxPauseCFCDeltaAvg OBJECT-TYPE
    SYNTAX       Unsigned64
    MAX-ACCESS   read-only
    STATUS       current
    DESCRIPTION
        "Cisco UCS adaptor:MenloHostPortStats:rxPauseCFCDeltaAvg
        managed object property"
    ::= { cucsAdaptorMenloHostPortStatsEntry 8 }

cucsAdaptorMenloHostPortStatsRxPauseCFCDeltaMax OBJECT-TYPE
    SYNTAX       Unsigned64
    MAX-ACCESS   read-only
    STATUS       current
    DESCRIPTION
        "Cisco UCS adaptor:MenloHostPortStats:rxPauseCFCDeltaMax
        managed object property"
    ::= { cucsAdaptorMenloHostPortStatsEntry 9 }

cucsAdaptorMenloHostPortStatsRxPauseCFCDeltaMin OBJECT-TYPE
    SYNTAX       Unsigned64
    MAX-ACCESS   read-only
    STATUS       current
    DESCRIPTION
        "Cisco UCS adaptor:MenloHostPortStats:rxPauseCFCDeltaMin
        managed object property"
    ::= { cucsAdaptorMenloHostPortStatsEntry 10 }

cucsAdaptorMenloHostPortStatsRxPausePFC OBJECT-TYPE
    SYNTAX       Unsigned64
    MAX-ACCESS   read-only
    STATUS       current
    DESCRIPTION
        "Cisco UCS adaptor:MenloHostPortStats:rxPausePFC
        managed object property"
    ::= { cucsAdaptorMenloHostPortStatsEntry 11 }

cucsAdaptorMenloHostPortStatsRxPausePFCDelta OBJECT-TYPE
    SYNTAX       Counter64
    MAX-ACCESS   read-only
    STATUS       current
    DESCRIPTION
        "Cisco UCS adaptor:MenloHostPortStats:rxPausePFCDelta
        managed object property"
    ::= { cucsAdaptorMenloHostPortStatsEntry 12 }

cucsAdaptorMenloHostPortStatsRxPausePFCDeltaAvg OBJECT-TYPE
    SYNTAX       Unsigned64
    MAX-ACCESS   read-only
    STATUS       current
    DESCRIPTION
        "Cisco UCS adaptor:MenloHostPortStats:rxPausePFCDeltaAvg
        managed object property"
    ::= { cucsAdaptorMenloHostPortStatsEntry 13 }

cucsAdaptorMenloHostPortStatsRxPausePFCDeltaMax OBJECT-TYPE
    SYNTAX       Unsigned64
    MAX-ACCESS   read-only
    STATUS       current
    DESCRIPTION
        "Cisco UCS adaptor:MenloHostPortStats:rxPausePFCDeltaMax
        managed object property"
    ::= { cucsAdaptorMenloHostPortStatsEntry 14 }

cucsAdaptorMenloHostPortStatsRxPausePFCDeltaMin OBJECT-TYPE
    SYNTAX       Unsigned64
    MAX-ACCESS   read-only
    STATUS       current
    DESCRIPTION
        "Cisco UCS adaptor:MenloHostPortStats:rxPausePFCDeltaMin
        managed object property"
    ::= { cucsAdaptorMenloHostPortStatsEntry 15 }

cucsAdaptorMenloHostPortStatsSuspect OBJECT-TYPE
    SYNTAX       TruthValue
    MAX-ACCESS   read-only
    STATUS       current
    DESCRIPTION
        "Cisco UCS adaptor:MenloHostPortStats:suspect managed
        object property"
    ::= { cucsAdaptorMenloHostPortStatsEntry 16 }

cucsAdaptorMenloHostPortStatsThresholded OBJECT-TYPE
    SYNTAX       CucsAdaptorMenloHostPortStatsThresholded
    MAX-ACCESS   read-only
    STATUS       current
    DESCRIPTION
        "Cisco UCS adaptor:MenloHostPortStats:thresholded
        managed object property"
    ::= { cucsAdaptorMenloHostPortStatsEntry 17 }

cucsAdaptorMenloHostPortStatsTimeCollected OBJECT-TYPE
    SYNTAX       DateAndTime
    MAX-ACCESS   read-only
    STATUS       current
    DESCRIPTION
        "Cisco UCS adaptor:MenloHostPortStats:timeCollected
        managed object property"
    ::= { cucsAdaptorMenloHostPortStatsEntry 18 }

cucsAdaptorMenloHostPortStatsTxPauseCFC OBJECT-TYPE
    SYNTAX       Unsigned64
    MAX-ACCESS   read-only
    STATUS       current
    DESCRIPTION
        "Cisco UCS adaptor:MenloHostPortStats:txPauseCFC
        managed object property"
    ::= { cucsAdaptorMenloHostPortStatsEntry 19 }

cucsAdaptorMenloHostPortStatsTxPauseCFCDelta OBJECT-TYPE
    SYNTAX       Counter64
    MAX-ACCESS   read-only
    STATUS       current
    DESCRIPTION
        "Cisco UCS adaptor:MenloHostPortStats:txPauseCFCDelta
        managed object property"
    ::= { cucsAdaptorMenloHostPortStatsEntry 20 }

cucsAdaptorMenloHostPortStatsTxPauseCFCDeltaAvg OBJECT-TYPE
    SYNTAX       Unsigned64
    MAX-ACCESS   read-only
    STATUS       current
    DESCRIPTION
        "Cisco UCS adaptor:MenloHostPortStats:txPauseCFCDeltaAvg
        managed object property"
    ::= { cucsAdaptorMenloHostPortStatsEntry 21 }

cucsAdaptorMenloHostPortStatsTxPauseCFCDeltaMax OBJECT-TYPE
    SYNTAX       Unsigned64
    MAX-ACCESS   read-only
    STATUS       current
    DESCRIPTION
        "Cisco UCS adaptor:MenloHostPortStats:txPauseCFCDeltaMax
        managed object property"
    ::= { cucsAdaptorMenloHostPortStatsEntry 22 }

cucsAdaptorMenloHostPortStatsTxPauseCFCDeltaMin OBJECT-TYPE
    SYNTAX       Unsigned64
    MAX-ACCESS   read-only
    STATUS       current
    DESCRIPTION
        "Cisco UCS adaptor:MenloHostPortStats:txPauseCFCDeltaMin
        managed object property"
    ::= { cucsAdaptorMenloHostPortStatsEntry 23 }

cucsAdaptorMenloHostPortStatsTxPausePFC OBJECT-TYPE
    SYNTAX       Unsigned64
    MAX-ACCESS   read-only
    STATUS       current
    DESCRIPTION
        "Cisco UCS adaptor:MenloHostPortStats:txPausePFC
        managed object property"
    ::= { cucsAdaptorMenloHostPortStatsEntry 24 }

cucsAdaptorMenloHostPortStatsTxPausePFCDelta OBJECT-TYPE
    SYNTAX       Counter64
    MAX-ACCESS   read-only
    STATUS       current
    DESCRIPTION
        "Cisco UCS adaptor:MenloHostPortStats:txPausePFCDelta
        managed object property"
    ::= { cucsAdaptorMenloHostPortStatsEntry 25 }

cucsAdaptorMenloHostPortStatsTxPausePFCDeltaAvg OBJECT-TYPE
    SYNTAX       Unsigned64
    MAX-ACCESS   read-only
    STATUS       current
    DESCRIPTION
        "Cisco UCS adaptor:MenloHostPortStats:txPausePFCDeltaAvg
        managed object property"
    ::= { cucsAdaptorMenloHostPortStatsEntry 26 }

cucsAdaptorMenloHostPortStatsTxPausePFCDeltaMax OBJECT-TYPE
    SYNTAX       Unsigned64
    MAX-ACCESS   read-only
    STATUS       current
    DESCRIPTION
        "Cisco UCS adaptor:MenloHostPortStats:txPausePFCDeltaMax
        managed object property"
    ::= { cucsAdaptorMenloHostPortStatsEntry 27 }

cucsAdaptorMenloHostPortStatsTxPausePFCDeltaMin OBJECT-TYPE
    SYNTAX       Unsigned64
    MAX-ACCESS   read-only
    STATUS       current
    DESCRIPTION
        "Cisco UCS adaptor:MenloHostPortStats:txPausePFCDeltaMin
        managed object property"
    ::= { cucsAdaptorMenloHostPortStatsEntry 28 }

cucsAdaptorMenloHostPortStatsUpdate OBJECT-TYPE
    SYNTAX       Gauge32
    MAX-ACCESS   read-only
    STATUS       current
    DESCRIPTION
        "Cisco UCS adaptor:MenloHostPortStats:update managed
        object property"
    ::= { cucsAdaptorMenloHostPortStatsEntry 29 }

cucsAdaptorMenloHostPortStatsHistTable OBJECT-TYPE
    SYNTAX           SEQUENCE OF CucsAdaptorMenloHostPortStatsHistEntry
    MAX-ACCESS       not-accessible
    STATUS           current
    DESCRIPTION
        "Cisco UCS adaptor:MenloHostPortStatsHist managed object table"
    ::= { cucsAdaptorObjects 68 }

cucsAdaptorMenloHostPortStatsHistEntry OBJECT-TYPE
    SYNTAX           CucsAdaptorMenloHostPortStatsHistEntry
    MAX-ACCESS       not-accessible
    STATUS           current
    DESCRIPTION
        "Entry for the cucsAdaptorMenloHostPortStatsHistTable table."
    INDEX { cucsAdaptorMenloHostPortStatsHistInstanceId }
    ::= { cucsAdaptorMenloHostPortStatsHistTable 1 }

CucsAdaptorMenloHostPortStatsHistEntry ::= SEQUENCE {
    cucsAdaptorMenloHostPortStatsHistInstanceId                      CucsManagedObjectId,
    cucsAdaptorMenloHostPortStatsHistDn                              CucsManagedObjectDn,
    cucsAdaptorMenloHostPortStatsHistRn                              SnmpAdminString,
    cucsAdaptorMenloHostPortStatsHistId                              Unsigned64,
    cucsAdaptorMenloHostPortStatsHistMostRecent                      TruthValue,
    cucsAdaptorMenloHostPortStatsHistRxPauseCFC                      Unsigned64,
    cucsAdaptorMenloHostPortStatsHistRxPauseCFCDelta                 Unsigned64,
    cucsAdaptorMenloHostPortStatsHistRxPauseCFCDeltaAvg              Unsigned64,
    cucsAdaptorMenloHostPortStatsHistRxPauseCFCDeltaMax              Unsigned64,
    cucsAdaptorMenloHostPortStatsHistRxPauseCFCDeltaMin              Unsigned64,
    cucsAdaptorMenloHostPortStatsHistRxPausePFC                      Unsigned64,
    cucsAdaptorMenloHostPortStatsHistRxPausePFCDelta                 Unsigned64,
    cucsAdaptorMenloHostPortStatsHistRxPausePFCDeltaAvg              Unsigned64,
    cucsAdaptorMenloHostPortStatsHistRxPausePFCDeltaMax              Unsigned64,
    cucsAdaptorMenloHostPortStatsHistRxPausePFCDeltaMin              Unsigned64,
    cucsAdaptorMenloHostPortStatsHistSuspect                         TruthValue,
    cucsAdaptorMenloHostPortStatsHistThresholded                     CucsAdaptorMenloHostPortStatsHistThresholded,
    cucsAdaptorMenloHostPortStatsHistTimeCollected                   DateAndTime,
    cucsAdaptorMenloHostPortStatsHistTxPauseCFC                      Unsigned64,
    cucsAdaptorMenloHostPortStatsHistTxPauseCFCDelta                 Unsigned64,
    cucsAdaptorMenloHostPortStatsHistTxPauseCFCDeltaAvg              Unsigned64,
    cucsAdaptorMenloHostPortStatsHistTxPauseCFCDeltaMax              Unsigned64,
    cucsAdaptorMenloHostPortStatsHistTxPauseCFCDeltaMin              Unsigned64,
    cucsAdaptorMenloHostPortStatsHistTxPausePFC                      Unsigned64,
    cucsAdaptorMenloHostPortStatsHistTxPausePFCDelta                 Unsigned64,
    cucsAdaptorMenloHostPortStatsHistTxPausePFCDeltaAvg              Unsigned64,
    cucsAdaptorMenloHostPortStatsHistTxPausePFCDeltaMax              Unsigned64,
    cucsAdaptorMenloHostPortStatsHistTxPausePFCDeltaMin              Unsigned64
}

cucsAdaptorMenloHostPortStatsHistInstanceId OBJECT-TYPE
    SYNTAX       CucsManagedObjectId
    MAX-ACCESS   not-accessible
    STATUS       current
    DESCRIPTION
        "Instance identifier of the managed object."
    ::= { cucsAdaptorMenloHostPortStatsHistEntry 1 }

cucsAdaptorMenloHostPortStatsHistDn OBJECT-TYPE
    SYNTAX       CucsManagedObjectDn
    MAX-ACCESS   read-only
    STATUS       current
    DESCRIPTION
        "Cisco UCS adaptor:MenloHostPortStatsHist:dn managed
        object property"
    ::= { cucsAdaptorMenloHostPortStatsHistEntry 2 }

cucsAdaptorMenloHostPortStatsHistRn OBJECT-TYPE
    SYNTAX       SnmpAdminString
    MAX-ACCESS   read-only
    STATUS       current
    DESCRIPTION
        "Cisco UCS adaptor:MenloHostPortStatsHist:rn managed
        object property"
    ::= { cucsAdaptorMenloHostPortStatsHistEntry 3 }

cucsAdaptorMenloHostPortStatsHistId OBJECT-TYPE
    SYNTAX       Unsigned64
    MAX-ACCESS   read-only
    STATUS       current
    DESCRIPTION
        "Cisco UCS adaptor:MenloHostPortStatsHist:id managed
        object property"
    ::= { cucsAdaptorMenloHostPortStatsHistEntry 4 }

cucsAdaptorMenloHostPortStatsHistMostRecent OBJECT-TYPE
    SYNTAX       TruthValue
    MAX-ACCESS   read-only
    STATUS       current
    DESCRIPTION
        "Cisco UCS adaptor:MenloHostPortStatsHist:mostRecent
        managed object property"
    ::= { cucsAdaptorMenloHostPortStatsHistEntry 5 }

cucsAdaptorMenloHostPortStatsHistRxPauseCFC OBJECT-TYPE
    SYNTAX       Unsigned64
    MAX-ACCESS   read-only
    STATUS       current
    DESCRIPTION
        "Cisco UCS adaptor:MenloHostPortStatsHist:rxPauseCFC
        managed object property"
    ::= { cucsAdaptorMenloHostPortStatsHistEntry 6 }

cucsAdaptorMenloHostPortStatsHistRxPauseCFCDelta OBJECT-TYPE
    SYNTAX       Unsigned64
    MAX-ACCESS   read-only
    STATUS       current
    DESCRIPTION
        "Cisco UCS adaptor:MenloHostPortStatsHist:rxPauseCFCDelta
        managed object property"
    ::= { cucsAdaptorMenloHostPortStatsHistEntry 7 }

cucsAdaptorMenloHostPortStatsHistRxPauseCFCDeltaAvg OBJECT-TYPE
    SYNTAX       Unsigned64
    MAX-ACCESS   read-only
    STATUS       current
    DESCRIPTION
        "Cisco UCS adaptor:MenloHostPortStatsHist:rxPauseCFCDeltaAvg
        managed object property"
    ::= { cucsAdaptorMenloHostPortStatsHistEntry 8 }

cucsAdaptorMenloHostPortStatsHistRxPauseCFCDeltaMax OBJECT-TYPE
    SYNTAX       Unsigned64
    MAX-ACCESS   read-only
    STATUS       current
    DESCRIPTION
        "Cisco UCS adaptor:MenloHostPortStatsHist:rxPauseCFCDeltaMax
        managed object property"
    ::= { cucsAdaptorMenloHostPortStatsHistEntry 9 }

cucsAdaptorMenloHostPortStatsHistRxPauseCFCDeltaMin OBJECT-TYPE
    SYNTAX       Unsigned64
    MAX-ACCESS   read-only
    STATUS       current
    DESCRIPTION
        "Cisco UCS adaptor:MenloHostPortStatsHist:rxPauseCFCDeltaMin
        managed object property"
    ::= { cucsAdaptorMenloHostPortStatsHistEntry 10 }

cucsAdaptorMenloHostPortStatsHistRxPausePFC OBJECT-TYPE
    SYNTAX       Unsigned64
    MAX-ACCESS   read-only
    STATUS       current
    DESCRIPTION
        "Cisco UCS adaptor:MenloHostPortStatsHist:rxPausePFC
        managed object property"
    ::= { cucsAdaptorMenloHostPortStatsHistEntry 11 }

cucsAdaptorMenloHostPortStatsHistRxPausePFCDelta OBJECT-TYPE
    SYNTAX       Unsigned64
    MAX-ACCESS   read-only
    STATUS       current
    DESCRIPTION
        "Cisco UCS adaptor:MenloHostPortStatsHist:rxPausePFCDelta
        managed object property"
    ::= { cucsAdaptorMenloHostPortStatsHistEntry 12 }

cucsAdaptorMenloHostPortStatsHistRxPausePFCDeltaAvg OBJECT-TYPE
    SYNTAX       Unsigned64
    MAX-ACCESS   read-only
    STATUS       current
    DESCRIPTION
        "Cisco UCS adaptor:MenloHostPortStatsHist:rxPausePFCDeltaAvg
        managed object property"
    ::= { cucsAdaptorMenloHostPortStatsHistEntry 13 }

cucsAdaptorMenloHostPortStatsHistRxPausePFCDeltaMax OBJECT-TYPE
    SYNTAX       Unsigned64
    MAX-ACCESS   read-only
    STATUS       current
    DESCRIPTION
        "Cisco UCS adaptor:MenloHostPortStatsHist:rxPausePFCDeltaMax
        managed object property"
    ::= { cucsAdaptorMenloHostPortStatsHistEntry 14 }

cucsAdaptorMenloHostPortStatsHistRxPausePFCDeltaMin OBJECT-TYPE
    SYNTAX       Unsigned64
    MAX-ACCESS   read-only
    STATUS       current
    DESCRIPTION
        "Cisco UCS adaptor:MenloHostPortStatsHist:rxPausePFCDeltaMin
        managed object property"
    ::= { cucsAdaptorMenloHostPortStatsHistEntry 15 }

cucsAdaptorMenloHostPortStatsHistSuspect OBJECT-TYPE
    SYNTAX       TruthValue
    MAX-ACCESS   read-only
    STATUS       current
    DESCRIPTION
        "Cisco UCS adaptor:MenloHostPortStatsHist:suspect
        managed object property"
    ::= { cucsAdaptorMenloHostPortStatsHistEntry 16 }

cucsAdaptorMenloHostPortStatsHistThresholded OBJECT-TYPE
    SYNTAX       CucsAdaptorMenloHostPortStatsHistThresholded
    MAX-ACCESS   read-only
    STATUS       current
    DESCRIPTION
        "Cisco UCS adaptor:MenloHostPortStatsHist:thresholded
        managed object property"
    ::= { cucsAdaptorMenloHostPortStatsHistEntry 17 }

cucsAdaptorMenloHostPortStatsHistTimeCollected OBJECT-TYPE
    SYNTAX       DateAndTime
    MAX-ACCESS   read-only
    STATUS       current
    DESCRIPTION
        "Cisco UCS adaptor:MenloHostPortStatsHist:timeCollected
        managed object property"
    ::= { cucsAdaptorMenloHostPortStatsHistEntry 18 }

cucsAdaptorMenloHostPortStatsHistTxPauseCFC OBJECT-TYPE
    SYNTAX       Unsigned64
    MAX-ACCESS   read-only
    STATUS       current
    DESCRIPTION
        "Cisco UCS adaptor:MenloHostPortStatsHist:txPauseCFC
        managed object property"
    ::= { cucsAdaptorMenloHostPortStatsHistEntry 19 }

cucsAdaptorMenloHostPortStatsHistTxPauseCFCDelta OBJECT-TYPE
    SYNTAX       Unsigned64
    MAX-ACCESS   read-only
    STATUS       current
    DESCRIPTION
        "Cisco UCS adaptor:MenloHostPortStatsHist:txPauseCFCDelta
        managed object property"
    ::= { cucsAdaptorMenloHostPortStatsHistEntry 20 }

cucsAdaptorMenloHostPortStatsHistTxPauseCFCDeltaAvg OBJECT-TYPE
    SYNTAX       Unsigned64
    MAX-ACCESS   read-only
    STATUS       current
    DESCRIPTION
        "Cisco UCS adaptor:MenloHostPortStatsHist:txPauseCFCDeltaAvg
        managed object property"
    ::= { cucsAdaptorMenloHostPortStatsHistEntry 21 }

cucsAdaptorMenloHostPortStatsHistTxPauseCFCDeltaMax OBJECT-TYPE
    SYNTAX       Unsigned64
    MAX-ACCESS   read-only
    STATUS       current
    DESCRIPTION
        "Cisco UCS adaptor:MenloHostPortStatsHist:txPauseCFCDeltaMax
        managed object property"
    ::= { cucsAdaptorMenloHostPortStatsHistEntry 22 }

cucsAdaptorMenloHostPortStatsHistTxPauseCFCDeltaMin OBJECT-TYPE
    SYNTAX       Unsigned64
    MAX-ACCESS   read-only
    STATUS       current
    DESCRIPTION
        "Cisco UCS adaptor:MenloHostPortStatsHist:txPauseCFCDeltaMin
        managed object property"
    ::= { cucsAdaptorMenloHostPortStatsHistEntry 23 }

cucsAdaptorMenloHostPortStatsHistTxPausePFC OBJECT-TYPE
    SYNTAX       Unsigned64
    MAX-ACCESS   read-only
    STATUS       current
    DESCRIPTION
        "Cisco UCS adaptor:MenloHostPortStatsHist:txPausePFC
        managed object property"
    ::= { cucsAdaptorMenloHostPortStatsHistEntry 24 }

cucsAdaptorMenloHostPortStatsHistTxPausePFCDelta OBJECT-TYPE
    SYNTAX       Unsigned64
    MAX-ACCESS   read-only
    STATUS       current
    DESCRIPTION
        "Cisco UCS adaptor:MenloHostPortStatsHist:txPausePFCDelta
        managed object property"
    ::= { cucsAdaptorMenloHostPortStatsHistEntry 25 }

cucsAdaptorMenloHostPortStatsHistTxPausePFCDeltaAvg OBJECT-TYPE
    SYNTAX       Unsigned64
    MAX-ACCESS   read-only
    STATUS       current
    DESCRIPTION
        "Cisco UCS adaptor:MenloHostPortStatsHist:txPausePFCDeltaAvg
        managed object property"
    ::= { cucsAdaptorMenloHostPortStatsHistEntry 26 }

cucsAdaptorMenloHostPortStatsHistTxPausePFCDeltaMax OBJECT-TYPE
    SYNTAX       Unsigned64
    MAX-ACCESS   read-only
    STATUS       current
    DESCRIPTION
        "Cisco UCS adaptor:MenloHostPortStatsHist:txPausePFCDeltaMax
        managed object property"
    ::= { cucsAdaptorMenloHostPortStatsHistEntry 27 }

cucsAdaptorMenloHostPortStatsHistTxPausePFCDeltaMin OBJECT-TYPE
    SYNTAX       Unsigned64
    MAX-ACCESS   read-only
    STATUS       current
    DESCRIPTION
        "Cisco UCS adaptor:MenloHostPortStatsHist:txPausePFCDeltaMin
        managed object property"
    ::= { cucsAdaptorMenloHostPortStatsHistEntry 28 }

cucsAdaptorMenloMcpuErrorStatsTable OBJECT-TYPE
    SYNTAX           SEQUENCE OF CucsAdaptorMenloMcpuErrorStatsEntry
    MAX-ACCESS       not-accessible
    STATUS           current
    DESCRIPTION
        "Cisco UCS adaptor:MenloMcpuErrorStats managed object table"
    ::= { cucsAdaptorObjects 69 }

cucsAdaptorMenloMcpuErrorStatsEntry OBJECT-TYPE
    SYNTAX           CucsAdaptorMenloMcpuErrorStatsEntry
    MAX-ACCESS       not-accessible
    STATUS           current
    DESCRIPTION
        "Entry for the cucsAdaptorMenloMcpuErrorStatsTable table."
    INDEX { cucsAdaptorMenloMcpuErrorStatsInstanceId }
    ::= { cucsAdaptorMenloMcpuErrorStatsTable 1 }

CucsAdaptorMenloMcpuErrorStatsEntry ::= SEQUENCE {
    cucsAdaptorMenloMcpuErrorStatsInstanceId                         CucsManagedObjectId,
    cucsAdaptorMenloMcpuErrorStatsDn                                 CucsManagedObjectDn,
    cucsAdaptorMenloMcpuErrorStatsRn                                 SnmpAdminString,
    cucsAdaptorMenloMcpuErrorStatsCorrectableErrors                  Unsigned64,
    cucsAdaptorMenloMcpuErrorStatsCorrectableErrorsDelta             Counter64,
    cucsAdaptorMenloMcpuErrorStatsCorrectableErrorsDeltaAvg          Unsigned64,
    cucsAdaptorMenloMcpuErrorStatsCorrectableErrorsDeltaMax          Unsigned64,
    cucsAdaptorMenloMcpuErrorStatsCorrectableErrorsDeltaMin          Unsigned64,
    cucsAdaptorMenloMcpuErrorStatsIntervals                          Gauge32,
    cucsAdaptorMenloMcpuErrorStatsMenloMcpuIndex                     CucsAdaptorMenloStatsIndex,
    cucsAdaptorMenloMcpuErrorStatsPopErrors                          Unsigned64,
    cucsAdaptorMenloMcpuErrorStatsPopErrorsDelta                     Counter64,
    cucsAdaptorMenloMcpuErrorStatsPopErrorsDeltaAvg                  Unsigned64,
    cucsAdaptorMenloMcpuErrorStatsPopErrorsDeltaMax                  Unsigned64,
    cucsAdaptorMenloMcpuErrorStatsPopErrorsDeltaMin                  Unsigned64,
    cucsAdaptorMenloMcpuErrorStatsPushErrors                         Unsigned64,
    cucsAdaptorMenloMcpuErrorStatsPushErrorsDelta                    Counter64,
    cucsAdaptorMenloMcpuErrorStatsPushErrorsDeltaAvg                 Unsigned64,
    cucsAdaptorMenloMcpuErrorStatsPushErrorsDeltaMax                 Unsigned64,
    cucsAdaptorMenloMcpuErrorStatsPushErrorsDeltaMin                 Unsigned64,
    cucsAdaptorMenloMcpuErrorStatsSuspect                            TruthValue,
    cucsAdaptorMenloMcpuErrorStatsThresholded                        CucsAdaptorMenloMcpuErrorStatsThresholded,
    cucsAdaptorMenloMcpuErrorStatsTimeCollected                      DateAndTime,
    cucsAdaptorMenloMcpuErrorStatsUncorrectableErrors                Unsigned64,
    cucsAdaptorMenloMcpuErrorStatsUncorrectableErrorsDelta           Counter64,
    cucsAdaptorMenloMcpuErrorStatsUncorrectableErrorsDeltaAvg        Unsigned64,
    cucsAdaptorMenloMcpuErrorStatsUncorrectableErrorsDeltaMax        Unsigned64,
    cucsAdaptorMenloMcpuErrorStatsUncorrectableErrorsDeltaMin        Unsigned64,
    cucsAdaptorMenloMcpuErrorStatsUpdate                             Gauge32
}

cucsAdaptorMenloMcpuErrorStatsInstanceId OBJECT-TYPE
    SYNTAX       CucsManagedObjectId
    MAX-ACCESS   not-accessible
    STATUS       current
    DESCRIPTION
        "Instance identifier of the managed object."
    ::= { cucsAdaptorMenloMcpuErrorStatsEntry 1 }

cucsAdaptorMenloMcpuErrorStatsDn OBJECT-TYPE
    SYNTAX       CucsManagedObjectDn
    MAX-ACCESS   read-only
    STATUS       current
    DESCRIPTION
        "Cisco UCS adaptor:MenloMcpuErrorStats:dn managed object property"
    ::= { cucsAdaptorMenloMcpuErrorStatsEntry 2 }

cucsAdaptorMenloMcpuErrorStatsRn OBJECT-TYPE
    SYNTAX       SnmpAdminString
    MAX-ACCESS   read-only
    STATUS       current
    DESCRIPTION
        "Cisco UCS adaptor:MenloMcpuErrorStats:rn managed object property"
    ::= { cucsAdaptorMenloMcpuErrorStatsEntry 3 }

cucsAdaptorMenloMcpuErrorStatsCorrectableErrors OBJECT-TYPE
    SYNTAX       Unsigned64
    MAX-ACCESS   read-only
    STATUS       current
    DESCRIPTION
        "Cisco UCS adaptor:MenloMcpuErrorStats:correctableErrors
        managed object property"
    ::= { cucsAdaptorMenloMcpuErrorStatsEntry 4 }

cucsAdaptorMenloMcpuErrorStatsCorrectableErrorsDelta OBJECT-TYPE
    SYNTAX       Counter64
    MAX-ACCESS   read-only
    STATUS       current
    DESCRIPTION
        "Cisco UCS adaptor:MenloMcpuErrorStats:correctableErrorsDelta
        managed object property"
    ::= { cucsAdaptorMenloMcpuErrorStatsEntry 5 }

cucsAdaptorMenloMcpuErrorStatsCorrectableErrorsDeltaAvg OBJECT-TYPE
    SYNTAX       Unsigned64
    MAX-ACCESS   read-only
    STATUS       current
    DESCRIPTION
        "Cisco UCS adaptor:MenloMcpuErrorStats:correctableErrorsDeltaAvg
        managed object property"
    ::= { cucsAdaptorMenloMcpuErrorStatsEntry 6 }

cucsAdaptorMenloMcpuErrorStatsCorrectableErrorsDeltaMax OBJECT-TYPE
    SYNTAX       Unsigned64
    MAX-ACCESS   read-only
    STATUS       current
    DESCRIPTION
        "Cisco UCS adaptor:MenloMcpuErrorStats:correctableErrorsDeltaMax
        managed object property"
    ::= { cucsAdaptorMenloMcpuErrorStatsEntry 7 }

cucsAdaptorMenloMcpuErrorStatsCorrectableErrorsDeltaMin OBJECT-TYPE
    SYNTAX       Unsigned64
    MAX-ACCESS   read-only
    STATUS       current
    DESCRIPTION
        "Cisco UCS adaptor:MenloMcpuErrorStats:correctableErrorsDeltaMin
        managed object property"
    ::= { cucsAdaptorMenloMcpuErrorStatsEntry 8 }

cucsAdaptorMenloMcpuErrorStatsIntervals OBJECT-TYPE
    SYNTAX       Gauge32
    MAX-ACCESS   read-only
    STATUS       current
    DESCRIPTION
        "Cisco UCS adaptor:MenloMcpuErrorStats:intervals
        managed object property"
    ::= { cucsAdaptorMenloMcpuErrorStatsEntry 9 }

cucsAdaptorMenloMcpuErrorStatsMenloMcpuIndex OBJECT-TYPE
    SYNTAX       CucsAdaptorMenloStatsIndex
    MAX-ACCESS   read-only
    STATUS       current
    DESCRIPTION
        "Cisco UCS adaptor:MenloMcpuErrorStats:menloMcpuIndex
        managed object property"
    ::= { cucsAdaptorMenloMcpuErrorStatsEntry 10 }

cucsAdaptorMenloMcpuErrorStatsPopErrors OBJECT-TYPE
    SYNTAX       Unsigned64
    MAX-ACCESS   read-only
    STATUS       current
    DESCRIPTION
        "Cisco UCS adaptor:MenloMcpuErrorStats:popErrors
        managed object property"
    ::= { cucsAdaptorMenloMcpuErrorStatsEntry 11 }

cucsAdaptorMenloMcpuErrorStatsPopErrorsDelta OBJECT-TYPE
    SYNTAX       Counter64
    MAX-ACCESS   read-only
    STATUS       current
    DESCRIPTION
        "Cisco UCS adaptor:MenloMcpuErrorStats:popErrorsDelta
        managed object property"
    ::= { cucsAdaptorMenloMcpuErrorStatsEntry 12 }

cucsAdaptorMenloMcpuErrorStatsPopErrorsDeltaAvg OBJECT-TYPE
    SYNTAX       Unsigned64
    MAX-ACCESS   read-only
    STATUS       current
    DESCRIPTION
        "Cisco UCS adaptor:MenloMcpuErrorStats:popErrorsDeltaAvg
        managed object property"
    ::= { cucsAdaptorMenloMcpuErrorStatsEntry 13 }

cucsAdaptorMenloMcpuErrorStatsPopErrorsDeltaMax OBJECT-TYPE
    SYNTAX       Unsigned64
    MAX-ACCESS   read-only
    STATUS       current
    DESCRIPTION
        "Cisco UCS adaptor:MenloMcpuErrorStats:popErrorsDeltaMax
        managed object property"
    ::= { cucsAdaptorMenloMcpuErrorStatsEntry 14 }

cucsAdaptorMenloMcpuErrorStatsPopErrorsDeltaMin OBJECT-TYPE
    SYNTAX       Unsigned64
    MAX-ACCESS   read-only
    STATUS       current
    DESCRIPTION
        "Cisco UCS adaptor:MenloMcpuErrorStats:popErrorsDeltaMin
        managed object property"
    ::= { cucsAdaptorMenloMcpuErrorStatsEntry 15 }

cucsAdaptorMenloMcpuErrorStatsPushErrors OBJECT-TYPE
    SYNTAX       Unsigned64
    MAX-ACCESS   read-only
    STATUS       current
    DESCRIPTION
        "Cisco UCS adaptor:MenloMcpuErrorStats:pushErrors
        managed object property"
    ::= { cucsAdaptorMenloMcpuErrorStatsEntry 16 }

cucsAdaptorMenloMcpuErrorStatsPushErrorsDelta OBJECT-TYPE
    SYNTAX       Counter64
    MAX-ACCESS   read-only
    STATUS       current
    DESCRIPTION
        "Cisco UCS adaptor:MenloMcpuErrorStats:pushErrorsDelta
        managed object property"
    ::= { cucsAdaptorMenloMcpuErrorStatsEntry 17 }

cucsAdaptorMenloMcpuErrorStatsPushErrorsDeltaAvg OBJECT-TYPE
    SYNTAX       Unsigned64
    MAX-ACCESS   read-only
    STATUS       current
    DESCRIPTION
        "Cisco UCS adaptor:MenloMcpuErrorStats:pushErrorsDeltaAvg
        managed object property"
    ::= { cucsAdaptorMenloMcpuErrorStatsEntry 18 }

cucsAdaptorMenloMcpuErrorStatsPushErrorsDeltaMax OBJECT-TYPE
    SYNTAX       Unsigned64
    MAX-ACCESS   read-only
    STATUS       current
    DESCRIPTION
        "Cisco UCS adaptor:MenloMcpuErrorStats:pushErrorsDeltaMax
        managed object property"
    ::= { cucsAdaptorMenloMcpuErrorStatsEntry 19 }

cucsAdaptorMenloMcpuErrorStatsPushErrorsDeltaMin OBJECT-TYPE
    SYNTAX       Unsigned64
    MAX-ACCESS   read-only
    STATUS       current
    DESCRIPTION
        "Cisco UCS adaptor:MenloMcpuErrorStats:pushErrorsDeltaMin
        managed object property"
    ::= { cucsAdaptorMenloMcpuErrorStatsEntry 20 }

cucsAdaptorMenloMcpuErrorStatsSuspect OBJECT-TYPE
    SYNTAX       TruthValue
    MAX-ACCESS   read-only
    STATUS       current
    DESCRIPTION
        "Cisco UCS adaptor:MenloMcpuErrorStats:suspect
        managed object property"
    ::= { cucsAdaptorMenloMcpuErrorStatsEntry 21 }

cucsAdaptorMenloMcpuErrorStatsThresholded OBJECT-TYPE
    SYNTAX       CucsAdaptorMenloMcpuErrorStatsThresholded
    MAX-ACCESS   read-only
    STATUS       current
    DESCRIPTION
        "Cisco UCS adaptor:MenloMcpuErrorStats:thresholded
        managed object property"
    ::= { cucsAdaptorMenloMcpuErrorStatsEntry 22 }

cucsAdaptorMenloMcpuErrorStatsTimeCollected OBJECT-TYPE
    SYNTAX       DateAndTime
    MAX-ACCESS   read-only
    STATUS       current
    DESCRIPTION
        "Cisco UCS adaptor:MenloMcpuErrorStats:timeCollected
        managed object property"
    ::= { cucsAdaptorMenloMcpuErrorStatsEntry 23 }

cucsAdaptorMenloMcpuErrorStatsUncorrectableErrors OBJECT-TYPE
    SYNTAX       Unsigned64
    MAX-ACCESS   read-only
    STATUS       current
    DESCRIPTION
        "Cisco UCS adaptor:MenloMcpuErrorStats:uncorrectableErrors
        managed object property"
    ::= { cucsAdaptorMenloMcpuErrorStatsEntry 24 }

cucsAdaptorMenloMcpuErrorStatsUncorrectableErrorsDelta OBJECT-TYPE
    SYNTAX       Counter64
    MAX-ACCESS   read-only
    STATUS       current
    DESCRIPTION
        "Cisco UCS adaptor:MenloMcpuErrorStats:uncorrectableErrorsDelta
        managed object property"
    ::= { cucsAdaptorMenloMcpuErrorStatsEntry 25 }

cucsAdaptorMenloMcpuErrorStatsUncorrectableErrorsDeltaAvg OBJECT-TYPE
    SYNTAX       Unsigned64
    MAX-ACCESS   read-only
    STATUS       current
    DESCRIPTION
        "Cisco UCS adaptor:MenloMcpuErrorStats:uncorrectableErrorsDeltaAvg
         managed object property"
    ::= { cucsAdaptorMenloMcpuErrorStatsEntry 26 }

cucsAdaptorMenloMcpuErrorStatsUncorrectableErrorsDeltaMax OBJECT-TYPE
    SYNTAX       Unsigned64
    MAX-ACCESS   read-only
    STATUS       current
    DESCRIPTION
        "Cisco UCS adaptor:MenloMcpuErrorStats:uncorrectableErrorsDeltaMax
         managed object property"
    ::= { cucsAdaptorMenloMcpuErrorStatsEntry 27 }

cucsAdaptorMenloMcpuErrorStatsUncorrectableErrorsDeltaMin OBJECT-TYPE
    SYNTAX       Unsigned64
    MAX-ACCESS   read-only
    STATUS       current
    DESCRIPTION
        "Cisco UCS adaptor:MenloMcpuErrorStats:uncorrectableErrorsDeltaMin
         managed object property"
    ::= { cucsAdaptorMenloMcpuErrorStatsEntry 28 }

cucsAdaptorMenloMcpuErrorStatsUpdate OBJECT-TYPE
    SYNTAX       Gauge32
    MAX-ACCESS   read-only
    STATUS       current
    DESCRIPTION
        "Cisco UCS adaptor:MenloMcpuErrorStats:update managed
        object property"
    ::= { cucsAdaptorMenloMcpuErrorStatsEntry 29 }

cucsAdaptorMenloMcpuErrorStatsHistTable OBJECT-TYPE
    SYNTAX           SEQUENCE OF CucsAdaptorMenloMcpuErrorStatsHistEntry
    MAX-ACCESS       not-accessible
    STATUS           current
    DESCRIPTION
        "Cisco UCS adaptor:MenloMcpuErrorStatsHist managed object table"
    ::= { cucsAdaptorObjects 70 }

cucsAdaptorMenloMcpuErrorStatsHistEntry OBJECT-TYPE
    SYNTAX           CucsAdaptorMenloMcpuErrorStatsHistEntry
    MAX-ACCESS       not-accessible
    STATUS           current
    DESCRIPTION
        "Entry for the cucsAdaptorMenloMcpuErrorStatsHistTable table."
    INDEX { cucsAdaptorMenloMcpuErrorStatsHistInstanceId }
    ::= { cucsAdaptorMenloMcpuErrorStatsHistTable 1 }

CucsAdaptorMenloMcpuErrorStatsHistEntry ::= SEQUENCE {
    cucsAdaptorMenloMcpuErrorStatsHistInstanceId                     CucsManagedObjectId,
    cucsAdaptorMenloMcpuErrorStatsHistDn                             CucsManagedObjectDn,
    cucsAdaptorMenloMcpuErrorStatsHistRn                             SnmpAdminString,
    cucsAdaptorMenloMcpuErrorStatsHistCorrectableErrors              Unsigned64,
    cucsAdaptorMenloMcpuErrorStatsHistCorrectableErrorsDelta         Unsigned64,
    cucsAdaptorMenloMcpuErrorStatsHistCorrectableErrorsDeltaAvg      Unsigned64,
    cucsAdaptorMenloMcpuErrorStatsHistCorrectableErrorsDeltaMax      Unsigned64,
    cucsAdaptorMenloMcpuErrorStatsHistCorrectableErrorsDeltaMin      Unsigned64,
    cucsAdaptorMenloMcpuErrorStatsHistId                             Unsigned64,
    cucsAdaptorMenloMcpuErrorStatsHistMostRecent                     TruthValue,
    cucsAdaptorMenloMcpuErrorStatsHistPopErrors                      Unsigned64,
    cucsAdaptorMenloMcpuErrorStatsHistPopErrorsDelta                 Unsigned64,
    cucsAdaptorMenloMcpuErrorStatsHistPopErrorsDeltaAvg              Unsigned64,
    cucsAdaptorMenloMcpuErrorStatsHistPopErrorsDeltaMax              Unsigned64,
    cucsAdaptorMenloMcpuErrorStatsHistPopErrorsDeltaMin              Unsigned64,
    cucsAdaptorMenloMcpuErrorStatsHistPushErrors                     Unsigned64,
    cucsAdaptorMenloMcpuErrorStatsHistPushErrorsDelta                Unsigned64,
    cucsAdaptorMenloMcpuErrorStatsHistPushErrorsDeltaAvg             Unsigned64,
    cucsAdaptorMenloMcpuErrorStatsHistPushErrorsDeltaMax             Unsigned64,
    cucsAdaptorMenloMcpuErrorStatsHistPushErrorsDeltaMin             Unsigned64,
    cucsAdaptorMenloMcpuErrorStatsHistSuspect                        TruthValue,
    cucsAdaptorMenloMcpuErrorStatsHistThresholded                    CucsAdaptorMenloMcpuErrorStatsHistThresholded,
    cucsAdaptorMenloMcpuErrorStatsHistTimeCollected                  DateAndTime,
    cucsAdaptorMenloMcpuErrorStatsHistUncorrectableErrors            Unsigned64,
    cucsAdaptorMenloMcpuErrorStatsHistUncorrectableErrorsDelta       Unsigned64,
    cucsAdaptorMenloMcpuErrorStatsHistUncorrectableErrorsDeltaAvg    Unsigned64,
    cucsAdaptorMenloMcpuErrorStatsHistUncorrectableErrorsDeltaMax    Unsigned64,
    cucsAdaptorMenloMcpuErrorStatsHistUncorrectableErrorsDeltaMin    Unsigned64
}

cucsAdaptorMenloMcpuErrorStatsHistInstanceId OBJECT-TYPE
    SYNTAX       CucsManagedObjectId
    MAX-ACCESS   not-accessible
    STATUS       current
    DESCRIPTION
        "Instance identifier of the managed object."
    ::= { cucsAdaptorMenloMcpuErrorStatsHistEntry 1 }

cucsAdaptorMenloMcpuErrorStatsHistDn OBJECT-TYPE
    SYNTAX       CucsManagedObjectDn
    MAX-ACCESS   read-only
    STATUS       current
    DESCRIPTION
        "Cisco UCS adaptor:MenloMcpuErrorStatsHist:dn managed
        object property"
    ::= { cucsAdaptorMenloMcpuErrorStatsHistEntry 2 }

cucsAdaptorMenloMcpuErrorStatsHistRn OBJECT-TYPE
    SYNTAX       SnmpAdminString
    MAX-ACCESS   read-only
    STATUS       current
    DESCRIPTION
        "Cisco UCS adaptor:MenloMcpuErrorStatsHist:rn managed
        object property"
    ::= { cucsAdaptorMenloMcpuErrorStatsHistEntry 3 }

cucsAdaptorMenloMcpuErrorStatsHistCorrectableErrors OBJECT-TYPE
    SYNTAX       Unsigned64
    MAX-ACCESS   read-only
    STATUS       current
    DESCRIPTION
        "Cisco UCS adaptor:MenloMcpuErrorStatsHist:correctableErrors
        managed object property"
    ::= { cucsAdaptorMenloMcpuErrorStatsHistEntry 4 }

cucsAdaptorMenloMcpuErrorStatsHistCorrectableErrorsDelta OBJECT-TYPE
    SYNTAX       Unsigned64
    MAX-ACCESS   read-only
    STATUS       current
    DESCRIPTION
        "Cisco UCS adaptor:MenloMcpuErrorStatsHist:correctableErrorsDelta
        managed object property"
    ::= { cucsAdaptorMenloMcpuErrorStatsHistEntry 5 }

cucsAdaptorMenloMcpuErrorStatsHistCorrectableErrorsDeltaAvg OBJECT-TYPE
    SYNTAX       Unsigned64
    MAX-ACCESS   read-only
    STATUS       current
    DESCRIPTION
        "Cisco UCS adaptor:MenloMcpuErrorStatsHist:correctableErrorsDeltaA
        vg managed object property"
    ::= { cucsAdaptorMenloMcpuErrorStatsHistEntry 6 }

cucsAdaptorMenloMcpuErrorStatsHistCorrectableErrorsDeltaMax OBJECT-TYPE
    SYNTAX       Unsigned64
    MAX-ACCESS   read-only
    STATUS       current
    DESCRIPTION
        "Cisco UCS adaptor:MenloMcpuErrorStatsHist:correctableErrorsDeltaM
        ax managed object property"
    ::= { cucsAdaptorMenloMcpuErrorStatsHistEntry 7 }

cucsAdaptorMenloMcpuErrorStatsHistCorrectableErrorsDeltaMin OBJECT-TYPE
    SYNTAX       Unsigned64
    MAX-ACCESS   read-only
    STATUS       current
    DESCRIPTION
        "Cisco UCS adaptor:MenloMcpuErrorStatsHist:correctableErrorsDeltaM
        in managed object property"
    ::= { cucsAdaptorMenloMcpuErrorStatsHistEntry 8 }

cucsAdaptorMenloMcpuErrorStatsHistId OBJECT-TYPE
    SYNTAX       Unsigned64
    MAX-ACCESS   read-only
    STATUS       current
    DESCRIPTION
        "Cisco UCS adaptor:MenloMcpuErrorStatsHist:id managed
        object property"
    ::= { cucsAdaptorMenloMcpuErrorStatsHistEntry 9 }

cucsAdaptorMenloMcpuErrorStatsHistMostRecent OBJECT-TYPE
    SYNTAX       TruthValue
    MAX-ACCESS   read-only
    STATUS       current
    DESCRIPTION
        "Cisco UCS adaptor:MenloMcpuErrorStatsHist:mostRecent
        managed object property"
    ::= { cucsAdaptorMenloMcpuErrorStatsHistEntry 10 }

cucsAdaptorMenloMcpuErrorStatsHistPopErrors OBJECT-TYPE
    SYNTAX       Unsigned64
    MAX-ACCESS   read-only
    STATUS       current
    DESCRIPTION
        "Cisco UCS adaptor:MenloMcpuErrorStatsHist:popErrors
        managed object property"
    ::= { cucsAdaptorMenloMcpuErrorStatsHistEntry 11 }

cucsAdaptorMenloMcpuErrorStatsHistPopErrorsDelta OBJECT-TYPE
    SYNTAX       Unsigned64
    MAX-ACCESS   read-only
    STATUS       current
    DESCRIPTION
        "Cisco UCS adaptor:MenloMcpuErrorStatsHist:popErrorsDelta
        managed object property"
    ::= { cucsAdaptorMenloMcpuErrorStatsHistEntry 12 }

cucsAdaptorMenloMcpuErrorStatsHistPopErrorsDeltaAvg OBJECT-TYPE
    SYNTAX       Unsigned64
    MAX-ACCESS   read-only
    STATUS       current
    DESCRIPTION
        "Cisco UCS adaptor:MenloMcpuErrorStatsHist:popErrorsDeltaAvg
        managed object property"
    ::= { cucsAdaptorMenloMcpuErrorStatsHistEntry 13 }

cucsAdaptorMenloMcpuErrorStatsHistPopErrorsDeltaMax OBJECT-TYPE
    SYNTAX       Unsigned64
    MAX-ACCESS   read-only
    STATUS       current
    DESCRIPTION
        "Cisco UCS adaptor:MenloMcpuErrorStatsHist:popErrorsDeltaMax
        managed object property"
    ::= { cucsAdaptorMenloMcpuErrorStatsHistEntry 14 }

cucsAdaptorMenloMcpuErrorStatsHistPopErrorsDeltaMin OBJECT-TYPE
    SYNTAX       Unsigned64
    MAX-ACCESS   read-only
    STATUS       current
    DESCRIPTION
        "Cisco UCS adaptor:MenloMcpuErrorStatsHist:popErrorsDeltaMin
        managed object property"
    ::= { cucsAdaptorMenloMcpuErrorStatsHistEntry 15 }

cucsAdaptorMenloMcpuErrorStatsHistPushErrors OBJECT-TYPE
    SYNTAX       Unsigned64
    MAX-ACCESS   read-only
    STATUS       current
    DESCRIPTION
        "Cisco UCS adaptor:MenloMcpuErrorStatsHist:pushErrors
        managed object property"
    ::= { cucsAdaptorMenloMcpuErrorStatsHistEntry 16 }

cucsAdaptorMenloMcpuErrorStatsHistPushErrorsDelta OBJECT-TYPE
    SYNTAX       Unsigned64
    MAX-ACCESS   read-only
    STATUS       current
    DESCRIPTION
        "Cisco UCS adaptor:MenloMcpuErrorStatsHist:pushErrorsDelta
        managed object property"
    ::= { cucsAdaptorMenloMcpuErrorStatsHistEntry 17 }

cucsAdaptorMenloMcpuErrorStatsHistPushErrorsDeltaAvg OBJECT-TYPE
    SYNTAX       Unsigned64
    MAX-ACCESS   read-only
    STATUS       current
    DESCRIPTION
        "Cisco UCS adaptor:MenloMcpuErrorStatsHist:pushErrorsDeltaAvg
        managed object property"
    ::= { cucsAdaptorMenloMcpuErrorStatsHistEntry 18 }

cucsAdaptorMenloMcpuErrorStatsHistPushErrorsDeltaMax OBJECT-TYPE
    SYNTAX       Unsigned64
    MAX-ACCESS   read-only
    STATUS       current
    DESCRIPTION
        "Cisco UCS adaptor:MenloMcpuErrorStatsHist:pushErrorsDeltaMax
        managed object property"
    ::= { cucsAdaptorMenloMcpuErrorStatsHistEntry 19 }

cucsAdaptorMenloMcpuErrorStatsHistPushErrorsDeltaMin OBJECT-TYPE
    SYNTAX       Unsigned64
    MAX-ACCESS   read-only
    STATUS       current
    DESCRIPTION
        "Cisco UCS adaptor:MenloMcpuErrorStatsHist:pushErrorsDeltaMin
        managed object property"
    ::= { cucsAdaptorMenloMcpuErrorStatsHistEntry 20 }

cucsAdaptorMenloMcpuErrorStatsHistSuspect OBJECT-TYPE
    SYNTAX       TruthValue
    MAX-ACCESS   read-only
    STATUS       current
    DESCRIPTION
        "Cisco UCS adaptor:MenloMcpuErrorStatsHist:suspect
        managed object property"
    ::= { cucsAdaptorMenloMcpuErrorStatsHistEntry 21 }

cucsAdaptorMenloMcpuErrorStatsHistThresholded OBJECT-TYPE
    SYNTAX       CucsAdaptorMenloMcpuErrorStatsHistThresholded
    MAX-ACCESS   read-only
    STATUS       current
    DESCRIPTION
        "Cisco UCS adaptor:MenloMcpuErrorStatsHist:thresholded
        managed object property"
    ::= { cucsAdaptorMenloMcpuErrorStatsHistEntry 22 }

cucsAdaptorMenloMcpuErrorStatsHistTimeCollected OBJECT-TYPE
    SYNTAX       DateAndTime
    MAX-ACCESS   read-only
    STATUS       current
    DESCRIPTION
        "Cisco UCS adaptor:MenloMcpuErrorStatsHist:timeCollected
        managed object property"
    ::= { cucsAdaptorMenloMcpuErrorStatsHistEntry 23 }

cucsAdaptorMenloMcpuErrorStatsHistUncorrectableErrors OBJECT-TYPE
    SYNTAX       Unsigned64
    MAX-ACCESS   read-only
    STATUS       current
    DESCRIPTION
        "Cisco UCS adaptor:MenloMcpuErrorStatsHist:uncorrectableErrors
        managed object property"
    ::= { cucsAdaptorMenloMcpuErrorStatsHistEntry 24 }

cucsAdaptorMenloMcpuErrorStatsHistUncorrectableErrorsDelta OBJECT-TYPE
    SYNTAX       Unsigned64
    MAX-ACCESS   read-only
    STATUS       current
    DESCRIPTION
        "Cisco UCS adaptor:MenloMcpuErrorStatsHist:uncorrectableErrorsDelt
        a managed object property"
    ::= { cucsAdaptorMenloMcpuErrorStatsHistEntry 25 }

cucsAdaptorMenloMcpuErrorStatsHistUncorrectableErrorsDeltaAvg OBJECT-TYPE
    SYNTAX       Unsigned64
    MAX-ACCESS   read-only
    STATUS       current
    DESCRIPTION
        "Cisco UCS adaptor:MenloMcpuErrorStatsHist:uncorrectableErrorsDelt
        aAvg managed object property"
    ::= { cucsAdaptorMenloMcpuErrorStatsHistEntry 26 }

cucsAdaptorMenloMcpuErrorStatsHistUncorrectableErrorsDeltaMax OBJECT-TYPE
    SYNTAX       Unsigned64
    MAX-ACCESS   read-only
    STATUS       current
    DESCRIPTION
        "Cisco UCS adaptor:MenloMcpuErrorStatsHist:uncorrectableErrorsDelt
        aMax managed object property"
    ::= { cucsAdaptorMenloMcpuErrorStatsHistEntry 27 }

cucsAdaptorMenloMcpuErrorStatsHistUncorrectableErrorsDeltaMin OBJECT-TYPE
    SYNTAX       Unsigned64
    MAX-ACCESS   read-only
    STATUS       current
    DESCRIPTION
        "Cisco UCS adaptor:MenloMcpuErrorStatsHist:uncorrectableErrorsDelt
        aMin managed object property"
    ::= { cucsAdaptorMenloMcpuErrorStatsHistEntry 28 }

cucsAdaptorMenloMcpuStatsTable OBJECT-TYPE
    SYNTAX           SEQUENCE OF CucsAdaptorMenloMcpuStatsEntry
    MAX-ACCESS       not-accessible
    STATUS           current
    DESCRIPTION
        "Cisco UCS adaptor:MenloMcpuStats managed object table"
    ::= { cucsAdaptorObjects 71 }

cucsAdaptorMenloMcpuStatsEntry OBJECT-TYPE
    SYNTAX           CucsAdaptorMenloMcpuStatsEntry
    MAX-ACCESS       not-accessible
    STATUS           current
    DESCRIPTION
        "Entry for the cucsAdaptorMenloMcpuStatsTable table."
    INDEX { cucsAdaptorMenloMcpuStatsInstanceId }
    ::= { cucsAdaptorMenloMcpuStatsTable 1 }

CucsAdaptorMenloMcpuStatsEntry ::= SEQUENCE {
    cucsAdaptorMenloMcpuStatsInstanceId                              CucsManagedObjectId,
    cucsAdaptorMenloMcpuStatsDn                                      CucsManagedObjectDn,
    cucsAdaptorMenloMcpuStatsRn                                      SnmpAdminString,
    cucsAdaptorMenloMcpuStatsDropAcl                                 Unsigned64,
    cucsAdaptorMenloMcpuStatsDropAclDelta                            Counter64,
    cucsAdaptorMenloMcpuStatsDropAclDeltaAvg                         Unsigned64,
    cucsAdaptorMenloMcpuStatsDropAclDeltaMax                         Unsigned64,
    cucsAdaptorMenloMcpuStatsDropAclDeltaMin                         Unsigned64,
    cucsAdaptorMenloMcpuStatsDropOverrun                             Unsigned64,
    cucsAdaptorMenloMcpuStatsDropOverrunDelta                        Counter64,
    cucsAdaptorMenloMcpuStatsDropOverrunDeltaAvg                     Unsigned64,
    cucsAdaptorMenloMcpuStatsDropOverrunDeltaMax                     Unsigned64,
    cucsAdaptorMenloMcpuStatsDropOverrunDeltaMin                     Unsigned64,
    cucsAdaptorMenloMcpuStatsDropRunt                                Unsigned64,
    cucsAdaptorMenloMcpuStatsDropRuntDelta                           Counter64,
    cucsAdaptorMenloMcpuStatsDropRuntDeltaAvg                        Unsigned64,
    cucsAdaptorMenloMcpuStatsDropRuntDeltaMax                        Unsigned64,
    cucsAdaptorMenloMcpuStatsDropRuntDeltaMin                        Unsigned64,
    cucsAdaptorMenloMcpuStatsIntervals                               Gauge32,
    cucsAdaptorMenloMcpuStatsMenloMcpuIndex                          CucsAdaptorMenloStatsIndex,
    cucsAdaptorMenloMcpuStatsSuspect                                 TruthValue,
    cucsAdaptorMenloMcpuStatsThresholded                             CucsAdaptorMenloMcpuStatsThresholded,
    cucsAdaptorMenloMcpuStatsTimeCollected                           DateAndTime,
    cucsAdaptorMenloMcpuStatsTruncateOverrun                         Unsigned64,
    cucsAdaptorMenloMcpuStatsTruncateOverrunDelta                    Counter64,
    cucsAdaptorMenloMcpuStatsTruncateOverrunDeltaAvg                 Unsigned64,
    cucsAdaptorMenloMcpuStatsTruncateOverrunDeltaMax                 Unsigned64,
    cucsAdaptorMenloMcpuStatsTruncateOverrunDeltaMin                 Unsigned64,
    cucsAdaptorMenloMcpuStatsUpdate                                  Gauge32
}

cucsAdaptorMenloMcpuStatsInstanceId OBJECT-TYPE
    SYNTAX       CucsManagedObjectId
    MAX-ACCESS   not-accessible
    STATUS       current
    DESCRIPTION
        "Instance identifier of the managed object."
    ::= { cucsAdaptorMenloMcpuStatsEntry 1 }

cucsAdaptorMenloMcpuStatsDn OBJECT-TYPE
    SYNTAX       CucsManagedObjectDn
    MAX-ACCESS   read-only
    STATUS       current
    DESCRIPTION
        "Cisco UCS adaptor:MenloMcpuStats:dn managed object property"
    ::= { cucsAdaptorMenloMcpuStatsEntry 2 }

cucsAdaptorMenloMcpuStatsRn OBJECT-TYPE
    SYNTAX       SnmpAdminString
    MAX-ACCESS   read-only
    STATUS       current
    DESCRIPTION
        "Cisco UCS adaptor:MenloMcpuStats:rn managed object property"
    ::= { cucsAdaptorMenloMcpuStatsEntry 3 }

cucsAdaptorMenloMcpuStatsDropAcl OBJECT-TYPE
    SYNTAX       Unsigned64
    MAX-ACCESS   read-only
    STATUS       current
    DESCRIPTION
        "Cisco UCS adaptor:MenloMcpuStats:dropAcl managed object property"
    ::= { cucsAdaptorMenloMcpuStatsEntry 4 }

cucsAdaptorMenloMcpuStatsDropAclDelta OBJECT-TYPE
    SYNTAX       Counter64
    MAX-ACCESS   read-only
    STATUS       current
    DESCRIPTION
        "Cisco UCS adaptor:MenloMcpuStats:dropAclDelta
        managed object property"
    ::= { cucsAdaptorMenloMcpuStatsEntry 5 }

cucsAdaptorMenloMcpuStatsDropAclDeltaAvg OBJECT-TYPE
    SYNTAX       Unsigned64
    MAX-ACCESS   read-only
    STATUS       current
    DESCRIPTION
        "Cisco UCS adaptor:MenloMcpuStats:dropAclDeltaAvg
        managed object property"
    ::= { cucsAdaptorMenloMcpuStatsEntry 6 }

cucsAdaptorMenloMcpuStatsDropAclDeltaMax OBJECT-TYPE
    SYNTAX       Unsigned64
    MAX-ACCESS   read-only
    STATUS       current
    DESCRIPTION
        "Cisco UCS adaptor:MenloMcpuStats:dropAclDeltaMax
        managed object property"
    ::= { cucsAdaptorMenloMcpuStatsEntry 7 }

cucsAdaptorMenloMcpuStatsDropAclDeltaMin OBJECT-TYPE
    SYNTAX       Unsigned64
    MAX-ACCESS   read-only
    STATUS       current
    DESCRIPTION
        "Cisco UCS adaptor:MenloMcpuStats:dropAclDeltaMin
        managed object property"
    ::= { cucsAdaptorMenloMcpuStatsEntry 8 }

cucsAdaptorMenloMcpuStatsDropOverrun OBJECT-TYPE
    SYNTAX       Unsigned64
    MAX-ACCESS   read-only
    STATUS       current
    DESCRIPTION
        "Cisco UCS adaptor:MenloMcpuStats:dropOverrun managed
        object property"
    ::= { cucsAdaptorMenloMcpuStatsEntry 9 }

cucsAdaptorMenloMcpuStatsDropOverrunDelta OBJECT-TYPE
    SYNTAX       Counter64
    MAX-ACCESS   read-only
    STATUS       current
    DESCRIPTION
        "Cisco UCS adaptor:MenloMcpuStats:dropOverrunDelta
        managed object property"
    ::= { cucsAdaptorMenloMcpuStatsEntry 10 }

cucsAdaptorMenloMcpuStatsDropOverrunDeltaAvg OBJECT-TYPE
    SYNTAX       Unsigned64
    MAX-ACCESS   read-only
    STATUS       current
    DESCRIPTION
        "Cisco UCS adaptor:MenloMcpuStats:dropOverrunDeltaAvg
        managed object property"
    ::= { cucsAdaptorMenloMcpuStatsEntry 11 }

cucsAdaptorMenloMcpuStatsDropOverrunDeltaMax OBJECT-TYPE
    SYNTAX       Unsigned64
    MAX-ACCESS   read-only
    STATUS       current
    DESCRIPTION
        "Cisco UCS adaptor:MenloMcpuStats:dropOverrunDeltaMax
        managed object property"
    ::= { cucsAdaptorMenloMcpuStatsEntry 12 }

cucsAdaptorMenloMcpuStatsDropOverrunDeltaMin OBJECT-TYPE
    SYNTAX       Unsigned64
    MAX-ACCESS   read-only
    STATUS       current
    DESCRIPTION
        "Cisco UCS adaptor:MenloMcpuStats:dropOverrunDeltaMin
        managed object property"
    ::= { cucsAdaptorMenloMcpuStatsEntry 13 }

cucsAdaptorMenloMcpuStatsDropRunt OBJECT-TYPE
    SYNTAX       Unsigned64
    MAX-ACCESS   read-only
    STATUS       current
    DESCRIPTION
        "Cisco UCS adaptor:MenloMcpuStats:dropRunt managed
        object property"
    ::= { cucsAdaptorMenloMcpuStatsEntry 14 }

cucsAdaptorMenloMcpuStatsDropRuntDelta OBJECT-TYPE
    SYNTAX       Counter64
    MAX-ACCESS   read-only
    STATUS       current
    DESCRIPTION
        "Cisco UCS adaptor:MenloMcpuStats:dropRuntDelta
        managed object property"
    ::= { cucsAdaptorMenloMcpuStatsEntry 15 }

cucsAdaptorMenloMcpuStatsDropRuntDeltaAvg OBJECT-TYPE
    SYNTAX       Unsigned64
    MAX-ACCESS   read-only
    STATUS       current
    DESCRIPTION
        "Cisco UCS adaptor:MenloMcpuStats:dropRuntDeltaAvg
        managed object property"
    ::= { cucsAdaptorMenloMcpuStatsEntry 16 }

cucsAdaptorMenloMcpuStatsDropRuntDeltaMax OBJECT-TYPE
    SYNTAX       Unsigned64
    MAX-ACCESS   read-only
    STATUS       current
    DESCRIPTION
        "Cisco UCS adaptor:MenloMcpuStats:dropRuntDeltaMax
        managed object property"
    ::= { cucsAdaptorMenloMcpuStatsEntry 17 }

cucsAdaptorMenloMcpuStatsDropRuntDeltaMin OBJECT-TYPE
    SYNTAX       Unsigned64
    MAX-ACCESS   read-only
    STATUS       current
    DESCRIPTION
        "Cisco UCS adaptor:MenloMcpuStats:dropRuntDeltaMin
        managed object property"
    ::= { cucsAdaptorMenloMcpuStatsEntry 18 }

cucsAdaptorMenloMcpuStatsIntervals OBJECT-TYPE
    SYNTAX       Gauge32
    MAX-ACCESS   read-only
    STATUS       current
    DESCRIPTION
        "Cisco UCS adaptor:MenloMcpuStats:intervals managed
        object property"
    ::= { cucsAdaptorMenloMcpuStatsEntry 19 }

cucsAdaptorMenloMcpuStatsMenloMcpuIndex OBJECT-TYPE
    SYNTAX       CucsAdaptorMenloStatsIndex
    MAX-ACCESS   read-only
    STATUS       current
    DESCRIPTION
        "Cisco UCS adaptor:MenloMcpuStats:menloMcpuIndex
        managed object property"
    ::= { cucsAdaptorMenloMcpuStatsEntry 20 }

cucsAdaptorMenloMcpuStatsSuspect OBJECT-TYPE
    SYNTAX       TruthValue
    MAX-ACCESS   read-only
    STATUS       current
    DESCRIPTION
        "Cisco UCS adaptor:MenloMcpuStats:suspect managed object property"
    ::= { cucsAdaptorMenloMcpuStatsEntry 21 }

cucsAdaptorMenloMcpuStatsThresholded OBJECT-TYPE
    SYNTAX       CucsAdaptorMenloMcpuStatsThresholded
    MAX-ACCESS   read-only
    STATUS       current
    DESCRIPTION
        "Cisco UCS adaptor:MenloMcpuStats:thresholded managed
        object property"
    ::= { cucsAdaptorMenloMcpuStatsEntry 22 }

cucsAdaptorMenloMcpuStatsTimeCollected OBJECT-TYPE
    SYNTAX       DateAndTime
    MAX-ACCESS   read-only
    STATUS       current
    DESCRIPTION
        "Cisco UCS adaptor:MenloMcpuStats:timeCollected
        managed object property"
    ::= { cucsAdaptorMenloMcpuStatsEntry 23 }

cucsAdaptorMenloMcpuStatsTruncateOverrun OBJECT-TYPE
    SYNTAX       Unsigned64
    MAX-ACCESS   read-only
    STATUS       current
    DESCRIPTION
        "Cisco UCS adaptor:MenloMcpuStats:truncateOverrun
        managed object property"
    ::= { cucsAdaptorMenloMcpuStatsEntry 24 }

cucsAdaptorMenloMcpuStatsTruncateOverrunDelta OBJECT-TYPE
    SYNTAX       Counter64
    MAX-ACCESS   read-only
    STATUS       current
    DESCRIPTION
        "Cisco UCS adaptor:MenloMcpuStats:truncateOverrunDelta
        managed object property"
    ::= { cucsAdaptorMenloMcpuStatsEntry 25 }

cucsAdaptorMenloMcpuStatsTruncateOverrunDeltaAvg OBJECT-TYPE
    SYNTAX       Unsigned64
    MAX-ACCESS   read-only
    STATUS       current
    DESCRIPTION
        "Cisco UCS adaptor:MenloMcpuStats:truncateOverrunDeltaAvg
        managed object property"
    ::= { cucsAdaptorMenloMcpuStatsEntry 26 }

cucsAdaptorMenloMcpuStatsTruncateOverrunDeltaMax OBJECT-TYPE
    SYNTAX       Unsigned64
    MAX-ACCESS   read-only
    STATUS       current
    DESCRIPTION
        "Cisco UCS adaptor:MenloMcpuStats:truncateOverrunDeltaMax
        managed object property"
    ::= { cucsAdaptorMenloMcpuStatsEntry 27 }

cucsAdaptorMenloMcpuStatsTruncateOverrunDeltaMin OBJECT-TYPE
    SYNTAX       Unsigned64
    MAX-ACCESS   read-only
    STATUS       current
    DESCRIPTION
        "Cisco UCS adaptor:MenloMcpuStats:truncateOverrunDeltaMin
        managed object property"
    ::= { cucsAdaptorMenloMcpuStatsEntry 28 }

cucsAdaptorMenloMcpuStatsUpdate OBJECT-TYPE
    SYNTAX       Gauge32
    MAX-ACCESS   read-only
    STATUS       current
    DESCRIPTION
        "Cisco UCS adaptor:MenloMcpuStats:update managed object property"
    ::= { cucsAdaptorMenloMcpuStatsEntry 29 }

cucsAdaptorMenloMcpuStatsHistTable OBJECT-TYPE
    SYNTAX           SEQUENCE OF CucsAdaptorMenloMcpuStatsHistEntry
    MAX-ACCESS       not-accessible
    STATUS           current
    DESCRIPTION
        "Cisco UCS adaptor:MenloMcpuStatsHist managed object table"
    ::= { cucsAdaptorObjects 72 }

cucsAdaptorMenloMcpuStatsHistEntry OBJECT-TYPE
    SYNTAX           CucsAdaptorMenloMcpuStatsHistEntry
    MAX-ACCESS       not-accessible
    STATUS           current
    DESCRIPTION
        "Entry for the cucsAdaptorMenloMcpuStatsHistTable table."
    INDEX { cucsAdaptorMenloMcpuStatsHistInstanceId }
    ::= { cucsAdaptorMenloMcpuStatsHistTable 1 }

CucsAdaptorMenloMcpuStatsHistEntry ::= SEQUENCE {
    cucsAdaptorMenloMcpuStatsHistInstanceId                          CucsManagedObjectId,
    cucsAdaptorMenloMcpuStatsHistDn                                  CucsManagedObjectDn,
    cucsAdaptorMenloMcpuStatsHistRn                                  SnmpAdminString,
    cucsAdaptorMenloMcpuStatsHistDropAcl                             Unsigned64,
    cucsAdaptorMenloMcpuStatsHistDropAclDelta                        Unsigned64,
    cucsAdaptorMenloMcpuStatsHistDropAclDeltaAvg                     Unsigned64,
    cucsAdaptorMenloMcpuStatsHistDropAclDeltaMax                     Unsigned64,
    cucsAdaptorMenloMcpuStatsHistDropAclDeltaMin                     Unsigned64,
    cucsAdaptorMenloMcpuStatsHistDropOverrun                         Unsigned64,
    cucsAdaptorMenloMcpuStatsHistDropOverrunDelta                    Unsigned64,
    cucsAdaptorMenloMcpuStatsHistDropOverrunDeltaAvg                 Unsigned64,
    cucsAdaptorMenloMcpuStatsHistDropOverrunDeltaMax                 Unsigned64,
    cucsAdaptorMenloMcpuStatsHistDropOverrunDeltaMin                 Unsigned64,
    cucsAdaptorMenloMcpuStatsHistDropRunt                            Unsigned64,
    cucsAdaptorMenloMcpuStatsHistDropRuntDelta                       Unsigned64,
    cucsAdaptorMenloMcpuStatsHistDropRuntDeltaAvg                    Unsigned64,
    cucsAdaptorMenloMcpuStatsHistDropRuntDeltaMax                    Unsigned64,
    cucsAdaptorMenloMcpuStatsHistDropRuntDeltaMin                    Unsigned64,
    cucsAdaptorMenloMcpuStatsHistId                                  Unsigned64,
    cucsAdaptorMenloMcpuStatsHistMostRecent                          TruthValue,
    cucsAdaptorMenloMcpuStatsHistSuspect                             TruthValue,
    cucsAdaptorMenloMcpuStatsHistThresholded                         CucsAdaptorMenloMcpuStatsHistThresholded,
    cucsAdaptorMenloMcpuStatsHistTimeCollected                       DateAndTime,
    cucsAdaptorMenloMcpuStatsHistTruncateOverrun                     Unsigned64,
    cucsAdaptorMenloMcpuStatsHistTruncateOverrunDelta                Unsigned64,
    cucsAdaptorMenloMcpuStatsHistTruncateOverrunDeltaAvg             Unsigned64,
    cucsAdaptorMenloMcpuStatsHistTruncateOverrunDeltaMax             Unsigned64,
    cucsAdaptorMenloMcpuStatsHistTruncateOverrunDeltaMin             Unsigned64
}

cucsAdaptorMenloMcpuStatsHistInstanceId OBJECT-TYPE
    SYNTAX       CucsManagedObjectId
    MAX-ACCESS   not-accessible
    STATUS       current
    DESCRIPTION
        "Instance identifier of the managed object."
    ::= { cucsAdaptorMenloMcpuStatsHistEntry 1 }

cucsAdaptorMenloMcpuStatsHistDn OBJECT-TYPE
    SYNTAX       CucsManagedObjectDn
    MAX-ACCESS   read-only
    STATUS       current
    DESCRIPTION
        "Cisco UCS adaptor:MenloMcpuStatsHist:dn managed object property"
    ::= { cucsAdaptorMenloMcpuStatsHistEntry 2 }

cucsAdaptorMenloMcpuStatsHistRn OBJECT-TYPE
    SYNTAX       SnmpAdminString
    MAX-ACCESS   read-only
    STATUS       current
    DESCRIPTION
        "Cisco UCS adaptor:MenloMcpuStatsHist:rn managed object property"
    ::= { cucsAdaptorMenloMcpuStatsHistEntry 3 }

cucsAdaptorMenloMcpuStatsHistDropAcl OBJECT-TYPE
    SYNTAX       Unsigned64
    MAX-ACCESS   read-only
    STATUS       current
    DESCRIPTION
        "Cisco UCS adaptor:MenloMcpuStatsHist:dropAcl managed
        object property"
    ::= { cucsAdaptorMenloMcpuStatsHistEntry 4 }

cucsAdaptorMenloMcpuStatsHistDropAclDelta OBJECT-TYPE
    SYNTAX       Unsigned64
    MAX-ACCESS   read-only
    STATUS       current
    DESCRIPTION
        "Cisco UCS adaptor:MenloMcpuStatsHist:dropAclDelta
        managed object property"
    ::= { cucsAdaptorMenloMcpuStatsHistEntry 5 }

cucsAdaptorMenloMcpuStatsHistDropAclDeltaAvg OBJECT-TYPE
    SYNTAX       Unsigned64
    MAX-ACCESS   read-only
    STATUS       current
    DESCRIPTION
        "Cisco UCS adaptor:MenloMcpuStatsHist:dropAclDeltaAvg
        managed object property"
    ::= { cucsAdaptorMenloMcpuStatsHistEntry 6 }

cucsAdaptorMenloMcpuStatsHistDropAclDeltaMax OBJECT-TYPE
    SYNTAX       Unsigned64
    MAX-ACCESS   read-only
    STATUS       current
    DESCRIPTION
        "Cisco UCS adaptor:MenloMcpuStatsHist:dropAclDeltaMax
        managed object property"
    ::= { cucsAdaptorMenloMcpuStatsHistEntry 7 }

cucsAdaptorMenloMcpuStatsHistDropAclDeltaMin OBJECT-TYPE
    SYNTAX       Unsigned64
    MAX-ACCESS   read-only
    STATUS       current
    DESCRIPTION
        "Cisco UCS adaptor:MenloMcpuStatsHist:dropAclDeltaMin
        managed object property"
    ::= { cucsAdaptorMenloMcpuStatsHistEntry 8 }

cucsAdaptorMenloMcpuStatsHistDropOverrun OBJECT-TYPE
    SYNTAX       Unsigned64
    MAX-ACCESS   read-only
    STATUS       current
    DESCRIPTION
        "Cisco UCS adaptor:MenloMcpuStatsHist:dropOverrun
        managed object property"
    ::= { cucsAdaptorMenloMcpuStatsHistEntry 9 }

cucsAdaptorMenloMcpuStatsHistDropOverrunDelta OBJECT-TYPE
    SYNTAX       Unsigned64
    MAX-ACCESS   read-only
    STATUS       current
    DESCRIPTION
        "Cisco UCS adaptor:MenloMcpuStatsHist:dropOverrunDelta
        managed object property"
    ::= { cucsAdaptorMenloMcpuStatsHistEntry 10 }

cucsAdaptorMenloMcpuStatsHistDropOverrunDeltaAvg OBJECT-TYPE
    SYNTAX       Unsigned64
    MAX-ACCESS   read-only
    STATUS       current
    DESCRIPTION
        "Cisco UCS adaptor:MenloMcpuStatsHist:dropOverrunDeltaAvg
        managed object property"
    ::= { cucsAdaptorMenloMcpuStatsHistEntry 11 }

cucsAdaptorMenloMcpuStatsHistDropOverrunDeltaMax OBJECT-TYPE
    SYNTAX       Unsigned64
    MAX-ACCESS   read-only
    STATUS       current
    DESCRIPTION
        "Cisco UCS adaptor:MenloMcpuStatsHist:dropOverrunDeltaMax
        managed object property"
    ::= { cucsAdaptorMenloMcpuStatsHistEntry 12 }

cucsAdaptorMenloMcpuStatsHistDropOverrunDeltaMin OBJECT-TYPE
    SYNTAX       Unsigned64
    MAX-ACCESS   read-only
    STATUS       current
    DESCRIPTION
        "Cisco UCS adaptor:MenloMcpuStatsHist:dropOverrunDeltaMin
        managed object property"
    ::= { cucsAdaptorMenloMcpuStatsHistEntry 13 }

cucsAdaptorMenloMcpuStatsHistDropRunt OBJECT-TYPE
    SYNTAX       Unsigned64
    MAX-ACCESS   read-only
    STATUS       current
    DESCRIPTION
        "Cisco UCS adaptor:MenloMcpuStatsHist:dropRunt
        managed object property"
    ::= { cucsAdaptorMenloMcpuStatsHistEntry 14 }

cucsAdaptorMenloMcpuStatsHistDropRuntDelta OBJECT-TYPE
    SYNTAX       Unsigned64
    MAX-ACCESS   read-only
    STATUS       current
    DESCRIPTION
        "Cisco UCS adaptor:MenloMcpuStatsHist:dropRuntDelta
        managed object property"
    ::= { cucsAdaptorMenloMcpuStatsHistEntry 15 }

cucsAdaptorMenloMcpuStatsHistDropRuntDeltaAvg OBJECT-TYPE
    SYNTAX       Unsigned64
    MAX-ACCESS   read-only
    STATUS       current
    DESCRIPTION
        "Cisco UCS adaptor:MenloMcpuStatsHist:dropRuntDeltaAvg
        managed object property"
    ::= { cucsAdaptorMenloMcpuStatsHistEntry 16 }

cucsAdaptorMenloMcpuStatsHistDropRuntDeltaMax OBJECT-TYPE
    SYNTAX       Unsigned64
    MAX-ACCESS   read-only
    STATUS       current
    DESCRIPTION
        "Cisco UCS adaptor:MenloMcpuStatsHist:dropRuntDeltaMax
        managed object property"
    ::= { cucsAdaptorMenloMcpuStatsHistEntry 17 }

cucsAdaptorMenloMcpuStatsHistDropRuntDeltaMin OBJECT-TYPE
    SYNTAX       Unsigned64
    MAX-ACCESS   read-only
    STATUS       current
    DESCRIPTION
        "Cisco UCS adaptor:MenloMcpuStatsHist:dropRuntDeltaMin
        managed object property"
    ::= { cucsAdaptorMenloMcpuStatsHistEntry 18 }

cucsAdaptorMenloMcpuStatsHistId OBJECT-TYPE
    SYNTAX       Unsigned64
    MAX-ACCESS   read-only
    STATUS       current
    DESCRIPTION
        "Cisco UCS adaptor:MenloMcpuStatsHist:id managed object property"
    ::= { cucsAdaptorMenloMcpuStatsHistEntry 19 }

cucsAdaptorMenloMcpuStatsHistMostRecent OBJECT-TYPE
    SYNTAX       TruthValue
    MAX-ACCESS   read-only
    STATUS       current
    DESCRIPTION
        "Cisco UCS adaptor:MenloMcpuStatsHist:mostRecent
        managed object property"
    ::= { cucsAdaptorMenloMcpuStatsHistEntry 20 }

cucsAdaptorMenloMcpuStatsHistSuspect OBJECT-TYPE
    SYNTAX       TruthValue
    MAX-ACCESS   read-only
    STATUS       current
    DESCRIPTION
        "Cisco UCS adaptor:MenloMcpuStatsHist:suspect managed
        object property"
    ::= { cucsAdaptorMenloMcpuStatsHistEntry 21 }

cucsAdaptorMenloMcpuStatsHistThresholded OBJECT-TYPE
    SYNTAX       CucsAdaptorMenloMcpuStatsHistThresholded
    MAX-ACCESS   read-only
    STATUS       current
    DESCRIPTION
        "Cisco UCS adaptor:MenloMcpuStatsHist:thresholded
        managed object property"
    ::= { cucsAdaptorMenloMcpuStatsHistEntry 22 }

cucsAdaptorMenloMcpuStatsHistTimeCollected OBJECT-TYPE
    SYNTAX       DateAndTime
    MAX-ACCESS   read-only
    STATUS       current
    DESCRIPTION
        "Cisco UCS adaptor:MenloMcpuStatsHist:timeCollected
        managed object property"
    ::= { cucsAdaptorMenloMcpuStatsHistEntry 23 }

cucsAdaptorMenloMcpuStatsHistTruncateOverrun OBJECT-TYPE
    SYNTAX       Unsigned64
    MAX-ACCESS   read-only
    STATUS       current
    DESCRIPTION
        "Cisco UCS adaptor:MenloMcpuStatsHist:truncateOverrun
        managed object property"
    ::= { cucsAdaptorMenloMcpuStatsHistEntry 24 }

cucsAdaptorMenloMcpuStatsHistTruncateOverrunDelta OBJECT-TYPE
    SYNTAX       Unsigned64
    MAX-ACCESS   read-only
    STATUS       current
    DESCRIPTION
        "Cisco UCS adaptor:MenloMcpuStatsHist:truncateOverrunDelta
        managed object property"
    ::= { cucsAdaptorMenloMcpuStatsHistEntry 25 }

cucsAdaptorMenloMcpuStatsHistTruncateOverrunDeltaAvg OBJECT-TYPE
    SYNTAX       Unsigned64
    MAX-ACCESS   read-only
    STATUS       current
    DESCRIPTION
        "Cisco UCS adaptor:MenloMcpuStatsHist:truncateOverrunDeltaAvg
        managed object property"
    ::= { cucsAdaptorMenloMcpuStatsHistEntry 26 }

cucsAdaptorMenloMcpuStatsHistTruncateOverrunDeltaMax OBJECT-TYPE
    SYNTAX       Unsigned64
    MAX-ACCESS   read-only
    STATUS       current
    DESCRIPTION
        "Cisco UCS adaptor:MenloMcpuStatsHist:truncateOverrunDeltaMax
        managed object property"
    ::= { cucsAdaptorMenloMcpuStatsHistEntry 27 }

cucsAdaptorMenloMcpuStatsHistTruncateOverrunDeltaMin OBJECT-TYPE
    SYNTAX       Unsigned64
    MAX-ACCESS   read-only
    STATUS       current
    DESCRIPTION
        "Cisco UCS adaptor:MenloMcpuStatsHist:truncateOverrunDeltaMin
        managed object property"
    ::= { cucsAdaptorMenloMcpuStatsHistEntry 28 }

cucsAdaptorMenloNetEgStatsTable OBJECT-TYPE
    SYNTAX           SEQUENCE OF CucsAdaptorMenloNetEgStatsEntry
    MAX-ACCESS       not-accessible
    STATUS           current
    DESCRIPTION
        "Cisco UCS adaptor:MenloNetEgStats managed object table"
    ::= { cucsAdaptorObjects 73 }

cucsAdaptorMenloNetEgStatsEntry OBJECT-TYPE
    SYNTAX           CucsAdaptorMenloNetEgStatsEntry
    MAX-ACCESS       not-accessible
    STATUS           current
    DESCRIPTION
        "Entry for the cucsAdaptorMenloNetEgStatsTable table."
    INDEX { cucsAdaptorMenloNetEgStatsInstanceId }
    ::= { cucsAdaptorMenloNetEgStatsTable 1 }

CucsAdaptorMenloNetEgStatsEntry ::= SEQUENCE {
    cucsAdaptorMenloNetEgStatsInstanceId                             CucsManagedObjectId,
    cucsAdaptorMenloNetEgStatsDn                                     CucsManagedObjectDn,
    cucsAdaptorMenloNetEgStatsRn                                     SnmpAdminString,
    cucsAdaptorMenloNetEgStatsDropCmd                                Unsigned64,
    cucsAdaptorMenloNetEgStatsDropCmdDelta                           Counter64,
    cucsAdaptorMenloNetEgStatsDropCmdDeltaAvg                        Unsigned64,
    cucsAdaptorMenloNetEgStatsDropCmdDeltaMax                        Unsigned64,
    cucsAdaptorMenloNetEgStatsDropCmdDeltaMin                        Unsigned64,
    cucsAdaptorMenloNetEgStatsDropLifCfgInvalid                      Unsigned64,
    cucsAdaptorMenloNetEgStatsDropLifCfgInvalidDelta                 Counter64,
    cucsAdaptorMenloNetEgStatsDropLifCfgInvalidDeltaAvg              Unsigned64,
    cucsAdaptorMenloNetEgStatsDropLifCfgInvalidDeltaMax              Unsigned64,
    cucsAdaptorMenloNetEgStatsDropLifCfgInvalidDeltaMin              Unsigned64,
    cucsAdaptorMenloNetEgStatsDropLifMapNoHit                        Unsigned64,
    cucsAdaptorMenloNetEgStatsDropLifMapNoHitDelta                   Counter64,
    cucsAdaptorMenloNetEgStatsDropLifMapNoHitDeltaAvg                Unsigned64,
    cucsAdaptorMenloNetEgStatsDropLifMapNoHitDeltaMax                Unsigned64,
    cucsAdaptorMenloNetEgStatsDropLifMapNoHitDeltaMin                Unsigned64,
    cucsAdaptorMenloNetEgStatsDropSrcBind                            Unsigned64,
    cucsAdaptorMenloNetEgStatsDropSrcBindDelta                       Counter64,
    cucsAdaptorMenloNetEgStatsDropSrcBindDeltaAvg                    Unsigned64,
    cucsAdaptorMenloNetEgStatsDropSrcBindDeltaMax                    Unsigned64,
    cucsAdaptorMenloNetEgStatsDropSrcBindDeltaMin                    Unsigned64,
    cucsAdaptorMenloNetEgStatsIntervals                              Gauge32,
    cucsAdaptorMenloNetEgStatsLearnReqDrop                           Unsigned64,
    cucsAdaptorMenloNetEgStatsLearnReqDropDelta                      Counter64,
    cucsAdaptorMenloNetEgStatsLearnReqDropDeltaAvg                   Unsigned64,
    cucsAdaptorMenloNetEgStatsLearnReqDropDeltaMax                   Unsigned64,
    cucsAdaptorMenloNetEgStatsLearnReqDropDeltaMin                   Unsigned64,
    cucsAdaptorMenloNetEgStatsMenloNetIndex                          CucsAdaptorMenloStatsIndex,
    cucsAdaptorMenloNetEgStatsSuspect                                TruthValue,
    cucsAdaptorMenloNetEgStatsThresholded                            CucsAdaptorMenloNetEgStatsThresholded,
    cucsAdaptorMenloNetEgStatsTimeCollected                          DateAndTime,
    cucsAdaptorMenloNetEgStatsUpdate                                 Gauge32
}

cucsAdaptorMenloNetEgStatsInstanceId OBJECT-TYPE
    SYNTAX       CucsManagedObjectId
    MAX-ACCESS   not-accessible
    STATUS       current
    DESCRIPTION
        "Instance identifier of the managed object."
    ::= { cucsAdaptorMenloNetEgStatsEntry 1 }

cucsAdaptorMenloNetEgStatsDn OBJECT-TYPE
    SYNTAX       CucsManagedObjectDn
    MAX-ACCESS   read-only
    STATUS       current
    DESCRIPTION
        "Cisco UCS adaptor:MenloNetEgStats:dn managed object property"
    ::= { cucsAdaptorMenloNetEgStatsEntry 2 }

cucsAdaptorMenloNetEgStatsRn OBJECT-TYPE
    SYNTAX       SnmpAdminString
    MAX-ACCESS   read-only
    STATUS       current
    DESCRIPTION
        "Cisco UCS adaptor:MenloNetEgStats:rn managed object property"
    ::= { cucsAdaptorMenloNetEgStatsEntry 3 }

cucsAdaptorMenloNetEgStatsDropCmd OBJECT-TYPE
    SYNTAX       Unsigned64
    MAX-ACCESS   read-only
    STATUS       current
    DESCRIPTION
        "Cisco UCS adaptor:MenloNetEgStats:dropCmd managed
        object property"
    ::= { cucsAdaptorMenloNetEgStatsEntry 4 }

cucsAdaptorMenloNetEgStatsDropCmdDelta OBJECT-TYPE
    SYNTAX       Counter64
    MAX-ACCESS   read-only
    STATUS       current
    DESCRIPTION
        "Cisco UCS adaptor:MenloNetEgStats:dropCmdDelta
        managed object property"
    ::= { cucsAdaptorMenloNetEgStatsEntry 5 }

cucsAdaptorMenloNetEgStatsDropCmdDeltaAvg OBJECT-TYPE
    SYNTAX       Unsigned64
    MAX-ACCESS   read-only
    STATUS       current
    DESCRIPTION
        "Cisco UCS adaptor:MenloNetEgStats:dropCmdDeltaAvg
        managed object property"
    ::= { cucsAdaptorMenloNetEgStatsEntry 6 }

cucsAdaptorMenloNetEgStatsDropCmdDeltaMax OBJECT-TYPE
    SYNTAX       Unsigned64
    MAX-ACCESS   read-only
    STATUS       current
    DESCRIPTION
        "Cisco UCS adaptor:MenloNetEgStats:dropCmdDeltaMax
        managed object property"
    ::= { cucsAdaptorMenloNetEgStatsEntry 7 }

cucsAdaptorMenloNetEgStatsDropCmdDeltaMin OBJECT-TYPE
    SYNTAX       Unsigned64
    MAX-ACCESS   read-only
    STATUS       current
    DESCRIPTION
        "Cisco UCS adaptor:MenloNetEgStats:dropCmdDeltaMin
        managed object property"
    ::= { cucsAdaptorMenloNetEgStatsEntry 8 }

cucsAdaptorMenloNetEgStatsDropLifCfgInvalid OBJECT-TYPE
    SYNTAX       Unsigned64
    MAX-ACCESS   read-only
    STATUS       current
    DESCRIPTION
        "Cisco UCS adaptor:MenloNetEgStats:dropLifCfgInvalid
        managed object property"
    ::= { cucsAdaptorMenloNetEgStatsEntry 9 }

cucsAdaptorMenloNetEgStatsDropLifCfgInvalidDelta OBJECT-TYPE
    SYNTAX       Counter64
    MAX-ACCESS   read-only
    STATUS       current
    DESCRIPTION
        "Cisco UCS adaptor:MenloNetEgStats:dropLifCfgInvalidDelta
        managed object property"
    ::= { cucsAdaptorMenloNetEgStatsEntry 10 }

cucsAdaptorMenloNetEgStatsDropLifCfgInvalidDeltaAvg OBJECT-TYPE
    SYNTAX       Unsigned64
    MAX-ACCESS   read-only
    STATUS       current
    DESCRIPTION
        "Cisco UCS adaptor:MenloNetEgStats:dropLifCfgInvalidDeltaAvg
        managed object property"
    ::= { cucsAdaptorMenloNetEgStatsEntry 11 }

cucsAdaptorMenloNetEgStatsDropLifCfgInvalidDeltaMax OBJECT-TYPE
    SYNTAX       Unsigned64
    MAX-ACCESS   read-only
    STATUS       current
    DESCRIPTION
        "Cisco UCS adaptor:MenloNetEgStats:dropLifCfgInvalidDeltaMax
        managed object property"
    ::= { cucsAdaptorMenloNetEgStatsEntry 12 }

cucsAdaptorMenloNetEgStatsDropLifCfgInvalidDeltaMin OBJECT-TYPE
    SYNTAX       Unsigned64
    MAX-ACCESS   read-only
    STATUS       current
    DESCRIPTION
        "Cisco UCS adaptor:MenloNetEgStats:dropLifCfgInvalidDeltaMin
        managed object property"
    ::= { cucsAdaptorMenloNetEgStatsEntry 13 }

cucsAdaptorMenloNetEgStatsDropLifMapNoHit OBJECT-TYPE
    SYNTAX       Unsigned64
    MAX-ACCESS   read-only
    STATUS       current
    DESCRIPTION
        "Cisco UCS adaptor:MenloNetEgStats:dropLifMapNoHit
        managed object property"
    ::= { cucsAdaptorMenloNetEgStatsEntry 14 }

cucsAdaptorMenloNetEgStatsDropLifMapNoHitDelta OBJECT-TYPE
    SYNTAX       Counter64
    MAX-ACCESS   read-only
    STATUS       current
    DESCRIPTION
        "Cisco UCS adaptor:MenloNetEgStats:dropLifMapNoHitDelta
        managed object property"
    ::= { cucsAdaptorMenloNetEgStatsEntry 15 }

cucsAdaptorMenloNetEgStatsDropLifMapNoHitDeltaAvg OBJECT-TYPE
    SYNTAX       Unsigned64
    MAX-ACCESS   read-only
    STATUS       current
    DESCRIPTION
        "Cisco UCS adaptor:MenloNetEgStats:dropLifMapNoHitDeltaAvg
        managed object property"
    ::= { cucsAdaptorMenloNetEgStatsEntry 16 }

cucsAdaptorMenloNetEgStatsDropLifMapNoHitDeltaMax OBJECT-TYPE
    SYNTAX       Unsigned64
    MAX-ACCESS   read-only
    STATUS       current
    DESCRIPTION
        "Cisco UCS adaptor:MenloNetEgStats:dropLifMapNoHitDeltaMax
        managed object property"
    ::= { cucsAdaptorMenloNetEgStatsEntry 17 }

cucsAdaptorMenloNetEgStatsDropLifMapNoHitDeltaMin OBJECT-TYPE
    SYNTAX       Unsigned64
    MAX-ACCESS   read-only
    STATUS       current
    DESCRIPTION
        "Cisco UCS adaptor:MenloNetEgStats:dropLifMapNoHitDeltaMin
        managed object property"
    ::= { cucsAdaptorMenloNetEgStatsEntry 18 }

cucsAdaptorMenloNetEgStatsDropSrcBind OBJECT-TYPE
    SYNTAX       Unsigned64
    MAX-ACCESS   read-only
    STATUS       current
    DESCRIPTION
        "Cisco UCS adaptor:MenloNetEgStats:dropSrcBind
        managed object property"
    ::= { cucsAdaptorMenloNetEgStatsEntry 19 }

cucsAdaptorMenloNetEgStatsDropSrcBindDelta OBJECT-TYPE
    SYNTAX       Counter64
    MAX-ACCESS   read-only
    STATUS       current
    DESCRIPTION
        "Cisco UCS adaptor:MenloNetEgStats:dropSrcBindDelta
        managed object property"
    ::= { cucsAdaptorMenloNetEgStatsEntry 20 }

cucsAdaptorMenloNetEgStatsDropSrcBindDeltaAvg OBJECT-TYPE
    SYNTAX       Unsigned64
    MAX-ACCESS   read-only
    STATUS       current
    DESCRIPTION
        "Cisco UCS adaptor:MenloNetEgStats:dropSrcBindDeltaAvg
        managed object property"
    ::= { cucsAdaptorMenloNetEgStatsEntry 21 }

cucsAdaptorMenloNetEgStatsDropSrcBindDeltaMax OBJECT-TYPE
    SYNTAX       Unsigned64
    MAX-ACCESS   read-only
    STATUS       current
    DESCRIPTION
        "Cisco UCS adaptor:MenloNetEgStats:dropSrcBindDeltaMax
        managed object property"
    ::= { cucsAdaptorMenloNetEgStatsEntry 22 }

cucsAdaptorMenloNetEgStatsDropSrcBindDeltaMin OBJECT-TYPE
    SYNTAX       Unsigned64
    MAX-ACCESS   read-only
    STATUS       current
    DESCRIPTION
        "Cisco UCS adaptor:MenloNetEgStats:dropSrcBindDeltaMin
        managed object property"
    ::= { cucsAdaptorMenloNetEgStatsEntry 23 }

cucsAdaptorMenloNetEgStatsIntervals OBJECT-TYPE
    SYNTAX       Gauge32
    MAX-ACCESS   read-only
    STATUS       current
    DESCRIPTION
        "Cisco UCS adaptor:MenloNetEgStats:intervals managed
        object property"
    ::= { cucsAdaptorMenloNetEgStatsEntry 24 }

cucsAdaptorMenloNetEgStatsLearnReqDrop OBJECT-TYPE
    SYNTAX       Unsigned64
    MAX-ACCESS   read-only
    STATUS       current
    DESCRIPTION
        "Cisco UCS adaptor:MenloNetEgStats:learnReqDrop
        managed object property"
    ::= { cucsAdaptorMenloNetEgStatsEntry 25 }

cucsAdaptorMenloNetEgStatsLearnReqDropDelta OBJECT-TYPE
    SYNTAX       Counter64
    MAX-ACCESS   read-only
    STATUS       current
    DESCRIPTION
        "Cisco UCS adaptor:MenloNetEgStats:learnReqDropDelta
        managed object property"
    ::= { cucsAdaptorMenloNetEgStatsEntry 26 }

cucsAdaptorMenloNetEgStatsLearnReqDropDeltaAvg OBJECT-TYPE
    SYNTAX       Unsigned64
    MAX-ACCESS   read-only
    STATUS       current
    DESCRIPTION
        "Cisco UCS adaptor:MenloNetEgStats:learnReqDropDeltaAvg
        managed object property"
    ::= { cucsAdaptorMenloNetEgStatsEntry 27 }

cucsAdaptorMenloNetEgStatsLearnReqDropDeltaMax OBJECT-TYPE
    SYNTAX       Unsigned64
    MAX-ACCESS   read-only
    STATUS       current
    DESCRIPTION
        "Cisco UCS adaptor:MenloNetEgStats:learnReqDropDeltaMax
        managed object property"
    ::= { cucsAdaptorMenloNetEgStatsEntry 28 }

cucsAdaptorMenloNetEgStatsLearnReqDropDeltaMin OBJECT-TYPE
    SYNTAX       Unsigned64
    MAX-ACCESS   read-only
    STATUS       current
    DESCRIPTION
        "Cisco UCS adaptor:MenloNetEgStats:learnReqDropDeltaMin
        managed object property"
    ::= { cucsAdaptorMenloNetEgStatsEntry 29 }

cucsAdaptorMenloNetEgStatsMenloNetIndex OBJECT-TYPE
    SYNTAX       CucsAdaptorMenloStatsIndex
    MAX-ACCESS   read-only
    STATUS       current
    DESCRIPTION
        "Cisco UCS adaptor:MenloNetEgStats:menloNetIndex
        managed object property"
    ::= { cucsAdaptorMenloNetEgStatsEntry 30 }

cucsAdaptorMenloNetEgStatsSuspect OBJECT-TYPE
    SYNTAX       TruthValue
    MAX-ACCESS   read-only
    STATUS       current
    DESCRIPTION
        "Cisco UCS adaptor:MenloNetEgStats:suspect managed
        object property"
    ::= { cucsAdaptorMenloNetEgStatsEntry 31 }

cucsAdaptorMenloNetEgStatsThresholded OBJECT-TYPE
    SYNTAX       CucsAdaptorMenloNetEgStatsThresholded
    MAX-ACCESS   read-only
    STATUS       current
    DESCRIPTION
        "Cisco UCS adaptor:MenloNetEgStats:thresholded
        managed object property"
    ::= { cucsAdaptorMenloNetEgStatsEntry 32 }

cucsAdaptorMenloNetEgStatsTimeCollected OBJECT-TYPE
    SYNTAX       DateAndTime
    MAX-ACCESS   read-only
    STATUS       current
    DESCRIPTION
        "Cisco UCS adaptor:MenloNetEgStats:timeCollected
        managed object property"
    ::= { cucsAdaptorMenloNetEgStatsEntry 33 }

cucsAdaptorMenloNetEgStatsUpdate OBJECT-TYPE
    SYNTAX       Gauge32
    MAX-ACCESS   read-only
    STATUS       current
    DESCRIPTION
        "Cisco UCS adaptor:MenloNetEgStats:update managed object property"
    ::= { cucsAdaptorMenloNetEgStatsEntry 34 }

cucsAdaptorMenloNetEgStatsHistTable OBJECT-TYPE
    SYNTAX           SEQUENCE OF CucsAdaptorMenloNetEgStatsHistEntry
    MAX-ACCESS       not-accessible
    STATUS           current
    DESCRIPTION
        "Cisco UCS adaptor:MenloNetEgStatsHist managed object table"
    ::= { cucsAdaptorObjects 74 }

cucsAdaptorMenloNetEgStatsHistEntry OBJECT-TYPE
    SYNTAX           CucsAdaptorMenloNetEgStatsHistEntry
    MAX-ACCESS       not-accessible
    STATUS           current
    DESCRIPTION
        "Entry for the cucsAdaptorMenloNetEgStatsHistTable table."
    INDEX { cucsAdaptorMenloNetEgStatsHistInstanceId }
    ::= { cucsAdaptorMenloNetEgStatsHistTable 1 }

CucsAdaptorMenloNetEgStatsHistEntry ::= SEQUENCE {
    cucsAdaptorMenloNetEgStatsHistInstanceId                         CucsManagedObjectId,
    cucsAdaptorMenloNetEgStatsHistDn                                 CucsManagedObjectDn,
    cucsAdaptorMenloNetEgStatsHistRn                                 SnmpAdminString,
    cucsAdaptorMenloNetEgStatsHistDropCmd                            Unsigned64,
    cucsAdaptorMenloNetEgStatsHistDropCmdDelta                       Unsigned64,
    cucsAdaptorMenloNetEgStatsHistDropCmdDeltaAvg                    Unsigned64,
    cucsAdaptorMenloNetEgStatsHistDropCmdDeltaMax                    Unsigned64,
    cucsAdaptorMenloNetEgStatsHistDropCmdDeltaMin                    Unsigned64,
    cucsAdaptorMenloNetEgStatsHistDropLifCfgInvalid                  Unsigned64,
    cucsAdaptorMenloNetEgStatsHistDropLifCfgInvalidDelta             Unsigned64,
    cucsAdaptorMenloNetEgStatsHistDropLifCfgInvalidDeltaAvg          Unsigned64,
    cucsAdaptorMenloNetEgStatsHistDropLifCfgInvalidDeltaMax          Unsigned64,
    cucsAdaptorMenloNetEgStatsHistDropLifCfgInvalidDeltaMin          Unsigned64,
    cucsAdaptorMenloNetEgStatsHistDropLifMapNoHit                    Unsigned64,
    cucsAdaptorMenloNetEgStatsHistDropLifMapNoHitDelta               Unsigned64,
    cucsAdaptorMenloNetEgStatsHistDropLifMapNoHitDeltaAvg            Unsigned64,
    cucsAdaptorMenloNetEgStatsHistDropLifMapNoHitDeltaMax            Unsigned64,
    cucsAdaptorMenloNetEgStatsHistDropLifMapNoHitDeltaMin            Unsigned64,
    cucsAdaptorMenloNetEgStatsHistDropSrcBind                        Unsigned64,
    cucsAdaptorMenloNetEgStatsHistDropSrcBindDelta                   Unsigned64,
    cucsAdaptorMenloNetEgStatsHistDropSrcBindDeltaAvg                Unsigned64,
    cucsAdaptorMenloNetEgStatsHistDropSrcBindDeltaMax                Unsigned64,
    cucsAdaptorMenloNetEgStatsHistDropSrcBindDeltaMin                Unsigned64,
    cucsAdaptorMenloNetEgStatsHistId                                 Unsigned64,
    cucsAdaptorMenloNetEgStatsHistLearnReqDrop                       Unsigned64,
    cucsAdaptorMenloNetEgStatsHistLearnReqDropDelta                  Unsigned64,
    cucsAdaptorMenloNetEgStatsHistLearnReqDropDeltaAvg               Unsigned64,
    cucsAdaptorMenloNetEgStatsHistLearnReqDropDeltaMax               Unsigned64,
    cucsAdaptorMenloNetEgStatsHistLearnReqDropDeltaMin               Unsigned64,
    cucsAdaptorMenloNetEgStatsHistMostRecent                         TruthValue,
    cucsAdaptorMenloNetEgStatsHistSuspect                            TruthValue,
    cucsAdaptorMenloNetEgStatsHistThresholded                        CucsAdaptorMenloNetEgStatsHistThresholded,
    cucsAdaptorMenloNetEgStatsHistTimeCollected                      DateAndTime
}

cucsAdaptorMenloNetEgStatsHistInstanceId OBJECT-TYPE
    SYNTAX       CucsManagedObjectId
    MAX-ACCESS   not-accessible
    STATUS       current
    DESCRIPTION
        "Instance identifier of the managed object."
    ::= { cucsAdaptorMenloNetEgStatsHistEntry 1 }

cucsAdaptorMenloNetEgStatsHistDn OBJECT-TYPE
    SYNTAX       CucsManagedObjectDn
    MAX-ACCESS   read-only
    STATUS       current
    DESCRIPTION
        "Cisco UCS adaptor:MenloNetEgStatsHist:dn managed object property"
    ::= { cucsAdaptorMenloNetEgStatsHistEntry 2 }

cucsAdaptorMenloNetEgStatsHistRn OBJECT-TYPE
    SYNTAX       SnmpAdminString
    MAX-ACCESS   read-only
    STATUS       current
    DESCRIPTION
        "Cisco UCS adaptor:MenloNetEgStatsHist:rn managed object property"
    ::= { cucsAdaptorMenloNetEgStatsHistEntry 3 }

cucsAdaptorMenloNetEgStatsHistDropCmd OBJECT-TYPE
    SYNTAX       Unsigned64
    MAX-ACCESS   read-only
    STATUS       current
    DESCRIPTION
        "Cisco UCS adaptor:MenloNetEgStatsHist:dropCmd
        managed object property"
    ::= { cucsAdaptorMenloNetEgStatsHistEntry 4 }

cucsAdaptorMenloNetEgStatsHistDropCmdDelta OBJECT-TYPE
    SYNTAX       Unsigned64
    MAX-ACCESS   read-only
    STATUS       current
    DESCRIPTION
        "Cisco UCS adaptor:MenloNetEgStatsHist:dropCmdDelta
        managed object property"
    ::= { cucsAdaptorMenloNetEgStatsHistEntry 5 }

cucsAdaptorMenloNetEgStatsHistDropCmdDeltaAvg OBJECT-TYPE
    SYNTAX       Unsigned64
    MAX-ACCESS   read-only
    STATUS       current
    DESCRIPTION
        "Cisco UCS adaptor:MenloNetEgStatsHist:dropCmdDeltaAvg
        managed object property"
    ::= { cucsAdaptorMenloNetEgStatsHistEntry 6 }

cucsAdaptorMenloNetEgStatsHistDropCmdDeltaMax OBJECT-TYPE
    SYNTAX       Unsigned64
    MAX-ACCESS   read-only
    STATUS       current
    DESCRIPTION
        "Cisco UCS adaptor:MenloNetEgStatsHist:dropCmdDeltaMax
        managed object property"
    ::= { cucsAdaptorMenloNetEgStatsHistEntry 7 }

cucsAdaptorMenloNetEgStatsHistDropCmdDeltaMin OBJECT-TYPE
    SYNTAX       Unsigned64
    MAX-ACCESS   read-only
    STATUS       current
    DESCRIPTION
        "Cisco UCS adaptor:MenloNetEgStatsHist:dropCmdDeltaMin
        managed object property"
    ::= { cucsAdaptorMenloNetEgStatsHistEntry 8 }

cucsAdaptorMenloNetEgStatsHistDropLifCfgInvalid OBJECT-TYPE
    SYNTAX       Unsigned64
    MAX-ACCESS   read-only
    STATUS       current
    DESCRIPTION
        "Cisco UCS adaptor:MenloNetEgStatsHist:dropLifCfgInvalid
        managed object property"
    ::= { cucsAdaptorMenloNetEgStatsHistEntry 9 }

cucsAdaptorMenloNetEgStatsHistDropLifCfgInvalidDelta OBJECT-TYPE
    SYNTAX       Unsigned64
    MAX-ACCESS   read-only
    STATUS       current
    DESCRIPTION
        "Cisco UCS adaptor:MenloNetEgStatsHist:dropLifCfgInvalidDelta
        managed object property"
    ::= { cucsAdaptorMenloNetEgStatsHistEntry 10 }

cucsAdaptorMenloNetEgStatsHistDropLifCfgInvalidDeltaAvg OBJECT-TYPE
    SYNTAX       Unsigned64
    MAX-ACCESS   read-only
    STATUS       current
    DESCRIPTION
        "Cisco UCS adaptor:MenloNetEgStatsHist:dropLifCfgInvalidDeltaAvg
        managed object property"
    ::= { cucsAdaptorMenloNetEgStatsHistEntry 11 }

cucsAdaptorMenloNetEgStatsHistDropLifCfgInvalidDeltaMax OBJECT-TYPE
    SYNTAX       Unsigned64
    MAX-ACCESS   read-only
    STATUS       current
    DESCRIPTION
        "Cisco UCS adaptor:MenloNetEgStatsHist:dropLifCfgInvalidDeltaMax
        managed object property"
    ::= { cucsAdaptorMenloNetEgStatsHistEntry 12 }

cucsAdaptorMenloNetEgStatsHistDropLifCfgInvalidDeltaMin OBJECT-TYPE
    SYNTAX       Unsigned64
    MAX-ACCESS   read-only
    STATUS       current
    DESCRIPTION
        "Cisco UCS adaptor:MenloNetEgStatsHist:dropLifCfgInvalidDeltaMin
        managed object property"
    ::= { cucsAdaptorMenloNetEgStatsHistEntry 13 }

cucsAdaptorMenloNetEgStatsHistDropLifMapNoHit OBJECT-TYPE
    SYNTAX       Unsigned64
    MAX-ACCESS   read-only
    STATUS       current
    DESCRIPTION
        "Cisco UCS adaptor:MenloNetEgStatsHist:dropLifMapNoHit
        managed object property"
    ::= { cucsAdaptorMenloNetEgStatsHistEntry 14 }

cucsAdaptorMenloNetEgStatsHistDropLifMapNoHitDelta OBJECT-TYPE
    SYNTAX       Unsigned64
    MAX-ACCESS   read-only
    STATUS       current
    DESCRIPTION
        "Cisco UCS adaptor:MenloNetEgStatsHist:dropLifMapNoHitDelta
        managed object property"
    ::= { cucsAdaptorMenloNetEgStatsHistEntry 15 }

cucsAdaptorMenloNetEgStatsHistDropLifMapNoHitDeltaAvg OBJECT-TYPE
    SYNTAX       Unsigned64
    MAX-ACCESS   read-only
    STATUS       current
    DESCRIPTION
        "Cisco UCS adaptor:MenloNetEgStatsHist:dropLifMapNoHitDeltaAvg
        managed object property"
    ::= { cucsAdaptorMenloNetEgStatsHistEntry 16 }

cucsAdaptorMenloNetEgStatsHistDropLifMapNoHitDeltaMax OBJECT-TYPE
    SYNTAX       Unsigned64
    MAX-ACCESS   read-only
    STATUS       current
    DESCRIPTION
        "Cisco UCS adaptor:MenloNetEgStatsHist:dropLifMapNoHitDeltaMax
        managed object property"
    ::= { cucsAdaptorMenloNetEgStatsHistEntry 17 }

cucsAdaptorMenloNetEgStatsHistDropLifMapNoHitDeltaMin OBJECT-TYPE
    SYNTAX       Unsigned64
    MAX-ACCESS   read-only
    STATUS       current
    DESCRIPTION
        "Cisco UCS adaptor:MenloNetEgStatsHist:dropLifMapNoHitDeltaMin
        managed object property"
    ::= { cucsAdaptorMenloNetEgStatsHistEntry 18 }

cucsAdaptorMenloNetEgStatsHistDropSrcBind OBJECT-TYPE
    SYNTAX       Unsigned64
    MAX-ACCESS   read-only
    STATUS       current
    DESCRIPTION
        "Cisco UCS adaptor:MenloNetEgStatsHist:dropSrcBind
        managed object property"
    ::= { cucsAdaptorMenloNetEgStatsHistEntry 19 }

cucsAdaptorMenloNetEgStatsHistDropSrcBindDelta OBJECT-TYPE
    SYNTAX       Unsigned64
    MAX-ACCESS   read-only
    STATUS       current
    DESCRIPTION
        "Cisco UCS adaptor:MenloNetEgStatsHist:dropSrcBindDelta
        managed object property"
    ::= { cucsAdaptorMenloNetEgStatsHistEntry 20 }

cucsAdaptorMenloNetEgStatsHistDropSrcBindDeltaAvg OBJECT-TYPE
    SYNTAX       Unsigned64
    MAX-ACCESS   read-only
    STATUS       current
    DESCRIPTION
        "Cisco UCS adaptor:MenloNetEgStatsHist:dropSrcBindDeltaAvg
        managed object property"
    ::= { cucsAdaptorMenloNetEgStatsHistEntry 21 }

cucsAdaptorMenloNetEgStatsHistDropSrcBindDeltaMax OBJECT-TYPE
    SYNTAX       Unsigned64
    MAX-ACCESS   read-only
    STATUS       current
    DESCRIPTION
        "Cisco UCS adaptor:MenloNetEgStatsHist:dropSrcBindDeltaMax
        managed object property"
    ::= { cucsAdaptorMenloNetEgStatsHistEntry 22 }

cucsAdaptorMenloNetEgStatsHistDropSrcBindDeltaMin OBJECT-TYPE
    SYNTAX       Unsigned64
    MAX-ACCESS   read-only
    STATUS       current
    DESCRIPTION
        "Cisco UCS adaptor:MenloNetEgStatsHist:dropSrcBindDeltaMin
        managed object property"
    ::= { cucsAdaptorMenloNetEgStatsHistEntry 23 }

cucsAdaptorMenloNetEgStatsHistId OBJECT-TYPE
    SYNTAX       Unsigned64
    MAX-ACCESS   read-only
    STATUS       current
    DESCRIPTION
        "Cisco UCS adaptor:MenloNetEgStatsHist:id managed object property"
    ::= { cucsAdaptorMenloNetEgStatsHistEntry 24 }

cucsAdaptorMenloNetEgStatsHistLearnReqDrop OBJECT-TYPE
    SYNTAX       Unsigned64
    MAX-ACCESS   read-only
    STATUS       current
    DESCRIPTION
        "Cisco UCS adaptor:MenloNetEgStatsHist:learnReqDrop
        managed object property"
    ::= { cucsAdaptorMenloNetEgStatsHistEntry 25 }

cucsAdaptorMenloNetEgStatsHistLearnReqDropDelta OBJECT-TYPE
    SYNTAX       Unsigned64
    MAX-ACCESS   read-only
    STATUS       current
    DESCRIPTION
        "Cisco UCS adaptor:MenloNetEgStatsHist:learnReqDropDelta
        managed object property"
    ::= { cucsAdaptorMenloNetEgStatsHistEntry 26 }

cucsAdaptorMenloNetEgStatsHistLearnReqDropDeltaAvg OBJECT-TYPE
    SYNTAX       Unsigned64
    MAX-ACCESS   read-only
    STATUS       current
    DESCRIPTION
        "Cisco UCS adaptor:MenloNetEgStatsHist:learnReqDropDeltaAvg
        managed object property"
    ::= { cucsAdaptorMenloNetEgStatsHistEntry 27 }

cucsAdaptorMenloNetEgStatsHistLearnReqDropDeltaMax OBJECT-TYPE
    SYNTAX       Unsigned64
    MAX-ACCESS   read-only
    STATUS       current
    DESCRIPTION
        "Cisco UCS adaptor:MenloNetEgStatsHist:learnReqDropDeltaMax
        managed object property"
    ::= { cucsAdaptorMenloNetEgStatsHistEntry 28 }

cucsAdaptorMenloNetEgStatsHistLearnReqDropDeltaMin OBJECT-TYPE
    SYNTAX       Unsigned64
    MAX-ACCESS   read-only
    STATUS       current
    DESCRIPTION
        "Cisco UCS adaptor:MenloNetEgStatsHist:learnReqDropDeltaMin
        managed object property"
    ::= { cucsAdaptorMenloNetEgStatsHistEntry 29 }

cucsAdaptorMenloNetEgStatsHistMostRecent OBJECT-TYPE
    SYNTAX       TruthValue
    MAX-ACCESS   read-only
    STATUS       current
    DESCRIPTION
        "Cisco UCS adaptor:MenloNetEgStatsHist:mostRecent
        managed object property"
    ::= { cucsAdaptorMenloNetEgStatsHistEntry 30 }

cucsAdaptorMenloNetEgStatsHistSuspect OBJECT-TYPE
    SYNTAX       TruthValue
    MAX-ACCESS   read-only
    STATUS       current
    DESCRIPTION
        "Cisco UCS adaptor:MenloNetEgStatsHist:suspect
        managed object property"
    ::= { cucsAdaptorMenloNetEgStatsHistEntry 31 }

cucsAdaptorMenloNetEgStatsHistThresholded OBJECT-TYPE
    SYNTAX       CucsAdaptorMenloNetEgStatsHistThresholded
    MAX-ACCESS   read-only
    STATUS       current
    DESCRIPTION
        "Cisco UCS adaptor:MenloNetEgStatsHist:thresholded
        managed object property"
    ::= { cucsAdaptorMenloNetEgStatsHistEntry 32 }

cucsAdaptorMenloNetEgStatsHistTimeCollected OBJECT-TYPE
    SYNTAX       DateAndTime
    MAX-ACCESS   read-only
    STATUS       current
    DESCRIPTION
        "Cisco UCS adaptor:MenloNetEgStatsHist:timeCollected
        managed object property"
    ::= { cucsAdaptorMenloNetEgStatsHistEntry 33 }

cucsAdaptorMenloNetInStatsTable OBJECT-TYPE
    SYNTAX           SEQUENCE OF CucsAdaptorMenloNetInStatsEntry
    MAX-ACCESS       not-accessible
    STATUS           current
    DESCRIPTION
        "Cisco UCS adaptor:MenloNetInStats managed object table"
    ::= { cucsAdaptorObjects 75 }

cucsAdaptorMenloNetInStatsEntry OBJECT-TYPE
    SYNTAX           CucsAdaptorMenloNetInStatsEntry
    MAX-ACCESS       not-accessible
    STATUS           current
    DESCRIPTION
        "Entry for the cucsAdaptorMenloNetInStatsTable table."
    INDEX { cucsAdaptorMenloNetInStatsInstanceId }
    ::= { cucsAdaptorMenloNetInStatsTable 1 }

CucsAdaptorMenloNetInStatsEntry ::= SEQUENCE {
    cucsAdaptorMenloNetInStatsInstanceId                             CucsManagedObjectId,
    cucsAdaptorMenloNetInStatsDn                                     CucsManagedObjectDn,
    cucsAdaptorMenloNetInStatsRn                                     SnmpAdminString,
    cucsAdaptorMenloNetInStatsDropFcLifInvalid                       Unsigned64,
    cucsAdaptorMenloNetInStatsDropFcLifInvalidDelta                  Counter64,
    cucsAdaptorMenloNetInStatsDropFcLifInvalidDeltaAvg               Unsigned64,
    cucsAdaptorMenloNetInStatsDropFcLifInvalidDeltaMax               Unsigned64,
    cucsAdaptorMenloNetInStatsDropFcLifInvalidDeltaMin               Unsigned64,
    cucsAdaptorMenloNetInStatsDropFcMulticast                        Unsigned64,
    cucsAdaptorMenloNetInStatsDropFcMulticastDelta                   Counter64,
    cucsAdaptorMenloNetInStatsDropFcMulticastDeltaAvg                Unsigned64,
    cucsAdaptorMenloNetInStatsDropFcMulticastDeltaMax                Unsigned64,
    cucsAdaptorMenloNetInStatsDropFcMulticastDeltaMin                Unsigned64,
    cucsAdaptorMenloNetInStatsDropNullPif                            Unsigned64,
    cucsAdaptorMenloNetInStatsDropNullPifDelta                       Counter64,
    cucsAdaptorMenloNetInStatsDropNullPifDeltaAvg                    Unsigned64,
    cucsAdaptorMenloNetInStatsDropNullPifDeltaMax                    Unsigned64,
    cucsAdaptorMenloNetInStatsDropNullPifDeltaMin                    Unsigned64,
    cucsAdaptorMenloNetInStatsFwdLookupNoHit                         Unsigned64,
    cucsAdaptorMenloNetInStatsFwdLookupNoHitDelta                    Counter64,
    cucsAdaptorMenloNetInStatsFwdLookupNoHitDeltaAvg                 Unsigned64,
    cucsAdaptorMenloNetInStatsFwdLookupNoHitDeltaMax                 Unsigned64,
    cucsAdaptorMenloNetInStatsFwdLookupNoHitDeltaMin                 Unsigned64,
    cucsAdaptorMenloNetInStatsIntervals                              Gauge32,
    cucsAdaptorMenloNetInStatsMenloNetIndex                          CucsAdaptorMenloStatsIndex,
    cucsAdaptorMenloNetInStatsSuspect                                TruthValue,
    cucsAdaptorMenloNetInStatsThresholded                            CucsAdaptorMenloNetInStatsThresholded,
    cucsAdaptorMenloNetInStatsTimeCollected                          DateAndTime,
    cucsAdaptorMenloNetInStatsUpdate                                 Gauge32
}

cucsAdaptorMenloNetInStatsInstanceId OBJECT-TYPE
    SYNTAX       CucsManagedObjectId
    MAX-ACCESS   not-accessible
    STATUS       current
    DESCRIPTION
        "Instance identifier of the managed object."
    ::= { cucsAdaptorMenloNetInStatsEntry 1 }

cucsAdaptorMenloNetInStatsDn OBJECT-TYPE
    SYNTAX       CucsManagedObjectDn
    MAX-ACCESS   read-only
    STATUS       current
    DESCRIPTION
        "Cisco UCS adaptor:MenloNetInStats:dn managed object property"
    ::= { cucsAdaptorMenloNetInStatsEntry 2 }

cucsAdaptorMenloNetInStatsRn OBJECT-TYPE
    SYNTAX       SnmpAdminString
    MAX-ACCESS   read-only
    STATUS       current
    DESCRIPTION
        "Cisco UCS adaptor:MenloNetInStats:rn managed object property"
    ::= { cucsAdaptorMenloNetInStatsEntry 3 }

cucsAdaptorMenloNetInStatsDropFcLifInvalid OBJECT-TYPE
    SYNTAX       Unsigned64
    MAX-ACCESS   read-only
    STATUS       current
    DESCRIPTION
        "Cisco UCS adaptor:MenloNetInStats:dropFcLifInvalid
        managed object property"
    ::= { cucsAdaptorMenloNetInStatsEntry 4 }

cucsAdaptorMenloNetInStatsDropFcLifInvalidDelta OBJECT-TYPE
    SYNTAX       Counter64
    MAX-ACCESS   read-only
    STATUS       current
    DESCRIPTION
        "Cisco UCS adaptor:MenloNetInStats:dropFcLifInvalidDelta
        managed object property"
    ::= { cucsAdaptorMenloNetInStatsEntry 5 }

cucsAdaptorMenloNetInStatsDropFcLifInvalidDeltaAvg OBJECT-TYPE
    SYNTAX       Unsigned64
    MAX-ACCESS   read-only
    STATUS       current
    DESCRIPTION
        "Cisco UCS adaptor:MenloNetInStats:dropFcLifInvalidDeltaAvg
        managed object property"
    ::= { cucsAdaptorMenloNetInStatsEntry 6 }

cucsAdaptorMenloNetInStatsDropFcLifInvalidDeltaMax OBJECT-TYPE
    SYNTAX       Unsigned64
    MAX-ACCESS   read-only
    STATUS       current
    DESCRIPTION
        "Cisco UCS adaptor:MenloNetInStats:dropFcLifInvalidDeltaMax
        managed object property"
    ::= { cucsAdaptorMenloNetInStatsEntry 7 }

cucsAdaptorMenloNetInStatsDropFcLifInvalidDeltaMin OBJECT-TYPE
    SYNTAX       Unsigned64
    MAX-ACCESS   read-only
    STATUS       current
    DESCRIPTION
        "Cisco UCS adaptor:MenloNetInStats:dropFcLifInvalidDeltaMin
        managed object property"
    ::= { cucsAdaptorMenloNetInStatsEntry 8 }

cucsAdaptorMenloNetInStatsDropFcMulticast OBJECT-TYPE
    SYNTAX       Unsigned64
    MAX-ACCESS   read-only
    STATUS       current
    DESCRIPTION
        "Cisco UCS adaptor:MenloNetInStats:dropFcMulticast
        managed object property"
    ::= { cucsAdaptorMenloNetInStatsEntry 9 }

cucsAdaptorMenloNetInStatsDropFcMulticastDelta OBJECT-TYPE
    SYNTAX       Counter64
    MAX-ACCESS   read-only
    STATUS       current
    DESCRIPTION
        "Cisco UCS adaptor:MenloNetInStats:dropFcMulticastDelta
        managed object property"
    ::= { cucsAdaptorMenloNetInStatsEntry 10 }

cucsAdaptorMenloNetInStatsDropFcMulticastDeltaAvg OBJECT-TYPE
    SYNTAX       Unsigned64
    MAX-ACCESS   read-only
    STATUS       current
    DESCRIPTION
        "Cisco UCS adaptor:MenloNetInStats:dropFcMulticastDeltaAvg
        managed object property"
    ::= { cucsAdaptorMenloNetInStatsEntry 11 }

cucsAdaptorMenloNetInStatsDropFcMulticastDeltaMax OBJECT-TYPE
    SYNTAX       Unsigned64
    MAX-ACCESS   read-only
    STATUS       current
    DESCRIPTION
        "Cisco UCS adaptor:MenloNetInStats:dropFcMulticastDeltaMax
        managed object property"
    ::= { cucsAdaptorMenloNetInStatsEntry 12 }

cucsAdaptorMenloNetInStatsDropFcMulticastDeltaMin OBJECT-TYPE
    SYNTAX       Unsigned64
    MAX-ACCESS   read-only
    STATUS       current
    DESCRIPTION
        "Cisco UCS adaptor:MenloNetInStats:dropFcMulticastDeltaMin
        managed object property"
    ::= { cucsAdaptorMenloNetInStatsEntry 13 }

cucsAdaptorMenloNetInStatsDropNullPif OBJECT-TYPE
    SYNTAX       Unsigned64
    MAX-ACCESS   read-only
    STATUS       current
    DESCRIPTION
        "Cisco UCS adaptor:MenloNetInStats:dropNullPif
        managed object property"
    ::= { cucsAdaptorMenloNetInStatsEntry 14 }

cucsAdaptorMenloNetInStatsDropNullPifDelta OBJECT-TYPE
    SYNTAX       Counter64
    MAX-ACCESS   read-only
    STATUS       current
    DESCRIPTION
        "Cisco UCS adaptor:MenloNetInStats:dropNullPifDelta
        managed object property"
    ::= { cucsAdaptorMenloNetInStatsEntry 15 }

cucsAdaptorMenloNetInStatsDropNullPifDeltaAvg OBJECT-TYPE
    SYNTAX       Unsigned64
    MAX-ACCESS   read-only
    STATUS       current
    DESCRIPTION
        "Cisco UCS adaptor:MenloNetInStats:dropNullPifDeltaAvg
        managed object property"
    ::= { cucsAdaptorMenloNetInStatsEntry 16 }

cucsAdaptorMenloNetInStatsDropNullPifDeltaMax OBJECT-TYPE
    SYNTAX       Unsigned64
    MAX-ACCESS   read-only
    STATUS       current
    DESCRIPTION
        "Cisco UCS adaptor:MenloNetInStats:dropNullPifDeltaMax
        managed object property"
    ::= { cucsAdaptorMenloNetInStatsEntry 17 }

cucsAdaptorMenloNetInStatsDropNullPifDeltaMin OBJECT-TYPE
    SYNTAX       Unsigned64
    MAX-ACCESS   read-only
    STATUS       current
    DESCRIPTION
        "Cisco UCS adaptor:MenloNetInStats:dropNullPifDeltaMin
        managed object property"
    ::= { cucsAdaptorMenloNetInStatsEntry 18 }

cucsAdaptorMenloNetInStatsFwdLookupNoHit OBJECT-TYPE
    SYNTAX       Unsigned64
    MAX-ACCESS   read-only
    STATUS       current
    DESCRIPTION
        "Cisco UCS adaptor:MenloNetInStats:fwdLookupNoHit
        managed object property"
    ::= { cucsAdaptorMenloNetInStatsEntry 19 }

cucsAdaptorMenloNetInStatsFwdLookupNoHitDelta OBJECT-TYPE
    SYNTAX       Counter64
    MAX-ACCESS   read-only
    STATUS       current
    DESCRIPTION
        "Cisco UCS adaptor:MenloNetInStats:fwdLookupNoHitDelta
        managed object property"
    ::= { cucsAdaptorMenloNetInStatsEntry 20 }

cucsAdaptorMenloNetInStatsFwdLookupNoHitDeltaAvg OBJECT-TYPE
    SYNTAX       Unsigned64
    MAX-ACCESS   read-only
    STATUS       current
    DESCRIPTION
        "Cisco UCS adaptor:MenloNetInStats:fwdLookupNoHitDeltaAvg
        managed object property"
    ::= { cucsAdaptorMenloNetInStatsEntry 21 }

cucsAdaptorMenloNetInStatsFwdLookupNoHitDeltaMax OBJECT-TYPE
    SYNTAX       Unsigned64
    MAX-ACCESS   read-only
    STATUS       current
    DESCRIPTION
        "Cisco UCS adaptor:MenloNetInStats:fwdLookupNoHitDeltaMax
        managed object property"
    ::= { cucsAdaptorMenloNetInStatsEntry 22 }

cucsAdaptorMenloNetInStatsFwdLookupNoHitDeltaMin OBJECT-TYPE
    SYNTAX       Unsigned64
    MAX-ACCESS   read-only
    STATUS       current
    DESCRIPTION
        "Cisco UCS adaptor:MenloNetInStats:fwdLookupNoHitDeltaMin
        managed object property"
    ::= { cucsAdaptorMenloNetInStatsEntry 23 }

cucsAdaptorMenloNetInStatsIntervals OBJECT-TYPE
    SYNTAX       Gauge32
    MAX-ACCESS   read-only
    STATUS       current
    DESCRIPTION
        "Cisco UCS adaptor:MenloNetInStats:intervals managed
        object property"
    ::= { cucsAdaptorMenloNetInStatsEntry 24 }

cucsAdaptorMenloNetInStatsMenloNetIndex OBJECT-TYPE
    SYNTAX       CucsAdaptorMenloStatsIndex
    MAX-ACCESS   read-only
    STATUS       current
    DESCRIPTION
        "Cisco UCS adaptor:MenloNetInStats:menloNetIndex
        managed object property"
    ::= { cucsAdaptorMenloNetInStatsEntry 25 }

cucsAdaptorMenloNetInStatsSuspect OBJECT-TYPE
    SYNTAX       TruthValue
    MAX-ACCESS   read-only
    STATUS       current
    DESCRIPTION
        "Cisco UCS adaptor:MenloNetInStats:suspect managed
        object property"
    ::= { cucsAdaptorMenloNetInStatsEntry 26 }

cucsAdaptorMenloNetInStatsThresholded OBJECT-TYPE
    SYNTAX       CucsAdaptorMenloNetInStatsThresholded
    MAX-ACCESS   read-only
    STATUS       current
    DESCRIPTION
        "Cisco UCS adaptor:MenloNetInStats:thresholded
        managed object property"
    ::= { cucsAdaptorMenloNetInStatsEntry 27 }

cucsAdaptorMenloNetInStatsTimeCollected OBJECT-TYPE
    SYNTAX       DateAndTime
    MAX-ACCESS   read-only
    STATUS       current
    DESCRIPTION
        "Cisco UCS adaptor:MenloNetInStats:timeCollected
        managed object property"
    ::= { cucsAdaptorMenloNetInStatsEntry 28 }

cucsAdaptorMenloNetInStatsUpdate OBJECT-TYPE
    SYNTAX       Gauge32
    MAX-ACCESS   read-only
    STATUS       current
    DESCRIPTION
        "Cisco UCS adaptor:MenloNetInStats:update managed object property"
    ::= { cucsAdaptorMenloNetInStatsEntry 29 }

cucsAdaptorMenloNetInStatsHistTable OBJECT-TYPE
    SYNTAX           SEQUENCE OF CucsAdaptorMenloNetInStatsHistEntry
    MAX-ACCESS       not-accessible
    STATUS           current
    DESCRIPTION
        "Cisco UCS adaptor:MenloNetInStatsHist managed object table"
    ::= { cucsAdaptorObjects 76 }

cucsAdaptorMenloNetInStatsHistEntry OBJECT-TYPE
    SYNTAX           CucsAdaptorMenloNetInStatsHistEntry
    MAX-ACCESS       not-accessible
    STATUS           current
    DESCRIPTION
        "Entry for the cucsAdaptorMenloNetInStatsHistTable table."
    INDEX { cucsAdaptorMenloNetInStatsHistInstanceId }
    ::= { cucsAdaptorMenloNetInStatsHistTable 1 }

CucsAdaptorMenloNetInStatsHistEntry ::= SEQUENCE {
    cucsAdaptorMenloNetInStatsHistInstanceId                         CucsManagedObjectId,
    cucsAdaptorMenloNetInStatsHistDn                                 CucsManagedObjectDn,
    cucsAdaptorMenloNetInStatsHistRn                                 SnmpAdminString,
    cucsAdaptorMenloNetInStatsHistDropFcLifInvalid                   Unsigned64,
    cucsAdaptorMenloNetInStatsHistDropFcLifInvalidDelta              Unsigned64,
    cucsAdaptorMenloNetInStatsHistDropFcLifInvalidDeltaAvg           Unsigned64,
    cucsAdaptorMenloNetInStatsHistDropFcLifInvalidDeltaMax           Unsigned64,
    cucsAdaptorMenloNetInStatsHistDropFcLifInvalidDeltaMin           Unsigned64,
    cucsAdaptorMenloNetInStatsHistDropFcMulticast                    Unsigned64,
    cucsAdaptorMenloNetInStatsHistDropFcMulticastDelta               Unsigned64,
    cucsAdaptorMenloNetInStatsHistDropFcMulticastDeltaAvg            Unsigned64,
    cucsAdaptorMenloNetInStatsHistDropFcMulticastDeltaMax            Unsigned64,
    cucsAdaptorMenloNetInStatsHistDropFcMulticastDeltaMin            Unsigned64,
    cucsAdaptorMenloNetInStatsHistDropNullPif                        Unsigned64,
    cucsAdaptorMenloNetInStatsHistDropNullPifDelta                   Unsigned64,
    cucsAdaptorMenloNetInStatsHistDropNullPifDeltaAvg                Unsigned64,
    cucsAdaptorMenloNetInStatsHistDropNullPifDeltaMax                Unsigned64,
    cucsAdaptorMenloNetInStatsHistDropNullPifDeltaMin                Unsigned64,
    cucsAdaptorMenloNetInStatsHistFwdLookupNoHit                     Unsigned64,
    cucsAdaptorMenloNetInStatsHistFwdLookupNoHitDelta                Unsigned64,
    cucsAdaptorMenloNetInStatsHistFwdLookupNoHitDeltaAvg             Unsigned64,
    cucsAdaptorMenloNetInStatsHistFwdLookupNoHitDeltaMax             Unsigned64,
    cucsAdaptorMenloNetInStatsHistFwdLookupNoHitDeltaMin             Unsigned64,
    cucsAdaptorMenloNetInStatsHistId                                 Unsigned64,
    cucsAdaptorMenloNetInStatsHistMostRecent                         TruthValue,
    cucsAdaptorMenloNetInStatsHistSuspect                            TruthValue,
    cucsAdaptorMenloNetInStatsHistThresholded                        CucsAdaptorMenloNetInStatsHistThresholded,
    cucsAdaptorMenloNetInStatsHistTimeCollected                      DateAndTime
}

cucsAdaptorMenloNetInStatsHistInstanceId OBJECT-TYPE
    SYNTAX       CucsManagedObjectId
    MAX-ACCESS   not-accessible
    STATUS       current
    DESCRIPTION
        "Instance identifier of the managed object."
    ::= { cucsAdaptorMenloNetInStatsHistEntry 1 }

cucsAdaptorMenloNetInStatsHistDn OBJECT-TYPE
    SYNTAX       CucsManagedObjectDn
    MAX-ACCESS   read-only
    STATUS       current
    DESCRIPTION
        "Cisco UCS adaptor:MenloNetInStatsHist:dn managed object property"
    ::= { cucsAdaptorMenloNetInStatsHistEntry 2 }

cucsAdaptorMenloNetInStatsHistRn OBJECT-TYPE
    SYNTAX       SnmpAdminString
    MAX-ACCESS   read-only
    STATUS       current
    DESCRIPTION
        "Cisco UCS adaptor:MenloNetInStatsHist:rn managed object property"
    ::= { cucsAdaptorMenloNetInStatsHistEntry 3 }

cucsAdaptorMenloNetInStatsHistDropFcLifInvalid OBJECT-TYPE
    SYNTAX       Unsigned64
    MAX-ACCESS   read-only
    STATUS       current
    DESCRIPTION
        "Cisco UCS adaptor:MenloNetInStatsHist:dropFcLifInvalid
        managed object property"
    ::= { cucsAdaptorMenloNetInStatsHistEntry 4 }

cucsAdaptorMenloNetInStatsHistDropFcLifInvalidDelta OBJECT-TYPE
    SYNTAX       Unsigned64
    MAX-ACCESS   read-only
    STATUS       current
    DESCRIPTION
        "Cisco UCS adaptor:MenloNetInStatsHist:dropFcLifInvalidDelta
        managed object property"
    ::= { cucsAdaptorMenloNetInStatsHistEntry 5 }

cucsAdaptorMenloNetInStatsHistDropFcLifInvalidDeltaAvg OBJECT-TYPE
    SYNTAX       Unsigned64
    MAX-ACCESS   read-only
    STATUS       current
    DESCRIPTION
        "Cisco UCS adaptor:MenloNetInStatsHist:dropFcLifInvalidDeltaAvg
        managed object property"
    ::= { cucsAdaptorMenloNetInStatsHistEntry 6 }

cucsAdaptorMenloNetInStatsHistDropFcLifInvalidDeltaMax OBJECT-TYPE
    SYNTAX       Unsigned64
    MAX-ACCESS   read-only
    STATUS       current
    DESCRIPTION
        "Cisco UCS adaptor:MenloNetInStatsHist:dropFcLifInvalidDeltaMax
        managed object property"
    ::= { cucsAdaptorMenloNetInStatsHistEntry 7 }

cucsAdaptorMenloNetInStatsHistDropFcLifInvalidDeltaMin OBJECT-TYPE
    SYNTAX       Unsigned64
    MAX-ACCESS   read-only
    STATUS       current
    DESCRIPTION
        "Cisco UCS adaptor:MenloNetInStatsHist:dropFcLifInvalidDeltaMin
        managed object property"
    ::= { cucsAdaptorMenloNetInStatsHistEntry 8 }

cucsAdaptorMenloNetInStatsHistDropFcMulticast OBJECT-TYPE
    SYNTAX       Unsigned64
    MAX-ACCESS   read-only
    STATUS       current
    DESCRIPTION
        "Cisco UCS adaptor:MenloNetInStatsHist:dropFcMulticast
        managed object property"
    ::= { cucsAdaptorMenloNetInStatsHistEntry 9 }

cucsAdaptorMenloNetInStatsHistDropFcMulticastDelta OBJECT-TYPE
    SYNTAX       Unsigned64
    MAX-ACCESS   read-only
    STATUS       current
    DESCRIPTION
        "Cisco UCS adaptor:MenloNetInStatsHist:dropFcMulticastDelta
        managed object property"
    ::= { cucsAdaptorMenloNetInStatsHistEntry 10 }

cucsAdaptorMenloNetInStatsHistDropFcMulticastDeltaAvg OBJECT-TYPE
    SYNTAX       Unsigned64
    MAX-ACCESS   read-only
    STATUS       current
    DESCRIPTION
        "Cisco UCS adaptor:MenloNetInStatsHist:dropFcMulticastDeltaAvg
        managed object property"
    ::= { cucsAdaptorMenloNetInStatsHistEntry 11 }

cucsAdaptorMenloNetInStatsHistDropFcMulticastDeltaMax OBJECT-TYPE
    SYNTAX       Unsigned64
    MAX-ACCESS   read-only
    STATUS       current
    DESCRIPTION
        "Cisco UCS adaptor:MenloNetInStatsHist:dropFcMulticastDeltaMax
        managed object property"
    ::= { cucsAdaptorMenloNetInStatsHistEntry 12 }

cucsAdaptorMenloNetInStatsHistDropFcMulticastDeltaMin OBJECT-TYPE
    SYNTAX       Unsigned64
    MAX-ACCESS   read-only
    STATUS       current
    DESCRIPTION
        "Cisco UCS adaptor:MenloNetInStatsHist:dropFcMulticastDeltaMin
        managed object property"
    ::= { cucsAdaptorMenloNetInStatsHistEntry 13 }

cucsAdaptorMenloNetInStatsHistDropNullPif OBJECT-TYPE
    SYNTAX       Unsigned64
    MAX-ACCESS   read-only
    STATUS       current
    DESCRIPTION
        "Cisco UCS adaptor:MenloNetInStatsHist:dropNullPif
        managed object property"
    ::= { cucsAdaptorMenloNetInStatsHistEntry 14 }

cucsAdaptorMenloNetInStatsHistDropNullPifDelta OBJECT-TYPE
    SYNTAX       Unsigned64
    MAX-ACCESS   read-only
    STATUS       current
    DESCRIPTION
        "Cisco UCS adaptor:MenloNetInStatsHist:dropNullPifDelta
        managed object property"
    ::= { cucsAdaptorMenloNetInStatsHistEntry 15 }

cucsAdaptorMenloNetInStatsHistDropNullPifDeltaAvg OBJECT-TYPE
    SYNTAX       Unsigned64
    MAX-ACCESS   read-only
    STATUS       current
    DESCRIPTION
        "Cisco UCS adaptor:MenloNetInStatsHist:dropNullPifDeltaAvg
        managed object property"
    ::= { cucsAdaptorMenloNetInStatsHistEntry 16 }

cucsAdaptorMenloNetInStatsHistDropNullPifDeltaMax OBJECT-TYPE
    SYNTAX       Unsigned64
    MAX-ACCESS   read-only
    STATUS       current
    DESCRIPTION
        "Cisco UCS adaptor:MenloNetInStatsHist:dropNullPifDeltaMax
        managed object property"
    ::= { cucsAdaptorMenloNetInStatsHistEntry 17 }

cucsAdaptorMenloNetInStatsHistDropNullPifDeltaMin OBJECT-TYPE
    SYNTAX       Unsigned64
    MAX-ACCESS   read-only
    STATUS       current
    DESCRIPTION
        "Cisco UCS adaptor:MenloNetInStatsHist:dropNullPifDeltaMin
        managed object property"
    ::= { cucsAdaptorMenloNetInStatsHistEntry 18 }

cucsAdaptorMenloNetInStatsHistFwdLookupNoHit OBJECT-TYPE
    SYNTAX       Unsigned64
    MAX-ACCESS   read-only
    STATUS       current
    DESCRIPTION
        "Cisco UCS adaptor:MenloNetInStatsHist:fwdLookupNoHit
        managed object property"
    ::= { cucsAdaptorMenloNetInStatsHistEntry 19 }

cucsAdaptorMenloNetInStatsHistFwdLookupNoHitDelta OBJECT-TYPE
    SYNTAX       Unsigned64
    MAX-ACCESS   read-only
    STATUS       current
    DESCRIPTION
        "Cisco UCS adaptor:MenloNetInStatsHist:fwdLookupNoHitDelta
        managed object property"
    ::= { cucsAdaptorMenloNetInStatsHistEntry 20 }

cucsAdaptorMenloNetInStatsHistFwdLookupNoHitDeltaAvg OBJECT-TYPE
    SYNTAX       Unsigned64
    MAX-ACCESS   read-only
    STATUS       current
    DESCRIPTION
        "Cisco UCS adaptor:MenloNetInStatsHist:fwdLookupNoHitDeltaAvg
        managed object property"
    ::= { cucsAdaptorMenloNetInStatsHistEntry 21 }

cucsAdaptorMenloNetInStatsHistFwdLookupNoHitDeltaMax OBJECT-TYPE
    SYNTAX       Unsigned64
    MAX-ACCESS   read-only
    STATUS       current
    DESCRIPTION
        "Cisco UCS adaptor:MenloNetInStatsHist:fwdLookupNoHitDeltaMax
        managed object property"
    ::= { cucsAdaptorMenloNetInStatsHistEntry 22 }

cucsAdaptorMenloNetInStatsHistFwdLookupNoHitDeltaMin OBJECT-TYPE
    SYNTAX       Unsigned64
    MAX-ACCESS   read-only
    STATUS       current
    DESCRIPTION
        "Cisco UCS adaptor:MenloNetInStatsHist:fwdLookupNoHitDeltaMin
        managed object property"
    ::= { cucsAdaptorMenloNetInStatsHistEntry 23 }

cucsAdaptorMenloNetInStatsHistId OBJECT-TYPE
    SYNTAX       Unsigned64
    MAX-ACCESS   read-only
    STATUS       current
    DESCRIPTION
        "Cisco UCS adaptor:MenloNetInStatsHist:id managed object property"
    ::= { cucsAdaptorMenloNetInStatsHistEntry 24 }

cucsAdaptorMenloNetInStatsHistMostRecent OBJECT-TYPE
    SYNTAX       TruthValue
    MAX-ACCESS   read-only
    STATUS       current
    DESCRIPTION
        "Cisco UCS adaptor:MenloNetInStatsHist:mostRecent
        managed object property"
    ::= { cucsAdaptorMenloNetInStatsHistEntry 25 }

cucsAdaptorMenloNetInStatsHistSuspect OBJECT-TYPE
    SYNTAX       TruthValue
    MAX-ACCESS   read-only
    STATUS       current
    DESCRIPTION
        "Cisco UCS adaptor:MenloNetInStatsHist:suspect
        managed object property"
    ::= { cucsAdaptorMenloNetInStatsHistEntry 26 }

cucsAdaptorMenloNetInStatsHistThresholded OBJECT-TYPE
    SYNTAX       CucsAdaptorMenloNetInStatsHistThresholded
    MAX-ACCESS   read-only
    STATUS       current
    DESCRIPTION
        "Cisco UCS adaptor:MenloNetInStatsHist:thresholded
        managed object property"
    ::= { cucsAdaptorMenloNetInStatsHistEntry 27 }

cucsAdaptorMenloNetInStatsHistTimeCollected OBJECT-TYPE
    SYNTAX       DateAndTime
    MAX-ACCESS   read-only
    STATUS       current
    DESCRIPTION
        "Cisco UCS adaptor:MenloNetInStatsHist:timeCollected
        managed object property"
    ::= { cucsAdaptorMenloNetInStatsHistEntry 28 }

cucsAdaptorMenloQErrorStatsTable OBJECT-TYPE
    SYNTAX           SEQUENCE OF CucsAdaptorMenloQErrorStatsEntry
    MAX-ACCESS       not-accessible
    STATUS           current
    DESCRIPTION
        "Cisco UCS adaptor:MenloQErrorStats managed object table"
    ::= { cucsAdaptorObjects 77 }

cucsAdaptorMenloQErrorStatsEntry OBJECT-TYPE
    SYNTAX           CucsAdaptorMenloQErrorStatsEntry
    MAX-ACCESS       not-accessible
    STATUS           current
    DESCRIPTION
        "Entry for the cucsAdaptorMenloQErrorStatsTable table."
    INDEX { cucsAdaptorMenloQErrorStatsInstanceId }
    ::= { cucsAdaptorMenloQErrorStatsTable 1 }

CucsAdaptorMenloQErrorStatsEntry ::= SEQUENCE {
    cucsAdaptorMenloQErrorStatsInstanceId                            CucsManagedObjectId,
    cucsAdaptorMenloQErrorStatsDn                                    CucsManagedObjectDn,
    cucsAdaptorMenloQErrorStatsRn                                    SnmpAdminString,
    cucsAdaptorMenloQErrorStatsCorrectableErrors                     Unsigned64,
    cucsAdaptorMenloQErrorStatsCorrectableErrorsDelta                Counter64,
    cucsAdaptorMenloQErrorStatsCorrectableErrorsDeltaAvg             Unsigned64,
    cucsAdaptorMenloQErrorStatsCorrectableErrorsDeltaMax             Unsigned64,
    cucsAdaptorMenloQErrorStatsCorrectableErrorsDeltaMin             Unsigned64,
    cucsAdaptorMenloQErrorStatsIntervals                             Gauge32,
    cucsAdaptorMenloQErrorStatsMenloQueueComponent                   CucsAdaptorMenloQueueStatsComponent,
    cucsAdaptorMenloQErrorStatsMenloQueueIndex                       CucsAdaptorMenloStatsIndex,
    cucsAdaptorMenloQErrorStatsPopErrors                             Unsigned64,
    cucsAdaptorMenloQErrorStatsPopErrorsDelta                        Counter64,
    cucsAdaptorMenloQErrorStatsPopErrorsDeltaAvg                     Unsigned64,
    cucsAdaptorMenloQErrorStatsPopErrorsDeltaMax                     Unsigned64,
    cucsAdaptorMenloQErrorStatsPopErrorsDeltaMin                     Unsigned64,
    cucsAdaptorMenloQErrorStatsPushErrors                            Unsigned64,
    cucsAdaptorMenloQErrorStatsPushErrorsDelta                       Counter64,
    cucsAdaptorMenloQErrorStatsPushErrorsDeltaAvg                    Unsigned64,
    cucsAdaptorMenloQErrorStatsPushErrorsDeltaMax                    Unsigned64,
    cucsAdaptorMenloQErrorStatsPushErrorsDeltaMin                    Unsigned64,
    cucsAdaptorMenloQErrorStatsSuspect                               TruthValue,
    cucsAdaptorMenloQErrorStatsThresholded                           CucsAdaptorMenloQErrorStatsThresholded,
    cucsAdaptorMenloQErrorStatsTimeCollected                         DateAndTime,
    cucsAdaptorMenloQErrorStatsUncorrectableErrors                   Unsigned64,
    cucsAdaptorMenloQErrorStatsUncorrectableErrorsDelta              Counter64,
    cucsAdaptorMenloQErrorStatsUncorrectableErrorsDeltaAvg           Unsigned64,
    cucsAdaptorMenloQErrorStatsUncorrectableErrorsDeltaMax           Unsigned64,
    cucsAdaptorMenloQErrorStatsUncorrectableErrorsDeltaMin           Unsigned64,
    cucsAdaptorMenloQErrorStatsUpdate                                Gauge32
}

cucsAdaptorMenloQErrorStatsInstanceId OBJECT-TYPE
    SYNTAX       CucsManagedObjectId
    MAX-ACCESS   not-accessible
    STATUS       current
    DESCRIPTION
        "Instance identifier of the managed object."
    ::= { cucsAdaptorMenloQErrorStatsEntry 1 }

cucsAdaptorMenloQErrorStatsDn OBJECT-TYPE
    SYNTAX       CucsManagedObjectDn
    MAX-ACCESS   read-only
    STATUS       current
    DESCRIPTION
        "Cisco UCS adaptor:MenloQErrorStats:dn managed object property"
    ::= { cucsAdaptorMenloQErrorStatsEntry 2 }

cucsAdaptorMenloQErrorStatsRn OBJECT-TYPE
    SYNTAX       SnmpAdminString
    MAX-ACCESS   read-only
    STATUS       current
    DESCRIPTION
        "Cisco UCS adaptor:MenloQErrorStats:rn managed object property"
    ::= { cucsAdaptorMenloQErrorStatsEntry 3 }

cucsAdaptorMenloQErrorStatsCorrectableErrors OBJECT-TYPE
    SYNTAX       Unsigned64
    MAX-ACCESS   read-only
    STATUS       current
    DESCRIPTION
        "Cisco UCS adaptor:MenloQErrorStats:correctableErrors
        managed object property"
    ::= { cucsAdaptorMenloQErrorStatsEntry 4 }

cucsAdaptorMenloQErrorStatsCorrectableErrorsDelta OBJECT-TYPE
    SYNTAX       Counter64
    MAX-ACCESS   read-only
    STATUS       current
    DESCRIPTION
        "Cisco UCS adaptor:MenloQErrorStats:correctableErrorsDelta
        managed object property"
    ::= { cucsAdaptorMenloQErrorStatsEntry 5 }

cucsAdaptorMenloQErrorStatsCorrectableErrorsDeltaAvg OBJECT-TYPE
    SYNTAX       Unsigned64
    MAX-ACCESS   read-only
    STATUS       current
    DESCRIPTION
        "Cisco UCS adaptor:MenloQErrorStats:correctableErrorsDeltaAvg
        managed object property"
    ::= { cucsAdaptorMenloQErrorStatsEntry 6 }

cucsAdaptorMenloQErrorStatsCorrectableErrorsDeltaMax OBJECT-TYPE
    SYNTAX       Unsigned64
    MAX-ACCESS   read-only
    STATUS       current
    DESCRIPTION
        "Cisco UCS adaptor:MenloQErrorStats:correctableErrorsDeltaMax
        managed object property"
    ::= { cucsAdaptorMenloQErrorStatsEntry 7 }

cucsAdaptorMenloQErrorStatsCorrectableErrorsDeltaMin OBJECT-TYPE
    SYNTAX       Unsigned64
    MAX-ACCESS   read-only
    STATUS       current
    DESCRIPTION
        "Cisco UCS adaptor:MenloQErrorStats:correctableErrorsDeltaMin
        managed object property"
    ::= { cucsAdaptorMenloQErrorStatsEntry 8 }

cucsAdaptorMenloQErrorStatsIntervals OBJECT-TYPE
    SYNTAX       Gauge32
    MAX-ACCESS   read-only
    STATUS       current
    DESCRIPTION
        "Cisco UCS adaptor:MenloQErrorStats:intervals managed
        object property"
    ::= { cucsAdaptorMenloQErrorStatsEntry 9 }

cucsAdaptorMenloQErrorStatsMenloQueueComponent OBJECT-TYPE
    SYNTAX       CucsAdaptorMenloQueueStatsComponent
    MAX-ACCESS   read-only
    STATUS       current
    DESCRIPTION
        "Cisco UCS adaptor:MenloQErrorStats:menloQueueComponent
        managed object property"
    ::= { cucsAdaptorMenloQErrorStatsEntry 10 }

cucsAdaptorMenloQErrorStatsMenloQueueIndex OBJECT-TYPE
    SYNTAX       CucsAdaptorMenloStatsIndex
    MAX-ACCESS   read-only
    STATUS       current
    DESCRIPTION
        "Cisco UCS adaptor:MenloQErrorStats:menloQueueIndex
        managed object property"
    ::= { cucsAdaptorMenloQErrorStatsEntry 11 }

cucsAdaptorMenloQErrorStatsPopErrors OBJECT-TYPE
    SYNTAX       Unsigned64
    MAX-ACCESS   read-only
    STATUS       current
    DESCRIPTION
        "Cisco UCS adaptor:MenloQErrorStats:popErrors managed
        object property"
    ::= { cucsAdaptorMenloQErrorStatsEntry 12 }

cucsAdaptorMenloQErrorStatsPopErrorsDelta OBJECT-TYPE
    SYNTAX       Counter64
    MAX-ACCESS   read-only
    STATUS       current
    DESCRIPTION
        "Cisco UCS adaptor:MenloQErrorStats:popErrorsDelta
        managed object property"
    ::= { cucsAdaptorMenloQErrorStatsEntry 13 }

cucsAdaptorMenloQErrorStatsPopErrorsDeltaAvg OBJECT-TYPE
    SYNTAX       Unsigned64
    MAX-ACCESS   read-only
    STATUS       current
    DESCRIPTION
        "Cisco UCS adaptor:MenloQErrorStats:popErrorsDeltaAvg
        managed object property"
    ::= { cucsAdaptorMenloQErrorStatsEntry 14 }

cucsAdaptorMenloQErrorStatsPopErrorsDeltaMax OBJECT-TYPE
    SYNTAX       Unsigned64
    MAX-ACCESS   read-only
    STATUS       current
    DESCRIPTION
        "Cisco UCS adaptor:MenloQErrorStats:popErrorsDeltaMax
        managed object property"
    ::= { cucsAdaptorMenloQErrorStatsEntry 15 }

cucsAdaptorMenloQErrorStatsPopErrorsDeltaMin OBJECT-TYPE
    SYNTAX       Unsigned64
    MAX-ACCESS   read-only
    STATUS       current
    DESCRIPTION
        "Cisco UCS adaptor:MenloQErrorStats:popErrorsDeltaMin
        managed object property"
    ::= { cucsAdaptorMenloQErrorStatsEntry 16 }

cucsAdaptorMenloQErrorStatsPushErrors OBJECT-TYPE
    SYNTAX       Unsigned64
    MAX-ACCESS   read-only
    STATUS       current
    DESCRIPTION
        "Cisco UCS adaptor:MenloQErrorStats:pushErrors
        managed object property"
    ::= { cucsAdaptorMenloQErrorStatsEntry 17 }

cucsAdaptorMenloQErrorStatsPushErrorsDelta OBJECT-TYPE
    SYNTAX       Counter64
    MAX-ACCESS   read-only
    STATUS       current
    DESCRIPTION
        "Cisco UCS adaptor:MenloQErrorStats:pushErrorsDelta
        managed object property"
    ::= { cucsAdaptorMenloQErrorStatsEntry 18 }

cucsAdaptorMenloQErrorStatsPushErrorsDeltaAvg OBJECT-TYPE
    SYNTAX       Unsigned64
    MAX-ACCESS   read-only
    STATUS       current
    DESCRIPTION
        "Cisco UCS adaptor:MenloQErrorStats:pushErrorsDeltaAvg
        managed object property"
    ::= { cucsAdaptorMenloQErrorStatsEntry 19 }

cucsAdaptorMenloQErrorStatsPushErrorsDeltaMax OBJECT-TYPE
    SYNTAX       Unsigned64
    MAX-ACCESS   read-only
    STATUS       current
    DESCRIPTION
        "Cisco UCS adaptor:MenloQErrorStats:pushErrorsDeltaMax
        managed object property"
    ::= { cucsAdaptorMenloQErrorStatsEntry 20 }

cucsAdaptorMenloQErrorStatsPushErrorsDeltaMin OBJECT-TYPE
    SYNTAX       Unsigned64
    MAX-ACCESS   read-only
    STATUS       current
    DESCRIPTION
        "Cisco UCS adaptor:MenloQErrorStats:pushErrorsDeltaMin
        managed object property"
    ::= { cucsAdaptorMenloQErrorStatsEntry 21 }

cucsAdaptorMenloQErrorStatsSuspect OBJECT-TYPE
    SYNTAX       TruthValue
    MAX-ACCESS   read-only
    STATUS       current
    DESCRIPTION
        "Cisco UCS adaptor:MenloQErrorStats:suspect managed
        object property"
    ::= { cucsAdaptorMenloQErrorStatsEntry 22 }

cucsAdaptorMenloQErrorStatsThresholded OBJECT-TYPE
    SYNTAX       CucsAdaptorMenloQErrorStatsThresholded
    MAX-ACCESS   read-only
    STATUS       current
    DESCRIPTION
        "Cisco UCS adaptor:MenloQErrorStats:thresholded
        managed object property"
    ::= { cucsAdaptorMenloQErrorStatsEntry 23 }

cucsAdaptorMenloQErrorStatsTimeCollected OBJECT-TYPE
    SYNTAX       DateAndTime
    MAX-ACCESS   read-only
    STATUS       current
    DESCRIPTION
        "Cisco UCS adaptor:MenloQErrorStats:timeCollected
        managed object property"
    ::= { cucsAdaptorMenloQErrorStatsEntry 24 }

cucsAdaptorMenloQErrorStatsUncorrectableErrors OBJECT-TYPE
    SYNTAX       Unsigned64
    MAX-ACCESS   read-only
    STATUS       current
    DESCRIPTION
        "Cisco UCS adaptor:MenloQErrorStats:uncorrectableErrors
        managed object property"
    ::= { cucsAdaptorMenloQErrorStatsEntry 25 }

cucsAdaptorMenloQErrorStatsUncorrectableErrorsDelta OBJECT-TYPE
    SYNTAX       Counter64
    MAX-ACCESS   read-only
    STATUS       current
    DESCRIPTION
        "Cisco UCS adaptor:MenloQErrorStats:uncorrectableErrorsDelta
        managed object property"
    ::= { cucsAdaptorMenloQErrorStatsEntry 26 }

cucsAdaptorMenloQErrorStatsUncorrectableErrorsDeltaAvg OBJECT-TYPE
    SYNTAX       Unsigned64
    MAX-ACCESS   read-only
    STATUS       current
    DESCRIPTION
        "Cisco UCS adaptor:MenloQErrorStats:uncorrectableErrorsDeltaAvg
        managed object property"
    ::= { cucsAdaptorMenloQErrorStatsEntry 27 }

cucsAdaptorMenloQErrorStatsUncorrectableErrorsDeltaMax OBJECT-TYPE
    SYNTAX       Unsigned64
    MAX-ACCESS   read-only
    STATUS       current
    DESCRIPTION
        "Cisco UCS adaptor:MenloQErrorStats:uncorrectableErrorsDeltaMax
        managed object property"
    ::= { cucsAdaptorMenloQErrorStatsEntry 28 }

cucsAdaptorMenloQErrorStatsUncorrectableErrorsDeltaMin OBJECT-TYPE
    SYNTAX       Unsigned64
    MAX-ACCESS   read-only
    STATUS       current
    DESCRIPTION
        "Cisco UCS adaptor:MenloQErrorStats:uncorrectableErrorsDeltaMin
        managed object property"
    ::= { cucsAdaptorMenloQErrorStatsEntry 29 }

cucsAdaptorMenloQErrorStatsUpdate OBJECT-TYPE
    SYNTAX       Gauge32
    MAX-ACCESS   read-only
    STATUS       current
    DESCRIPTION
        "Cisco UCS adaptor:MenloQErrorStats:update managed
        object property"
    ::= { cucsAdaptorMenloQErrorStatsEntry 30 }

cucsAdaptorMenloQErrorStatsHistTable OBJECT-TYPE
    SYNTAX           SEQUENCE OF CucsAdaptorMenloQErrorStatsHistEntry
    MAX-ACCESS       not-accessible
    STATUS           current
    DESCRIPTION
        "Cisco UCS adaptor:MenloQErrorStatsHist managed object table"
    ::= { cucsAdaptorObjects 78 }

cucsAdaptorMenloQErrorStatsHistEntry OBJECT-TYPE
    SYNTAX           CucsAdaptorMenloQErrorStatsHistEntry
    MAX-ACCESS       not-accessible
    STATUS           current
    DESCRIPTION
        "Entry for the cucsAdaptorMenloQErrorStatsHistTable table."
    INDEX { cucsAdaptorMenloQErrorStatsHistInstanceId }
    ::= { cucsAdaptorMenloQErrorStatsHistTable 1 }

CucsAdaptorMenloQErrorStatsHistEntry ::= SEQUENCE {
    cucsAdaptorMenloQErrorStatsHistInstanceId                        CucsManagedObjectId,
    cucsAdaptorMenloQErrorStatsHistDn                                CucsManagedObjectDn,
    cucsAdaptorMenloQErrorStatsHistRn                                SnmpAdminString,
    cucsAdaptorMenloQErrorStatsHistCorrectableErrors                 Unsigned64,
    cucsAdaptorMenloQErrorStatsHistCorrectableErrorsDelta            Unsigned64,
    cucsAdaptorMenloQErrorStatsHistCorrectableErrorsDeltaAvg         Unsigned64,
    cucsAdaptorMenloQErrorStatsHistCorrectableErrorsDeltaMax         Unsigned64,
    cucsAdaptorMenloQErrorStatsHistCorrectableErrorsDeltaMin         Unsigned64,
    cucsAdaptorMenloQErrorStatsHistId                                Unsigned64,
    cucsAdaptorMenloQErrorStatsHistMostRecent                        TruthValue,
    cucsAdaptorMenloQErrorStatsHistPopErrors                         Unsigned64,
    cucsAdaptorMenloQErrorStatsHistPopErrorsDelta                    Unsigned64,
    cucsAdaptorMenloQErrorStatsHistPopErrorsDeltaAvg                 Unsigned64,
    cucsAdaptorMenloQErrorStatsHistPopErrorsDeltaMax                 Unsigned64,
    cucsAdaptorMenloQErrorStatsHistPopErrorsDeltaMin                 Unsigned64,
    cucsAdaptorMenloQErrorStatsHistPushErrors                        Unsigned64,
    cucsAdaptorMenloQErrorStatsHistPushErrorsDelta                   Unsigned64,
    cucsAdaptorMenloQErrorStatsHistPushErrorsDeltaAvg                Unsigned64,
    cucsAdaptorMenloQErrorStatsHistPushErrorsDeltaMax                Unsigned64,
    cucsAdaptorMenloQErrorStatsHistPushErrorsDeltaMin                Unsigned64,
    cucsAdaptorMenloQErrorStatsHistSuspect                           TruthValue,
    cucsAdaptorMenloQErrorStatsHistThresholded                       CucsAdaptorMenloQErrorStatsHistThresholded,
    cucsAdaptorMenloQErrorStatsHistTimeCollected                     DateAndTime,
    cucsAdaptorMenloQErrorStatsHistUncorrectableErrors               Unsigned64,
    cucsAdaptorMenloQErrorStatsHistUncorrectableErrorsDelta          Unsigned64,
    cucsAdaptorMenloQErrorStatsHistUncorrectableErrorsDeltaAvg       Unsigned64,
    cucsAdaptorMenloQErrorStatsHistUncorrectableErrorsDeltaMax       Unsigned64,
    cucsAdaptorMenloQErrorStatsHistUncorrectableErrorsDeltaMin       Unsigned64
}

cucsAdaptorMenloQErrorStatsHistInstanceId OBJECT-TYPE
    SYNTAX       CucsManagedObjectId
    MAX-ACCESS   not-accessible
    STATUS       current
    DESCRIPTION
        "Instance identifier of the managed object."
    ::= { cucsAdaptorMenloQErrorStatsHistEntry 1 }

cucsAdaptorMenloQErrorStatsHistDn OBJECT-TYPE
    SYNTAX       CucsManagedObjectDn
    MAX-ACCESS   read-only
    STATUS       current
    DESCRIPTION
        "Cisco UCS adaptor:MenloQErrorStatsHist:dn managed
        object property"
    ::= { cucsAdaptorMenloQErrorStatsHistEntry 2 }

cucsAdaptorMenloQErrorStatsHistRn OBJECT-TYPE
    SYNTAX       SnmpAdminString
    MAX-ACCESS   read-only
    STATUS       current
    DESCRIPTION
        "Cisco UCS adaptor:MenloQErrorStatsHist:rn managed
        object property"
    ::= { cucsAdaptorMenloQErrorStatsHistEntry 3 }

cucsAdaptorMenloQErrorStatsHistCorrectableErrors OBJECT-TYPE
    SYNTAX       Unsigned64
    MAX-ACCESS   read-only
    STATUS       current
    DESCRIPTION
        "Cisco UCS adaptor:MenloQErrorStatsHist:correctableErrors
        managed object property"
    ::= { cucsAdaptorMenloQErrorStatsHistEntry 4 }

cucsAdaptorMenloQErrorStatsHistCorrectableErrorsDelta OBJECT-TYPE
    SYNTAX       Unsigned64
    MAX-ACCESS   read-only
    STATUS       current
    DESCRIPTION
        "Cisco UCS adaptor:MenloQErrorStatsHist:correctableErrorsDelta
        managed object property"
    ::= { cucsAdaptorMenloQErrorStatsHistEntry 5 }

cucsAdaptorMenloQErrorStatsHistCorrectableErrorsDeltaAvg OBJECT-TYPE
    SYNTAX       Unsigned64
    MAX-ACCESS   read-only
    STATUS       current
    DESCRIPTION
        "Cisco UCS adaptor:MenloQErrorStatsHist:correctableErrorsDeltaAvg
        managed object property"
    ::= { cucsAdaptorMenloQErrorStatsHistEntry 6 }

cucsAdaptorMenloQErrorStatsHistCorrectableErrorsDeltaMax OBJECT-TYPE
    SYNTAX       Unsigned64
    MAX-ACCESS   read-only
    STATUS       current
    DESCRIPTION
        "Cisco UCS adaptor:MenloQErrorStatsHist:correctableErrorsDeltaMax
        managed object property"
    ::= { cucsAdaptorMenloQErrorStatsHistEntry 7 }

cucsAdaptorMenloQErrorStatsHistCorrectableErrorsDeltaMin OBJECT-TYPE
    SYNTAX       Unsigned64
    MAX-ACCESS   read-only
    STATUS       current
    DESCRIPTION
        "Cisco UCS adaptor:MenloQErrorStatsHist:correctableErrorsDeltaMin
        managed object property"
    ::= { cucsAdaptorMenloQErrorStatsHistEntry 8 }

cucsAdaptorMenloQErrorStatsHistId OBJECT-TYPE
    SYNTAX       Unsigned64
    MAX-ACCESS   read-only
    STATUS       current
    DESCRIPTION
        "Cisco UCS adaptor:MenloQErrorStatsHist:id managed
        object property"
    ::= { cucsAdaptorMenloQErrorStatsHistEntry 9 }

cucsAdaptorMenloQErrorStatsHistMostRecent OBJECT-TYPE
    SYNTAX       TruthValue
    MAX-ACCESS   read-only
    STATUS       current
    DESCRIPTION
        "Cisco UCS adaptor:MenloQErrorStatsHist:mostRecent
        managed object property"
    ::= { cucsAdaptorMenloQErrorStatsHistEntry 10 }

cucsAdaptorMenloQErrorStatsHistPopErrors OBJECT-TYPE
    SYNTAX       Unsigned64
    MAX-ACCESS   read-only
    STATUS       current
    DESCRIPTION
        "Cisco UCS adaptor:MenloQErrorStatsHist:popErrors
        managed object property"
    ::= { cucsAdaptorMenloQErrorStatsHistEntry 11 }

cucsAdaptorMenloQErrorStatsHistPopErrorsDelta OBJECT-TYPE
    SYNTAX       Unsigned64
    MAX-ACCESS   read-only
    STATUS       current
    DESCRIPTION
        "Cisco UCS adaptor:MenloQErrorStatsHist:popErrorsDelta
        managed object property"
    ::= { cucsAdaptorMenloQErrorStatsHistEntry 12 }

cucsAdaptorMenloQErrorStatsHistPopErrorsDeltaAvg OBJECT-TYPE
    SYNTAX       Unsigned64
    MAX-ACCESS   read-only
    STATUS       current
    DESCRIPTION
        "Cisco UCS adaptor:MenloQErrorStatsHist:popErrorsDeltaAvg
        managed object property"
    ::= { cucsAdaptorMenloQErrorStatsHistEntry 13 }

cucsAdaptorMenloQErrorStatsHistPopErrorsDeltaMax OBJECT-TYPE
    SYNTAX       Unsigned64
    MAX-ACCESS   read-only
    STATUS       current
    DESCRIPTION
        "Cisco UCS adaptor:MenloQErrorStatsHist:popErrorsDeltaMax
        managed object property"
    ::= { cucsAdaptorMenloQErrorStatsHistEntry 14 }

cucsAdaptorMenloQErrorStatsHistPopErrorsDeltaMin OBJECT-TYPE
    SYNTAX       Unsigned64
    MAX-ACCESS   read-only
    STATUS       current
    DESCRIPTION
        "Cisco UCS adaptor:MenloQErrorStatsHist:popErrorsDeltaMin
        managed object property"
    ::= { cucsAdaptorMenloQErrorStatsHistEntry 15 }

cucsAdaptorMenloQErrorStatsHistPushErrors OBJECT-TYPE
    SYNTAX       Unsigned64
    MAX-ACCESS   read-only
    STATUS       current
    DESCRIPTION
        "Cisco UCS adaptor:MenloQErrorStatsHist:pushErrors
        managed object property"
    ::= { cucsAdaptorMenloQErrorStatsHistEntry 16 }

cucsAdaptorMenloQErrorStatsHistPushErrorsDelta OBJECT-TYPE
    SYNTAX       Unsigned64
    MAX-ACCESS   read-only
    STATUS       current
    DESCRIPTION
        "Cisco UCS adaptor:MenloQErrorStatsHist:pushErrorsDelta
        managed object property"
    ::= { cucsAdaptorMenloQErrorStatsHistEntry 17 }

cucsAdaptorMenloQErrorStatsHistPushErrorsDeltaAvg OBJECT-TYPE
    SYNTAX       Unsigned64
    MAX-ACCESS   read-only
    STATUS       current
    DESCRIPTION
        "Cisco UCS adaptor:MenloQErrorStatsHist:pushErrorsDeltaAvg
        managed object property"
    ::= { cucsAdaptorMenloQErrorStatsHistEntry 18 }

cucsAdaptorMenloQErrorStatsHistPushErrorsDeltaMax OBJECT-TYPE
    SYNTAX       Unsigned64
    MAX-ACCESS   read-only
    STATUS       current
    DESCRIPTION
        "Cisco UCS adaptor:MenloQErrorStatsHist:pushErrorsDeltaMax
        managed object property"
    ::= { cucsAdaptorMenloQErrorStatsHistEntry 19 }

cucsAdaptorMenloQErrorStatsHistPushErrorsDeltaMin OBJECT-TYPE
    SYNTAX       Unsigned64
    MAX-ACCESS   read-only
    STATUS       current
    DESCRIPTION
        "Cisco UCS adaptor:MenloQErrorStatsHist:pushErrorsDeltaMin
        managed object property"
    ::= { cucsAdaptorMenloQErrorStatsHistEntry 20 }

cucsAdaptorMenloQErrorStatsHistSuspect OBJECT-TYPE
    SYNTAX       TruthValue
    MAX-ACCESS   read-only
    STATUS       current
    DESCRIPTION
        "Cisco UCS adaptor:MenloQErrorStatsHist:suspect
        managed object property"
    ::= { cucsAdaptorMenloQErrorStatsHistEntry 21 }

cucsAdaptorMenloQErrorStatsHistThresholded OBJECT-TYPE
    SYNTAX       CucsAdaptorMenloQErrorStatsHistThresholded
    MAX-ACCESS   read-only
    STATUS       current
    DESCRIPTION
        "Cisco UCS adaptor:MenloQErrorStatsHist:thresholded
        managed object property"
    ::= { cucsAdaptorMenloQErrorStatsHistEntry 22 }

cucsAdaptorMenloQErrorStatsHistTimeCollected OBJECT-TYPE
    SYNTAX       DateAndTime
    MAX-ACCESS   read-only
    STATUS       current
    DESCRIPTION
        "Cisco UCS adaptor:MenloQErrorStatsHist:timeCollected
        managed object property"
    ::= { cucsAdaptorMenloQErrorStatsHistEntry 23 }

cucsAdaptorMenloQErrorStatsHistUncorrectableErrors OBJECT-TYPE
    SYNTAX       Unsigned64
    MAX-ACCESS   read-only
    STATUS       current
    DESCRIPTION
        "Cisco UCS adaptor:MenloQErrorStatsHist:uncorrectableErrors
        managed object property"
    ::= { cucsAdaptorMenloQErrorStatsHistEntry 24 }

cucsAdaptorMenloQErrorStatsHistUncorrectableErrorsDelta OBJECT-TYPE
    SYNTAX       Unsigned64
    MAX-ACCESS   read-only
    STATUS       current
    DESCRIPTION
        "Cisco UCS adaptor:MenloQErrorStatsHist:uncorrectableErrorsDelta
        managed object property"
    ::= { cucsAdaptorMenloQErrorStatsHistEntry 25 }

cucsAdaptorMenloQErrorStatsHistUncorrectableErrorsDeltaAvg OBJECT-TYPE
    SYNTAX       Unsigned64
    MAX-ACCESS   read-only
    STATUS       current
    DESCRIPTION
        "Cisco UCS adaptor:MenloQErrorStatsHist:uncorrectableErrorsDeltaAv
        g managed object property"
    ::= { cucsAdaptorMenloQErrorStatsHistEntry 26 }

cucsAdaptorMenloQErrorStatsHistUncorrectableErrorsDeltaMax OBJECT-TYPE
    SYNTAX       Unsigned64
    MAX-ACCESS   read-only
    STATUS       current
    DESCRIPTION
        "Cisco UCS adaptor:MenloQErrorStatsHist:uncorrectableErrorsDeltaMa
        x managed object property"
    ::= { cucsAdaptorMenloQErrorStatsHistEntry 27 }

cucsAdaptorMenloQErrorStatsHistUncorrectableErrorsDeltaMin OBJECT-TYPE
    SYNTAX       Unsigned64
    MAX-ACCESS   read-only
    STATUS       current
    DESCRIPTION
        "Cisco UCS adaptor:MenloQErrorStatsHist:uncorrectableErrorsDeltaMi
        n managed object property"
    ::= { cucsAdaptorMenloQErrorStatsHistEntry 28 }

cucsAdaptorMenloQStatsTable OBJECT-TYPE
    SYNTAX           SEQUENCE OF CucsAdaptorMenloQStatsEntry
    MAX-ACCESS       not-accessible
    STATUS           current
    DESCRIPTION
        "Cisco UCS adaptor:MenloQStats managed object table"
    ::= { cucsAdaptorObjects 79 }

cucsAdaptorMenloQStatsEntry OBJECT-TYPE
    SYNTAX           CucsAdaptorMenloQStatsEntry
    MAX-ACCESS       not-accessible
    STATUS           current
    DESCRIPTION
        "Entry for the cucsAdaptorMenloQStatsTable table."
    INDEX { cucsAdaptorMenloQStatsInstanceId }
    ::= { cucsAdaptorMenloQStatsTable 1 }

CucsAdaptorMenloQStatsEntry ::= SEQUENCE {
    cucsAdaptorMenloQStatsInstanceId                                 CucsManagedObjectId,
    cucsAdaptorMenloQStatsDn                                         CucsManagedObjectDn,
    cucsAdaptorMenloQStatsRn                                         SnmpAdminString,
    cucsAdaptorMenloQStatsDropOverrunN0                              Unsigned64,
    cucsAdaptorMenloQStatsDropOverrunN0Delta                         Counter64,
    cucsAdaptorMenloQStatsDropOverrunN0DeltaAvg                      Unsigned64,
    cucsAdaptorMenloQStatsDropOverrunN0DeltaMax                      Unsigned64,
    cucsAdaptorMenloQStatsDropOverrunN0DeltaMin                      Unsigned64,
    cucsAdaptorMenloQStatsDropOverrunN1                              Unsigned64,
    cucsAdaptorMenloQStatsDropOverrunN1Delta                         Counter64,
    cucsAdaptorMenloQStatsDropOverrunN1DeltaAvg                      Unsigned64,
    cucsAdaptorMenloQStatsDropOverrunN1DeltaMax                      Unsigned64,
    cucsAdaptorMenloQStatsDropOverrunN1DeltaMin                      Unsigned64,
    cucsAdaptorMenloQStatsIntervals                                  Gauge32,
    cucsAdaptorMenloQStatsMenloQueueComponent                        CucsAdaptorMenloQueueStatsComponent,
    cucsAdaptorMenloQStatsMenloQueueIndex                            CucsAdaptorMenloStatsIndex,
    cucsAdaptorMenloQStatsSuspect                                    TruthValue,
    cucsAdaptorMenloQStatsThresholded                                CucsAdaptorMenloQStatsThresholded,
    cucsAdaptorMenloQStatsTimeCollected                              DateAndTime,
    cucsAdaptorMenloQStatsTruncateOverrunN0                          Unsigned64,
    cucsAdaptorMenloQStatsTruncateOverrunN0Delta                     Counter64,
    cucsAdaptorMenloQStatsTruncateOverrunN0DeltaAvg                  Unsigned64,
    cucsAdaptorMenloQStatsTruncateOverrunN0DeltaMax                  Unsigned64,
    cucsAdaptorMenloQStatsTruncateOverrunN0DeltaMin                  Unsigned64,
    cucsAdaptorMenloQStatsTruncateOverrunN1                          Unsigned64,
    cucsAdaptorMenloQStatsTruncateOverrunN1Delta                     Counter64,
    cucsAdaptorMenloQStatsTruncateOverrunN1DeltaAvg                  Unsigned64,
    cucsAdaptorMenloQStatsTruncateOverrunN1DeltaMax                  Unsigned64,
    cucsAdaptorMenloQStatsTruncateOverrunN1DeltaMin                  Unsigned64,
    cucsAdaptorMenloQStatsUpdate                                     Gauge32
}

cucsAdaptorMenloQStatsInstanceId OBJECT-TYPE
    SYNTAX       CucsManagedObjectId
    MAX-ACCESS   not-accessible
    STATUS       current
    DESCRIPTION
        "Instance identifier of the managed object."
    ::= { cucsAdaptorMenloQStatsEntry 1 }

cucsAdaptorMenloQStatsDn OBJECT-TYPE
    SYNTAX       CucsManagedObjectDn
    MAX-ACCESS   read-only
    STATUS       current
    DESCRIPTION
        "Cisco UCS adaptor:MenloQStats:dn managed object property"
    ::= { cucsAdaptorMenloQStatsEntry 2 }

cucsAdaptorMenloQStatsRn OBJECT-TYPE
    SYNTAX       SnmpAdminString
    MAX-ACCESS   read-only
    STATUS       current
    DESCRIPTION
        "Cisco UCS adaptor:MenloQStats:rn managed object property"
    ::= { cucsAdaptorMenloQStatsEntry 3 }

cucsAdaptorMenloQStatsDropOverrunN0 OBJECT-TYPE
    SYNTAX       Unsigned64
    MAX-ACCESS   read-only
    STATUS       current
    DESCRIPTION
        "Cisco UCS adaptor:MenloQStats:dropOverrunN0 managed
        object property"
    ::= { cucsAdaptorMenloQStatsEntry 4 }

cucsAdaptorMenloQStatsDropOverrunN0Delta OBJECT-TYPE
    SYNTAX       Counter64
    MAX-ACCESS   read-only
    STATUS       current
    DESCRIPTION
        "Cisco UCS adaptor:MenloQStats:dropOverrunN0Delta
        managed object property"
    ::= { cucsAdaptorMenloQStatsEntry 5 }

cucsAdaptorMenloQStatsDropOverrunN0DeltaAvg OBJECT-TYPE
    SYNTAX       Unsigned64
    MAX-ACCESS   read-only
    STATUS       current
    DESCRIPTION
        "Cisco UCS adaptor:MenloQStats:dropOverrunN0DeltaAvg
        managed object property"
    ::= { cucsAdaptorMenloQStatsEntry 6 }

cucsAdaptorMenloQStatsDropOverrunN0DeltaMax OBJECT-TYPE
    SYNTAX       Unsigned64
    MAX-ACCESS   read-only
    STATUS       current
    DESCRIPTION
        "Cisco UCS adaptor:MenloQStats:dropOverrunN0DeltaMax
        managed object property"
    ::= { cucsAdaptorMenloQStatsEntry 7 }

cucsAdaptorMenloQStatsDropOverrunN0DeltaMin OBJECT-TYPE
    SYNTAX       Unsigned64
    MAX-ACCESS   read-only
    STATUS       current
    DESCRIPTION
        "Cisco UCS adaptor:MenloQStats:dropOverrunN0DeltaMin
        managed object property"
    ::= { cucsAdaptorMenloQStatsEntry 8 }

cucsAdaptorMenloQStatsDropOverrunN1 OBJECT-TYPE
    SYNTAX       Unsigned64
    MAX-ACCESS   read-only
    STATUS       current
    DESCRIPTION
        "Cisco UCS adaptor:MenloQStats:dropOverrunN1 managed
        object property"
    ::= { cucsAdaptorMenloQStatsEntry 9 }

cucsAdaptorMenloQStatsDropOverrunN1Delta OBJECT-TYPE
    SYNTAX       Counter64
    MAX-ACCESS   read-only
    STATUS       current
    DESCRIPTION
        "Cisco UCS adaptor:MenloQStats:dropOverrunN1Delta
        managed object property"
    ::= { cucsAdaptorMenloQStatsEntry 10 }

cucsAdaptorMenloQStatsDropOverrunN1DeltaAvg OBJECT-TYPE
    SYNTAX       Unsigned64
    MAX-ACCESS   read-only
    STATUS       current
    DESCRIPTION
        "Cisco UCS adaptor:MenloQStats:dropOverrunN1DeltaAvg
        managed object property"
    ::= { cucsAdaptorMenloQStatsEntry 11 }

cucsAdaptorMenloQStatsDropOverrunN1DeltaMax OBJECT-TYPE
    SYNTAX       Unsigned64
    MAX-ACCESS   read-only
    STATUS       current
    DESCRIPTION
        "Cisco UCS adaptor:MenloQStats:dropOverrunN1DeltaMax
        managed object property"
    ::= { cucsAdaptorMenloQStatsEntry 12 }

cucsAdaptorMenloQStatsDropOverrunN1DeltaMin OBJECT-TYPE
    SYNTAX       Unsigned64
    MAX-ACCESS   read-only
    STATUS       current
    DESCRIPTION
        "Cisco UCS adaptor:MenloQStats:dropOverrunN1DeltaMin
        managed object property"
    ::= { cucsAdaptorMenloQStatsEntry 13 }

cucsAdaptorMenloQStatsIntervals OBJECT-TYPE
    SYNTAX       Gauge32
    MAX-ACCESS   read-only
    STATUS       current
    DESCRIPTION
        "Cisco UCS adaptor:MenloQStats:intervals managed object property"
    ::= { cucsAdaptorMenloQStatsEntry 14 }

cucsAdaptorMenloQStatsMenloQueueComponent OBJECT-TYPE
    SYNTAX       CucsAdaptorMenloQueueStatsComponent
    MAX-ACCESS   read-only
    STATUS       current
    DESCRIPTION
        "Cisco UCS adaptor:MenloQStats:menloQueueComponent
        managed object property"
    ::= { cucsAdaptorMenloQStatsEntry 15 }

cucsAdaptorMenloQStatsMenloQueueIndex OBJECT-TYPE
    SYNTAX       CucsAdaptorMenloStatsIndex
    MAX-ACCESS   read-only
    STATUS       current
    DESCRIPTION
        "Cisco UCS adaptor:MenloQStats:menloQueueIndex
        managed object property"
    ::= { cucsAdaptorMenloQStatsEntry 16 }

cucsAdaptorMenloQStatsSuspect OBJECT-TYPE
    SYNTAX       TruthValue
    MAX-ACCESS   read-only
    STATUS       current
    DESCRIPTION
        "Cisco UCS adaptor:MenloQStats:suspect managed object property"
    ::= { cucsAdaptorMenloQStatsEntry 17 }

cucsAdaptorMenloQStatsThresholded OBJECT-TYPE
    SYNTAX       CucsAdaptorMenloQStatsThresholded
    MAX-ACCESS   read-only
    STATUS       current
    DESCRIPTION
        "Cisco UCS adaptor:MenloQStats:thresholded managed
        object property"
    ::= { cucsAdaptorMenloQStatsEntry 18 }

cucsAdaptorMenloQStatsTimeCollected OBJECT-TYPE
    SYNTAX       DateAndTime
    MAX-ACCESS   read-only
    STATUS       current
    DESCRIPTION
        "Cisco UCS adaptor:MenloQStats:timeCollected managed
        object property"
    ::= { cucsAdaptorMenloQStatsEntry 19 }

cucsAdaptorMenloQStatsTruncateOverrunN0 OBJECT-TYPE
    SYNTAX       Unsigned64
    MAX-ACCESS   read-only
    STATUS       current
    DESCRIPTION
        "Cisco UCS adaptor:MenloQStats:truncateOverrunN0
        managed object property"
    ::= { cucsAdaptorMenloQStatsEntry 20 }

cucsAdaptorMenloQStatsTruncateOverrunN0Delta OBJECT-TYPE
    SYNTAX       Counter64
    MAX-ACCESS   read-only
    STATUS       current
    DESCRIPTION
        "Cisco UCS adaptor:MenloQStats:truncateOverrunN0Delta
        managed object property"
    ::= { cucsAdaptorMenloQStatsEntry 21 }

cucsAdaptorMenloQStatsTruncateOverrunN0DeltaAvg OBJECT-TYPE
    SYNTAX       Unsigned64
    MAX-ACCESS   read-only
    STATUS       current
    DESCRIPTION
        "Cisco UCS adaptor:MenloQStats:truncateOverrunN0DeltaAvg
        managed object property"
    ::= { cucsAdaptorMenloQStatsEntry 22 }

cucsAdaptorMenloQStatsTruncateOverrunN0DeltaMax OBJECT-TYPE
    SYNTAX       Unsigned64
    MAX-ACCESS   read-only
    STATUS       current
    DESCRIPTION
        "Cisco UCS adaptor:MenloQStats:truncateOverrunN0DeltaMax
        managed object property"
    ::= { cucsAdaptorMenloQStatsEntry 23 }

cucsAdaptorMenloQStatsTruncateOverrunN0DeltaMin OBJECT-TYPE
    SYNTAX       Unsigned64
    MAX-ACCESS   read-only
    STATUS       current
    DESCRIPTION
        "Cisco UCS adaptor:MenloQStats:truncateOverrunN0DeltaMin
        managed object property"
    ::= { cucsAdaptorMenloQStatsEntry 24 }

cucsAdaptorMenloQStatsTruncateOverrunN1 OBJECT-TYPE
    SYNTAX       Unsigned64
    MAX-ACCESS   read-only
    STATUS       current
    DESCRIPTION
        "Cisco UCS adaptor:MenloQStats:truncateOverrunN1
        managed object property"
    ::= { cucsAdaptorMenloQStatsEntry 25 }

cucsAdaptorMenloQStatsTruncateOverrunN1Delta OBJECT-TYPE
    SYNTAX       Counter64
    MAX-ACCESS   read-only
    STATUS       current
    DESCRIPTION
        "Cisco UCS adaptor:MenloQStats:truncateOverrunN1Delta
        managed object property"
    ::= { cucsAdaptorMenloQStatsEntry 26 }

cucsAdaptorMenloQStatsTruncateOverrunN1DeltaAvg OBJECT-TYPE
    SYNTAX       Unsigned64
    MAX-ACCESS   read-only
    STATUS       current
    DESCRIPTION
        "Cisco UCS adaptor:MenloQStats:truncateOverrunN1DeltaAvg
        managed object property"
    ::= { cucsAdaptorMenloQStatsEntry 27 }

cucsAdaptorMenloQStatsTruncateOverrunN1DeltaMax OBJECT-TYPE
    SYNTAX       Unsigned64
    MAX-ACCESS   read-only
    STATUS       current
    DESCRIPTION
        "Cisco UCS adaptor:MenloQStats:truncateOverrunN1DeltaMax
        managed object property"
    ::= { cucsAdaptorMenloQStatsEntry 28 }

cucsAdaptorMenloQStatsTruncateOverrunN1DeltaMin OBJECT-TYPE
    SYNTAX       Unsigned64
    MAX-ACCESS   read-only
    STATUS       current
    DESCRIPTION
        "Cisco UCS adaptor:MenloQStats:truncateOverrunN1DeltaMin
        managed object property"
    ::= { cucsAdaptorMenloQStatsEntry 29 }

cucsAdaptorMenloQStatsUpdate OBJECT-TYPE
    SYNTAX       Gauge32
    MAX-ACCESS   read-only
    STATUS       current
    DESCRIPTION
        "Cisco UCS adaptor:MenloQStats:update managed object property"
    ::= { cucsAdaptorMenloQStatsEntry 30 }

cucsAdaptorMenloQStatsHistTable OBJECT-TYPE
    SYNTAX           SEQUENCE OF CucsAdaptorMenloQStatsHistEntry
    MAX-ACCESS       not-accessible
    STATUS           current
    DESCRIPTION
        "Cisco UCS adaptor:MenloQStatsHist managed object table"
    ::= { cucsAdaptorObjects 80 }

cucsAdaptorMenloQStatsHistEntry OBJECT-TYPE
    SYNTAX           CucsAdaptorMenloQStatsHistEntry
    MAX-ACCESS       not-accessible
    STATUS           current
    DESCRIPTION
        "Entry for the cucsAdaptorMenloQStatsHistTable table."
    INDEX { cucsAdaptorMenloQStatsHistInstanceId }
    ::= { cucsAdaptorMenloQStatsHistTable 1 }

CucsAdaptorMenloQStatsHistEntry ::= SEQUENCE {
    cucsAdaptorMenloQStatsHistInstanceId                             CucsManagedObjectId,
    cucsAdaptorMenloQStatsHistDn                                     CucsManagedObjectDn,
    cucsAdaptorMenloQStatsHistRn                                     SnmpAdminString,
    cucsAdaptorMenloQStatsHistDropOverrunN0                          Unsigned64,
    cucsAdaptorMenloQStatsHistDropOverrunN0Delta                     Unsigned64,
    cucsAdaptorMenloQStatsHistDropOverrunN0DeltaAvg                  Unsigned64,
    cucsAdaptorMenloQStatsHistDropOverrunN0DeltaMax                  Unsigned64,
    cucsAdaptorMenloQStatsHistDropOverrunN0DeltaMin                  Unsigned64,
    cucsAdaptorMenloQStatsHistDropOverrunN1                          Unsigned64,
    cucsAdaptorMenloQStatsHistDropOverrunN1Delta                     Unsigned64,
    cucsAdaptorMenloQStatsHistDropOverrunN1DeltaAvg                  Unsigned64,
    cucsAdaptorMenloQStatsHistDropOverrunN1DeltaMax                  Unsigned64,
    cucsAdaptorMenloQStatsHistDropOverrunN1DeltaMin                  Unsigned64,
    cucsAdaptorMenloQStatsHistId                                     Unsigned64,
    cucsAdaptorMenloQStatsHistMostRecent                             TruthValue,
    cucsAdaptorMenloQStatsHistSuspect                                TruthValue,
    cucsAdaptorMenloQStatsHistThresholded                            CucsAdaptorMenloQStatsHistThresholded,
    cucsAdaptorMenloQStatsHistTimeCollected                          DateAndTime,
    cucsAdaptorMenloQStatsHistTruncateOverrunN0                      Unsigned64,
    cucsAdaptorMenloQStatsHistTruncateOverrunN0Delta                 Unsigned64,
    cucsAdaptorMenloQStatsHistTruncateOverrunN0DeltaAvg              Unsigned64,
    cucsAdaptorMenloQStatsHistTruncateOverrunN0DeltaMax              Unsigned64,
    cucsAdaptorMenloQStatsHistTruncateOverrunN0DeltaMin              Unsigned64,
    cucsAdaptorMenloQStatsHistTruncateOverrunN1                      Unsigned64,
    cucsAdaptorMenloQStatsHistTruncateOverrunN1Delta                 Unsigned64,
    cucsAdaptorMenloQStatsHistTruncateOverrunN1DeltaAvg              Unsigned64,
    cucsAdaptorMenloQStatsHistTruncateOverrunN1DeltaMax              Unsigned64,
    cucsAdaptorMenloQStatsHistTruncateOverrunN1DeltaMin              Unsigned64
}

cucsAdaptorMenloQStatsHistInstanceId OBJECT-TYPE
    SYNTAX       CucsManagedObjectId
    MAX-ACCESS   not-accessible
    STATUS       current
    DESCRIPTION
        "Instance identifier of the managed object."
    ::= { cucsAdaptorMenloQStatsHistEntry 1 }

cucsAdaptorMenloQStatsHistDn OBJECT-TYPE
    SYNTAX       CucsManagedObjectDn
    MAX-ACCESS   read-only
    STATUS       current
    DESCRIPTION
        "Cisco UCS adaptor:MenloQStatsHist:dn managed object property"
    ::= { cucsAdaptorMenloQStatsHistEntry 2 }

cucsAdaptorMenloQStatsHistRn OBJECT-TYPE
    SYNTAX       SnmpAdminString
    MAX-ACCESS   read-only
    STATUS       current
    DESCRIPTION
        "Cisco UCS adaptor:MenloQStatsHist:rn managed object property"
    ::= { cucsAdaptorMenloQStatsHistEntry 3 }

cucsAdaptorMenloQStatsHistDropOverrunN0 OBJECT-TYPE
    SYNTAX       Unsigned64
    MAX-ACCESS   read-only
    STATUS       current
    DESCRIPTION
        "Cisco UCS adaptor:MenloQStatsHist:dropOverrunN0
        managed object property"
    ::= { cucsAdaptorMenloQStatsHistEntry 4 }

cucsAdaptorMenloQStatsHistDropOverrunN0Delta OBJECT-TYPE
    SYNTAX       Unsigned64
    MAX-ACCESS   read-only
    STATUS       current
    DESCRIPTION
        "Cisco UCS adaptor:MenloQStatsHist:dropOverrunN0Delta
        managed object property"
    ::= { cucsAdaptorMenloQStatsHistEntry 5 }

cucsAdaptorMenloQStatsHistDropOverrunN0DeltaAvg OBJECT-TYPE
    SYNTAX       Unsigned64
    MAX-ACCESS   read-only
    STATUS       current
    DESCRIPTION
        "Cisco UCS adaptor:MenloQStatsHist:dropOverrunN0DeltaAvg
        managed object property"
    ::= { cucsAdaptorMenloQStatsHistEntry 6 }

cucsAdaptorMenloQStatsHistDropOverrunN0DeltaMax OBJECT-TYPE
    SYNTAX       Unsigned64
    MAX-ACCESS   read-only
    STATUS       current
    DESCRIPTION
        "Cisco UCS adaptor:MenloQStatsHist:dropOverrunN0DeltaMax
        managed object property"
    ::= { cucsAdaptorMenloQStatsHistEntry 7 }

cucsAdaptorMenloQStatsHistDropOverrunN0DeltaMin OBJECT-TYPE
    SYNTAX       Unsigned64
    MAX-ACCESS   read-only
    STATUS       current
    DESCRIPTION
        "Cisco UCS adaptor:MenloQStatsHist:dropOverrunN0DeltaMin
        managed object property"
    ::= { cucsAdaptorMenloQStatsHistEntry 8 }

cucsAdaptorMenloQStatsHistDropOverrunN1 OBJECT-TYPE
    SYNTAX       Unsigned64
    MAX-ACCESS   read-only
    STATUS       current
    DESCRIPTION
        "Cisco UCS adaptor:MenloQStatsHist:dropOverrunN1
        managed object property"
    ::= { cucsAdaptorMenloQStatsHistEntry 9 }

cucsAdaptorMenloQStatsHistDropOverrunN1Delta OBJECT-TYPE
    SYNTAX       Unsigned64
    MAX-ACCESS   read-only
    STATUS       current
    DESCRIPTION
        "Cisco UCS adaptor:MenloQStatsHist:dropOverrunN1Delta
        managed object property"
    ::= { cucsAdaptorMenloQStatsHistEntry 10 }

cucsAdaptorMenloQStatsHistDropOverrunN1DeltaAvg OBJECT-TYPE
    SYNTAX       Unsigned64
    MAX-ACCESS   read-only
    STATUS       current
    DESCRIPTION
        "Cisco UCS adaptor:MenloQStatsHist:dropOverrunN1DeltaAvg
        managed object property"
    ::= { cucsAdaptorMenloQStatsHistEntry 11 }

cucsAdaptorMenloQStatsHistDropOverrunN1DeltaMax OBJECT-TYPE
    SYNTAX       Unsigned64
    MAX-ACCESS   read-only
    STATUS       current
    DESCRIPTION
        "Cisco UCS adaptor:MenloQStatsHist:dropOverrunN1DeltaMax
        managed object property"
    ::= { cucsAdaptorMenloQStatsHistEntry 12 }

cucsAdaptorMenloQStatsHistDropOverrunN1DeltaMin OBJECT-TYPE
    SYNTAX       Unsigned64
    MAX-ACCESS   read-only
    STATUS       current
    DESCRIPTION
        "Cisco UCS adaptor:MenloQStatsHist:dropOverrunN1DeltaMin
        managed object property"
    ::= { cucsAdaptorMenloQStatsHistEntry 13 }

cucsAdaptorMenloQStatsHistId OBJECT-TYPE
    SYNTAX       Unsigned64
    MAX-ACCESS   read-only
    STATUS       current
    DESCRIPTION
        "Cisco UCS adaptor:MenloQStatsHist:id managed object property"
    ::= { cucsAdaptorMenloQStatsHistEntry 14 }

cucsAdaptorMenloQStatsHistMostRecent OBJECT-TYPE
    SYNTAX       TruthValue
    MAX-ACCESS   read-only
    STATUS       current
    DESCRIPTION
        "Cisco UCS adaptor:MenloQStatsHist:mostRecent managed
        object property"
    ::= { cucsAdaptorMenloQStatsHistEntry 15 }

cucsAdaptorMenloQStatsHistSuspect OBJECT-TYPE
    SYNTAX       TruthValue
    MAX-ACCESS   read-only
    STATUS       current
    DESCRIPTION
        "Cisco UCS adaptor:MenloQStatsHist:suspect managed
        object property"
    ::= { cucsAdaptorMenloQStatsHistEntry 16 }

cucsAdaptorMenloQStatsHistThresholded OBJECT-TYPE
    SYNTAX       CucsAdaptorMenloQStatsHistThresholded
    MAX-ACCESS   read-only
    STATUS       current
    DESCRIPTION
        "Cisco UCS adaptor:MenloQStatsHist:thresholded
        managed object property"
    ::= { cucsAdaptorMenloQStatsHistEntry 17 }

cucsAdaptorMenloQStatsHistTimeCollected OBJECT-TYPE
    SYNTAX       DateAndTime
    MAX-ACCESS   read-only
    STATUS       current
    DESCRIPTION
        "Cisco UCS adaptor:MenloQStatsHist:timeCollected
        managed object property"
    ::= { cucsAdaptorMenloQStatsHistEntry 18 }

cucsAdaptorMenloQStatsHistTruncateOverrunN0 OBJECT-TYPE
    SYNTAX       Unsigned64
    MAX-ACCESS   read-only
    STATUS       current
    DESCRIPTION
        "Cisco UCS adaptor:MenloQStatsHist:truncateOverrunN0
        managed object property"
    ::= { cucsAdaptorMenloQStatsHistEntry 19 }

cucsAdaptorMenloQStatsHistTruncateOverrunN0Delta OBJECT-TYPE
    SYNTAX       Unsigned64
    MAX-ACCESS   read-only
    STATUS       current
    DESCRIPTION
        "Cisco UCS adaptor:MenloQStatsHist:truncateOverrunN0Delta
        managed object property"
    ::= { cucsAdaptorMenloQStatsHistEntry 20 }

cucsAdaptorMenloQStatsHistTruncateOverrunN0DeltaAvg OBJECT-TYPE
    SYNTAX       Unsigned64
    MAX-ACCESS   read-only
    STATUS       current
    DESCRIPTION
        "Cisco UCS adaptor:MenloQStatsHist:truncateOverrunN0DeltaAvg
        managed object property"
    ::= { cucsAdaptorMenloQStatsHistEntry 21 }

cucsAdaptorMenloQStatsHistTruncateOverrunN0DeltaMax OBJECT-TYPE
    SYNTAX       Unsigned64
    MAX-ACCESS   read-only
    STATUS       current
    DESCRIPTION
        "Cisco UCS adaptor:MenloQStatsHist:truncateOverrunN0DeltaMax
        managed object property"
    ::= { cucsAdaptorMenloQStatsHistEntry 22 }

cucsAdaptorMenloQStatsHistTruncateOverrunN0DeltaMin OBJECT-TYPE
    SYNTAX       Unsigned64
    MAX-ACCESS   read-only
    STATUS       current
    DESCRIPTION
        "Cisco UCS adaptor:MenloQStatsHist:truncateOverrunN0DeltaMin
        managed object property"
    ::= { cucsAdaptorMenloQStatsHistEntry 23 }

cucsAdaptorMenloQStatsHistTruncateOverrunN1 OBJECT-TYPE
    SYNTAX       Unsigned64
    MAX-ACCESS   read-only
    STATUS       current
    DESCRIPTION
        "Cisco UCS adaptor:MenloQStatsHist:truncateOverrunN1
        managed object property"
    ::= { cucsAdaptorMenloQStatsHistEntry 24 }

cucsAdaptorMenloQStatsHistTruncateOverrunN1Delta OBJECT-TYPE
    SYNTAX       Unsigned64
    MAX-ACCESS   read-only
    STATUS       current
    DESCRIPTION
        "Cisco UCS adaptor:MenloQStatsHist:truncateOverrunN1Delta
        managed object property"
    ::= { cucsAdaptorMenloQStatsHistEntry 25 }

cucsAdaptorMenloQStatsHistTruncateOverrunN1DeltaAvg OBJECT-TYPE
    SYNTAX       Unsigned64
    MAX-ACCESS   read-only
    STATUS       current
    DESCRIPTION
        "Cisco UCS adaptor:MenloQStatsHist:truncateOverrunN1DeltaAvg
        managed object property"
    ::= { cucsAdaptorMenloQStatsHistEntry 26 }

cucsAdaptorMenloQStatsHistTruncateOverrunN1DeltaMax OBJECT-TYPE
    SYNTAX       Unsigned64
    MAX-ACCESS   read-only
    STATUS       current
    DESCRIPTION
        "Cisco UCS adaptor:MenloQStatsHist:truncateOverrunN1DeltaMax
        managed object property"
    ::= { cucsAdaptorMenloQStatsHistEntry 27 }

cucsAdaptorMenloQStatsHistTruncateOverrunN1DeltaMin OBJECT-TYPE
    SYNTAX       Unsigned64
    MAX-ACCESS   read-only
    STATUS       current
    DESCRIPTION
        "Cisco UCS adaptor:MenloQStatsHist:truncateOverrunN1DeltaMin
        managed object property"
    ::= { cucsAdaptorMenloQStatsHistEntry 28 }

cucsAdaptorMgmtVnicEthConfigTable OBJECT-TYPE
    SYNTAX           SEQUENCE OF CucsAdaptorMgmtVnicEthConfigEntry
    MAX-ACCESS       not-accessible
    STATUS           current
    DESCRIPTION
        "Cisco UCS adaptor:MgmtVnicEthConfig managed object table"
    ::= { cucsAdaptorObjects 128 }

cucsAdaptorMgmtVnicEthConfigEntry OBJECT-TYPE
    SYNTAX           CucsAdaptorMgmtVnicEthConfigEntry
    MAX-ACCESS       not-accessible
    STATUS           current
    DESCRIPTION
        "Entry for the cucsAdaptorMgmtVnicEthConfigTable table."
    INDEX { cucsAdaptorMgmtVnicEthConfigInstanceId }
    ::= { cucsAdaptorMgmtVnicEthConfigTable 1 }

CucsAdaptorMgmtVnicEthConfigEntry ::= SEQUENCE {
    cucsAdaptorMgmtVnicEthConfigInstanceId                           CucsManagedObjectId,
    cucsAdaptorMgmtVnicEthConfigDn                                   CucsManagedObjectDn,
    cucsAdaptorMgmtVnicEthConfigRn                                   SnmpAdminString,
    cucsAdaptorMgmtVnicEthConfigHostPortId                           Gauge32,
    cucsAdaptorMgmtVnicEthConfigMacOffset                            Gauge32,
    cucsAdaptorMgmtVnicEthConfigPciSlot                              Gauge32
}

cucsAdaptorMgmtVnicEthConfigInstanceId OBJECT-TYPE
    SYNTAX       CucsManagedObjectId
    MAX-ACCESS   not-accessible
    STATUS       current
    DESCRIPTION
        "Instance identifier of the managed object."
    ::= { cucsAdaptorMgmtVnicEthConfigEntry 1 }

cucsAdaptorMgmtVnicEthConfigDn OBJECT-TYPE
    SYNTAX       CucsManagedObjectDn
    MAX-ACCESS   read-only
    STATUS       current
    DESCRIPTION
        "Cisco UCS adaptor:MgmtVnicEthConfig:dn managed object property"
    ::= { cucsAdaptorMgmtVnicEthConfigEntry 2 }

cucsAdaptorMgmtVnicEthConfigRn OBJECT-TYPE
    SYNTAX       SnmpAdminString
    MAX-ACCESS   read-only
    STATUS       current
    DESCRIPTION
        "Cisco UCS adaptor:MgmtVnicEthConfig:rn managed object property"
    ::= { cucsAdaptorMgmtVnicEthConfigEntry 3 }

cucsAdaptorMgmtVnicEthConfigHostPortId OBJECT-TYPE
    SYNTAX       Gauge32
    MAX-ACCESS   read-only
    STATUS       current
    DESCRIPTION
        "Cisco UCS adaptor:MgmtVnicEthConfig:hostPortId
        managed object property"
    ::= { cucsAdaptorMgmtVnicEthConfigEntry 4 }

cucsAdaptorMgmtVnicEthConfigMacOffset OBJECT-TYPE
    SYNTAX       Gauge32
    MAX-ACCESS   read-only
    STATUS       current
    DESCRIPTION
        "Cisco UCS adaptor:MgmtVnicEthConfig:macOffset
        managed object property"
    ::= { cucsAdaptorMgmtVnicEthConfigEntry 5 }

cucsAdaptorMgmtVnicEthConfigPciSlot OBJECT-TYPE
    SYNTAX       Gauge32
    MAX-ACCESS   read-only
    STATUS       current
    DESCRIPTION
        "Cisco UCS adaptor:MgmtVnicEthConfig:pciSlot managed
        object property"
    ::= { cucsAdaptorMgmtVnicEthConfigEntry 6 }

cucsAdaptorNwMgmtCapTable OBJECT-TYPE
    SYNTAX           SEQUENCE OF CucsAdaptorNwMgmtCapEntry
    MAX-ACCESS       not-accessible
    STATUS           current
    DESCRIPTION
        "Cisco UCS adaptor:NwMgmtCap managed object table"
    ::= { cucsAdaptorObjects 81 }

cucsAdaptorNwMgmtCapEntry OBJECT-TYPE
    SYNTAX           CucsAdaptorNwMgmtCapEntry
    MAX-ACCESS       not-accessible
    STATUS           current
    DESCRIPTION
        "Entry for the cucsAdaptorNwMgmtCapTable table."
    INDEX { cucsAdaptorNwMgmtCapInstanceId }
    ::= { cucsAdaptorNwMgmtCapTable 1 }

CucsAdaptorNwMgmtCapEntry ::= SEQUENCE {
    cucsAdaptorNwMgmtCapInstanceId                                   CucsManagedObjectId,
    cucsAdaptorNwMgmtCapDn                                           CucsManagedObjectDn,
    cucsAdaptorNwMgmtCapRn                                           SnmpAdminString,
    cucsAdaptorNwMgmtCapApi                                          CucsAdaptorNwMgmtCapApi,
    cucsAdaptorNwMgmtCapMgmtTransport                                CucsAdaptorNwMgmtCapMgmtTransport,
    cucsAdaptorNwMgmtCapMode                                         CucsAdaptorMgmtCapMode,
    cucsAdaptorNwMgmtCapOperPowerRequirement                         CucsAdaptorMgmtCapOperPowerRequirement,
    cucsAdaptorNwMgmtCapRebootActionOnDestructive                    CucsAdaptorMgmtCapRebootActionOnDestructive
}

cucsAdaptorNwMgmtCapInstanceId OBJECT-TYPE
    SYNTAX       CucsManagedObjectId
    MAX-ACCESS   not-accessible
    STATUS       current
    DESCRIPTION
        "Instance identifier of the managed object."
    ::= { cucsAdaptorNwMgmtCapEntry 1 }

cucsAdaptorNwMgmtCapDn OBJECT-TYPE
    SYNTAX       CucsManagedObjectDn
    MAX-ACCESS   read-only
    STATUS       current
    DESCRIPTION
        "Cisco UCS adaptor:NwMgmtCap:dn managed object property"
    ::= { cucsAdaptorNwMgmtCapEntry 2 }

cucsAdaptorNwMgmtCapRn OBJECT-TYPE
    SYNTAX       SnmpAdminString
    MAX-ACCESS   read-only
    STATUS       current
    DESCRIPTION
        "Cisco UCS adaptor:NwMgmtCap:rn managed object property"
    ::= { cucsAdaptorNwMgmtCapEntry 3 }

cucsAdaptorNwMgmtCapApi OBJECT-TYPE
    SYNTAX       CucsAdaptorNwMgmtCapApi
    MAX-ACCESS   read-only
    STATUS       current
    DESCRIPTION
        "Cisco UCS adaptor:NwMgmtCap:api managed object property"
    ::= { cucsAdaptorNwMgmtCapEntry 4 }

cucsAdaptorNwMgmtCapMgmtTransport OBJECT-TYPE
    SYNTAX       CucsAdaptorNwMgmtCapMgmtTransport
    MAX-ACCESS   read-only
    STATUS       current
    DESCRIPTION
        "Cisco UCS adaptor:NwMgmtCap:mgmtTransport managed
        object property"
    ::= { cucsAdaptorNwMgmtCapEntry 5 }

cucsAdaptorNwMgmtCapMode OBJECT-TYPE
    SYNTAX       CucsAdaptorMgmtCapMode
    MAX-ACCESS   read-only
    STATUS       current
    DESCRIPTION
        "Cisco UCS adaptor:NwMgmtCap:mode managed object property"
    ::= { cucsAdaptorNwMgmtCapEntry 6 }

cucsAdaptorNwMgmtCapOperPowerRequirement OBJECT-TYPE
    SYNTAX       CucsAdaptorMgmtCapOperPowerRequirement
    MAX-ACCESS   read-only
    STATUS       current
    DESCRIPTION
        "Cisco UCS adaptor:NwMgmtCap:operPowerRequirement
        managed object property"
    ::= { cucsAdaptorNwMgmtCapEntry 7 }

cucsAdaptorNwMgmtCapRebootActionOnDestructive OBJECT-TYPE
    SYNTAX       CucsAdaptorMgmtCapRebootActionOnDestructive
    MAX-ACCESS   read-only
    STATUS       current
    DESCRIPTION
        "Cisco UCS adaptor:NwMgmtCap:rebootActionOnDestructive
        managed object property"
    ::= { cucsAdaptorNwMgmtCapEntry 8 }

cucsAdaptorNwStatsMgmtCapTable OBJECT-TYPE
    SYNTAX           SEQUENCE OF CucsAdaptorNwStatsMgmtCapEntry
    MAX-ACCESS       not-accessible
    STATUS           current
    DESCRIPTION
        "Cisco UCS adaptor:NwStatsMgmtCap managed object table"
    ::= { cucsAdaptorObjects 124 }

cucsAdaptorNwStatsMgmtCapEntry OBJECT-TYPE
    SYNTAX           CucsAdaptorNwStatsMgmtCapEntry
    MAX-ACCESS       not-accessible
    STATUS           current
    DESCRIPTION
        "Entry for the cucsAdaptorNwStatsMgmtCapTable table."
    INDEX { cucsAdaptorNwStatsMgmtCapInstanceId }
    ::= { cucsAdaptorNwStatsMgmtCapTable 1 }

CucsAdaptorNwStatsMgmtCapEntry ::= SEQUENCE {
    cucsAdaptorNwStatsMgmtCapInstanceId                              CucsManagedObjectId,
    cucsAdaptorNwStatsMgmtCapDn                                      CucsManagedObjectDn,
    cucsAdaptorNwStatsMgmtCapRn                                      SnmpAdminString,
    cucsAdaptorNwStatsMgmtCapEnableNwStatsCollection                 TruthValue,
    cucsAdaptorNwStatsMgmtCapMode                                    CucsAdaptorMgmtCapMode,
    cucsAdaptorNwStatsMgmtCapOperPowerRequirement                    CucsAdaptorMgmtCapOperPowerRequirement,
    cucsAdaptorNwStatsMgmtCapRebootActionOnDestructive               CucsAdaptorMgmtCapRebootActionOnDestructive
}

cucsAdaptorNwStatsMgmtCapInstanceId OBJECT-TYPE
    SYNTAX       CucsManagedObjectId
    MAX-ACCESS   not-accessible
    STATUS       current
    DESCRIPTION
        "Instance identifier of the managed object."
    ::= { cucsAdaptorNwStatsMgmtCapEntry 1 }

cucsAdaptorNwStatsMgmtCapDn OBJECT-TYPE
    SYNTAX       CucsManagedObjectDn
    MAX-ACCESS   read-only
    STATUS       current
    DESCRIPTION
        "Cisco UCS adaptor:NwStatsMgmtCap:dn managed object property"
    ::= { cucsAdaptorNwStatsMgmtCapEntry 2 }

cucsAdaptorNwStatsMgmtCapRn OBJECT-TYPE
    SYNTAX       SnmpAdminString
    MAX-ACCESS   read-only
    STATUS       current
    DESCRIPTION
        "Cisco UCS adaptor:NwStatsMgmtCap:rn managed object property"
    ::= { cucsAdaptorNwStatsMgmtCapEntry 3 }

cucsAdaptorNwStatsMgmtCapEnableNwStatsCollection OBJECT-TYPE
    SYNTAX       TruthValue
    MAX-ACCESS   read-only
    STATUS       current
    DESCRIPTION
        "Cisco UCS adaptor:NwStatsMgmtCap:enableNwStatsCollection
        managed object property"
    ::= { cucsAdaptorNwStatsMgmtCapEntry 4 }

cucsAdaptorNwStatsMgmtCapMode OBJECT-TYPE
    SYNTAX       CucsAdaptorMgmtCapMode
    MAX-ACCESS   read-only
    STATUS       current
    DESCRIPTION
        "Cisco UCS adaptor:NwStatsMgmtCap:mode managed object property"
    ::= { cucsAdaptorNwStatsMgmtCapEntry 5 }

cucsAdaptorNwStatsMgmtCapOperPowerRequirement OBJECT-TYPE
    SYNTAX       CucsAdaptorMgmtCapOperPowerRequirement
    MAX-ACCESS   read-only
    STATUS       current
    DESCRIPTION
        "Cisco UCS adaptor:NwStatsMgmtCap:operPowerRequirement
        managed object property"
    ::= { cucsAdaptorNwStatsMgmtCapEntry 6 }

cucsAdaptorNwStatsMgmtCapRebootActionOnDestructive OBJECT-TYPE
    SYNTAX       CucsAdaptorMgmtCapRebootActionOnDestructive
    MAX-ACCESS   read-only
    STATUS       current
    DESCRIPTION
        "Cisco UCS adaptor:NwStatsMgmtCap:rebootActionOnDestructive
        managed object property"
    ::= { cucsAdaptorNwStatsMgmtCapEntry 7 }

cucsAdaptorProtocolProfileTable OBJECT-TYPE
    SYNTAX           SEQUENCE OF CucsAdaptorProtocolProfileEntry
    MAX-ACCESS       not-accessible
    STATUS           current
    DESCRIPTION
        "Cisco UCS adaptor:ProtocolProfile managed object table"
    ::= { cucsAdaptorObjects 105 }

cucsAdaptorProtocolProfileEntry OBJECT-TYPE
    SYNTAX           CucsAdaptorProtocolProfileEntry
    MAX-ACCESS       not-accessible
    STATUS           current
    DESCRIPTION
        "Entry for the cucsAdaptorProtocolProfileTable table."
    INDEX { cucsAdaptorProtocolProfileInstanceId }
    ::= { cucsAdaptorProtocolProfileTable 1 }

CucsAdaptorProtocolProfileEntry ::= SEQUENCE {
    cucsAdaptorProtocolProfileInstanceId                             CucsManagedObjectId,
    cucsAdaptorProtocolProfileDn                                     CucsManagedObjectDn,
    cucsAdaptorProtocolProfileRn                                     SnmpAdminString,
    cucsAdaptorProtocolProfileConnectionTimeOut                      CucsAdaptorProtocolProfileConnectionTimeOut,
    cucsAdaptorProtocolProfileDhcpTimeOut                            Gauge32,
    cucsAdaptorProtocolProfileLunBusyRetryCount                      CucsAdaptorProtocolProfileLunBusyRetryCount,
    cucsAdaptorProtocolProfileTcpTimeStamp                           TruthValue,
    cucsAdaptorProtocolProfileBootToTarget                           TruthValue,
    cucsAdaptorProtocolProfileHbaMode                                TruthValue
}

cucsAdaptorProtocolProfileInstanceId OBJECT-TYPE
    SYNTAX       CucsManagedObjectId
    MAX-ACCESS   not-accessible
    STATUS       current
    DESCRIPTION
        "Instance identifier of the managed object."
    ::= { cucsAdaptorProtocolProfileEntry 1 }

cucsAdaptorProtocolProfileDn OBJECT-TYPE
    SYNTAX       CucsManagedObjectDn
    MAX-ACCESS   read-only
    STATUS       current
    DESCRIPTION
        "Cisco UCS adaptor:ProtocolProfile:dn managed object property"
    ::= { cucsAdaptorProtocolProfileEntry 2 }

cucsAdaptorProtocolProfileRn OBJECT-TYPE
    SYNTAX       SnmpAdminString
    MAX-ACCESS   read-only
    STATUS       current
    DESCRIPTION
        "Cisco UCS adaptor:ProtocolProfile:rn managed object property"
    ::= { cucsAdaptorProtocolProfileEntry 3 }

cucsAdaptorProtocolProfileConnectionTimeOut OBJECT-TYPE
    SYNTAX       CucsAdaptorProtocolProfileConnectionTimeOut
    MAX-ACCESS   read-only
    STATUS       current
    DESCRIPTION
        "Cisco UCS adaptor:ProtocolProfile:connectionTimeOut
        managed object property"
    ::= { cucsAdaptorProtocolProfileEntry 4 }

cucsAdaptorProtocolProfileDhcpTimeOut OBJECT-TYPE
    SYNTAX       Gauge32
    MAX-ACCESS   read-only
    STATUS       current
    DESCRIPTION
        "Cisco UCS adaptor:ProtocolProfile:dhcpTimeOut
        managed object property"
    ::= { cucsAdaptorProtocolProfileEntry 5 }

cucsAdaptorProtocolProfileLunBusyRetryCount OBJECT-TYPE
    SYNTAX       CucsAdaptorProtocolProfileLunBusyRetryCount
    MAX-ACCESS   read-only
    STATUS       current
    DESCRIPTION
        "Cisco UCS adaptor:ProtocolProfile:lunBusyRetryCount
        managed object property"
    ::= { cucsAdaptorProtocolProfileEntry 6 }

cucsAdaptorProtocolProfileTcpTimeStamp OBJECT-TYPE
    SYNTAX       TruthValue
    MAX-ACCESS   read-only
    STATUS       current
    DESCRIPTION
        "Cisco UCS adaptor:ProtocolProfile:tcpTimeStamp
        managed object property"
    ::= { cucsAdaptorProtocolProfileEntry 7 }

cucsAdaptorProtocolProfileBootToTarget OBJECT-TYPE
    SYNTAX       TruthValue
    MAX-ACCESS   read-only
    STATUS       current
    DESCRIPTION
        "Cisco UCS adaptor:ProtocolProfile:bootToTarget
        managed object property"
    ::= { cucsAdaptorProtocolProfileEntry 8 }

cucsAdaptorProtocolProfileHbaMode OBJECT-TYPE
    SYNTAX       TruthValue
    MAX-ACCESS   read-only
    STATUS       current
    DESCRIPTION
        "Cisco UCS adaptor:ProtocolProfile:hbaMode managed
        object property"
    ::= { cucsAdaptorProtocolProfileEntry 9 }

cucsAdaptorQualTable OBJECT-TYPE
    SYNTAX           SEQUENCE OF CucsAdaptorQualEntry
    MAX-ACCESS       not-accessible
    STATUS           current
    DESCRIPTION
        "Cisco UCS adaptor:Qual managed object table"
    ::= { cucsAdaptorObjects 82 }

cucsAdaptorQualEntry OBJECT-TYPE
    SYNTAX           CucsAdaptorQualEntry
    MAX-ACCESS       not-accessible
    STATUS           current
    DESCRIPTION
        "Entry for the cucsAdaptorQualTable table."
    INDEX { cucsAdaptorQualInstanceId }
    ::= { cucsAdaptorQualTable 1 }

CucsAdaptorQualEntry ::= SEQUENCE {
    cucsAdaptorQualInstanceId                                        CucsManagedObjectId,
    cucsAdaptorQualDn                                                CucsManagedObjectDn,
    cucsAdaptorQualRn                                                SnmpAdminString
}

cucsAdaptorQualInstanceId OBJECT-TYPE
    SYNTAX       CucsManagedObjectId
    MAX-ACCESS   not-accessible
    STATUS       current
    DESCRIPTION
        "Instance identifier of the managed object."
    ::= { cucsAdaptorQualEntry 1 }

cucsAdaptorQualDn OBJECT-TYPE
    SYNTAX       CucsManagedObjectDn
    MAX-ACCESS   read-only
    STATUS       current
    DESCRIPTION
        "Cisco UCS adaptor:Qual:dn managed object property"
    ::= { cucsAdaptorQualEntry 2 }

cucsAdaptorQualRn OBJECT-TYPE
    SYNTAX       SnmpAdminString
    MAX-ACCESS   read-only
    STATUS       current
    DESCRIPTION
        "Cisco UCS adaptor:Qual:rn managed object property"
    ::= { cucsAdaptorQualEntry 3 }

cucsAdaptorRnicCapSpecTable OBJECT-TYPE
    SYNTAX           SEQUENCE OF CucsAdaptorRnicCapSpecEntry
    MAX-ACCESS       not-accessible
    STATUS           current
    DESCRIPTION
        "Cisco UCS adaptor:RnicCapSpec managed object table"
    ::= { cucsAdaptorObjects 129 }

cucsAdaptorRnicCapSpecEntry OBJECT-TYPE
    SYNTAX           CucsAdaptorRnicCapSpecEntry
    MAX-ACCESS       not-accessible
    STATUS           current
    DESCRIPTION
        "Entry for the cucsAdaptorRnicCapSpecTable table."
    INDEX { cucsAdaptorRnicCapSpecInstanceId }
    ::= { cucsAdaptorRnicCapSpecTable 1 }

CucsAdaptorRnicCapSpecEntry ::= SEQUENCE {
    cucsAdaptorRnicCapSpecInstanceId                                 CucsManagedObjectId,
    cucsAdaptorRnicCapSpecDn                                         CucsManagedObjectDn,
    cucsAdaptorRnicCapSpecRn                                         SnmpAdminString,
    cucsAdaptorRnicCapSpecFwVersionHi                                SnmpAdminString,
    cucsAdaptorRnicCapSpecFwVersionLo                                SnmpAdminString,
    cucsAdaptorRnicCapSpecFwVersionOpr                               CucsAdaptorCapDefFwVersionOpr,
    cucsAdaptorRnicCapSpecMaximum                                    Gauge32,
    cucsAdaptorRnicCapSpecMaximumMR                                  Gauge32,
    cucsAdaptorRnicCapSpecMaximumQP                                  Gauge32,
    cucsAdaptorRnicCapSpecNfVersionLo                                SnmpAdminString,
    cucsAdaptorRnicCapSpecType                                       CucsAdaptorRnicCapSpecType
}

cucsAdaptorRnicCapSpecInstanceId OBJECT-TYPE
    SYNTAX       CucsManagedObjectId
    MAX-ACCESS   not-accessible
    STATUS       current
    DESCRIPTION
        "Instance identifier of the managed object."
    ::= { cucsAdaptorRnicCapSpecEntry 1 }

cucsAdaptorRnicCapSpecDn OBJECT-TYPE
    SYNTAX       CucsManagedObjectDn
    MAX-ACCESS   read-only
    STATUS       current
    DESCRIPTION
        "Cisco UCS adaptor:RnicCapSpec:dn managed object property"
    ::= { cucsAdaptorRnicCapSpecEntry 2 }

cucsAdaptorRnicCapSpecRn OBJECT-TYPE
    SYNTAX       SnmpAdminString
    MAX-ACCESS   read-only
    STATUS       current
    DESCRIPTION
        "Cisco UCS adaptor:RnicCapSpec:rn managed object property"
    ::= { cucsAdaptorRnicCapSpecEntry 3 }

cucsAdaptorRnicCapSpecFwVersionHi OBJECT-TYPE
    SYNTAX       SnmpAdminString
    MAX-ACCESS   read-only
    STATUS       current
    DESCRIPTION
        "Cisco UCS adaptor:RnicCapSpec:fwVersionHi managed
        object property"
    ::= { cucsAdaptorRnicCapSpecEntry 4 }

cucsAdaptorRnicCapSpecFwVersionLo OBJECT-TYPE
    SYNTAX       SnmpAdminString
    MAX-ACCESS   read-only
    STATUS       current
    DESCRIPTION
        "Cisco UCS adaptor:RnicCapSpec:fwVersionLo managed
        object property"
    ::= { cucsAdaptorRnicCapSpecEntry 5 }

cucsAdaptorRnicCapSpecFwVersionOpr OBJECT-TYPE
    SYNTAX       CucsAdaptorCapDefFwVersionOpr
    MAX-ACCESS   read-only
    STATUS       current
    DESCRIPTION
        "Cisco UCS adaptor:RnicCapSpec:fwVersionOpr managed
        object property"
    ::= { cucsAdaptorRnicCapSpecEntry 6 }

cucsAdaptorRnicCapSpecMaximum OBJECT-TYPE
    SYNTAX       Gauge32
    MAX-ACCESS   read-only
    STATUS       current
    DESCRIPTION
        "Cisco UCS adaptor:RnicCapSpec:maximum managed object property"
    ::= { cucsAdaptorRnicCapSpecEntry 7 }

cucsAdaptorRnicCapSpecMaximumMR OBJECT-TYPE
    SYNTAX       Gauge32
    MAX-ACCESS   read-only
    STATUS       current
    DESCRIPTION
        "Cisco UCS adaptor:RnicCapSpec:maximumMR managed object property"
    ::= { cucsAdaptorRnicCapSpecEntry 8 }

cucsAdaptorRnicCapSpecMaximumQP OBJECT-TYPE
    SYNTAX       Gauge32
    MAX-ACCESS   read-only
    STATUS       current
    DESCRIPTION
        "Cisco UCS adaptor:RnicCapSpec:maximumQP managed object property"
    ::= { cucsAdaptorRnicCapSpecEntry 9 }

cucsAdaptorRnicCapSpecNfVersionLo OBJECT-TYPE
    SYNTAX       SnmpAdminString
    MAX-ACCESS   read-only
    STATUS       current
    DESCRIPTION
        "Cisco UCS adaptor:RnicCapSpec:nfVersionLo managed
        object property"
    ::= { cucsAdaptorRnicCapSpecEntry 10 }

cucsAdaptorRnicCapSpecType OBJECT-TYPE
    SYNTAX       CucsAdaptorRnicCapSpecType
    MAX-ACCESS   read-only
    STATUS       current
    DESCRIPTION
        "Cisco UCS adaptor:RnicCapSpec:type managed object property"
    ::= { cucsAdaptorRnicCapSpecEntry 11 }

cucsAdaptorRssProfileTable OBJECT-TYPE
    SYNTAX           SEQUENCE OF CucsAdaptorRssProfileEntry
    MAX-ACCESS       not-accessible
    STATUS           current
    DESCRIPTION
        "Cisco UCS adaptor:RssProfile managed object table"
    ::= { cucsAdaptorObjects 83 }

cucsAdaptorRssProfileEntry OBJECT-TYPE
    SYNTAX           CucsAdaptorRssProfileEntry
    MAX-ACCESS       not-accessible
    STATUS           current
    DESCRIPTION
        "Entry for the cucsAdaptorRssProfileTable table."
    INDEX { cucsAdaptorRssProfileInstanceId }
    ::= { cucsAdaptorRssProfileTable 1 }

CucsAdaptorRssProfileEntry ::= SEQUENCE {
    cucsAdaptorRssProfileInstanceId                                  CucsManagedObjectId,
    cucsAdaptorRssProfileDn                                          CucsManagedObjectDn,
    cucsAdaptorRssProfileRn                                          SnmpAdminString,
    cucsAdaptorRssProfileReceiveSideScaling                          CucsAdaptorRssProfileReceiveSideScaling
}

cucsAdaptorRssProfileInstanceId OBJECT-TYPE
    SYNTAX       CucsManagedObjectId
    MAX-ACCESS   not-accessible
    STATUS       current
    DESCRIPTION
        "Instance identifier of the managed object."
    ::= { cucsAdaptorRssProfileEntry 1 }

cucsAdaptorRssProfileDn OBJECT-TYPE
    SYNTAX       CucsManagedObjectDn
    MAX-ACCESS   read-only
    STATUS       current
    DESCRIPTION
        "Cisco UCS adaptor:RssProfile:dn managed object property"
    ::= { cucsAdaptorRssProfileEntry 2 }

cucsAdaptorRssProfileRn OBJECT-TYPE
    SYNTAX       SnmpAdminString
    MAX-ACCESS   read-only
    STATUS       current
    DESCRIPTION
        "Cisco UCS adaptor:RssProfile:rn managed object property"
    ::= { cucsAdaptorRssProfileEntry 3 }

cucsAdaptorRssProfileReceiveSideScaling OBJECT-TYPE
    SYNTAX       CucsAdaptorRssProfileReceiveSideScaling
    MAX-ACCESS   read-only
    STATUS       current
    DESCRIPTION
        "Cisco UCS adaptor:RssProfile:receiveSideScaling
        managed object property"
    ::= { cucsAdaptorRssProfileEntry 4 }

cucsAdaptorSanCapTable OBJECT-TYPE
    SYNTAX           SEQUENCE OF CucsAdaptorSanCapEntry
    MAX-ACCESS       not-accessible
    STATUS           current
    DESCRIPTION
        "Cisco UCS adaptor:SanCap managed object table"
    ::= { cucsAdaptorObjects 84 }

cucsAdaptorSanCapEntry OBJECT-TYPE
    SYNTAX           CucsAdaptorSanCapEntry
    MAX-ACCESS       not-accessible
    STATUS           current
    DESCRIPTION
        "Entry for the cucsAdaptorSanCapTable table."
    INDEX { cucsAdaptorSanCapInstanceId }
    ::= { cucsAdaptorSanCapTable 1 }

CucsAdaptorSanCapEntry ::= SEQUENCE {
    cucsAdaptorSanCapInstanceId                                      CucsManagedObjectId,
    cucsAdaptorSanCapDn                                              CucsManagedObjectDn,
    cucsAdaptorSanCapRn                                              SnmpAdminString,
    cucsAdaptorSanCapHostNvram                                       CucsAdaptorSanCapHostNvram
}

cucsAdaptorSanCapInstanceId OBJECT-TYPE
    SYNTAX       CucsManagedObjectId
    MAX-ACCESS   not-accessible
    STATUS       current
    DESCRIPTION
        "Instance identifier of the managed object."
    ::= { cucsAdaptorSanCapEntry 1 }

cucsAdaptorSanCapDn OBJECT-TYPE
    SYNTAX       CucsManagedObjectDn
    MAX-ACCESS   read-only
    STATUS       current
    DESCRIPTION
        "Cisco UCS adaptor:SanCap:dn managed object property"
    ::= { cucsAdaptorSanCapEntry 2 }

cucsAdaptorSanCapRn OBJECT-TYPE
    SYNTAX       SnmpAdminString
    MAX-ACCESS   read-only
    STATUS       current
    DESCRIPTION
        "Cisco UCS adaptor:SanCap:rn managed object property"
    ::= { cucsAdaptorSanCapEntry 3 }

cucsAdaptorSanCapHostNvram OBJECT-TYPE
    SYNTAX       CucsAdaptorSanCapHostNvram
    MAX-ACCESS   read-only
    STATUS       current
    DESCRIPTION
        "Cisco UCS adaptor:SanCap:hostNvram managed object property"
    ::= { cucsAdaptorSanCapEntry 4 }

cucsAdaptorUnitTable OBJECT-TYPE
    SYNTAX           SEQUENCE OF CucsAdaptorUnitEntry
    MAX-ACCESS       not-accessible
    STATUS           current
    DESCRIPTION
        "Cisco UCS adaptor:Unit managed object table"
    ::= { cucsAdaptorObjects 85 }

cucsAdaptorUnitEntry OBJECT-TYPE
    SYNTAX           CucsAdaptorUnitEntry
    MAX-ACCESS       not-accessible
    STATUS           current
    DESCRIPTION
        "Entry for the cucsAdaptorUnitTable table."
    INDEX { cucsAdaptorUnitInstanceId }
    ::= { cucsAdaptorUnitTable 1 }

CucsAdaptorUnitEntry ::= SEQUENCE {
    cucsAdaptorUnitInstanceId                                        CucsManagedObjectId,
    cucsAdaptorUnitDn                                                CucsManagedObjectDn,
    cucsAdaptorUnitRn                                                SnmpAdminString,
    cucsAdaptorUnitBladeId                                           Gauge32,
    cucsAdaptorUnitChassisId                                         Gauge32,
    cucsAdaptorUnitConnPath                                          CucsEquipmentConnectionStatus,
    cucsAdaptorUnitConnStatus                                        CucsEquipmentConnectionStatus,
    cucsAdaptorUnitFltAggr                                           Unsigned64,
    cucsAdaptorUnitId                                                CucsAdaptorUnitId,
    cucsAdaptorUnitManagingInst                                      CucsNetworkSwitchId,
    cucsAdaptorUnitModel                                             SnmpAdminString,
    cucsAdaptorUnitOperState                                         CucsEquipmentOperability,
    cucsAdaptorUnitOperability                                       CucsEquipmentOperability,
    cucsAdaptorUnitPciAddr                                           SnmpAdminString,
    cucsAdaptorUnitPciSlot                                           SnmpAdminString,
    cucsAdaptorUnitPerf                                              CucsEquipmentSensorThresholdStatus,
    cucsAdaptorUnitPower                                             CucsEquipmentPowerState,
    cucsAdaptorUnitPresence                                          CucsEquipmentPresence,
    cucsAdaptorUnitReachability                                      CucsAdaptorReachability,
    cucsAdaptorUnitRevision                                          SnmpAdminString,
    cucsAdaptorUnitSerial                                            SnmpAdminString,
    cucsAdaptorUnitThermal                                           CucsEquipmentSensorThresholdStatus,
    cucsAdaptorUnitVendor                                            SnmpAdminString,
    cucsAdaptorUnitVoltage                                           CucsEquipmentSensorThresholdStatus,
    cucsAdaptorUnitIntegrated                                        TruthValue,
    cucsAdaptorUnitPartNumber                                        SnmpAdminString,
    cucsAdaptorUnitBaseMac                                           MacAddress,
    cucsAdaptorUnitMfgTime                                           DateAndTime,
    cucsAdaptorUnitAdminPowerState                                   CucsAdaptorAdminPowerState,
    cucsAdaptorUnitOperQualifierReason                               SnmpAdminString,
    cucsAdaptorUnitLocationDn                                        SnmpAdminString,
    cucsAdaptorUnitCartridgeId                                       Gauge32,
    cucsAdaptorUnitDiscoveryStatus                                   CucsEquipmentConnectionStatus,
    cucsAdaptorUnitVid                                               SnmpAdminString,
    cucsAdaptorUnitAssetTag                                          SnmpAdminString,
    cucsAdaptorUnitVisibility                                        CucsAdaptorUnitVisibility
}

cucsAdaptorUnitInstanceId OBJECT-TYPE
    SYNTAX       CucsManagedObjectId
    MAX-ACCESS   not-accessible
    STATUS       current
    DESCRIPTION
        "Instance identifier of the managed object."
    ::= { cucsAdaptorUnitEntry 1 }

cucsAdaptorUnitDn OBJECT-TYPE
    SYNTAX       CucsManagedObjectDn
    MAX-ACCESS   read-only
    STATUS       current
    DESCRIPTION
        "Cisco UCS adaptor:Unit:dn managed object property"
    ::= { cucsAdaptorUnitEntry 2 }

cucsAdaptorUnitRn OBJECT-TYPE
    SYNTAX       SnmpAdminString
    MAX-ACCESS   read-only
    STATUS       current
    DESCRIPTION
        "Cisco UCS adaptor:Unit:rn managed object property"
    ::= { cucsAdaptorUnitEntry 3 }

cucsAdaptorUnitBladeId OBJECT-TYPE
    SYNTAX       Gauge32
    MAX-ACCESS   read-only
    STATUS       current
    DESCRIPTION
        "Cisco UCS adaptor:Unit:bladeId managed object property"
    ::= { cucsAdaptorUnitEntry 4 }

cucsAdaptorUnitChassisId OBJECT-TYPE
    SYNTAX       Gauge32
    MAX-ACCESS   read-only
    STATUS       current
    DESCRIPTION
        "Cisco UCS adaptor:Unit:chassisId managed object property"
    ::= { cucsAdaptorUnitEntry 5 }

cucsAdaptorUnitConnPath OBJECT-TYPE
    SYNTAX       CucsEquipmentConnectionStatus
    MAX-ACCESS   read-only
    STATUS       current
    DESCRIPTION
        "Cisco UCS adaptor:Unit:connPath managed object property"
    ::= { cucsAdaptorUnitEntry 6 }

cucsAdaptorUnitConnStatus OBJECT-TYPE
    SYNTAX       CucsEquipmentConnectionStatus
    MAX-ACCESS   read-only
    STATUS       current
    DESCRIPTION
        "Cisco UCS adaptor:Unit:connStatus managed object property"
    ::= { cucsAdaptorUnitEntry 7 }

cucsAdaptorUnitFltAggr OBJECT-TYPE
    SYNTAX       Unsigned64
    MAX-ACCESS   read-only
    STATUS       current
    DESCRIPTION
        "Cisco UCS adaptor:Unit:fltAggr managed object property"
    ::= { cucsAdaptorUnitEntry 8 }

cucsAdaptorUnitId OBJECT-TYPE
    SYNTAX       CucsAdaptorUnitId
    MAX-ACCESS   read-only
    STATUS       current
    DESCRIPTION
        "Cisco UCS adaptor:Unit:id managed object property"
    ::= { cucsAdaptorUnitEntry 9 }

cucsAdaptorUnitManagingInst OBJECT-TYPE
    SYNTAX       CucsNetworkSwitchId
    MAX-ACCESS   read-only
    STATUS       current
    DESCRIPTION
        "Cisco UCS adaptor:Unit:managingInst managed object property"
    ::= { cucsAdaptorUnitEntry 10 }

cucsAdaptorUnitModel OBJECT-TYPE
    SYNTAX       SnmpAdminString
    MAX-ACCESS   read-only
    STATUS       current
    DESCRIPTION
        "Cisco UCS adaptor:Unit:model managed object property"
    ::= { cucsAdaptorUnitEntry 11 }

cucsAdaptorUnitOperState OBJECT-TYPE
    SYNTAX       CucsEquipmentOperability
    MAX-ACCESS   read-only
    STATUS       current
    DESCRIPTION
        "Cisco UCS adaptor:Unit:operState managed object property"
    ::= { cucsAdaptorUnitEntry 12 }

cucsAdaptorUnitOperability OBJECT-TYPE
    SYNTAX       CucsEquipmentOperability
    MAX-ACCESS   read-only
    STATUS       current
    DESCRIPTION
        "Cisco UCS adaptor:Unit:operability managed object property"
    ::= { cucsAdaptorUnitEntry 13 }

cucsAdaptorUnitPciAddr OBJECT-TYPE
    SYNTAX       SnmpAdminString
    MAX-ACCESS   read-only
    STATUS       current
    DESCRIPTION
        "Cisco UCS adaptor:Unit:pciAddr managed object property"
    ::= { cucsAdaptorUnitEntry 14 }

cucsAdaptorUnitPciSlot OBJECT-TYPE
    SYNTAX       SnmpAdminString
    MAX-ACCESS   read-only
    STATUS       current
    DESCRIPTION
        "Cisco UCS adaptor:Unit:pciSlot managed object property"
    ::= { cucsAdaptorUnitEntry 15 }

cucsAdaptorUnitPerf OBJECT-TYPE
    SYNTAX       CucsEquipmentSensorThresholdStatus
    MAX-ACCESS   read-only
    STATUS       current
    DESCRIPTION
        "Cisco UCS adaptor:Unit:perf managed object property"
    ::= { cucsAdaptorUnitEntry 16 }

cucsAdaptorUnitPower OBJECT-TYPE
    SYNTAX       CucsEquipmentPowerState
    MAX-ACCESS   read-only
    STATUS       current
    DESCRIPTION
        "Cisco UCS adaptor:Unit:power managed object property"
    ::= { cucsAdaptorUnitEntry 17 }

cucsAdaptorUnitPresence OBJECT-TYPE
    SYNTAX       CucsEquipmentPresence
    MAX-ACCESS   read-only
    STATUS       current
    DESCRIPTION
        "Cisco UCS adaptor:Unit:presence managed object property"
    ::= { cucsAdaptorUnitEntry 18 }

cucsAdaptorUnitReachability OBJECT-TYPE
    SYNTAX       CucsAdaptorReachability
    MAX-ACCESS   read-only
    STATUS       current
    DESCRIPTION
        "Cisco UCS adaptor:Unit:reachability managed object property"
    ::= { cucsAdaptorUnitEntry 19 }

cucsAdaptorUnitRevision OBJECT-TYPE
    SYNTAX       SnmpAdminString
    MAX-ACCESS   read-only
    STATUS       current
    DESCRIPTION
        "Cisco UCS adaptor:Unit:revision managed object property"
    ::= { cucsAdaptorUnitEntry 20 }

cucsAdaptorUnitSerial OBJECT-TYPE
    SYNTAX       SnmpAdminString
    MAX-ACCESS   read-only
    STATUS       current
    DESCRIPTION
        "Cisco UCS adaptor:Unit:serial managed object property"
    ::= { cucsAdaptorUnitEntry 21 }

cucsAdaptorUnitThermal OBJECT-TYPE
    SYNTAX       CucsEquipmentSensorThresholdStatus
    MAX-ACCESS   read-only
    STATUS       current
    DESCRIPTION
        "Cisco UCS adaptor:Unit:thermal managed object property"
    ::= { cucsAdaptorUnitEntry 22 }

cucsAdaptorUnitVendor OBJECT-TYPE
    SYNTAX       SnmpAdminString
    MAX-ACCESS   read-only
    STATUS       current
    DESCRIPTION
        "Cisco UCS adaptor:Unit:vendor managed object property"
    ::= { cucsAdaptorUnitEntry 23 }

cucsAdaptorUnitVoltage OBJECT-TYPE
    SYNTAX       CucsEquipmentSensorThresholdStatus
    MAX-ACCESS   read-only
    STATUS       current
    DESCRIPTION
        "Cisco UCS adaptor:Unit:voltage managed object property"
    ::= { cucsAdaptorUnitEntry 24 }

cucsAdaptorUnitIntegrated OBJECT-TYPE
    SYNTAX       TruthValue
    MAX-ACCESS   read-only
    STATUS       current
    DESCRIPTION
        "Cisco UCS adaptor:Unit:integrated managed object property"
    ::= { cucsAdaptorUnitEntry 25 }

cucsAdaptorUnitPartNumber OBJECT-TYPE
    SYNTAX       SnmpAdminString
    MAX-ACCESS   read-only
    STATUS       current
    DESCRIPTION
        "Cisco UCS adaptor:Unit:partNumber managed object property"
    ::= { cucsAdaptorUnitEntry 26 }

cucsAdaptorUnitBaseMac OBJECT-TYPE
    SYNTAX       MacAddress
    MAX-ACCESS   read-only
    STATUS       current
    DESCRIPTION
        "Cisco UCS adaptor:Unit:baseMac managed object property"
    ::= { cucsAdaptorUnitEntry 27 }

cucsAdaptorUnitMfgTime OBJECT-TYPE
    SYNTAX       DateAndTime
    MAX-ACCESS   read-only
    STATUS       current
    DESCRIPTION
        "Cisco UCS adaptor:Unit:mfgTime managed object property"
    ::= { cucsAdaptorUnitEntry 28 }

cucsAdaptorUnitAdminPowerState OBJECT-TYPE
    SYNTAX       CucsAdaptorAdminPowerState
    MAX-ACCESS   read-only
    STATUS       current
    DESCRIPTION
        "Cisco UCS adaptor:Unit:adminPowerState managed object property"
    ::= { cucsAdaptorUnitEntry 29 }

cucsAdaptorUnitOperQualifierReason OBJECT-TYPE
    SYNTAX       SnmpAdminString
    MAX-ACCESS   read-only
    STATUS       current
    DESCRIPTION
        "Cisco UCS adaptor:Unit:operQualifierReason managed
        object property"
    ::= { cucsAdaptorUnitEntry 30 }

cucsAdaptorUnitLocationDn OBJECT-TYPE
    SYNTAX       SnmpAdminString
    MAX-ACCESS   read-only
    STATUS       current
    DESCRIPTION
        "Cisco UCS adaptor:Unit:locationDn managed object property"
    ::= { cucsAdaptorUnitEntry 31 }

cucsAdaptorUnitCartridgeId OBJECT-TYPE
    SYNTAX       Gauge32
    MAX-ACCESS   read-only
    STATUS       current
    DESCRIPTION
        "Cisco UCS adaptor:Unit:cartridgeId managed object property"
    ::= { cucsAdaptorUnitEntry 32 }

cucsAdaptorUnitDiscoveryStatus OBJECT-TYPE
    SYNTAX       CucsEquipmentConnectionStatus
    MAX-ACCESS   read-only
    STATUS       current
    DESCRIPTION
        "Cisco UCS adaptor:Unit:discoveryStatus managed object property"
    ::= { cucsAdaptorUnitEntry 33 }

cucsAdaptorUnitVid OBJECT-TYPE
    SYNTAX       SnmpAdminString
    MAX-ACCESS   read-only
    STATUS       current
    DESCRIPTION
        "Cisco UCS adaptor:Unit:vid managed object property"
    ::= { cucsAdaptorUnitEntry 34 }

cucsAdaptorUnitAssetTag OBJECT-TYPE
    SYNTAX       SnmpAdminString
    MAX-ACCESS   read-only
    STATUS       current
    DESCRIPTION
        "Cisco UCS adaptor:Unit:assetTag managed object property"
    ::= { cucsAdaptorUnitEntry 35 }

cucsAdaptorUnitVisibility OBJECT-TYPE
    SYNTAX       CucsAdaptorUnitVisibility
    MAX-ACCESS   read-only
    STATUS       current
    DESCRIPTION
        "Cisco UCS adaptor:Unit:visibility managed object property"
    ::= { cucsAdaptorUnitEntry 36 }

cucsAdaptorUnitAssocCtxTable OBJECT-TYPE
    SYNTAX           SEQUENCE OF CucsAdaptorUnitAssocCtxEntry
    MAX-ACCESS       not-accessible
    STATUS           current
    DESCRIPTION
        "Cisco UCS adaptor:UnitAssocCtx managed object table"
    ::= { cucsAdaptorObjects 90 }

cucsAdaptorUnitAssocCtxEntry OBJECT-TYPE
    SYNTAX           CucsAdaptorUnitAssocCtxEntry
    MAX-ACCESS       not-accessible
    STATUS           current
    DESCRIPTION
        "Entry for the cucsAdaptorUnitAssocCtxTable table."
    INDEX { cucsAdaptorUnitAssocCtxInstanceId }
    ::= { cucsAdaptorUnitAssocCtxTable 1 }

CucsAdaptorUnitAssocCtxEntry ::= SEQUENCE {
    cucsAdaptorUnitAssocCtxInstanceId                                CucsManagedObjectId,
    cucsAdaptorUnitAssocCtxDn                                        CucsManagedObjectDn,
    cucsAdaptorUnitAssocCtxRn                                        SnmpAdminString,
    cucsAdaptorUnitAssocCtxFruCapDn                                  SnmpAdminString,
    cucsAdaptorUnitAssocCtxId                                        Gauge32,
    cucsAdaptorUnitAssocCtxPciAddr                                   SnmpAdminString
}

cucsAdaptorUnitAssocCtxInstanceId OBJECT-TYPE
    SYNTAX       CucsManagedObjectId
    MAX-ACCESS   not-accessible
    STATUS       current
    DESCRIPTION
        "Instance identifier of the managed object."
    ::= { cucsAdaptorUnitAssocCtxEntry 1 }

cucsAdaptorUnitAssocCtxDn OBJECT-TYPE
    SYNTAX       CucsManagedObjectDn
    MAX-ACCESS   read-only
    STATUS       current
    DESCRIPTION
        "Cisco UCS adaptor:UnitAssocCtx:dn managed object property"
    ::= { cucsAdaptorUnitAssocCtxEntry 2 }

cucsAdaptorUnitAssocCtxRn OBJECT-TYPE
    SYNTAX       SnmpAdminString
    MAX-ACCESS   read-only
    STATUS       current
    DESCRIPTION
        "Cisco UCS adaptor:UnitAssocCtx:rn managed object property"
    ::= { cucsAdaptorUnitAssocCtxEntry 3 }

cucsAdaptorUnitAssocCtxFruCapDn OBJECT-TYPE
    SYNTAX       SnmpAdminString
    MAX-ACCESS   read-only
    STATUS       current
    DESCRIPTION
        "Cisco UCS adaptor:UnitAssocCtx:fruCapDn managed object property"
    ::= { cucsAdaptorUnitAssocCtxEntry 4 }

cucsAdaptorUnitAssocCtxId OBJECT-TYPE
    SYNTAX       Gauge32
    MAX-ACCESS   read-only
    STATUS       current
    DESCRIPTION
        "Cisco UCS adaptor:UnitAssocCtx:id managed object property"
    ::= { cucsAdaptorUnitAssocCtxEntry 5 }

cucsAdaptorUnitAssocCtxPciAddr OBJECT-TYPE
    SYNTAX       SnmpAdminString
    MAX-ACCESS   read-only
    STATUS       current
    DESCRIPTION
        "Cisco UCS adaptor:UnitAssocCtx:pciAddr managed object property"
    ::= { cucsAdaptorUnitAssocCtxEntry 6 }

cucsAdaptorUnitExtnTable OBJECT-TYPE
    SYNTAX           SEQUENCE OF CucsAdaptorUnitExtnEntry
    MAX-ACCESS       not-accessible
    STATUS           current
    DESCRIPTION
        "Cisco UCS adaptor:UnitExtn managed object table"
    ::= { cucsAdaptorObjects 107 }

cucsAdaptorUnitExtnEntry OBJECT-TYPE
    SYNTAX           CucsAdaptorUnitExtnEntry
    MAX-ACCESS       not-accessible
    STATUS           current
    DESCRIPTION
        "Entry for the cucsAdaptorUnitExtnTable table."
    INDEX { cucsAdaptorUnitExtnInstanceId }
    ::= { cucsAdaptorUnitExtnTable 1 }

CucsAdaptorUnitExtnEntry ::= SEQUENCE {
    cucsAdaptorUnitExtnInstanceId                                    CucsManagedObjectId,
    cucsAdaptorUnitExtnDn                                            CucsManagedObjectDn,
    cucsAdaptorUnitExtnRn                                            SnmpAdminString,
    cucsAdaptorUnitExtnAdaptorId                                     Gauge32,
    cucsAdaptorUnitExtnBladeId                                       Gauge32,
    cucsAdaptorUnitExtnChassisId                                     Gauge32,
    cucsAdaptorUnitExtnFltAggr                                       Unsigned64,
    cucsAdaptorUnitExtnId                                            CucsAdaptorUnitExtnId,
    cucsAdaptorUnitExtnModel                                         SnmpAdminString,
    cucsAdaptorUnitExtnOperState                                     CucsEquipmentOperability,
    cucsAdaptorUnitExtnOperability                                   CucsEquipmentOperability,
    cucsAdaptorUnitExtnPartNumber                                    SnmpAdminString,
    cucsAdaptorUnitExtnPerf                                          CucsEquipmentSensorThresholdStatus,
    cucsAdaptorUnitExtnPower                                         CucsEquipmentPowerState,
    cucsAdaptorUnitExtnPresence                                      CucsEquipmentPresence,
    cucsAdaptorUnitExtnRevision                                      SnmpAdminString,
    cucsAdaptorUnitExtnSerial                                        SnmpAdminString,
    cucsAdaptorUnitExtnThermal                                       CucsEquipmentSensorThresholdStatus,
    cucsAdaptorUnitExtnVendor                                        SnmpAdminString,
    cucsAdaptorUnitExtnVoltage                                       CucsEquipmentSensorThresholdStatus,
    cucsAdaptorUnitExtnOperQualifierReason                           SnmpAdminString,
    cucsAdaptorUnitExtnLocationDn                                    SnmpAdminString,
    cucsAdaptorUnitExtnVid                                           SnmpAdminString,
    cucsAdaptorUnitExtnAssetTag                                      SnmpAdminString
}

cucsAdaptorUnitExtnInstanceId OBJECT-TYPE
    SYNTAX       CucsManagedObjectId
    MAX-ACCESS   not-accessible
    STATUS       current
    DESCRIPTION
        "Instance identifier of the managed object."
    ::= { cucsAdaptorUnitExtnEntry 1 }

cucsAdaptorUnitExtnDn OBJECT-TYPE
    SYNTAX       CucsManagedObjectDn
    MAX-ACCESS   read-only
    STATUS       current
    DESCRIPTION
        "Cisco UCS adaptor:UnitExtn:dn managed object property"
    ::= { cucsAdaptorUnitExtnEntry 2 }

cucsAdaptorUnitExtnRn OBJECT-TYPE
    SYNTAX       SnmpAdminString
    MAX-ACCESS   read-only
    STATUS       current
    DESCRIPTION
        "Cisco UCS adaptor:UnitExtn:rn managed object property"
    ::= { cucsAdaptorUnitExtnEntry 3 }

cucsAdaptorUnitExtnAdaptorId OBJECT-TYPE
    SYNTAX       Gauge32
    MAX-ACCESS   read-only
    STATUS       current
    DESCRIPTION
        "Cisco UCS adaptor:UnitExtn:adaptorId managed object property"
    ::= { cucsAdaptorUnitExtnEntry 4 }

cucsAdaptorUnitExtnBladeId OBJECT-TYPE
    SYNTAX       Gauge32
    MAX-ACCESS   read-only
    STATUS       current
    DESCRIPTION
        "Cisco UCS adaptor:UnitExtn:bladeId managed object property"
    ::= { cucsAdaptorUnitExtnEntry 5 }

cucsAdaptorUnitExtnChassisId OBJECT-TYPE
    SYNTAX       Gauge32
    MAX-ACCESS   read-only
    STATUS       current
    DESCRIPTION
        "Cisco UCS adaptor:UnitExtn:chassisId managed object property"
    ::= { cucsAdaptorUnitExtnEntry 6 }

cucsAdaptorUnitExtnFltAggr OBJECT-TYPE
    SYNTAX       Unsigned64
    MAX-ACCESS   read-only
    STATUS       current
    DESCRIPTION
        "Cisco UCS adaptor:UnitExtn:fltAggr managed object property"
    ::= { cucsAdaptorUnitExtnEntry 7 }

cucsAdaptorUnitExtnId OBJECT-TYPE
    SYNTAX       CucsAdaptorUnitExtnId
    MAX-ACCESS   read-only
    STATUS       current
    DESCRIPTION
        "Cisco UCS adaptor:UnitExtn:id managed object property"
    ::= { cucsAdaptorUnitExtnEntry 8 }

cucsAdaptorUnitExtnModel OBJECT-TYPE
    SYNTAX       SnmpAdminString
    MAX-ACCESS   read-only
    STATUS       current
    DESCRIPTION
        "Cisco UCS adaptor:UnitExtn:model managed object property"
    ::= { cucsAdaptorUnitExtnEntry 9 }

cucsAdaptorUnitExtnOperState OBJECT-TYPE
    SYNTAX       CucsEquipmentOperability
    MAX-ACCESS   read-only
    STATUS       current
    DESCRIPTION
        "Cisco UCS adaptor:UnitExtn:operState managed object property"
    ::= { cucsAdaptorUnitExtnEntry 10 }

cucsAdaptorUnitExtnOperability OBJECT-TYPE
    SYNTAX       CucsEquipmentOperability
    MAX-ACCESS   read-only
    STATUS       current
    DESCRIPTION
        "Cisco UCS adaptor:UnitExtn:operability managed object property"
    ::= { cucsAdaptorUnitExtnEntry 11 }

cucsAdaptorUnitExtnPartNumber OBJECT-TYPE
    SYNTAX       SnmpAdminString
    MAX-ACCESS   read-only
    STATUS       current
    DESCRIPTION
        "Cisco UCS adaptor:UnitExtn:partNumber managed object property"
    ::= { cucsAdaptorUnitExtnEntry 12 }

cucsAdaptorUnitExtnPerf OBJECT-TYPE
    SYNTAX       CucsEquipmentSensorThresholdStatus
    MAX-ACCESS   read-only
    STATUS       current
    DESCRIPTION
        "Cisco UCS adaptor:UnitExtn:perf managed object property"
    ::= { cucsAdaptorUnitExtnEntry 13 }

cucsAdaptorUnitExtnPower OBJECT-TYPE
    SYNTAX       CucsEquipmentPowerState
    MAX-ACCESS   read-only
    STATUS       current
    DESCRIPTION
        "Cisco UCS adaptor:UnitExtn:power managed object property"
    ::= { cucsAdaptorUnitExtnEntry 14 }

cucsAdaptorUnitExtnPresence OBJECT-TYPE
    SYNTAX       CucsEquipmentPresence
    MAX-ACCESS   read-only
    STATUS       current
    DESCRIPTION
        "Cisco UCS adaptor:UnitExtn:presence managed object property"
    ::= { cucsAdaptorUnitExtnEntry 15 }

cucsAdaptorUnitExtnRevision OBJECT-TYPE
    SYNTAX       SnmpAdminString
    MAX-ACCESS   read-only
    STATUS       current
    DESCRIPTION
        "Cisco UCS adaptor:UnitExtn:revision managed object property"
    ::= { cucsAdaptorUnitExtnEntry 16 }

cucsAdaptorUnitExtnSerial OBJECT-TYPE
    SYNTAX       SnmpAdminString
    MAX-ACCESS   read-only
    STATUS       current
    DESCRIPTION
        "Cisco UCS adaptor:UnitExtn:serial managed object property"
    ::= { cucsAdaptorUnitExtnEntry 17 }

cucsAdaptorUnitExtnThermal OBJECT-TYPE
    SYNTAX       CucsEquipmentSensorThresholdStatus
    MAX-ACCESS   read-only
    STATUS       current
    DESCRIPTION
        "Cisco UCS adaptor:UnitExtn:thermal managed object property"
    ::= { cucsAdaptorUnitExtnEntry 18 }

cucsAdaptorUnitExtnVendor OBJECT-TYPE
    SYNTAX       SnmpAdminString
    MAX-ACCESS   read-only
    STATUS       current
    DESCRIPTION
        "Cisco UCS adaptor:UnitExtn:vendor managed object property"
    ::= { cucsAdaptorUnitExtnEntry 19 }

cucsAdaptorUnitExtnVoltage OBJECT-TYPE
    SYNTAX       CucsEquipmentSensorThresholdStatus
    MAX-ACCESS   read-only
    STATUS       current
    DESCRIPTION
        "Cisco UCS adaptor:UnitExtn:voltage managed object property"
    ::= { cucsAdaptorUnitExtnEntry 20 }

cucsAdaptorUnitExtnOperQualifierReason OBJECT-TYPE
    SYNTAX       SnmpAdminString
    MAX-ACCESS   read-only
    STATUS       current
    DESCRIPTION
        "Cisco UCS adaptor:UnitExtn:operQualifierReason
        managed object property"
    ::= { cucsAdaptorUnitExtnEntry 21 }

cucsAdaptorUnitExtnLocationDn OBJECT-TYPE
    SYNTAX       SnmpAdminString
    MAX-ACCESS   read-only
    STATUS       current
    DESCRIPTION
        "Cisco UCS adaptor:UnitExtn:locationDn managed object property"
    ::= { cucsAdaptorUnitExtnEntry 22 }

cucsAdaptorUnitExtnVid OBJECT-TYPE
    SYNTAX       SnmpAdminString
    MAX-ACCESS   read-only
    STATUS       current
    DESCRIPTION
        "Cisco UCS adaptor:UnitExtn:vid managed object property"
    ::= { cucsAdaptorUnitExtnEntry 23 }

cucsAdaptorUnitExtnAssetTag OBJECT-TYPE
    SYNTAX       SnmpAdminString
    MAX-ACCESS   read-only
    STATUS       current
    DESCRIPTION
        "Cisco UCS adaptor:UnitExtn:assetTag managed object property"
    ::= { cucsAdaptorUnitExtnEntry 24 }

cucsAdaptorUplinkHwAddrCapTable OBJECT-TYPE
    SYNTAX           SEQUENCE OF CucsAdaptorUplinkHwAddrCapEntry
    MAX-ACCESS       not-accessible
    STATUS           current
    DESCRIPTION
        "Cisco UCS adaptor:UplinkHwAddrCap managed object table"
    ::= { cucsAdaptorObjects 93 }

cucsAdaptorUplinkHwAddrCapEntry OBJECT-TYPE
    SYNTAX           CucsAdaptorUplinkHwAddrCapEntry
    MAX-ACCESS       not-accessible
    STATUS           current
    DESCRIPTION
        "Entry for the cucsAdaptorUplinkHwAddrCapTable table."
    INDEX { cucsAdaptorUplinkHwAddrCapInstanceId }
    ::= { cucsAdaptorUplinkHwAddrCapTable 1 }

CucsAdaptorUplinkHwAddrCapEntry ::= SEQUENCE {
    cucsAdaptorUplinkHwAddrCapInstanceId                             CucsManagedObjectId,
    cucsAdaptorUplinkHwAddrCapDn                                     CucsManagedObjectDn,
    cucsAdaptorUplinkHwAddrCapRn                                     SnmpAdminString,
    cucsAdaptorUplinkHwAddrCapMacOffset1                             Gauge32,
    cucsAdaptorUplinkHwAddrCapMacOffset2                             Gauge32,
    cucsAdaptorUplinkHwAddrCapMacOffsetSub00                         Gauge32,
    cucsAdaptorUplinkHwAddrCapMacOffsetSub01                         Gauge32,
    cucsAdaptorUplinkHwAddrCapMacOffsetSub02                         Gauge32,
    cucsAdaptorUplinkHwAddrCapMacOffsetSub03                         Gauge32,
    cucsAdaptorUplinkHwAddrCapMacOffsetSub10                         Gauge32,
    cucsAdaptorUplinkHwAddrCapMacOffsetSub11                         Gauge32,
    cucsAdaptorUplinkHwAddrCapMacOffsetSub12                         Gauge32,
    cucsAdaptorUplinkHwAddrCapMacOffsetSub13                         Gauge32,
    cucsAdaptorUplinkHwAddrCapLldpMacOffset1                         Gauge32,
    cucsAdaptorUplinkHwAddrCapLldpMacOffset2                         Gauge32
}

cucsAdaptorUplinkHwAddrCapInstanceId OBJECT-TYPE
    SYNTAX       CucsManagedObjectId
    MAX-ACCESS   not-accessible
    STATUS       current
    DESCRIPTION
        "Instance identifier of the managed object."
    ::= { cucsAdaptorUplinkHwAddrCapEntry 1 }

cucsAdaptorUplinkHwAddrCapDn OBJECT-TYPE
    SYNTAX       CucsManagedObjectDn
    MAX-ACCESS   read-only
    STATUS       current
    DESCRIPTION
        "Cisco UCS adaptor:UplinkHwAddrCap:dn managed object property"
    ::= { cucsAdaptorUplinkHwAddrCapEntry 2 }

cucsAdaptorUplinkHwAddrCapRn OBJECT-TYPE
    SYNTAX       SnmpAdminString
    MAX-ACCESS   read-only
    STATUS       current
    DESCRIPTION
        "Cisco UCS adaptor:UplinkHwAddrCap:rn managed object property"
    ::= { cucsAdaptorUplinkHwAddrCapEntry 3 }

cucsAdaptorUplinkHwAddrCapMacOffset1 OBJECT-TYPE
    SYNTAX       Gauge32
    MAX-ACCESS   read-only
    STATUS       current
    DESCRIPTION
        "Cisco UCS adaptor:UplinkHwAddrCap:macOffset1 managed
        object property"
    ::= { cucsAdaptorUplinkHwAddrCapEntry 4 }

cucsAdaptorUplinkHwAddrCapMacOffset2 OBJECT-TYPE
    SYNTAX       Gauge32
    MAX-ACCESS   read-only
    STATUS       current
    DESCRIPTION
        "Cisco UCS adaptor:UplinkHwAddrCap:macOffset2 managed
        object property"
    ::= { cucsAdaptorUplinkHwAddrCapEntry 5 }

cucsAdaptorUplinkHwAddrCapMacOffsetSub00 OBJECT-TYPE
    SYNTAX       Gauge32
    MAX-ACCESS   read-only
    STATUS       current
    DESCRIPTION
        "Cisco UCS adaptor:UplinkHwAddrCap:macOffsetSub00
        managed object property"
    ::= { cucsAdaptorUplinkHwAddrCapEntry 6 }

cucsAdaptorUplinkHwAddrCapMacOffsetSub01 OBJECT-TYPE
    SYNTAX       Gauge32
    MAX-ACCESS   read-only
    STATUS       current
    DESCRIPTION
        "Cisco UCS adaptor:UplinkHwAddrCap:macOffsetSub01
        managed object property"
    ::= { cucsAdaptorUplinkHwAddrCapEntry 7 }

cucsAdaptorUplinkHwAddrCapMacOffsetSub02 OBJECT-TYPE
    SYNTAX       Gauge32
    MAX-ACCESS   read-only
    STATUS       current
    DESCRIPTION
        "Cisco UCS adaptor:UplinkHwAddrCap:macOffsetSub02
        managed object property"
    ::= { cucsAdaptorUplinkHwAddrCapEntry 8 }

cucsAdaptorUplinkHwAddrCapMacOffsetSub03 OBJECT-TYPE
    SYNTAX       Gauge32
    MAX-ACCESS   read-only
    STATUS       current
    DESCRIPTION
        "Cisco UCS adaptor:UplinkHwAddrCap:macOffsetSub03
        managed object property"
    ::= { cucsAdaptorUplinkHwAddrCapEntry 9 }

cucsAdaptorUplinkHwAddrCapMacOffsetSub10 OBJECT-TYPE
    SYNTAX       Gauge32
    MAX-ACCESS   read-only
    STATUS       current
    DESCRIPTION
        "Cisco UCS adaptor:UplinkHwAddrCap:macOffsetSub10
        managed object property"
    ::= { cucsAdaptorUplinkHwAddrCapEntry 10 }

cucsAdaptorUplinkHwAddrCapMacOffsetSub11 OBJECT-TYPE
    SYNTAX       Gauge32
    MAX-ACCESS   read-only
    STATUS       current
    DESCRIPTION
        "Cisco UCS adaptor:UplinkHwAddrCap:macOffsetSub11
        managed object property"
    ::= { cucsAdaptorUplinkHwAddrCapEntry 11 }

cucsAdaptorUplinkHwAddrCapMacOffsetSub12 OBJECT-TYPE
    SYNTAX       Gauge32
    MAX-ACCESS   read-only
    STATUS       current
    DESCRIPTION
        "Cisco UCS adaptor:UplinkHwAddrCap:macOffsetSub12
        managed object property"
    ::= { cucsAdaptorUplinkHwAddrCapEntry 12 }

cucsAdaptorUplinkHwAddrCapMacOffsetSub13 OBJECT-TYPE
    SYNTAX       Gauge32
    MAX-ACCESS   read-only
    STATUS       current
    DESCRIPTION
        "Cisco UCS adaptor:UplinkHwAddrCap:macOffsetSub13
        managed object property"
    ::= { cucsAdaptorUplinkHwAddrCapEntry 13 }

cucsAdaptorUplinkHwAddrCapLldpMacOffset1 OBJECT-TYPE
    SYNTAX       Gauge32
    MAX-ACCESS   read-only
    STATUS       current
    DESCRIPTION
        "Cisco UCS adaptor:UplinkHwAddrCap:lldpMacOffset1
        managed object property"
    ::= { cucsAdaptorUplinkHwAddrCapEntry 14 }

cucsAdaptorUplinkHwAddrCapLldpMacOffset2 OBJECT-TYPE
    SYNTAX       Gauge32
    MAX-ACCESS   read-only
    STATUS       current
    DESCRIPTION
        "Cisco UCS adaptor:UplinkHwAddrCap:lldpMacOffset2
        managed object property"
    ::= { cucsAdaptorUplinkHwAddrCapEntry 15 }

cucsAdaptorUplinkPortStatsTable OBJECT-TYPE
    SYNTAX           SEQUENCE OF CucsAdaptorUplinkPortStatsEntry
    MAX-ACCESS       not-accessible
    STATUS           current
    DESCRIPTION
        "Cisco UCS adaptor:UplinkPortStats managed object table"
    ::= { cucsAdaptorObjects 127 }

cucsAdaptorUplinkPortStatsEntry OBJECT-TYPE
    SYNTAX           CucsAdaptorUplinkPortStatsEntry
    MAX-ACCESS       not-accessible
    STATUS           current
    DESCRIPTION
        "Entry for the cucsAdaptorUplinkPortStatsTable table."
    INDEX { cucsAdaptorUplinkPortStatsInstanceId }
    ::= { cucsAdaptorUplinkPortStatsTable 1 }

CucsAdaptorUplinkPortStatsEntry ::= SEQUENCE {
    cucsAdaptorUplinkPortStatsInstanceId                             CucsManagedObjectId,
    cucsAdaptorUplinkPortStatsDn                                     CucsManagedObjectDn,
    cucsAdaptorUplinkPortStatsRn                                     SnmpAdminString,
    cucsAdaptorUplinkPortStatsCrc                                    Gauge32,
    cucsAdaptorUplinkPortStatsFrameTx                                Gauge32,
    cucsAdaptorUplinkPortStatsInRange                                Gauge32,
    cucsAdaptorUplinkPortStatsPortId                                 Gauge32,
    cucsAdaptorUplinkPortStatsTooLong                                Gauge32,
    cucsAdaptorUplinkPortStatsTooShort                               Gauge32
}

cucsAdaptorUplinkPortStatsInstanceId OBJECT-TYPE
    SYNTAX       CucsManagedObjectId
    MAX-ACCESS   not-accessible
    STATUS       current
    DESCRIPTION
        "Instance identifier of the managed object."
    ::= { cucsAdaptorUplinkPortStatsEntry 1 }

cucsAdaptorUplinkPortStatsDn OBJECT-TYPE
    SYNTAX       CucsManagedObjectDn
    MAX-ACCESS   read-only
    STATUS       current
    DESCRIPTION
        "Cisco UCS adaptor:UplinkPortStats:dn managed object property"
    ::= { cucsAdaptorUplinkPortStatsEntry 2 }

cucsAdaptorUplinkPortStatsRn OBJECT-TYPE
    SYNTAX       SnmpAdminString
    MAX-ACCESS   read-only
    STATUS       current
    DESCRIPTION
        "Cisco UCS adaptor:UplinkPortStats:rn managed object property"
    ::= { cucsAdaptorUplinkPortStatsEntry 3 }

cucsAdaptorUplinkPortStatsCrc OBJECT-TYPE
    SYNTAX       Gauge32
    MAX-ACCESS   read-only
    STATUS       current
    DESCRIPTION
        "Cisco UCS adaptor:UplinkPortStats:crc managed object property"
    ::= { cucsAdaptorUplinkPortStatsEntry 4 }

cucsAdaptorUplinkPortStatsFrameTx OBJECT-TYPE
    SYNTAX       Gauge32
    MAX-ACCESS   read-only
    STATUS       current
    DESCRIPTION
        "Cisco UCS adaptor:UplinkPortStats:frameTx managed
        object property"
    ::= { cucsAdaptorUplinkPortStatsEntry 5 }

cucsAdaptorUplinkPortStatsInRange OBJECT-TYPE
    SYNTAX       Gauge32
    MAX-ACCESS   read-only
    STATUS       current
    DESCRIPTION
        "Cisco UCS adaptor:UplinkPortStats:inRange managed
        object property"
    ::= { cucsAdaptorUplinkPortStatsEntry 6 }

cucsAdaptorUplinkPortStatsPortId OBJECT-TYPE
    SYNTAX       Gauge32
    MAX-ACCESS   read-only
    STATUS       current
    DESCRIPTION
        "Cisco UCS adaptor:UplinkPortStats:portId managed object property"
    ::= { cucsAdaptorUplinkPortStatsEntry 7 }

cucsAdaptorUplinkPortStatsTooLong OBJECT-TYPE
    SYNTAX       Gauge32
    MAX-ACCESS   read-only
    STATUS       current
    DESCRIPTION
        "Cisco UCS adaptor:UplinkPortStats:tooLong managed
        object property"
    ::= { cucsAdaptorUplinkPortStatsEntry 8 }

cucsAdaptorUplinkPortStatsTooShort OBJECT-TYPE
    SYNTAX       Gauge32
    MAX-ACCESS   read-only
    STATUS       current
    DESCRIPTION
        "Cisco UCS adaptor:UplinkPortStats:tooShort managed
        object property"
    ::= { cucsAdaptorUplinkPortStatsEntry 9 }

cucsAdaptorUsnicConnDefTable OBJECT-TYPE
    SYNTAX           SEQUENCE OF CucsAdaptorUsnicConnDefEntry
    MAX-ACCESS       not-accessible
    STATUS           current
    DESCRIPTION
        "Cisco UCS adaptor:UsnicConnDef managed object table"
    ::= { cucsAdaptorObjects 115 }

cucsAdaptorUsnicConnDefEntry OBJECT-TYPE
    SYNTAX           CucsAdaptorUsnicConnDefEntry
    MAX-ACCESS       not-accessible
    STATUS           current
    DESCRIPTION
        "Entry for the cucsAdaptorUsnicConnDefTable table."
    INDEX { cucsAdaptorUsnicConnDefInstanceId }
    ::= { cucsAdaptorUsnicConnDefTable 1 }

CucsAdaptorUsnicConnDefEntry ::= SEQUENCE {
    cucsAdaptorUsnicConnDefInstanceId                                CucsManagedObjectId,
    cucsAdaptorUsnicConnDefDn                                        CucsManagedObjectDn,
    cucsAdaptorUsnicConnDefRn                                        SnmpAdminString,
    cucsAdaptorUsnicConnDefConPolicyName                             SnmpAdminString,
    cucsAdaptorUsnicConnDefUsnicCount                                Gauge32
}

cucsAdaptorUsnicConnDefInstanceId OBJECT-TYPE
    SYNTAX       CucsManagedObjectId
    MAX-ACCESS   not-accessible
    STATUS       current
    DESCRIPTION
        "Instance identifier of the managed object."
    ::= { cucsAdaptorUsnicConnDefEntry 1 }

cucsAdaptorUsnicConnDefDn OBJECT-TYPE
    SYNTAX       CucsManagedObjectDn
    MAX-ACCESS   read-only
    STATUS       current
    DESCRIPTION
        "Cisco UCS adaptor:UsnicConnDef:dn managed object property"
    ::= { cucsAdaptorUsnicConnDefEntry 2 }

cucsAdaptorUsnicConnDefRn OBJECT-TYPE
    SYNTAX       SnmpAdminString
    MAX-ACCESS   read-only
    STATUS       current
    DESCRIPTION
        "Cisco UCS adaptor:UsnicConnDef:rn managed object property"
    ::= { cucsAdaptorUsnicConnDefEntry 3 }

cucsAdaptorUsnicConnDefConPolicyName OBJECT-TYPE
    SYNTAX       SnmpAdminString
    MAX-ACCESS   read-only
    STATUS       current
    DESCRIPTION
        "Cisco UCS adaptor:UsnicConnDef:conPolicyName managed
        object property"
    ::= { cucsAdaptorUsnicConnDefEntry 4 }

cucsAdaptorUsnicConnDefUsnicCount OBJECT-TYPE
    SYNTAX       Gauge32
    MAX-ACCESS   read-only
    STATUS       current
    DESCRIPTION
        "Cisco UCS adaptor:UsnicConnDef:usnicCount managed
        object property"
    ::= { cucsAdaptorUsnicConnDefEntry 5 }

cucsAdaptorVlanTable OBJECT-TYPE
    SYNTAX           SEQUENCE OF CucsAdaptorVlanEntry
    MAX-ACCESS       not-accessible
    STATUS           current
    DESCRIPTION
        "Cisco UCS adaptor:Vlan managed object table"
    ::= { cucsAdaptorObjects 86 }

cucsAdaptorVlanEntry OBJECT-TYPE
    SYNTAX           CucsAdaptorVlanEntry
    MAX-ACCESS       not-accessible
    STATUS           current
    DESCRIPTION
        "Entry for the cucsAdaptorVlanTable table."
    INDEX { cucsAdaptorVlanInstanceId }
    ::= { cucsAdaptorVlanTable 1 }

CucsAdaptorVlanEntry ::= SEQUENCE {
    cucsAdaptorVlanInstanceId                                        CucsManagedObjectId,
    cucsAdaptorVlanDn                                                CucsManagedObjectDn,
    cucsAdaptorVlanRn                                                SnmpAdminString,
    cucsAdaptorVlanEpDn                                              SnmpAdminString,
    cucsAdaptorVlanId                                                Gauge32,
    cucsAdaptorVlanIfRole                                            CucsFabricVnetEpIfRole,
    cucsAdaptorVlanIfType                                            CucsNetworkVnetEpIfType,
    cucsAdaptorVlanLc                                                CucsFsmLifecycle,
    cucsAdaptorVlanLocale                                            CucsFabricVnetEpLocale,
    cucsAdaptorVlanName                                              SnmpAdminString,
    cucsAdaptorVlanPeerDn                                            SnmpAdminString,
    cucsAdaptorVlanPubNwDn                                           SnmpAdminString,
    cucsAdaptorVlanPubNwId                                           Gauge32,
    cucsAdaptorVlanPubNwName                                         SnmpAdminString,
    cucsAdaptorVlanSharing                                           CucsFabricAVlanSharing,
    cucsAdaptorVlanSwitchId                                          CucsNetworkSwitchId,
    cucsAdaptorVlanTransport                                         CucsFabricAVlanTransport,
    cucsAdaptorVlanType                                              CucsFabricAVlanType,
    cucsAdaptorVlanVlanType                                          CucsFabricEpVlanVlanType,
    cucsAdaptorVlanOperState                                         CucsFabricVlanOperState,
    cucsAdaptorVlanPolicyOwner                                       CucsFabricVnetEpPolicyOwner,
    cucsAdaptorVlanAssocPrimaryVlanState                             CucsFabricVlanAssocPrimaryVlanState,
    cucsAdaptorVlanAssocPrimaryVlanSwitchId                          CucsFabricAVlanAssocPrimaryVlanSwitchId,
    cucsAdaptorVlanOverlapStateForA                                  CucsFabricVlanOverlapState,
    cucsAdaptorVlanOverlapStateForB                                  CucsFabricVlanOverlapState
}

cucsAdaptorVlanInstanceId OBJECT-TYPE
    SYNTAX       CucsManagedObjectId
    MAX-ACCESS   not-accessible
    STATUS       current
    DESCRIPTION
        "Instance identifier of the managed object."
    ::= { cucsAdaptorVlanEntry 1 }

cucsAdaptorVlanDn OBJECT-TYPE
    SYNTAX       CucsManagedObjectDn
    MAX-ACCESS   read-only
    STATUS       current
    DESCRIPTION
        "Cisco UCS adaptor:Vlan:dn managed object property"
    ::= { cucsAdaptorVlanEntry 2 }

cucsAdaptorVlanRn OBJECT-TYPE
    SYNTAX       SnmpAdminString
    MAX-ACCESS   read-only
    STATUS       current
    DESCRIPTION
        "Cisco UCS adaptor:Vlan:rn managed object property"
    ::= { cucsAdaptorVlanEntry 3 }

cucsAdaptorVlanEpDn OBJECT-TYPE
    SYNTAX       SnmpAdminString
    MAX-ACCESS   read-only
    STATUS       current
    DESCRIPTION
        "Cisco UCS adaptor:Vlan:epDn managed object property"
    ::= { cucsAdaptorVlanEntry 4 }

cucsAdaptorVlanId OBJECT-TYPE
    SYNTAX       Gauge32
    MAX-ACCESS   read-only
    STATUS       current
    DESCRIPTION
        "Cisco UCS adaptor:Vlan:id managed object property"
    ::= { cucsAdaptorVlanEntry 5 }

cucsAdaptorVlanIfRole OBJECT-TYPE
    SYNTAX       CucsFabricVnetEpIfRole
    MAX-ACCESS   read-only
    STATUS       current
    DESCRIPTION
        "Cisco UCS adaptor:Vlan:ifRole managed object property"
    ::= { cucsAdaptorVlanEntry 6 }

cucsAdaptorVlanIfType OBJECT-TYPE
    SYNTAX       CucsNetworkVnetEpIfType
    MAX-ACCESS   read-only
    STATUS       current
    DESCRIPTION
        "Cisco UCS adaptor:Vlan:ifType managed object property"
    ::= { cucsAdaptorVlanEntry 7 }

cucsAdaptorVlanLc OBJECT-TYPE
    SYNTAX       CucsFsmLifecycle
    MAX-ACCESS   read-only
    STATUS       current
    DESCRIPTION
        "Cisco UCS adaptor:Vlan:lc managed object property"
    ::= { cucsAdaptorVlanEntry 8 }

cucsAdaptorVlanLocale OBJECT-TYPE
    SYNTAX       CucsFabricVnetEpLocale
    MAX-ACCESS   read-only
    STATUS       current
    DESCRIPTION
        "Cisco UCS adaptor:Vlan:locale managed object property"
    ::= { cucsAdaptorVlanEntry 9 }

cucsAdaptorVlanName OBJECT-TYPE
    SYNTAX       SnmpAdminString
    MAX-ACCESS   read-only
    STATUS       current
    DESCRIPTION
        "Cisco UCS adaptor:Vlan:name managed object property"
    ::= { cucsAdaptorVlanEntry 10 }

cucsAdaptorVlanPeerDn OBJECT-TYPE
    SYNTAX       SnmpAdminString
    MAX-ACCESS   read-only
    STATUS       current
    DESCRIPTION
        "Cisco UCS adaptor:Vlan:peerDn managed object property"
    ::= { cucsAdaptorVlanEntry 11 }

cucsAdaptorVlanPubNwDn OBJECT-TYPE
    SYNTAX       SnmpAdminString
    MAX-ACCESS   read-only
    STATUS       current
    DESCRIPTION
        "Cisco UCS adaptor:Vlan:pubNwDn managed object property"
    ::= { cucsAdaptorVlanEntry 12 }

cucsAdaptorVlanPubNwId OBJECT-TYPE
    SYNTAX       Gauge32
    MAX-ACCESS   read-only
    STATUS       current
    DESCRIPTION
        "Cisco UCS adaptor:Vlan:pubNwId managed object property"
    ::= { cucsAdaptorVlanEntry 13 }

cucsAdaptorVlanPubNwName OBJECT-TYPE
    SYNTAX       SnmpAdminString
    MAX-ACCESS   read-only
    STATUS       current
    DESCRIPTION
        "Cisco UCS adaptor:Vlan:pubNwName managed object property"
    ::= { cucsAdaptorVlanEntry 14 }

cucsAdaptorVlanSharing OBJECT-TYPE
    SYNTAX       CucsFabricAVlanSharing
    MAX-ACCESS   read-only
    STATUS       current
    DESCRIPTION
        "Cisco UCS adaptor:Vlan:sharing managed object property"
    ::= { cucsAdaptorVlanEntry 15 }

cucsAdaptorVlanSwitchId OBJECT-TYPE
    SYNTAX       CucsNetworkSwitchId
    MAX-ACCESS   read-only
    STATUS       current
    DESCRIPTION
        "Cisco UCS adaptor:Vlan:switchId managed object property"
    ::= { cucsAdaptorVlanEntry 16 }

cucsAdaptorVlanTransport OBJECT-TYPE
    SYNTAX       CucsFabricAVlanTransport
    MAX-ACCESS   read-only
    STATUS       current
    DESCRIPTION
        "Cisco UCS adaptor:Vlan:transport managed object property"
    ::= { cucsAdaptorVlanEntry 17 }

cucsAdaptorVlanType OBJECT-TYPE
    SYNTAX       CucsFabricAVlanType
    MAX-ACCESS   read-only
    STATUS       current
    DESCRIPTION
        "Cisco UCS adaptor:Vlan:type managed object property"
    ::= { cucsAdaptorVlanEntry 18 }

cucsAdaptorVlanVlanType OBJECT-TYPE
    SYNTAX       CucsFabricEpVlanVlanType
    MAX-ACCESS   read-only
    STATUS       current
    DESCRIPTION
        "Cisco UCS adaptor:Vlan:vlanType managed object property"
    ::= { cucsAdaptorVlanEntry 19 }

cucsAdaptorVlanOperState OBJECT-TYPE
    SYNTAX       CucsFabricVlanOperState
    MAX-ACCESS   read-only
    STATUS       current
    DESCRIPTION
        "Cisco UCS adaptor:Vlan:operState managed object property"
    ::= { cucsAdaptorVlanEntry 20 }

cucsAdaptorVlanPolicyOwner OBJECT-TYPE
    SYNTAX       CucsFabricVnetEpPolicyOwner
    MAX-ACCESS   read-only
    STATUS       current
    DESCRIPTION
        "Cisco UCS adaptor:Vlan:policyOwner managed object property"
    ::= { cucsAdaptorVlanEntry 22 }

cucsAdaptorVlanAssocPrimaryVlanState OBJECT-TYPE
    SYNTAX       CucsFabricVlanAssocPrimaryVlanState
    MAX-ACCESS   read-only
    STATUS       current
    DESCRIPTION
        "Cisco UCS adaptor:Vlan:assocPrimaryVlanState managed
        object property"
    ::= { cucsAdaptorVlanEntry 23 }

cucsAdaptorVlanAssocPrimaryVlanSwitchId OBJECT-TYPE
    SYNTAX       CucsFabricAVlanAssocPrimaryVlanSwitchId
    MAX-ACCESS   read-only
    STATUS       current
    DESCRIPTION
        "Cisco UCS adaptor:Vlan:assocPrimaryVlanSwitchId
        managed object property"
    ::= { cucsAdaptorVlanEntry 24 }

cucsAdaptorVlanOverlapStateForA OBJECT-TYPE
    SYNTAX       CucsFabricVlanOverlapState
    MAX-ACCESS   read-only
    STATUS       current
    DESCRIPTION
        "Cisco UCS adaptor:Vlan:overlapStateForA managed object property"
    ::= { cucsAdaptorVlanEntry 25 }

cucsAdaptorVlanOverlapStateForB OBJECT-TYPE
    SYNTAX       CucsFabricVlanOverlapState
    MAX-ACCESS   read-only
    STATUS       current
    DESCRIPTION
        "Cisco UCS adaptor:Vlan:overlapStateForB managed object property"
    ::= { cucsAdaptorVlanEntry 26 }

cucsAdaptorVnicStatsTable OBJECT-TYPE
    SYNTAX           SEQUENCE OF CucsAdaptorVnicStatsEntry
    MAX-ACCESS       not-accessible
    STATUS           current
    DESCRIPTION
        "Cisco UCS adaptor:VnicStats managed object table"
    ::= { cucsAdaptorObjects 87 }

cucsAdaptorVnicStatsEntry OBJECT-TYPE
    SYNTAX           CucsAdaptorVnicStatsEntry
    MAX-ACCESS       not-accessible
    STATUS           current
    DESCRIPTION
        "Entry for the cucsAdaptorVnicStatsTable table."
    INDEX { cucsAdaptorVnicStatsInstanceId }
    ::= { cucsAdaptorVnicStatsTable 1 }

CucsAdaptorVnicStatsEntry ::= SEQUENCE {
    cucsAdaptorVnicStatsInstanceId                                   CucsManagedObjectId,
    cucsAdaptorVnicStatsDn                                           CucsManagedObjectDn,
    cucsAdaptorVnicStatsRn                                           SnmpAdminString,
    cucsAdaptorVnicStatsBytesRx                                      Unsigned64,
    cucsAdaptorVnicStatsBytesRxDelta                                 Counter64,
    cucsAdaptorVnicStatsBytesRxDeltaAvg                              Unsigned64,
    cucsAdaptorVnicStatsBytesRxDeltaMax                              Unsigned64,
    cucsAdaptorVnicStatsBytesRxDeltaMin                              Unsigned64,
    cucsAdaptorVnicStatsBytesTx                                      Unsigned64,
    cucsAdaptorVnicStatsBytesTxDelta                                 Counter64,
    cucsAdaptorVnicStatsBytesTxDeltaAvg                              Unsigned64,
    cucsAdaptorVnicStatsBytesTxDeltaMax                              Unsigned64,
    cucsAdaptorVnicStatsBytesTxDeltaMin                              Unsigned64,
    cucsAdaptorVnicStatsDroppedRx                                    Unsigned64,
    cucsAdaptorVnicStatsDroppedRxDelta                               Counter64,
    cucsAdaptorVnicStatsDroppedRxDeltaAvg                            Unsigned64,
    cucsAdaptorVnicStatsDroppedRxDeltaMax                            Unsigned64,
    cucsAdaptorVnicStatsDroppedRxDeltaMin                            Unsigned64,
    cucsAdaptorVnicStatsDroppedTx                                    Unsigned64,
    cucsAdaptorVnicStatsDroppedTxDelta                               Counter64,
    cucsAdaptorVnicStatsDroppedTxDeltaAvg                            Unsigned64,
    cucsAdaptorVnicStatsDroppedTxDeltaMax                            Unsigned64,
    cucsAdaptorVnicStatsDroppedTxDeltaMin                            Unsigned64,
    cucsAdaptorVnicStatsErrorsRx                                     Unsigned64,
    cucsAdaptorVnicStatsErrorsRxDelta                                Counter64,
    cucsAdaptorVnicStatsErrorsRxDeltaAvg                             Unsigned64,
    cucsAdaptorVnicStatsErrorsRxDeltaMax                             Unsigned64,
    cucsAdaptorVnicStatsErrorsRxDeltaMin                             Unsigned64,
    cucsAdaptorVnicStatsErrorsTx                                     Unsigned64,
    cucsAdaptorVnicStatsErrorsTxDelta                                Counter64,
    cucsAdaptorVnicStatsErrorsTxDeltaAvg                             Unsigned64,
    cucsAdaptorVnicStatsErrorsTxDeltaMax                             Unsigned64,
    cucsAdaptorVnicStatsErrorsTxDeltaMin                             Unsigned64,
    cucsAdaptorVnicStatsIntervals                                    Gauge32,
    cucsAdaptorVnicStatsPacketsRx                                    Unsigned64,
    cucsAdaptorVnicStatsPacketsRxDelta                               Counter64,
    cucsAdaptorVnicStatsPacketsRxDeltaAvg                            Unsigned64,
    cucsAdaptorVnicStatsPacketsRxDeltaMax                            Unsigned64,
    cucsAdaptorVnicStatsPacketsRxDeltaMin                            Unsigned64,
    cucsAdaptorVnicStatsPacketsTx                                    Unsigned64,
    cucsAdaptorVnicStatsPacketsTxDelta                               Counter64,
    cucsAdaptorVnicStatsPacketsTxDeltaAvg                            Unsigned64,
    cucsAdaptorVnicStatsPacketsTxDeltaMax                            Unsigned64,
    cucsAdaptorVnicStatsPacketsTxDeltaMin                            Unsigned64,
    cucsAdaptorVnicStatsSuspect                                      TruthValue,
    cucsAdaptorVnicStatsThresholded                                  CucsAdaptorVnicStatsThresholded,
    cucsAdaptorVnicStatsTimeCollected                                DateAndTime,
    cucsAdaptorVnicStatsUpdate                                       Gauge32
}

cucsAdaptorVnicStatsInstanceId OBJECT-TYPE
    SYNTAX       CucsManagedObjectId
    MAX-ACCESS   not-accessible
    STATUS       current
    DESCRIPTION
        "Instance identifier of the managed object."
    ::= { cucsAdaptorVnicStatsEntry 1 }

cucsAdaptorVnicStatsDn OBJECT-TYPE
    SYNTAX       CucsManagedObjectDn
    MAX-ACCESS   read-only
    STATUS       current
    DESCRIPTION
        "Cisco UCS adaptor:VnicStats:dn managed object property"
    ::= { cucsAdaptorVnicStatsEntry 2 }

cucsAdaptorVnicStatsRn OBJECT-TYPE
    SYNTAX       SnmpAdminString
    MAX-ACCESS   read-only
    STATUS       current
    DESCRIPTION
        "Cisco UCS adaptor:VnicStats:rn managed object property"
    ::= { cucsAdaptorVnicStatsEntry 3 }

cucsAdaptorVnicStatsBytesRx OBJECT-TYPE
    SYNTAX       Unsigned64
    MAX-ACCESS   read-only
    STATUS       current
    DESCRIPTION
        "Cisco UCS adaptor:VnicStats:bytesRx managed object property"
    ::= { cucsAdaptorVnicStatsEntry 4 }

cucsAdaptorVnicStatsBytesRxDelta OBJECT-TYPE
    SYNTAX       Counter64
    MAX-ACCESS   read-only
    STATUS       current
    DESCRIPTION
        "Cisco UCS adaptor:VnicStats:bytesRxDelta managed object property"
    ::= { cucsAdaptorVnicStatsEntry 5 }

cucsAdaptorVnicStatsBytesRxDeltaAvg OBJECT-TYPE
    SYNTAX       Unsigned64
    MAX-ACCESS   read-only
    STATUS       current
    DESCRIPTION
        "Cisco UCS adaptor:VnicStats:bytesRxDeltaAvg managed
        object property"
    ::= { cucsAdaptorVnicStatsEntry 6 }

cucsAdaptorVnicStatsBytesRxDeltaMax OBJECT-TYPE
    SYNTAX       Unsigned64
    MAX-ACCESS   read-only
    STATUS       current
    DESCRIPTION
        "Cisco UCS adaptor:VnicStats:bytesRxDeltaMax managed
        object property"
    ::= { cucsAdaptorVnicStatsEntry 7 }

cucsAdaptorVnicStatsBytesRxDeltaMin OBJECT-TYPE
    SYNTAX       Unsigned64
    MAX-ACCESS   read-only
    STATUS       current
    DESCRIPTION
        "Cisco UCS adaptor:VnicStats:bytesRxDeltaMin managed
        object property"
    ::= { cucsAdaptorVnicStatsEntry 8 }

cucsAdaptorVnicStatsBytesTx OBJECT-TYPE
    SYNTAX       Unsigned64
    MAX-ACCESS   read-only
    STATUS       current
    DESCRIPTION
        "Cisco UCS adaptor:VnicStats:bytesTx managed object property"
    ::= { cucsAdaptorVnicStatsEntry 9 }

cucsAdaptorVnicStatsBytesTxDelta OBJECT-TYPE
    SYNTAX       Counter64
    MAX-ACCESS   read-only
    STATUS       current
    DESCRIPTION
        "Cisco UCS adaptor:VnicStats:bytesTxDelta managed object property"
    ::= { cucsAdaptorVnicStatsEntry 10 }

cucsAdaptorVnicStatsBytesTxDeltaAvg OBJECT-TYPE
    SYNTAX       Unsigned64
    MAX-ACCESS   read-only
    STATUS       current
    DESCRIPTION
        "Cisco UCS adaptor:VnicStats:bytesTxDeltaAvg managed
        object property"
    ::= { cucsAdaptorVnicStatsEntry 11 }

cucsAdaptorVnicStatsBytesTxDeltaMax OBJECT-TYPE
    SYNTAX       Unsigned64
    MAX-ACCESS   read-only
    STATUS       current
    DESCRIPTION
        "Cisco UCS adaptor:VnicStats:bytesTxDeltaMax managed
        object property"
    ::= { cucsAdaptorVnicStatsEntry 12 }

cucsAdaptorVnicStatsBytesTxDeltaMin OBJECT-TYPE
    SYNTAX       Unsigned64
    MAX-ACCESS   read-only
    STATUS       current
    DESCRIPTION
        "Cisco UCS adaptor:VnicStats:bytesTxDeltaMin managed
        object property"
    ::= { cucsAdaptorVnicStatsEntry 13 }

cucsAdaptorVnicStatsDroppedRx OBJECT-TYPE
    SYNTAX       Unsigned64
    MAX-ACCESS   read-only
    STATUS       current
    DESCRIPTION
        "Cisco UCS adaptor:VnicStats:droppedRx managed object property"
    ::= { cucsAdaptorVnicStatsEntry 14 }

cucsAdaptorVnicStatsDroppedRxDelta OBJECT-TYPE
    SYNTAX       Counter64
    MAX-ACCESS   read-only
    STATUS       current
    DESCRIPTION
        "Cisco UCS adaptor:VnicStats:droppedRxDelta managed
        object property"
    ::= { cucsAdaptorVnicStatsEntry 15 }

cucsAdaptorVnicStatsDroppedRxDeltaAvg OBJECT-TYPE
    SYNTAX       Unsigned64
    MAX-ACCESS   read-only
    STATUS       current
    DESCRIPTION
        "Cisco UCS adaptor:VnicStats:droppedRxDeltaAvg
        managed object property"
    ::= { cucsAdaptorVnicStatsEntry 16 }

cucsAdaptorVnicStatsDroppedRxDeltaMax OBJECT-TYPE
    SYNTAX       Unsigned64
    MAX-ACCESS   read-only
    STATUS       current
    DESCRIPTION
        "Cisco UCS adaptor:VnicStats:droppedRxDeltaMax
        managed object property"
    ::= { cucsAdaptorVnicStatsEntry 17 }

cucsAdaptorVnicStatsDroppedRxDeltaMin OBJECT-TYPE
    SYNTAX       Unsigned64
    MAX-ACCESS   read-only
    STATUS       current
    DESCRIPTION
        "Cisco UCS adaptor:VnicStats:droppedRxDeltaMin
        managed object property"
    ::= { cucsAdaptorVnicStatsEntry 18 }

cucsAdaptorVnicStatsDroppedTx OBJECT-TYPE
    SYNTAX       Unsigned64
    MAX-ACCESS   read-only
    STATUS       current
    DESCRIPTION
        "Cisco UCS adaptor:VnicStats:droppedTx managed object property"
    ::= { cucsAdaptorVnicStatsEntry 19 }

cucsAdaptorVnicStatsDroppedTxDelta OBJECT-TYPE
    SYNTAX       Counter64
    MAX-ACCESS   read-only
    STATUS       current
    DESCRIPTION
        "Cisco UCS adaptor:VnicStats:droppedTxDelta managed
        object property"
    ::= { cucsAdaptorVnicStatsEntry 20 }

cucsAdaptorVnicStatsDroppedTxDeltaAvg OBJECT-TYPE
    SYNTAX       Unsigned64
    MAX-ACCESS   read-only
    STATUS       current
    DESCRIPTION
        "Cisco UCS adaptor:VnicStats:droppedTxDeltaAvg
        managed object property"
    ::= { cucsAdaptorVnicStatsEntry 21 }

cucsAdaptorVnicStatsDroppedTxDeltaMax OBJECT-TYPE
    SYNTAX       Unsigned64
    MAX-ACCESS   read-only
    STATUS       current
    DESCRIPTION
        "Cisco UCS adaptor:VnicStats:droppedTxDeltaMax
        managed object property"
    ::= { cucsAdaptorVnicStatsEntry 22 }

cucsAdaptorVnicStatsDroppedTxDeltaMin OBJECT-TYPE
    SYNTAX       Unsigned64
    MAX-ACCESS   read-only
    STATUS       current
    DESCRIPTION
        "Cisco UCS adaptor:VnicStats:droppedTxDeltaMin
        managed object property"
    ::= { cucsAdaptorVnicStatsEntry 23 }

cucsAdaptorVnicStatsErrorsRx OBJECT-TYPE
    SYNTAX       Unsigned64
    MAX-ACCESS   read-only
    STATUS       current
    DESCRIPTION
        "Cisco UCS adaptor:VnicStats:errorsRx managed object property"
    ::= { cucsAdaptorVnicStatsEntry 24 }

cucsAdaptorVnicStatsErrorsRxDelta OBJECT-TYPE
    SYNTAX       Counter64
    MAX-ACCESS   read-only
    STATUS       current
    DESCRIPTION
        "Cisco UCS adaptor:VnicStats:errorsRxDelta managed
        object property"
    ::= { cucsAdaptorVnicStatsEntry 25 }

cucsAdaptorVnicStatsErrorsRxDeltaAvg OBJECT-TYPE
    SYNTAX       Unsigned64
    MAX-ACCESS   read-only
    STATUS       current
    DESCRIPTION
        "Cisco UCS adaptor:VnicStats:errorsRxDeltaAvg managed
        object property"
    ::= { cucsAdaptorVnicStatsEntry 26 }

cucsAdaptorVnicStatsErrorsRxDeltaMax OBJECT-TYPE
    SYNTAX       Unsigned64
    MAX-ACCESS   read-only
    STATUS       current
    DESCRIPTION
        "Cisco UCS adaptor:VnicStats:errorsRxDeltaMax managed
        object property"
    ::= { cucsAdaptorVnicStatsEntry 27 }

cucsAdaptorVnicStatsErrorsRxDeltaMin OBJECT-TYPE
    SYNTAX       Unsigned64
    MAX-ACCESS   read-only
    STATUS       current
    DESCRIPTION
        "Cisco UCS adaptor:VnicStats:errorsRxDeltaMin managed
        object property"
    ::= { cucsAdaptorVnicStatsEntry 28 }

cucsAdaptorVnicStatsErrorsTx OBJECT-TYPE
    SYNTAX       Unsigned64
    MAX-ACCESS   read-only
    STATUS       current
    DESCRIPTION
        "Cisco UCS adaptor:VnicStats:errorsTx managed object property"
    ::= { cucsAdaptorVnicStatsEntry 29 }

cucsAdaptorVnicStatsErrorsTxDelta OBJECT-TYPE
    SYNTAX       Counter64
    MAX-ACCESS   read-only
    STATUS       current
    DESCRIPTION
        "Cisco UCS adaptor:VnicStats:errorsTxDelta managed
        object property"
    ::= { cucsAdaptorVnicStatsEntry 30 }

cucsAdaptorVnicStatsErrorsTxDeltaAvg OBJECT-TYPE
    SYNTAX       Unsigned64
    MAX-ACCESS   read-only
    STATUS       current
    DESCRIPTION
        "Cisco UCS adaptor:VnicStats:errorsTxDeltaAvg managed
        object property"
    ::= { cucsAdaptorVnicStatsEntry 31 }

cucsAdaptorVnicStatsErrorsTxDeltaMax OBJECT-TYPE
    SYNTAX       Unsigned64
    MAX-ACCESS   read-only
    STATUS       current
    DESCRIPTION
        "Cisco UCS adaptor:VnicStats:errorsTxDeltaMax managed
        object property"
    ::= { cucsAdaptorVnicStatsEntry 32 }

cucsAdaptorVnicStatsErrorsTxDeltaMin OBJECT-TYPE
    SYNTAX       Unsigned64
    MAX-ACCESS   read-only
    STATUS       current
    DESCRIPTION
        "Cisco UCS adaptor:VnicStats:errorsTxDeltaMin managed
        object property"
    ::= { cucsAdaptorVnicStatsEntry 33 }

cucsAdaptorVnicStatsIntervals OBJECT-TYPE
    SYNTAX       Gauge32
    MAX-ACCESS   read-only
    STATUS       current
    DESCRIPTION
        "Cisco UCS adaptor:VnicStats:intervals managed object property"
    ::= { cucsAdaptorVnicStatsEntry 34 }

cucsAdaptorVnicStatsPacketsRx OBJECT-TYPE
    SYNTAX       Unsigned64
    MAX-ACCESS   read-only
    STATUS       current
    DESCRIPTION
        "Cisco UCS adaptor:VnicStats:packetsRx managed object property"
    ::= { cucsAdaptorVnicStatsEntry 35 }

cucsAdaptorVnicStatsPacketsRxDelta OBJECT-TYPE
    SYNTAX       Counter64
    MAX-ACCESS   read-only
    STATUS       current
    DESCRIPTION
        "Cisco UCS adaptor:VnicStats:packetsRxDelta managed
        object property"
    ::= { cucsAdaptorVnicStatsEntry 36 }

cucsAdaptorVnicStatsPacketsRxDeltaAvg OBJECT-TYPE
    SYNTAX       Unsigned64
    MAX-ACCESS   read-only
    STATUS       current
    DESCRIPTION
        "Cisco UCS adaptor:VnicStats:packetsRxDeltaAvg
        managed object property"
    ::= { cucsAdaptorVnicStatsEntry 37 }

cucsAdaptorVnicStatsPacketsRxDeltaMax OBJECT-TYPE
    SYNTAX       Unsigned64
    MAX-ACCESS   read-only
    STATUS       current
    DESCRIPTION
        "Cisco UCS adaptor:VnicStats:packetsRxDeltaMax
        managed object property"
    ::= { cucsAdaptorVnicStatsEntry 38 }

cucsAdaptorVnicStatsPacketsRxDeltaMin OBJECT-TYPE
    SYNTAX       Unsigned64
    MAX-ACCESS   read-only
    STATUS       current
    DESCRIPTION
        "Cisco UCS adaptor:VnicStats:packetsRxDeltaMin
        managed object property"
    ::= { cucsAdaptorVnicStatsEntry 39 }

cucsAdaptorVnicStatsPacketsTx OBJECT-TYPE
    SYNTAX       Unsigned64
    MAX-ACCESS   read-only
    STATUS       current
    DESCRIPTION
        "Cisco UCS adaptor:VnicStats:packetsTx managed object property"
    ::= { cucsAdaptorVnicStatsEntry 40 }

cucsAdaptorVnicStatsPacketsTxDelta OBJECT-TYPE
    SYNTAX       Counter64
    MAX-ACCESS   read-only
    STATUS       current
    DESCRIPTION
        "Cisco UCS adaptor:VnicStats:packetsTxDelta managed
        object property"
    ::= { cucsAdaptorVnicStatsEntry 41 }

cucsAdaptorVnicStatsPacketsTxDeltaAvg OBJECT-TYPE
    SYNTAX       Unsigned64
    MAX-ACCESS   read-only
    STATUS       current
    DESCRIPTION
        "Cisco UCS adaptor:VnicStats:packetsTxDeltaAvg
        managed object property"
    ::= { cucsAdaptorVnicStatsEntry 42 }

cucsAdaptorVnicStatsPacketsTxDeltaMax OBJECT-TYPE
    SYNTAX       Unsigned64
    MAX-ACCESS   read-only
    STATUS       current
    DESCRIPTION
        "Cisco UCS adaptor:VnicStats:packetsTxDeltaMax
        managed object property"
    ::= { cucsAdaptorVnicStatsEntry 43 }

cucsAdaptorVnicStatsPacketsTxDeltaMin OBJECT-TYPE
    SYNTAX       Unsigned64
    MAX-ACCESS   read-only
    STATUS       current
    DESCRIPTION
        "Cisco UCS adaptor:VnicStats:packetsTxDeltaMin
        managed object property"
    ::= { cucsAdaptorVnicStatsEntry 44 }

cucsAdaptorVnicStatsSuspect OBJECT-TYPE
    SYNTAX       TruthValue
    MAX-ACCESS   read-only
    STATUS       current
    DESCRIPTION
        "Cisco UCS adaptor:VnicStats:suspect managed object property"
    ::= { cucsAdaptorVnicStatsEntry 45 }

cucsAdaptorVnicStatsThresholded OBJECT-TYPE
    SYNTAX       CucsAdaptorVnicStatsThresholded
    MAX-ACCESS   read-only
    STATUS       current
    DESCRIPTION
        "Cisco UCS adaptor:VnicStats:thresholded managed object property"
    ::= { cucsAdaptorVnicStatsEntry 46 }

cucsAdaptorVnicStatsTimeCollected OBJECT-TYPE
    SYNTAX       DateAndTime
    MAX-ACCESS   read-only
    STATUS       current
    DESCRIPTION
        "Cisco UCS adaptor:VnicStats:timeCollected managed
        object property"
    ::= { cucsAdaptorVnicStatsEntry 47 }

cucsAdaptorVnicStatsUpdate OBJECT-TYPE
    SYNTAX       Gauge32
    MAX-ACCESS   read-only
    STATUS       current
    DESCRIPTION
        "Cisco UCS adaptor:VnicStats:update managed object property"
    ::= { cucsAdaptorVnicStatsEntry 48 }

cucsAdaptorVnicStatsHistTable OBJECT-TYPE
    SYNTAX           SEQUENCE OF CucsAdaptorVnicStatsHistEntry
    MAX-ACCESS       not-accessible
    STATUS           current
    DESCRIPTION
        "Cisco UCS adaptor:VnicStatsHist managed object table"
    ::= { cucsAdaptorObjects 88 }

cucsAdaptorVnicStatsHistEntry OBJECT-TYPE
    SYNTAX           CucsAdaptorVnicStatsHistEntry
    MAX-ACCESS       not-accessible
    STATUS           current
    DESCRIPTION
        "Entry for the cucsAdaptorVnicStatsHistTable table."
    INDEX { cucsAdaptorVnicStatsHistInstanceId }
    ::= { cucsAdaptorVnicStatsHistTable 1 }

CucsAdaptorVnicStatsHistEntry ::= SEQUENCE {
    cucsAdaptorVnicStatsHistInstanceId                               CucsManagedObjectId,
    cucsAdaptorVnicStatsHistDn                                       CucsManagedObjectDn,
    cucsAdaptorVnicStatsHistRn                                       SnmpAdminString,
    cucsAdaptorVnicStatsHistBytesRx                                  Unsigned64,
    cucsAdaptorVnicStatsHistBytesRxDelta                             Unsigned64,
    cucsAdaptorVnicStatsHistBytesRxDeltaAvg                          Unsigned64,
    cucsAdaptorVnicStatsHistBytesRxDeltaMax                          Unsigned64,
    cucsAdaptorVnicStatsHistBytesRxDeltaMin                          Unsigned64,
    cucsAdaptorVnicStatsHistBytesTx                                  Unsigned64,
    cucsAdaptorVnicStatsHistBytesTxDelta                             Unsigned64,
    cucsAdaptorVnicStatsHistBytesTxDeltaAvg                          Unsigned64,
    cucsAdaptorVnicStatsHistBytesTxDeltaMax                          Unsigned64,
    cucsAdaptorVnicStatsHistBytesTxDeltaMin                          Unsigned64,
    cucsAdaptorVnicStatsHistDroppedRx                                Unsigned64,
    cucsAdaptorVnicStatsHistDroppedRxDelta                           Unsigned64,
    cucsAdaptorVnicStatsHistDroppedRxDeltaAvg                        Unsigned64,
    cucsAdaptorVnicStatsHistDroppedRxDeltaMax                        Unsigned64,
    cucsAdaptorVnicStatsHistDroppedRxDeltaMin                        Unsigned64,
    cucsAdaptorVnicStatsHistDroppedTx                                Unsigned64,
    cucsAdaptorVnicStatsHistDroppedTxDelta                           Unsigned64,
    cucsAdaptorVnicStatsHistDroppedTxDeltaAvg                        Unsigned64,
    cucsAdaptorVnicStatsHistDroppedTxDeltaMax                        Unsigned64,
    cucsAdaptorVnicStatsHistDroppedTxDeltaMin                        Unsigned64,
    cucsAdaptorVnicStatsHistErrorsRx                                 Unsigned64,
    cucsAdaptorVnicStatsHistErrorsRxDelta                            Unsigned64,
    cucsAdaptorVnicStatsHistErrorsRxDeltaAvg                         Unsigned64,
    cucsAdaptorVnicStatsHistErrorsRxDeltaMax                         Unsigned64,
    cucsAdaptorVnicStatsHistErrorsRxDeltaMin                         Unsigned64,
    cucsAdaptorVnicStatsHistErrorsTx                                 Unsigned64,
    cucsAdaptorVnicStatsHistErrorsTxDelta                            Unsigned64,
    cucsAdaptorVnicStatsHistErrorsTxDeltaAvg                         Unsigned64,
    cucsAdaptorVnicStatsHistErrorsTxDeltaMax                         Unsigned64,
    cucsAdaptorVnicStatsHistErrorsTxDeltaMin                         Unsigned64,
    cucsAdaptorVnicStatsHistId                                       Unsigned64,
    cucsAdaptorVnicStatsHistMostRecent                               TruthValue,
    cucsAdaptorVnicStatsHistPacketsRx                                Unsigned64,
    cucsAdaptorVnicStatsHistPacketsRxDelta                           Unsigned64,
    cucsAdaptorVnicStatsHistPacketsRxDeltaAvg                        Unsigned64,
    cucsAdaptorVnicStatsHistPacketsRxDeltaMax                        Unsigned64,
    cucsAdaptorVnicStatsHistPacketsRxDeltaMin                        Unsigned64,
    cucsAdaptorVnicStatsHistPacketsTx                                Unsigned64,
    cucsAdaptorVnicStatsHistPacketsTxDelta                           Unsigned64,
    cucsAdaptorVnicStatsHistPacketsTxDeltaAvg                        Unsigned64,
    cucsAdaptorVnicStatsHistPacketsTxDeltaMax                        Unsigned64,
    cucsAdaptorVnicStatsHistPacketsTxDeltaMin                        Unsigned64,
    cucsAdaptorVnicStatsHistSuspect                                  TruthValue,
    cucsAdaptorVnicStatsHistThresholded                              CucsAdaptorVnicStatsHistThresholded,
    cucsAdaptorVnicStatsHistTimeCollected                            DateAndTime
}

cucsAdaptorVnicStatsHistInstanceId OBJECT-TYPE
    SYNTAX       CucsManagedObjectId
    MAX-ACCESS   not-accessible
    STATUS       current
    DESCRIPTION
        "Instance identifier of the managed object."
    ::= { cucsAdaptorVnicStatsHistEntry 1 }

cucsAdaptorVnicStatsHistDn OBJECT-TYPE
    SYNTAX       CucsManagedObjectDn
    MAX-ACCESS   read-only
    STATUS       current
    DESCRIPTION
        "Cisco UCS adaptor:VnicStatsHist:dn managed object property"
    ::= { cucsAdaptorVnicStatsHistEntry 2 }

cucsAdaptorVnicStatsHistRn OBJECT-TYPE
    SYNTAX       SnmpAdminString
    MAX-ACCESS   read-only
    STATUS       current
    DESCRIPTION
        "Cisco UCS adaptor:VnicStatsHist:rn managed object property"
    ::= { cucsAdaptorVnicStatsHistEntry 3 }

cucsAdaptorVnicStatsHistBytesRx OBJECT-TYPE
    SYNTAX       Unsigned64
    MAX-ACCESS   read-only
    STATUS       current
    DESCRIPTION
        "Cisco UCS adaptor:VnicStatsHist:bytesRx managed object property"
    ::= { cucsAdaptorVnicStatsHistEntry 4 }

cucsAdaptorVnicStatsHistBytesRxDelta OBJECT-TYPE
    SYNTAX       Unsigned64
    MAX-ACCESS   read-only
    STATUS       current
    DESCRIPTION
        "Cisco UCS adaptor:VnicStatsHist:bytesRxDelta managed
        object property"
    ::= { cucsAdaptorVnicStatsHistEntry 5 }

cucsAdaptorVnicStatsHistBytesRxDeltaAvg OBJECT-TYPE
    SYNTAX       Unsigned64
    MAX-ACCESS   read-only
    STATUS       current
    DESCRIPTION
        "Cisco UCS adaptor:VnicStatsHist:bytesRxDeltaAvg
        managed object property"
    ::= { cucsAdaptorVnicStatsHistEntry 6 }

cucsAdaptorVnicStatsHistBytesRxDeltaMax OBJECT-TYPE
    SYNTAX       Unsigned64
    MAX-ACCESS   read-only
    STATUS       current
    DESCRIPTION
        "Cisco UCS adaptor:VnicStatsHist:bytesRxDeltaMax
        managed object property"
    ::= { cucsAdaptorVnicStatsHistEntry 7 }

cucsAdaptorVnicStatsHistBytesRxDeltaMin OBJECT-TYPE
    SYNTAX       Unsigned64
    MAX-ACCESS   read-only
    STATUS       current
    DESCRIPTION
        "Cisco UCS adaptor:VnicStatsHist:bytesRxDeltaMin
        managed object property"
    ::= { cucsAdaptorVnicStatsHistEntry 8 }

cucsAdaptorVnicStatsHistBytesTx OBJECT-TYPE
    SYNTAX       Unsigned64
    MAX-ACCESS   read-only
    STATUS       current
    DESCRIPTION
        "Cisco UCS adaptor:VnicStatsHist:bytesTx managed object property"
    ::= { cucsAdaptorVnicStatsHistEntry 9 }

cucsAdaptorVnicStatsHistBytesTxDelta OBJECT-TYPE
    SYNTAX       Unsigned64
    MAX-ACCESS   read-only
    STATUS       current
    DESCRIPTION
        "Cisco UCS adaptor:VnicStatsHist:bytesTxDelta managed
        object property"
    ::= { cucsAdaptorVnicStatsHistEntry 10 }

cucsAdaptorVnicStatsHistBytesTxDeltaAvg OBJECT-TYPE
    SYNTAX       Unsigned64
    MAX-ACCESS   read-only
    STATUS       current
    DESCRIPTION
        "Cisco UCS adaptor:VnicStatsHist:bytesTxDeltaAvg
        managed object property"
    ::= { cucsAdaptorVnicStatsHistEntry 11 }

cucsAdaptorVnicStatsHistBytesTxDeltaMax OBJECT-TYPE
    SYNTAX       Unsigned64
    MAX-ACCESS   read-only
    STATUS       current
    DESCRIPTION
        "Cisco UCS adaptor:VnicStatsHist:bytesTxDeltaMax
        managed object property"
    ::= { cucsAdaptorVnicStatsHistEntry 12 }

cucsAdaptorVnicStatsHistBytesTxDeltaMin OBJECT-TYPE
    SYNTAX       Unsigned64
    MAX-ACCESS   read-only
    STATUS       current
    DESCRIPTION
        "Cisco UCS adaptor:VnicStatsHist:bytesTxDeltaMin
        managed object property"
    ::= { cucsAdaptorVnicStatsHistEntry 13 }

cucsAdaptorVnicStatsHistDroppedRx OBJECT-TYPE
    SYNTAX       Unsigned64
    MAX-ACCESS   read-only
    STATUS       current
    DESCRIPTION
        "Cisco UCS adaptor:VnicStatsHist:droppedRx managed
        object property"
    ::= { cucsAdaptorVnicStatsHistEntry 14 }

cucsAdaptorVnicStatsHistDroppedRxDelta OBJECT-TYPE
    SYNTAX       Unsigned64
    MAX-ACCESS   read-only
    STATUS       current
    DESCRIPTION
        "Cisco UCS adaptor:VnicStatsHist:droppedRxDelta
        managed object property"
    ::= { cucsAdaptorVnicStatsHistEntry 15 }

cucsAdaptorVnicStatsHistDroppedRxDeltaAvg OBJECT-TYPE
    SYNTAX       Unsigned64
    MAX-ACCESS   read-only
    STATUS       current
    DESCRIPTION
        "Cisco UCS adaptor:VnicStatsHist:droppedRxDeltaAvg
        managed object property"
    ::= { cucsAdaptorVnicStatsHistEntry 16 }

cucsAdaptorVnicStatsHistDroppedRxDeltaMax OBJECT-TYPE
    SYNTAX       Unsigned64
    MAX-ACCESS   read-only
    STATUS       current
    DESCRIPTION
        "Cisco UCS adaptor:VnicStatsHist:droppedRxDeltaMax
        managed object property"
    ::= { cucsAdaptorVnicStatsHistEntry 17 }

cucsAdaptorVnicStatsHistDroppedRxDeltaMin OBJECT-TYPE
    SYNTAX       Unsigned64
    MAX-ACCESS   read-only
    STATUS       current
    DESCRIPTION
        "Cisco UCS adaptor:VnicStatsHist:droppedRxDeltaMin
        managed object property"
    ::= { cucsAdaptorVnicStatsHistEntry 18 }

cucsAdaptorVnicStatsHistDroppedTx OBJECT-TYPE
    SYNTAX       Unsigned64
    MAX-ACCESS   read-only
    STATUS       current
    DESCRIPTION
        "Cisco UCS adaptor:VnicStatsHist:droppedTx managed
        object property"
    ::= { cucsAdaptorVnicStatsHistEntry 19 }

cucsAdaptorVnicStatsHistDroppedTxDelta OBJECT-TYPE
    SYNTAX       Unsigned64
    MAX-ACCESS   read-only
    STATUS       current
    DESCRIPTION
        "Cisco UCS adaptor:VnicStatsHist:droppedTxDelta
        managed object property"
    ::= { cucsAdaptorVnicStatsHistEntry 20 }

cucsAdaptorVnicStatsHistDroppedTxDeltaAvg OBJECT-TYPE
    SYNTAX       Unsigned64
    MAX-ACCESS   read-only
    STATUS       current
    DESCRIPTION
        "Cisco UCS adaptor:VnicStatsHist:droppedTxDeltaAvg
        managed object property"
    ::= { cucsAdaptorVnicStatsHistEntry 21 }

cucsAdaptorVnicStatsHistDroppedTxDeltaMax OBJECT-TYPE
    SYNTAX       Unsigned64
    MAX-ACCESS   read-only
    STATUS       current
    DESCRIPTION
        "Cisco UCS adaptor:VnicStatsHist:droppedTxDeltaMax
        managed object property"
    ::= { cucsAdaptorVnicStatsHistEntry 22 }

cucsAdaptorVnicStatsHistDroppedTxDeltaMin OBJECT-TYPE
    SYNTAX       Unsigned64
    MAX-ACCESS   read-only
    STATUS       current
    DESCRIPTION
        "Cisco UCS adaptor:VnicStatsHist:droppedTxDeltaMin
        managed object property"
    ::= { cucsAdaptorVnicStatsHistEntry 23 }

cucsAdaptorVnicStatsHistErrorsRx OBJECT-TYPE
    SYNTAX       Unsigned64
    MAX-ACCESS   read-only
    STATUS       current
    DESCRIPTION
        "Cisco UCS adaptor:VnicStatsHist:errorsRx managed object property"
    ::= { cucsAdaptorVnicStatsHistEntry 24 }

cucsAdaptorVnicStatsHistErrorsRxDelta OBJECT-TYPE
    SYNTAX       Unsigned64
    MAX-ACCESS   read-only
    STATUS       current
    DESCRIPTION
        "Cisco UCS adaptor:VnicStatsHist:errorsRxDelta
        managed object property"
    ::= { cucsAdaptorVnicStatsHistEntry 25 }

cucsAdaptorVnicStatsHistErrorsRxDeltaAvg OBJECT-TYPE
    SYNTAX       Unsigned64
    MAX-ACCESS   read-only
    STATUS       current
    DESCRIPTION
        "Cisco UCS adaptor:VnicStatsHist:errorsRxDeltaAvg
        managed object property"
    ::= { cucsAdaptorVnicStatsHistEntry 26 }

cucsAdaptorVnicStatsHistErrorsRxDeltaMax OBJECT-TYPE
    SYNTAX       Unsigned64
    MAX-ACCESS   read-only
    STATUS       current
    DESCRIPTION
        "Cisco UCS adaptor:VnicStatsHist:errorsRxDeltaMax
        managed object property"
    ::= { cucsAdaptorVnicStatsHistEntry 27 }

cucsAdaptorVnicStatsHistErrorsRxDeltaMin OBJECT-TYPE
    SYNTAX       Unsigned64
    MAX-ACCESS   read-only
    STATUS       current
    DESCRIPTION
        "Cisco UCS adaptor:VnicStatsHist:errorsRxDeltaMin
        managed object property"
    ::= { cucsAdaptorVnicStatsHistEntry 28 }

cucsAdaptorVnicStatsHistErrorsTx OBJECT-TYPE
    SYNTAX       Unsigned64
    MAX-ACCESS   read-only
    STATUS       current
    DESCRIPTION
        "Cisco UCS adaptor:VnicStatsHist:errorsTx managed object property"
    ::= { cucsAdaptorVnicStatsHistEntry 29 }

cucsAdaptorVnicStatsHistErrorsTxDelta OBJECT-TYPE
    SYNTAX       Unsigned64
    MAX-ACCESS   read-only
    STATUS       current
    DESCRIPTION
        "Cisco UCS adaptor:VnicStatsHist:errorsTxDelta
        managed object property"
    ::= { cucsAdaptorVnicStatsHistEntry 30 }

cucsAdaptorVnicStatsHistErrorsTxDeltaAvg OBJECT-TYPE
    SYNTAX       Unsigned64
    MAX-ACCESS   read-only
    STATUS       current
    DESCRIPTION
        "Cisco UCS adaptor:VnicStatsHist:errorsTxDeltaAvg
        managed object property"
    ::= { cucsAdaptorVnicStatsHistEntry 31 }

cucsAdaptorVnicStatsHistErrorsTxDeltaMax OBJECT-TYPE
    SYNTAX       Unsigned64
    MAX-ACCESS   read-only
    STATUS       current
    DESCRIPTION
        "Cisco UCS adaptor:VnicStatsHist:errorsTxDeltaMax
        managed object property"
    ::= { cucsAdaptorVnicStatsHistEntry 32 }

cucsAdaptorVnicStatsHistErrorsTxDeltaMin OBJECT-TYPE
    SYNTAX       Unsigned64
    MAX-ACCESS   read-only
    STATUS       current
    DESCRIPTION
        "Cisco UCS adaptor:VnicStatsHist:errorsTxDeltaMin
        managed object property"
    ::= { cucsAdaptorVnicStatsHistEntry 33 }

cucsAdaptorVnicStatsHistId OBJECT-TYPE
    SYNTAX       Unsigned64
    MAX-ACCESS   read-only
    STATUS       current
    DESCRIPTION
        "Cisco UCS adaptor:VnicStatsHist:id managed object property"
    ::= { cucsAdaptorVnicStatsHistEntry 34 }

cucsAdaptorVnicStatsHistMostRecent OBJECT-TYPE
    SYNTAX       TruthValue
    MAX-ACCESS   read-only
    STATUS       current
    DESCRIPTION
        "Cisco UCS adaptor:VnicStatsHist:mostRecent managed
        object property"
    ::= { cucsAdaptorVnicStatsHistEntry 35 }

cucsAdaptorVnicStatsHistPacketsRx OBJECT-TYPE
    SYNTAX       Unsigned64
    MAX-ACCESS   read-only
    STATUS       current
    DESCRIPTION
        "Cisco UCS adaptor:VnicStatsHist:packetsRx managed
        object property"
    ::= { cucsAdaptorVnicStatsHistEntry 36 }

cucsAdaptorVnicStatsHistPacketsRxDelta OBJECT-TYPE
    SYNTAX       Unsigned64
    MAX-ACCESS   read-only
    STATUS       current
    DESCRIPTION
        "Cisco UCS adaptor:VnicStatsHist:packetsRxDelta
        managed object property"
    ::= { cucsAdaptorVnicStatsHistEntry 37 }

cucsAdaptorVnicStatsHistPacketsRxDeltaAvg OBJECT-TYPE
    SYNTAX       Unsigned64
    MAX-ACCESS   read-only
    STATUS       current
    DESCRIPTION
        "Cisco UCS adaptor:VnicStatsHist:packetsRxDeltaAvg
        managed object property"
    ::= { cucsAdaptorVnicStatsHistEntry 38 }

cucsAdaptorVnicStatsHistPacketsRxDeltaMax OBJECT-TYPE
    SYNTAX       Unsigned64
    MAX-ACCESS   read-only
    STATUS       current
    DESCRIPTION
        "Cisco UCS adaptor:VnicStatsHist:packetsRxDeltaMax
        managed object property"
    ::= { cucsAdaptorVnicStatsHistEntry 39 }

cucsAdaptorVnicStatsHistPacketsRxDeltaMin OBJECT-TYPE
    SYNTAX       Unsigned64
    MAX-ACCESS   read-only
    STATUS       current
    DESCRIPTION
        "Cisco UCS adaptor:VnicStatsHist:packetsRxDeltaMin
        managed object property"
    ::= { cucsAdaptorVnicStatsHistEntry 40 }

cucsAdaptorVnicStatsHistPacketsTx OBJECT-TYPE
    SYNTAX       Unsigned64
    MAX-ACCESS   read-only
    STATUS       current
    DESCRIPTION
        "Cisco UCS adaptor:VnicStatsHist:packetsTx managed
        object property"
    ::= { cucsAdaptorVnicStatsHistEntry 41 }

cucsAdaptorVnicStatsHistPacketsTxDelta OBJECT-TYPE
    SYNTAX       Unsigned64
    MAX-ACCESS   read-only
    STATUS       current
    DESCRIPTION
        "Cisco UCS adaptor:VnicStatsHist:packetsTxDelta
        managed object property"
    ::= { cucsAdaptorVnicStatsHistEntry 42 }

cucsAdaptorVnicStatsHistPacketsTxDeltaAvg OBJECT-TYPE
    SYNTAX       Unsigned64
    MAX-ACCESS   read-only
    STATUS       current
    DESCRIPTION
        "Cisco UCS adaptor:VnicStatsHist:packetsTxDeltaAvg
        managed object property"
    ::= { cucsAdaptorVnicStatsHistEntry 43 }

cucsAdaptorVnicStatsHistPacketsTxDeltaMax OBJECT-TYPE
    SYNTAX       Unsigned64
    MAX-ACCESS   read-only
    STATUS       current
    DESCRIPTION
        "Cisco UCS adaptor:VnicStatsHist:packetsTxDeltaMax
        managed object property"
    ::= { cucsAdaptorVnicStatsHistEntry 44 }

cucsAdaptorVnicStatsHistPacketsTxDeltaMin OBJECT-TYPE
    SYNTAX       Unsigned64
    MAX-ACCESS   read-only
    STATUS       current
    DESCRIPTION
        "Cisco UCS adaptor:VnicStatsHist:packetsTxDeltaMin
        managed object property"
    ::= { cucsAdaptorVnicStatsHistEntry 45 }

cucsAdaptorVnicStatsHistSuspect OBJECT-TYPE
    SYNTAX       TruthValue
    MAX-ACCESS   read-only
    STATUS       current
    DESCRIPTION
        "Cisco UCS adaptor:VnicStatsHist:suspect managed object property"
    ::= { cucsAdaptorVnicStatsHistEntry 46 }

cucsAdaptorVnicStatsHistThresholded OBJECT-TYPE
    SYNTAX       CucsAdaptorVnicStatsHistThresholded
    MAX-ACCESS   read-only
    STATUS       current
    DESCRIPTION
        "Cisco UCS adaptor:VnicStatsHist:thresholded managed
        object property"
    ::= { cucsAdaptorVnicStatsHistEntry 47 }

cucsAdaptorVnicStatsHistTimeCollected OBJECT-TYPE
    SYNTAX       DateAndTime
    MAX-ACCESS   read-only
    STATUS       current
    DESCRIPTION
        "Cisco UCS adaptor:VnicStatsHist:timeCollected
        managed object property"
    ::= { cucsAdaptorVnicStatsHistEntry 48 }

cucsAdaptorVsanTable OBJECT-TYPE
    SYNTAX           SEQUENCE OF CucsAdaptorVsanEntry
    MAX-ACCESS       not-accessible
    STATUS           current
    DESCRIPTION
        "Cisco UCS adaptor:Vsan managed object table"
    ::= { cucsAdaptorObjects 89 }

cucsAdaptorVsanEntry OBJECT-TYPE
    SYNTAX           CucsAdaptorVsanEntry
    MAX-ACCESS       not-accessible
    STATUS           current
    DESCRIPTION
        "Entry for the cucsAdaptorVsanTable table."
    INDEX { cucsAdaptorVsanInstanceId }
    ::= { cucsAdaptorVsanTable 1 }

CucsAdaptorVsanEntry ::= SEQUENCE {
    cucsAdaptorVsanInstanceId                                        CucsManagedObjectId,
    cucsAdaptorVsanDn                                                CucsManagedObjectDn,
    cucsAdaptorVsanRn                                                SnmpAdminString,
    cucsAdaptorVsanEpDn                                              SnmpAdminString,
    cucsAdaptorVsanFcoeVlan                                          Gauge32,
    cucsAdaptorVsanId                                                Gauge32,
    cucsAdaptorVsanIfRole                                            CucsFabricVnetEpIfRole,
    cucsAdaptorVsanIfType                                            CucsNetworkVnetEpIfType,
    cucsAdaptorVsanLc                                                CucsFsmLifecycle,
    cucsAdaptorVsanLocale                                            CucsFabricVnetEpLocale,
    cucsAdaptorVsanName                                              SnmpAdminString,
    cucsAdaptorVsanPeerDn                                            SnmpAdminString,
    cucsAdaptorVsanSwitchId                                          CucsNetworkSwitchId,
    cucsAdaptorVsanTransport                                         CucsFabricAVsanTransport,
    cucsAdaptorVsanType                                              CucsFabricAVsanType,
    cucsAdaptorVsanOperState                                         CucsFabricVsanOperState,
    cucsAdaptorVsanZoningState                                       CucsFabricZoningState,
    cucsAdaptorVsanPolicyOwner                                       CucsFabricVnetEpPolicyOwner
}

cucsAdaptorVsanInstanceId OBJECT-TYPE
    SYNTAX       CucsManagedObjectId
    MAX-ACCESS   not-accessible
    STATUS       current
    DESCRIPTION
        "Instance identifier of the managed object."
    ::= { cucsAdaptorVsanEntry 1 }

cucsAdaptorVsanDn OBJECT-TYPE
    SYNTAX       CucsManagedObjectDn
    MAX-ACCESS   read-only
    STATUS       current
    DESCRIPTION
        "Cisco UCS adaptor:Vsan:dn managed object property"
    ::= { cucsAdaptorVsanEntry 2 }

cucsAdaptorVsanRn OBJECT-TYPE
    SYNTAX       SnmpAdminString
    MAX-ACCESS   read-only
    STATUS       current
    DESCRIPTION
        "Cisco UCS adaptor:Vsan:rn managed object property"
    ::= { cucsAdaptorVsanEntry 3 }

cucsAdaptorVsanEpDn OBJECT-TYPE
    SYNTAX       SnmpAdminString
    MAX-ACCESS   read-only
    STATUS       current
    DESCRIPTION
        "Cisco UCS adaptor:Vsan:epDn managed object property"
    ::= { cucsAdaptorVsanEntry 4 }

cucsAdaptorVsanFcoeVlan OBJECT-TYPE
    SYNTAX       Gauge32
    MAX-ACCESS   read-only
    STATUS       current
    DESCRIPTION
        "Cisco UCS adaptor:Vsan:fcoeVlan managed object property"
    ::= { cucsAdaptorVsanEntry 5 }

cucsAdaptorVsanId OBJECT-TYPE
    SYNTAX       Gauge32
    MAX-ACCESS   read-only
    STATUS       current
    DESCRIPTION
        "Cisco UCS adaptor:Vsan:id managed object property"
    ::= { cucsAdaptorVsanEntry 6 }

cucsAdaptorVsanIfRole OBJECT-TYPE
    SYNTAX       CucsFabricVnetEpIfRole
    MAX-ACCESS   read-only
    STATUS       current
    DESCRIPTION
        "Cisco UCS adaptor:Vsan:ifRole managed object property"
    ::= { cucsAdaptorVsanEntry 7 }

cucsAdaptorVsanIfType OBJECT-TYPE
    SYNTAX       CucsNetworkVnetEpIfType
    MAX-ACCESS   read-only
    STATUS       current
    DESCRIPTION
        "Cisco UCS adaptor:Vsan:ifType managed object property"
    ::= { cucsAdaptorVsanEntry 8 }

cucsAdaptorVsanLc OBJECT-TYPE
    SYNTAX       CucsFsmLifecycle
    MAX-ACCESS   read-only
    STATUS       current
    DESCRIPTION
        "Cisco UCS adaptor:Vsan:lc managed object property"
    ::= { cucsAdaptorVsanEntry 9 }

cucsAdaptorVsanLocale OBJECT-TYPE
    SYNTAX       CucsFabricVnetEpLocale
    MAX-ACCESS   read-only
    STATUS       current
    DESCRIPTION
        "Cisco UCS adaptor:Vsan:locale managed object property"
    ::= { cucsAdaptorVsanEntry 10 }

cucsAdaptorVsanName OBJECT-TYPE
    SYNTAX       SnmpAdminString
    MAX-ACCESS   read-only
    STATUS       current
    DESCRIPTION
        "Cisco UCS adaptor:Vsan:name managed object property"
    ::= { cucsAdaptorVsanEntry 11 }

cucsAdaptorVsanPeerDn OBJECT-TYPE
    SYNTAX       SnmpAdminString
    MAX-ACCESS   read-only
    STATUS       current
    DESCRIPTION
        "Cisco UCS adaptor:Vsan:peerDn managed object property"
    ::= { cucsAdaptorVsanEntry 12 }

cucsAdaptorVsanSwitchId OBJECT-TYPE
    SYNTAX       CucsNetworkSwitchId
    MAX-ACCESS   read-only
    STATUS       current
    DESCRIPTION
        "Cisco UCS adaptor:Vsan:switchId managed object property"
    ::= { cucsAdaptorVsanEntry 13 }

cucsAdaptorVsanTransport OBJECT-TYPE
    SYNTAX       CucsFabricAVsanTransport
    MAX-ACCESS   read-only
    STATUS       current
    DESCRIPTION
        "Cisco UCS adaptor:Vsan:transport managed object property"
    ::= { cucsAdaptorVsanEntry 14 }

cucsAdaptorVsanType OBJECT-TYPE
    SYNTAX       CucsFabricAVsanType
    MAX-ACCESS   read-only
    STATUS       current
    DESCRIPTION
        "Cisco UCS adaptor:Vsan:type managed object property"
    ::= { cucsAdaptorVsanEntry 15 }

cucsAdaptorVsanOperState OBJECT-TYPE
    SYNTAX       CucsFabricVsanOperState
    MAX-ACCESS   read-only
    STATUS       current
    DESCRIPTION
        "Cisco UCS adaptor:Vsan:operState managed object property"
    ::= { cucsAdaptorVsanEntry 16 }

cucsAdaptorVsanZoningState OBJECT-TYPE
    SYNTAX       CucsFabricZoningState
    MAX-ACCESS   read-only
    STATUS       current
    DESCRIPTION
        "Cisco UCS adaptor:Vsan:zoningState managed object property"
    ::= { cucsAdaptorVsanEntry 17 }

cucsAdaptorVsanPolicyOwner OBJECT-TYPE
    SYNTAX       CucsFabricVnetEpPolicyOwner
    MAX-ACCESS   read-only
    STATUS       current
    DESCRIPTION
        "Cisco UCS adaptor:Vsan:policyOwner managed object property"
    ::= { cucsAdaptorVsanEntry 19 }

END
