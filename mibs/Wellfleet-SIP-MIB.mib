Wellfleet-SIP-MIB DEFINITIONS ::= BEGIN

-- Created by mdl2asn version 3.1
-- Creation date: Wed Aug 30 16:47:34 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfSipGroup
        FROM Wellfleet-COMMON-MIB;

    wfSipPlcpGroup	OBJECT IDENTIFIER ::= { wfSipGroup 2 }

    wfSipL2 OBJECT-TYPE
        SYNTAX	SEQUENCE OF WfSipL2Entry
        ACCESS	not-accessible
        STATUS	mandatory
        DESCRIPTION
                "The SIP L2 Table"
        ::= { wfSipGroup 1 }

    wfSipL2Entry OBJECT-TYPE
        SYNTAX	WfSipL2Entry
        ACCESS	not-accessible
        STATUS	mandatory
        DESCRIPTION
                "per circuit SIP Level 2 objects - wfSipL2Index
                corresponds to Wellfleet circuit number"
        INDEX	{ wfSipL2Index }
        ::= { wfSipL2 1 }

    WfSipL2Entry ::= SEQUENCE {
    	    wfSipL2Index
    		INTEGER,
    	    wfSipL2ReceivedCounts
    		Counter,
    	    wfSipL2SentCounts
    		Counter,
    	    wfSipHcsOrCRCErrors
    		Counter,
    	    wfSipL2PayloadLengthErrors
    		Counter,
    	    wfSipL2SequenceNumberErrors
    		Counter,
    	    wfSipL2MidCurrentlyActiveErrors
    		Counter,
    	    wfSipL2BomOrSSMsMIDErrors
    		Counter,
    	    wfSipL2EomsMIDErrors
    		Counter
        }

    wfSipL2Index OBJECT-TYPE
        SYNTAX	INTEGER(1..1024)
        ACCESS	read-only
        STATUS	mandatory
        DESCRIPTION
                "this corresponds to the Wellfleet circuit number"
        ::= { wfSipL2Entry 1 }

    wfSipL2ReceivedCounts OBJECT-TYPE
        SYNTAX	Counter
        ACCESS	read-only
        STATUS	mandatory
        DESCRIPTION
                "total of unerrored received SIP L2 PDUs"
        ::= { wfSipL2Entry 2 }

    wfSipL2SentCounts OBJECT-TYPE
        SYNTAX	Counter
        ACCESS	read-only
        STATUS	mandatory
        DESCRIPTION
                "total of unerrored SIP L2 PDU's sent across the SNI"
        ::= { wfSipL2Entry 3 }

    wfSipHcsOrCRCErrors OBJECT-TYPE
        SYNTAX	Counter
        ACCESS	read-only
        STATUS	mandatory
        DESCRIPTION
                "total SIP L2 PDUs with HCS or CRC errors"
        ::= { wfSipL2Entry 4 }

    wfSipL2PayloadLengthErrors OBJECT-TYPE
        SYNTAX	Counter
        ACCESS	read-only
        STATUS	mandatory
        DESCRIPTION
                "total SIP L2 PDUs with length errors"
        ::= { wfSipL2Entry 5 }

    wfSipL2SequenceNumberErrors OBJECT-TYPE
        SYNTAX	Counter
        ACCESS	read-only
        STATUS	mandatory
        DESCRIPTION
                "total SIP L2 PDUs with unexpected sequence numbers"
        ::= { wfSipL2Entry 6 }

    wfSipL2MidCurrentlyActiveErrors OBJECT-TYPE
        SYNTAX	Counter
        ACCESS	read-only
        STATUS	mandatory
        DESCRIPTION
                "number of SIP L2 PDUs with BOMs previously started"
        ::= { wfSipL2Entry 7 }

    wfSipL2BomOrSSMsMIDErrors OBJECT-TYPE
        SYNTAX	Counter
        ACCESS	read-only
        STATUS	mandatory
        DESCRIPTION
                "number of SIP L2 PDUs with zero BOMs or SSMs not zero"
        ::= { wfSipL2Entry 8 }

    wfSipL2EomsMIDErrors OBJECT-TYPE
        SYNTAX	Counter
        ACCESS	read-only
        STATUS	mandatory
        DESCRIPTION
                "number of SIP L2 PDUs with zero EOMs or EOMs without BOMs"
        ::= { wfSipL2Entry 9 }

    wfSipDs1Plcp OBJECT-TYPE
        SYNTAX	SEQUENCE OF WfSipDs1PlcpEntry
        ACCESS	not-accessible
        STATUS	mandatory
        DESCRIPTION
                "The SIP DS1 PLCP Table"
        ::= { wfSipPlcpGroup 1 }

    wfSipDs1PlcpEntry OBJECT-TYPE
        SYNTAX	WfSipDs1PlcpEntry
        ACCESS	not-accessible
        STATUS	mandatory
        DESCRIPTION
                "per circuit DS1 PLCP objects - wfSipDs1PlcpIndex
                corresponds to Wellfleet circuit number"
        INDEX	{ wfSipDs1PlcpIndex }
        ::= { wfSipDs1Plcp 1 }

    WfSipDs1PlcpEntry ::= SEQUENCE {
    	    wfSipDs1PlcpIndex
    		INTEGER,
    	    wfSipDs1PlcpSEFs
    		Counter,
    	    wfSipDs1PlcpAlarmState
    		INTEGER,
    	    wfSipDs1PlcpUASs
    		Counter
        }

    wfSipDs1PlcpIndex OBJECT-TYPE
        SYNTAX	INTEGER(1..1024)
        ACCESS	read-only
        STATUS	mandatory
        DESCRIPTION
                "this corresponds to the Wellfleet circuit number"
        ::= { wfSipDs1PlcpEntry 1 }

    wfSipDs1PlcpSEFs OBJECT-TYPE
        SYNTAX	Counter
        ACCESS	read-only
        STATUS	mandatory
        DESCRIPTION
                "number of second intervals containing one or more
                severely errored seconds"
        ::= { wfSipDs1PlcpEntry 2 }

    wfSipDs1PlcpAlarmState OBJECT-TYPE
        SYNTAX	INTEGER {
    		    noalarm(1),
    		    receivedfarendalarm(2),
    		    incominglof(3)
    		}
        ACCESS	read-only
        STATUS	mandatory
        DESCRIPTION
                "alarm state"
        ::= { wfSipDs1PlcpEntry 3 }

    wfSipDs1PlcpUASs OBJECT-TYPE
        SYNTAX	Counter
        ACCESS	read-only
        STATUS	mandatory
        DESCRIPTION
                "number of second intervals containing one or more unavailable
                seconds"
        ::= { wfSipDs1PlcpEntry 4 }

    wfSipDs3Plcp OBJECT-TYPE
        SYNTAX	SEQUENCE OF WfSipDs3PlcpEntry
        ACCESS	not-accessible
        STATUS	mandatory
        DESCRIPTION
                "The SIP DS3 PLCP Table"
        ::= { wfSipPlcpGroup 2 }

    wfSipDs3PlcpEntry OBJECT-TYPE
        SYNTAX	WfSipDs3PlcpEntry
        ACCESS	not-accessible
        STATUS	mandatory
        DESCRIPTION
                "per circuit DS3 PLCP objects - wfSipDs3PlcpIndex
                corresponds to Wellfleet circuit number"
        INDEX	{ wfSipDs3PlcpIndex }
        ::= { wfSipDs3Plcp 1 }

    WfSipDs3PlcpEntry ::= SEQUENCE {
    	    wfSipDs3PlcpIndex
    		INTEGER,
    	    wfSipDs3PlcpSEFs
    		Counter,
    	    wfSipDs3PlcpAlarmState
    		INTEGER,
    	    wfSipDs3PlcpUASs
    		Counter
        }

    wfSipDs3PlcpIndex OBJECT-TYPE
        SYNTAX	INTEGER(1..1024)
        ACCESS	read-only
        STATUS	mandatory
        DESCRIPTION
                "this corresponds to the Wellfleet circuit number"
        ::= { wfSipDs3PlcpEntry 1 }

    wfSipDs3PlcpSEFs OBJECT-TYPE
        SYNTAX	Counter
        ACCESS	read-only
        STATUS	mandatory
        DESCRIPTION
                "number of second intervals containing one or more
                severely errored seconds"
        ::= { wfSipDs3PlcpEntry 2 }

    wfSipDs3PlcpAlarmState OBJECT-TYPE
        SYNTAX	INTEGER {
    		    noalarm(1),
    		    receivedfarendalarm(2),
    		    incominglof(3)
    		}
        ACCESS	read-only
        STATUS	mandatory
        DESCRIPTION
                "alarm state"
        ::= { wfSipDs3PlcpEntry 3 }

    wfSipDs3PlcpUASs OBJECT-TYPE
        SYNTAX	Counter
        ACCESS	read-only
        STATUS	mandatory
        DESCRIPTION
                "number of second intervals containing one or more unavailable
                seconds"
        ::= { wfSipDs3PlcpEntry 4 }

    END  -- Wellfleet-SIP-MIB
