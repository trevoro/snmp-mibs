-- *****************************************************************************
-- Unisphere-Data-COPS-MIB
--
-- Unisphere Networks Enterprise MIB
-- Common Open Policy Service (COPS) Protocol Layer MIB
--
-- Copyright (c) 2000, 2002 Unisphere Networks, Inc.  All Rights Reserved.
-- *****************************************************************************

Unisphere-Data-COPS-MIB DEFINITIONS ::= BEGIN

IMPORTS
    MODULE-IDENTITY, OBJECT-TYPE, Integer32, IpAddress, Counter32
        FROM SNMPv2-SMI
    MODULE-COMPLIANCE, OBJECT-GROUP
        FROM SNMPv2-CONF
    UsdName
        FROM Unisphere-Data-TC
    usDataMibs
        FROM Unisphere-Data-MIBs;

usdCopsProtocolMIB  MODULE-IDENTITY
    LAST-UPDATED "200201141901Z"  -- 14-Jan-02 02:01 PM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Common Open Policy Service (COPS) Protocol MIB for the Unisphere
        Networks enterprise."
    -- Revision History
    REVISION    "200201141901Z"  -- 14-Jan-02 02:01 PM EST  - RX 4.0
    DESCRIPTION
        "Expanded MIB to include following objects:
            usdCopsProtocolSessionLocalAddress,
            usdCopsProtocolSessionTransportRouterName "
    REVISION    "200002220000Z"  -- 22-Feb-00               - RX 2.0
    DESCRIPTION
        "Initial version of this MIB module."
    ::= { usDataMibs 37 }


-- +++++++++++++++++++++++++++++++++++++++++++++++++++++++++++++++++++++++++++++
-- Managed objects
-- +++++++++++++++++++++++++++++++++++++++++++++++++++++++++++++++++++++++++++++

--
--  This MIB contains definitions needed for the COPS Protocol component.
--
usdCopsProtocolObjects    OBJECT IDENTIFIER ::= { usdCopsProtocolMIB 1 }

usdCopsProtocolCfg        OBJECT IDENTIFIER ::= { usdCopsProtocolObjects 1 }
usdCopsProtocolStatus     OBJECT IDENTIFIER ::= { usdCopsProtocolObjects 2 }
usdCopsProtocolStatistics OBJECT IDENTIFIER ::= { usdCopsProtocolObjects 3 }
usdCopsProtocolSession    OBJECT IDENTIFIER ::= { usdCopsProtocolObjects 4 }

--
-- Statistics Objects
--

usdCopsProtocolStatisticsScalars
        OBJECT IDENTIFIER ::= { usdCopsProtocolStatistics 1 }

usdCopsProtocolSessionsCreated  OBJECT-TYPE
    SYNTAX      Counter32
    MAX-ACCESS  read-only
    STATUS      current
    DESCRIPTION
        "Total number of COPS protocol sessions created."
    ::= { usdCopsProtocolStatisticsScalars 1 }

usdCopsProtocolSessionsDeleted  OBJECT-TYPE
    SYNTAX      Counter32
    MAX-ACCESS  read-only
    STATUS      current
    DESCRIPTION
        "The number of COPS protocol sessions deleted."
    ::= { usdCopsProtocolStatisticsScalars 2 }

usdCopsProtocolCurrentSessions  OBJECT-TYPE
    SYNTAX      Counter32
    MAX-ACCESS  read-only
    STATUS      current
    DESCRIPTION
        "The number of current COPS protocol sessions."
    ::= { usdCopsProtocolStatisticsScalars 3 }

usdCopsProtocolBytesReceived  OBJECT-TYPE
    SYNTAX      Counter32
    MAX-ACCESS  read-only
    STATUS      current
    DESCRIPTION
        "The number of bytes received by the COPS protocol layer."
    ::= { usdCopsProtocolStatisticsScalars 4 }

usdCopsProtocolPacketsReceived  OBJECT-TYPE
    SYNTAX      Counter32
    MAX-ACCESS  read-only
    STATUS      current
    DESCRIPTION
        "The number of packets received by the COPS protocol layer."
    ::= { usdCopsProtocolStatisticsScalars 5 }

usdCopsProtocolBytesSent  OBJECT-TYPE
    SYNTAX      Counter32
    MAX-ACCESS  read-only
    STATUS      current
    DESCRIPTION
        "The number of bytes sent by the COPS protocol layer."
    ::= { usdCopsProtocolStatisticsScalars 6 }

usdCopsProtocolPacketsSent  OBJECT-TYPE
    SYNTAX      Counter32
    MAX-ACCESS  read-only
    STATUS      current
    DESCRIPTION
        "The number of packets sent by the COPS protocol layer."
    ::= { usdCopsProtocolStatisticsScalars 7 }

usdCopsProtocolKeepAlivesReceived  OBJECT-TYPE
    SYNTAX      Counter32
    MAX-ACCESS  read-only
    STATUS      current
    DESCRIPTION
        "The number keep alive packets received by the COPS protocol layer."
    ::= { usdCopsProtocolStatisticsScalars 8 }

usdCopsProtocolKeepAlivesSent  OBJECT-TYPE
    SYNTAX      Counter32
    MAX-ACCESS  read-only
    STATUS      current
    DESCRIPTION
        "The number of keep alive packets sent by the COPS protocol layer."
    ::= { usdCopsProtocolStatisticsScalars 9 }


--
--  Session Information
--
usdCopsProtocolSessionTable  OBJECT-TYPE
    SYNTAX      SEQUENCE OF UsdCopsProtocolSessionEntry
    MAX-ACCESS  not-accessible
    STATUS      current
    DESCRIPTION
        "The COPS protocol session information table."
    ::= { usdCopsProtocolSession 1 }

usdCopsProtocolSessionEntry  OBJECT-TYPE
    SYNTAX      UsdCopsProtocolSessionEntry
    MAX-ACCESS  not-accessible
    STATUS      current
    DESCRIPTION
        "An entry in the COPS protocol session information table."
    INDEX     { usdCopsProtocolSessionClientType }
    ::= { usdCopsProtocolSessionTable 1 }

UsdCopsProtocolSessionEntry ::= SEQUENCE {
    usdCopsProtocolSessionClientType            Integer32,
    usdCopsProtocolSessionRemoteAddress         IpAddress,
    usdCopsProtocolSessionRemotePort            Integer32,
    usdCopsProtocolSessionBytesReceived         Counter32,
    usdCopsProtocolSessionPacketsReceived       Counter32,
    usdCopsProtocolSessionBytesSent             Counter32,
    usdCopsProtocolSessionPacketsSent           Counter32,
    usdCopsProtocolSessionREQSent               Counter32,
    usdCopsProtocolSessionDECReceived           Counter32,
    usdCopsProtocolSessionRPTSent               Counter32,
    usdCopsProtocolSessionDRQSent               Counter32,
    usdCopsProtocolSessionSSQSent               Counter32,
    usdCopsProtocolSessionOPNSent               Counter32,
    usdCopsProtocolSessionCATReceived           Counter32,
    usdCopsProtocolSessionCCSent                Counter32,
    usdCopsProtocolSessionCCReceived            Counter32,
    usdCopsProtocolSessionSSCSent               Counter32,
    usdCopsProtocolSessionLocalAddress          IpAddress,
    usdCopsProtocolSessionTransportRouterName   UsdName }

usdCopsProtocolSessionClientType  OBJECT-TYPE
    SYNTAX      Integer32 (0..65535)
    MAX-ACCESS  not-accessible
    STATUS      current
    DESCRIPTION
        "The COPS client-type for which this entry information is valid."
    ::= { usdCopsProtocolSessionEntry 1 }

usdCopsProtocolSessionRemoteAddress  OBJECT-TYPE
    SYNTAX      IpAddress
    MAX-ACCESS  read-only
    STATUS      current
    DESCRIPTION
        "The IP address of the remote end of this session."
    ::= { usdCopsProtocolSessionEntry 2 }

usdCopsProtocolSessionRemotePort  OBJECT-TYPE
    SYNTAX      Integer32
    MAX-ACCESS  read-only
    STATUS      current
    DESCRIPTION
        "The remote port for this session."
    ::= { usdCopsProtocolSessionEntry 3 }

usdCopsProtocolSessionBytesReceived  OBJECT-TYPE
    SYNTAX      Counter32
    MAX-ACCESS  read-only
    STATUS      current
    DESCRIPTION
        "The number of bytes received by this session."
    ::= { usdCopsProtocolSessionEntry 4 }

usdCopsProtocolSessionPacketsReceived  OBJECT-TYPE
    SYNTAX      Counter32
    MAX-ACCESS  read-only
    STATUS      current
    DESCRIPTION
        "The number of packets received by this session."
    ::= { usdCopsProtocolSessionEntry 5 }

usdCopsProtocolSessionBytesSent  OBJECT-TYPE
    SYNTAX      Counter32
    MAX-ACCESS  read-only
    STATUS      current
    DESCRIPTION
        "The number of bytes sent on this session."
    ::= { usdCopsProtocolSessionEntry 6 }

usdCopsProtocolSessionPacketsSent  OBJECT-TYPE
    SYNTAX      Counter32
    MAX-ACCESS  read-only
    STATUS      current
    DESCRIPTION
        "The number of packets sent on this session."
    ::= { usdCopsProtocolSessionEntry 7 }

usdCopsProtocolSessionREQSent  OBJECT-TYPE
    SYNTAX      Counter32
    MAX-ACCESS  read-only
    STATUS      current
    DESCRIPTION
        "The number of REQ packets sent on this session."
    ::= { usdCopsProtocolSessionEntry 8 }

usdCopsProtocolSessionDECReceived  OBJECT-TYPE
    SYNTAX      Counter32
    MAX-ACCESS  read-only
    STATUS      current
    DESCRIPTION
        "The number of DEC packets received on this session."
    ::= { usdCopsProtocolSessionEntry 9 }

usdCopsProtocolSessionRPTSent  OBJECT-TYPE
    SYNTAX      Counter32
    MAX-ACCESS  read-only
    STATUS      current
    DESCRIPTION
        "The number of RPT packets sent on this session."
    ::= { usdCopsProtocolSessionEntry 10 }

usdCopsProtocolSessionDRQSent  OBJECT-TYPE
    SYNTAX      Counter32
    MAX-ACCESS  read-only
    STATUS      current
    DESCRIPTION
        "The number of DRQ packets sent on this session."
    ::= { usdCopsProtocolSessionEntry 11 }

usdCopsProtocolSessionSSQSent  OBJECT-TYPE
    SYNTAX      Counter32
    MAX-ACCESS  read-only
    STATUS      current
    DESCRIPTION
        "The number of SSQ packets sent on this session."
    ::= { usdCopsProtocolSessionEntry 12 }

usdCopsProtocolSessionOPNSent  OBJECT-TYPE
    SYNTAX      Counter32
    MAX-ACCESS  read-only
    STATUS      current
    DESCRIPTION
        "The number of OPN packets sent on this session."
    ::= { usdCopsProtocolSessionEntry 13 }

usdCopsProtocolSessionCATReceived  OBJECT-TYPE
    SYNTAX      Counter32
    MAX-ACCESS  read-only
    STATUS      current
    DESCRIPTION
        "The number of CAT packets received on this session."
    ::= { usdCopsProtocolSessionEntry 14 }

usdCopsProtocolSessionCCSent  OBJECT-TYPE
    SYNTAX      Counter32
    MAX-ACCESS  read-only
    STATUS      current
    DESCRIPTION
        "The number of CC packets sent on this session."
    ::= { usdCopsProtocolSessionEntry 15 }

usdCopsProtocolSessionCCReceived  OBJECT-TYPE
    SYNTAX      Counter32
    MAX-ACCESS  read-only
    STATUS      current
    DESCRIPTION
        "The number of CC packets received on this session."
    ::= { usdCopsProtocolSessionEntry 16 }

usdCopsProtocolSessionSSCSent  OBJECT-TYPE
    SYNTAX      Counter32
    MAX-ACCESS  read-only
    STATUS      current
    DESCRIPTION
        "The number of SSC packets sent on this session."
    ::= { usdCopsProtocolSessionEntry 17 }


usdCopsProtocolSessionLocalAddress  OBJECT-TYPE
    SYNTAX      IpAddress
    MAX-ACCESS  read-only
    STATUS      current
    DESCRIPTION
        "The IP address of the local end of this session."
    ::= { usdCopsProtocolSessionEntry 18 }

usdCopsProtocolSessionTransportRouterName  OBJECT-TYPE
    SYNTAX      UsdName
    MAX-ACCESS  read-only
    STATUS      current
    DESCRIPTION
        "The administratively assigned name of the transport router for this
        session."
    ::= { usdCopsProtocolSessionEntry 19 }


-- +++++++++++++++++++++++++++++++++++++++++++++++++++++++++++++++++++++++++++++
-- Notification control objects
-- +++++++++++++++++++++++++++++++++++++++++++++++++++++++++++++++++++++++++++++

-- No notifications are defined in this MIB. Placeholder follows.
-- usdCopsProtocolTrapControl   OBJECT IDENTIFIER ::= { usdCopsProtocolMIB 2 }

-- +++++++++++++++++++++++++++++++++++++++++++++++++++++++++++++++++++++++++++++
-- Notifications
-- +++++++++++++++++++++++++++++++++++++++++++++++++++++++++++++++++++++++++++++

-- No notifications are defined in this MIB. Placeholder follows.
-- The following two OBJECT IDENTIFIERS are used to define SNMPv2
-- Notifications that are easily translated into SNMPv1 Traps.
-- usdCopsProtocolTraps         OBJECT IDENTIFIER ::= { usdCopsProtocolMIB 3 }
-- usdCopsProtocolTrapPrefix    OBJECT IDENTIFIER ::= { usdCopsProtocolTraps 0 }


-- +++++++++++++++++++++++++++++++++++++++++++++++++++++++++++++++++++++++++++++
-- Conformance information
-- +++++++++++++++++++++++++++++++++++++++++++++++++++++++++++++++++++++++++++++

usdCopsProtocolMIBConformance   OBJECT IDENTIFIER
    ::= { usdCopsProtocolMIB 4 }
usdCopsProtocolMIBCompliances   OBJECT IDENTIFIER
    ::= { usdCopsProtocolMIBConformance 1 }
usdCopsProtocolMIBGroups        OBJECT IDENTIFIER
    ::= { usdCopsProtocolMIBConformance 2 }

-- compliance statements

usdCopsProtocolAuthCompliance MODULE-COMPLIANCE
    STATUS      obsolete
    DESCRIPTION
        "Current compliance statement for authentication clients implementing
        the Unisphere COPS Protocol MIB authentication functionality.  This
        statement became obsolete when the local address and transport router
        name objects were add."
    MODULE   -- this module
    MANDATORY-GROUPS {
        usdCopsProtocolGroup }
    ::= { usdCopsProtocolMIBCompliances 1 }                            -- RX 2.0

usdCopsProtocolAuthCompliance2 MODULE-COMPLIANCE
    STATUS      current
    DESCRIPTION
        "The compliance statement for authentication clients implementing the
        Unisphere COPS Protocol MIB authentication functionality."
    MODULE   -- this module
    MANDATORY-GROUPS {
        usdCopsProtocolGroup2 }
    ::= { usdCopsProtocolMIBCompliances 2 }                            -- RX 4.0

-- units of conformance

usdCopsProtocolGroup OBJECT-GROUP
    OBJECTS {
        usdCopsProtocolSessionsCreated,
        usdCopsProtocolSessionsDeleted,
        usdCopsProtocolCurrentSessions,
        usdCopsProtocolBytesReceived,
        usdCopsProtocolPacketsReceived,
        usdCopsProtocolBytesSent,
        usdCopsProtocolPacketsSent,
        usdCopsProtocolKeepAlivesReceived,
        usdCopsProtocolKeepAlivesSent,

        usdCopsProtocolSessionRemoteAddress,
        usdCopsProtocolSessionRemotePort,
        usdCopsProtocolSessionBytesReceived,
        usdCopsProtocolSessionPacketsReceived,
        usdCopsProtocolSessionBytesSent,
        usdCopsProtocolSessionPacketsSent,
        usdCopsProtocolSessionREQSent,
        usdCopsProtocolSessionDECReceived,
        usdCopsProtocolSessionRPTSent,
        usdCopsProtocolSessionDRQSent,
        usdCopsProtocolSessionSSQSent,
        usdCopsProtocolSessionOPNSent,
        usdCopsProtocolSessionCATReceived,
        usdCopsProtocolSessionCCSent,
        usdCopsProtocolSessionCCReceived,
        usdCopsProtocolSessionSSCSent }
    STATUS      obsolete
    DESCRIPTION
        "Obsolete basic collection of objects providing management of the COPS
        Protocol.  This group became obsolete when the local address and
        transport router name objects were add."
    ::= { usdCopsProtocolMIBGroups 1 }

usdCopsProtocolGroup2 OBJECT-GROUP
    OBJECTS {
        usdCopsProtocolSessionsCreated,
        usdCopsProtocolSessionsDeleted,
        usdCopsProtocolCurrentSessions,
        usdCopsProtocolBytesReceived,
        usdCopsProtocolPacketsReceived,
        usdCopsProtocolBytesSent,
        usdCopsProtocolPacketsSent,
        usdCopsProtocolKeepAlivesReceived,
        usdCopsProtocolKeepAlivesSent,

        usdCopsProtocolSessionRemoteAddress,
        usdCopsProtocolSessionRemotePort,
        usdCopsProtocolSessionBytesReceived,
        usdCopsProtocolSessionPacketsReceived,
        usdCopsProtocolSessionBytesSent,
        usdCopsProtocolSessionPacketsSent,
        usdCopsProtocolSessionREQSent,
        usdCopsProtocolSessionDECReceived,
        usdCopsProtocolSessionRPTSent,
        usdCopsProtocolSessionDRQSent,
        usdCopsProtocolSessionSSQSent,
        usdCopsProtocolSessionOPNSent,
        usdCopsProtocolSessionCATReceived,
        usdCopsProtocolSessionCCSent,
        usdCopsProtocolSessionCCReceived,
        usdCopsProtocolSessionSSCSent,
        usdCopsProtocolSessionLocalAddress,
        usdCopsProtocolSessionTransportRouterName }
    STATUS      current
    DESCRIPTION
        "The basic collection of objects providing management of the COPS
        Protocol."
    ::= { usdCopsProtocolMIBGroups 2 }

END
