--			Ascend mibtime MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBTIME-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibtimeDateProfile  OBJECT IDENTIFIER ::= { configuration 130}

	-- The mibtimeDateProfile table
	--
	-- This table contains parameters for the mibtimeDateProfile profile
	--

    mibtimeDateProfileTable	OBJECT-TYPE
	SYNTAX		SEQUENCE OF MibtimeDateProfileEntry
	ACCESS		not-accessible
	STATUS		mandatory
	DESCRIPTION	"A list of mibtimeDateProfile profile entries."
	::= { mibtimeDateProfile 1 }

    mibtimeDateProfileEntry	OBJECT-TYPE
	SYNTAX		MibtimeDateProfileEntry
	ACCESS		not-accessible
	STATUS		mandatory
	DESCRIPTION	"A mibtimeDateProfile entry containing objects that
			 maps to the parameters of mibtimeDateProfile profile."
	INDEX		{ timeDateProfile-Index-o }
	::= { mibtimeDateProfileTable 1 }

    MibtimeDateProfileEntry ::=
	SEQUENCE {
	    timeDateProfile-Index-o
		INTEGER,
	    timeDateProfile-Time-Hour
		INTEGER,
	    timeDateProfile-Time-Minute
		INTEGER,
	    timeDateProfile-Time-Second
		INTEGER,
	    timeDateProfile-Date-Weekday
		INTEGER,
	    timeDateProfile-Date-Month
		INTEGER,
	    timeDateProfile-Date-Year
		INTEGER,
	    timeDateProfile-Date-Day
		INTEGER,
	    timeDateProfile-Action-o
		INTEGER
	}

    timeDateProfile-Index-o	OBJECT-TYPE
	SYNTAX	INTEGER
	ACCESS	read-only
	STATUS	mandatory
	DESCRIPTION	""
	::= { mibtimeDateProfileEntry 1 }

    timeDateProfile-Time-Hour	OBJECT-TYPE
	SYNTAX	INTEGER
	ACCESS	read-write
	STATUS	mandatory
	DESCRIPTION	"Number of hours, in 24 hour format, where midnight is a zero, etc."
	::= { mibtimeDateProfileEntry 2 }

    timeDateProfile-Time-Minute	OBJECT-TYPE
	SYNTAX	INTEGER
	ACCESS	read-write
	STATUS	mandatory
	DESCRIPTION	"Number of minutes since last hour."
	::= { mibtimeDateProfileEntry 3 }

    timeDateProfile-Time-Second	OBJECT-TYPE
	SYNTAX	INTEGER
	ACCESS	read-write
	STATUS	mandatory
	DESCRIPTION	"Number of seconds since last minute."
	::= { mibtimeDateProfileEntry 4 }

    timeDateProfile-Date-Weekday	OBJECT-TYPE
	SYNTAX	INTEGER {
		    sunday (2),
		    monday (3),
		    tuesday (4),
		    wednesday (5),
		    thursday (6),
		    friday (7),
		    saturday (8)
		}
	ACCESS	read-only
	STATUS	mandatory
	DESCRIPTION	"The day of the week, where Sunday is a one, and Saturday is a seven."
	::= { mibtimeDateProfileEntry 5 }

    timeDateProfile-Date-Month	OBJECT-TYPE
	SYNTAX	INTEGER {
		    january (2),
		    february (3),
		    march (4),
		    april (5),
		    may (6),
		    june (7),
		    july (8),
		    august (9),
		    september (10),
		    october (11),
		    november (12),
		    december (13)
		}
	ACCESS	read-write
	STATUS	mandatory
	DESCRIPTION	"The month of the year (i.e. 1..12)."
	::= { mibtimeDateProfileEntry 6 }

    timeDateProfile-Date-Year	OBJECT-TYPE
	SYNTAX	INTEGER
	ACCESS	read-write
	STATUS	mandatory
	DESCRIPTION	"The year in 'yyyy' format should be in the range (1990 - 2089). The year in 'yy' format should be in the range (00 - 99). Year from (0 - 89) will be taken as (2000 - 2089) and (90 - 99) will be taken as (1990 - 1999)."
	::= { mibtimeDateProfileEntry 7 }

    timeDateProfile-Date-Day	OBJECT-TYPE
	SYNTAX	INTEGER
	ACCESS	read-write
	STATUS	mandatory
	DESCRIPTION	"The day in the month (i.e. 1..31)."
	::= { mibtimeDateProfileEntry 8 }

    timeDateProfile-Action-o	OBJECT-TYPE
	SYNTAX	INTEGER {
		    noAction (1),
		    createProfile (2),
		    deleteProfile (3)
		}
	ACCESS	read-write
	STATUS	mandatory
	DESCRIPTION	""
	::= { mibtimeDateProfileEntry 9 }

END
