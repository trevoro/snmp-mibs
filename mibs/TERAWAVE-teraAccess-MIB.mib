TERAWAVE-teraAccess-MIB DEFINITIONS ::= BEGIN
        -- Created by sml2mib compiler 
        IMPORTS

 enterprises,  OBJECT-TYPE,  Counter,  Gauge,  TimeTicks
        FROM RFC1155-SMI;

terawave OBJECT IDENTIFIER ::=  { enterprises 4513 }

     -- teraAccess (special)

teraAccess OBJECT IDENTIFIER ::=  { terawave 24 }

     -- teraUserProfilesTable

teraUserProfilesTable OBJECT-TYPE
     SYNTAX SEQUENCE OF TeraUserProfilesTableEntryType
     ACCESS not-accessible
     STATUS mandatory
     DESCRIPTION
          " table teraUserProfilesTable"
     ::= { teraAccess 1 }

teraUserProfileClear OBJECT-TYPE
          SYNTAX INTEGER
          ACCESS read-write
          STATUS mandatory
          DESCRIPTION
               " Next index to the table."
     ::= { teraUserProfilesTable 2 }
teraUserProfilesTableEntry OBJECT-TYPE
          SYNTAX TeraUserProfilesTableEntryType
          ACCESS not-accessible
          STATUS mandatory
          DESCRIPTION
               " table entry teraUserProfilesTableEntry "
          INDEX {                   teraUserProfileIndex }
     ::= { teraUserProfilesTable 1 }

TeraUserProfilesTableEntryType ::= SEQUENCE {
          teraUserProfileIndex   
             INTEGER,
          teraUserProfileName   
             OCTET STRING,
          teraUserProfilePassword   
             OCTET STRING,
          teraUserProfileAccessLevel   
             INTEGER,
          teraUserProfileStatus   
             INTEGER
}

teraUserProfileIndex OBJECT-TYPE
          SYNTAX INTEGER
          ACCESS read-only
          STATUS mandatory
          DESCRIPTION
               ""
          ::= { teraUserProfilesTableEntry 1 }

teraUserProfileName OBJECT-TYPE
          SYNTAX OCTET STRING
          ACCESS read-write
          STATUS mandatory
          DESCRIPTION
               ""
          ::= { teraUserProfilesTableEntry 2 }

teraUserProfilePassword OBJECT-TYPE
          SYNTAX OCTET STRING
          ACCESS read-write
          STATUS mandatory
          DESCRIPTION
               ""
          ::= { teraUserProfilesTableEntry 3 }

teraUserProfileAccessLevel OBJECT-TYPE
          SYNTAX INTEGER
                  {
                  admin(1),
                  oper(2),
                  test(3),
                  view(4)
                  }
          ACCESS read-write
          STATUS mandatory
          DESCRIPTION
               ""
          ::= { teraUserProfilesTableEntry 4 }

teraUserProfileStatus OBJECT-TYPE
          SYNTAX INTEGER
                  {
                  ok(1),
                  delete(2)
                  }
          ACCESS read-write
          STATUS mandatory
          DESCRIPTION
               ""
          ::= { teraUserProfilesTableEntry 5 }

END
