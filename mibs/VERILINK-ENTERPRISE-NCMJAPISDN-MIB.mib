VERILINK-ENTERPRISE-NCMJAPISDN-MIB


--              FORCE-INCLUDE <stdio.h>
--              FORCE-INCLUDE <prepc.h>
--              FORCE-INCLUDE <snmp/asn1.h>
--              FORCE-INCLUDE <snmp/mib.h>
--              FORCE-INCLUDE <snmp/snmp.h>
--              FORCE-INCLUDE <snmp/snmpstat.h>
--              FORCE-INCLUDE <snmp/buildpkt.h>
--              FORCE-INCLUDE "vl.h"
--              FORCE-INCLUDE "vkmib.h"
--              FORCE-INCLUDE "vktrap.h"
--              FORCE-INCLUDE "mib2.h"
--

	-- Created:  Latha Ganapathy in Sept, 1997.
	-- set up MIB-wide defaults
	-- all functions can use %n for object name and
	-- %t for object type, %p for parent name,
	-- %d for name of default-bearing node and %% for %

	  DEFINITIONS ::= BEGIN

     IMPORTS
	     DisplayString
		     FROM RFC1213-MIB
--              Gauge
--                     FROM RFC1155-SMI

	     OBJECT-TYPE
		     FROM RFC-1212
	     ncm-japisdn
		     FROM 
             VERILINK-ENTERPRISE-NCMALARM-MIB;

	     
 
     --  This MIB module uses the extended OBJECT-TYPE macro as
     --  defined in RFC 1212.
     --  This MIB module uses the TRAP-TYPE macro as
     --  defined in RFC 1215.
     --  enterprises{iso(1).org(3).dod(6).intrnet(1).pvt(4).entrprs(1).
     --                                                    vlnk(321).as2000(1).x }

     --  Please update verilink.mib whenever a new entry is added
     --  or deleted

     


--Japanese  PRI Port Configuration Table


        ncmJapPRIPortConfigTable OBJECT-TYPE
        SYNTAX  SEQUENCE OF NcmJapPRIPortConfigEntry
        ACCESS  not-accessible
        STATUS  mandatory
	DESCRIPTION
        "The Japanese PRI Port Configuration table  ."

        --DEFAULT test-function    japisdn-test
        --DEFAULT next-function    japisdn-next

         ::= { ncm-japisdn 8000 }


        ncmJapPRIPortConfigEntry OBJECT-TYPE
        SYNTAX  NcmJapPRIPortConfigEntry
        ACCESS  not-accessible
        STATUS  mandatory
        DESCRIPTION
        "An entry in the Japanese PRI Port Configuration table  ."
         INDEX   { ncmJapPRIPortNIDIndex, ncmJapPRIPortLineIndex }
         ::= { ncmJapPRIPortConfigTable 1 }


         NcmJapPRIPortConfigEntry ::=
         SEQUENCE {
	
	   ncmJapPRIPortNIDIndex
		 INTEGER,
           ncmJapPRIPortLineIndex
                 INTEGER,
           ncmJapPRIPortInService 
                 INTEGER,
           ncmJapPRIPortNFASMode 
                 INTEGER,
           ncmJapPRIPortDChanMode				
                 INTEGER,
           ncmJapPRIPortDChanBits				
                 INTEGER,
	   ncmJapPRIPortTimeslotMap
		 DisplayString,
           ncmJapPRIPortSwitchType				
                INTEGER,
           ncmJapPRIPortOwnNumPlan				
                INTEGER,
           ncmJapPRIPortOwnNumType				
                INTEGER,
           ncmJapPRIPortSecurityLevel				
                INTEGER,
	   ncmJapPRIPortConfigStatus
		INTEGER,
           ncmJapPRIPortSetConfig
		INTEGER,
	   ncmJapPRICallProfCallRefCount
		INTEGER,
	   ncmJapPRIL2AutoEstablish
		 INTEGER
                }


	 ncmJapPRIPortNIDIndex OBJECT-TYPE
          SYNTAX  INTEGER (1..'7fffffff'h)
          ACCESS  read-only
          STATUS  mandatory
          DESCRIPTION
         "The object specifies the node id of the node."
	  --DEFAULT get-function    get-ncmJapPRINIDIndex      
          ::= { ncmJapPRIPortConfigEntry 1 }



	 ncmJapPRIPortLineIndex OBJECT-TYPE
          SYNTAX  INTEGER (1..'7fffffff'h)
          ACCESS  read-only
          STATUS  mandatory
          DESCRIPTION
         "The index value which uniquely identifies  the
          interface to which this entry is applicable."
	  --DEFAULT get-function    get-ncmJapPRILineIndex  
           
          ::= { ncmJapPRIPortConfigEntry 2 }
 
 
         ncmJapPRIPortInService OBJECT-TYPE
          SYNTAX INTEGER {
           
                       no(1),
                       yes(2)
               } 
          ACCESS read-write
          STATUS mandatory
	
	  DESCRIPTION
          "The object specifies whether the PRI Port is in service 
           or not."
 
	  --DEFAULT get-function    get-ncmPRIPortInService
	  --DEFAULT set-function    set-ncmPRIPortInService

          ::= { ncmJapPRIPortConfigEntry 3 }
 
 

         ncmJapPRIPortNFASMode OBJECT-TYPE
          SYNTAX INTEGER {
           
                       no-Nfas(1),
                       nfas-No-Backup(2),
		       nfas-Backup(3)	
               } 
          ACCESS read-write
          STATUS mandatory

	  
          DESCRIPTION
          "The variable specifies the pri NFAS mode." 

	  --DEFAULT get-function    get-ncmPRIPortNFASMode
	  --DEFAULT set-function    set-ncmPRIPortNFASMode

          ::= { ncmJapPRIPortConfigEntry 4 }
 
 
         ncmJapPRIPortDChanMode OBJECT-TYPE
          SYNTAX INTEGER {
           
                       normal(1),
                       inverted(2)
               } 
          ACCESS read-write
          STATUS mandatory

	  DESCRIPTION
          "The variable specifies the pri D-channel mode."

	  --DEFAULT get-function    get-ncmPRIPortDChanMode
	  --DEFAULT set-function    set-ncmPRIPortDChanMode
 
          ::= { ncmJapPRIPortConfigEntry 5 }
 

         ncmJapPRIPortDChanBits OBJECT-TYPE
          SYNTAX INTEGER {
           
			chan-8-Bit(1),
			chan-7-Bit(2),
			chan-6-Bit(3),
			undefined(4) 
               } 
          ACCESS read-write
          STATUS mandatory

          DESCRIPTION
          "The variable specifies the pri D-channel bits." 
          
	  --DEFAULT get-function    get-ncmPRIPortDChanBits
	  --DEFAULT set-function    set-ncmPRIPortDChanBits
 
          ::= { ncmJapPRIPortConfigEntry 6 }
 

         ncmJapPRIPortTimeslotMap OBJECT-TYPE
          SYNTAX DisplayString 
          ACCESS read-write
          STATUS mandatory

	 
          DESCRIPTION
          "The variable specifies the timeslot map." 

          --DEFAULT get-function    get-ncmPRIPortTimeslotMap
	  --DEFAULT set-function    set-ncmPRIPortTimeslotMap

 
          ::= { ncmJapPRIPortConfigEntry 7 }
 


         ncmJapPRIPortSwitchType OBJECT-TYPE
          SYNTAX INTEGER {
           
			sw-NTT(15)
		} 
          ACCESS read-write
          STATUS mandatory
          DESCRIPTION
          "The variable specifies the pri switch type." 
 
          ::= { ncmJapPRIPortConfigEntry 8 }
 

         ncmJapPRIPortOwnNumPlan OBJECT-TYPE
          SYNTAX INTEGER {
           
		       unkn-NumPlan(1)
               } 
          ACCESS read-write
          STATUS mandatory
          DESCRIPTION
          "The variable specifies the pri own numbering plan." 
 
          ::= { ncmJapPRIPortConfigEntry 9 }
 

         ncmJapPRIPortOwnNumType OBJECT-TYPE
          SYNTAX INTEGER {
           
		       unkn-NumType(1)
		         } 
          ACCESS read-write
          STATUS mandatory
          DESCRIPTION
          "The variable specifies the pri own numbering type." 
 
          ::= { ncmJapPRIPortConfigEntry 10 }
 

         ncmJapPRIPortSecurityLevel OBJECT-TYPE
          SYNTAX INTEGER {
           
                       no-Checks(1),
                       own-Numbers(2),
                       ext-Numbers(3),
		       both-Numbers(4)	
               } 
          ACCESS read-write
          STATUS mandatory
	  

          DESCRIPTION
          "The variable specifies the fdl mode which is bit 0 of  fdl
           Parameter1."

          --DEFAULT get-function    get-ncmPRIPortSecurityLevel
	  --DEFAULT set-function    set-ncmPRIPortSecurityLevel
 
          ::= { ncmJapPRIPortConfigEntry 11 }
 

         ncmJapPRIPortConfigStatus OBJECT-TYPE
          SYNTAX INTEGER {
           
		       configuration-OK(1),
		       configuration-Error(2)
               } 
          ACCESS read-only
          STATUS mandatory
	    
          DESCRIPTION
          "The variable specifies the configuration result."
           --DEFAULT get-function    get-ncmPRIPortConfigStatus
 
          ::= { ncmJapPRIPortConfigEntry 12 }
 

         ncmJapPRIPortSetConfig OBJECT-TYPE
          SYNTAX INTEGER {
		       set-Config(1),
		       not-in-use(2)
               } 
          ACCESS read-write
          STATUS mandatory
 	  
          DESCRIPTION
          "The set configuration operation that involves sending out
           the ACP message to set the configuration with the setup parameters" 
           --DEFAULT get-function    get-ncmPRIPortSetConfig
	   --DEFAULT set-function    set-ncmPRIPortSetConfig
 
          ::= { ncmJapPRIPortConfigEntry 13 }
 

         ncmJapPRICallProfCallRefCount OBJECT-TYPE
           SYNTAX INTEGER 
           ACCESS read-only
           STATUS mandatory
	  
           DESCRIPTION
           "The variable specifies the number of valid call reference numbers"
           --DEFAULT get-function    get-ncmPRICallProfCallRefCount
	   --DEFAULT set-function    set-ncmPRICallProfCallRefCount

          ::= { ncmJapPRIPortConfigEntry 14 }


         ncmJapPRIL2AutoEstablish OBJECT-TYPE
          SYNTAX INTEGER {
           
                       no(1),
                       yes(2)
               } 
          ACCESS read-write
          STATUS mandatory
	  
          DESCRIPTION
          "The object specifies whether the PRI Port has an Auto
           establishment for Layer-2 or not."

          --DEFAULT get-function    get-ncmPRIL2AutoEstablish
	  --DEFAULT set-function    set-ncmPRIL2AutoEstablish
 
          ::= { ncmJapPRIPortConfigEntry 15 }
 
 


--   ncm  Japanese PRI Call Profile Table

        ncmJapPRICallProfileTable OBJECT-TYPE
        SYNTAX  SEQUENCE OF NcmJapPRICallProfEntry
        ACCESS  not-accessible
        STATUS  mandatory
	DESCRIPTION
        "The PRI Call Profile table  ."

        --DEFAULT test-function    japisdn-test
        --DEFAULT next-function    japisdn-callprof-next

         ::= { ncm-japisdn 8001 }


        ncmJapPRICallProfEntry OBJECT-TYPE
        SYNTAX  NcmJapPRICallProfEntry
        ACCESS  not-accessible
        STATUS  mandatory
        DESCRIPTION
        "An entry in the PRI Call Profile table  ."
         INDEX   { ncmJapPRICallProfNIDIndex, ncmJapPRICallProfLineIndex, ncmJapPRICPCallProfileRef }
         ::= { ncmJapPRICallProfileTable 1 }


         NcmJapPRICallProfEntry ::=
         SEQUENCE {
	
	   ncmJapPRICallProfNIDIndex
		 INTEGER,
           ncmJapPRICallProfLineIndex
                 INTEGER,
	   ncmJapPRICPCallProfileRef
		 INTEGER,
	   ncmJapPRICallProfCallDir
		 INTEGER,
	   ncmJapPRICallProfNumOwnDigit
		 INTEGER,
           ncmJapPRICallProfOwnCallNum
	         DisplayString, 
	   ncmJapPRICallProfExtNumPlan
                 INTEGER,
	   ncmJapPRICallProfExtNumType
		 INTEGER,
	   ncmJapPRICallProfExtNumDigit
		 INTEGER,
	   ncmJapPRICallProfExtCallNum
	         DisplayString, 
           ncmJapPRICallProfTransferMode
                 INTEGER,
           ncmJapPRICallProfCallBandWth
                 INTEGER,
	   ncmJapPRICallProfMultiRateCnt
		 INTEGER,
	   ncmJapPRICallProfRateAdaptn
		 INTEGER,
	   ncmJapPRICallProfTestCallIntvl
       	 	 INTEGER,
           ncmJapPRICallProfCallStatus
		 INTEGER,
           ncmJapPRICallProfCallAction
		 INTEGER,
	   ncmJapPRICPSetCallProf
		 INTEGER,
	   ncmJapPRICPSetCallProfResp
		 INTEGER,
	   ncmJapPRICPCallActionResp
		 INTEGER

                }


	 ncmJapPRICallProfNIDIndex OBJECT-TYPE
          SYNTAX  INTEGER (1..'7fffffff'h)
          ACCESS  read-only
          STATUS  mandatory
          DESCRIPTION
         "The object specifies the node id of the node."
	  --DEFAULT get-function    get-ncmJapPRINIDIndex
           
          ::= { ncmJapPRICallProfEntry 1 }


	 ncmJapPRICallProfLineIndex OBJECT-TYPE
          SYNTAX  INTEGER (1..'7fffffff'h)
          ACCESS  read-only
          STATUS  mandatory
          DESCRIPTION
         "The index value which uniquely identifies  the
          interface to which this entry is applicable."
	  --DEFAULT get-function    get-ncmJapPRILineIndex  
           
          ::= { ncmJapPRICallProfEntry 2 }
 
         
         ncmJapPRICPCallProfileRef OBJECT-TYPE
           SYNTAX INTEGER 
           ACCESS read-write
           STATUS mandatory
           DESCRIPTION
           "The variable specifies the number of the call profile in the
            list (starting from one, then two and so on)."

           --DEFAULT get-function    get-ncmPRICPCallProfileRef
	   --DEFAULT set-function    set-ncmPRICPCallProfileRef

          ::= { ncmJapPRICallProfEntry 3 }


         ncmJapPRICallProfCallDir OBJECT-TYPE
          SYNTAX INTEGER {

		       no-Direction(1),
		       incoming(2),
	               outgoing(3),	
                       both-Directions(4)
                   }
           ACCESS read-write
           STATUS mandatory
           DESCRIPTION
           "The variable specifies the call direction."

           --DEFAULT get-function    get-ncmPRICallProfCallDir
	   --DEFAULT set-function    set-ncmPRICallProfCallDir

           ::= { ncmJapPRICallProfEntry 4 }


        ncmJapPRICallProfNumOwnDigit OBJECT-TYPE
           SYNTAX INTEGER 
           ACCESS read-write
           STATUS mandatory
           DESCRIPTION
           "The variable specifies the number of own digits."
           
	   --DEFAULT get-function    get-ncmPRICallProfNumOwnDigit
	   --DEFAULT set-function    set-ncmPRICallProfNumOwnDigit

           ::= { ncmJapPRICallProfEntry 5 }


         ncmJapPRICallProfOwnCallNum OBJECT-TYPE
           SYNTAX DisplayString 
           ACCESS read-write
           STATUS mandatory
           DESCRIPTION
           "The variable specifies the own call number."

           --DEFAULT get-function    get-ncmPRICallProfOwnCallNum
	   --DEFAULT set-function    set-ncmPRICallProfOwnCallNum

           ::= { ncmJapPRICallProfEntry 6 }


         ncmJapPRICallProfExtNumPlan OBJECT-TYPE
          SYNTAX INTEGER {

		       unkn-NumPlan(1)

                   }
           ACCESS read-write
           STATUS mandatory
           DESCRIPTION
           "The variable specifies the external numbering plan."

           ::= { ncmJapPRICallProfEntry 7 }


         ncmJapPRICallProfExtNumType OBJECT-TYPE
          SYNTAX INTEGER {
		       unkn-NumType(1)
		         }
           ACCESS read-write
           STATUS mandatory
           DESCRIPTION
           "The variable specifies the external numbering type."

           ::= { ncmJapPRICallProfEntry 8 }


         ncmJapPRICallProfExtNumDigit OBJECT-TYPE
           SYNTAX INTEGER 
           ACCESS read-write
           STATUS mandatory
           DESCRIPTION
           "The variable specifies the external number of digits."
            --DEFAULT get-function    get-ncmPRICallProfExtNumDigit
	    --DEFAULT set-function    set-ncmPRICallProfExtNumDigit

           ::= { ncmJapPRICallProfEntry 9 }


         ncmJapPRICallProfExtCallNum OBJECT-TYPE
           SYNTAX DisplayString 
           ACCESS read-write
           STATUS mandatory
           DESCRIPTION
           "The variable specifies the external call number."
             --DEFAULT get-function    get-ncmPRICallProfExtCallNum
	     --DEFAULT set-function    set-ncmPRICallProfExtCallNum

           ::= { ncmJapPRICallProfEntry 10 }


         ncmJapPRICallProfTransferMode OBJECT-TYPE
           SYNTAX INTEGER {
                       unrestricted-digital(8)
                   }
           ACCESS read-write
           STATUS mandatory
           DESCRIPTION
           "The variable specifies the transfer mode."
             --DEFAULT get-function    get-ncmPRICallProfTransferMode
	     --DEFAULT set-function    set-ncmPRICallProfTransferMode

           ::= { ncmJapPRICallProfEntry 11 }


         ncmJapPRICallProfCallBandWth OBJECT-TYPE
          SYNTAX INTEGER {

		       b1-64K(16),
		       h0-6X64K(19),	
		       h11-24X64K(21)	
		          }
           ACCESS read-write
           STATUS mandatory
           DESCRIPTION
           "The variable specifies the call bandwidth."

           ::= { ncmJapPRICallProfEntry 12 }


         ncmJapPRICallProfMultiRateCnt OBJECT-TYPE
          SYNTAX INTEGER {

		       mR-2(2),
		       mR-4(4),
		       mR-6(6),	
		       mR-8(8),	
		       mR-12(12),	
                       mR-23(23),
		       mR-24(24),
		       mR-30(30),
		       mR-31(31)			
                   }
           ACCESS read-write
           STATUS mandatory
           DESCRIPTION
           "The variable specifies the multirate count.
	    Not use for the time being."
             --DEFAULT get-function    get-ncmPRICallProfMultiRateCnt
	     --DEFAULT set-function    set-ncmPRICallProfMultiRateCnt

           ::= { ncmJapPRICallProfEntry 13 }


         ncmJapPRICallProfRateAdaptn OBJECT-TYPE
           SYNTAX INTEGER {

                       no-Adapt(1),
                       adapt-56K(2)
                   }
           ACCESS read-write
           STATUS mandatory
           DESCRIPTION
           "The variable specifies the rate adaptation."
            --DEFAULT get-function    get-ncmPRICallProfRateAdaptn
	    --DEFAULT set-function    set-ncmPRICallProfRateAdaptn

           ::= { ncmJapPRICallProfEntry 14 }


         ncmJapPRICallProfTestCallIntvl OBJECT-TYPE
           SYNTAX INTEGER 
           ACCESS read-write
           STATUS mandatory
           DESCRIPTION
           "The variable specifies the test call interval."
            --DEFAULT get-function    get-ncmPRICallProfTestCallIntvl
	    --DEFAULT set-function    set-ncmPRICallProfTestCallIntvl

           ::= { ncmJapPRICallProfEntry 15 }


         ncmJapPRICallProfCallStatus OBJECT-TYPE
           SYNTAX INTEGER {

                       fail-Takedown-Idle(1),
                       successful-Setup(2),
		       unknown(3)	
                   }
           ACCESS read-only
           STATUS mandatory
           DESCRIPTION
           "The variable specifies the get call profile call status."
            --DEFAULT get-function    get-ncmPRICallProfCallStatus

           ::= { ncmJapPRICallProfEntry 16 }


         ncmJapPRICallProfCallAction OBJECT-TYPE
           SYNTAX INTEGER {

                       setup-Call(1),
		       takedown-Call(2)	
                   }
           ACCESS read-write
           STATUS mandatory
           DESCRIPTION
           "The variable specifies the call profile call action."
	    --DEFAULT get-function    get-ncmPRICallProfCallAction
	    --DEFAULT set-function    set-ncmPRICallProfCallAction

           ::= { ncmJapPRICallProfEntry 17 }



	 ncmJapPRICPSetCallProf OBJECT-TYPE
	   SYNTAX INTEGER {
			
			set-CallProf(1),
			not-in-use(2)
	           }		
           ACCESS read-write
           STATUS mandatory
           DESCRIPTION
           "The variable specifies the call profile call action."
            --DEFAULT get-function    get-ncmPRICPSetCallProf
	    --DEFAULT set-function    set-ncmPRICPSetCallProf

           ::= { ncmJapPRICallProfEntry 18 }


	 ncmJapPRICPSetCallProfResp OBJECT-TYPE
           SYNTAX INTEGER {

                       configuration-OK(1),
                       configuration-Error(2)
                   }
           ACCESS read-only
           STATUS mandatory
           DESCRIPTION
           "The variable specifies the set call profile result"
	    --DEFAULT get-function    get-ncmPRICPSetCallProfResp

           ::= { ncmJapPRICallProfEntry 19 }


	 ncmJapPRICPCallActionResp OBJECT-TYPE
           SYNTAX INTEGER {

                       configuration-OK(1),
                       configuration-Error(2)
                   }
           ACCESS read-only
           STATUS mandatory
           DESCRIPTION
           "The variable specifies the call action result"
             --DEFAULT get-function    get-ncmPRICPCallActionResp

           ::= { ncmJapPRICallProfEntry 20 }




-- ncm Japanese PRI Call Profile List Table


        ncmJapPRICallProfListTable OBJECT-TYPE
        SYNTAX  SEQUENCE OF NcmJapPRICallProfListEntry
        ACCESS  not-accessible
        STATUS  mandatory
	DESCRIPTION
        "The PRI Call Profile List table  ."


        --DEFAULT test-function    japisdn-callprof-test
        --DEFAULT next-function    japisdn-callprof-next

	 ::= { ncm-japisdn 8002 }


        ncmJapPRICallProfListEntry OBJECT-TYPE
        SYNTAX  NcmJapPRICallProfListEntry
        ACCESS  not-accessible
        STATUS  mandatory
        DESCRIPTION
        "An entry in the PRI Call Profile List table  ."
         INDEX   { ncmJapPRICPListNIDIndex, ncmJapPRICPListLineIndex, ncmJapPRICPListIndex }
         ::= { ncmJapPRICallProfListTable 1 }


         NcmJapPRICallProfListEntry ::=
         SEQUENCE {
	
	   ncmJapPRICPListNIDIndex
		 INTEGER,
           ncmJapPRICPListLineIndex
                 INTEGER,
	   ncmJapPRICPListIndex
		 INTEGER,
	   ncmJapPRICPListValidCPRefNum
		 INTEGER
	 }


	 ncmJapPRICPListNIDIndex OBJECT-TYPE
          SYNTAX  INTEGER (1..'7fffffff'h)
          ACCESS  read-only
          STATUS  mandatory
          DESCRIPTION
         "The object specifies the node id of the node of the 
          call profile list group."
	  --DEFAULT get-function    get-ncmJapPRINIDIndex  
           
          ::= { ncmJapPRICallProfListEntry 1 }


	 ncmJapPRICPListLineIndex OBJECT-TYPE
          SYNTAX  INTEGER (1..'7fffffff'h)
          ACCESS  read-only
          STATUS  mandatory
          DESCRIPTION
         "The index value which uniquely identifies the
          interface to which this entry is applicable."
	  --DEFAULT get-function    get-ncmJapPRILineIndex  
           
          ::= { ncmJapPRICallProfListEntry 2 }
 
         
         ncmJapPRICPListIndex OBJECT-TYPE
          SYNTAX  INTEGER 
             ACCESS  read-only
             STATUS  mandatory
             DESCRIPTION
                "The call profile list call reference index." 
              --DEFAULT get-function    get-ncmPRICPListIndex

          ::= { ncmJapPRICallProfListEntry 3 }
 

         ncmJapPRICPListValidCPRefNum OBJECT-TYPE
           SYNTAX INTEGER 
           ACCESS read-only
           STATUS mandatory
           DESCRIPTION
           "The variable is the valid call reference number."
	    --DEFAULT get-function       get-ncmPRICPListValidCPRefNum

          ::= { ncmJapPRICallProfListEntry 4 }



-- ncm Japanese PRI Current Table


        ncmJapPRICurrentTable OBJECT-TYPE
        SYNTAX  SEQUENCE OF NcmJapPRICurrentEntry
        ACCESS  not-accessible
        STATUS  mandatory
	DESCRIPTION
        "The PRI Current Interval table  ."

        --DEFAULT test-function    japisdn-test
        --DEFAULT next-function    japisdn-next
	 
         ::= { ncm-japisdn 8003 }


        ncmJapPRICurrentEntry OBJECT-TYPE
        SYNTAX  NcmJapPRICurrentEntry
        ACCESS  not-accessible
        STATUS  mandatory
        DESCRIPTION
        "An entry in the PRI Current Interval table  ."
         INDEX   { ncmJapPRICurrNIDIndex, ncmJapPRICurrLineIndex, ncmJapPRICurrEndType }
         ::= { ncmJapPRICurrentTable 1 }


         NcmJapPRICurrentEntry ::=
         SEQUENCE {
	
	   ncmJapPRICurrNIDIndex
		 INTEGER,
           ncmJapPRICurrLineIndex
                 INTEGER,
           ncmJapPRICurrEndType 
                 INTEGER,
	   ncmJapPRICurrTimestamp
	         INTEGER,
	   ncmJapPRICurrSecsInCurrIntvl
		 INTEGER,
	   ncmJapPRICurrInfoRx
	         INTEGER,
	   ncmJapPRICurrInfoTx
	         INTEGER,
	   ncmJapPRICurrCRCErrRx
	         INTEGER,
	   ncmJapPRICurrInvalidFrameRx
	         INTEGER,
	   ncmJapPRICurrFrameAbortRx
	         INTEGER,
	   ncmJapPRICurrDISCSRx
	         INTEGER,
	   ncmJapPRICurrDISCSTx
	         INTEGER,
	   ncmJapPRICurrFramerRx
	         INTEGER,
	   ncmJapPRICurrFramerTx
	         INTEGER,
	   ncmJapPRICurrLyr3ProtErr
	         INTEGER,
	   ncmJapPRICurrCallSetupSent
	         INTEGER,
	   ncmJapPRICurrCallSetupSentnFail
	         INTEGER,
	   ncmJapPRICurrCallSetupRx
	         INTEGER,
	   ncmJapPRICurrCallSetupRxnFail
	         INTEGER,
	   ncmJapPRICurrUnSupportMsgRx
	         INTEGER,
	   ncmJapPRICurrTstCalSetupSentnFail
	         INTEGER,
	   ncmJapPRICurrValidIntvls
		 INTEGER,
	   ncmJapPRICurrStatisticReset
		 INTEGER
                }


	 ncmJapPRICurrNIDIndex OBJECT-TYPE
          SYNTAX  INTEGER (1..'7fffffff'h)
          ACCESS  read-only
          STATUS  mandatory
          DESCRIPTION
         "The object specifies the node id of the node."
	 --DEFAULT get-function    get-ncmJapPRINIDIndex  
           
          ::= { ncmJapPRICurrentEntry 1 }


	 ncmJapPRICurrLineIndex OBJECT-TYPE
          SYNTAX  INTEGER (1..'7fffffff'h)
          ACCESS  read-only
          STATUS  mandatory
          DESCRIPTION
         "The index value which uniquely identifies  the
          interface to which this entry is applicable."
	  --DEFAULT get-function    get-ncmJapPRILineIndex  
           
          ::= { ncmJapPRICurrentEntry 2 }
 

         ncmJapPRICurrEndType OBJECT-TYPE
          SYNTAX INTEGER {

                       near-End(1),
                       far-End(2)
                   }
           ACCESS read-only
           STATUS mandatory
           DESCRIPTION
           "The variable specifies the End Type   ."
            --DEFAULT get-function       get-ncmPRICurrEndType
	  
          ::= { ncmJapPRICurrentEntry 3 }


	 ncmJapPRICurrTimestamp OBJECT-TYPE
          SYNTAX  INTEGER 
          ACCESS  read-only
          STATUS  mandatory
          DESCRIPTION
         "The object specifies the timestamp in seconds."
           --DEFAULT get-function       get-ncmPRICurrTimestamp
	   
          ::= { ncmJapPRICurrentEntry 4 }


	 ncmJapPRICurrSecsInCurrIntvl OBJECT-TYPE
          SYNTAX  INTEGER 
          ACCESS  read-only
          STATUS  mandatory
          DESCRIPTION
         "The object specifies the seconds in current interval."
	   --DEFAULT get-function       get-ncmPRICurrSecsInCurrIntvl
           
          ::= { ncmJapPRICurrentEntry 5 }


	 ncmJapPRICurrInfoRx OBJECT-TYPE
          SYNTAX  INTEGER 
          ACCESS  read-only
          STATUS  mandatory
          DESCRIPTION
         "The object specifies the current INFOs received."
           --DEFAULT get-function       get-ncmPRICurrInfoRx
           
          ::= { ncmJapPRICurrentEntry 6 }


	 ncmJapPRICurrInfoTx OBJECT-TYPE
          SYNTAX  INTEGER 
          ACCESS  read-only
          STATUS  mandatory
          DESCRIPTION
         "The object specifies the current INFOs transmitted."
	  --DEFAULT get-function       get-ncmPRICurrInfoTx
           
          ::= { ncmJapPRICurrentEntry 7 }


	 ncmJapPRICurrCRCErrRx OBJECT-TYPE
          SYNTAX  INTEGER 
          ACCESS  read-only
          STATUS  mandatory
          DESCRIPTION
         "The object specifies the current CRC errors received."
	  --DEFAULT get-function       get-ncmPRICurrCRCErrRx
	           
          ::= { ncmJapPRICurrentEntry 8 }


	 ncmJapPRICurrInvalidFrameRx OBJECT-TYPE
          SYNTAX  INTEGER 
          ACCESS  read-only
          STATUS  mandatory
          DESCRIPTION
         "The object specifies the current invalid frames received."
          --DEFAULT get-function       get-ncmPRICurrInvalidFrameRx
	         
          ::= { ncmJapPRICurrentEntry 9 }


	 ncmJapPRICurrFrameAbortRx OBJECT-TYPE
          SYNTAX  INTEGER 
          ACCESS  read-only
          STATUS  mandatory
          DESCRIPTION
         "The object specifies the current frame aborts received."
          --DEFAULT get-function       get-ncmPRICurrFrameAbortRx
           
          ::= { ncmJapPRICurrentEntry 10 }


	 ncmJapPRICurrDISCSRx OBJECT-TYPE
          SYNTAX  INTEGER 
          ACCESS  read-only
          STATUS  mandatory
          DESCRIPTION
         "The object specifies the current DISCs received."
	   --DEFAULT get-function       get-ncmPRICurrDISCSRx
	   
          ::= { ncmJapPRICurrentEntry 11 }


	 ncmJapPRICurrDISCSTx OBJECT-TYPE
          SYNTAX  INTEGER 
          ACCESS  read-only
          STATUS  mandatory
          DESCRIPTION
         "The object specifies the current DISCs transmitted."
           --DEFAULT get-function       get-ncmPRICurrDISCSTx

          ::= { ncmJapPRICurrentEntry 12 }


	 ncmJapPRICurrFramerRx OBJECT-TYPE
          SYNTAX  INTEGER 
          ACCESS  read-only
          STATUS  mandatory
          DESCRIPTION
         "The object specifies the current framer received."
           --DEFAULT get-function       get-ncmPRICurrFramerRx

          ::= { ncmJapPRICurrentEntry 13 }


	 ncmJapPRICurrFramerTx OBJECT-TYPE
          SYNTAX  INTEGER 
          ACCESS  read-only
          STATUS  mandatory
          DESCRIPTION
         "The object specifies the current framer transmitted."
          --DEFAULT get-function       get-ncmPRICurrFramerTx

          ::= { ncmJapPRICurrentEntry 14 }


	 ncmJapPRICurrLyr3ProtErr OBJECT-TYPE
          SYNTAX  INTEGER 
          ACCESS  read-only
          STATUS  mandatory
          DESCRIPTION
         "The object specifies the current Layer 3 protocol errors."
          --DEFAULT get-function       get-ncmPRICurrLyr3ProtErr

          ::= { ncmJapPRICurrentEntry 15 }


	 ncmJapPRICurrCallSetupSent OBJECT-TYPE
          SYNTAX  INTEGER 
          ACCESS  read-only
          STATUS  mandatory
          DESCRIPTION
         "The object specifies the current call setup sent."
	  --DEFAULT get-function       get-ncmPRICurrCallSetupSent

          ::= { ncmJapPRICurrentEntry 16 }


	 ncmJapPRICurrCallSetupSentnFail OBJECT-TYPE
          SYNTAX  INTEGER 
          ACCESS  read-only
          STATUS  mandatory
          DESCRIPTION
         "The object specifies the current call setup sent and failed."
	  --DEFAULT get-function       get-ncmPRICurrCallSetupSentnFail

          ::= { ncmJapPRICurrentEntry 17 }


	 ncmJapPRICurrCallSetupRx OBJECT-TYPE
          SYNTAX  INTEGER 
          ACCESS  read-only
          STATUS  mandatory
          DESCRIPTION
         "The object specifies the current call setup received."
          --DEFAULT get-function       get-ncmPRICurrCallSetupRx
           
          ::= { ncmJapPRICurrentEntry 18 }


	 ncmJapPRICurrCallSetupRxnFail OBJECT-TYPE
          SYNTAX  INTEGER 
          ACCESS  read-only
          STATUS  mandatory
          DESCRIPTION
         "The object specifies the current call setup received and failed."
	   --DEFAULT get-function       get-ncmPRICurrCallSetupRxnFail

          ::= { ncmJapPRICurrentEntry 19 }


	 ncmJapPRICurrUnSupportMsgRx OBJECT-TYPE
          SYNTAX  INTEGER 
          ACCESS  read-only
          STATUS  mandatory
          DESCRIPTION
         "The object specifies the current unsupported message received."
          --DEFAULT get-function       get-ncmPRICurrUnSupportMsgRx
           
          ::= { ncmJapPRICurrentEntry 20 }


	 ncmJapPRICurrTstCalSetupSentnFail OBJECT-TYPE
          SYNTAX  INTEGER 
          ACCESS  read-only
          STATUS  mandatory
          DESCRIPTION
         "The object specifies the current test call setups sent and failed."
           --DEFAULT get-function       get-ncmPRICurrTstCalSetupSentnFail

          ::= { ncmJapPRICurrentEntry 21 }


         ncmJapPRICurrValidIntvls OBJECT-TYPE
          SYNTAX  INTEGER 
             ACCESS  read-only
             STATUS  mandatory
             DESCRIPTION
                "A number between 1 and 96" 
	      --DEFAULT get-function       get-ncmPRICurrValidIntvls

          ::= { ncmJapPRICurrentEntry 22 }
 

	 ncmJapPRICurrStatisticReset OBJECT-TYPE
	   SYNTAX INTEGER {
			
			statistic-Reset(1),
			not-in-use(2)
	           }		
           ACCESS read-write
           STATUS mandatory
           DESCRIPTION
           "The variable specifies the statistic reset operation."
            --DEFAULT get-function       get-ncmPRICurrStatisticReset
            --DEFAULT set-function       set-ncmPRICurrStatisticReset

          ::= { ncmJapPRICurrentEntry 23 }




--  PRI Japanese Interval Table


        ncmJapPRIIntervalTable OBJECT-TYPE
        SYNTAX  SEQUENCE OF NcmJapPRIIntervalEntry
        ACCESS  not-accessible
        STATUS  mandatory
	DESCRIPTION
        "The PRI Interval table  ."
        --DEFAULT test-function    japisdn-interval-test
        --DEFAULT next-function    japisdn-interval-next

         ::= { ncm-japisdn 8004 }


        ncmJapPRIIntervalEntry OBJECT-TYPE
        SYNTAX  NcmJapPRIIntervalEntry
        ACCESS  not-accessible
        STATUS  mandatory
        DESCRIPTION
        "An entry in the PRI Interval table  ."
         INDEX   { ncmJapPRIntvlNIDIndex, ncmJapPRIntvlLineIndex, ncmJapPRIntvlEndType, ncmJapPRIntvlIndex }
         ::= { ncmJapPRIIntervalTable 1 }


         NcmJapPRIIntervalEntry ::=
         SEQUENCE {
	
	   ncmJapPRIntvlNIDIndex
		 INTEGER,
           ncmJapPRIntvlLineIndex
                 INTEGER,
           ncmJapPRIntvlEndType 
                 INTEGER,
	   ncmJapPRIntvlIndex
		 INTEGER,
	   ncmJapPRIntvlTimestamp
	         INTEGER,
	   ncmJapPRIntvlSecsInCurrIntvl
		 INTEGER,
	   ncmJapPRIntvlInfoRx
	         INTEGER,
	   ncmJapPRIntvlInfoTx
	         INTEGER,
	   ncmJapPRIntvlCRCErrRx
	         INTEGER,
	   ncmJapPRIntvlInvalidFrameRx
	         INTEGER,
	   ncmJapPRIntvlFrameAbortRx
	         INTEGER,
	   ncmJapPRIntvlDISCSRx
	         INTEGER,
	   ncmJapPRIntvlDISCSTx
	         INTEGER,
	   ncmJapPRIntvlFramerRx
	         INTEGER,
	   ncmJapPRIntvlFramerTx
	         INTEGER,
	   ncmJapPRIntvlLyr3ProtErr
	         INTEGER,
	   ncmJapPRIntvlCallSetupSent
	         INTEGER,
	   ncmJapPRIntvlCallSetupSentnFail
	         INTEGER,
	   ncmJapPRIntvlCallSetupRx
	         INTEGER,
	   ncmJapPRIntvlCallSetupRxnFail
	         INTEGER,
	   ncmJapPRIntvlUnSupportMsgRx
	         INTEGER,
	   ncmJapPRIntvlTstCalSetupSentnFail
	         INTEGER
                }


	 ncmJapPRIntvlNIDIndex OBJECT-TYPE
          SYNTAX  INTEGER (1..'7fffffff'h)
          ACCESS  read-only
          STATUS  mandatory
          DESCRIPTION
         "The object specifies the node id of the node."
	  --DEFAULT get-function    get-ncmJapPRINIDIndex 
           
          ::= { ncmJapPRIIntervalEntry 1 }



	 ncmJapPRIntvlLineIndex OBJECT-TYPE
          SYNTAX  INTEGER (1..'7fffffff'h)
          ACCESS  read-only
          STATUS  mandatory
          DESCRIPTION
         "The index value which uniquely identifies  the
          interface to which this entry is applicable."
	 --DEFAULT get-function    get-ncmJapPRILineIndex  
           
          ::= { ncmJapPRIIntervalEntry 2 }
 

         ncmJapPRIntvlEndType OBJECT-TYPE
          SYNTAX INTEGER {

                       near-End(1),
                       far-End(2)

                   }
           ACCESS read-only
           STATUS mandatory
           DESCRIPTION
           "The variable specifies the End Type   ."
            --DEFAULT get-function       get-ncmPRIntvlEndType

          ::= { ncmJapPRIIntervalEntry 3 }


         ncmJapPRIntvlIndex OBJECT-TYPE
          SYNTAX  INTEGER 
             ACCESS  read-only
             STATUS  mandatory
             DESCRIPTION
                "The interval index."
             --DEFAULT get-function       get-ncmPRIntvlIndex
 
          ::= { ncmJapPRIIntervalEntry 4 }
 

	 ncmJapPRIntvlTimestamp OBJECT-TYPE
          SYNTAX  INTEGER 
          ACCESS  read-only
          STATUS  mandatory
          DESCRIPTION
         "The object specifies the interval timestamp in seconds."
          --DEFAULT get-function       get-ncmPRIntvlTimestamp
           
          ::= { ncmJapPRIIntervalEntry 5 }


	 ncmJapPRIntvlSecsInCurrIntvl OBJECT-TYPE
          SYNTAX  INTEGER 
          ACCESS  read-only
          STATUS  mandatory
          DESCRIPTION
         "The object specifies the interval seconds in current interval."
	  --DEFAULT get-function       get-ncmPRIntvlSecsInCurrIntvl
           
          ::= { ncmJapPRIIntervalEntry 6 }


	 ncmJapPRIntvlInfoRx OBJECT-TYPE
          SYNTAX  INTEGER 
          ACCESS  read-only
          STATUS  mandatory
          DESCRIPTION
         "The object specifies the interval INFOs received."
          --DEFAULT get-function       get-ncmPRIntvlInfoRx

          ::= { ncmJapPRIIntervalEntry 7 }


	 ncmJapPRIntvlInfoTx OBJECT-TYPE
          SYNTAX  INTEGER 
          ACCESS  read-only
          STATUS  mandatory
          DESCRIPTION
         "The object specifies the interval INFOs transmitted."
          --DEFAULT get-function       get-ncmPRIntvlInfoTx

          ::= { ncmJapPRIIntervalEntry 8 }


	 ncmJapPRIntvlCRCErrRx OBJECT-TYPE
          SYNTAX  INTEGER 
          ACCESS  read-only
          STATUS  mandatory
          DESCRIPTION
         "The object specifies the interval CRC errors received."
          --DEFAULT get-function       get-ncmPRIntvlCRCErrRx

          ::= { ncmJapPRIIntervalEntry 9 }


	 ncmJapPRIntvlInvalidFrameRx OBJECT-TYPE
          SYNTAX  INTEGER 
          ACCESS  read-only
          STATUS  mandatory
          DESCRIPTION
         "The object specifies the interval invalid frames received."
	  --DEFAULT get-function       get-ncmPRIntvlInvalidFrameRx
           
          ::= { ncmJapPRIIntervalEntry 10 }


	 ncmJapPRIntvlFrameAbortRx OBJECT-TYPE
          SYNTAX  INTEGER 
          ACCESS  read-only
          STATUS  mandatory
          DESCRIPTION
         "The object specifies the interval frame aborts received."
          --DEFAULT get-function       get-ncmPRIntvlFrameAbortRx

          ::= { ncmJapPRIIntervalEntry 11 }


	 ncmJapPRIntvlDISCSRx OBJECT-TYPE
          SYNTAX  INTEGER 
          ACCESS  read-only
          STATUS  mandatory
          DESCRIPTION
         "The object specifies the interval DISCs received."
	  --DEFAULT get-function       get-ncmPRIntvlDISCSRx

          ::= { ncmJapPRIIntervalEntry 12 }


	 ncmJapPRIntvlDISCSTx OBJECT-TYPE
          SYNTAX  INTEGER 
          ACCESS  read-only
          STATUS  mandatory
          DESCRIPTION
         "The object specifies the interval DISCs transmitted."
          --DEFAULT get-function       get-ncmPRIntvlDISCSTx
           
          ::= { ncmJapPRIIntervalEntry 13 }


	 ncmJapPRIntvlFramerRx OBJECT-TYPE
          SYNTAX  INTEGER 
          ACCESS  read-only
          STATUS  mandatory
          DESCRIPTION
         "The object specifies the interval framer received."
	 --DEFAULT get-function       get-ncmPRIntvlFramerRx

          ::= { ncmJapPRIIntervalEntry 14 }


	 ncmJapPRIntvlFramerTx OBJECT-TYPE
          SYNTAX  INTEGER 
          ACCESS  read-only
          STATUS  mandatory
          DESCRIPTION
         "The object specifies the interval framer transmitted."
          --DEFAULT get-function       get-ncmPRIntvlFramerTx

          ::= { ncmJapPRIIntervalEntry 15 }


	 ncmJapPRIntvlLyr3ProtErr OBJECT-TYPE
          SYNTAX  INTEGER 
          ACCESS  read-only
          STATUS  mandatory
          DESCRIPTION
         "The object specifies the interval Layer 3 protocol errors."
          --DEFAULT get-function       get-ncmPRIntvlLyr3ProtErr

          ::= { ncmJapPRIIntervalEntry 16 }


	 ncmJapPRIntvlCallSetupSent OBJECT-TYPE
          SYNTAX  INTEGER 
          ACCESS  read-only
          STATUS  mandatory
          DESCRIPTION
         "The object specifies the interval call setup sent."
          --DEFAULT get-function       get-ncmPRIntvlCallSetupSent

          ::= { ncmJapPRIIntervalEntry 17 }


	 ncmJapPRIntvlCallSetupSentnFail OBJECT-TYPE
          SYNTAX  INTEGER 
          ACCESS  read-only
          STATUS  mandatory
          DESCRIPTION
         "The object specifies the interval call setup sent and failed."
          --DEFAULT get-function       get-ncmPRIntvlCallSetupSentnFail
           
          ::= { ncmJapPRIIntervalEntry 18 }


	 ncmJapPRIntvlCallSetupRx OBJECT-TYPE
          SYNTAX  INTEGER 
          ACCESS  read-only
          STATUS  mandatory
          DESCRIPTION
         "The object specifies the interval call setup received."
          --DEFAULT get-function       get-ncmPRIntvlCallSetupSentnFail

          ::= { ncmJapPRIIntervalEntry 19 }


	 ncmJapPRIntvlCallSetupRxnFail OBJECT-TYPE
          SYNTAX  INTEGER 
          ACCESS  read-only
          STATUS  mandatory
          DESCRIPTION
         "The object specifies the interval call setup received and failed."
           --DEFAULT get-function       get-ncmPRIntvlCallSetupRxnFail

          ::= { ncmJapPRIIntervalEntry 20 }


	 ncmJapPRIntvlUnSupportMsgRx OBJECT-TYPE
          SYNTAX  INTEGER 
          ACCESS  read-only
          STATUS  mandatory
          DESCRIPTION
         "The object specifies the interval unsupported message received."
          --DEFAULT get-function       get-ncmPRIntvlUnSupportMsgRx

          ::= { ncmJapPRIIntervalEntry 21 }


	 ncmJapPRIntvlTstCalSetupSentnFail OBJECT-TYPE
          SYNTAX  INTEGER 
          ACCESS  read-only
          STATUS  mandatory
          DESCRIPTION
         "The object specifies the interval test call setups sent and failed."
           --DEFAULT get-function       get-ncmPRIntvlTstCalSetupSentnFail

          ::= { ncmJapPRIIntervalEntry 22 }




--  PRI Japanese Security Operation Table


        ncmJapPRISecurOperTable OBJECT-TYPE
        SYNTAX  SEQUENCE OF NcmJapPRISecurOperEntry
        ACCESS  not-accessible
        STATUS  mandatory
	DESCRIPTION
        "The PRI Security Operation Table  ."

        --DEFAULT test-function    japisdn-test
        --DEFAULT next-function    japisdn-next

         ::= { ncm-japisdn 8005 }


        ncmJapPRISecurOperEntry OBJECT-TYPE
        SYNTAX  NcmJapPRISecurOperEntry
        ACCESS  not-accessible
        STATUS  mandatory
        DESCRIPTION
        "An entry in the PRI Security Operation Table  ."
         INDEX   { ncmJapPRISecOpNIDIndex, ncmJapPRISecOpLineIndex }
         ::= { ncmJapPRISecurOperTable 1 }


         NcmJapPRISecurOperEntry ::=
         SEQUENCE {
	
	   ncmJapPRISecOpNIDIndex
		 INTEGER,
           ncmJapPRISecOpLineIndex
                 INTEGER,
	   ncmJapPRISecOpFirstNum
		 INTEGER,
	   ncmJapPRISecOpListype
		 INTEGER,
	   ncmJapPRISecOpCountNum
		 INTEGER,
	   ncmJapPRISecOpClearElement
		 INTEGER,
	   ncmJapPRISecOpStatus
		 INTEGER,
           ncmJapPRISecOpAction
		 INTEGER

	}


	 ncmJapPRISecOpNIDIndex OBJECT-TYPE
          SYNTAX  INTEGER (1..'7fffffff'h)
          ACCESS  read-only
          STATUS  mandatory
          DESCRIPTION
         "The object specifies the node id of the node."
	 --DEFAULT get-function    get-ncmJapPRINIDIndex 
           
          ::= { ncmJapPRISecurOperEntry 1 }


	 ncmJapPRISecOpLineIndex OBJECT-TYPE
          SYNTAX  INTEGER (1..'7fffffff'h)
          ACCESS  read-only
          STATUS  mandatory
          DESCRIPTION
         "The index value which uniquely identifies  the
          interface to which this entry is applicable."
	 --DEFAULT get-function    get-ncmJapPRILineIndex  
           
          ::= { ncmJapPRISecurOperEntry 2 }
 
         
         ncmJapPRISecOpFirstNum OBJECT-TYPE
          SYNTAX INTEGER {
		       zeroth(1),	
                       twelfth(13),
                       twenty-Fourth(25),
		       thirty-Sixth(37),
		       fourty-Eighth(49)

                   }
             ACCESS  read-write
             STATUS  mandatory
             DESCRIPTION
                "The first item number of the present group of security number."
	     --DEFAULT get-function    get-ncmPRISecOpFirstNum
             --DEFAULT set-function    set-ncmPRISecOpFirstNum

           ::= { ncmJapPRISecurOperEntry 3 }
 

         ncmJapPRISecOpListype OBJECT-TYPE
          SYNTAX INTEGER {

                       own-number(1),
                       remote-number(2)

                   }
           ACCESS read-write
           STATUS mandatory
           DESCRIPTION
           "The variable specifies the type of list: own or remote numbers."
	    --DEFAULT get-function    get-ncmPRISecOpListype
	    --DEFAULT set-function    set-ncmPRISecOpListype

           ::= { ncmJapPRISecurOperEntry 4 }


         ncmJapPRISecOpCountNum OBJECT-TYPE
           SYNTAX INTEGER 
           ACCESS read-only
           STATUS mandatory
           DESCRIPTION
           "The variable specifies the number of numbers/elements in this group."
	    --DEFAULT get-function    get-ncmPRISecOpCountNum

           ::= { ncmJapPRISecurOperEntry 5 }


         ncmJapPRISecOpClearElement OBJECT-TYPE
           SYNTAX INTEGER 
           ACCESS read-write
           STATUS mandatory
           DESCRIPTION
           "The variable specifies the element number of the number to be cleared."
	    --DEFAULT get-function    get-ncmPRISecOpClearElement
	    --DEFAULT set-function    set-ncmPRISecOpClearElement

           ::= { ncmJapPRISecurOperEntry 6 }


         ncmJapPRISecOpStatus OBJECT-TYPE
           SYNTAX INTEGER {

                       configuration-OK(1),
                       configuration-Error(2)

                   }
           ACCESS read-only
           STATUS mandatory
           DESCRIPTION
           "The variable specifies the result of writing security number."
            --DEFAULT get-function    get-ncmPRISecOpStatus

           ::= { ncmJapPRISecurOperEntry 7 }


         ncmJapPRISecOpAction OBJECT-TYPE
          SYNTAX INTEGER {

                       clear-Security-List(1),
                       set-Security-List(2)

                   }
             ACCESS  read-write
             STATUS  mandatory
             DESCRIPTION
                "The operation that involves sending the corresponding ACP command
                 to execute the specified action with all necessary parameters setup
                 properly." 

		 --DEFAULT get-function    get-ncmPRISecOpAction
		 --DEFAULT set-function    set-ncmPRISecOpAction

           ::= { ncmJapPRISecurOperEntry 8 }
 



     -- ncm Japanese PRI Security Number Table


        ncmJapPRISecurNumbTable OBJECT-TYPE
        SYNTAX  SEQUENCE OF NcmJapPRISecurNumbEntry
        ACCESS  not-accessible
        STATUS  mandatory
	DESCRIPTION
        "The PRI Security Number table  ."
        --DEFAULT test-function    japisdn-security-test
        --DEFAULT next-function    japisdn-security-next
	         ::= { ncm-japisdn 8006 }


        ncmJapPRISecurNumbEntry OBJECT-TYPE
        SYNTAX  NcmJapPRISecurNumbEntry
        ACCESS  not-accessible
        STATUS  mandatory
        DESCRIPTION
        "An entry in the PRI Security Number table  ."
         INDEX   { ncmJapPRISecNumNIDIndex, ncmJapPRISecNumLineIndex, ncmJapPRISecNumIndex }
         ::= { ncmJapPRISecurNumbTable 1 }


         NcmJapPRISecurNumbEntry ::=
         SEQUENCE {
	
	   ncmJapPRISecNumNIDIndex
		 INTEGER,
           ncmJapPRISecNumLineIndex
                 INTEGER,
	   ncmJapPRISecNumIndex
		 INTEGER,
	   ncmJapPRISecNumCount
		 INTEGER,
	   ncmJapPRISecNumNumber
		 DisplayString 

	}


	 ncmJapPRISecNumNIDIndex OBJECT-TYPE
          SYNTAX  INTEGER (1..'7fffffff'h)
          ACCESS  read-only
          STATUS  mandatory
          DESCRIPTION
         "The object specifies the node id of the node."
	  --DEFAULT get-function    get-ncmJapPRILineIndex  
           
          ::= { ncmJapPRISecurNumbEntry 1 }


	 ncmJapPRISecNumLineIndex OBJECT-TYPE
          SYNTAX  INTEGER (1..'7fffffff'h)
          ACCESS  read-only
          STATUS  mandatory
          DESCRIPTION
         "The index value which uniquely identifies  the
          interface to which this entry is applicable."
	  --DEFAULT get-function    get-ncmJapPRILineIndex  
           
          ::= { ncmJapPRISecurNumbEntry 2 }
 
         
         ncmJapPRISecNumIndex OBJECT-TYPE
          SYNTAX  INTEGER 
             ACCESS  read-only
             STATUS  mandatory
             DESCRIPTION
                "The index number of the security number." 
	   --DEFAULT get-function    get-ncmPRISecNumIndex

          ::= { ncmJapPRISecurNumbEntry 3 }
 

         ncmJapPRISecNumCount OBJECT-TYPE
          SYNTAX  INTEGER 
             ACCESS  read-write
             STATUS  mandatory
             DESCRIPTION
                "The number of digits of the security number." 
	   --DEFAULT get-function    get-ncmPRISecNumCount 
	   --DEFAULT set-function    set-ncmPRISecNumCount 

          ::= { ncmJapPRISecurNumbEntry 4 }
 

         ncmJapPRISecNumNumber OBJECT-TYPE
           SYNTAX DisplayString 
           ACCESS read-write
           STATUS mandatory
           DESCRIPTION
           "The variable specifies the security number."
	  --DEFAULT get-function    get-ncmPRISecNumNumber
	  --DEFAULT set-function    set-ncmPRISecNumNumber 

          ::= { ncmJapPRISecurNumbEntry 5 }



     -- ncm Japanese PRI Call Log Line Table


        ncmJapPRICallLogLineTable OBJECT-TYPE
        SYNTAX  SEQUENCE OF NcmJapPRICallLogLineEntry
        ACCESS  not-accessible
        STATUS  mandatory
	DESCRIPTION
        "The PRI Call Log Line Table  ."
        --DEFAULT test-function    japisdn-test
        --DEFAULT next-function    japisdn-loglin-next

         ::= { ncm-japisdn 8007 }


        ncmJapPRICallLogLineEntry OBJECT-TYPE
        SYNTAX  NcmJapPRICallLogLineEntry
        ACCESS  not-accessible
        STATUS  mandatory
        DESCRIPTION
        "An entry in the PRI Call Log Line Table  ."
         -- INDEX   { ncmJapPRICaloglinNIDIndex, ncmJapPRICaloglinLineIndex }
         INDEX   { ncmJapPRICaloglinNIDIndex, ncmJapPRICaloglinLineIndex, ncmJapPRICaloglinLineNum }
         ::= { ncmJapPRICallLogLineTable 1 }


         NcmJapPRICallLogLineEntry ::=
         SEQUENCE {
	
	   ncmJapPRICaloglinNIDIndex
		 INTEGER,
           ncmJapPRICaloglinLineIndex
                 INTEGER,
	   ncmJapPRICaloglinLineNum
		 INTEGER,
	   ncmJapPRICaloglinLogLine
		 DisplayString, 
	   ncmJapPRICaloglinStatus
		 INTEGER

	}


	 ncmJapPRICaloglinNIDIndex OBJECT-TYPE
          SYNTAX  INTEGER (1..'7fffffff'h)
          ACCESS  read-only
          STATUS  mandatory
          DESCRIPTION
         "The object specifies the node id of the node."
	 --DEFAULT get-function    get-ncmJapPRINIDIndex 
           
          ::= { ncmJapPRICallLogLineEntry 1 }


	 ncmJapPRICaloglinLineIndex OBJECT-TYPE
          SYNTAX  INTEGER (1..'7fffffff'h)
          ACCESS  read-only
          STATUS  mandatory
          DESCRIPTION
         "The index value which uniquely identifies the
          interface to which this entry is applicable."
	 --DEFAULT get-function    get-ncmJapPRILineIndex  
           
          ::= { ncmJapPRICallLogLineEntry 2 }
 
         
	 ncmJapPRICaloglinLineNum OBJECT-TYPE
          SYNTAX INTEGER 
             ACCESS  read-only
             STATUS  mandatory
             DESCRIPTION
                "The log line number of the log line to be displayed." 
	    --DEFAULT get-function    get-ncmPRICaloglinLineNum

          ::= { ncmJapPRICallLogLineEntry 3 }
 

	 ncmJapPRICaloglinLogLine OBJECT-TYPE
          SYNTAX DisplayString 
             ACCESS  read-only
             STATUS  mandatory
             DESCRIPTION
                "The log line to be displayed." 
	    --DEFAULT get-function    get-ncmPRICaloglinLogLine

          ::= { ncmJapPRICallLogLineEntry 4 }
 

         ncmJapPRICaloglinStatus OBJECT-TYPE
           SYNTAX INTEGER {

                       valid-CallLogLine(1),
                       invalid-CallLogLine(2)
                   }
           ACCESS read-only
           STATUS mandatory
           DESCRIPTION
           "The variable specifies the result of listing the call log line."
	   --DEFAULT get-function    get-ncmPRICaloglinStatus 

          ::= { ncmJapPRICallLogLineEntry 5 }


END
