-- ZyXEL Communications Corporation
-- Private Enterprise MIB definition 
  
-- This file describes the ZyXEL Communications Corporation Enterprise MIB.
-- It contains ZyXEL products OIDs, and common managed objects.

-- $Log: ZYXEL-BRIDGE-CONTROL-PROTOCOL-TRANSPARENCY-MIB.mib $ 
-- Revision 1.3  2012/09/19 07:29:40  Kevin 
-- if it's leaf node, revise the vender name from zyxel to zy 
-- Revision 1.2  2012/07/05 06:22:18  Kevin 
-- 1. upgrade from SNMP to SNMPv2  
-- 2. clean warning 
-- Revision 1.1  2012/05/30 07:48:11  Kevin 
-- Initial revision 

ZYXEL-BRIDGE-CONTROL-PROTOCOL-TRANSPARENCY-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelBridgeControlProtocolTransparency MODULE-IDENTITY
		LAST-UPDATED	"201207010000Z"    
		ORGANIZATION "Enterprise Solution ZyXEL"     
		CONTACT-INFO
			""	   
		DESCRIPTION
			"The subtree for bridge control protocol transparency"
		::= { esMgmt 15 }	

	zyxelBridgeControlProtocolTransparencySetup 	OBJECT IDENTIFIER ::= { zyxelBridgeControlProtocolTransparency 1 }
	
    
--  1.zyxelBridgeControlProtocolTransparencySetup

        zyBridgeControlProtocolTransparencyState OBJECT-TYPE
        SYNTAX  EnabledStatus
        MAX-ACCESS  read-write
        STATUS  current
        DESCRIPTION
        "Enable/Disable bridge control protocol transparency on the switch."
        ::= { zyxelBridgeControlProtocolTransparencySetup 1 }

-- 		zyxelBridgeControlProtocolTransparencyPortTable

        zyxelBridgeControlProtocolTransparencyPortTable OBJECT-TYPE
        SYNTAX	SEQUENCE OF ZyxelBridgeControlProtocolTransparencyPortEntry
        MAX-ACCESS  not-accessible
        STATUS  current
        DESCRIPTION
        "The table contains bridge control protocol transparency port configuration."
        ::= { zyxelBridgeControlProtocolTransparencySetup 2 }
        
		zyxelBridgeControlProtocolTransparencyPortEntry OBJECT-TYPE
        SYNTAX	ZyxelBridgeControlProtocolTransparencyPortEntry
        MAX-ACCESS	not-accessible
        STATUS	current
        DESCRIPTION    	
		"An entry contains bridge control protocol transparency port configuration."
        INDEX          	{ dot1dBasePort }
        ::= { zyxelBridgeControlProtocolTransparencyPortTable 1 }

        ZyxelBridgeControlProtocolTransparencyPortEntry ::=
           SEQUENCE {
        	zyBridgeControlProtocolTransparencyPortMode	INTEGER
           }

        zyBridgeControlProtocolTransparencyPortMode OBJECT-TYPE
        SYNTAX  INTEGER{
		peer(0),
		tunnel(1),
		discard(2),
		network(3)
        }
        MAX-ACCESS  read-write
        STATUS  current
        DESCRIPTION
        "Configure bridge control protocol transparency mode for the port. 
		 'Peer' means to process any BPDU (Bridge Protocol Data Unit) received on this port. 
		 'Tunnel' means to forward BPDUs received on this port. 
		 'Discard' means to drop any BPDU received on this port. 
		 'Network' means to process a BPDU with no VLAN tag and forward a tagged BPDU."
        ::= { zyxelBridgeControlProtocolTransparencyPortEntry 1 }

END
