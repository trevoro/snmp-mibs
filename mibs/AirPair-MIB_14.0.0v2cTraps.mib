-- File Name : AirPair-13.0.0
-- Version   : 13.0.0
-- Date      : Dec 2005
-- Author    : DragonWave Inc.

AirPairv2cTrap-MIB	DEFINITIONS ::= BEGIN


         IMPORTS
                  NOTIFICATION-TYPE
                          FROM SNMPv2-SMI
 
                  ifIndex,                     
                  OBJECT-TYPE
                          FROM RFC-1212

                  airPair,
                  ttySessionUserName,
                  ttySessionUserConnectionType
                          FROM AirPair-MIB;

         
        apSnmpV2Notification	OBJECT IDENTIFIER
             ::=  {  airPair  26  }
		
        apSnmpV2Traps	OBJECT IDENTIFIER
             ::=  {  apSnmpV2Notification  0  }

	coldStartV2c	NOTIFICATION-TYPE
             STATUS  current
       	     DESCRIPTION		
                  "A coldStart trap signifies that the sending protocol entity 
                   is reinitializing itself such that the agent's configuration
                   or the protocol entity implementation may be altered."
             ::= { apSnmpV2Traps 0 }

	linkDownV2c	NOTIFICATION-TYPE
              OBJECTS {ifIndex}
              STATUS  current
              DESCRIPTION		
        	   "A linkDown trap signifies that the sending protocol entity 
                    recognizes a failure in one of the communication links 
                    represented in the agent's configuration."
              ::= { apSnmpV2Traps 1 }

	linkUpV2c	NOTIFICATION-TYPE
                OBJECTS {ifIndex}
                STATUS  current
        	DESCRIPTION		 
        	      "A linkUp trap signifies that the sending protocol entity
                      recognizes that one of the communication links represented
                      in the agent's configuration has come up."		 
              ::= { apSnmpV2Traps 2 }


	explicitAuthenticationFailureV2c	NOTIFICATION-TYPE
                STATUS  current
        	DESCRIPTION
                     "Authentication of the peer AirPair node has failed. The 
                      severity is critical, the probable cause is an incorrect 
                      authentication configuration on AirPair faulty cable 
                      between the modem and radio, and recommended course of 
                      action is to check both ends of the link."

        ::= { apSnmpV2Traps 3 }

	autoNegotiationDuplexMismatchV2c	NOTIFICATION-TYPE
                STATUS  current
        	DESCRIPTION	
                     "The AirPair ethernet interface has a mismatch in duplex. The
                      severity is major, the probable cause is an incorrect 
                      configuration of the switch or router connected to AirPair, 
                      or the AirPair autonegotion settings. The recommended course 
                      of action is to check the connection."
        ::= { apSnmpV2Traps 4 }

	modemLossOfSignalLockFromDemodulatorV2c	NOTIFICATION-TYPE
                STATUS  current
        	DESCRIPTION	
                      "Loss of signal lock from the demodulator. The severity is 
                       critical, the probable cause is lost synchronization with
                       the far end, and recommended course of action is to check
                       the operational state of both ends of the link."
        ::= { apSnmpV2Traps 5 }

	modemUncorrectedBerThresholdExceededV2c	NOTIFICATION-TYPE
                STATUS  current
        	DESCRIPTION	
                      "The uncorrected BER threshold has been exceeded. The severity is major, 
                       the probable cause is physical interference in the air link
                       or misalignment of the radios or severe weather conditions,
                       and recommended course of action is to check the line of site
                       between the air pair nodes."
        ::= { apSnmpV2Traps 6 }

	modemModulatorPllLockFailureV2c	NOTIFICATION-TYPE
                STATUS  current
        	DESCRIPTION		
                      "Modulator PLL failure. The severity is critical, the probable
                       cause a faulty modem card within AirPair, and recommended 
                       course of action is to replace the modem unit."
        ::= { apSnmpV2Traps 7 }

	modemModulatorLossOfSyncBytesV2c	NOTIFICATION-TYPE
                STATUS  current
        	DESCRIPTION		
                      "Loss of sync bytes at the input of the modulator. The severity 
                      is critical, the probable cause is physical interference in the
                      air link, and recommended course of action is to check the line
                      of site between the air pair nodes."
        ::= { apSnmpV2Traps 8 }

	modemModulatorInputFifoErrorV2c	NOTIFICATION-TYPE
                STATUS  current
        	DESCRIPTION	
                      "Overrun or underrun of the FIFO contained inside the modulator. 
                       The severity is critical, the probable cause is electrical 
                       interference, and recommended course of action is to reset the
                       modem unit, or relpace the modem unit."
        ::= { apSnmpV2Traps 9 }

	modemModulatorInputDataErrorV2c	NOTIFICATION-TYPE
                STATUS  current
        	DESCRIPTION		
                      "All ones or all zeroes at the input of the modulator. The severity 
                       is critical, the probable cause is electrical interference, and 
                       recommended course of action is to reset the modem unit, or replace
                       the modem unit. "
        ::= { apSnmpV2Traps 10 }

	modemSnrBelowThresholdV2c	NOTIFICATION-TYPE
                STATUS  current
        	DESCRIPTION		
                       "The demodulator SNR performance worse than programmed levels. The 
                       severity is major, the probable cause is physical interference in the
                       air link path or misalignment of the radios or severe weather conditions,
                       and recommended course of action is to check the line of site between
                       the air pair nodes."
        ::= { apSnmpV2Traps 11 }

	radioPLDROLostLockV2c	NOTIFICATION-TYPE
                STATUS  current
        	DESCRIPTION		
                     "The PLDRO/LO has lost lock on the radio. The severity is critical, the 
                     probable cause a faulty radio unit within AirPair, and recommended course
                     of action is to replace the radio unit."
        ::= { apSnmpV2Traps 12 }


	radioLostCommunicationV2c	NOTIFICATION-TYPE
                STATUS  current
       	        DESCRIPTION		
                     "RS232 communication lost between AIRPAIR and the radio. The severity is 
                     critical, the probable cause is a faulty cable between the modem and radio,
                     and recommended course of action is to check the connection."
        ::= { apSnmpV2Traps 13 }

	radioMismatchV2c	NOTIFICATION-TYPE
                STATUS  current
        	DESCRIPTION		
                     "The radio connected to the AIRPAIR modem does not match the frequency 
                     programmed into the modem unit. The severity is major, the probable cause
                     is an incorrectly programmed modem or an incorrect radio type connected to
                     the modem, and recommended course of action is to check the modem frequency
                     settings and radio hardware version number or serial number."
        ::= { apSnmpV2Traps 14 }

	radioPowerAmpV2c	NOTIFICATION-TYPE
                STATUS  current
        	DESCRIPTION		
                     "The power amplifier on the radio is not operating within normal operating 
                      specifications. The severity is critical, the probable cause a faulty radio
                      unit within AirPair, and recommended course of action is to replace the 
                      radio unit."
        ::= { apSnmpV2Traps 15 }

	ifTxSynthUnlockedV2c	NOTIFICATION-TYPE
                STATUS  current
        	DESCRIPTION	
                      "The IF card within the modem unit has a Transmit Synthesizer which is not 
                       locked and as a result will not transmit. The severity is critical, the 
                       probable cause an incorrectly programmed frequency setting in the modem
                       or a faulty IF card, and recommended course of action is to check frequency
                       setting in the modem or to replace the modem unit."
        ::= { apSnmpV2Traps 16 }

	ifRxSynthUnlockedV2c	NOTIFICATION-TYPE
                STATUS  current
        	DESCRIPTION		
                       "The IF card within the modem unit has a Receive Synthesizer which is not 
                        locked. The severity is critical, the probable cause an incorrectly 
                        programmed frequency setting in the modem or a faulty IF card, and 
                        recommended course of action is to check frequency setting in the modem 
                        or to replace the modem unit."
        ::= { apSnmpV2Traps 17 }

	
        ttySessionCommencedV2c	NOTIFICATION-TYPE
		OBJECTS   { ttySessionUserName,
			      ttySessionUserConnectionType }
        	
                STATUS  current
                DESCRIPTION		
                      "A person has successfully gained access to the ascii management port (telnet,
                      local management port, or HTTP). The username is included in the Trap."
        ::= { apSnmpV2Traps 18 }

	ttySessionTerminatedV2c	NOTIFICATION-TYPE
		OBJECTS   { ttySessionUserName,
			      ttySessionUserConnectionType }
                STATUS  current
        	DESCRIPTION		
                       "A person has logged out of an ascii management port (telnet, local management 
                        port, or HTTP). The username is included in the Trap."
        ::= { apSnmpV2Traps 19 }


        rslBelowThresholdV2c	NOTIFICATION-TYPE
                STATUS  current
        	DESCRIPTION     
                      "The RSL has been detected below its minimum threshold."
        ::= { apSnmpV2Traps 20 }
	
        droppedFramesThresholdExceededV2c	NOTIFICATION-TYPE
                STATUS  current
        	DESCRIPTION     
                      "The ethernet dropped frames threshold has been detected above its threshold value."
        ::= { apSnmpV2Traps 21 }
        
        bwUtilizationThresholdExceededV2c	NOTIFICATION-TYPE
                STATUS  current
        	DESCRIPTION     
                      "The ethernet bandwidth threshold has been detected above its threshold value."
        ::= { apSnmpV2Traps 22 }
        
        explicitAuthFailureClearedV2c	NOTIFICATION-TYPE
                STATUS  current
        	DESCRIPTION		
                     "The condition has cleared. The peer node is now authenticated."
        ::= { apSnmpV2Traps 23 }

 		
	autoNegDuplexMismatchClearedV2c	NOTIFICATION-TYPE
                STATUS  current
        	DESCRIPTION		
                     "The condition has cleared. The Ethernet connection is not experiencing 
                      auto-negotiation duplex mismatch."
        ::= { apSnmpV2Traps 24 }

	lossOfSyncSigFromDemoClearedV2c	NOTIFICATION-TYPE
                STATUS  current
        	DESCRIPTION		
                     "The condition has cleared. The demodulator is synchronized."
        ::= { apSnmpV2Traps 25 }
                
	uncorrectedBerThresExceededClearedV2c	NOTIFICATION-TYPE
                STATUS  current
        	DESCRIPTION		
                     "The condition has cleared. The demodulator uncorrected BER is now below its minimum 
                     threshold value."
        ::= { apSnmpV2Traps 26 }
                
	modemModPLLFailureClearedV2c	NOTIFICATION-TYPE
                STATUS  current
        	DESCRIPTION		
                      "The condition has cleared. The modem PLL is not failing."
        ::= { apSnmpV2Traps 27 }
                
	modemModLossOfSyncBytesClearedV2c	NOTIFICATION-TYPE
                STATUS  current
        	DESCRIPTION		
                      "The condition has cleared. The modem is not experiencing loss of synch bytes."
        ::= { apSnmpV2Traps 28 }
                
	modemModInputFifoOverUnderClearedV2c	NOTIFICATION-TYPE
                STATUS  current
        	DESCRIPTION		
                      "The condition has cleared. The modem is not experiencing input FIFO 
                      over/under runs."
        ::= { apSnmpV2Traps 29 }
                
	modemModInputDataInacClearedV2c	NOTIFICATION-TYPE
                STATUS  current
        	DESCRIPTION		
                      "The condition has cleared. The modem is not experiencing data inactivity."
        ::= { apSnmpV2Traps 30 }
                
	snrBelowThresholdClearedV2c	NOTIFICATION-TYPE
                STATUS  current
        	DESCRIPTION		
                      "The condition has cleared. SNR is now above its minimum threshold value."
        ::= { apSnmpV2Traps 31 }
                
	radioPLDROLostLockClearedV2c	NOTIFICATION-TYPE
                STATUS  current
        	DESCRIPTION		
                      "The condition has cleared. The radio PLDRO/LO lost lock condition has cleared."
        ::= { apSnmpV2Traps 32 }
        
        
        radioLostCommunicationClearedV2c	NOTIFICATION-TYPE
                STATUS  current
        	DESCRIPTION     
                     "The condition has cleared. RS232 communication has been re-establisted between
                     AIRPAIR and the radio."
        ::= { apSnmpV2Traps 33 }

        
        radioMismatchClearedV2c	NOTIFICATION-TYPE
                STATUS  current
        	DESCRIPTION     
                     "The condtion has cleared. The radio matches the programmed parameters in the modem."
        ::= { apSnmpV2Traps 34 }

        radioPowerAmpClearedV2c	NOTIFICATION-TYPE
                STATUS  current
        	DESCRIPTION     
                      "The condtion has cleared. The radio Power Amp is not in the failed state."
        ::= { apSnmpV2Traps 35 }
        
        ifTxSynthUnlockedClearedV2c	NOTIFICATION-TYPE
                STATUS  current
        	DESCRIPTION     
                      "The condtion has cleared. The IF stage transmit synthesizer is now locked."
        ::= { apSnmpV2Traps 36 }
        
        ifRxSynthUnlockedClearedV2c	NOTIFICATION-TYPE
                STATUS  current
        	DESCRIPTION     
                      "The condtion has cleared. The IF stage receive synthesizer is now locked."
        ::= { apSnmpV2Traps 37 }
        
        

        rslBelowThresholdClearedV2c        NOTIFICATION-TYPE
                STATUS  current
        	DESCRIPTION     "The condition has cleared. RSL is now above its minimum threshold."
        ::= { apSnmpV2Traps 38 }



        droppedFramesThresholdExceededClearedV2c        NOTIFICATION-TYPE
                STATUS  current
        	DESCRIPTION     
                      "The condition has cleared.The ethernet dropped frames threshold is now 
                      below its threshold value."
        ::= { apSnmpV2Traps 39 }
        

        bwUtilizationThresholdExceededClearedV2c        NOTIFICATION-TYPE
                STATUS  current
        	DESCRIPTION     
                       "The condition has cleared. The ethernet bandwidth threshold is now below 
                       its threshold value."
        ::= { apSnmpV2Traps 40 }
        
     rxIfCableLossExceededV2c        NOTIFICATION-TYPE
     		STATUS  current
        	DESCRIPTION     
                       "The Rx cable loss has exceeded limit. This trap is only valid when the
                       AirPair installation type is IDU-ODU split."
        ::= { apSnmpV2Traps 41 }
        
     rxIfCableLossExceededClearedV2c        NOTIFICATION-TYPE
        	STATUS  current
        	DESCRIPTION     
                       "The condition has cleared. The Rx cable loss is now within limit. This trap
                       is only valid when the AirPair installation type is IDU-ODU split"
        ::= { apSnmpV2Traps 42 }
        

     txIfCableLossExceededV2c        NOTIFICATION-TYPE
        	STATUS  current
        	DESCRIPTION     
                      "The Tx cable loss has exceeded limit. This trap is only valid when the AirPair
                      installation type is IDU-ODU split"
        ::= { apSnmpV2Traps 43 }
        
     txIfCableLossExceededClearedV2c        NOTIFICATION-TYPE
        	STATUS  current
        	DESCRIPTION     
                      "The condition has cleared. The Tx cable loss is now within limit. This trap is
                       only valid when the AirPair installation type is IDU-ODU split"
        ::= { apSnmpV2Traps 44 }
        
     fan1FailedV2c        NOTIFICATION-TYPE
        	STATUS  current
        	DESCRIPTION     
                       "The Fan1 has failed. This trap is only valid when the AirPair installation 
                        type is IDU-ODU split"
        ::= { apSnmpV2Traps 45 }
        
     fan1FailedClearedV2c        NOTIFICATION-TYPE
        	STATUS  current
        	DESCRIPTION     
                       "The condition has cleared. The fan1 is running normally. This trap is only 
                        valid when the AirPair installation type is IDU-ODU split"
        ::= { apSnmpV2Traps 46 }
        
     fan2FailedV2c        NOTIFICATION-TYPE
        	STATUS  current
        	DESCRIPTION     
                      "The Fan2 has failed. This trap is only valid when the AirPair installation 
                       type is IDU-ODU split"
        ::= { apSnmpV2Traps 47 }
        
     fan2FailedClearedV2c        NOTIFICATION-TYPE
        	STATUS  current
        	DESCRIPTION     
                      "The condition has cleared. The fan2 is running normally. This trap is only valid
                      when the AirPair installation type is IDU-ODU split"
        ::= { apSnmpV2Traps 48 }

     
     modemCardMismatchedHardwareFirmwareV2c        NOTIFICATION-TYPE
        	STATUS  current
        	DESCRIPTION     
                      "The modem card has incompatible hardware and firmware. The firmware will not run properly on this card."
        ::= { apSnmpV2Traps 49 }

     modemCardMismatchedHardwareFirmwareClearedV2c        NOTIFICATION-TYPE
        	STATUS  current
        	DESCRIPTION     
                      "The condition has cleared. The modem card has compatible hardware and firmware. The firmware will run properly on this card."
        ::= { apSnmpV2Traps 50 }

     atpcConfigMismatchV2c        NOTIFICATION-TYPE
        	STATUS  current
        	DESCRIPTION     
                      "ATPC configuration mismatch in the Airpair systems. ATPC is 
                       enabled at one system, but ATPC is not enabled at the other 
                       system."

        ::= { apSnmpV2Traps 51 }
        
     atpcConfigMismatchClearedV2c        NOTIFICATION-TYPE
        	STATUS  current
        	DESCRIPTION     
                      "ATPC configuration mismatch in the Airpair systems is cleared. 
                       Both systems enabled ATPC."

        ::= { apSnmpV2Traps 52 }


    radioHiPwrOptM1V2c             NOTIFICATION-TYPE
        	STATUS             current
        	DESCRIPTION        "When hi-power radio is used, hi-power gate M1 drain current is 
                                    out of lower or upper limits."
        ::= { apSnmpV2Traps  53 } 

    radioHiPwrOptM1ClearedV2c      NOTIFICATION-TYPE
        	STATUS  current
        	DESCRIPTION           "When hi-power radio is used, hi-power gate M1 drain current 
                                       is between lower and upper limits."
        ::= { apSnmpV2Traps 54 } 

    radioHiPwrOptM2V2c            NOTIFICATION-TYPE
        	STATUS  current
        	DESCRIPTION        "When hi-power radio is used, hi-power gate M2 drain current is 
                                    out of lower or upper limits."
        ::= { apSnmpV2Traps 55 } 

    radioHiPwrOptM2ClearedV2c     NOTIFICATION-TYPE
         	STATUS  current
        	DESCRIPTION           "When hi-power radio is used, hi-power gate M2 drain current 
                                       is between lower and upper limits."
        ::= { apSnmpV2Traps 56 } 
                
    radioHiPwrTxDetectorV2c       NOTIFICATION-TYPE
        	STATUS  current
        	DESCRIPTION          "When hi-power radio is used, hi-power tx detector dBm value 
                                      is smaller than limit."
        ::= { apSnmpV2Traps 57 } 

    radioHiPwrTxDetectorClearedV2c     NOTIFICATION-TYPE
        	STATUS  current
        	DESCRIPTION               "When hi-power radio is used, hi-power tx detector dBm 
                                           value is not smaller than limit."
        ::= { apSnmpV2Traps 58 }  

    sntpServersUnreachableV2c       NOTIFICATION-TYPE
       	      	      STATUS       current
        	DESCRIPTION        "Can't reach any of the sntp servers"
        ::=  { apSnmpV2Traps 59 }  

    sntpServersUnreachableClearedV2c     NOTIFICATION-TYPE
        	       	STATUS          current
         	   DESCRIPTION          "At least one of SNTP servers is reachable"
        ::= { apSnmpV2Traps 60 }       


    rlsMismatchV2c       NOTIFICATION-TYPE
       	      	         STATUS       current
        DESCRIPTION        "RLS mismatch"
        ::=  { apSnmpV2Traps 61 }  

    rlsMismatchClearedV2c              NOTIFICATION-TYPE
        	       	STATUS          current
         	   DESCRIPTION          "RLS mismatch cleared"
        ::= { apSnmpV2Traps 62 }       


    rLSShutdownActivatedV2c           NOTIFICATION-TYPE
       	      	      STATUS          current
        	DESCRIPTION           "RLS shutdown is activated"
        ::=  { apSnmpV2Traps 63 }  


    rLSShutdownActivatedClearedV2c     NOTIFICATION-TYPE
        	       	STATUS          current
         	   DESCRIPTION          "RLS shutdown is not activated"
        ::= { apSnmpV2Traps 64 }       

--
-- FREQUENCY FILE RELATED TRAPS
--
   frequencyFileInvalidV2c	        NOTIFICATION-TYPE
		STATUS  current
        	DESCRIPTION             "When the executing frequency file is invalid, 
					this trap is generated."
        ::= { apSnmpV2Traps 65 }      



   optionalParaNotEntFreqFileV2c	        NOTIFICATION-TYPE
		STATUS  current
        	DESCRIPTION               "when the optional parameters are not entered in frequency file,
                                           and the system boots up, this trap is generated."
        ::= { apSnmpV2Traps 66 }      



   progRadioBandNotFoundFreqFileV2c	        NOTIFICATION-TYPE
		STATUS  current
        	DESCRIPTION               "when the executing frequency file doesn't contain the info related to programmed
                                           radio band, this trap is generated."
        ::= { apSnmpV2Traps 67 }      


redundancySwitchOverSuccessV2c     NOTIFICATION-TYPE
        	       	STATUS          current
         	   DESCRIPTION          "Radio Redundancy Switch over success"
        ::= { apSnmpV2Traps 68 }

redundancySwitchOverFailedV2c     NOTIFICATION-TYPE
        	       	STATUS          current
         	   DESCRIPTION          "Radio Redundancy Switch over failed"
        ::= { apSnmpV2Traps 69 }

redundancyNoAtpcSupportV2c     NOTIFICATION-TYPE
        	       	STATUS          current
         	   DESCRIPTION          "Radio does not support atpc"
        ::= { apSnmpV2Traps 70 }

redundancyNoAtpcSupportClearedV2c     NOTIFICATION-TYPE
        	       	STATUS          current
         	   DESCRIPTION          "Radio does not support atpc cleared"
        ::= { apSnmpV2Traps 71 }

redundancyInvalidFirmwareV2c     NOTIFICATION-TYPE
        	       	STATUS          current
         	   DESCRIPTION          "Radio firmware on radio and on modem card mismatch"
        ::= { apSnmpV2Traps 72 }

redundancyInvalidFirmwareClearedV2c     NOTIFICATION-TYPE
        	       	STATUS          current
         	   DESCRIPTION          "Radio firmware mismatch cleared"
        ::= { apSnmpV2Traps 73 }

redundancySwitchInitByLocalendV2c     NOTIFICATION-TYPE
        	       	STATUS          current
         	   DESCRIPTION          "Radio switch initiated by local end"
        ::= { apSnmpV2Traps 74 }

redundancySwitchInitByPeerV2c     NOTIFICATION-TYPE
        	       	STATUS          current
         	   DESCRIPTION          "Radio switch initiated by peer"
        ::= { apSnmpV2Traps 75 }

aamConfigMisMatchV2c     NOTIFICATION-TYPE
        	       	STATUS          current
         	   DESCRIPTION          "Automatic Adaptive modulation configuration mismatch"
        ::= { apSnmpV2Traps 76 }

aamConfigMisMatchClearV2c     NOTIFICATION-TYPE
        	       	STATUS          current
         	   DESCRIPTION          "Automatic Adaptive modulation configuration mismatch cleared"
        ::= { apSnmpV2Traps 77 }

aamQpskActiveV2c     NOTIFICATION-TYPE
        	       	STATUS          current
         	   DESCRIPTION          "Automatic Adaptive modulation running on QPSK modulation"
        ::= { apSnmpV2Traps 78 }

aamQpskActiveClearedV2c     NOTIFICATION-TYPE
        	       	STATUS          current
         	   DESCRIPTION          "Automatic Adaptive modulation running on higher modulation"
        ::= { apSnmpV2Traps 79 }

primaryRadioFaultyV2c NOTIFICATION-TYPE
        	       	STATUS          current
         	   DESCRIPTION          "Primary radio is faulty."
        ::= { apSnmpV2Traps 80 }


primaryRadioFaultyClearedV2c  NOTIFICATION-TYPE
        	       	STATUS          current
         	   DESCRIPTION          "primary radio is not faulty anymore."
        ::= { apSnmpV2Traps 81 }

radioSerialNumberMismatchV2c NOTIFICATION-TYPE
        	       	STATUS          current
         	   DESCRIPTION          "Redundancy, Radio Serial number mismatch."
        ::= { apSnmpV2Traps 82 }


radioSerialNumberMismatchClearedV2c  NOTIFICATION-TYPE
        	       	STATUS          current
         	   DESCRIPTION          "Redundancy, Radio Serial number mismatch cleared."
        ::= { apSnmpV2Traps 83 }


excessiveCableLossChangeV2c  NOTIFICATION-TYPE				
        	   STATUS          current
         	   DESCRIPTION          "Excessive cable loss change"
        ::= { apSnmpV2Traps 84 }

excessiveCableLossChangeClearedV2c  NOTIFICATION-TYPE
      	       	STATUS          current
         	DESCRIPTION          "Excessive cable loss change cleared"
        ::= { apSnmpV2Traps 85 }

END
