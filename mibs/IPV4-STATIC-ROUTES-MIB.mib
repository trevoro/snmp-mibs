IPV4-STATIC-ROUTES-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, Integer32,IpAddress
			FROM SNMPv2-SMI
		RowStatus, TruthValue
			FROM SNMPv2-TC
		apIpv4StaticRoutes
			FROM APENT-MIB;


    apIpv4StaticRoutesMib MODULE-IDENTITY
	   LAST-UPDATED "9802072000Z" -- Sat February 07 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for IPv4 Static Routes."
      ::= { apIpv4StaticRoutes 1}

--arrowpoint
-- apmgmt
--  ipv4Ext
--   apIpv4StaticRoutes
--     apIpv4StaticRouteTable

-- static route table

apIpv4StaticRouteTable OBJECT-TYPE
	SYNTAX      SEQUENCE OF ApIpv4StaticRouteEntry
	MAX-ACCESS  not-accessible
	STATUS      current
	DESCRIPTION
		"A table of IP static routes."
	::= {apIpv4StaticRoutes 2}

apIpv4StaticRouteEntry OBJECT-TYPE
	SYNTAX      ApIpv4StaticRouteEntry
	MAX-ACCESS  not-accessible
	STATUS      current
	DESCRIPTION
	       "ArrowPoint static route table extensions"
	INDEX  {apIpv4SrAddress, apIpv4SrPrefixLen,
 	        apIpv4SrNextHop}
	--DEFAULT apjam-group apIpv4StaticRouteInst, apIpv4SrAddress
	--DEFAULT apjam-popup-def apIpv4StaticRouteInst, Properties, local
	--DEFAULT apjam-popup-def apIpv4StaticRouteInst, Delete, special, apIpv4SrStatus
	--DEFAULT apjam-wizard	Static Route Wizard, 1, images/arrowlogo.gif, "Static Routes Setup wizard.  Set next hop to 255.255.255.255 to create a blackhole route."
	::= {apIpv4StaticRouteTable 1}

ApIpv4StaticRouteEntry ::=
	SEQUENCE {
	       apIpv4SrAddress              IpAddress,
	       apIpv4SrPrefixLen            Integer32,
	       apIpv4SrNextHop              IpAddress,
	       apIpv4SrDistance             Integer32,
	       apIpv4SrRepeat               Integer32,
	       apIpv4SrInUse                INTEGER,
           apIpv4SrStatus               RowStatus,
	       apIpv4SrScmOnly              TruthValue,
	       apIpv4SrFirewall             TruthValue,
	       apIpv4SrRouteIndex           Integer32
		 }

apIpv4SrAddress OBJECT-TYPE
	SYNTAX      IpAddress
	MAX-ACCESS  read-only
	STATUS      current
	DESCRIPTION
	       "The route address"
	--DEFAULT ap-display-name	IP Address
	--DEFAULT apjam-popup-ref apIpv4StaticRouteInst, Properties
	--DEFAULT apjam-wizard-field	1, normal
	--DEFAULT apjam-noedit-dlg	True
	::= {apIpv4StaticRouteEntry 1}

apIpv4SrPrefixLen OBJECT-TYPE
	SYNTAX      Integer32
	MAX-ACCESS  read-only
	STATUS      current
	DESCRIPTION
	       "The prefix length of the route."
	--DEFAULT ap-display-name	Prefix Length
	--DEFAULT apjam-popup-ref apIpv4StaticRouteInst, Properties
	--DEFAULT apjam-wizard-field	1, normal
	--DEFAULT apjam-noedit-dlg	True
	::= {apIpv4StaticRouteEntry 2}

apIpv4SrNextHop OBJECT-TYPE
	SYNTAX      IpAddress
	MAX-ACCESS  read-only
	STATUS      current
	DESCRIPTION
	       "The address of the next hop.  If this is not a legitimate IP
            address, it is the ifIndex of an unnumbered interface."
	--DEFAULT ap-display-name	Next Hop
	--DEFAULT apjam-popup-ref apIpv4StaticRouteInst, Properties
	--DEFAULT apjam-wizard-field	1, normal
	--DEFAULT apjam-noedit-dlg	True
	::= {apIpv4StaticRouteEntry 3}

apIpv4SrDistance OBJECT-TYPE
	SYNTAX      Integer32 (1..254)
	MAX-ACCESS  read-create
	STATUS      current
	DESCRIPTION
	       "The administrative distance to assign to the route."
    DEFVAL  { 1 }
	--DEFAULT ap-display-name	Distance
	--DEFAULT apjam-popup-ref apIpv4StaticRouteInst, Properties
	--DEFAULT ap-create-requires Yes
	--DEFAULT apjam-wizard-field	1, normal
	::= {apIpv4StaticRouteEntry 4}

apIpv4SrRepeat OBJECT-TYPE
	SYNTAX      Integer32
	MAX-ACCESS  read-create
	STATUS      current
	DESCRIPTION
	       "DEBUG FEATURE ONLY: The number of consecutive routes to create,
            starting at this address.  Not available in shipping code."
	::= {apIpv4StaticRouteEntry 5}

apIpv4SrInUse OBJECT-TYPE
    SYNTAX   INTEGER {
                inUse    (1),  -- route is currently in use
                notInUse (2)   -- route is not currently in use
             }
	MAX-ACCESS  read-only
	STATUS      current
	DESCRIPTION
	       "The current state of the route in relation to the forwarding
            table."
    DEFVAL  { 2 }
	--DEFAULT ap-display-name	Status
	--DEFAULT apjam-popup-ref apIpv4StaticRouteInst, Properties
	--DEFAULT apjam-noedit-dlg	True
	::= {apIpv4StaticRouteEntry 6}

apIpv4SrStatus OBJECT-TYPE
	SYNTAX      RowStatus
	MAX-ACCESS  read-create
	STATUS      current
	DESCRIPTION
	       "(fill in later)"
	::= {apIpv4StaticRouteEntry 7}

apIpv4SrScmOnly OBJECT-TYPE
	SYNTAX      TruthValue
	MAX-ACCESS  read-create
	STATUS      current
	DESCRIPTION
	       "This route is only used for packets originating from the box
            and is not propagated to SFMs."
	::= {apIpv4StaticRouteEntry 8}

apIpv4SrFirewall OBJECT-TYPE
	SYNTAX      TruthValue
	MAX-ACCESS  read-create
	STATUS      current
	DESCRIPTION
	       "Indicates whether the switch should use firewall load-balancing
		for this route."
	::= {apIpv4StaticRouteEntry 9}

apIpv4SrRouteIndex OBJECT-TYPE
	SYNTAX      Integer32 (1..15)
	MAX-ACCESS  read-create
	STATUS      current
	DESCRIPTION
	       "Identifies the route index."
    DEFVAL  { 1 }
	--DEFAULT ap-display-name	Firewall Id
	--DEFAULT apjam-popup-ref apIpv4StaticRouteInst, Properties
	--DEFAULT ap-create-requires Yes
	--DEFAULT apjam-wizard-field	1, normal
	::= {apIpv4StaticRouteEntry 10}

-- static firewall index table

apIpv4StaticFirewallTable OBJECT-TYPE
	SYNTAX      SEQUENCE OF ApIpv4StaticFirewallEntry
	MAX-ACCESS  not-accessible
	STATUS      current
	DESCRIPTION
		"A table of IP static firewalls."
	::= {apIpv4StaticRoutes 3}

apIpv4StaticFirewallEntry OBJECT-TYPE
	SYNTAX      ApIpv4StaticFirewallEntry
	MAX-ACCESS  not-accessible
	STATUS      current
	DESCRIPTION
	       "ArrowPoint static firewall table extensions"
	INDEX  {apIpv4FirewallIndex}
	::= {apIpv4StaticFirewallTable 1}

ApIpv4StaticFirewallEntry ::=
	SEQUENCE {
	       apIpv4FirewallIndex                Integer32,
	       apIpv4FirewallNextHop              IpAddress,
	       apIpv4FirewallRemoteAddress        IpAddress,
	       apIpv4FirewallRemoteSwitch         IpAddress,
           apIpv4FirewallStatus               RowStatus
		 }

apIpv4FirewallIndex OBJECT-TYPE
	SYNTAX      Integer32 (1..15)
	MAX-ACCESS  read-create
	STATUS      current
	DESCRIPTION
	       "The firewall index"
	::= {apIpv4StaticFirewallEntry 1}

apIpv4FirewallNextHop OBJECT-TYPE
	SYNTAX      IpAddress
	MAX-ACCESS  read-create
	STATUS      current
	DESCRIPTION
	       "The address of the next hop."
	::= {apIpv4StaticFirewallEntry 2}

apIpv4FirewallRemoteAddress OBJECT-TYPE
	SYNTAX      IpAddress
	MAX-ACCESS  read-create
	STATUS      current
	DESCRIPTION
	       "The assigned firewall IP address that connects to the remote 
		subnet."
	::= {apIpv4StaticFirewallEntry 3}

apIpv4FirewallRemoteSwitch OBJECT-TYPE
	SYNTAX      IpAddress
	MAX-ACCESS  read-create
	STATUS      current
	DESCRIPTION
	       "The switch IP address that is connected to firewall remote
		subnet."
	::= {apIpv4StaticFirewallEntry 4}

apIpv4FirewallStatus OBJECT-TYPE
	SYNTAX      RowStatus
	MAX-ACCESS  read-create
	STATUS      current
	DESCRIPTION
	       "(fill in later)"
	::= {apIpv4StaticFirewallEntry 5}

END
