-- Do not edit this file.
-- It is generated automatically by mib-expand
-- from call.mib.in and *.mibdef.
--			Ascend Call Mib
--
--			Lucent Technologies,, Inc
--			1275 Harbor Bay Pkwy
--			Alameda, CA 94502
--			+1 510 769 6001
--			info@ascend.com
--
--		Copyright (c) 1999 Lucent Technologies, Inc.
--		All rights reserved.
--
-- $Id: call.mib.in,v 1.1.2.2 2000/05/25 02:06:03 ayadav Exp $
--
-- 11 Mar 97 rm  Initially created
-- 25 May 99 AKS Added callCalledPartyID callCallingPartyID callMultiLinkID
--                     callActiveCalledPartyID callActiveCallingPartyID 
--                     callActiveMultiLinkID
--

ASCEND-CALL-MIB DEFINITIONS ::= BEGIN

    IMPORTS
	callStatusGroup
	    FROM ASCEND-MIB
        DisplayString
            FROM RFC1213-MIB
	OBJECT-TYPE
	    FROM RFC-1212;

	--
	-- Ascend Call Status group
	--
	-- This group contains a table of entries for the status of each
	-- possible call in the system.
	--

    callStatusMaximumEntries  OBJECT-TYPE
	SYNTAX		INTEGER
	ACCESS		read-only
	STATUS		mandatory
	DESCRIPTION	"The maximum number of entries that can exist
			 in the call status table."
	::= { callStatusGroup 1 }

    callStatusTable	OBJECT-TYPE
	SYNTAX		SEQUENCE OF CallStatusEntry
	ACCESS		not-accessible
	STATUS		mandatory
	DESCRIPTION	"A list of call status entries."
	::= { callStatusGroup 2 }

    callStatusEntry	OBJECT-TYPE
	SYNTAX		CallStatusEntry
	ACCESS		not-accessible
	STATUS		mandatory
	DESCRIPTION	"An entry containing object variables to describe
			 a call's status."
	INDEX		{ callStatusIndex }
	::= { callStatusTable 1 }

    CallStatusEntry ::=
	SEQUENCE {
	    callStatusIndex
		INTEGER,
	    callStatusValidFlag
		INTEGER,
	    callStatusStartingTimeStamp
		INTEGER,
	    callStatusCallReferenceNum
		INTEGER,
	    callStatusDataRate
		INTEGER,
	    callStatusSlotNumber
		INTEGER,
	    callStatusSlotLineNumber
		INTEGER,
	    callStatusSlotChannelNumber
		INTEGER,
	    callStatusModemSlotNumber
		INTEGER,
	    callStatusModemOnSlot
		INTEGER,
	    callStatusIfIndex
		INTEGER,
	    callSessionIndex
		INTEGER,
            callStatusType
                INTEGER,
	    callStatusXmitRate
		INTEGER,
            callStatusPortType
                INTEGER,
            callStatusCalledParyID
                DisplayString,
            callStatusCallingPartyID
                DisplayString,
            callStatusMultiLinkID
                INTEGER
	}

    callStatusIndex	OBJECT-TYPE
	SYNTAX		INTEGER
	ACCESS		read-only
	STATUS		mandatory
	DESCRIPTION	"The index number for this call status entry. Its
			 value ranges from 1 to 'callStatusMaximumEntries'."
	::= { callStatusEntry 1 }

    callStatusValidFlag OBJECT-TYPE
	SYNTAX		INTEGER {
			    invalid(1),
			    valid(2)
			}
	ACCESS		read-only
	STATUS		mandatory
	DESCRIPTION	"Value indicates whether this entry indexed by
			 'callStatusIndex' contains valid information or not."
	::= { callStatusEntry 2 }

    callStatusStartingTimeStamp	 OBJECT-TYPE
	SYNTAX		INTEGER
	ACCESS		read-only
	STATUS		mandatory
	DESCRIPTION	"The starting time for this call in seconds
			 since startup.	 A value of 0 is returned if
			 entry is invalid (ie. 'callStatusValidFlag' is
			 invalid(1))."
	::= { callStatusEntry 3 }

    callStatusCallReferenceNum  OBJECT-TYPE
--	SYNTAX		INTEGER (1..'7fffffff'h)
	SYNTAX		INTEGER
	ACCESS		read-only
	STATUS		mandatory
	DESCRIPTION	"The unique number identifying the session for which
			 this call is associated. A value of 0 is returned
			 if entry is invalid."
	::= { callStatusEntry 4 }

    callStatusDataRate	OBJECT-TYPE
	SYNTAX		INTEGER
	ACCESS		read-only
	STATUS		mandatory
	DESCRIPTION	"The receive rate for ISDN calls or the baud rate
			 for modem calls. A value of 0 is returned if entry
			 is invalid."
	::= { callStatusEntry 5 }

    callStatusSlotNumber    OBJECT-TYPE
	SYNTAX		INTEGER
	ACCESS		read-only
	STATUS		mandatory
	DESCRIPTION	"Identifies the slot of the line being used.  It's
			 value ranges between 1 and the value 'slotNumber'
			 in Ascend's slots group. This variable is equivalent
			 to 'slotIndex' in the slot group.  A value of 0 is
			 returned if entry is invalid."
	::= { callStatusEntry 6 }

    callStatusSlotLineNumber  OBJECT-TYPE
	SYNTAX		INTEGER
	ACCESS		read-only
	STATUS		mandatory
	DESCRIPTION	"Identifies the line for network slots. This variable
			 is equivalent to 'slotItemIndex' in Ascend's slot
			 group. A value of 0 is returned if entry is invalid."
	::= { callStatusEntry 7 }

    callStatusSlotChannelNumber	 OBJECT-TYPE
	SYNTAX		INTEGER
	ACCESS		read-only
	STATUS		mandatory
	DESCRIPTION	"Identifies the channel for the particular line
			 identified by 'callStatusSlotLineNumber'. A value
			 of 0 is returned if entry is invalid."
	::= { callStatusEntry 8 }

    callStatusModemSlotNumber  OBJECT-TYPE
	SYNTAX		INTEGER
	ACCESS		read-only
	STATUS		mandatory
	DESCRIPTION	"Identifies the slot on the device.  It's
			 value ranges between 1 and the value 'slotNumber'
			 in Ascend's slot group. A value of 0 is returned
			 if entry is invalid."
	::= { callStatusEntry 9 }

    callStatusModemOnSlot   OBJECT-TYPE
	SYNTAX		INTEGER
	ACCESS		read-only
	STATUS		mandatory
	DESCRIPTION	"It identifies the particular port within a slot. 
			 A value of 0 is returned if entry is invalid."
	::= { callStatusEntry 10 }

    callStatusIfIndex	OBJECT-TYPE
	SYNTAX		INTEGER
	ACCESS		read-only
	STATUS		mandatory
	DESCRIPTION	"The interface index, ranging from 1 to the number of
			 interfaces specified in the MIB-II variable ifNumber.
			 The interface identified by a particular value of
			 this index is the same interface as identified by the
			 same value if ifIndex. A value of 0 is returned if
			 entry is invalid."
	::= { callStatusEntry 11 }

    callSessionIndex	OBJECT-TYPE
	SYNTAX		INTEGER
	ACCESS		read-only
	STATUS		mandatory
	DESCRIPTION	"The index of the associated session entry.  Value
			 ranges from 1 to 'ssnStatusMaximumSessions'.
			 A value of 0 is returned if entry is invalid."
	::= { callStatusEntry 12 }

    callStatusType      OBJECT-TYPE
        SYNTAX          INTEGER   {
                        callOutgoing(1),    -- outgoing call
                        callIncoming(2)     -- incoming call
        }
        ACCESS          read-only
        STATUS          mandatory
        DESCRIPTION     "A value of 0 is returned if entry is invalid."
        ::= { callStatusEntry 13 }

    callStatusXmitRate	OBJECT-TYPE
	SYNTAX		INTEGER
	ACCESS		read-only
	STATUS		mandatory
	DESCRIPTION	"The transmit rate for ISDN calls or the baud rate
			 for modem calls. A value of 0 is returned if entry
			 is invalid."
	::= { callStatusEntry 14 }

    callStatusPortType	OBJECT-TYPE
	SYNTAX		INTEGER {
                        callPortUnknown(1),
                        callPortAsync(2),
                        callPortSync(3),
                        callPortISDNSync(4),
                        callPortISDNAsyncV120(5),
                        callPortISDNAsyncV110(6),
                        callPortVirtual(7),
                        callPortISDNAsyncV32(8),
                        callPortISDNAsyncVDSP(9)
        }
	ACCESS		read-only
	STATUS		mandatory
	DESCRIPTION	"The port type associated with the call."
	::= { callStatusEntry 15 }

     callStatusCalledParyID   OBJECT-TYPE
         SYNTAX         DisplayString
         ACCESS         read-only
         STATUS         mandatory
         DESCRIPTION    "The called party Number. In case of incoming calls
                         this is set to the DNIS, in the case of outgoing 
                         calls this is set to the number dialed."
	::= { callStatusEntry 16 }

     callStatusCallingPartyID OBJECT-TYPE
         SYNTAX         DisplayString
         ACCESS         read-only
         STATUS         mandatory
         DESCRIPTION    "The calling party Number. In the case of incoming calls
                         this variable is set to the CLID ( calling Line Identification )
                         received. This variable is set to the empty string for 
                         outgoing calls."
        ::= { callStatusEntry 17 }

     callStatusMultiLinkID    OBJECT-TYPE
         SYNTAX         INTEGER
         ACCESS         read-only
         STATUS         mandatory
         DESCRIPTION    "This is applicable only when the call is part
                         of an MPP bundle, for other cases it is 0."
        ::= { callStatusEntry 18 }

-- Defination of the callStatus Talble ends here.

    callStatusHighWaterMark OBJECT-TYPE
	SYNTAX		INTEGER
	ACCESS		read-write
	STATUS		mandatory
	DESCRIPTION	"The highest number of channels ever used on the 
			 wide area network since power up. Nailed channels,
                         if any, are also included in this count. Its value can
			 be set to zero with a SET command."
	::= { callStatusGroup 3 }

    callCurrentAnalogOutgoing OBJECT-TYPE
	SYNTAX		INTEGER
	ACCESS		read-only
	STATUS		mandatory
	DESCRIPTION	"The number of current analog outgoing calls
                         is returned."
	::= { callStatusGroup 4 }

    callCurrentAnalogIncoming OBJECT-TYPE
	SYNTAX		INTEGER
	ACCESS		read-only
	STATUS		mandatory
	DESCRIPTION	"The number of current analog incoming calls
                         is returned."
	::= { callStatusGroup 5 }

    callCurrentDigitalOutgoing OBJECT-TYPE
	SYNTAX		INTEGER
	ACCESS		read-only
	STATUS		mandatory
	DESCRIPTION	"The number of current digital outgoing calls
                         is returned."
	::= { callStatusGroup 6 }

    callCurrentDigitalIncoming OBJECT-TYPE
	SYNTAX		INTEGER
	ACCESS		read-only
	STATUS		mandatory
	DESCRIPTION	"The number of current digital incoming calls
                         is returned."
	::= { callStatusGroup 7 }

    callCurrentFROutgoing OBJECT-TYPE
	SYNTAX		INTEGER
	ACCESS		read-only
	STATUS		mandatory
	DESCRIPTION	"The number of current frame relay outgoing calls
                         is returned."
	::= { callStatusGroup 8 }

    callCurrentFRIncoming OBJECT-TYPE
	SYNTAX		INTEGER
	ACCESS		read-only
	STATUS		mandatory
	DESCRIPTION	"The number of current frame relay incoming calls
                         is returned."
	::= { callStatusGroup 9 }

    callTotalAnalogOutgoing OBJECT-TYPE
	SYNTAX		INTEGER
	ACCESS		read-write
	STATUS		mandatory
	DESCRIPTION	"The total number of analog outgoing calls
                         since system bootup or last clear of the
                         variable is returned."
	::= { callStatusGroup 10 }

    callTotalAnalogIncoming OBJECT-TYPE
	SYNTAX		INTEGER
	ACCESS		read-write
	STATUS		mandatory
	DESCRIPTION	"The total number of analog incoming calls
                         since system bootup or last clear of the
                         variable is returned."
	::= { callStatusGroup 11 }

    callTotalDigitalOutgoing OBJECT-TYPE
	SYNTAX		INTEGER
	ACCESS		read-write
	STATUS		mandatory
	DESCRIPTION	"The total number of digital outgoing calls
                         since system bootup or last clear of the
                         variable is returned."
	::= { callStatusGroup 12 }

    callTotalDigitalIncoming OBJECT-TYPE
	SYNTAX		INTEGER
	ACCESS		read-write
	STATUS		mandatory
	DESCRIPTION	"The total number of digital incoming calls
                         since system bootup or last clear of the
                         variable is returned."
	::= { callStatusGroup 13 }

    callTotalFROutgoing OBJECT-TYPE
	SYNTAX		INTEGER
	ACCESS		read-write
	STATUS		mandatory
	DESCRIPTION	"The total number of frame relay outgoing calls
                         since system bootup or last clear of the
                         variable is returned."
	::= { callStatusGroup 14 }

    callTotalFRIncoming OBJECT-TYPE
	SYNTAX		INTEGER
	ACCESS		read-write
	STATUS		mandatory
	DESCRIPTION	"The total number of frame relay incoming calls
                         since system bootup or last clear of the
                         variable is returned."
	::= { callStatusGroup 15 }

    callActiveTable	OBJECT-TYPE
	SYNTAX		SEQUENCE OF CallActiveEntry
	ACCESS		not-accessible
	STATUS		mandatory
	DESCRIPTION	"A list of active call status entries."
	::= { callStatusGroup 16 }

    callActiveEntry	OBJECT-TYPE
	SYNTAX		CallActiveEntry
	ACCESS		not-accessible
	STATUS		mandatory
	DESCRIPTION	"An entry containing object variables to describe
			 an active call's status."
	INDEX		{ callActiveCallReferenceNum }
	::= { callActiveTable 1 }

    CallActiveEntry ::=
	SEQUENCE {
	    callActiveCallReferenceNum
		INTEGER,
	    callActiveIndex
		INTEGER,
	    callActiveValidFlag
		INTEGER,
	    callActiveStartingTimeStamp
		INTEGER,
	    callActiveDataRate
		INTEGER,
	    callActiveSlotNumber
		INTEGER,
	    callActiveSlotLineNumber
		INTEGER,
	    callActiveSlotChannelNumber
		INTEGER,
	    callActiveModemSlotNumber
		INTEGER,
	    callActiveModemOnSlot
		INTEGER,
	    callActiveIfIndex
		INTEGER,
	    callActiveSessionIndex
		INTEGER,
            callActiveType
                INTEGER,
	    callActiveXmitRate
		INTEGER,
            callActivePortType
		INTEGER,
            callActiveCalledParyID
                DisplayString,
            callActiveCallingPartyID
                DisplayString,
            callActiveMultiLinkID
                INTEGER
	}

    callActiveCallReferenceNum  OBJECT-TYPE
--	SYNTAX		INTEGER (1..'7fffffff'h)
	SYNTAX		INTEGER
	ACCESS		read-only
	STATUS		mandatory
	DESCRIPTION	"The unique number identifying the session for which
			 this call is associated."
	::= { callActiveEntry 1 }

    callActiveIndex	OBJECT-TYPE
	SYNTAX		INTEGER
	ACCESS		read-only
	STATUS		mandatory
	DESCRIPTION	"The index number for this call status entry. Its
			 value ranges from 1 to 'callStatusMaximumEntries'."
	::= { callActiveEntry 2 }

    callActiveValidFlag OBJECT-TYPE
	SYNTAX		INTEGER {
			    invalid(1),
			    valid(2)
			}
	ACCESS		read-only
	STATUS		mandatory
	DESCRIPTION	"valid(2) for all active calls."
	::= { callActiveEntry 3 }

    callActiveStartingTimeStamp	 OBJECT-TYPE
	SYNTAX		INTEGER
	ACCESS		read-only
	STATUS		mandatory
	DESCRIPTION	"The starting time for this call in seconds
			 since startup."
	::= { callActiveEntry 4 }

    callActiveDataRate	OBJECT-TYPE
	SYNTAX		INTEGER
	ACCESS		read-only
	STATUS		mandatory
	DESCRIPTION	"The receive rate for ISDN calls or the baud rate
			 for modem calls."
	::= { callActiveEntry 5 }

    callActiveSlotNumber    OBJECT-TYPE
	SYNTAX		INTEGER
	ACCESS		read-only
	STATUS		mandatory
	DESCRIPTION	"Identifies the slot of the line being used.  It's
			 value ranges between 1 and the value 'slotNumber'
			 in Ascend's slots group. This variable is equivalent
			 to 'slotIndex' in the slot group."
	::= { callActiveEntry 6 }

    callActiveSlotLineNumber  OBJECT-TYPE
	SYNTAX		INTEGER
	ACCESS		read-only
	STATUS		mandatory
	DESCRIPTION	"Identifies the line for network slots. This variable
			 is equivalent to 'slotItemIndex' in Ascend's slot
			 group."
	::= { callActiveEntry 7 }

    callActiveSlotChannelNumber	 OBJECT-TYPE
	SYNTAX		INTEGER
	ACCESS		read-only
	STATUS		mandatory
	DESCRIPTION	"Identifies the channel for the particular line
			 identified by 'callActiveSlotLineNumber'."
	::= { callActiveEntry 8 }

    callActiveModemSlotNumber  OBJECT-TYPE
	SYNTAX		INTEGER
	ACCESS		read-only
	STATUS		mandatory
	DESCRIPTION	"Identifies the slot on the device.  It's
			 value ranges between 1 and the value 'slotNumber'
			 in Ascend's slot group. A value of 0 is returned if
			 entry is invalid."
	::= { callActiveEntry 9 }

    callActiveModemOnSlot   OBJECT-TYPE
	SYNTAX		INTEGER
	ACCESS		read-only
	STATUS		mandatory
	DESCRIPTION	"It identifies the particular port within a slot. 
			 A value of 0 is returned if entry is invalid."
	::= { callActiveEntry 10 }

    callActiveIfIndex	OBJECT-TYPE
	SYNTAX		INTEGER
	ACCESS		read-only
	STATUS		mandatory
	DESCRIPTION	"The interface index, ranging from 1 to the number of
			 interfaces specified in the MIB-II variable ifNumber.
			 The interface identified by a particular value of
			 this index is the same interface as identified by the
			 same value if ifIndex."
	::= { callActiveEntry 11 }

    callActiveSessionIndex	OBJECT-TYPE
	SYNTAX		INTEGER
	ACCESS		read-only
	STATUS		mandatory
	DESCRIPTION	"The index of the associated session entry.  Value
			 ranges from 1 to 'ssnActiveMaximumSessions'."
	::= { callActiveEntry 12 }

    callActiveType      OBJECT-TYPE
        SYNTAX          INTEGER   {
                        callOutgoing(1),    -- outgoing call
                        callIncoming(2)     -- incoming call
        }
        ACCESS          read-only
        STATUS          mandatory
        DESCRIPTION     "Differenciates between outgoing and incoming calls."
        ::= { callActiveEntry 13 }

    callActiveXmitRate	OBJECT-TYPE
	SYNTAX		INTEGER
	ACCESS		read-only
	STATUS		mandatory
	DESCRIPTION	"The transmit rate for ISDN calls or the baud rate
			 for modem calls."
	::= { callActiveEntry 14 }

    callActivePortType	OBJECT-TYPE
	SYNTAX		INTEGER {
                        callPortUnknown(1),
                        callPortAsync(2),
                        callPortSync(3),
                        callPortISDNSync(4),
                        callPortISDNAsyncV120(5),
                        callPortISDNAsyncV110(6),
                        callPortVirtual(7),
                        callPortISDNAsyncV32(8),
                        callPortISDNAsyncVDSP(9)
        }
	ACCESS		read-only
	STATUS		mandatory
	DESCRIPTION	"The port type associated with the call."
	::= { callActiveEntry 15 }

     callActiveCalledParyID   OBJECT-TYPE
         SYNTAX         DisplayString
         ACCESS         read-only
         STATUS         mandatory
         DESCRIPTION    "The called party Number. In case of incoming calls
                         this is set to the DNIS, in the case of outgoing 
                         calls this is set to the number dialed."
        ::= { callActiveEntry 16 }

     callActiveCallingPartyID OBJECT-TYPE
         SYNTAX         DisplayString
         ACCESS         read-only
         STATUS         mandatory
         DESCRIPTION    "The calling party Number. In the case of incoming calls
                         this variable is set to the CLID ( calling Line Identification )
                         received. This variable is set to the empty string for outgoing calls."
        ::= { callActiveEntry 17 }

     callActiveMultiLinkID    OBJECT-TYPE
         SYNTAX         INTEGER
         ACCESS         read-only
         STATUS         mandatory
         DESCRIPTION    "This is applicable only when the call is part
                         of an MPP bundle, for other cases it is 0."
        ::= { callActiveEntry 18 }

END
