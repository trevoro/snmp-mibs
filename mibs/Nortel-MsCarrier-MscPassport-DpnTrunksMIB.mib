Nortel-MsCarrier-MscPassport-DpnTrunksMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Gauge32,
      Integer32,
      Unsigned32
   FROM Nortel-MsCarrier-MscPassport-StandardTextualConventionsMIB

      AsciiString,
      NonReplicated,
      PassportCounter64,
      FixedPoint1
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DpnTrunks Enterprise MIB."

dpnTrunksMIB OBJECT IDENTIFIER ::= { mscPassportMIBs 40 }










-- DpnGateway/n
-- The DpnGateway component provides a Passport to DPN-100 
-- connection. It controls a protocol stack associated with a logical 
-- port on a Functional Processor providing a connection to a DPN-
-- 100 Utp Trunk or NetworkLink. The underlying link protocol may 
-- be provided by either Utp or FrAccess. A maximum of 256 
-- instances of DpnGateway may be provisioned on a module.

mscDpnGate OBJECT IDENTIFIER ::= { mscComponents 61 }



mscDpnGateRowStatusTable OBJECT-TYPE
   SYNTAX     SEQUENCE OF MscDpnGateRowStatusEntry
   ACCESS     not-accessible
   STATUS     mandatory
   DESCRIPTION
     "This entry controls the addition and deletion of 
      mscDpnGate components."
::= { mscDpnGate 1 }

mscDpnGateRowStatusEntry OBJECT-TYPE
   SYNTAX     MscDpnGateRowStatusEntry
   ACCESS     not-accessible
   STATUS     mandatory
   DESCRIPTION
     "A single entry in the table represents a single 
      mscDpnGate component."
   INDEX {
      mscDpnGateIndex }
::= { mscDpnGateRowStatusTable 1 }

MscDpnGateRowStatusEntry ::= SEQUENCE {
   mscDpnGateRowStatus
      RowStatus,
   mscDpnGateComponentName
      DisplayString,
   mscDpnGateStorageType
      StorageType,
   mscDpnGateIndex
      Integer32 }

mscDpnGateRowStatus OBJECT-TYPE
   SYNTAX     RowStatus 
   ACCESS     read-write
   STATUS     mandatory
   DESCRIPTION
     "This variable is used as the basis for SNMP naming of
      mscDpnGate components.
      These components can be added and deleted."
::= { mscDpnGateRowStatusEntry 1 }

mscDpnGateComponentName OBJECT-TYPE
   SYNTAX     DisplayString 
   ACCESS     read-only
   STATUS     mandatory
   DESCRIPTION
     "This variable provides the component's string name for
      use with the ASCII Console Interface"
::= { mscDpnGateRowStatusEntry 2 }

mscDpnGateStorageType OBJECT-TYPE
   SYNTAX     StorageType 
   ACCESS     read-only
   STATUS     mandatory
   DESCRIPTION
     "This variable represents the storage type value for the
      mscDpnGate tables."
::= { mscDpnGateRowStatusEntry 4 }

mscDpnGateIndex OBJECT-TYPE
   SYNTAX     Integer32 (0..65535)
   ACCESS     not-accessible
   STATUS     mandatory
   DESCRIPTION
     "This variable represents the index for the mscDpnGate tables."
::= { mscDpnGateRowStatusEntry 10 }

mscDpnGateIfEntryTable OBJECT-TYPE
   SYNTAX     SEQUENCE OF MscDpnGateIfEntryEntry
   ACCESS     not-accessible
   STATUS     mandatory
   DESCRIPTION
     "This group contains the provisionable attributes for the ifEntry."
::= { mscDpnGate 100 }

mscDpnGateIfEntryEntry OBJECT-TYPE
   SYNTAX     MscDpnGateIfEntryEntry
   ACCESS     not-accessible
   STATUS     mandatory
   DESCRIPTION
     "An entry in the mscDpnGateIfEntryTable."
   INDEX {
      mscDpnGateIndex }
::= { mscDpnGateIfEntryTable 1 }

MscDpnGateIfEntryEntry ::= SEQUENCE {
   mscDpnGateIfAdminStatus
      INTEGER,
   mscDpnGateIfIndex
      InterfaceIndex }

mscDpnGateIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscDpnGateIfEntryEntry 1 }

mscDpnGateIfIndex OBJECT-TYPE
   SYNTAX     InterfaceIndex (1..65535)
   ACCESS     read-only
   STATUS     mandatory
   DESCRIPTION
     "This is the index for the IfEntry. Its value is automatically initialized 
      during the provisioning process."
::= { mscDpnGateIfEntryEntry 2 }

mscDpnGateProvTable OBJECT-TYPE
   SYNTAX     SEQUENCE OF MscDpnGateProvEntry
   ACCESS     not-accessible
   STATUS     mandatory
   DESCRIPTION
     "This group of provisionable attributes provide parameters used by 
      DpnGateway for staging."
::= { mscDpnGate 101 }

mscDpnGateProvEntry OBJECT-TYPE
   SYNTAX     MscDpnGateProvEntry
   ACCESS     not-accessible
   STATUS     mandatory
   DESCRIPTION
     "An entry in the mscDpnGateProvTable."
   INDEX {
      mscDpnGateIndex }
::= { mscDpnGateProvTable 1 }

MscDpnGateProvEntry ::= SEQUENCE {
   mscDpnGateExpectedRemoteNamsId
      Unsigned32,
   mscDpnGateRemoteValidationAction
      INTEGER,
   mscDpnGateLinkType
      INTEGER }

mscDpnGateExpectedRemoteNamsId OBJECT-TYPE
   SYNTAX     Unsigned32 (0..65535)
   ACCESS     read-write
   STATUS     mandatory
   DESCRIPTION
     "This attribute specifies the expected Nams Identifier of the module 
      to which this DpnGateway is connected. The DpnGateway end 
      points exchange their Nams Identifiers through the DpnGateway's 
      staging protocol. The staged value is validated and the 
      remoteValidationAction will be executed for those values not 
      matching the value supplied for this attribute.
      If this value is zero, then the comparison is always successful."
   DEFVAL     { 0 }
::= { mscDpnGateProvEntry 1 }

mscDpnGateRemoteValidationAction OBJECT-TYPE
   SYNTAX     INTEGER  {
                 continue(0),
                 disable(1) }
   ACCESS     read-write
   STATUS     mandatory
   DESCRIPTION
     "This attribute specifies the action to be taken if there is a mismatch 
      between the provisioned value and the value received from the 
      remote end, in cases where the expectedRemoteNamsId is non-zero. 
      If this attribute is provisioned to continue then upon an unsucessful 
      validation staging continues, otherwise, if disable is set then the 
      DpnGateway does not continue to stage but, attempts to stage again 
      after a one minute time out.
      All unsuccessful validation when expectedRemoteNamsId has been 
      set result in the generation of an alarm."
   DEFVAL     { continue }
::= { mscDpnGateProvEntry 2 }

mscDpnGateLinkType OBJECT-TYPE
   SYNTAX     INTEGER  {
                 dedicated(0),
                 dialIn(3) }
   ACCESS     read-write
   STATUS     mandatory
   DESCRIPTION
     "This attribute specifies the type of network link. If this attribute is 
      provisioned to dedicated then the link is a dedicated network link to 
      a DPN module. If this attribute is provisioned to dialIn then the link 
      is connected to the DPN module through a public telephone 
      network, on a dial line."
   DEFVAL     { dedicated }
::= { mscDpnGateProvEntry 3 }

mscDpnGateOverridesTable OBJECT-TYPE
   SYNTAX     SEQUENCE OF MscDpnGateOverridesEntry
   ACCESS     not-accessible
   STATUS     mandatory
   DESCRIPTION
     "Theses attribute comprise the set of provisionable override 
      parameters supported by both the Trunk and DpnGateway 
      components. The attributes are used when reporting operational 
      attributes (used for metric calculations) to the routing system."
::= { mscDpnGate 102 }

mscDpnGateOverridesEntry OBJECT-TYPE
   SYNTAX     MscDpnGateOverridesEntry
   ACCESS     not-accessible
   STATUS     mandatory
   DESCRIPTION
     "An entry in the mscDpnGateOverridesTable."
   INDEX {
      mscDpnGateIndex }
::= { mscDpnGateOverridesTable 1 }

MscDpnGateOverridesEntry ::= SEQUENCE {
   mscDpnGateOverrideTransmitSpeed
      Gauge32,
   mscDpnGateOldOverrideRoundTripDelay
      Gauge32,
   mscDpnGateOverrideRoundTripUsec
      FixedPoint1 }

mscDpnGateOverrideTransmitSpeed OBJECT-TYPE
   SYNTAX     Gauge32 (0 | 1000..4294967295)
   ACCESS     read-write
   STATUS     mandatory
   DESCRIPTION
     "This is the overridden value of link speed (bit/s) that, if staged 
      successfully with the remote, is reported to the routing system for 
      metric calculations. A zero indicates that an override value has not 
      been provided and that only the measured value will be reported to 
      the routing system.
      If this value is changed on a Trunk or DpnGateway that is enabled, 
      the LOCK and UNLOCK commands must be issued to the 
      component to restage the override with the remote."
   DEFVAL     { 0 }
::= { mscDpnGateOverridesEntry 1 }

mscDpnGateOldOverrideRoundTripDelay OBJECT-TYPE
   SYNTAX     Gauge32 (0..1500)
   ACCESS     read-write
   STATUS     obsolete
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { mscDpnGateOverridesEntry 2 }

mscDpnGateOverrideRoundTripUsec OBJECT-TYPE
   SYNTAX     FixedPoint1 (0..15000)
   ACCESS     read-write
   STATUS     mandatory
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { mscDpnGateOverridesEntry 3 }

mscDpnGateStateTable OBJECT-TYPE
   SYNTAX     SEQUENCE OF MscDpnGateStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscDpnGate 103 }

mscDpnGateStateEntry OBJECT-TYPE
   SYNTAX     MscDpnGateStateEntry
   ACCESS     not-accessible
   STATUS     mandatory
   DESCRIPTION
     "An entry in the mscDpnGateStateTable."
   INDEX {
      mscDpnGateIndex }
::= { mscDpnGateStateTable 1 }

MscDpnGateStateEntry ::= SEQUENCE {
   mscDpnGateAdminState
      INTEGER,
   mscDpnGateOperationalState
      INTEGER,
   mscDpnGateUsageState
      INTEGER,
   mscDpnGateAvailabilityStatus
      OCTET STRING,
   mscDpnGateProceduralStatus
      OCTET STRING,
   mscDpnGateControlStatus
      OCTET STRING,
   mscDpnGateAlarmStatus
      OCTET STRING,
   mscDpnGateStandbyStatus
      INTEGER,
   mscDpnGateUnknownStatus
      INTEGER }

mscDpnGateAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscDpnGateStateEntry 1 }

mscDpnGateOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscDpnGateStateEntry 2 }

mscDpnGateUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscDpnGateStateEntry 3 }

mscDpnGateAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscDpnGateStateEntry 4 }

mscDpnGateProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscDpnGateStateEntry 5 }

mscDpnGateControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscDpnGateStateEntry 6 }

mscDpnGateAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscDpnGateStateEntry 7 }

mscDpnGateStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscDpnGateStateEntry 8 }

mscDpnGateUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscDpnGateStateEntry 9 }

mscDpnGateOperStatusTable OBJECT-TYPE
   SYNTAX     SEQUENCE OF MscDpnGateOperStatusEntry
   ACCESS     not-accessible
   STATUS     mandatory
   DESCRIPTION
     "This group includes the Operational Status attribute. This attribute 
      defines the current operational state of this component."
::= { mscDpnGate 104 }

mscDpnGateOperStatusEntry OBJECT-TYPE
   SYNTAX     MscDpnGateOperStatusEntry
   ACCESS     not-accessible
   STATUS     mandatory
   DESCRIPTION
     "An entry in the mscDpnGateOperStatusTable."
   INDEX {
      mscDpnGateIndex }
::= { mscDpnGateOperStatusTable 1 }

MscDpnGateOperStatusEntry ::= SEQUENCE {
   mscDpnGateSnmpOperStatus
      INTEGER }

mscDpnGateSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscDpnGateOperStatusEntry 1 }

mscDpnGateOperTable OBJECT-TYPE
   SYNTAX     SEQUENCE OF MscDpnGateOperEntry
   ACCESS     not-accessible
   STATUS     mandatory
   DESCRIPTION
     "This group of attributes contain the operational information 
      associated with this DpnGateway and the remote to which it has it 
      staged."
::= { mscDpnGate 105 }

mscDpnGateOperEntry OBJECT-TYPE
   SYNTAX     MscDpnGateOperEntry
   ACCESS     not-accessible
   STATUS     mandatory
   DESCRIPTION
     "An entry in the mscDpnGateOperTable."
   INDEX {
      mscDpnGateIndex }
::= { mscDpnGateOperTable 1 }

MscDpnGateOperEntry ::= SEQUENCE {
   mscDpnGateRemoteComponentName
      AsciiString,
   mscDpnGateRemoteNamsMnemonic
      AsciiString,
   mscDpnGateLinkMode
      INTEGER,
   mscDpnGateActivateReason
      INTEGER }

mscDpnGateRemoteComponentName OBJECT-TYPE
   SYNTAX     AsciiString (SIZE (1..26))
   ACCESS     read-only
   STATUS     mandatory
   DESCRIPTION
     "This attribute indicates the Component Name of the remote DPN-
      100 Utp Trunk or NetworkLink supplied by the staging protocol. It 
      is in the format PM/n PE/n PI/n PO/n where PM is the remote 
      module Nams Identifier, PE is the remote module Processor 
      Element that is staged with, PI is the remote module Peripheral 
      Interface card associated with the PE, and PO is the remote module 
      Port (physical or virtual) on the PI that the physical line is 
      connected to."
::= { mscDpnGateOperEntry 1 }

mscDpnGateRemoteNamsMnemonic OBJECT-TYPE
   SYNTAX     AsciiString (SIZE (1..12))
   ACCESS     read-only
   STATUS     mandatory
   DESCRIPTION
     "This attribute indicates the Nams Mnemonic of the remote DPN-
      100 Module supplied by the staging protocol. It can be used as a 
      parameter to Rtg Dpn for displaying all DpnGateway that are 
      connect to the same module."
::= { mscDpnGateOperEntry 2 }

mscDpnGateLinkMode OBJECT-TYPE
   SYNTAX     INTEGER  {
                 trunk(0),
                 networkLink(1),
                 unknown(2) }
   ACCESS     read-only
   STATUS     mandatory
   DESCRIPTION
     "This attribute indicates whether the DpnGateway is a Trunk 
      connected to a DPN-100 RM or a NetworkLink connected to a 
      DPN-100 AM."
::= { mscDpnGateOperEntry 3 }

mscDpnGateActivateReason OBJECT-TYPE
   SYNTAX     INTEGER  {
                 dedicated(0),
                 dnl(1),
                 dbnl(2),
                 dialIn(3),
                 bwod(5),
                 unknown(15) }
   ACCESS     read-only
   STATUS     mandatory
   DESCRIPTION
     "This attribute indicates the reason the DpnGateway has been 
      activated by the remote end. The value corresponds to the link type 
      of the DPN end. It is always unknown until the link comes into 
      service. If this attribute is set to dedicated, the DPN is a dedicated 
      network link. If this attribute is set to dnl, the DPN end is a dial 
      network link, meaning a network link which is connected through a 
      dial-up service. If this attribute is set to dbnl, the DPN end is dial 
      backup network link, activated because the main network link is out 
      of service. If this attribute is set to bwod, the DPN end is a 
      bandwidth on demand link, activated because extra bandwidth is 
      required. If the attribute is set to unknown, the link is either not 
      currently in use, or the DPN end has an unrecognized link type."
   DEFVAL     { unknown }
::= { mscDpnGateOperEntry 4 }

mscDpnGateTransportTable OBJECT-TYPE
   SYNTAX     SEQUENCE OF MscDpnGateTransportEntry
   ACCESS     not-accessible
   STATUS     mandatory
   DESCRIPTION
     "This group of attributes contains the set of operational parameters 
      measured and maintained by both the Trunk and DpnGateway 
      components."
::= { mscDpnGate 106 }

mscDpnGateTransportEntry OBJECT-TYPE
   SYNTAX     MscDpnGateTransportEntry
   ACCESS     not-accessible
   STATUS     mandatory
   DESCRIPTION
     "An entry in the mscDpnGateTransportTable."
   INDEX {
      mscDpnGateIndex }
::= { mscDpnGateTransportTable 1 }

MscDpnGateTransportEntry ::= SEQUENCE {
   mscDpnGateMeasuredSpeedToIf
      Gauge32,
   mscDpnGateMeasuredRoundTripDelay
      Gauge32,
   mscDpnGateMaxTxUnit
      Gauge32,
   mscDpnGateMeasuredRoundTripDelayUsec
      FixedPoint1 }

mscDpnGateMeasuredSpeedToIf OBJECT-TYPE
   SYNTAX     Gauge32 (0..4294967295)
   ACCESS     read-only
   STATUS     mandatory
   DESCRIPTION
     "This attribute indicates the current 'transmittable' bandwidth of the 
      underlying facility.
      For a Trunk with a Unack subcomponent, and a DpnGateway with a 
      Utp subcomponent, if a serial port is used, the value is the measured 
      transmit speed of the port; if a channelized port (E1/DS1) is used, 
      the value is the measured transmit speed of the Channel. 
      For a Trunk with an AtmAccess subcomponent, the value is 
      calculated by converting the VCC transmit cell rate to an equivalent 
      bit rate. The VCC transmit cell rate is determined based on the 
      vccReportingBw attribute of the Trunk AtmAccess component. If 
      vccReportingBw has a value of pcr and attribute bwElastic of 
      AtmAccess has a value of no, the peak cell rate (PCR) of the VCC, 
      defined in txTrafficDescParm of AtmIf Vcc Vcd, is used. If 
      vccReportingBw has a value of pcr and attribute bwElastic of 
      AtmAccess has a value of yes, the minimum of the PCR, defined in 
      txTrafficDescParm of AtmIf Vcc Vcd, and the current cell rate 
      (CCR) of the VCC is used. If vccReportingBw has a value of acr, 
      the best measurement of the actual cell rate (ACR) of the VCC is 
      used, which is the minimum of the PCR, the CCR and the actual 
      shaping rate (ASR).
      For a DpnGateway with a FrAccess subcomponent, the value 
      indicates the committedInformationRate of FrAccess FrMuxSetup.
      A value of zero is displayed when the underlying facility is disabled 
      or the current 'transmittable' bandwidth is unknown."
   DEFVAL     { 0 }
::= { mscDpnGateTransportEntry 1 }

mscDpnGateMeasuredRoundTripDelay OBJECT-TYPE
   SYNTAX     Gauge32 (0..1500)
   ACCESS     read-only
   STATUS     obsolete
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { mscDpnGateTransportEntry 2 }

mscDpnGateMaxTxUnit OBJECT-TYPE
   SYNTAX     Gauge32 (0..65535)
   ACCESS     read-only
   STATUS     mandatory
   DESCRIPTION
     "This is the maximum transmission unit (byte size) that is supported 
      by the Trunk or DpnGateway component. This size includes the 
      data and routing headers. A value of zero indicates the MTU has not 
      yet been determined."
   DEFVAL     { 0 }
::= { mscDpnGateTransportEntry 3 }

mscDpnGateMeasuredRoundTripDelayUsec OBJECT-TYPE
   SYNTAX     FixedPoint1 (0..15000)
   ACCESS     read-only
   STATUS     mandatory
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { mscDpnGateTransportEntry 4 }

mscDpnGateStatsTable OBJECT-TYPE
   SYNTAX     SEQUENCE OF MscDpnGateStatsEntry
   ACCESS     not-accessible
   STATUS     mandatory
   DESCRIPTION
     "This group of attributes contains statistics collected by the 
      DpnGateway component."
::= { mscDpnGate 107 }

mscDpnGateStatsEntry OBJECT-TYPE
   SYNTAX     MscDpnGateStatsEntry
   ACCESS     not-accessible
   STATUS     mandatory
   DESCRIPTION
     "An entry in the mscDpnGateStatsTable."
   INDEX {
      mscDpnGateIndex }
::= { mscDpnGateStatsTable 1 }

MscDpnGateStatsEntry ::= SEQUENCE {
   mscDpnGatePktFromIf
      PassportCounter64,
   mscDpnGateTrunkPktFromIf
      Counter32,
   mscDpnGateTrunkPktToIf
      Counter32,
   mscDpnGateDiscardUnforward
      PassportCounter64,
   mscDpnGateDiscardTrunkPktFromIf
      Counter32,
   mscDpnGateStagingAttempts
      Counter32,
   mscDpnGateDiscardTrunkPktToIf
      Counter32 }

mscDpnGatePktFromIf OBJECT-TYPE
   SYNTAX     PassportCounter64 
   ACCESS     read-only
   STATUS     mandatory
   DESCRIPTION
     "This attribute counts the number of packets received from the 
      remote module. This counter wraps around to zero when the 
      maximum value is reached."
::= { mscDpnGateStatsEntry 1 }

mscDpnGateTrunkPktFromIf OBJECT-TYPE
   SYNTAX     Counter32 
   ACCESS     read-only
   STATUS     mandatory
   DESCRIPTION
     "This attribute counts the number of internal trunk protocol packets 
      received from the remote module. These packets are forwarded to 
      the DpnGateway component. This counter wraps around to zero 
      when the maximum value is reached."
::= { mscDpnGateStatsEntry 2 }

mscDpnGateTrunkPktToIf OBJECT-TYPE
   SYNTAX     Counter32 
   ACCESS     read-only
   STATUS     mandatory
   DESCRIPTION
     "This attribute counts the number of internal trunk protocol packets 
      transmitted to the remote module. This counter wraps around to 
      zero when the maximum value is reached."
::= { mscDpnGateStatsEntry 3 }

mscDpnGateDiscardUnforward OBJECT-TYPE
   SYNTAX     PassportCounter64 
   ACCESS     read-only
   STATUS     mandatory
   DESCRIPTION
     "This attribute counts the number of packets received from the 
      remote module that have been discarded. This counter wraps around 
      to zero when the maximum value is reached. Two main reasons that 
      cause this counter to increment are: the remote protocol is not 
      compatible to the local protocol stack or, the packet cannot be 
      forwarded due to either a recent loss of connectivity or due to 
      congestion."
::= { mscDpnGateStatsEntry 4 }

mscDpnGateDiscardTrunkPktFromIf OBJECT-TYPE
   SYNTAX     Counter32 
   ACCESS     read-only
   STATUS     mandatory
   DESCRIPTION
     "This attribute counts the number of internal trunk protocol packets 
      received from the remote module that have been discarded. This 
      counter wraps around to zero when the maximum value is reached. 
      The two main reasons that cause this counter to increment is if the 
      DpnGateway is unsynchronized with DPN-100 and if the remote 
      protocol is not the same version as the local protocol."
::= { mscDpnGateStatsEntry 5 }

mscDpnGateStagingAttempts OBJECT-TYPE
   SYNTAX     Counter32 
   ACCESS     read-only
   STATUS     mandatory
   DESCRIPTION
     "This attribute counts the number of times that the staging protocol 
      has attempted to stage with the remote module. This counter wraps 
      around to zero when the maximum value is reached. The main 
      reason for this counter to increment is that the local hardware is up 
      but the local protocol cannot stage with the remote protocol due to a 
      faulty connection. If the value is zero, then the local hardware has 
      never enabled successfully."
::= { mscDpnGateStatsEntry 6 }

mscDpnGateDiscardTrunkPktToIf OBJECT-TYPE
   SYNTAX     Counter32 
   ACCESS     read-only
   STATUS     mandatory
   DESCRIPTION
     "This attribute counts the number of internal trunk protocol packets 
      that have been discarded before being transmitted to the remote 
      module. This counter wraps around to zero when the maximum 
      value is reached. The main reason that causes this counter to 
      increment is that the DpnGateway can not get sufficient resources to 
      create an internal trunk protocol packet."
::= { mscDpnGateStatsEntry 7 }


-- Trunk/n ForwardingStatistics
-- This is a dynamic subcomponent of a Trunk or DpnGateway which 
-- appears when packet forwarding traffic is used over the Trunk or 
-- DpnGateway. It contains statistics associated with packet 
-- forwarding traffic for Trunks and DpnGateways.

mscDpnGateFwdStats OBJECT IDENTIFIER ::= { mscDpnGate 3 }



mscDpnGateFwdStatsRowStatusTable OBJECT-TYPE
   SYNTAX     SEQUENCE OF MscDpnGateFwdStatsRowStatusEntry
   ACCESS     not-accessible
   STATUS     mandatory
   DESCRIPTION
     "This entry controls the addition and deletion of 
      mscDpnGateFwdStats components."
::= { mscDpnGateFwdStats 1 }

mscDpnGateFwdStatsRowStatusEntry OBJECT-TYPE
   SYNTAX     MscDpnGateFwdStatsRowStatusEntry
   ACCESS     not-accessible
   STATUS     mandatory
   DESCRIPTION
     "A single entry in the table represents a single 
      mscDpnGateFwdStats component."
   INDEX {
      mscDpnGateIndex,
      mscDpnGateFwdStatsIndex }
::= { mscDpnGateFwdStatsRowStatusTable 1 }

MscDpnGateFwdStatsRowStatusEntry ::= SEQUENCE {
   mscDpnGateFwdStatsRowStatus
      RowStatus,
   mscDpnGateFwdStatsComponentName
      DisplayString,
   mscDpnGateFwdStatsStorageType
      StorageType,
   mscDpnGateFwdStatsIndex
      NonReplicated }

mscDpnGateFwdStatsRowStatus OBJECT-TYPE
   SYNTAX     RowStatus 
   ACCESS     read-only
   STATUS     mandatory
   DESCRIPTION
     "This variable is used as the basis for SNMP naming of
      mscDpnGateFwdStats components.
      These components cannot be added nor deleted."
::= { mscDpnGateFwdStatsRowStatusEntry 1 }

mscDpnGateFwdStatsComponentName OBJECT-TYPE
   SYNTAX     DisplayString 
   ACCESS     read-only
   STATUS     mandatory
   DESCRIPTION
     "This variable provides the component's string name for
      use with the ASCII Console Interface"
::= { mscDpnGateFwdStatsRowStatusEntry 2 }

mscDpnGateFwdStatsStorageType OBJECT-TYPE
   SYNTAX     StorageType 
   ACCESS     read-only
   STATUS     mandatory
   DESCRIPTION
     "This variable represents the storage type value for the
      mscDpnGateFwdStats tables."
::= { mscDpnGateFwdStatsRowStatusEntry 4 }

mscDpnGateFwdStatsIndex OBJECT-TYPE
   SYNTAX     NonReplicated 
   ACCESS     not-accessible
   STATUS     mandatory
   DESCRIPTION
     "This variable represents the index for the mscDpnGateFwdStats tables."
::= { mscDpnGateFwdStatsRowStatusEntry 10 }

mscDpnGateFwdStatsOperTable OBJECT-TYPE
   SYNTAX     SEQUENCE OF MscDpnGateFwdStatsOperEntry
   ACCESS     not-accessible
   STATUS     mandatory
   DESCRIPTION
     "This operational group counts the Trunk or DpnGateway packet 
      forwarding traffic statistics for operator console display."
::= { mscDpnGateFwdStats 10 }

mscDpnGateFwdStatsOperEntry OBJECT-TYPE
   SYNTAX     MscDpnGateFwdStatsOperEntry
   ACCESS     not-accessible
   STATUS     mandatory
   DESCRIPTION
     "An entry in the mscDpnGateFwdStatsOperTable."
   INDEX {
      mscDpnGateIndex,
      mscDpnGateFwdStatsIndex }
::= { mscDpnGateFwdStatsOperTable 1 }

MscDpnGateFwdStatsOperEntry ::= SEQUENCE {
   mscDpnGateFwdStatsFwdPktFromIf
      PassportCounter64,
   mscDpnGateFwdStatsFwdDiscUnforwardFromIf
      PassportCounter64,
   mscDpnGateFwdStatsFwdOctetFromIf
      PassportCounter64 }

mscDpnGateFwdStatsFwdPktFromIf OBJECT-TYPE
   SYNTAX     PassportCounter64 
   ACCESS     read-only
   STATUS     mandatory
   DESCRIPTION
     "This attribute counts the number of forwarding packets received by 
      the Trunk or DpnGateway. This counter wraps around to zero when 
      the maximum value is exceeded."
::= { mscDpnGateFwdStatsOperEntry 1 }

mscDpnGateFwdStatsFwdDiscUnforwardFromIf OBJECT-TYPE
   SYNTAX     PassportCounter64 
   ACCESS     read-only
   STATUS     mandatory
   DESCRIPTION
     "This attribute counts the number of forwarding packets discarded by 
      the Trunk or DpnGateway. This counter wraps around to zero when 
      the maximum value is exceeded."
::= { mscDpnGateFwdStatsOperEntry 2 }

mscDpnGateFwdStatsFwdOctetFromIf OBJECT-TYPE
   SYNTAX     PassportCounter64 
   ACCESS     read-only
   STATUS     mandatory
   DESCRIPTION
     "This attribute counts the number of forwarding bytes received by 
      the Trunk or DpnGateway. This counter wraps around to zero when 
      the maximum value is exceeded."
::= { mscDpnGateFwdStatsOperEntry 3 }




-- 
-- Version and Compliance statements
-- 



-- Object-Group Statement:
-- A list of all current accessible leaf objects.

-- OBJECTS { mscDpnGateExpectedRemoteNamsId,
--           mscDpnGateOperationalState,
--           mscDpnGateLinkMode,
--           mscDpnGateFwdStatsStorageType,
--           mscDpnGateFwdStatsRowStatus,
--           mscDpnGateMaxTxUnit,
--           mscDpnGateRemoteComponentName,
--           mscDpnGateControlStatus,
--           mscDpnGateAdminState,
--           mscDpnGateActivateReason,
--           mscDpnGateStorageType,
--           mscDpnGateUnknownStatus,
--           mscDpnGateRowStatus,
--           mscDpnGateIfAdminStatus,
--           mscDpnGateRemoteNamsMnemonic,
--           mscDpnGateLinkType,
--           mscDpnGateProceduralStatus,
--           mscDpnGateAvailabilityStatus,
--           mscDpnGateFwdStatsComponentName,
--           mscDpnGateStagingAttempts,
--           mscDpnGateFwdStatsFwdPktFromIf,
--           mscDpnGateSnmpOperStatus,
--           mscDpnGateIfIndex,
--           mscDpnGateAlarmStatus,
--           mscDpnGateUsageState,
--           mscDpnGateDiscardTrunkPktFromIf,
--           mscDpnGateDiscardTrunkPktToIf,
--           mscDpnGateComponentName,
--           mscDpnGateMeasuredSpeedToIf,
--           mscDpnGateFwdStatsFwdDiscUnforwardFromIf,
--           mscDpnGateOverrideTransmitSpeed,
--           mscDpnGateTrunkPktToIf,
--           mscDpnGatePktFromIf,
--           mscDpnGateOverrideRoundTripUsec,
--           mscDpnGateMeasuredRoundTripDelayUsec,
--           mscDpnGateDiscardUnforward,
--           mscDpnGateTrunkPktFromIf,
--           mscDpnGateFwdStatsFwdOctetFromIf,
--           mscDpnGateStandbyStatus,
--           mscDpnGateRemoteValidationAction }
-- STATUS  mandatory
-- DESCRIPTION
--   "A list of all current accessible leaf objects."

dpnTrunksGroup OBJECT IDENTIFIER ::= { dpnTrunksMIB 1 }
dpnTrunksGroupCA OBJECT IDENTIFIER ::= { dpnTrunksGroup 1 }
dpnTrunksGroupCA02 OBJECT IDENTIFIER ::= { dpnTrunksGroupCA 3 }
dpnTrunksGroupCA02A OBJECT IDENTIFIER ::= { dpnTrunksGroupCA02 2 }



-- Agent-Capabilities Statement:

-- PRODUCT-RELEASE "MscPassport Release 1.2 DpnTrunks."
-- STATUS          mandatory
-- DESCRIPTION     "Carrier Passport DpnTrunks MIB: MIB Version CA02A,
--                  Software Version CA02S9C."
-- SUPPORTS        Nortel-MsCarrier-MscPassport-DpnTrunksMIB
--    INCLUDES     { dpnTrunksGroupCA02A }

dpnTrunksCapabilities OBJECT IDENTIFIER ::= { dpnTrunksMIB 3 }
dpnTrunksCapabilitiesCA OBJECT IDENTIFIER ::= { dpnTrunksCapabilities 1 }
dpnTrunksCapabilitiesCA02 OBJECT IDENTIFIER ::= { dpnTrunksCapabilitiesCA 3 }
dpnTrunksCapabilitiesCA02A OBJECT IDENTIFIER ::= { dpnTrunksCapabilitiesCA02 2 }





END
