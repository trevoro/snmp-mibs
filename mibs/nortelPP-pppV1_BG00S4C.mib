Nortel-Magellan-Passport-PppMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      InterfaceIndex,
      Gauge32,
      Integer32,
      Unsigned32
   FROM Nortel-Magellan-Passport-StandardTextualConventionsMIB

      NonReplicated,
      Link
   FROM Nortel-Magellan-Passport-TextualConventionsMIB;




-- LAST-UPDATED   "9603010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Ppp Enterprise MIB."

pppMIB OBJECT IDENTIFIER ::= { passportMIBs 33 }










-- PointToPointProtocol/n
-- This component defines an instance of the Ppp link level protocol. The 
-- component instance value is a unique number.

ppp OBJECT IDENTIFIER ::= { components 102 }



pppRowStatusTable OBJECT-TYPE
   SYNTAX     SEQUENCE OF PppRowStatusEntry
   ACCESS     not-accessible
   STATUS     mandatory
   DESCRIPTION
     "This entry controls the addition and deletion of 
      ppp components."
::= { ppp 1 }

pppRowStatusEntry OBJECT-TYPE
   SYNTAX     PppRowStatusEntry
   ACCESS     not-accessible
   STATUS     mandatory
   DESCRIPTION
     "A single entry in the table represents a single 
      ppp component."
   INDEX {
      pppIndex }
::= { pppRowStatusTable 1 }

PppRowStatusEntry ::= SEQUENCE {
   pppRowStatus
      RowStatus,
   pppComponentName
      DisplayString,
   pppStorageType
      StorageType,
   pppIndex
      Integer32 }

pppRowStatus OBJECT-TYPE
   SYNTAX     RowStatus 
   ACCESS     read-write
   STATUS     mandatory
   DESCRIPTION
     "This variable is used as the basis for SNMP naming of
      ppp components.
      These components can be added and deleted."
::= { pppRowStatusEntry 1 }

pppComponentName OBJECT-TYPE
   SYNTAX     DisplayString 
   ACCESS     read-only
   STATUS     mandatory
   DESCRIPTION
     "This variable provides the component's string name for
      use with the ASCII Console Interface"
::= { pppRowStatusEntry 2 }

pppStorageType OBJECT-TYPE
   SYNTAX     StorageType 
   ACCESS     read-only
   STATUS     mandatory
   DESCRIPTION
     "This variable represents the storage type value for the
      ppp tables."
::= { pppRowStatusEntry 4 }

pppIndex OBJECT-TYPE
   SYNTAX     Integer32 (1..65535)
   ACCESS     not-accessible
   STATUS     mandatory
   DESCRIPTION
     "This variable represents the index for the ppp tables."
::= { pppRowStatusEntry 10 }

pppCidDataTable OBJECT-TYPE
   SYNTAX     SEQUENCE OF PppCidDataEntry
   ACCESS     not-accessible
   STATUS     mandatory
   DESCRIPTION
     "This group contains the attribute for a component's Customer 
      Identifier (CID). Refer to the attribute description for a detailed 
      explanation of CIDs."
::= { ppp 20 }

pppCidDataEntry OBJECT-TYPE
   SYNTAX     PppCidDataEntry
   ACCESS     not-accessible
   STATUS     mandatory
   DESCRIPTION
     "An entry in the pppCidDataTable."
   INDEX {
      pppIndex }
::= { pppCidDataTable 1 }

PppCidDataEntry ::= SEQUENCE {
   pppCustomerIdentifier
      Unsigned32 }

pppCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { pppCidDataEntry 1 }

pppIfEntryTable OBJECT-TYPE
   SYNTAX     SEQUENCE OF PppIfEntryEntry
   ACCESS     not-accessible
   STATUS     mandatory
   DESCRIPTION
     "This group contains the provisionable attributes for the ifEntry."
::= { ppp 21 }

pppIfEntryEntry OBJECT-TYPE
   SYNTAX     PppIfEntryEntry
   ACCESS     not-accessible
   STATUS     mandatory
   DESCRIPTION
     "An entry in the pppIfEntryTable."
   INDEX {
      pppIndex }
::= { pppIfEntryTable 1 }

PppIfEntryEntry ::= SEQUENCE {
   pppIfAdminStatus
      INTEGER,
   pppIfIndex
      InterfaceIndex }

pppIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { pppIfEntryEntry 1 }

pppIfIndex OBJECT-TYPE
   SYNTAX     InterfaceIndex (1..65535)
   ACCESS     read-only
   STATUS     mandatory
   DESCRIPTION
     "This is the index for the IfEntry. Its value is automatically initialized 
      during the provisioning process."
::= { pppIfEntryEntry 2 }

pppMpTable OBJECT-TYPE
   SYNTAX     SEQUENCE OF PppMpEntry
   ACCESS     not-accessible
   STATUS     mandatory
   DESCRIPTION
     "This group contains the base provisioning data for the Media 
      Application component."
::= { ppp 22 }

pppMpEntry OBJECT-TYPE
   SYNTAX     PppMpEntry
   ACCESS     not-accessible
   STATUS     mandatory
   DESCRIPTION
     "An entry in the pppMpTable."
   INDEX {
      pppIndex }
::= { pppMpTable 1 }

PppMpEntry ::= SEQUENCE {
   pppLinkToProtocolPort
      Link }

pppLinkToProtocolPort OBJECT-TYPE
   SYNTAX     Link 
   ACCESS     read-write
   STATUS     mandatory
   DESCRIPTION
     "This attribute contains a protocol port component name. The attribute 
      associates the application with a protocol port."
::= { pppMpEntry 1 }

pppStateTable OBJECT-TYPE
   SYNTAX     SEQUENCE OF PppStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { ppp 23 }

pppStateEntry OBJECT-TYPE
   SYNTAX     PppStateEntry
   ACCESS     not-accessible
   STATUS     mandatory
   DESCRIPTION
     "An entry in the pppStateTable."
   INDEX {
      pppIndex }
::= { pppStateTable 1 }

PppStateEntry ::= SEQUENCE {
   pppAdminState
      INTEGER,
   pppOperationalState
      INTEGER,
   pppUsageState
      INTEGER }

pppAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { pppStateEntry 1 }

pppOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { pppStateEntry 2 }

pppUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { pppStateEntry 3 }

pppOperStatusTable OBJECT-TYPE
   SYNTAX     SEQUENCE OF PppOperStatusEntry
   ACCESS     not-accessible
   STATUS     mandatory
   DESCRIPTION
     "This group includes the Operational Status attribute. This attribute 
      defines the current operational state of this component."
::= { ppp 24 }

pppOperStatusEntry OBJECT-TYPE
   SYNTAX     PppOperStatusEntry
   ACCESS     not-accessible
   STATUS     mandatory
   DESCRIPTION
     "An entry in the pppOperStatusTable."
   INDEX {
      pppIndex }
::= { pppOperStatusTable 1 }

PppOperStatusEntry ::= SEQUENCE {
   pppSnmpOperStatus
      INTEGER }

pppSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { pppOperStatusEntry 1 }


-- Ppp/n Link
-- This component is used to contain all the attributes related to the Ppp 
-- link. This is a mandatory subcomponent of Ppp and does not need to be 
-- added.

pppLnk OBJECT IDENTIFIER ::= { ppp 2 }



pppLnkRowStatusTable OBJECT-TYPE
   SYNTAX     SEQUENCE OF PppLnkRowStatusEntry
   ACCESS     not-accessible
   STATUS     mandatory
   DESCRIPTION
     "This entry controls the addition and deletion of 
      pppLnk components."
::= { pppLnk 1 }

pppLnkRowStatusEntry OBJECT-TYPE
   SYNTAX     PppLnkRowStatusEntry
   ACCESS     not-accessible
   STATUS     mandatory
   DESCRIPTION
     "A single entry in the table represents a single 
      pppLnk component."
   INDEX {
      pppIndex,
      pppLnkIndex }
::= { pppLnkRowStatusTable 1 }

PppLnkRowStatusEntry ::= SEQUENCE {
   pppLnkRowStatus
      RowStatus,
   pppLnkComponentName
      DisplayString,
   pppLnkStorageType
      StorageType,
   pppLnkIndex
      NonReplicated }

pppLnkRowStatus OBJECT-TYPE
   SYNTAX     RowStatus 
   ACCESS     read-only
   STATUS     mandatory
   DESCRIPTION
     "This variable is used as the basis for SNMP naming of
      pppLnk components.
      These components cannot be added nor deleted."
::= { pppLnkRowStatusEntry 1 }

pppLnkComponentName OBJECT-TYPE
   SYNTAX     DisplayString 
   ACCESS     read-only
   STATUS     mandatory
   DESCRIPTION
     "This variable provides the component's string name for
      use with the ASCII Console Interface"
::= { pppLnkRowStatusEntry 2 }

pppLnkStorageType OBJECT-TYPE
   SYNTAX     StorageType 
   ACCESS     read-only
   STATUS     mandatory
   DESCRIPTION
     "This variable represents the storage type value for the
      pppLnk tables."
::= { pppLnkRowStatusEntry 4 }

pppLnkIndex OBJECT-TYPE
   SYNTAX     NonReplicated 
   ACCESS     not-accessible
   STATUS     mandatory
   DESCRIPTION
     "This variable represents the index for the pppLnk tables."
::= { pppLnkRowStatusEntry 10 }

pppLnkProvTable OBJECT-TYPE
   SYNTAX     SEQUENCE OF PppLnkProvEntry
   ACCESS     not-accessible
   STATUS     mandatory
   DESCRIPTION
     "This group contains the provisioned attributes for the Ppp Link 
      component."
::= { pppLnk 10 }

pppLnkProvEntry OBJECT-TYPE
   SYNTAX     PppLnkProvEntry
   ACCESS     not-accessible
   STATUS     mandatory
   DESCRIPTION
     "An entry in the pppLnkProvTable."
   INDEX {
      pppIndex,
      pppLnkIndex }
::= { pppLnkProvTable 1 }

PppLnkProvEntry ::= SEQUENCE {
   pppLnkConfigInitialMru
      Unsigned32,
   pppLnkConfigMagicNumber
      INTEGER,
   pppLnkRestartTimer
      Unsigned32,
   pppLnkContinuityMonitor
      INTEGER,
   pppLnkNegativeAckTries
      Unsigned32,
   pppLnkQualityThreshold
      Unsigned32,
   pppLnkQualityWindow
      Unsigned32,
   pppLnkTerminateRequestTries
      Unsigned32,
   pppLnkConfigureRequestTries
      Unsigned32 }

pppLnkConfigInitialMru OBJECT-TYPE
   SYNTAX     Unsigned32 (68..18000)
   ACCESS     read-write
   STATUS     mandatory
   DESCRIPTION
     "This is the initial Maximum Receive Unit (Mru) that the local Ppp entity 
      will advertise to the remote entity. A change to this attribute will not 
      take effect until Ppp is restarted (lock/unlock)."
   DEFVAL     { 18000 }
::= { pppLnkProvEntry 1 }

pppLnkConfigMagicNumber OBJECT-TYPE
   SYNTAX     INTEGER  {
                 disabled(1),
                 enabled(2) }
   ACCESS     read-write
   STATUS     mandatory
   DESCRIPTION
     "If enabled then the local node will attempt to perform Magic Number 
      negotiation with the remote node. If disabled then this negotiation is not 
      performed. In any event, the local node will comply with any magic 
      number negotiations attempted by the remote node, per the Ppp 
      specification. A change to this attribute will not take effect until Ppp is 
      restarted (lock/unlock)."
   DEFVAL     { enabled }
::= { pppLnkProvEntry 4 }

pppLnkRestartTimer OBJECT-TYPE
   SYNTAX     Unsigned32 (1000..10000)
   ACCESS     read-write
   STATUS     mandatory
   DESCRIPTION
     "This is the time, in milliseconds, that Ppp will wait for a response to a 
      configure request or a terminate request before retrying."
   DEFVAL     { 3000 }
::= { pppLnkProvEntry 6 }

pppLnkContinuityMonitor OBJECT-TYPE
   SYNTAX     INTEGER  {
                 enabled(1),
                 disabled(2) }
   ACCESS     read-write
   STATUS     mandatory
   DESCRIPTION
     "This 					attribute turns on/off (enabled/disabled) the Link Continuity 
      Monitor. If set to enabled, periodic keep alive echo packet will be sent 
      over the Ppp link. If set to disabled, no keep alive packets will be sent. 
      A change to this attribute will not take effect until Ppp is restarted (lock/
      unlock)."
   DEFVAL     { enabled }
::= { pppLnkProvEntry 7 }

pppLnkNegativeAckTries OBJECT-TYPE
   SYNTAX     Unsigned32 (0..4294967295)
   ACCESS     read-write
   STATUS     mandatory
   DESCRIPTION
     "This attribute specifies the maximum negative acknowledgments sent to 
      the remote Ppp entity during negotiation before defaulting it's 
      configuration parameters."
   DEFVAL     { 10 }
::= { pppLnkProvEntry 8 }

pppLnkQualityThreshold OBJECT-TYPE
   SYNTAX     Unsigned32 (10..99)
   ACCESS     read-write
   STATUS     mandatory
   DESCRIPTION
     "This attribute specifies the minimum allowed line quality before the line 
      is considered too poor to continue operation. The value for this attribute 
      is a percentage measure of the line quality given in integers (10 to 99). 
      The higher the value, the more stringent the line requirements."
   DEFVAL     { 90 }
::= { pppLnkProvEntry 9 }

pppLnkQualityWindow OBJECT-TYPE
   SYNTAX     Unsigned32 (10..400)
   ACCESS     read-write
   STATUS     mandatory
   DESCRIPTION
     "This attribute specifies the number of seconds used for sampling line 
      quality. If line quality drops below the level set with the 
      qualityThreshold attribute during this window, this instance of Ppp will 
      be marked down until line quality recovers."
   DEFVAL     { 30 }
::= { pppLnkProvEntry 10 }

pppLnkTerminateRequestTries OBJECT-TYPE
   SYNTAX     Unsigned32 (0..4294967295)
   ACCESS     read-write
   STATUS     mandatory
   DESCRIPTION
     "This attribute specifies the maximum terminate requests to be sent, when 
      closing the connection, and not answered before this instance of Ppp 
      enters a closing state."
   DEFVAL     { 10 }
::= { pppLnkProvEntry 11 }

pppLnkConfigureRequestTries OBJECT-TYPE
   SYNTAX     Unsigned32 (0..4294967295)
   ACCESS     read-write
   STATUS     mandatory
   DESCRIPTION
     "This attribute specifies the number of configuration requests that will be 
      sent out and not answered before this instance of Ppp enters a listening 
      state. If both sides enter the listening state then the link will not come 
      up. To eliminate this possibility, this attribute should be set to 
      1000000000. This will ensure that this end of the Ppp link will 
      continue to try until the link is good."
   DEFVAL     { 1000000000 }
::= { pppLnkProvEntry 12 }

pppLnkOperTable OBJECT-TYPE
   SYNTAX     SEQUENCE OF PppLnkOperEntry
   ACCESS     not-accessible
   STATUS     mandatory
   DESCRIPTION
     "This group contains the Ppp Link Operational attributes."
::= { pppLnk 11 }

pppLnkOperEntry OBJECT-TYPE
   SYNTAX     PppLnkOperEntry
   ACCESS     not-accessible
   STATUS     mandatory
   DESCRIPTION
     "An entry in the pppLnkOperTable."
   INDEX {
      pppIndex,
      pppLnkIndex }
::= { pppLnkOperTable 1 }

PppLnkOperEntry ::= SEQUENCE {
   pppLnkOperState
      INTEGER,
   pppLnkLineCondition
      INTEGER,
   pppLnkBadAddresses
      Counter32,
   pppLnkBadControls
      Counter32,
   pppLnkPacketTooLongs
      Counter32,
   pppLnkBadFcss
      Counter32,
   pppLnkLocalMru
      Unsigned32,
   pppLnkRemoteMru
      Unsigned32,
   pppLnkTransmitFcsSize
      Unsigned32,
   pppLnkReceiveFcsSize
      Unsigned32 }

pppLnkOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Link Control Protocol. For more 
      information as to the definition of each state see RFC1331 section 5.3."
   DEFVAL     { initial }
::= { pppLnkOperEntry 1 }

pppLnkLineCondition OBJECT-TYPE
   SYNTAX     INTEGER  {
                 ok(0),
                 looped(1),
                 noClock(3),
                 badLineCondition(4) }
   ACCESS     read-only
   STATUS     mandatory
   DESCRIPTION
     "This attribute describes the condition of the physical line that Ppp is 
      running over.
      ok: The condition of the line is good.
      looped: The line is looped back on itself, probably at the remote end.
      noClock: There is a hardware problem with the line. The cable may not 
      be plugged in correctly.
      badLineCondition: The quality of the line is below the 
      qualityThreshold."
   DEFVAL     { ok }
::= { pppLnkOperEntry 2 }

pppLnkBadAddresses OBJECT-TYPE
   SYNTAX     Counter32 
   ACCESS     read-only
   STATUS     mandatory
   DESCRIPTION
     "This attribute counts the number of packets received with an incorrect 
      Address Field. If this count is going up quickly, it could indicate that 
      there is a line quality problem or that the remote end is transmitting a 
      protocol other than Ppp. This counter will wrap around to 0 when it 
      exceeds its maximum count."
::= { pppLnkOperEntry 4 }

pppLnkBadControls OBJECT-TYPE
   SYNTAX     Counter32 
   ACCESS     read-only
   STATUS     mandatory
   DESCRIPTION
     "This attribute counts the number of packets received on this link with an 
      incorrect Control Field. If this count is going up quickly, it could 
      indicate that there is a line quality problem or that the remote end is 
      transmitting a protocol other than Ppp. This counter will wrap around to 
      0 when it exceeds its maximum count."
::= { pppLnkOperEntry 5 }

pppLnkPacketTooLongs OBJECT-TYPE
   SYNTAX     Counter32 
   ACCESS     read-only
   STATUS     mandatory
   DESCRIPTION
     "This attribute counts the number of packets received that have been 
      discarded because their length exceeded the Maximum Receive Unit 
      (Mru). This counter will wrap around to 0 when it exceeds its maximum 
      count."
::= { pppLnkOperEntry 6 }

pppLnkBadFcss OBJECT-TYPE
   SYNTAX     Counter32 
   ACCESS     read-only
   STATUS     mandatory
   DESCRIPTION
     "This attribute counts the number of packets received that have been 
      discarded due to having an incorrect Frame Check Sequence (Fcs). This 
      counter will wrap around to 0 when it exceeds its maximum count."
::= { pppLnkOperEntry 7 }

pppLnkLocalMru OBJECT-TYPE
   SYNTAX     Unsigned32 (1..2147483648)
   ACCESS     read-only
   STATUS     mandatory
   DESCRIPTION
     "This is the current value of the Maximum Receive Unit (Mru) for the 
      local Ppp Entity. This value is the Mru that the remote entity is using 
      when sending packets to the local Ppp entity."
   DEFVAL     { 1 }
::= { pppLnkOperEntry 8 }

pppLnkRemoteMru OBJECT-TYPE
   SYNTAX     Unsigned32 (1..2147483648)
   ACCESS     read-only
   STATUS     mandatory
   DESCRIPTION
     "This is the current value of the Maximum Receive Unit (Mru) for the 
      remote Ppp entity. This value is the Mru that the local entity is using 
      when sending packets to the remote Ppp entity."
::= { pppLnkOperEntry 9 }

pppLnkTransmitFcsSize OBJECT-TYPE
   SYNTAX     Unsigned32 (0..128)
   ACCESS     read-only
   STATUS     mandatory
   DESCRIPTION
     "This is the size of the Frame Check Sequence (Fcs) in bits that the local 
      node will generate when sending packets to the remote node."
   DEFVAL     { 0 }
::= { pppLnkOperEntry 16 }

pppLnkReceiveFcsSize OBJECT-TYPE
   SYNTAX     Unsigned32 (0..128)
   ACCESS     read-only
   STATUS     mandatory
   DESCRIPTION
     "This is the size of the Frame Check Sequence (Fcs) in bits that the 
      remote node will generate when sending packets to the local node."
   DEFVAL     { 0 }
::= { pppLnkOperEntry 17 }


-- Ppp/n LinkQualityMonitor
-- This component is used to contain all the operational attributes for the 
-- Ppp Link Quality Monitor. This is a mandatory subcomponent of Ppp 
-- and does not need to be manually added.

pppLqm OBJECT IDENTIFIER ::= { ppp 3 }



pppLqmRowStatusTable OBJECT-TYPE
   SYNTAX     SEQUENCE OF PppLqmRowStatusEntry
   ACCESS     not-accessible
   STATUS     mandatory
   DESCRIPTION
     "This entry controls the addition and deletion of 
      pppLqm components."
::= { pppLqm 1 }

pppLqmRowStatusEntry OBJECT-TYPE
   SYNTAX     PppLqmRowStatusEntry
   ACCESS     not-accessible
   STATUS     mandatory
   DESCRIPTION
     "A single entry in the table represents a single 
      pppLqm component."
   INDEX {
      pppIndex,
      pppLqmIndex }
::= { pppLqmRowStatusTable 1 }

PppLqmRowStatusEntry ::= SEQUENCE {
   pppLqmRowStatus
      RowStatus,
   pppLqmComponentName
      DisplayString,
   pppLqmStorageType
      StorageType,
   pppLqmIndex
      NonReplicated }

pppLqmRowStatus OBJECT-TYPE
   SYNTAX     RowStatus 
   ACCESS     read-only
   STATUS     mandatory
   DESCRIPTION
     "This variable is used as the basis for SNMP naming of
      pppLqm components.
      These components cannot be added nor deleted."
::= { pppLqmRowStatusEntry 1 }

pppLqmComponentName OBJECT-TYPE
   SYNTAX     DisplayString 
   ACCESS     read-only
   STATUS     mandatory
   DESCRIPTION
     "This variable provides the component's string name for
      use with the ASCII Console Interface"
::= { pppLqmRowStatusEntry 2 }

pppLqmStorageType OBJECT-TYPE
   SYNTAX     StorageType 
   ACCESS     read-only
   STATUS     mandatory
   DESCRIPTION
     "This variable represents the storage type value for the
      pppLqm tables."
::= { pppLqmRowStatusEntry 4 }

pppLqmIndex OBJECT-TYPE
   SYNTAX     NonReplicated 
   ACCESS     not-accessible
   STATUS     mandatory
   DESCRIPTION
     "This variable represents the index for the pppLqm tables."
::= { pppLqmRowStatusEntry 10 }

pppLqmProvTable OBJECT-TYPE
   SYNTAX     SEQUENCE OF PppLqmProvEntry
   ACCESS     not-accessible
   STATUS     mandatory
   DESCRIPTION
     "This group contains the provisioned attributes for the Ppp Link Quality 
      Monitor component."
::= { pppLqm 10 }

pppLqmProvEntry OBJECT-TYPE
   SYNTAX     PppLqmProvEntry
   ACCESS     not-accessible
   STATUS     mandatory
   DESCRIPTION
     "An entry in the pppLqmProvTable."
   INDEX {
      pppIndex,
      pppLqmIndex }
::= { pppLqmProvTable 1 }

PppLqmProvEntry ::= SEQUENCE {
   pppLqmConfigPeriod
      Unsigned32,
   pppLqmConfigStatus
      INTEGER }

pppLqmConfigPeriod OBJECT-TYPE
   SYNTAX     Unsigned32 (0..2147483647)
   ACCESS     read-write
   STATUS     mandatory
   DESCRIPTION
     "This is the Lqm reporting period that the local Ppp entity will attempt to 
      negotiate with the remote entity, in units of hundredths of a second. A 
      value of '0' will allow the remote Ppp entity to determine the reporting 
      period. A value greater than 180,000 (1/2 hour) will allow the period to 
      be determined dynamically as a function of the transmit data rate. A 
      value from 1-9 will be rounded up to 10 during negotiation. A change to 
      this attribute will not take effect until Ppp is restarted (lock/unlock)."
   DEFVAL     { 0 }
::= { pppLqmProvEntry 1 }

pppLqmConfigStatus OBJECT-TYPE
   SYNTAX     INTEGER  {
                 disabled(1),
                 enabled(2) }
   ACCESS     read-write
   STATUS     mandatory
   DESCRIPTION
     "If this attribute is enabled, the local node will attempt to perform Lqm 
      negotiation with the remote node. If it is disabled then this negotiation is 
      not performed. A change to this attribute will not take effect until Ppp is 
      restarted (lock/unlock)."
   DEFVAL     { disabled }
::= { pppLqmProvEntry 2 }

pppLqmOperTable OBJECT-TYPE
   SYNTAX     SEQUENCE OF PppLqmOperEntry
   ACCESS     not-accessible
   STATUS     mandatory
   DESCRIPTION
     "This group contains the operational attributes for the Ppp Link Quality 
      Monitor component."
::= { pppLqm 11 }

pppLqmOperEntry OBJECT-TYPE
   SYNTAX     PppLqmOperEntry
   ACCESS     not-accessible
   STATUS     mandatory
   DESCRIPTION
     "An entry in the pppLqmOperTable."
   INDEX {
      pppIndex,
      pppLqmIndex }
::= { pppLqmOperTable 1 }

PppLqmOperEntry ::= SEQUENCE {
   pppLqmQuality
      INTEGER,
   pppLqmInGoodOctets
      Counter32,
   pppLqmLocalPeriod
      Unsigned32,
   pppLqmRemotePeriod
      Unsigned32,
   pppLqmOutLqrs
      Counter32,
   pppLqmInLqrs
      Counter32 }

pppLqmQuality OBJECT-TYPE
   SYNTAX     INTEGER  {
                 good(1),
                 bad(2),
                 notDetermined(3) }
   ACCESS     read-only
   STATUS     mandatory
   DESCRIPTION
     "This is the current quality of the link as declared by the local Ppp 
      entity's Link-Quality Management modules. A value of good indicates 
      that LinkQualityMonitor configStatus is enabled and Link quality is 
      above Link qualityThreshold. A value of bad indicates that 
      LinkQualityMonitor configStatus is enabled and Link quality is not 
      above Link qualityThreshold. A value of notDetermined indicates that 
      LinkQualityMonitor configStatus is enabled and the quality of the link 
      has not been calculated yet or LinkQualityMonitor configStatus is 
      disabled."
   DEFVAL     { notDetermined }
::= { pppLqmOperEntry 1 }

pppLqmInGoodOctets OBJECT-TYPE
   SYNTAX     Counter32 
   ACCESS     read-only
   STATUS     mandatory
   DESCRIPTION
     "This attribute counts the number of good octets received. This counter 
      will wrap around to 0 when it exceeds its maximum count."
::= { pppLqmOperEntry 2 }

pppLqmLocalPeriod OBJECT-TYPE
   SYNTAX     Unsigned32 (1..4294967295)
   ACCESS     read-only
   STATUS     mandatory
   DESCRIPTION
     "This is the Lqm reporting period, in hundredths of a second that is in 
      effect for the local Ppp entity."
   DEFVAL     { 1 }
::= { pppLqmOperEntry 3 }

pppLqmRemotePeriod OBJECT-TYPE
   SYNTAX     Unsigned32 (1..4294967295)
   ACCESS     read-only
   STATUS     mandatory
   DESCRIPTION
     "This is the Lqm reporting period, in hundredths of a second, that is in 
      effect for the remote Ppp entity."
   DEFVAL     { 1 }
::= { pppLqmOperEntry 4 }

pppLqmOutLqrs OBJECT-TYPE
   SYNTAX     Counter32 
   ACCESS     read-only
   STATUS     mandatory
   DESCRIPTION
     "This attribute counts the number of link quality reports sent out. This 
      counter will wrap around to 0 when it exceeds its maximum count."
::= { pppLqmOperEntry 5 }

pppLqmInLqrs OBJECT-TYPE
   SYNTAX     Counter32 
   ACCESS     read-only
   STATUS     mandatory
   DESCRIPTION
     "This attribute counts the number of link quality reports received. This 
      counter will wrap around to 0 when it exceeds its maximum count."
::= { pppLqmOperEntry 6 }


-- Ppp/n NetworkControlProtocol
-- This component is used to contain all the operational attributes for the 
-- Ppp Network Control Protocols (Ncp). This is a mandatory 
-- subcomponent of Ppp and does not need to be manually added.

pppNcp OBJECT IDENTIFIER ::= { ppp 4 }



pppNcpRowStatusTable OBJECT-TYPE
   SYNTAX     SEQUENCE OF PppNcpRowStatusEntry
   ACCESS     not-accessible
   STATUS     mandatory
   DESCRIPTION
     "This entry controls the addition and deletion of 
      pppNcp components."
::= { pppNcp 1 }

pppNcpRowStatusEntry OBJECT-TYPE
   SYNTAX     PppNcpRowStatusEntry
   ACCESS     not-accessible
   STATUS     mandatory
   DESCRIPTION
     "A single entry in the table represents a single 
      pppNcp component."
   INDEX {
      pppIndex,
      pppNcpIndex }
::= { pppNcpRowStatusTable 1 }

PppNcpRowStatusEntry ::= SEQUENCE {
   pppNcpRowStatus
      RowStatus,
   pppNcpComponentName
      DisplayString,
   pppNcpStorageType
      StorageType,
   pppNcpIndex
      NonReplicated }

pppNcpRowStatus OBJECT-TYPE
   SYNTAX     RowStatus 
   ACCESS     read-only
   STATUS     mandatory
   DESCRIPTION
     "This variable is used as the basis for SNMP naming of
      pppNcp components.
      These components cannot be added nor deleted."
::= { pppNcpRowStatusEntry 1 }

pppNcpComponentName OBJECT-TYPE
   SYNTAX     DisplayString 
   ACCESS     read-only
   STATUS     mandatory
   DESCRIPTION
     "This variable provides the component's string name for
      use with the ASCII Console Interface"
::= { pppNcpRowStatusEntry 2 }

pppNcpStorageType OBJECT-TYPE
   SYNTAX     StorageType 
   ACCESS     read-only
   STATUS     mandatory
   DESCRIPTION
     "This variable represents the storage type value for the
      pppNcp tables."
::= { pppNcpRowStatusEntry 4 }

pppNcpIndex OBJECT-TYPE
   SYNTAX     NonReplicated 
   ACCESS     not-accessible
   STATUS     mandatory
   DESCRIPTION
     "This variable represents the index for the pppNcp tables."
::= { pppNcpRowStatusEntry 10 }

pppNcpBprovTable OBJECT-TYPE
   SYNTAX     SEQUENCE OF PppNcpBprovEntry
   ACCESS     not-accessible
   STATUS     mandatory
   DESCRIPTION
     "This group contains the provisioned attributes for the Bridge Network 
      Control Protocol."
::= { pppNcp 11 }

pppNcpBprovEntry OBJECT-TYPE
   SYNTAX     PppNcpBprovEntry
   ACCESS     not-accessible
   STATUS     mandatory
   DESCRIPTION
     "An entry in the pppNcpBprovTable."
   INDEX {
      pppIndex,
      pppNcpIndex }
::= { pppNcpBprovTable 1 }

PppNcpBprovEntry ::= SEQUENCE {
   pppNcpBConfigTinygram
      INTEGER,
   pppNcpBConfigLanId
      INTEGER }

pppNcpBConfigTinygram OBJECT-TYPE
   SYNTAX     INTEGER  {
                 disabled(1),
                 enabled(2) }
   ACCESS     read-write
   STATUS     mandatory
   DESCRIPTION
     "If this attribute is set to disabled then the local Bridge Network Control 
      Protocol (Bncp) entity will not initiate the tinygram compression option 
      negotiation. If it is enabled then the local Bncp entity will initiate 
      negotiation of this option. A change to this attribute will not take effect 
      until Ppp is restarted (lock/unlock)."
   DEFVAL     { enabled }
::= { pppNcpBprovEntry 1 }

pppNcpBConfigLanId OBJECT-TYPE
   SYNTAX     INTEGER  {
                 disabled(1),
                 enabled(2) }
   ACCESS     read-write
   STATUS     mandatory
   DESCRIPTION
     "If this attribute is set to disabled then the local Bncp entity will not 
      initiate the lan identification option negotiation. If it is enabled then the 
      local Bncp entity will initiate negotiation of the option. A change to this 
      attribute will not take effect until Ppp is restarted (lock/unlock)."
   DEFVAL     { enabled }
::= { pppNcpBprovEntry 4 }

pppNcpIpOperTable OBJECT-TYPE
   SYNTAX     SEQUENCE OF PppNcpIpOperEntry
   ACCESS     not-accessible
   STATUS     mandatory
   DESCRIPTION
     "This group contains the Ip Network Control Protocol operational 
      attributes."
::= { pppNcp 12 }

pppNcpIpOperEntry OBJECT-TYPE
   SYNTAX     PppNcpIpOperEntry
   ACCESS     not-accessible
   STATUS     mandatory
   DESCRIPTION
     "An entry in the pppNcpIpOperTable."
   INDEX {
      pppIndex,
      pppNcpIndex }
::= { pppNcpIpOperTable 1 }

PppNcpIpOperEntry ::= SEQUENCE {
   pppNcpIpOperState
      INTEGER }

pppNcpIpOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Ip network protocol. For more 
      information as to the definition of each state see RFC1331 section 5.3."
   DEFVAL     { initial }
::= { pppNcpIpOperEntry 1 }

pppNcpBoperTable OBJECT-TYPE
   SYNTAX     SEQUENCE OF PppNcpBoperEntry
   ACCESS     not-accessible
   STATUS     mandatory
   DESCRIPTION
     "This group contains the Bridge Network Control Protocol operational 
      attributes."
::= { pppNcp 14 }

pppNcpBoperEntry OBJECT-TYPE
   SYNTAX     PppNcpBoperEntry
   ACCESS     not-accessible
   STATUS     mandatory
   DESCRIPTION
     "An entry in the pppNcpBoperTable."
   INDEX {
      pppIndex,
      pppNcpIndex }
::= { pppNcpBoperTable 1 }

PppNcpBoperEntry ::= SEQUENCE {
   pppNcpBOperState
      INTEGER,
   pppNcpBLocalToRemoteTinygramComp
      INTEGER,
   pppNcpBRemoteToLocalTinygramComp
      INTEGER,
   pppNcpBLocalToRemoteLanId
      INTEGER,
   pppNcpBRemoteToLocalLanId
      INTEGER }

pppNcpBOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational status of the bridge network protocol. For more 
      information as to the definition of each state see RFC1331 section 5.3."
   DEFVAL     { initial }
::= { pppNcpBoperEntry 1 }

pppNcpBLocalToRemoteTinygramComp OBJECT-TYPE
   SYNTAX     INTEGER  {
                 disabled(1),
                 enabled(2) }
   ACCESS     read-only
   STATUS     mandatory
   DESCRIPTION
     "This attribute indicates whether the local node will perform tinygram 
      compression when sending packets to the remote entity. If it is disabled 
      then the local entity will not perform tinygram compression. If it is 
      enabled then the local entity will perform tinygram compression."
   DEFVAL     { disabled }
::= { pppNcpBoperEntry 3 }

pppNcpBRemoteToLocalTinygramComp OBJECT-TYPE
   SYNTAX     INTEGER  {
                 disabled(1),
                 enabled(2) }
   ACCESS     read-only
   STATUS     mandatory
   DESCRIPTION
     "If this attribute is disabled then the remote entity is not expected to 
      perform tinygram compression. If it is enabled then the remote entity is 
      expected to perform tinygram compression."
   DEFVAL     { disabled }
::= { pppNcpBoperEntry 4 }

pppNcpBLocalToRemoteLanId OBJECT-TYPE
   SYNTAX     INTEGER  {
                 disabled(1),
                 enabled(2) }
   ACCESS     read-only
   STATUS     mandatory
   DESCRIPTION
     "This attribute indicates whether the local node will include the lan 
      identification field in transmitted packets or not. If it is disabled then the 
      local node will not transmit this field, enabled means that the field will 
      be transmitted."
   DEFVAL     { disabled }
::= { pppNcpBoperEntry 5 }

pppNcpBRemoteToLocalLanId OBJECT-TYPE
   SYNTAX     INTEGER  {
                 disabled(1),
                 enabled(2) }
   ACCESS     read-only
   STATUS     mandatory
   DESCRIPTION
     "This attribute indicates whether the remote node has indicated that it 
      will include the lan identification field in transmitted packets or not. If it 
      is disabled then the field will not be transmitted, if enabled then the field 
      will be transmitted."
   DEFVAL     { disabled }
::= { pppNcpBoperEntry 6 }

pppNcpOperTable OBJECT-TYPE
   SYNTAX     SEQUENCE OF PppNcpOperEntry
   ACCESS     not-accessible
   STATUS     mandatory
   DESCRIPTION
     "This group contains the operational attributes for any Network Control 
      Protocols other than Ip and Bridge."
::= { pppNcp 16 }

pppNcpOperEntry OBJECT-TYPE
   SYNTAX     PppNcpOperEntry
   ACCESS     not-accessible
   STATUS     mandatory
   DESCRIPTION
     "An entry in the pppNcpOperTable."
   INDEX {
      pppIndex,
      pppNcpIndex }
::= { pppNcpOperTable 1 }

PppNcpOperEntry ::= SEQUENCE {
   pppNcpAppletalkOperState
      INTEGER,
   pppNcpIpxOperState
      INTEGER,
   pppNcpXnsOperState
      INTEGER,
   pppNcpDecnetOperState
      INTEGER }

pppNcpAppletalkOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the AppleTalk network protocol. For 
      more information as to the definition of each state see RFC1331 section 
      5.3."
   DEFVAL     { initial }
::= { pppNcpOperEntry 1 }

pppNcpIpxOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Ipx network protocol. For more 
      information as to the definition of each state see RFC1331 section 5.3."
   DEFVAL     { initial }
::= { pppNcpOperEntry 2 }

pppNcpXnsOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Xns network protocol. For more 
      information as to the definition of each state see RFC1331 section 5.3."
   DEFVAL     { initial }
::= { pppNcpOperEntry 3 }

pppNcpDecnetOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the DecNet network protocol. For more 
      information as to the definition of each state see RFC1331 section 5.3."
   DEFVAL     { initial }
::= { pppNcpOperEntry 4 }


-- Ppp/n Ncp BridgeMediaConfigEntry/n
-- This component is one entry in the BridgeMediaConfigEntry table. 
-- There are four of these components automatically added to create the 
-- table. The instances of this component are the mac types for which the 
-- data in this table entry pertains to.
-- 1) ethernet - IEEE 802.3/Ethernet
-- 2) tokenBus - IEEE 802.4/Token Bus
-- 3) tokenRing - IEEE 802.5/Token Ring
-- 4) fddi - Fddi

pppNcpBmcEntry OBJECT IDENTIFIER ::= { pppNcp 2 }



pppNcpBmcEntryRowStatusTable OBJECT-TYPE
   SYNTAX     SEQUENCE OF PppNcpBmcEntryRowStatusEntry
   ACCESS     not-accessible
   STATUS     mandatory
   DESCRIPTION
     "This entry controls the addition and deletion of 
      pppNcpBmcEntry components."
::= { pppNcpBmcEntry 1 }

pppNcpBmcEntryRowStatusEntry OBJECT-TYPE
   SYNTAX     PppNcpBmcEntryRowStatusEntry
   ACCESS     not-accessible
   STATUS     mandatory
   DESCRIPTION
     "A single entry in the table represents a single 
      pppNcpBmcEntry component."
   INDEX {
      pppIndex,
      pppNcpIndex,
      pppNcpBmcEntryMacTypeIndex }
::= { pppNcpBmcEntryRowStatusTable 1 }

PppNcpBmcEntryRowStatusEntry ::= SEQUENCE {
   pppNcpBmcEntryRowStatus
      RowStatus,
   pppNcpBmcEntryComponentName
      DisplayString,
   pppNcpBmcEntryStorageType
      StorageType,
   pppNcpBmcEntryMacTypeIndex
      INTEGER }

pppNcpBmcEntryRowStatus OBJECT-TYPE
   SYNTAX     RowStatus 
   ACCESS     read-write
   STATUS     mandatory
   DESCRIPTION
     "This variable is used as the basis for SNMP naming of
      pppNcpBmcEntry components.
      These components can be added."
::= { pppNcpBmcEntryRowStatusEntry 1 }

pppNcpBmcEntryComponentName OBJECT-TYPE
   SYNTAX     DisplayString 
   ACCESS     read-only
   STATUS     mandatory
   DESCRIPTION
     "This variable provides the component's string name for
      use with the ASCII Console Interface"
::= { pppNcpBmcEntryRowStatusEntry 2 }

pppNcpBmcEntryStorageType OBJECT-TYPE
   SYNTAX     StorageType 
   ACCESS     read-only
   STATUS     mandatory
   DESCRIPTION
     "This variable represents the storage type value for the
      pppNcpBmcEntry tables."
::= { pppNcpBmcEntryRowStatusEntry 4 }

pppNcpBmcEntryMacTypeIndex OBJECT-TYPE
   SYNTAX     INTEGER  {
                 ethernet(1),
                 tokenBus(2),
                 tokenRing(3),
                 fddi(4) }
   ACCESS     not-accessible
   STATUS     mandatory
   DESCRIPTION
     "This variable represents the index for the pppNcpBmcEntry tables."
::= { pppNcpBmcEntryRowStatusEntry 10 }

pppNcpBmcEntryProvTable OBJECT-TYPE
   SYNTAX     SEQUENCE OF PppNcpBmcEntryProvEntry
   ACCESS     not-accessible
   STATUS     mandatory
   DESCRIPTION
     "This group contains the attributes for one entry in the 
      BridgeMediaConfigEntry table."
::= { pppNcpBmcEntry 10 }

pppNcpBmcEntryProvEntry OBJECT-TYPE
   SYNTAX     PppNcpBmcEntryProvEntry
   ACCESS     not-accessible
   STATUS     mandatory
   DESCRIPTION
     "An entry in the pppNcpBmcEntryProvTable."
   INDEX {
      pppIndex,
      pppNcpIndex,
      pppNcpBmcEntryMacTypeIndex }
::= { pppNcpBmcEntryProvTable 1 }

PppNcpBmcEntryProvEntry ::= SEQUENCE {
   pppNcpBmcEntryLocalStatus
      INTEGER }

pppNcpBmcEntryLocalStatus OBJECT-TYPE
   SYNTAX     INTEGER  {
                 accept(1) }
   ACCESS     read-write
   STATUS     mandatory
   DESCRIPTION
     "This attribute indicates whether the local Ppp bridging entity should 
      accept packets of the protocol type identified by the instance value of 
      this component. Setting this attribute to accept allows packets of this 
      protocol type to be accepted. A change to this attribute will not take 
      effect until Ppp is restarted (lock/unlock)."
   DEFVAL     { accept }
::= { pppNcpBmcEntryProvEntry 1 }

-- 
-- *** THIS SUBTREE CURRENTLY NOT IMPLEMENTED ***
-- 

-- Ppp/n Ncp BridgeMediaEntry/n
-- This component is one entry in the BridgeMediaEntry table. There will 
-- be four of these components created automatically to create the table. 
-- The instances of this component are the mac types for which the data in 
-- this table entry pertains to.
-- 1) ethernet - IEEE 802.3/Ethernet
-- 2) tokenBus - IEEE 802.4/Token Bus
-- 3) tokenRing - IEEE 802.5/Token Ring
-- 4) fddi - Fddi

pppNcpBmEntry OBJECT IDENTIFIER ::= { pppNcp 3 }



pppNcpBmEntryRowStatusTable OBJECT-TYPE
   SYNTAX     SEQUENCE OF PppNcpBmEntryRowStatusEntry
   ACCESS     not-accessible
   STATUS     mandatory
   DESCRIPTION
     "*** THIS TABLE CURRENTLY NOT IMPLEMENTED ***

      This entry controls the addition and deletion of 
      pppNcpBmEntry components."
::= { pppNcpBmEntry 1 }

pppNcpBmEntryRowStatusEntry OBJECT-TYPE
   SYNTAX     PppNcpBmEntryRowStatusEntry
   ACCESS     not-accessible
   STATUS     mandatory
   DESCRIPTION
     "A single entry in the table represents a single 
      pppNcpBmEntry component."
   INDEX {
      pppIndex,
      pppNcpIndex,
      pppNcpBmEntryMacTypeIndex }
::= { pppNcpBmEntryRowStatusTable 1 }

PppNcpBmEntryRowStatusEntry ::= SEQUENCE {
   pppNcpBmEntryRowStatus
      RowStatus,
   pppNcpBmEntryComponentName
      DisplayString,
   pppNcpBmEntryStorageType
      StorageType,
   pppNcpBmEntryMacTypeIndex
      INTEGER }

pppNcpBmEntryRowStatus OBJECT-TYPE
   SYNTAX     RowStatus 
   ACCESS     read-only
   STATUS     mandatory
   DESCRIPTION
     "This variable is used as the basis for SNMP naming of
      pppNcpBmEntry components.
      These components cannot be added nor deleted."
::= { pppNcpBmEntryRowStatusEntry 1 }

pppNcpBmEntryComponentName OBJECT-TYPE
   SYNTAX     DisplayString 
   ACCESS     read-only
   STATUS     mandatory
   DESCRIPTION
     "This variable provides the component's string name for
      use with the ASCII Console Interface"
::= { pppNcpBmEntryRowStatusEntry 2 }

pppNcpBmEntryStorageType OBJECT-TYPE
   SYNTAX     StorageType 
   ACCESS     read-only
   STATUS     mandatory
   DESCRIPTION
     "This variable represents the storage type value for the
      pppNcpBmEntry tables."
::= { pppNcpBmEntryRowStatusEntry 4 }

pppNcpBmEntryMacTypeIndex OBJECT-TYPE
   SYNTAX     INTEGER  {
                 ethernet(1),
                 tokenBus(2),
                 tokenRing(3),
                 fddi(4) }
   ACCESS     not-accessible
   STATUS     mandatory
   DESCRIPTION
     "This variable represents the index for the pppNcpBmEntry tables."
::= { pppNcpBmEntryRowStatusEntry 10 }

pppNcpBmEntryOperTable OBJECT-TYPE
   SYNTAX     SEQUENCE OF PppNcpBmEntryOperEntry
   ACCESS     not-accessible
   STATUS     mandatory
   DESCRIPTION
     "*** THIS TABLE CURRENTLY NOT IMPLEMENTED ***

      This group contains the attributes for one entry in the BridgeMediaEntry 
      table."
::= { pppNcpBmEntry 10 }

pppNcpBmEntryOperEntry OBJECT-TYPE
   SYNTAX     PppNcpBmEntryOperEntry
   ACCESS     not-accessible
   STATUS     mandatory
   DESCRIPTION
     "An entry in the pppNcpBmEntryOperTable."
   INDEX {
      pppIndex,
      pppNcpIndex,
      pppNcpBmEntryMacTypeIndex }
::= { pppNcpBmEntryOperTable 1 }

PppNcpBmEntryOperEntry ::= SEQUENCE {
   pppNcpBmEntryLocalStatus
      INTEGER,
   pppNcpBmEntryRemoteStatus
      INTEGER }

pppNcpBmEntryLocalStatus OBJECT-TYPE
   SYNTAX     INTEGER  {
                 accept(1),
                 dontAccept(2) }
   ACCESS     read-only
   STATUS     mandatory
   DESCRIPTION
     "This attribute indicates whether the local Ppp bridging entity will accept 
      packets of the protocol type identified by the instance value of this 
      component. A value of accept indicates that packets of this protocol type 
      will be accepted. A value of dontAccept indicates that packets of this 
      type will not be accepted."
::= { pppNcpBmEntryOperEntry 2 }

pppNcpBmEntryRemoteStatus OBJECT-TYPE
   SYNTAX     INTEGER  {
                 accept(1),
                 dontAccept(2) }
   ACCESS     read-only
   STATUS     mandatory
   DESCRIPTION
     "This attribute indicates whether the remote Ppp bridging entity will 
      accept packets of the protocol type identified by the instance value of 
      this component. A value of accept indicates that packets of this protocol 
      type will be accepted. A value of dontAccept indicates that packets of 
      this type will not be accepted."
::= { pppNcpBmEntryOperEntry 3 }


-- 
-- Ppp/n Framer
-- 
-- The Framer component controls link layer framing for application 
-- components sending and receiving data on a link interface. It is also 
-- through Framer, that an application component is associated with a 
-- specific hardware link interface.
-- 
-- The Framer component provides provisionable attributes related to 
-- datapath aspects of the hardware interface (such as crc and frame length) 
-- rather than interface specific attributes (such as modem leads and 
-- clocking) which are associated with specific hardware components (such 
-- as V35/n or DS1/n). The Framer component also provides a 
-- provisionable attribute which binds the application component to a 
-- specific hardware component.
-- 
-- The Framer component contains operational attributes for link interface 
-- datapath statistics (such as frame counts and aborts).
-- 

pppFramer OBJECT IDENTIFIER ::= { ppp 5 }



pppFramerRowStatusTable OBJECT-TYPE
   SYNTAX     SEQUENCE OF PppFramerRowStatusEntry
   ACCESS     not-accessible
   STATUS     mandatory
   DESCRIPTION
     "This entry controls the addition and deletion of 
      pppFramer components."
::= { pppFramer 1 }

pppFramerRowStatusEntry OBJECT-TYPE
   SYNTAX     PppFramerRowStatusEntry
   ACCESS     not-accessible
   STATUS     mandatory
   DESCRIPTION
     "A single entry in the table represents a single 
      pppFramer component."
   INDEX {
      pppIndex,
      pppFramerIndex }
::= { pppFramerRowStatusTable 1 }

PppFramerRowStatusEntry ::= SEQUENCE {
   pppFramerRowStatus
      RowStatus,
   pppFramerComponentName
      DisplayString,
   pppFramerStorageType
      StorageType,
   pppFramerIndex
      NonReplicated }

pppFramerRowStatus OBJECT-TYPE
   SYNTAX     RowStatus 
   ACCESS     read-only
   STATUS     mandatory
   DESCRIPTION
     "This variable is used as the basis for SNMP naming of
      pppFramer components.
      These components cannot be added nor deleted."
::= { pppFramerRowStatusEntry 1 }

pppFramerComponentName OBJECT-TYPE
   SYNTAX     DisplayString 
   ACCESS     read-only
   STATUS     mandatory
   DESCRIPTION
     "This variable provides the component's string name for
      use with the ASCII Console Interface"
::= { pppFramerRowStatusEntry 2 }

pppFramerStorageType OBJECT-TYPE
   SYNTAX     StorageType 
   ACCESS     read-only
   STATUS     mandatory
   DESCRIPTION
     "This variable represents the storage type value for the
      pppFramer tables."
::= { pppFramerRowStatusEntry 4 }

pppFramerIndex OBJECT-TYPE
   SYNTAX     NonReplicated 
   ACCESS     not-accessible
   STATUS     mandatory
   DESCRIPTION
     "This variable represents the index for the pppFramer tables."
::= { pppFramerRowStatusEntry 10 }

pppFramerProvTable OBJECT-TYPE
   SYNTAX     SEQUENCE OF PppFramerProvEntry
   ACCESS     not-accessible
   STATUS     mandatory
   DESCRIPTION
     "This group contains the base provisioning data for the Framer 
      component. Application or hardware interface specific provisioning data 
      is contained in other provisionable Framer groups."
::= { pppFramer 10 }

pppFramerProvEntry OBJECT-TYPE
   SYNTAX     PppFramerProvEntry
   ACCESS     not-accessible
   STATUS     mandatory
   DESCRIPTION
     "An entry in the pppFramerProvTable."
   INDEX {
      pppIndex,
      pppFramerIndex }
::= { pppFramerProvTable 1 }

PppFramerProvEntry ::= SEQUENCE {
   pppFramerInterfaceName
      Link }

pppFramerInterfaceName OBJECT-TYPE
   SYNTAX     Link 
   ACCESS     read-write
   STATUS     mandatory
   DESCRIPTION
     "This attribute contains a hardware component name.
      
      The attribute associates the application with a specific link. This defines 
      the logical processor on which Framer's parent component (as well as 
      Framer itself) will run."
::= { pppFramerProvEntry 1 }

pppFramerStateTable OBJECT-TYPE
   SYNTAX     SEQUENCE OF PppFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { pppFramer 12 }

pppFramerStateEntry OBJECT-TYPE
   SYNTAX     PppFramerStateEntry
   ACCESS     not-accessible
   STATUS     mandatory
   DESCRIPTION
     "An entry in the pppFramerStateTable."
   INDEX {
      pppIndex,
      pppFramerIndex }
::= { pppFramerStateTable 1 }

PppFramerStateEntry ::= SEQUENCE {
   pppFramerAdminState
      INTEGER,
   pppFramerOperationalState
      INTEGER,
   pppFramerUsageState
      INTEGER }

pppFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { pppFramerStateEntry 1 }

pppFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { pppFramerStateEntry 2 }

pppFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { pppFramerStateEntry 3 }

pppFramerStatsTable OBJECT-TYPE
   SYNTAX     SEQUENCE OF PppFramerStatsEntry
   ACCESS     not-accessible
   STATUS     mandatory
   DESCRIPTION
     "This group contains the operational statistics data for a Framer 
      component."
::= { pppFramer 13 }

pppFramerStatsEntry OBJECT-TYPE
   SYNTAX     PppFramerStatsEntry
   ACCESS     not-accessible
   STATUS     mandatory
   DESCRIPTION
     "An entry in the pppFramerStatsTable."
   INDEX {
      pppIndex,
      pppFramerIndex }
::= { pppFramerStatsTable 1 }

PppFramerStatsEntry ::= SEQUENCE {
   pppFramerFrmToIf
      Counter32,
   pppFramerFrmFromIf
      Counter32,
   pppFramerAborts
      Counter32,
   pppFramerCrcErrors
      Counter32,
   pppFramerLrcErrors
      Counter32,
   pppFramerNonOctetErrors
      Counter32,
   pppFramerOverruns
      Counter32,
   pppFramerUnderruns
      Counter32,
   pppFramerLargeFrmErrors
      Counter32 }

pppFramerFrmToIf OBJECT-TYPE
   SYNTAX     Counter32 
   ACCESS     read-only
   STATUS     mandatory
   DESCRIPTION
     "This attribute counts the number of frames transmitted to the link 
      interface by Framer.
      
      Note: This does not include the number of frames transmitted directly to 
      the hardware queue, thus bypassing the Framer component."
::= { pppFramerStatsEntry 1 }

pppFramerFrmFromIf OBJECT-TYPE
   SYNTAX     Counter32 
   ACCESS     read-only
   STATUS     mandatory
   DESCRIPTION
     "This attribute counts the number of frames received from the link 
      interface by Framer."
::= { pppFramerStatsEntry 2 }

pppFramerAborts OBJECT-TYPE
   SYNTAX     Counter32 
   ACCESS     read-only
   STATUS     mandatory
   DESCRIPTION
     "This attribute counts the total number of aborts received."
::= { pppFramerStatsEntry 3 }

pppFramerCrcErrors OBJECT-TYPE
   SYNTAX     Counter32 
   ACCESS     read-only
   STATUS     mandatory
   DESCRIPTION
     "This attribute counts the total number of frames with CRC errors."
::= { pppFramerStatsEntry 4 }

pppFramerLrcErrors OBJECT-TYPE
   SYNTAX     Counter32 
   ACCESS     read-only
   STATUS     mandatory
   DESCRIPTION
     "This attribute counts the total number of frames with LRC errors."
::= { pppFramerStatsEntry 5 }

pppFramerNonOctetErrors OBJECT-TYPE
   SYNTAX     Counter32 
   ACCESS     read-only
   STATUS     mandatory
   DESCRIPTION
     "This attribute counts the total number of frames that were non octet 
      aligned."
::= { pppFramerStatsEntry 6 }

pppFramerOverruns OBJECT-TYPE
   SYNTAX     Counter32 
   ACCESS     read-only
   STATUS     mandatory
   DESCRIPTION
     "This attribute counts the total number of frames received from the link 
      for which overruns occurred."
::= { pppFramerStatsEntry 7 }

pppFramerUnderruns OBJECT-TYPE
   SYNTAX     Counter32 
   ACCESS     read-only
   STATUS     mandatory
   DESCRIPTION
     "This attribute counts the total number of frames transmitted to the link 
      for which underruns occurred."
::= { pppFramerStatsEntry 8 }

pppFramerLargeFrmErrors OBJECT-TYPE
   SYNTAX     Counter32 
   ACCESS     read-only
   STATUS     mandatory
   DESCRIPTION
     "This attribute counts the total number of frames received which were too 
      large. The frame execeeded the maximumFrameLengthLimit provisioned 
      attribute or it contained more than the 255 block hardware limit."
::= { pppFramerStatsEntry 9 }

pppFramerUtilTable OBJECT-TYPE
   SYNTAX     SEQUENCE OF PppFramerUtilEntry
   ACCESS     not-accessible
   STATUS     mandatory
   DESCRIPTION
     "This group contains the link utilizaiton operational data for a Framer 
      component."
::= { pppFramer 14 }

pppFramerUtilEntry OBJECT-TYPE
   SYNTAX     PppFramerUtilEntry
   ACCESS     not-accessible
   STATUS     mandatory
   DESCRIPTION
     "An entry in the pppFramerUtilTable."
   INDEX {
      pppIndex,
      pppFramerIndex }
::= { pppFramerUtilTable 1 }

PppFramerUtilEntry ::= SEQUENCE {
   pppFramerNormPrioLinkUtilToIf
      Gauge32,
   pppFramerNormPrioLinkUtilFromIf
      Gauge32 }

pppFramerNormPrioLinkUtilToIf OBJECT-TYPE
   SYNTAX     Gauge32 (0..100)
   ACCESS     read-only
   STATUS     mandatory
   DESCRIPTION
     "This attribute is the utilization of the normal priority data sent to the link 
      as a percentage of the available bandwidth on the link. The utilization is 
      the average for the last minute."
   DEFVAL     { 0 }
::= { pppFramerUtilEntry 1 }

pppFramerNormPrioLinkUtilFromIf OBJECT-TYPE
   SYNTAX     Gauge32 (0..100)
   ACCESS     read-only
   STATUS     mandatory
   DESCRIPTION
     "This attribute is the utilization of the normal priority data received from 
      the link as a percentage of the available bandwidth on the link. The 
      utilization is the average for the last minute."
   DEFVAL     { 0 }
::= { pppFramerUtilEntry 3 }


-- Ppp/n LinkEmissionQueue
-- This component provides a means of statistics gathering and packet 
-- discard.

pppLeq OBJECT IDENTIFIER ::= { ppp 6 }



pppLeqRowStatusTable OBJECT-TYPE
   SYNTAX     SEQUENCE OF PppLeqRowStatusEntry
   ACCESS     not-accessible
   STATUS     mandatory
   DESCRIPTION
     "This entry controls the addition and deletion of 
      pppLeq components."
::= { pppLeq 1 }

pppLeqRowStatusEntry OBJECT-TYPE
   SYNTAX     PppLeqRowStatusEntry
   ACCESS     not-accessible
   STATUS     mandatory
   DESCRIPTION
     "A single entry in the table represents a single 
      pppLeq component."
   INDEX {
      pppIndex,
      pppLeqIndex }
::= { pppLeqRowStatusTable 1 }

PppLeqRowStatusEntry ::= SEQUENCE {
   pppLeqRowStatus
      RowStatus,
   pppLeqComponentName
      DisplayString,
   pppLeqStorageType
      StorageType,
   pppLeqIndex
      NonReplicated }

pppLeqRowStatus OBJECT-TYPE
   SYNTAX     RowStatus 
   ACCESS     read-write
   STATUS     mandatory
   DESCRIPTION
     "This variable is used as the basis for SNMP naming of
      pppLeq components.
      These components can be added and deleted."
::= { pppLeqRowStatusEntry 1 }

pppLeqComponentName OBJECT-TYPE
   SYNTAX     DisplayString 
   ACCESS     read-only
   STATUS     mandatory
   DESCRIPTION
     "This variable provides the component's string name for
      use with the ASCII Console Interface"
::= { pppLeqRowStatusEntry 2 }

pppLeqStorageType OBJECT-TYPE
   SYNTAX     StorageType 
   ACCESS     read-only
   STATUS     mandatory
   DESCRIPTION
     "This variable represents the storage type value for the
      pppLeq tables."
::= { pppLeqRowStatusEntry 4 }

pppLeqIndex OBJECT-TYPE
   SYNTAX     NonReplicated 
   ACCESS     not-accessible
   STATUS     mandatory
   DESCRIPTION
     "This variable represents the index for the pppLeq tables."
::= { pppLeqRowStatusEntry 10 }

pppLeqProvTable OBJECT-TYPE
   SYNTAX     SEQUENCE OF PppLeqProvEntry
   ACCESS     not-accessible
   STATUS     mandatory
   DESCRIPTION
     "This group contains the provisioned attributes for the 
      LinkEmissionQueue component."
::= { pppLeq 10 }

pppLeqProvEntry OBJECT-TYPE
   SYNTAX     PppLeqProvEntry
   ACCESS     not-accessible
   STATUS     mandatory
   DESCRIPTION
     "An entry in the pppLeqProvTable."
   INDEX {
      pppIndex,
      pppLeqIndex }
::= { pppLeqProvTable 1 }

PppLeqProvEntry ::= SEQUENCE {
   pppLeqMaxPackets
      Unsigned32,
   pppLeqMaxMsecData
      Unsigned32,
   pppLeqMaxPercentMulticast
      Unsigned32,
   pppLeqTimeToLive
      Unsigned32 }

pppLeqMaxPackets OBJECT-TYPE
   SYNTAX     Unsigned32 (0..2048)
   ACCESS     read-write
   STATUS     mandatory
   DESCRIPTION
     "This attribute specifies the maximum number of packets allowed in the 
      Leq before being discarded. If this attribute is set to zero then the 
      maximum number of packets is calculated from the transmit data rate. 
      This calculated value is placed in queuePktThreshold."
   DEFVAL     { 0 }
::= { pppLeqProvEntry 1 }

pppLeqMaxMsecData OBJECT-TYPE
   SYNTAX     Unsigned32 (100..60000)
   ACCESS     read-write
   STATUS     mandatory
   DESCRIPTION
     "This attribute specifies the maximum number of 'Milliseconds worth of 
      data' allowed in the Leq before packets are discarded. The 
      queueByteThreshold will be calculated from this attribute, based on the 
      transmit data rate."
   DEFVAL     { 10000 }
::= { pppLeqProvEntry 2 }

pppLeqMaxPercentMulticast OBJECT-TYPE
   SYNTAX     Unsigned32 (1..100)
   ACCESS     read-write
   STATUS     mandatory
   DESCRIPTION
     "This attribute specifies the maximum percentage of multicast packets 
      allowed in the Leq, based on queuePktThreshold, before being 
      discarded. The calculated value will be placed in 
      queueMulticastThreshold."
   DEFVAL     { 50 }
::= { pppLeqProvEntry 3 }

pppLeqTimeToLive OBJECT-TYPE
   SYNTAX     Unsigned32 (100..60000)
   ACCESS     read-write
   STATUS     mandatory
   DESCRIPTION
     "This attribute specifies the 'Milliseconds Time To Live' of packets in 
      the Leq. If the timeToLive of a packet expires, it will be discarded."
   DEFVAL     { 10000 }
::= { pppLeqProvEntry 4 }

pppLeqStatsTable OBJECT-TYPE
   SYNTAX     SEQUENCE OF PppLeqStatsEntry
   ACCESS     not-accessible
   STATUS     mandatory
   DESCRIPTION
     "This group contains Link Emission Queue general statistics."
::= { pppLeq 11 }

pppLeqStatsEntry OBJECT-TYPE
   SYNTAX     PppLeqStatsEntry
   ACCESS     not-accessible
   STATUS     mandatory
   DESCRIPTION
     "An entry in the pppLeqStatsTable."
   INDEX {
      pppIndex,
      pppLeqIndex }
::= { pppLeqStatsTable 1 }

PppLeqStatsEntry ::= SEQUENCE {
   pppLeqTimedOutPkt
      Counter32,
   pppLeqHardwareForcedPkt
      Counter32,
   pppLeqForcedPktDiscards
      Counter32,
   pppLeqQueuePurgeDiscards
      Counter32 }

pppLeqTimedOutPkt OBJECT-TYPE
   SYNTAX     Counter32 
   ACCESS     read-only
   STATUS     mandatory
   DESCRIPTION
     "This attribute counts the number of packets that have been discarded due 
      to exceeding the timeToLive. This counter will wrap around to 0 when it 
      exceeds its maximum count."
::= { pppLeqStatsEntry 1 }

pppLeqHardwareForcedPkt OBJECT-TYPE
   SYNTAX     Counter32 
   ACCESS     read-only
   STATUS     mandatory
   DESCRIPTION
     "This attribute counts the number of hardware forced packets on this 
      instance of Ppp. This counter will wrap around to 0 when it exceeds its 
      maximum count."
::= { pppLeqStatsEntry 2 }

pppLeqForcedPktDiscards OBJECT-TYPE
   SYNTAX     Counter32 
   ACCESS     read-only
   STATUS     mandatory
   DESCRIPTION
     "This attribute counts the total number of hardware forced packets that 
      had to be discarded due to link failure. This counter will wrap around to 
      0 when it exceeds its maximum count."
::= { pppLeqStatsEntry 4 }

pppLeqQueuePurgeDiscards OBJECT-TYPE
   SYNTAX     Counter32 
   ACCESS     read-only
   STATUS     mandatory
   DESCRIPTION
     "This attribute counts the total number of packets discarded by a queue 
      purge (i.e. a discarding of all packets on the queue). This counter will 
      wrap around to 0 when it exceeds its maximum count."
::= { pppLeqStatsEntry 5 }

pppLeqTStatsTable OBJECT-TYPE
   SYNTAX     SEQUENCE OF PppLeqTStatsEntry
   ACCESS     not-accessible
   STATUS     mandatory
   DESCRIPTION
     "This group contains Link Emission Queue total statistics."
::= { pppLeq 12 }

pppLeqTStatsEntry OBJECT-TYPE
   SYNTAX     PppLeqTStatsEntry
   ACCESS     not-accessible
   STATUS     mandatory
   DESCRIPTION
     "An entry in the pppLeqTStatsTable."
   INDEX {
      pppIndex,
      pppLeqIndex }
::= { pppLeqTStatsTable 1 }

PppLeqTStatsEntry ::= SEQUENCE {
   pppLeqTotalPktHandled
      Counter32,
   pppLeqTotalPktForwarded
      Counter32,
   pppLeqTotalPktQueued
      Counter32,
   pppLeqTotalMulticastPkt
      Counter32,
   pppLeqTotalPktDiscards
      Counter32 }

pppLeqTotalPktHandled OBJECT-TYPE
   SYNTAX     Counter32 
   ACCESS     read-only
   STATUS     mandatory
   DESCRIPTION
     "This attribute counts the total number of packets handled by the Leq. 
      This counter will wrap around to 0 when it exceeds its maximum count."
::= { pppLeqTStatsEntry 1 }

pppLeqTotalPktForwarded OBJECT-TYPE
   SYNTAX     Counter32 
   ACCESS     read-only
   STATUS     mandatory
   DESCRIPTION
     "This attribute counts the total number of packets forwarded by the Leq. 
      This counter will wrap around to 0 when it exceeds its maximum count."
::= { pppLeqTStatsEntry 2 }

pppLeqTotalPktQueued OBJECT-TYPE
   SYNTAX     Counter32 
   ACCESS     read-only
   STATUS     mandatory
   DESCRIPTION
     "This attribute counts the total number of packets that required queuing 
      by the Leq due to transmit congestion. This counter will wrap around to 
      0 when it exceeds its maximum count."
::= { pppLeqTStatsEntry 3 }

pppLeqTotalMulticastPkt OBJECT-TYPE
   SYNTAX     Counter32 
   ACCESS     read-only
   STATUS     mandatory
   DESCRIPTION
     "This attribute counts the total number of multicast packets handled by 
      this instance of Ppp. This counter will wrap around to 0 when it exceeds 
      its maximum count."
::= { pppLeqTStatsEntry 4 }

pppLeqTotalPktDiscards OBJECT-TYPE
   SYNTAX     Counter32 
   ACCESS     read-only
   STATUS     mandatory
   DESCRIPTION
     "This attribute counts the total number of packets that were discarded for 
      this instance of Ppp. This is the sum of timedOutPkt, forcedPktDiscards, 
      queuePurgeDiscards, pktThresholdExceeded, byteThresholdExceeded, 
      mulThresholdExceeded, and memThresholdExceeded. This counter will 
      wrap around to 0 when it exceeds its maximum count."
::= { pppLeqTStatsEntry 8 }

pppLeqCStatsTable OBJECT-TYPE
   SYNTAX     SEQUENCE OF PppLeqCStatsEntry
   ACCESS     not-accessible
   STATUS     mandatory
   DESCRIPTION
     "This group contains Link Emission Queue current statistics."
::= { pppLeq 13 }

pppLeqCStatsEntry OBJECT-TYPE
   SYNTAX     PppLeqCStatsEntry
   ACCESS     not-accessible
   STATUS     mandatory
   DESCRIPTION
     "An entry in the pppLeqCStatsTable."
   INDEX {
      pppIndex,
      pppLeqIndex }
::= { pppLeqCStatsTable 1 }

PppLeqCStatsEntry ::= SEQUENCE {
   pppLeqCurrentPktQueued
      Gauge32,
   pppLeqCurrentBytesQueued
      Gauge32,
   pppLeqCurrentMulticastQueued
      Gauge32 }

pppLeqCurrentPktQueued OBJECT-TYPE
   SYNTAX     Gauge32 (0..4294967295)
   ACCESS     read-only
   STATUS     mandatory
   DESCRIPTION
     "This attribute counts the current number of packets queued."
   DEFVAL     { 0 }
::= { pppLeqCStatsEntry 1 }

pppLeqCurrentBytesQueued OBJECT-TYPE
   SYNTAX     Gauge32 (0..4294967295)
   ACCESS     read-only
   STATUS     mandatory
   DESCRIPTION
     "This attribute counts the current number of bytes queued."
   DEFVAL     { 0 }
::= { pppLeqCStatsEntry 2 }

pppLeqCurrentMulticastQueued OBJECT-TYPE
   SYNTAX     Gauge32 (0..4294967295)
   ACCESS     read-only
   STATUS     mandatory
   DESCRIPTION
     "This attribute counts the current number of multicast packets in the 
      queue."
   DEFVAL     { 0 }
::= { pppLeqCStatsEntry 3 }

pppLeqThrStatsTable OBJECT-TYPE
   SYNTAX     SEQUENCE OF PppLeqThrStatsEntry
   ACCESS     not-accessible
   STATUS     mandatory
   DESCRIPTION
     "This group contains Link Emission Queue threshold statistics."
::= { pppLeq 14 }

pppLeqThrStatsEntry OBJECT-TYPE
   SYNTAX     PppLeqThrStatsEntry
   ACCESS     not-accessible
   STATUS     mandatory
   DESCRIPTION
     "An entry in the pppLeqThrStatsTable."
   INDEX {
      pppIndex,
      pppLeqIndex }
::= { pppLeqThrStatsTable 1 }

PppLeqThrStatsEntry ::= SEQUENCE {
   pppLeqQueuePktThreshold
      Unsigned32,
   pppLeqPktThresholdExceeded
      Counter32,
   pppLeqQueueByteThreshold
      Unsigned32,
   pppLeqByteThresholdExceeded
      Counter32,
   pppLeqQueueMulticastThreshold
      Unsigned32,
   pppLeqMulThresholdExceeded
      Counter32,
   pppLeqMemThresholdExceeded
      Counter32 }

pppLeqQueuePktThreshold OBJECT-TYPE
   SYNTAX     Unsigned32 (0..4294967295)
   ACCESS     read-only
   STATUS     mandatory
   DESCRIPTION
     "This attribute is the maximum number of packets that can be contained 
      in the queue before being discarded. If maxPackets was set to 0 then this 
      attribute will contain the value that has been calculated based on the 
      transmit data rate. If maxPackets was set to one or more than this 
      attribute will contain that number."
   DEFVAL     { 0 }
::= { pppLeqThrStatsEntry 1 }

pppLeqPktThresholdExceeded OBJECT-TYPE
   SYNTAX     Counter32 
   ACCESS     read-only
   STATUS     mandatory
   DESCRIPTION
     "This attribute counts the number of packets discarded due to the 
      queuePktThreshold being exceeded. This counter will wrap around to 0 
      when it exceeds its maximum count."
::= { pppLeqThrStatsEntry 2 }

pppLeqQueueByteThreshold OBJECT-TYPE
   SYNTAX     Unsigned32 (0..4294967295)
   ACCESS     read-only
   STATUS     mandatory
   DESCRIPTION
     "This attribute is the maximum number of bytes allowed in the queue 
      based on maxMsecData and the transmit data rate."
   DEFVAL     { 0 }
::= { pppLeqThrStatsEntry 3 }

pppLeqByteThresholdExceeded OBJECT-TYPE
   SYNTAX     Counter32 
   ACCESS     read-only
   STATUS     mandatory
   DESCRIPTION
     "This attribute counts the number of packets discarded due to the 
      queueByteThreshold being exceeded. This counter will wrap around to 0 
      when it exceeds its maximum count."
::= { pppLeqThrStatsEntry 4 }

pppLeqQueueMulticastThreshold OBJECT-TYPE
   SYNTAX     Unsigned32 (0..4294967295)
   ACCESS     read-only
   STATUS     mandatory
   DESCRIPTION
     "This attribute is the number of multicast packets allowed in the queue 
      based on maxPercentMulticast and maxPackets."
   DEFVAL     { 0 }
::= { pppLeqThrStatsEntry 5 }

pppLeqMulThresholdExceeded OBJECT-TYPE
   SYNTAX     Counter32 
   ACCESS     read-only
   STATUS     mandatory
   DESCRIPTION
     "This attribute counts the number of packets discarded due to the 
      queueMulticastThreshold being exceeded. This counter will wrap 
      around to 0 when it exceeds its maximum count."
::= { pppLeqThrStatsEntry 6 }

pppLeqMemThresholdExceeded OBJECT-TYPE
   SYNTAX     Counter32 
   ACCESS     read-only
   STATUS     mandatory
   DESCRIPTION
     "This attribute counts the number of packets discarded due to exceeding 
      the memory usage threshold for Leq. The memory usage threshold is 
      determined by the Leq software, guaranteeing that the Leq does not 
      consume all of the memory. This counter will wrap around to 0 when it 
      exceeds its maximum count."
::= { pppLeqThrStatsEntry 7 }




-- 
-- Version and Compliance statements
-- 



-- Object-Group Statement:
-- A list of all current accessible leaf objects.

-- OBJECTS { pppNcpBOperState,
--           pppOperationalState,
--           pppNcpIpxOperState,
--           pppLnkTransmitFcsSize,
--           pppNcpStorageType,
--           pppFramerLrcErrors,
--           pppLeqTotalPktHandled,
--           pppLeqMemThresholdExceeded,
--           pppLqmComponentName,
--           pppLinkToProtocolPort,
--           pppLeqComponentName,
--           pppLnkConfigureRequestTries,
--           pppLnkQualityWindow,
--           pppLnkStorageType,
--           pppLeqQueuePurgeDiscards,
--           pppLqmStorageType,
--           pppNcpBConfigTinygram,
--           pppRowStatus,
--           pppLqmLocalPeriod,
--           pppLeqTotalPktForwarded,
--           pppLeqCurrentPktQueued,
--           pppLeqTotalPktDiscards,
--           pppNcpBmcEntryStorageType,
--           pppNcpBmEntryLocalStatus,
--           pppNcpAppletalkOperState,
--           pppNcpBLocalToRemoteTinygramComp,
--           pppLqmConfigStatus,
--           pppNcpBmcEntryLocalStatus,
--           pppLqmRemotePeriod,
--           pppFramerOverruns,
--           pppLnkReceiveFcsSize,
--           pppLeqTimeToLive,
--           pppLeqCurrentMulticastQueued,
--           pppNcpBmEntryComponentName,
--           pppLnkQualityThreshold,
--           pppNcpBmcEntryComponentName,
--           pppNcpBConfigLanId,
--           pppLeqTotalMulticastPkt,
--           pppLeqQueueByteThreshold,
--           pppLqmInGoodOctets,
--           pppAdminState,
--           pppLeqMulThresholdExceeded,
--           pppFramerComponentName,
--           pppNcpXnsOperState,
--           pppLeqRowStatus,
--           pppLeqMaxMsecData,
--           pppLnkLocalMru,
--           pppFramerFrmToIf,
--           pppLnkComponentName,
--           pppFramerUnderruns,
--           pppLeqQueueMulticastThreshold,
--           pppLqmRowStatus,
--           pppLqmOutLqrs,
--           pppComponentName,
--           pppLeqMaxPackets,
--           pppNcpIpOperState,
--           pppLnkConfigMagicNumber,
--           pppLeqMaxPercentMulticast,
--           pppLqmQuality,
--           pppNcpBmEntryStorageType,
--           pppLnkTerminateRequestTries,
--           pppLnkContinuityMonitor,
--           pppLeqHardwareForcedPkt,
--           pppLnkOperState,
--           pppNcpDecnetOperState,
--           pppLeqByteThresholdExceeded,
--           pppLnkNegativeAckTries,
--           pppSnmpOperStatus,
--           pppIfIndex,
--           pppFramerNormPrioLinkUtilToIf,
--           pppLeqForcedPktDiscards,
--           pppFramerFrmFromIf,
--           pppLnkBadAddresses,
--           pppFramerStorageType,
--           pppNcpBmEntryRowStatus,
--           pppLqmInLqrs,
--           pppFramerCrcErrors,
--           pppStorageType,
--           pppLeqTimedOutPkt,
--           pppNcpBmcEntryRowStatus,
--           pppNcpComponentName,
--           pppFramerAborts,
--           pppNcpBLocalToRemoteLanId,
--           pppFramerAdminState,
--           pppLnkConfigInitialMru,
--           pppLnkBadControls,
--           pppNcpBRemoteToLocalLanId,
--           pppLnkLineCondition,
--           pppFramerRowStatus,
--           pppLqmConfigPeriod,
--           pppFramerLargeFrmErrors,
--           pppLnkPacketTooLongs,
--           pppNcpRowStatus,
--           pppIfAdminStatus,
--           pppLnkRowStatus,
--           pppLnkRestartTimer,
--           pppCustomerIdentifier,
--           pppLeqPktThresholdExceeded,
--           pppFramerNonOctetErrors,
--           pppFramerUsageState,
--           pppFramerNormPrioLinkUtilFromIf,
--           pppLeqCurrentBytesQueued,
--           pppUsageState,
--           pppLnkBadFcss,
--           pppLnkRemoteMru,
--           pppFramerInterfaceName,
--           pppLeqStorageType,
--           pppLeqTotalPktQueued,
--           pppLeqQueuePktThreshold,
--           pppNcpBmEntryRemoteStatus,
--           pppNcpBRemoteToLocalTinygramComp,
--           pppFramerOperationalState }
-- STATUS  mandatory
-- DESCRIPTION
--   "A list of all current accessible leaf objects."

pppGroup OBJECT IDENTIFIER ::= { pppMIB 1 }
pppGroupBC OBJECT IDENTIFIER ::= { pppGroup 3 }
pppGroupBC02 OBJECT IDENTIFIER ::= { pppGroupBC 3 }
pppGroupBC02A OBJECT IDENTIFIER ::= { pppGroupBC02 2 }



-- Agent-Capabilities Statement:

-- PRODUCT-RELEASE "Passport Release 7.0 Ppp."
-- STATUS          mandatory
-- DESCRIPTION     "Ppp MIB: MIB Version BC02A,
--                  Software Version BG00S4C."
-- SUPPORTS        Nortel-Magellan-Passport-PppMIB
--    INCLUDES     { pppGroupBC02A }
--        rfc1471 (Link Control Protocol of the Point-to-Point Protocol)
-- 
-- SUPPORTS RFC1471-MIB
--    INCLUDES	{ pppLinkStatusTable, pppLinkConfigTable, pppLqrTable, 
--       	  pppLqrConfigTable }  
--    			   pppLqrExtnsTable, pppEchoTest, and
--       		   pppDiscardTest are not supported.
-- 
--       variations for pppLinkConfigTable
-- 
--    VARIATION		pppLinkConfigInitialMRU
--       SYNTAX		INTEGER (68..18000)
--       DEFVAL		{ 18000 }
--       DESCRIPTION	"Packets smaller than 68 bytes or larger than 18000
--          		bytes can not be supported.  This implementation
--         		will default the pppLinkConfigInitialMRU to 18000."
-- 
--    VARIATION		pppLinkConfigReceiveACCMap
--       DEFVAL		{ '00000000'h }
--       DESCRIPTION	"ACC map is not supported by this implementation."
-- 
-- 
--    VARIATION		pppLinkConfigTransmitACCMap
--       DEFVAL		{ '00000000'h }
--       DESCRIPTION	"ACC map is not supported by this implementation."
-- 
--    VARIATION		pppLinkConfigMagicNumber
--       DEFVAL		{ true }
--       DESCRIPTION	"This implementation will default
--          		 pppLinkConfigMagicNumber to true."
-- 
--    VARIATION		pppLinkConfigFcsSize
--       SYNTAX    	INTEGER (16)
--       DESCRIPTION	"Only 16 bit crc is supported by this implementation."
-- 
--       variations for pppLqrConfigTable
-- 
--    VARIATION		pppLqrConfigStatus
--       DEFVAL		{ disabled }
--       DESCRIPTION	"This implementation will default pppLqrConfigStatus 
--       		to disabled."
-- 
--  
--       rfc1472 (Security Protocols of the Point-to-Point Protocol are
--                not supported)
-- 
--       rfc1473 (IP Network Control Protocol of the Point-to-Point Protocol)
-- 
--    SUPPORTS RFC1473-MIB
--       INCLUDES	{ pppIpTable, pppIpConfigTable }
-- 
--       variations for pppIpConfigTable
-- 
--    VARIATION		pppIpConfigCompression
--       WRITE-SYNTAX	INTEGER { none(1) }
--       DESCRIPTION	"No IP compression is supported by this implementation."
-- 
-- 
-- 
--       rfc1474 (Bridge Network Control Protocol of the Point-to-Point Protocol)
-- 
--    SUPPORTS RFC1474-MIB
--       INCLUDES	{ pppBridgeTable, pppBridgeConfigTable,
--       		  pppBridgeMediaTable, pppBridgeMediaConfigTable }
-- 
--       variations for pppBridgeConfigTable
-- 
--    VARIATION		pppBridgeConfigRingId
--       WRITE-SYNTAX	INTEGER { false(1) }
--       DESCRIPTION	"Remote Ring Identification Option negotiation is not
--       		supported by this implementation."
-- 
--    VARIATION		pppBridgeConfigLineId
--       WRITE-SYNTAX	INTEGER { false(1) }
--       DESCRIPTION	"Line Identification Option negotiation is not 
--                         supported by this implementation."
-- 
--    VARIATION		pppBridgeConfigLanId
--       DEFVAL		{ true }
--       DESCRIPTION	"This implementation will initiate negotiation of this
--       		        option by default."
-- 
--       variations for pppBridgeMediaConfigTable
-- 
--    VARIATION		pppBridgeMediaConfigMacType
--       ACCESS		read-only
--       DESCRIPTION	"This implementation does not allow writes to the 
--       	        	pppBridgeMediaConfigMacType."
-- 
--    VARIATION		pppBridgeMediaConfigLocalStatus
--       WRITE-SYNTAX	INTEGER { accept(1) }
--       DESCRIPTION	"This implementation does not allow packets to be
--         		selectively accepted based on Mac type."
-- 

pppCapabilities OBJECT IDENTIFIER ::= { pppMIB 3 }
pppCapabilitiesBC OBJECT IDENTIFIER ::= { pppCapabilities 3 }
pppCapabilitiesBC02 OBJECT IDENTIFIER ::= { pppCapabilitiesBC 3 }
pppCapabilitiesBC02A OBJECT IDENTIFIER ::= { pppCapabilitiesBC02 2 }





END
