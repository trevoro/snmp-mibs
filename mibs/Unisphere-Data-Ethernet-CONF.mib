-- *****************************************************************************
-- Unisphere-Data-Ethernet-CONF
--
-- SNMP Agent Capabilities definitions for the Ethernet MIBs.
--
-- Copyright (c) 2001, 2002 Unisphere Networks, Inc.  All rights reserved.
-- *****************************************************************************

Unisphere-Data-Ethernet-CONF DEFINITIONS ::= BEGIN

IMPORTS
    MODULE-IDENTITY
        FROM SNMPv2-SMI
    AGENT-CAPABILITIES
        FROM SNMPv2-CONF
    usDataAgents
        FROM Unisphere-Data-Agents
    etherStatsGroup, etherStats100MbsGroup
        FROM EtherLike-MIB
    usdEthernetGroup, usdEthernetSubIfGroup, usdVlanGroup, usdVlanSubIfGroup,
    usdVlanSubIfGroup2
        FROM Unisphere-Data-ETHERNET-MIB;

usdEthernetAgent MODULE-IDENTITY
    LAST-UPDATED "200204052033Z"  -- 05-Apr-02 03:33 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Ethernet component of the
        SNMP agent in the Unisphere Routing Switch family of products."
    -- Revision History
    REVISION    "200204052033Z"  -- 05-Apr-02 03:33 PM EST  - RX 4.0
    DESCRIPTION
        "Added VLAN stack support."
    REVISION    "200110252136Z"  -- 25-Oct-01 05:36 PM EDT  - RX 3.2
    DESCRIPTION
        "The initial release of this management information module."
    ::= { usDataAgents 14 }


-- *****************************************************************************
-- Ethernet interface agent capabilities.
-- *****************************************************************************
usdEthernetAgentV1 AGENT-CAPABILITIES
    PRODUCT-RELEASE
        "Version 1 of the Ethernet component of the Unisphere Routing Switch
        SNMP agent.  This version of the Ethernet component was supported in the
        Unisphere RX 2.x system releases."
    STATUS      obsolete
    DESCRIPTION
        "The MIBs supported by the SNMP agent for the Ethernet application in
        the Unisphere Routing Switch.  These capabilities became obsolete when
        VLAN support was add."
    SUPPORTS    EtherLike-MIB
        INCLUDES  {
            etherStatsGroup,
            etherStats100MbsGroup }
    SUPPORTS    Unisphere-Data-ETHERNET-MIB
        INCLUDES  {
            usdEthernetGroup,
            usdEthernetSubIfGroup }
    ::= { usdEthernetAgent 1 }

usdEthernetAgentV2 AGENT-CAPABILITIES
    PRODUCT-RELEASE
        "Version 2 of the Ethernet component of the Unisphere Routing Switch
        SNMP agent.  This version of the Ethernet component was supported in the
        Unisphere RX 3.x system releases."
    STATUS      obsolete
    DESCRIPTION
        "The MIBs supported by the SNMP agent for the Ethernet application in
        the Unisphere Routing Switch.  These capabilities became obsolete when
        VLAN stack support was added."
    SUPPORTS    EtherLike-MIB
        INCLUDES  {
            etherStatsGroup,
            etherStats100MbsGroup }
    SUPPORTS    Unisphere-Data-ETHERNET-MIB
        INCLUDES  {
            usdEthernetGroup,
            usdEthernetSubIfGroup,
            usdVlanGroup,
            usdVlanSubIfGroup }
    ::= { usdEthernetAgent 2 }

usdEthernetAgentV3 AGENT-CAPABILITIES
    PRODUCT-RELEASE
        "Version 3 of the Ethernet component of the Unisphere Routing Switch
        SNMP agent.  This version of the Ethernet component is supported in the
        Unisphere RX 4.0 and subsequent system releases."
    STATUS      current
    DESCRIPTION
        "The MIBs supported by the SNMP agent for the Ethernet application in
        the Unisphere Routing Switch."
    SUPPORTS    EtherLike-MIB
        INCLUDES  {
            etherStatsGroup,
            etherStats100MbsGroup }
    SUPPORTS    Unisphere-Data-ETHERNET-MIB
        INCLUDES  {
            usdEthernetGroup,
            usdEthernetSubIfGroup,
            usdVlanGroup,
            usdVlanSubIfGroup2 }
    ::= { usdEthernetAgent 3 }

END
