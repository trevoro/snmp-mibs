-- *****************************************************************************
-- Copyright: Ericsson Telecom AB 2000
-- Doc no: 162/190 55-CAA 134 74 Uen
--
--
-- NAME ANS-MLBAS-MIB.mib
--
-- REVISION HISTORY
--
--
-- PA1  990505  Martin Reteike
--              First version
-- PA2	990511	qtxoswi
--		Second version
-- PA3	990519	qtxoswi
--		Converted to SNMPv2 etc.
-- PA4	990527	qtxoswi
--		Made some small changes
-- PA5	990602	qtxoswi
--		Changed mlbasAtSlotRnPos to read-only (from read-write)
--		Removed mlbasAtCUPerfStop
--		Added	mlbasDL15PerfAvailTime, mlbasUL15PerfAvailTime,
--			mlbasDL24PerfAvailTime, mlbasUL24PerfAvailTime
--		Changed some names
-- PA6	990624	qtxoswi
--		Added	mlbasDL15PerfTerminalId, mlbasUL15PerfTerminalId,
--			mlbasDL24PerfTerminalId, mlbasUL24PerfTerminalId
-- PA7  991011  etxanlg
--		Added	mlbasDownLinkLog15minTable, mlbasUpLinkLog15minTable,
--			mlbasDownLinkLog24hourTable, mlbasUpLinkLog24hourTable
-- PA8  991019  qtxoswi
--              Added mlbasAtSlotRowStatus to mlbasAtSlotTable
-- PA9  991022  qtxoswi
--              Removed mlbasDL15LogTerminalId, mlbasUL15LogTerminalId,
--			mlbasDL24LogTerminalId, mlbasUL24LogTerminalId
-- PA10 991028  qtxoswi
--              Added   mlbasServiceUnitPortTable
-- PA11 000217  etxlaaa
--              CR-69: Added mlbasRnRUNomRfInPower to mlbasRadioNodeTable
--
-- PA12 000313  etxlaaa
--              Added sign_off_ats to mlbasRadioNodeTable
-- PA13 001011  teiadeg Updated ansRadioNodeTable for Radio Node Protection.
-- PA14 001027  teiadeg Updated ansRadioNodeTable for 14 Mhz.
-- PA15 010608  teigaba Updated for MIB Clean-up.
-- PA16 010620  teigaba Converted to SNMPv1.
-- PA17 011015  teigaba Changed branch.


-- *****************************************************************************

ANS-MLBAS-MIB DEFINITIONS ::= BEGIN



IMPORTS
        OBJECT-TYPE
                FROM SNMPv2-SMI
	DisplayString
                FROM RFC1213-MIB
	RowPointer, RowStatus, mlpmpR115, DateAndTime
		FROM ANS-COMMON-MIB
	ansAccessUserPortSystemNode, ansAccessUserPortSubrack,
	ansAccessUserPortPosition, ansAccessUserPortIndex
		FROM ANS-GS-MIB
	ansBoardSystemNodeIndex, ansBoardSubrackIndex, ansBoardPosition,
	ansSlotSystemNodeIndex, ansSlotSubrackIndex, ansSlotPosition
		FROM ANS-EQUIPMENT-MIB;

mlbas			OBJECT IDENTIFIER ::= {mlpmpR115 5}
mlbasRadioNode		OBJECT IDENTIFIER ::= {mlbas 1}
mlbasAccessTerminalSlot	OBJECT IDENTIFIER ::= {mlbas 2}
mlbasAccessTerminal	OBJECT IDENTIFIER ::= {mlbas 3}
mlbasServiceUnit	OBJECT IDENTIFIER ::= {mlbas 4}
mlbasDownLinkPerf15min	OBJECT IDENTIFIER ::= {mlbas 5}
mlbasUpLinkPerf15min	OBJECT IDENTIFIER ::= {mlbas 6}
mlbasDownLinkPerf24hour	OBJECT IDENTIFIER ::= {mlbas 7}
mlbasUpLinkPerf24hour	OBJECT IDENTIFIER ::= {mlbas 8}
mlbasDownLinkLog15min	OBJECT IDENTIFIER ::= {mlbas 9}
mlbasUpLinkLog15min	OBJECT IDENTIFIER ::= {mlbas 10}
mlbasDownLinkLog24hour	OBJECT IDENTIFIER ::= {mlbas 11}
mlbasUpLinkLog24hour	OBJECT IDENTIFIER ::= {mlbas 12}
mlbasServiceUnitPort    OBJECT IDENTIFIER ::= {mlbas 13}



-- *****************************************************************************
-- 
--			MLBAS Radio Node Table
--
-- *****************************************************************************

mlbasRadioNodeTable OBJECT-TYPE 
	SYNTAX	SEQUENCE OF MlbasRadioNodeEntry
	ACCESS	not-accessible
	STATUS	mandatory
	DESCRIPTION
		"Radio node table"
	::= { mlbasRadioNode 1 }

mlbasRadioNodeEntry OBJECT-TYPE
	SYNTAX	MlbasRadioNodeEntry
	ACCESS	not-accessible
	STATUS	mandatory
	DESCRIPTION
		"This entity represents a WBAS radio node which consists of
		 an indoor Control Unit (CU) and an outdoor Radio Unit. The
		 CU consists of MAC and modem and is implemented as an
		 extended board that can be inserted into a subrack slot."
	INDEX {ansBoardSystemNodeIndex, ansBoardSubrackIndex, ansBoardPosition}
	::= { mlbasRadioNodeTable 1 }

MlbasRadioNodeEntry ::= SEQUENCE {
	mlbasRnCUId		DisplayString (SIZE(20)),
	mlbasRnCUSecurity	INTEGER,
	mlbasRnCUBerThreshold	INTEGER,
	mlbasRnCUBwLimit	INTEGER,
	mlbasRnCULoopMode	INTEGER,
	mlbasRnCULoopPoint	INTEGER,
	mlbasRnCUAlarmLevel	INTEGER,
	mlbasRnCUSignedOnAts	INTEGER,
	mlbasRnCUSignedOffAts	INTEGER,
	mlbasRnCUChBw		INTEGER,
	mlbasRnCUHwIdModem	DisplayString (SIZE(41)),
	mlbasRnCUSwIdModem	DisplayString (SIZE(29)),
	mlbasRnRUDownFreq	INTEGER,
	mlbasRnRUUpFreq		INTEGER,
	mlbasRnRUDownFreqMin	INTEGER,
	mlbasRnRUDownFreqMax	INTEGER,
	mlbasRnRUFreqDuplex	INTEGER,
	mlbasRnRUFreqStep	INTEGER,
	mlbasRnRUOutputPower	INTEGER,
	mlbasRnRUOutputPowerMin	INTEGER,
	mlbasRnRUOutputPowerMax	INTEGER,
	mlbasRnRUHwIdRadio	DisplayString (SIZE(41)),
	mlbasRnRUSwIdRadio	DisplayString (SIZE(29)),
	mlbasRnInterfLevel	INTEGER,
	mlbasRnRSSIEXP		INTEGER,
	mlbasRnCUSignOffAts	INTEGER,
	mlbasRnSwitchBoardAction	INTEGER
}

--
--	This table is an extension of the ansBoardTable and uses the index
--	(ansBoardSystemNodeIndex, ansBoardSubrackIndex, ansBoardPosition)
--

mlbasRnCUId	OBJECT-TYPE
	-- TODO: Check if it is ok to have a variable size on the rn id
	SYNTAX	DisplayString (SIZE(20))
	ACCESS	read-write
	STATUS		mandatory
	DESCRIPTION
		"Radio Node Identity"
	::= { mlbasRadioNodeEntry 1 }

mlbasRnCUSecurity	OBJECT-TYPE
	SYNTAX	INTEGER{
			enable(1),
			disable(2)
			}
	ACCESS	read-write
	STATUS		mandatory
	DESCRIPTION
		"Controls scrambling on RNs and ATs"
	::= { mlbasRadioNodeEntry 2 }

mlbasRnCUBerThreshold	OBJECT-TYPE
	SYNTAX	INTEGER{
			ber3(3),
			ber4(4),
			ber5(5),
			ber6(6)
			}
	ACCESS	read-write
	STATUS  mandatory	
	DESCRIPTION
		"Threshold for bit error rate alarms"
	::= { mlbasRadioNodeEntry 3 }

mlbasRnCUBwLimit	OBJECT-TYPE
	SYNTAX	INTEGER (1..100)
	ACCESS	read-write
	STATUS		mandatory
	DESCRIPTION
		"Percentage of the available RN - AT air interface bandwidth
		 that is to be utilized for user-traffic"
	::= { mlbasRadioNodeEntry 4 }

mlbasRnCULoopMode	OBJECT-TYPE
	SYNTAX	INTEGER{
			off(1),
			permanent(2),
			selfTest(3)
			}
	ACCESS	read-write
	STATUS		mandatory
	DESCRIPTION
		"The loop mode"
	::= { mlbasRadioNodeEntry 5 }

mlbasRnCULoopPoint	OBJECT-TYPE
	SYNTAX	INTEGER{
			modem(1),
			radio(2)
			}
	ACCESS	read-write
	STATUS		mandatory
	DESCRIPTION
		"The loop point: Only editable when permanent"
	::= { mlbasRadioNodeEntry 6 }

mlbasRnCUAlarmLevel	OBJECT-TYPE
	SYNTAX	INTEGER{
			allAlarms(1),
			filter(2),
			noAlarms(3)
			}
	ACCESS	read-write
	STATUS		mandatory
	DESCRIPTION
		"Controls the alarm filtering at the RN"
	::= { mlbasRadioNodeEntry 7 }

mlbasRnCUSignedOnAts	OBJECT-TYPE
	SYNTAX		INTEGER
	ACCESS		read-only
	STATUS		mandatory
	DESCRIPTION
		"Number of signed on ATs at the RN"
	::= { mlbasRadioNodeEntry 8 }

mlbasRnCUSignedOffAts	OBJECT-TYPE
	SYNTAX		INTEGER
	ACCESS		read-only
	STATUS		mandatory
	DESCRIPTION
		"Number of signed off ATs at the RN"
	::= { mlbasRadioNodeEntry 9 }

mlbasRnCUChBw	OBJECT-TYPE
	SYNTAX		INTEGER
	ACCESS		read-only
	STATUS		mandatory
	DESCRIPTION
		"Channel Bandwidth [kHz]"
	::= { mlbasRadioNodeEntry 10 }

mlbasRnCUHwIdModem	OBJECT-TYPE
	SYNTAX		DisplayString (SIZE(41))
	ACCESS		read-only
	STATUS		mandatory
	DESCRIPTION
		"The hardware id of the modem"
	::= { mlbasRadioNodeEntry 11 }

mlbasRnCUSwIdModem	OBJECT-TYPE
	SYNTAX		DisplayString (SIZE(29))
	ACCESS		read-only
	STATUS		mandatory
	DESCRIPTION
		"The software id of the modem"
	::= { mlbasRadioNodeEntry 12 }

mlbasRnRUDownFreq	OBJECT-TYPE
	SYNTAX		INTEGER
	ACCESS	read-write
	STATUS		mandatory
	DESCRIPTION
		"Current down link center frequency [kHz]"
	::= { mlbasRadioNodeEntry 13 }

mlbasRnRUUpFreq	OBJECT-TYPE
	SYNTAX		INTEGER
	ACCESS		read-only
	STATUS		mandatory
	DESCRIPTION
		"Current up link center frequency [kHz]"
	::= { mlbasRadioNodeEntry 14 }

mlbasRnRUDownFreqMin	OBJECT-TYPE
	SYNTAX		INTEGER
	ACCESS		read-only
	STATUS		mandatory
	DESCRIPTION
		"Min. down link center frequency in subband [kHz]"
	::= { mlbasRadioNodeEntry 15 }

mlbasRnRUDownFreqMax	OBJECT-TYPE
	SYNTAX		INTEGER
	ACCESS		read-only
	STATUS		mandatory
	DESCRIPTION
		"Max. down link center frequency in subband [kHz]"
	::= { mlbasRadioNodeEntry 16 }

mlbasRnRUFreqDuplex	OBJECT-TYPE
	SYNTAX		INTEGER
	ACCESS		read-only
	STATUS		mandatory
	DESCRIPTION
		"Duplex dist. (mlbasRnRUUpFreq - mlbasRnRUDownFreq) [kHz]"
	::= { mlbasRadioNodeEntry 17 }

mlbasRnRUFreqStep	OBJECT-TYPE
	SYNTAX		INTEGER
	ACCESS		read-only
	STATUS		mandatory
	DESCRIPTION
		"Size of one frequency tuning step [kHz]"
	::= { mlbasRadioNodeEntry 18 }

mlbasRnRUOutputPower	OBJECT-TYPE
	SYNTAX		INTEGER
	ACCESS	read-write
	STATUS		mandatory
	DESCRIPTION
		"Current output power [dbm]"
	::= { mlbasRadioNodeEntry 19 }

mlbasRnRUOutputPowerMin	OBJECT-TYPE
	SYNTAX		INTEGER
	ACCESS		read-only
	STATUS		mandatory
	DESCRIPTION
		"Minimum output power [dbm]"
	::= { mlbasRadioNodeEntry 20 }

mlbasRnRUOutputPowerMax	OBJECT-TYPE
	SYNTAX		INTEGER
	ACCESS		read-only
	STATUS		mandatory
	DESCRIPTION
		"Maximum output power [dbm]"
	::= { mlbasRadioNodeEntry 21 }

mlbasRnRUHwIdRadio	OBJECT-TYPE
	SYNTAX		DisplayString (SIZE(41))
	ACCESS		read-only
	STATUS		mandatory
	DESCRIPTION
		"The hardware id of the radio"
	::= { mlbasRadioNodeEntry 22 }

mlbasRnRUSwIdRadio	OBJECT-TYPE
	SYNTAX		DisplayString (SIZE(29))
	ACCESS		read-only
	STATUS		mandatory
	DESCRIPTION
		"The software id of the radio"
	::= { mlbasRadioNodeEntry 23 }


mlbasRnInterfLevel      OBJECT-TYPE
        SYNTAX          INTEGER{
                         low(1),
                         medium(2),
                         high(3),
                         manual(4)
			}
        ACCESS      read-write
        STATUS          mandatory
        DESCRIPTION
                "Interference levels to set the RSSI expected"
        ::= { mlbasRadioNodeEntry 24 }


mlbasRnRSSIEXP	 	OBJECT-TYPE
	SYNTAX		INTEGER
	ACCESS	read-write
	STATUS		mandatory
	DESCRIPTION
		"Nominal RF Input Power [dbm]"
	::= { mlbasRadioNodeEntry 25 }

mlbasRnCUSignOffAts	OBJECT-TYPE
	SYNTAX	INTEGER{
			normal(1),
			signOff(2)
			}
	ACCESS	read-write
	STATUS		mandatory
	DESCRIPTION
		"Initiates sign off of all ATs at the RN"
	::= { mlbasRadioNodeEntry 26 }

mlbasRnSwitchBoardAction  OBJECT-TYPE
        SYNTAX  INTEGER{
                        none(1),
                        switch-board(2)
                        }
        ACCESS      read-write
        STATUS          mandatory
        DESCRIPTION
                ""
        ::= { mlbasRadioNodeEntry 27 }




-- *****************************************************************************
-- 
--			MLBAS Access Terminal Slot Table
--
-- *****************************************************************************

mlbasAccessTerminalSlotTable OBJECT-TYPE 
	SYNTAX	SEQUENCE OF MlbasAccessTerminalSlotEntry
	ACCESS	not-accessible
	STATUS		mandatory
	DESCRIPTION
		"Access Terminal Slot table"
	::= { mlbasAccessTerminalSlot 1 }

mlbasAccessTerminalSlotEntry OBJECT-TYPE 
	SYNTAX	MlbasAccessTerminalSlotEntry
	ACCESS	not-accessible
	STATUS		mandatory
	DESCRIPTION
		"This entity represents the relation between a Radio Node
		 and an Access Terminal."
	INDEX {ansSlotSystemNodeIndex, ansSlotSubrackIndex, ansSlotPosition}
	::= { mlbasAccessTerminalSlotTable 1 }

MlbasAccessTerminalSlotEntry ::= SEQUENCE {
	mlbasAtSlotTerminalId		DisplayString (SIZE(20)),
	mlbasAtSlotRnPos		INTEGER,
	mlbasAtSlotLocation		DisplayString (SIZE(0..255)),
	mlbasAtSlotSignOnAction		INTEGER,
	mlbasAtSlotSignOnStatus		INTEGER,
	mlbasAtSlotRowStatus		RowStatus
}

--
--	This table is an extension of the ansSlotTable and uses the index
--	(ansSlotSystemNodeIndex, ansSlotSubrackIndex, ansSlotPosition)
--

mlbasAtSlotTerminalId	OBJECT-TYPE
	SYNTAX		DisplayString (SIZE(20))
	ACCESS	read-write -- sec_key
	STATUS		mandatory
	DESCRIPTION
		"Access Terminal Identity, unique within the system"
	::= { mlbasAccessTerminalSlotEntry 1 }

mlbasAtSlotRnPos	OBJECT-TYPE
	SYNTAX		INTEGER
	ACCESS	read-write
	STATUS		mandatory
	DESCRIPTION
		"RN control board pos. within the subrack"
	::= { mlbasAccessTerminalSlotEntry 2 }

mlbasAtSlotLocation	OBJECT-TYPE
	SYNTAX		DisplayString (SIZE(0..255))
	ACCESS	read-write
	STATUS		mandatory
	DESCRIPTION
		"Physical location of the AT"
	::= { mlbasAccessTerminalSlotEntry 3 }

mlbasAtSlotSignOnAction	OBJECT-TYPE
	SYNTAX	INTEGER{
			none(1),
			on(2),
			off(3)
			}
	ACCESS	read-write
	STATUS		mandatory
	DESCRIPTION
		"Initiates sign on for the AT"
	::= { mlbasAccessTerminalSlotEntry 4 }

mlbasAtSlotSignOnStatus	OBJECT-TYPE
	SYNTAX	INTEGER{
			signedOn(1),
			signedOff(2),
			signingOn(3),
			signingOff(4)
			}
	ACCESS 		read-only
	STATUS 		mandatory
	DESCRIPTION
		"Current sign on status for the AT"
	::= { mlbasAccessTerminalSlotEntry 5 }

mlbasAtSlotRowStatus OBJECT-TYPE
	SYNTAX		RowStatus
	ACCESS	read-write
	STATUS		mandatory
	DESCRIPTION
		""
	::= { mlbasAccessTerminalSlotEntry 6 }


-- *****************************************************************************
-- 
--			MLBAS Access Terminal Table
--
-- *****************************************************************************

mlbasAccessTerminalTable OBJECT-TYPE 
	SYNTAX	SEQUENCE OF MlbasAccessTerminalEntry
	ACCESS	not-accessible
	STATUS		mandatory
	DESCRIPTION
		"Access Terminal table"
	::= { mlbasAccessTerminal 1 }

mlbasAccessTerminalEntry OBJECT-TYPE 
	SYNTAX	MlbasAccessTerminalEntry
	ACCESS	not-accessible
	STATUS		mandatory
	DESCRIPTION
		"This entity represents a WBAS Access Terminal in the remote
		 part of the access network located at a customer.
		 Collection of link performance is also controlled via this
		 entity."
	INDEX {ansSlotSystemNodeIndex, ansSlotSubrackIndex, ansSlotPosition}
	::= { mlbasAccessTerminalTable 1 }

MlbasAccessTerminalEntry ::= SEQUENCE {
	mlbasAtCUPerformance		INTEGER,
	mlbasAtCUPerfStart		DateAndTime,
	mlbasAtCUAtmLoop		INTEGER,
	mlbasAtCUBerThreshold		INTEGER,
	mlbasAtCUValid15MinPerf		INTEGER,
	mlbasAtCUInvalid15MinPerf	INTEGER,
	mlbasAtCUValid24HPerf		INTEGER,
	mlbasAtCUInvalid24HPerf		INTEGER,
	mlbasAtCUHwIdModem		DisplayString (SIZE(41)),
	mlbasAtCUSwIdModem		DisplayString (SIZE(29)),
	mlbasAtRUDownFreq		INTEGER,
	mlbasAtRUUpFreq			INTEGER,
	mlbasAtRUOutputPower		INTEGER,
	mlbasAtRUHwIdRadio		DisplayString (SIZE(41)),
	mlbasAtRUSwIdRadio		DisplayString (SIZE(29))
}

--
--	This table has been modifed by qtxoswi
--

mlbasAtCUPerformance	OBJECT-TYPE
	SYNTAX	INTEGER{
			enable(1),
			disable(2)
			}
	ACCESS	read-write
	STATUS		mandatory
	DESCRIPTION
		"Current performance monitoring status"
	::= { mlbasAccessTerminalEntry 1 }

mlbasAtCUPerfStart	OBJECT-TYPE
	SYNTAX		DateAndTime
	ACCESS		read-only
	STATUS		mandatory
	DESCRIPTION
		"Indicates when monitoring was started"
	::= { mlbasAccessTerminalEntry 2 }

mlbasAtCUAtmLoop	OBJECT-TYPE
	SYNTAX	INTEGER{
			on(1),
			off(2)
			}
	ACCESS	read-write
	STATUS		mandatory
	DESCRIPTION
		"Controls ATM traffic loop"
	::= { mlbasAccessTerminalEntry 3 }

mlbasAtCUBerThreshold	OBJECT-TYPE
	SYNTAX	INTEGER{
			ber3(3),
			ber4(4),
			ber5(5),
			ber6(6)
			}
	ACCESS	read-write
	STATUS		mandatory
	DESCRIPTION
		"Threshold for bit error rate alarms"
	::= { mlbasAccessTerminalEntry 4 }

mlbasAtCUValid15MinPerf	OBJECT-TYPE
	SYNTAX		INTEGER
	ACCESS		read-only
	STATUS		mandatory
	DESCRIPTION
		"Number of valid 15 min. periods stored in CP"
	::= { mlbasAccessTerminalEntry 5 }

mlbasAtCUInvalid15MinPerf	OBJECT-TYPE
	SYNTAX			INTEGER
	ACCESS			read-only
	STATUS			mandatory
	DESCRIPTION
		"Number of invalid 15 min. periods stored in CP"
	::= { mlbasAccessTerminalEntry 6 }

mlbasAtCUValid24HPerf	OBJECT-TYPE
	SYNTAX		INTEGER
	ACCESS		read-only
	STATUS		mandatory
	DESCRIPTION
		"Number of valid 24 hour periods stored in CP"
	::= { mlbasAccessTerminalEntry 7 }

mlbasAtCUInvalid24HPerf	OBJECT-TYPE
	SYNTAX		INTEGER
	ACCESS		read-only
	STATUS		mandatory
	DESCRIPTION
		"Number of invalid 24 hour periods stored in CP"
	::= { mlbasAccessTerminalEntry 8 }

mlbasAtCUHwIdModem	OBJECT-TYPE
	SYNTAX		DisplayString (SIZE(41))
	ACCESS		read-only
	STATUS		mandatory
	DESCRIPTION
		"The hardware id of the modem"
	::= { mlbasAccessTerminalEntry 9 }

mlbasAtCUSwIdModem	OBJECT-TYPE
	SYNTAX		DisplayString (SIZE(29))
	ACCESS		read-only
	STATUS		mandatory
	DESCRIPTION
		"The software id of the modem"
	::= { mlbasAccessTerminalEntry 10 }

mlbasAtRUDownFreq	OBJECT-TYPE
	SYNTAX		INTEGER
	ACCESS		read-only
	STATUS		mandatory
	DESCRIPTION
		"Current down link frequency [kHz]"
	::= { mlbasAccessTerminalEntry 11 }

mlbasAtRUUpFreq		OBJECT-TYPE
	SYNTAX		INTEGER
	ACCESS		read-only
	STATUS		mandatory
	DESCRIPTION
		"Current up link frequency [kHz]"
	::= { mlbasAccessTerminalEntry 12 }

mlbasAtRUOutputPower	OBJECT-TYPE
	SYNTAX		INTEGER
	ACCESS		read-only
	STATUS		mandatory
	DESCRIPTION
		"Current output power [dbm]"
	::= { mlbasAccessTerminalEntry 13 }

mlbasAtRUHwIdRadio	OBJECT-TYPE
	SYNTAX		DisplayString (SIZE(41))
	ACCESS		read-only
	STATUS		mandatory
	DESCRIPTION
		"The hardware id of the radio"
	::= { mlbasAccessTerminalEntry 14 }

mlbasAtRUSwIdRadio	OBJECT-TYPE
	SYNTAX		DisplayString (SIZE(29))
	ACCESS		read-only
	STATUS		mandatory
	DESCRIPTION
		"The software id of the radio"
	::= { mlbasAccessTerminalEntry 15 }



-- *****************************************************************************
-- 
--			MLBAS Service (Interface) Unit Table
--
-- *****************************************************************************

mlbasServiceUnitTable OBJECT-TYPE
	SYNTAX	SEQUENCE OF MlbasServiceUnitEntry
	ACCESS	not-accessible
	STATUS		mandatory
	DESCRIPTION
		"Service Interface Unit table"
	::= { mlbasServiceUnit 1 }

mlbasServiceUnitEntry OBJECT-TYPE
	SYNTAX	MlbasServiceUnitEntry
	ACCESS	not-accessible
	STATUS		mandatory
	DESCRIPTION
		"This entity represents a WBAS Service Interface Unit which
		 can be inserted into an Access Terminal as a plug-in card.
		 Both plug-in card and corresponding slot are covered by
		 the entity."
	INDEX {ansBoardSystemNodeIndex, ansBoardSubrackIndex,
	       ansBoardPosition, mlbasSuPos}
	::= { mlbasServiceUnitTable 1 }

MlbasServiceUnitEntry ::= SEQUENCE {
	mlbasSuPos		INTEGER,
	mlbasSuManagedStatus	INTEGER,
	mlbasSuOperState	INTEGER,
	mlbasSuHwId		DisplayString (SIZE(35)),
	mlbasSuType		INTEGER,
	mlbasSuPciId		INTEGER,
	mlbasSuPciVendor	INTEGER,
	mlbasSuPortStartIndex	INTEGER,
	mlbasSuNumOfPorts	INTEGER
}


mlbasSuPos		OBJECT-TYPE
	SYNTAX		INTEGER
	ACCESS		read-only -- key
	STATUS		mandatory
	DESCRIPTION
		"Position within the AT"
	::= { mlbasServiceUnitEntry 1 }

mlbasSuManagedStatus	OBJECT-TYPE
	SYNTAX	INTEGER{
			unmanaged(1),
			empty(2),
			present(3),
			managed(4)
			}
	ACCESS	read-write
	STATUS		mandatory
	DESCRIPTION
		"Defines status of the slot; Only managed and unmanaged is
		 selectable; When setting managed, empty or present is
		 returned"
	::= { mlbasServiceUnitEntry 2 }

mlbasSuOperState	OBJECT-TYPE
	SYNTAX	INTEGER{
			enabled(1),
			disabled(2)
			}
	ACCESS	read-only
	STATUS	mandatory
	DESCRIPTION
		"Operational state"
	::= { mlbasServiceUnitEntry 3 }

mlbasSuHwId		OBJECT-TYPE
	SYNTAX		DisplayString (SIZE(35))
	ACCESS		read-only
	STATUS		mandatory
	DESCRIPTION
		"Hardware identity; mlbasSuManagedStatus must be set to
		 unmanaged"
	::= { mlbasServiceUnitEntry 4 }

mlbasSuType		OBJECT-TYPE
	SYNTAX	INTEGER{
			any(1),
			ethernet(2),
			e1(3),
			ds1(4),
			atm(5),
			unknown(6)
			}
	ACCESS	read-write
	STATUS		mandatory
	DESCRIPTION
		"Interface type"
	::= { mlbasServiceUnitEntry 5 }

mlbasSuPciId		OBJECT-TYPE
	SYNTAX		INTEGER
	ACCESS		read-only
	STATUS		mandatory
	DESCRIPTION
		"..."
	::= { mlbasServiceUnitEntry 6 }

mlbasSuPciVendor	OBJECT-TYPE
	SYNTAX		INTEGER
	ACCESS		read-only
	STATUS		mandatory
	DESCRIPTION
		"..."
	::= { mlbasServiceUnitEntry 7 }

mlbasSuPortStartIndex	OBJECT-TYPE
	SYNTAX		INTEGER
	ACCESS		read-only
	STATUS		mandatory
	DESCRIPTION
		"Port start index"
	::= { mlbasServiceUnitEntry 8 }

mlbasSuNumOfPorts	OBJECT-TYPE
	SYNTAX		INTEGER
	ACCESS		read-only
	STATUS		mandatory
	DESCRIPTION
		"Number of provided ports on the SU"
	::= { mlbasServiceUnitEntry 9 }



-- *****************************************************************************
-- 
--			MLBAS Down Link Performance 15 min Table
--
-- *****************************************************************************

mlbasDownLinkPerf15minTable OBJECT-TYPE
	SYNTAX	SEQUENCE OF MlbasDownLinkPerf15minEntry
	ACCESS	not-accessible
	STATUS		mandatory
	DESCRIPTION
		"Down Link Performance 15 min Table"
	::= { mlbasDownLinkPerf15min 1 }

mlbasDownLinkPerf15minEntry OBJECT-TYPE 
	SYNTAX	MlbasDownLinkPerf15minEntry
	ACCESS	not-accessible
	STATUS		mandatory
	DESCRIPTION
		"This entity contains performance data collected for the
		 down link."
	INDEX {ansBoardSystemNodeIndex, ansBoardSubrackIndex,
	       ansBoardPosition, mlbasDL15PeriodIndex}
	::= { mlbasDownLinkPerf15minTable 1 }

MlbasDownLinkPerf15minEntry ::= SEQUENCE {
	mlbasDL15PeriodIndex	INTEGER,
	mlbasDL15UpdateTime	DateAndTime,
	-- TODO: Perhaps implement this more beatifully later
	-- mlbasDL15Perf
	mlbasDL15PerfCellErrRatio	INTEGER,
	mlbasDL15PerfCellLossRatio	INTEGER,
	mlbasDL15PerfUbrDiscCell	INTEGER,
	mlbasDL15PerfCbrDiscCell	INTEGER,
	mlbasDL15PerfAvailTime		INTEGER,
	mlbasDL15PerfUnavailTime	INTEGER,
	mlbasDL15PerfErroredSecRatio	INTEGER,
	mlbasDL15PerfSevErroredSecRatio	INTEGER,
	mlbasDL15PerfBgBlockErrRatio	INTEGER,
	mlbasDL15PerfMinInPower		INTEGER,
	mlbasDL15PerfMaxInPower		INTEGER,
	mlbasDL15PerfAverageInPower	INTEGER,
	mlbasDL15PerfMinOutPower	INTEGER,
	mlbasDL15PerfMaxOutPower	INTEGER,
	mlbasDL15PerfAverageOutPower	INTEGER,
	mlbasDL15PerfTerminalId		DisplayString (SIZE(20))
}

--
--	This table has been modifed by qtxoswi
--	TODO: Check that the correct variables are included
--

mlbasDL15PeriodIndex	OBJECT-TYPE
	SYNTAX		INTEGER
	ACCESS		read-only -- key
	STATUS		mandatory
	DESCRIPTION
			"The period number"
	::= { mlbasDownLinkPerf15minEntry 1 }

mlbasDL15UpdateTime	OBJECT-TYPE
	SYNTAX		DateAndTime
	ACCESS		read-only
	STATUS		mandatory
	DESCRIPTION
			"Update time for the 15 minute counters"
	::= { mlbasDownLinkPerf15minEntry 2 }

mlbasDL15PerfCellErrRatio	OBJECT-TYPE
	SYNTAX			INTEGER
	ACCESS			read-only
	STATUS			mandatory
	DESCRIPTION
			"Values for 15 minute counters:
			 Cell error ratio"
	::= { mlbasDownLinkPerf15minEntry 3 }

mlbasDL15PerfCellLossRatio	OBJECT-TYPE
	SYNTAX			INTEGER
	ACCESS			read-only
	STATUS			mandatory
	DESCRIPTION
			"Values for 15 minute counters:
			 Cell loss ratio"
	::= { mlbasDownLinkPerf15minEntry 4 }

mlbasDL15PerfUbrDiscCell	OBJECT-TYPE
	SYNTAX			INTEGER
	ACCESS			read-only
	STATUS			mandatory
	DESCRIPTION
			"Values for 15 minute counters:
			 Unspecified Bit Rate discarded cells"
	::= { mlbasDownLinkPerf15minEntry 5 }

mlbasDL15PerfCbrDiscCell	OBJECT-TYPE
	SYNTAX			INTEGER
	ACCESS			read-only
	STATUS			mandatory
	DESCRIPTION
			"Values for 15 minute counters:
			 Constant Bit Rate discarded cells"
	::= { mlbasDownLinkPerf15minEntry 6 }

mlbasDL15PerfAvailTime		OBJECT-TYPE
	SYNTAX			INTEGER
	ACCESS			read-only
	STATUS			mandatory
	DESCRIPTION	"Values for 15 minute counters:
			 Availability time"
	::= { mlbasDownLinkPerf15minEntry 7 }

mlbasDL15PerfUnavailTime	OBJECT-TYPE
	SYNTAX			INTEGER
	ACCESS			read-only
	STATUS			mandatory
	DESCRIPTION
			"Values for 15 minute counters:
			 Unavailability time"
	::= { mlbasDownLinkPerf15minEntry 8 }

mlbasDL15PerfErroredSecRatio	OBJECT-TYPE
	SYNTAX			INTEGER
	ACCESS			read-only
	STATUS			mandatory
	DESCRIPTION
			"Values for 15 minute counters:
			 Errored seconds"
	::= { mlbasDownLinkPerf15minEntry 9 }

mlbasDL15PerfSevErroredSecRatio	OBJECT-TYPE
	SYNTAX			INTEGER
	ACCESS			read-only
	STATUS			mandatory
	DESCRIPTION
			"Values for 15 minute counters:
			 Severely errored seconds"
	::= { mlbasDownLinkPerf15minEntry 10 }

mlbasDL15PerfBgBlockErrRatio	OBJECT-TYPE
	SYNTAX			INTEGER
	ACCESS			read-only
	STATUS			mandatory
	DESCRIPTION
			"Values for 15 minute counters:
			 Background block error ratio"
	::= { mlbasDownLinkPerf15minEntry 11 }

mlbasDL15PerfMinInPower		OBJECT-TYPE
	SYNTAX			INTEGER
	ACCESS			read-only
	STATUS			mandatory
	DESCRIPTION
			"Values for 15 minute counters:
			 Minimum electric power received by antenna"
	::= { mlbasDownLinkPerf15minEntry 12 }

mlbasDL15PerfMaxInPower		OBJECT-TYPE
	SYNTAX			INTEGER
	ACCESS			read-only
	STATUS			mandatory
	DESCRIPTION
			"Values for 15 minute counters:
			 Maximum electric power received by antenna"
	::= { mlbasDownLinkPerf15minEntry 13 }

mlbasDL15PerfAverageInPower	OBJECT-TYPE
	SYNTAX			INTEGER
	ACCESS			read-only
	STATUS			mandatory
	DESCRIPTION
			"Values for 15 minute counters:
			 Average electric power received by antenna"
	::= { mlbasDownLinkPerf15minEntry 14 }

mlbasDL15PerfMinOutPower	OBJECT-TYPE
	SYNTAX			INTEGER
	ACCESS			read-only
	STATUS			mandatory
	DESCRIPTION
			"Values for 15 minute counters:
			 Minimum power transmitted by radio"
	::= { mlbasDownLinkPerf15minEntry 15 }

mlbasDL15PerfMaxOutPower	OBJECT-TYPE
	SYNTAX			INTEGER
	ACCESS			read-only
	STATUS			mandatory
	DESCRIPTION
			"Values for 15 minute counters:
			 Maximum power transmitted by radio"
	::= { mlbasDownLinkPerf15minEntry 16 }

mlbasDL15PerfAverageOutPower	OBJECT-TYPE
	SYNTAX			INTEGER
	ACCESS			read-only
	STATUS			mandatory
	DESCRIPTION
			"Values for 15 minute counters:
			 Average power transmitted by radio"
	::= { mlbasDownLinkPerf15minEntry 17 }

mlbasDL15PerfTerminalId	OBJECT-TYPE
	SYNTAX		DisplayString (SIZE(20))
	ACCESS		read-only -- sec_key
	STATUS		mandatory
	DESCRIPTION
		"Access Terminal Identity, unique within the system"
	::= { mlbasDownLinkPerf15minEntry 18 }



-- *****************************************************************************
-- 
--			MLBAS Up Link Performance 15 min Table
--
-- *****************************************************************************

mlbasUpLinkPerf15minTable OBJECT-TYPE
	SYNTAX	SEQUENCE OF MlbasUpLinkPerf15minEntry
	ACCESS	not-accessible
	STATUS		mandatory
	DESCRIPTION
		"Up Link Performance 15 min Table"
	::= { mlbasUpLinkPerf15min 1 }

mlbasUpLinkPerf15minEntry OBJECT-TYPE 
	SYNTAX	MlbasUpLinkPerf15minEntry
	ACCESS	not-accessible
	STATUS		mandatory
	DESCRIPTION
		"This entity contains performance data collected for the up
		 link."
	INDEX {ansBoardSystemNodeIndex, ansBoardSubrackIndex,
	       ansBoardPosition, mlbasUL15PeriodIndex}
	::= { mlbasUpLinkPerf15minTable 1 }

MlbasUpLinkPerf15minEntry ::= SEQUENCE {
	mlbasUL15PeriodIndex	INTEGER,
	mlbasUL15UpdateTime	DateAndTime,
	-- TODO: Perhaps implement this more beatifully later
	-- mlbasUL15Perf
	mlbasUL15PerfCellErrRatio	INTEGER,
	mlbasUL15PerfCellLossRatio	INTEGER,
	mlbasUL15PerfUbrDiscCell	INTEGER,
	mlbasUL15PerfCbrDiscCell	INTEGER,
	mlbasUL15PerfAvailTime		INTEGER,
	mlbasUL15PerfUnavailTime	INTEGER,
	mlbasUL15PerfErroredSecRatio	INTEGER,
	mlbasUL15PerfSevErroredSecRatio	INTEGER,
	mlbasUL15PerfBgBlockErrRatio	INTEGER,
	mlbasUL15PerfMinInPower		INTEGER,
	mlbasUL15PerfMaxInPower		INTEGER,
	mlbasUL15PerfAverageInPower	INTEGER,
	mlbasUL15PerfMinOutPower	INTEGER,
	mlbasUL15PerfMaxOutPower	INTEGER,
	mlbasUL15PerfAverageOutPower	INTEGER,
	mlbasUL15PerfTerminalId		DisplayString (SIZE(20))
}

--
--	This table has been modifed by qtxoswi
--	TODO: Check that the correct variables are included
--

mlbasUL15PeriodIndex	OBJECT-TYPE
	SYNTAX		INTEGER
	ACCESS		read-only -- key
	STATUS		mandatory
	DESCRIPTION
			"The period number"
	::= { mlbasUpLinkPerf15minEntry 1 }

mlbasUL15UpdateTime	OBJECT-TYPE
	SYNTAX		DateAndTime
	ACCESS		read-only
	STATUS		mandatory
	DESCRIPTION
			"Update time for the 15 minute counters"
	::= { mlbasUpLinkPerf15minEntry 2 }

mlbasUL15PerfCellErrRatio	OBJECT-TYPE
	SYNTAX			INTEGER
	ACCESS			read-only
	STATUS			mandatory
	DESCRIPTION
			"Previous values for 15 minute counters:
			 Cell error ratio"
	::= { mlbasUpLinkPerf15minEntry 3 }

mlbasUL15PerfCellLossRatio	OBJECT-TYPE
	SYNTAX			INTEGER
	ACCESS			read-only
	STATUS			mandatory
	DESCRIPTION
			"Values for 15 minute counters:
			 Cell loss ratio"
	::= { mlbasUpLinkPerf15minEntry 4 }

mlbasUL15PerfUbrDiscCell	OBJECT-TYPE
	SYNTAX			INTEGER
	ACCESS			read-only
	STATUS			mandatory
	DESCRIPTION
			"Values for 15 minute counters:
			 Unspecified Bit Rate discarded cells"
	::= { mlbasUpLinkPerf15minEntry 5 }

mlbasUL15PerfCbrDiscCell	OBJECT-TYPE
	SYNTAX			INTEGER
	ACCESS			read-only
	STATUS			mandatory
	DESCRIPTION
			"Values for 15 minute counters:
			 Constant Bit Rate discarded cells"
	::= { mlbasUpLinkPerf15minEntry 6 }

mlbasUL15PerfAvailTime		OBJECT-TYPE
	SYNTAX			INTEGER
	ACCESS			read-only
	STATUS			mandatory
	DESCRIPTION
			"Values for 15 minute counters:
			 Availability time"
	::= { mlbasUpLinkPerf15minEntry 7 }

mlbasUL15PerfUnavailTime	OBJECT-TYPE
	SYNTAX			INTEGER
	ACCESS			read-only
	STATUS			mandatory
	DESCRIPTION
			"Values for 15 minute counters:
			 Unavailability time"
	::= { mlbasUpLinkPerf15minEntry 8 }

mlbasUL15PerfErroredSecRatio	OBJECT-TYPE
	SYNTAX			INTEGER
	ACCESS			read-only
	STATUS			mandatory
	DESCRIPTION
			"Values for 15 minute counters:
			 Errored seconds"
	::= { mlbasUpLinkPerf15minEntry 9 }

mlbasUL15PerfSevErroredSecRatio	OBJECT-TYPE
	SYNTAX			INTEGER
	ACCESS			read-only
	STATUS			mandatory
	DESCRIPTION
			"Values for 15 minute counters:
			 Severely errored seconds"
	::= { mlbasUpLinkPerf15minEntry 10 }

mlbasUL15PerfBgBlockErrRatio	OBJECT-TYPE
	SYNTAX			INTEGER
	ACCESS			read-only
	STATUS			mandatory
	DESCRIPTION
			"Values for 15 minute counters:
			 Background block error ratio"
	::= { mlbasUpLinkPerf15minEntry 11 }

mlbasUL15PerfMinInPower		OBJECT-TYPE
	SYNTAX			INTEGER
	ACCESS			read-only
	STATUS			mandatory
	DESCRIPTION
			"Values for 15 minute counters:
			 Minimum electric power received by antenna"
	::= { mlbasUpLinkPerf15minEntry 12 }

mlbasUL15PerfMaxInPower		OBJECT-TYPE
	SYNTAX			INTEGER
	ACCESS			read-only
	STATUS			mandatory
	DESCRIPTION
			"Values for 15 minute counters:
			 Maximum electric power received by antenna"
	::= { mlbasUpLinkPerf15minEntry 13 }

mlbasUL15PerfAverageInPower	OBJECT-TYPE
	SYNTAX			INTEGER
	ACCESS			read-only
	STATUS			mandatory
	DESCRIPTION
			"Values for 15 minute counters:
			 Average electric power received by antenna"
	::= { mlbasUpLinkPerf15minEntry 14 }

mlbasUL15PerfMinOutPower	OBJECT-TYPE
	SYNTAX			INTEGER
	ACCESS			read-only
	STATUS			mandatory
	DESCRIPTION
			"Values for 15 minute counters:
			 Minimum power transmitted by radio"
	::= { mlbasUpLinkPerf15minEntry 15 }

mlbasUL15PerfMaxOutPower	OBJECT-TYPE
	SYNTAX			INTEGER
	ACCESS			read-only
	STATUS			mandatory
	DESCRIPTION
			"Values for 15 minute counters:
			 Maximum power transmitted by radio"
	::= { mlbasUpLinkPerf15minEntry 16 }

mlbasUL15PerfAverageOutPower	OBJECT-TYPE
	SYNTAX			INTEGER
	ACCESS			read-only
	STATUS			mandatory
	DESCRIPTION
			"Values for 15 minute counters:
			 Average power transmitted by radio"
	::= { mlbasUpLinkPerf15minEntry 17 }

mlbasUL15PerfTerminalId	OBJECT-TYPE
	SYNTAX		DisplayString (SIZE(20))
	ACCESS		read-only -- sec_key
	STATUS		mandatory
	DESCRIPTION
		"Access Terminal Identity, unique within the system"
	::= { mlbasUpLinkPerf15minEntry 18 }



-- *****************************************************************************
-- 
--			MLBAS Down Link Performance 24 hour Table
--
-- *****************************************************************************

mlbasDownLinkPerf24hourTable OBJECT-TYPE
	SYNTAX	SEQUENCE OF MlbasDownLinkPerf24hourEntry
	ACCESS	not-accessible
	STATUS		mandatory
	DESCRIPTION
		"This entity contains performance data collected for the
		 down link. Down Link Performance 24 hour Table."
	::= { mlbasDownLinkPerf24hour 1 }

mlbasDownLinkPerf24hourEntry OBJECT-TYPE 
	SYNTAX	MlbasDownLinkPerf24hourEntry
	ACCESS	not-accessible
	STATUS		mandatory
	DESCRIPTION ""
	INDEX {ansBoardSystemNodeIndex, ansBoardSubrackIndex, ansBoardPosition, mlbasDL24PeriodIndex}
	::= { mlbasDownLinkPerf24hourTable 1 }

MlbasDownLinkPerf24hourEntry ::= SEQUENCE {
	mlbasDL24PeriodIndex	INTEGER,
	mlbasDL24UpdateTime	DateAndTime,
	-- TODO: Perhaps implement this more beatifully later
	-- mlbasDL24Perf
	mlbasDL24PerfCellErrRatio	INTEGER,
	mlbasDL24PerfCellLossRatio	INTEGER,
	mlbasDL24PerfUbrDiscCell	INTEGER,
	mlbasDL24PerfCbrDiscCell	INTEGER,
	mlbasDL24PerfAvailTime		INTEGER,
	mlbasDL24PerfUnavailTime	INTEGER,
	mlbasDL24PerfErroredSecRatio	INTEGER,
	mlbasDL24PerfSevErroredSecRatio	INTEGER,
	mlbasDL24PerfBgBlockErrRatio	INTEGER,
	mlbasDL24PerfMinInPower		INTEGER,
	mlbasDL24PerfMaxInPower		INTEGER,
	mlbasDL24PerfAverageInPower	INTEGER,
	mlbasDL24PerfMinOutPower	INTEGER,
	mlbasDL24PerfMaxOutPower	INTEGER,
	mlbasDL24PerfAverageOutPower	INTEGER,
	mlbasDL24PerfTerminalId		DisplayString (SIZE(20))
}

--
--	This table has been modifed by qtxoswi
--	TODO: Check that the correct variables are included
--

mlbasDL24PeriodIndex	OBJECT-TYPE
	SYNTAX		INTEGER
	ACCESS		read-only -- key
	STATUS		mandatory
	DESCRIPTION
			"The period number"
	::= { mlbasDownLinkPerf24hourEntry 1 }

mlbasDL24UpdateTime	OBJECT-TYPE
	SYNTAX		DateAndTime
	ACCESS		read-only
	STATUS		mandatory
	DESCRIPTION
			"Update time for the 24 hour counters"
	::= { mlbasDownLinkPerf24hourEntry 2 }

mlbasDL24PerfCellErrRatio	OBJECT-TYPE
	SYNTAX			INTEGER
	ACCESS			read-only
	STATUS			mandatory
	DESCRIPTION
			"Values for the 24 hour counters:
			 Cell error ratio"
	::= { mlbasDownLinkPerf24hourEntry 3 }

mlbasDL24PerfCellLossRatio	OBJECT-TYPE
	SYNTAX			INTEGER
	ACCESS			read-only
	STATUS			mandatory
	DESCRIPTION
			"Values for the 24 hour counters:
			 Cell loss ratio"
	::= { mlbasDownLinkPerf24hourEntry 4 }

mlbasDL24PerfUbrDiscCell	OBJECT-TYPE
	SYNTAX			INTEGER
	ACCESS			read-only
	STATUS			mandatory
	DESCRIPTION
			"Values for the 24 hour counters:
			 Unspecified Bit Rate discarded cells"
	::= { mlbasDownLinkPerf24hourEntry 5 }

mlbasDL24PerfCbrDiscCell	OBJECT-TYPE
	SYNTAX			INTEGER
	ACCESS			read-only
	STATUS			mandatory
	DESCRIPTION
			"Values for the 24 hour counters:
			 Constant Bit Rate discarded cells"
	::= { mlbasDownLinkPerf24hourEntry 6 }

mlbasDL24PerfAvailTime		OBJECT-TYPE
	SYNTAX			INTEGER
	ACCESS			read-only
	STATUS			mandatory
	DESCRIPTION
			"Values for the 24 hour counters:
			 Availability time"
	::= { mlbasDownLinkPerf24hourEntry 7 }

mlbasDL24PerfUnavailTime	OBJECT-TYPE
	SYNTAX			INTEGER
	ACCESS			read-only
	STATUS			mandatory
	DESCRIPTION
			"Values for the 24 hour counters:
			 Unavailability time"
	::= { mlbasDownLinkPerf24hourEntry 8 }

mlbasDL24PerfErroredSecRatio	OBJECT-TYPE
	SYNTAX			INTEGER
	ACCESS			read-only
	STATUS			mandatory
	DESCRIPTION
			"Values for the 24 hour counters:
			 Errored seconds"
	::= { mlbasDownLinkPerf24hourEntry 9 }

mlbasDL24PerfSevErroredSecRatio	OBJECT-TYPE
	SYNTAX			INTEGER
	ACCESS			read-only
	STATUS			mandatory
	DESCRIPTION
			"Values for the 24 hour counters:
			 Severely errored seconds"
	::= { mlbasDownLinkPerf24hourEntry 10 }

mlbasDL24PerfBgBlockErrRatio	OBJECT-TYPE
	SYNTAX			INTEGER
	ACCESS			read-only
	STATUS			mandatory
	DESCRIPTION
			"Values for the 24 hour counters:
			 Background block error ratio"
	::= { mlbasDownLinkPerf24hourEntry 11 }

mlbasDL24PerfMinInPower		OBJECT-TYPE
	SYNTAX			INTEGER
	ACCESS			read-only
	STATUS			mandatory
	DESCRIPTION
			"Values for the 24 hour counters:
			 Minimum electric power received by antenna"
	::= { mlbasDownLinkPerf24hourEntry 12 }

mlbasDL24PerfMaxInPower		OBJECT-TYPE
	SYNTAX			INTEGER
	ACCESS			read-only
	STATUS			mandatory
	DESCRIPTION
			"Values for the 24 hour counters:
			 Maximum electric power received by antenna"
	::= { mlbasDownLinkPerf24hourEntry 13 }

mlbasDL24PerfAverageInPower	OBJECT-TYPE
	SYNTAX			INTEGER
	ACCESS			read-only
	STATUS			mandatory
	DESCRIPTION
			"Values for the 24 hour counters:
			 Average electric power received by antenna"
	::= { mlbasDownLinkPerf24hourEntry 14 }

mlbasDL24PerfMinOutPower	OBJECT-TYPE
	SYNTAX			INTEGER
	ACCESS			read-only
	STATUS			mandatory
	DESCRIPTION
			"Values for the 24 hour counters:
			 Minimum power transmitted by radio"
	::= { mlbasDownLinkPerf24hourEntry 15 }

mlbasDL24PerfMaxOutPower	OBJECT-TYPE
	SYNTAX			INTEGER
	ACCESS			read-only
	STATUS			mandatory
	DESCRIPTION
			"Values for the 24 hour counters:
			 Maximum power transmitted by radio"
	::= { mlbasDownLinkPerf24hourEntry 16 }

mlbasDL24PerfAverageOutPower	OBJECT-TYPE
	SYNTAX			INTEGER
	ACCESS			read-only
	STATUS			mandatory
	DESCRIPTION
			"Values for the 24 hour counters:
			 Average power transmitted by radio"
	::= { mlbasDownLinkPerf24hourEntry 17 }

mlbasDL24PerfTerminalId	OBJECT-TYPE
	SYNTAX		DisplayString (SIZE(20))
	ACCESS		read-only -- sec_key
	STATUS		mandatory
	DESCRIPTION
		"Access Terminal Identity, unique within the system"
	::= { mlbasDownLinkPerf24hourEntry 18 }



-- *****************************************************************************
-- 
--			MLBAS Up Link Performance 24 hour Table
--
-- *****************************************************************************

mlbasUpLinkPerf24hourTable OBJECT-TYPE
	SYNTAX	SEQUENCE OF MlbasUpLinkPerf24hourEntry
	ACCESS	not-accessible
	STATUS		mandatory
	DESCRIPTION
		"This entity contains performance data collected for the up
		 link. Up Link Performance 24 hour Table."
	::= { mlbasUpLinkPerf24hour 1 }

mlbasUpLinkPerf24hourEntry OBJECT-TYPE 
	SYNTAX	MlbasUpLinkPerf24hourEntry
	ACCESS	not-accessible
	STATUS		mandatory
	DESCRIPTION ""
	INDEX {ansBoardSystemNodeIndex, ansBoardSubrackIndex,
	       ansBoardPosition, mlbasUL24PeriodIndex}
	::= { mlbasUpLinkPerf24hourTable 1 }

MlbasUpLinkPerf24hourEntry ::= SEQUENCE {
	mlbasUL24PeriodIndex	INTEGER,
	mlbasUL24UpdateTime	DateAndTime,
	-- TODO: Perhaps implement this more beatifully later
	-- mlbasUL24Perf
	mlbasUL24PerfCellErrRatio	INTEGER,
	mlbasUL24PerfCellLossRatio	INTEGER,
	mlbasUL24PerfUbrDiscCell	INTEGER,
	mlbasUL24PerfCbrDiscCell	INTEGER,
	mlbasUL24PerfAvailTime		INTEGER,
	mlbasUL24PerfUnavailTime	INTEGER,
	mlbasUL24PerfErroredSecRatio	INTEGER,
	mlbasUL24PerfSevErroredSecRatio	INTEGER,
	mlbasUL24PerfBgBlockErrRatio	INTEGER,
	mlbasUL24PerfMinInPower		INTEGER,
	mlbasUL24PerfMaxInPower		INTEGER,
	mlbasUL24PerfAverageInPower	INTEGER,
	mlbasUL24PerfMinOutPower	INTEGER,
	mlbasUL24PerfMaxOutPower	INTEGER,
	mlbasUL24PerfAverageOutPower	INTEGER,
	mlbasUL24PerfTerminalId		DisplayString (SIZE(20))
}

--
--	This table has been modifed by qtxoswi
--	TODO: Check that the correct variables are included
--

mlbasUL24PeriodIndex	OBJECT-TYPE
	SYNTAX		INTEGER
	ACCESS		read-only -- key
	STATUS		mandatory
	DESCRIPTION
			"The period number"
	::= { mlbasUpLinkPerf24hourEntry 1 }

mlbasUL24UpdateTime	OBJECT-TYPE
	SYNTAX		DateAndTime
	ACCESS		read-only
	STATUS		mandatory
	DESCRIPTION
			"Update time for the 24 hour counters"
	::= { mlbasUpLinkPerf24hourEntry 2 }

mlbasUL24PerfCellErrRatio	OBJECT-TYPE
	SYNTAX			INTEGER
	ACCESS			read-only
	STATUS			mandatory
	DESCRIPTION
			"Values for the 24 hour counters:
			 Cell error ratio"
	::= { mlbasUpLinkPerf24hourEntry 3 }

mlbasUL24PerfCellLossRatio	OBJECT-TYPE
	SYNTAX			INTEGER
	ACCESS			read-only
	STATUS			mandatory
	DESCRIPTION
			"Values for the 24 hour counters:
			 Cell loss ratio"
	::= { mlbasUpLinkPerf24hourEntry 4 }

mlbasUL24PerfUbrDiscCell	OBJECT-TYPE
	SYNTAX			INTEGER
	ACCESS			read-only
	STATUS			mandatory
	DESCRIPTION
			"Values for the 24 hour counters:
			 Unspecified Bit Rate discarded cells"
	::= { mlbasUpLinkPerf24hourEntry 5 }

mlbasUL24PerfCbrDiscCell	OBJECT-TYPE
	SYNTAX			INTEGER
	ACCESS			read-only
	STATUS			mandatory
	DESCRIPTION
			"Values for the 24 hour counters:
			 Constant Bit Rate discarded cells"
	::= { mlbasUpLinkPerf24hourEntry 6 }

mlbasUL24PerfAvailTime		OBJECT-TYPE
	SYNTAX			INTEGER
	ACCESS			read-only
	STATUS			mandatory
	DESCRIPTION
			"Values for the 24 hour counters:
			 Availability time"
	::= { mlbasUpLinkPerf24hourEntry 7 }

mlbasUL24PerfUnavailTime	OBJECT-TYPE
	SYNTAX			INTEGER
	ACCESS			read-only
	STATUS			mandatory
	DESCRIPTION
			"Values for the 24 hour counters:
			 Unavailability time"
	::= { mlbasUpLinkPerf24hourEntry 8 }

mlbasUL24PerfErroredSecRatio	OBJECT-TYPE
	SYNTAX			INTEGER
	ACCESS			read-only
	STATUS			mandatory
	DESCRIPTION
			"Values for the 24 hour counters:
			 Errored seconds"
	::= { mlbasUpLinkPerf24hourEntry 9 }

mlbasUL24PerfSevErroredSecRatio	OBJECT-TYPE
	SYNTAX			INTEGER
	ACCESS			read-only
	STATUS			mandatory
	DESCRIPTION
			"Values for the 24 hour counters:
			 Severely errored seconds"
	::= { mlbasUpLinkPerf24hourEntry 10 }

mlbasUL24PerfBgBlockErrRatio	OBJECT-TYPE
	SYNTAX			INTEGER
	ACCESS			read-only
	STATUS			mandatory
	DESCRIPTION
			"Values for the 24 hour counters:
			 Background block error ratio"
	::= { mlbasUpLinkPerf24hourEntry 11 }

mlbasUL24PerfMinInPower		OBJECT-TYPE
	SYNTAX			INTEGER
	ACCESS			read-only
	STATUS			mandatory
	DESCRIPTION
			"Values for the 24 hour counters:
			 Minimum electric power received by antenna"
	::= { mlbasUpLinkPerf24hourEntry 12 }

mlbasUL24PerfMaxInPower		OBJECT-TYPE
	SYNTAX			INTEGER
	ACCESS			read-only
	STATUS			mandatory
	DESCRIPTION
			"Values for the 24 hour counters:
			 Maximum electric power received by antenna"
	::= { mlbasUpLinkPerf24hourEntry 13 }

mlbasUL24PerfAverageInPower	OBJECT-TYPE
	SYNTAX			INTEGER
	ACCESS			read-only
	STATUS			mandatory
	DESCRIPTION
			"Values for the 24 hour counters:
			 Average electric power received by antenna"
	::= { mlbasUpLinkPerf24hourEntry 14 }

mlbasUL24PerfMinOutPower	OBJECT-TYPE
	SYNTAX			INTEGER
	ACCESS			read-only
	STATUS			mandatory
	DESCRIPTION
			"Values for the 24 hour counters:
			 Minimum power transmitted by radio"
	::= { mlbasUpLinkPerf24hourEntry 15 }

mlbasUL24PerfMaxOutPower	OBJECT-TYPE
	SYNTAX			INTEGER
	ACCESS			read-only
	STATUS			mandatory
	DESCRIPTION
			"Values for the 24 hour counters:
			 Maximum power transmitted by radio"
	::= { mlbasUpLinkPerf24hourEntry 16 }

mlbasUL24PerfAverageOutPower	OBJECT-TYPE
	SYNTAX			INTEGER
	ACCESS			read-only
	STATUS			mandatory
	DESCRIPTION
			"Values for the 24 hour counters:
			 Average power transmitted by radio"
	::= { mlbasUpLinkPerf24hourEntry 17 }

mlbasUL24PerfTerminalId	OBJECT-TYPE
	SYNTAX		DisplayString (SIZE(20))
	ACCESS		read-only -- sec_key
	STATUS		mandatory
	DESCRIPTION
		"Access Terminal Identity, unique within the system"
	::= { mlbasUpLinkPerf24hourEntry 18 }





-- *****************************************************************************
-- 
--			MLBAS Down Link Log 15 min Table
--
-- *****************************************************************************

mlbasDownLinkLog15minTable OBJECT-TYPE
	SYNTAX	SEQUENCE OF MlbasDownLinkLog15minEntry
	ACCESS	not-accessible
	STATUS		mandatory
	DESCRIPTION
		"Down Link Log 15 min Table"
	::= { mlbasDownLinkLog15min 1 }

mlbasDownLinkLog15minEntry OBJECT-TYPE 
	SYNTAX	MlbasDownLinkLog15minEntry
	ACCESS	not-accessible
	STATUS		mandatory
	DESCRIPTION
		"This entity contains performance data collected for the
		 down link."
	INDEX {ansBoardSystemNodeIndex, ansBoardSubrackIndex,
	       ansBoardPosition}
	::= { mlbasDownLinkLog15minTable 1 }

MlbasDownLinkLog15minEntry ::= SEQUENCE {
	mlbasDL15LogCellErrRatio	INTEGER,
	mlbasDL15LogCellLossRatio	INTEGER,
	mlbasDL15LogUbrDiscCell		INTEGER,
	mlbasDL15LogCbrDiscCell		INTEGER,
	mlbasDL15LogAvailTime		INTEGER,
	mlbasDL15LogUnavailTime		INTEGER,
	mlbasDL15LogErroredSecRatio	INTEGER,
	mlbasDL15LogSevErroredSecRatio	INTEGER,
	mlbasDL15LogBgBlockErrRatio	INTEGER,
	mlbasDL15LogMinInPower		INTEGER,
	mlbasDL15LogMaxInPower		INTEGER,
	mlbasDL15LogAverageInPower	INTEGER,
	mlbasDL15LogMinOutPower		INTEGER,
	mlbasDL15LogMaxOutPower		INTEGER,
	mlbasDL15LogAverageOutPower	INTEGER
}

mlbasDL15LogCellErrRatio	OBJECT-TYPE
	SYNTAX			INTEGER
	ACCESS			read-only
	STATUS			mandatory
	DESCRIPTION
			"Values for 15 minute counters:
			 Cell error ratio"
	::= { mlbasDownLinkLog15minEntry 1 }

mlbasDL15LogCellLossRatio	OBJECT-TYPE
	SYNTAX			INTEGER
	ACCESS			read-only
	STATUS			mandatory
	DESCRIPTION
			"Values for 15 minute counters:
			 Cell loss ratio"
	::= { mlbasDownLinkLog15minEntry 2 }

mlbasDL15LogUbrDiscCell	OBJECT-TYPE
	SYNTAX			INTEGER
	ACCESS			read-only
	STATUS			mandatory
	DESCRIPTION
			"Values for 15 minute counters:
			 Unspecified Bit Rate discarded cells"
	::= { mlbasDownLinkLog15minEntry 3 }

mlbasDL15LogCbrDiscCell	OBJECT-TYPE
	SYNTAX			INTEGER
	ACCESS			read-only
	STATUS			mandatory
	DESCRIPTION
			"Values for 15 minute counters:
			 Constant Bit Rate discarded cells"
	::= { mlbasDownLinkLog15minEntry 4 }

mlbasDL15LogAvailTime		OBJECT-TYPE
	SYNTAX			INTEGER
	ACCESS			read-only
	STATUS			mandatory
	DESCRIPTION	"Values for 15 minute counters:
			 Availability time"
	::= { mlbasDownLinkLog15minEntry 5 }

mlbasDL15LogUnavailTime	OBJECT-TYPE
	SYNTAX			INTEGER
	ACCESS			read-only
	STATUS			mandatory
	DESCRIPTION
			"Values for 15 minute counters:
			 Unavailability time"
	::= { mlbasDownLinkLog15minEntry 6 }

mlbasDL15LogErroredSecRatio	OBJECT-TYPE
	SYNTAX			INTEGER
	ACCESS			read-only
	STATUS			mandatory
	DESCRIPTION
			"Values for 15 minute counters:
			 Errored seconds"
	::= { mlbasDownLinkLog15minEntry 7 }

mlbasDL15LogSevErroredSecRatio	OBJECT-TYPE
	SYNTAX			INTEGER
	ACCESS			read-only
	STATUS			mandatory
	DESCRIPTION
			"Values for 15 minute counters:
			 Severely errored seconds"
	::= { mlbasDownLinkLog15minEntry 8 }

mlbasDL15LogBgBlockErrRatio	OBJECT-TYPE
	SYNTAX			INTEGER
	ACCESS			read-only
	STATUS			mandatory
	DESCRIPTION
			"Values for 15 minute counters:
			 Background block error ratio"
	::= { mlbasDownLinkLog15minEntry 9 }

mlbasDL15LogMinInPower		OBJECT-TYPE
	SYNTAX			INTEGER
	ACCESS			read-only
	STATUS			mandatory
	DESCRIPTION
			"Values for 15 minute counters:
			 Minimum electric power received by antenna"
	::= { mlbasDownLinkLog15minEntry 10 }

mlbasDL15LogMaxInPower		OBJECT-TYPE
	SYNTAX			INTEGER
	ACCESS			read-only
	STATUS			mandatory
	DESCRIPTION
			"Values for 15 minute counters:
			 Maximum electric power received by antenna"
	::= { mlbasDownLinkLog15minEntry 11 }

mlbasDL15LogAverageInPower	OBJECT-TYPE
	SYNTAX			INTEGER
	ACCESS			read-only
	STATUS			mandatory
	DESCRIPTION
			"Values for 15 minute counters:
			 Average electric power received by antenna"
	::= { mlbasDownLinkLog15minEntry 12 }

mlbasDL15LogMinOutPower	OBJECT-TYPE
	SYNTAX			INTEGER
	ACCESS			read-only
	STATUS			mandatory
	DESCRIPTION
			"Values for 15 minute counters:
			 Minimum power transmitted by radio"
	::= { mlbasDownLinkLog15minEntry 13 }

mlbasDL15LogMaxOutPower	OBJECT-TYPE
	SYNTAX			INTEGER
	ACCESS			read-only
	STATUS			mandatory
	DESCRIPTION
			"Values for 15 minute counters:
			 Maximum power transmitted by radio"
	::= { mlbasDownLinkLog15minEntry 14 }

mlbasDL15LogAverageOutPower	OBJECT-TYPE
	SYNTAX			INTEGER
	ACCESS			read-only
	STATUS			mandatory
	DESCRIPTION
			"Values for 15 minute counters:
			 Average power transmitted by radio"
	::= { mlbasDownLinkLog15minEntry 15 }



-- *****************************************************************************
-- 
--			MLBAS Up Link Log 15 min Table
--
-- *****************************************************************************

mlbasUpLinkLog15minTable OBJECT-TYPE
	SYNTAX	SEQUENCE OF MlbasUpLinkLog15minEntry
	ACCESS	not-accessible
	STATUS		mandatory
	DESCRIPTION
		"Up Link Log 15 min Table"
	::= { mlbasUpLinkLog15min 1 }

mlbasUpLinkLog15minEntry OBJECT-TYPE 
	SYNTAX	MlbasUpLinkLog15minEntry
	ACCESS	not-accessible
	STATUS		mandatory
	DESCRIPTION
		"This entity contains performance data collected for the up
		 link."
	INDEX {ansBoardSystemNodeIndex, ansBoardSubrackIndex,
	       ansBoardPosition}
	::= { mlbasUpLinkLog15minTable 1 }

MlbasUpLinkLog15minEntry ::= SEQUENCE {
	mlbasUL15LogCellErrRatio	INTEGER,
	mlbasUL15LogCellLossRatio	INTEGER,
	mlbasUL15LogUbrDiscCell	INTEGER,
	mlbasUL15LogCbrDiscCell	INTEGER,
	mlbasUL15LogAvailTime		INTEGER,
	mlbasUL15LogUnavailTime	INTEGER,
	mlbasUL15LogErroredSecRatio	INTEGER,
	mlbasUL15LogSevErroredSecRatio	INTEGER,
	mlbasUL15LogBgBlockErrRatio	INTEGER,
	mlbasUL15LogMinInPower		INTEGER,
	mlbasUL15LogMaxInPower		INTEGER,
	mlbasUL15LogAverageInPower	INTEGER,
	mlbasUL15LogMinOutPower	INTEGER,
	mlbasUL15LogMaxOutPower	INTEGER,
	mlbasUL15LogAverageOutPower	INTEGER
}


mlbasUL15LogCellErrRatio	OBJECT-TYPE
	SYNTAX			INTEGER
	ACCESS			read-only
	STATUS			mandatory
	DESCRIPTION
			"Previous values for 15 minute counters:
			 Cell error ratio"
	::= { mlbasUpLinkLog15minEntry 1 }

mlbasUL15LogCellLossRatio	OBJECT-TYPE
	SYNTAX			INTEGER
	ACCESS			read-only
	STATUS			mandatory
	DESCRIPTION
			"Values for 15 minute counters:
			 Cell loss ratio"
	::= { mlbasUpLinkLog15minEntry 2 }

mlbasUL15LogUbrDiscCell	OBJECT-TYPE
	SYNTAX			INTEGER
	ACCESS			read-only
	STATUS			mandatory
	DESCRIPTION
			"Values for 15 minute counters:
			 Unspecified Bit Rate discarded cells"
	::= { mlbasUpLinkLog15minEntry 3 }

mlbasUL15LogCbrDiscCell	OBJECT-TYPE
	SYNTAX			INTEGER
	ACCESS			read-only
	STATUS			mandatory
	DESCRIPTION
			"Values for 15 minute counters:
			 Constant Bit Rate discarded cells"
	::= { mlbasUpLinkLog15minEntry 4 }

mlbasUL15LogAvailTime		OBJECT-TYPE
	SYNTAX			INTEGER
	ACCESS			read-only
	STATUS			mandatory
	DESCRIPTION
			"Values for 15 minute counters:
			 Availability time"
	::= { mlbasUpLinkLog15minEntry 5 }

mlbasUL15LogUnavailTime	OBJECT-TYPE
	SYNTAX			INTEGER
	ACCESS			read-only
	STATUS			mandatory
	DESCRIPTION
			"Values for 15 minute counters:
			 Unavailability time"
	::= { mlbasUpLinkLog15minEntry 6 }

mlbasUL15LogErroredSecRatio	OBJECT-TYPE
	SYNTAX			INTEGER
	ACCESS			read-only
	STATUS			mandatory
	DESCRIPTION
			"Values for 15 minute counters:
			 Errored seconds"
	::= { mlbasUpLinkLog15minEntry 7 }

mlbasUL15LogSevErroredSecRatio	OBJECT-TYPE
	SYNTAX			INTEGER
	ACCESS			read-only
	STATUS			mandatory
	DESCRIPTION
			"Values for 15 minute counters:
			 Severely errored seconds"
	::= { mlbasUpLinkLog15minEntry 8 }

mlbasUL15LogBgBlockErrRatio	OBJECT-TYPE
	SYNTAX			INTEGER
	ACCESS			read-only
	STATUS			mandatory
	DESCRIPTION
			"Values for 15 minute counters:
			 Background block error ratio"
	::= { mlbasUpLinkLog15minEntry 9 }

mlbasUL15LogMinInPower		OBJECT-TYPE
	SYNTAX			INTEGER
	ACCESS			read-only
	STATUS			mandatory
	DESCRIPTION
			"Values for 15 minute counters:
			 Minimum electric power received by antenna"
	::= { mlbasUpLinkLog15minEntry 10 }

mlbasUL15LogMaxInPower		OBJECT-TYPE
	SYNTAX			INTEGER
	ACCESS			read-only
	STATUS			mandatory
	DESCRIPTION
			"Values for 15 minute counters:
			 Maximum electric power received by antenna"
	::= { mlbasUpLinkLog15minEntry 11 }

mlbasUL15LogAverageInPower	OBJECT-TYPE
	SYNTAX			INTEGER
	ACCESS			read-only
	STATUS			mandatory
	DESCRIPTION
			"Values for 15 minute counters:
			 Average electric power received by antenna"
	::= { mlbasUpLinkLog15minEntry 12 }

mlbasUL15LogMinOutPower	OBJECT-TYPE
	SYNTAX			INTEGER
	ACCESS			read-only
	STATUS			mandatory
	DESCRIPTION
			"Values for 15 minute counters:
			 Minimum power transmitted by radio"
	::= { mlbasUpLinkLog15minEntry 13 }

mlbasUL15LogMaxOutPower	OBJECT-TYPE
	SYNTAX			INTEGER
	ACCESS			read-only
	STATUS			mandatory
	DESCRIPTION
			"Values for 15 minute counters:
			 Maximum power transmitted by radio"
	::= { mlbasUpLinkLog15minEntry 14 }

mlbasUL15LogAverageOutPower	OBJECT-TYPE
	SYNTAX			INTEGER
	ACCESS			read-only
	STATUS			mandatory
	DESCRIPTION
			"Values for 15 minute counters:
			 Average power transmitted by radio"
	::= { mlbasUpLinkLog15minEntry 15 }



-- *****************************************************************************
-- 
--			MLBAS Down Link Log 24 hour Table
--
-- *****************************************************************************

mlbasDownLinkLog24hourTable OBJECT-TYPE
	SYNTAX	SEQUENCE OF MlbasDownLinkLog24hourEntry
	ACCESS	not-accessible
	STATUS		mandatory
	DESCRIPTION
		"This entity contains performance data collected for the
		 down link. Down Link Log 24 hour Table."
	::= { mlbasDownLinkLog24hour 1 }

mlbasDownLinkLog24hourEntry OBJECT-TYPE 
	SYNTAX	MlbasDownLinkLog24hourEntry
	ACCESS	not-accessible
	STATUS		mandatory
	DESCRIPTION ""
	INDEX {ansBoardSystemNodeIndex, ansBoardSubrackIndex, ansBoardPosition}
	::= { mlbasDownLinkLog24hourTable 1 }

MlbasDownLinkLog24hourEntry ::= SEQUENCE {
	mlbasDL24LogCellErrRatio	INTEGER,
	mlbasDL24LogCellLossRatio	INTEGER,
	mlbasDL24LogUbrDiscCell	INTEGER,
	mlbasDL24LogCbrDiscCell	INTEGER,
	mlbasDL24LogAvailTime		INTEGER,
	mlbasDL24LogUnavailTime	INTEGER,
	mlbasDL24LogErroredSecRatio	INTEGER,
	mlbasDL24LogSevErroredSecRatio	INTEGER,
	mlbasDL24LogBgBlockErrRatio	INTEGER,
	mlbasDL24LogMinInPower		INTEGER,
	mlbasDL24LogMaxInPower		INTEGER,
	mlbasDL24LogAverageInPower	INTEGER,
	mlbasDL24LogMinOutPower	INTEGER,
	mlbasDL24LogMaxOutPower	INTEGER,
	mlbasDL24LogAverageOutPower	INTEGER
}


mlbasDL24LogCellErrRatio	OBJECT-TYPE
	SYNTAX			INTEGER
	ACCESS			read-only
	STATUS			mandatory
	DESCRIPTION
			"Values for the 24 hour counters:
			 Cell error ratio"
	::= { mlbasDownLinkLog24hourEntry 1 }

mlbasDL24LogCellLossRatio	OBJECT-TYPE
	SYNTAX			INTEGER
	ACCESS			read-only
	STATUS			mandatory
	DESCRIPTION
			"Values for the 24 hour counters:
			 Cell loss ratio"
	::= { mlbasDownLinkLog24hourEntry 2 }

mlbasDL24LogUbrDiscCell	OBJECT-TYPE
	SYNTAX			INTEGER
	ACCESS			read-only
	STATUS			mandatory
	DESCRIPTION
			"Values for the 24 hour counters:
			 Unspecified Bit Rate discarded cells"
	::= { mlbasDownLinkLog24hourEntry 3 }

mlbasDL24LogCbrDiscCell	OBJECT-TYPE
	SYNTAX			INTEGER
	ACCESS			read-only
	STATUS			mandatory
	DESCRIPTION
			"Values for the 24 hour counters:
			 Constant Bit Rate discarded cells"
	::= { mlbasDownLinkLog24hourEntry 4 }

mlbasDL24LogAvailTime		OBJECT-TYPE
	SYNTAX			INTEGER
	ACCESS			read-only
	STATUS			mandatory
	DESCRIPTION
			"Values for the 24 hour counters:
			 Availability time"
	::= { mlbasDownLinkLog24hourEntry 5 }

mlbasDL24LogUnavailTime	OBJECT-TYPE
	SYNTAX			INTEGER
	ACCESS			read-only
	STATUS			mandatory
	DESCRIPTION
			"Values for the 24 hour counters:
			 Unavailability time"
	::= { mlbasDownLinkLog24hourEntry 6 }

mlbasDL24LogErroredSecRatio	OBJECT-TYPE
	SYNTAX			INTEGER
	ACCESS			read-only
	STATUS			mandatory
	DESCRIPTION
			"Values for the 24 hour counters:
			 Errored seconds"
	::= { mlbasDownLinkLog24hourEntry 7 }

mlbasDL24LogSevErroredSecRatio	OBJECT-TYPE
	SYNTAX			INTEGER
	ACCESS			read-only
	STATUS			mandatory
	DESCRIPTION
			"Values for the 24 hour counters:
			 Severely errored seconds"
	::= { mlbasDownLinkLog24hourEntry 8 }

mlbasDL24LogBgBlockErrRatio	OBJECT-TYPE
	SYNTAX			INTEGER
	ACCESS			read-only
	STATUS			mandatory
	DESCRIPTION
			"Values for the 24 hour counters:
			 Background block error ratio"
	::= { mlbasDownLinkLog24hourEntry 9 }

mlbasDL24LogMinInPower		OBJECT-TYPE
	SYNTAX			INTEGER
	ACCESS			read-only
	STATUS			mandatory
	DESCRIPTION
			"Values for the 24 hour counters:
			 Minimum electric power received by antenna"
	::= { mlbasDownLinkLog24hourEntry 10 }

mlbasDL24LogMaxInPower		OBJECT-TYPE
	SYNTAX			INTEGER
	ACCESS			read-only
	STATUS			mandatory
	DESCRIPTION
			"Values for the 24 hour counters:
			 Maximum electric power received by antenna"
	::= { mlbasDownLinkLog24hourEntry 11 }

mlbasDL24LogAverageInPower	OBJECT-TYPE
	SYNTAX			INTEGER
	ACCESS			read-only
	STATUS			mandatory
	DESCRIPTION
			"Values for the 24 hour counters:
			 Average electric power received by antenna"
	::= { mlbasDownLinkLog24hourEntry 12 }

mlbasDL24LogMinOutPower	OBJECT-TYPE
	SYNTAX			INTEGER
	ACCESS			read-only
	STATUS			mandatory
	DESCRIPTION
			"Values for the 24 hour counters:
			 Minimum power transmitted by radio"
	::= { mlbasDownLinkLog24hourEntry 13 }

mlbasDL24LogMaxOutPower	OBJECT-TYPE
	SYNTAX			INTEGER
	ACCESS			read-only
	STATUS			mandatory
	DESCRIPTION
			"Values for the 24 hour counters:
			 Maximum power transmitted by radio"
	::= { mlbasDownLinkLog24hourEntry 14 }

mlbasDL24LogAverageOutPower	OBJECT-TYPE
	SYNTAX			INTEGER
	ACCESS			read-only
	STATUS			mandatory
	DESCRIPTION
			"Values for the 24 hour counters:
			 Average power transmitted by radio"
	::= { mlbasDownLinkLog24hourEntry 15 }



-- *****************************************************************************
-- 
--			MLBAS Up Link Log 24 hour Table
--
-- *****************************************************************************

mlbasUpLinkLog24hourTable OBJECT-TYPE
	SYNTAX	SEQUENCE OF MlbasUpLinkLog24hourEntry
	ACCESS	not-accessible
	STATUS		mandatory
	DESCRIPTION
		"This entity contains performance data collected for the up
		 link. Up Link Log 24 hour Table."
	::= { mlbasUpLinkLog24hour 1 }

mlbasUpLinkLog24hourEntry OBJECT-TYPE 
	SYNTAX	MlbasUpLinkLog24hourEntry
	ACCESS	not-accessible
	STATUS		mandatory
	DESCRIPTION ""
	INDEX {ansBoardSystemNodeIndex, ansBoardSubrackIndex,
	       ansBoardPosition}
	::= { mlbasUpLinkLog24hourTable 1 }

MlbasUpLinkLog24hourEntry ::= SEQUENCE {
	mlbasUL24LogCellErrRatio	INTEGER,
	mlbasUL24LogCellLossRatio	INTEGER,
	mlbasUL24LogUbrDiscCell	INTEGER,
	mlbasUL24LogCbrDiscCell	INTEGER,
	mlbasUL24LogAvailTime		INTEGER,
	mlbasUL24LogUnavailTime	INTEGER,
	mlbasUL24LogErroredSecRatio	INTEGER,
	mlbasUL24LogSevErroredSecRatio	INTEGER,
	mlbasUL24LogBgBlockErrRatio	INTEGER,
	mlbasUL24LogMinInPower		INTEGER,
	mlbasUL24LogMaxInPower		INTEGER,
	mlbasUL24LogAverageInPower	INTEGER,
	mlbasUL24LogMinOutPower	INTEGER,
	mlbasUL24LogMaxOutPower	INTEGER,
	mlbasUL24LogAverageOutPower	INTEGER
}


mlbasUL24LogCellErrRatio	OBJECT-TYPE
	SYNTAX			INTEGER
	ACCESS			read-only
	STATUS			mandatory
	DESCRIPTION
			"Values for the 24 hour counters:
			 Cell error ratio"
	::= { mlbasUpLinkLog24hourEntry 1 }

mlbasUL24LogCellLossRatio	OBJECT-TYPE
	SYNTAX			INTEGER
	ACCESS			read-only
	STATUS			mandatory
	DESCRIPTION
			"Values for the 24 hour counters:
			 Cell loss ratio"
	::= { mlbasUpLinkLog24hourEntry 2 }

mlbasUL24LogUbrDiscCell	OBJECT-TYPE
	SYNTAX			INTEGER
	ACCESS			read-only
	STATUS			mandatory
	DESCRIPTION
			"Values for the 24 hour counters:
			 Unspecified Bit Rate discarded cells"
	::= { mlbasUpLinkLog24hourEntry 3 }

mlbasUL24LogCbrDiscCell	OBJECT-TYPE
	SYNTAX			INTEGER
	ACCESS			read-only
	STATUS			mandatory
	DESCRIPTION
			"Values for the 24 hour counters:
			 Constant Bit Rate discarded cells"
	::= { mlbasUpLinkLog24hourEntry 4 }

mlbasUL24LogAvailTime		OBJECT-TYPE
	SYNTAX			INTEGER
	ACCESS			read-only
	STATUS			mandatory
	DESCRIPTION
			"Values for the 24 hour counters:
			 Availability time"
	::= { mlbasUpLinkLog24hourEntry 5 }

mlbasUL24LogUnavailTime	OBJECT-TYPE
	SYNTAX			INTEGER
	ACCESS			read-only
	STATUS			mandatory
	DESCRIPTION
			"Values for the 24 hour counters:
			 Unavailability time"
	::= { mlbasUpLinkLog24hourEntry 6 }

mlbasUL24LogErroredSecRatio	OBJECT-TYPE
	SYNTAX			INTEGER
	ACCESS			read-only
	STATUS			mandatory
	DESCRIPTION
			"Values for the 24 hour counters:
			 Errored seconds"
	::= { mlbasUpLinkLog24hourEntry 7 }

mlbasUL24LogSevErroredSecRatio	OBJECT-TYPE
	SYNTAX			INTEGER
	ACCESS			read-only
	STATUS			mandatory
	DESCRIPTION
			"Values for the 24 hour counters:
			 Severely errored seconds"
	::= { mlbasUpLinkLog24hourEntry 8 }

mlbasUL24LogBgBlockErrRatio	OBJECT-TYPE
	SYNTAX			INTEGER
	ACCESS			read-only
	STATUS			mandatory
	DESCRIPTION
			"Values for the 24 hour counters:
			 Background block error ratio"
	::= { mlbasUpLinkLog24hourEntry 9 }

mlbasUL24LogMinInPower		OBJECT-TYPE
	SYNTAX			INTEGER
	ACCESS			read-only
	STATUS			mandatory
	DESCRIPTION
			"Values for the 24 hour counters:
			 Minimum electric power received by antenna"
	::= { mlbasUpLinkLog24hourEntry 10 }

mlbasUL24LogMaxInPower		OBJECT-TYPE
	SYNTAX			INTEGER
	ACCESS			read-only
	STATUS			mandatory
	DESCRIPTION
			"Values for the 24 hour counters:
			 Maximum electric power received by antenna"
	::= { mlbasUpLinkLog24hourEntry 11 }

mlbasUL24LogAverageInPower	OBJECT-TYPE
	SYNTAX			INTEGER
	ACCESS			read-only
	STATUS			mandatory
	DESCRIPTION
			"Values for the 24 hour counters:
			 Average electric power received by antenna"
	::= { mlbasUpLinkLog24hourEntry 12 }

mlbasUL24LogMinOutPower	OBJECT-TYPE
	SYNTAX			INTEGER
	ACCESS			read-only
	STATUS			mandatory
	DESCRIPTION
			"Values for the 24 hour counters:
			 Minimum power transmitted by radio"
	::= { mlbasUpLinkLog24hourEntry 13 }

mlbasUL24LogMaxOutPower	OBJECT-TYPE
	SYNTAX			INTEGER
	ACCESS			read-only
	STATUS			mandatory
	DESCRIPTION
			"Values for the 24 hour counters:
			 Maximum power transmitted by radio"
	::= { mlbasUpLinkLog24hourEntry 14 }

mlbasUL24LogAverageOutPower	OBJECT-TYPE
	SYNTAX			INTEGER
	ACCESS			read-only
	STATUS			mandatory
	DESCRIPTION
			"Values for the 24 hour counters:
			 Average power transmitted by radio"
	::= { mlbasUpLinkLog24hourEntry 15 }



-- *****************************************************************************
-- 
--			MLBAS Service Unit Port Table
--
-- *****************************************************************************

mlbasServiceUnitPortTable OBJECT-TYPE
	SYNTAX	SEQUENCE OF MlbasServiceUnitPortEntry
	ACCESS	not-accessible
	STATUS		mandatory
	DESCRIPTION
		"Service Unit Port table"
	::= { mlbasServiceUnitPort 1 }

mlbasServiceUnitPortEntry OBJECT-TYPE 
	SYNTAX	MlbasServiceUnitPortEntry
	ACCESS	not-accessible
	STATUS		mandatory
	DESCRIPTION
		"Entries in the mlbasServiceUnitPortTable represent ports
		 at Access Terminals provided as Service Unit ports at each
		 Access Terminal."
	INDEX {ansAccessUserPortSystemNode, ansAccessUserPortSubrack,
	       ansAccessUserPortPosition, ansAccessUserPortIndex}
	::= { mlbasServiceUnitPortTable 1 }

MlbasServiceUnitPortEntry ::= SEQUENCE {
	mlbasSUPortPosition		INTEGER,
	mlbasSUPortIndex		INTEGER
}

-- The mlbasServiceUnitPortTable is indexed by a port at the Access Terminal
-- (system node, subrack, position, port) and gives a fast way to obtain
-- the corresponding service unit port

mlbasSUPortPosition	OBJECT-TYPE
	SYNTAX		INTEGER
	ACCESS		read-only
	STATUS		mandatory
	DESCRIPTION
		"Reference to slot at the AT for the SU."
	::= { mlbasServiceUnitPortEntry 1 }

mlbasSUPortIndex	OBJECT-TYPE
	SYNTAX		INTEGER
	ACCESS		read-only
	STATUS		mandatory
	DESCRIPTION
		"Reference to the port at the SU."
	::= { mlbasServiceUnitPortEntry 2 }

END
