PANDATEL-INAX-MODEM-MIB DEFINITIONS ::= BEGIN

 -- This is the private mib group section for the INAX modems.
 -- Because these modems must be installed in the PANDATEL modem rack
 -- the PANDATEL-MODEM-MIB also applies.

 -- Ver.1.02    Sep.13.1999

        IMPORTS
                enterprises, Gauge
                        FROM RFC1155-SMI
                DisplayString
                        FROM RFC1213-MIB
                OBJECT-TYPE
                        FROM RFC-1212
                mdmSpecifics, device-id
                        FROM PANDATEL-MODEM-MIB;

-- ********************** THE MDM-INAX SUBTREE ******************************

-- the specific identifier is identical to the modem type integer
-- of the FM-E modem entries in the PANDATEL-MODEM-MIB mdmModemTable.

inax-modem      OBJECT IDENTIFIER ::= { device-id 701 }     -- chassis-mib

inax            OBJECT IDENTIFIER ::= { mdmSpecifics 701 }  -- this subtree

inaxModemTable OBJECT-TYPE
        SYNTAX  SEQUENCE OF InaxTableEntry
        ACCESS  not-accessible
        STATUS  mandatory
        DESCRIPTION
                "This table contains information about all INAX units in all racks."
        ::= { inax 1 }

inaxTableEntry OBJECT-TYPE
        SYNTAX  InaxTableEntry
        ACCESS  not-accessible
        STATUS  mandatory
        DESCRIPTION
                "The index of the table."
        INDEX   { mdmRack, mdmModem, mdmPosition }
        ::= { inaxModemTable 1 }

InaxTableEntry ::= SEQUENCE {
        mdmRack
                INTEGER,
        mdmModem
                INTEGER,
        mdmPosition
                INTEGER,
        mdmModemName
                DisplayString,
        mdmModemProperty
                INTEGER,
        mdmActiveLink
                INTEGER,
        mdmRemoteAccessMode
                INTEGER
        }

mdmRack OBJECT-TYPE
        SYNTAX  INTEGER
        ACCESS  read-only
        STATUS  mandatory
        DESCRIPTION
                "The index of the rack where the unit is installed."
        ::= { inaxTableEntry 1 }

mdmModem OBJECT-TYPE
        SYNTAX  INTEGER
        ACCESS  read-only
        STATUS  mandatory
        DESCRIPTION
                "This entry displays the slot number where the corresponding
                 unit is installed in the rack."
        ::= { inaxTableEntry 2 }

mdmPosition OBJECT-TYPE
        SYNTAX  INTEGER {
                local       (1),
                remote      (2)
                }
        ACCESS  read-only
        STATUS  mandatory
        DESCRIPTION
                "This entry displays the location of the corresponding unit:
                 'local' or 'remote'. The unit which is plugged into a managed
                 rack is 'local', the counterpart is 'remote'."
        ::= { inaxTableEntry 3 }

mdmModemName OBJECT-TYPE
        SYNTAX  DisplayString
        ACCESS  read-only
        STATUS  mandatory
        DESCRIPTION
                "The verbal name of this unit."
        ::= { inaxTableEntry 5 }

mdmModemProperty OBJECT-TYPE
        SYNTAX  INTEGER {
                other           (1),
                e1              (2),
                t1              (3),
                unknown         (99)
        }
        ACCESS  read-only
        STATUS  mandatory
        DESCRIPTION
                "The speed class of the unit: 'e1' or 't1'."
        ::= { inaxTableEntry 7 }

mdmActiveLink OBJECT-TYPE
        SYNTAX  INTEGER {
                line-port-4         (4),
                line-port-5         (5),
                line-port-4-and-5   (11),
                disable             (90)
        }
        ACCESS  read-only
        STATUS  mandatory
        DESCRIPTION
                "This entry displays the line port that is receiving data."
        ::= { inaxTableEntry 12 }

mdmRemoteAccessMode OBJECT-TYPE
        SYNTAX  INTEGER {
                via-timeslot-1      (1),
                via-timeslot-2      (2),
                via-timeslot-3      (3),
                via-timeslot-4      (4),
                via-timeslot-5      (5),
                via-timeslot-6      (6),
                via-timeslot-7      (7),
                via-timeslot-8      (8),
                via-timeslot-9      (9),
                via-timeslot-10     (10),
                via-timeslot-11     (11),
                via-timeslot-12     (12),
                via-timeslot-13     (13),
                via-timeslot-14     (14),
                via-timeslot-15     (15),
                via-timeslot-16     (16),
                via-timeslot-17     (17),
                via-timeslot-18     (18),
                via-timeslot-19     (19),
                via-timeslot-20     (20),
                via-timeslot-21     (21),
                via-timeslot-22     (22),
                via-timeslot-23     (23),
                via-timeslot-24     (24),
                via-timeslot-25     (25),
                via-timeslot-26     (26),
                via-timeslot-27     (27),
                via-timeslot-28     (28),
                via-timeslot-29     (29),
                via-timeslot-30     (30),
                via-timeslot-31     (31),
                disable             (98),
                other               (99)
        }
        ACCESS  read-write
        STATUS  mandatory
        DESCRIPTION
                 "This entry defines the time slot assigned for remote management.
                  Remote management is realized via port 5 always. For T1 units
                  24 time slots are available only. The remote unit's
                  configuration changes simultaneously."
        ::= { inaxTableEntry 64 }

-- ****************** Interface Port Table ******************************

inaxIFPortTable OBJECT-TYPE
        SYNTAX  SEQUENCE OF InaxIFPortEntry
        ACCESS  not-accessible
        STATUS  mandatory
        DESCRIPTION
                "This table contains information about all I/F ports of the
                 INAX units in all racks."
        ::= { inax 2 }

inaxIFPortEntry OBJECT-TYPE
        SYNTAX  InaxIFPortEntry
        ACCESS  not-accessible
        STATUS  mandatory
        DESCRIPTION
                "The index of the table."
        INDEX   { iportRack, iportModem, iportPosition, iportPort }
        ::= { inaxIFPortTable 1 }

InaxIFPortEntry ::= SEQUENCE {
        iportRack
                INTEGER,
        iportModem
                INTEGER,
        iportPosition
                INTEGER,
        iportPort
                INTEGER,
        iportDataEmulationMode
                INTEGER,
        iportDataRate
                INTEGER,
        iportTimeslotSize
                INTEGER
        }

iportRack OBJECT-TYPE
        SYNTAX  INTEGER
        ACCESS  read-only
        STATUS  mandatory
        DESCRIPTION
                "The index of the rack where the unit is installed."
        ::= { inaxIFPortEntry 1 }

iportModem OBJECT-TYPE
        SYNTAX  INTEGER
        ACCESS  read-only
        STATUS  mandatory
        DESCRIPTION
                "The index of the INAX unit the port belongs to."
        ::= { inaxIFPortEntry 2 }

iportPosition OBJECT-TYPE
        SYNTAX  INTEGER {
                local       (1),
                remote      (2)
                }
        ACCESS  read-only
        STATUS  mandatory
        DESCRIPTION
                "This entry displays the location of the corresponding port:
                 'local' or 'remote'. The port which is plugged into a managed
                 rack is 'local', the counterpart is 'remote'."
        ::= { inaxIFPortEntry 3 }

iportPort OBJECT-TYPE
        SYNTAX  INTEGER
        ACCESS  read-only
        STATUS  mandatory
        DESCRIPTION
                "The index of the port."
        ::= { inaxIFPortEntry 4 }

iportDataEmulationMode OBJECT-TYPE
        SYNTAX  INTEGER {
                other       (1),
                dte         (2),
                dce         (3),
                te          (4),
                nt          (5),
                unknown     (99)
        }
        ACCESS  read-only
        STATUS  mandatory
        DESCRIPTION
                "Interface mode of the port: 'dte', 'dce', 'te', or 'nt'."
        ::= { inaxIFPortEntry 6 }

iportDataRate OBJECT-TYPE
        SYNTAX  INTEGER {
                off         (1)
        }
        ACCESS  read-only
        STATUS  mandatory
        DESCRIPTION
                "The data rate at the interface port in bits per seconds."
        ::= { inaxIFPortEntry 25 }

iportTimeslotSize OBJECT-TYPE
        SYNTAX  INTEGER {
                other           (1),
                nx64k           (2),
                nx56k           (3),
                not-available   (100)
        }
        ACCESS  read-write
        STATUS  mandatory
        DESCRIPTION
                "This entry determines the size of the time slots: 'nx64k' or
                 'nx56k'. 'nx56k' is valid for T1 units only. The remote unit's configuration
                 changes simultaneously."
        ::= { inaxIFPortEntry 27 }

-- ****************** Line Port Table ***********************************

inaxLinePortTable OBJECT-TYPE
        SYNTAX  SEQUENCE OF InaxLinePortEntry
        ACCESS  not-accessible
        STATUS  mandatory
        DESCRIPTION
                "This table contains information about all line ports of the
                 INAX units in all racks."
        ::= { inax 3 }

inaxLinePortEntry OBJECT-TYPE
        SYNTAX  InaxLinePortEntry
        ACCESS  not-accessible
        STATUS  mandatory
        DESCRIPTION
                "The index of the table."
        INDEX   { lportRack, lportModem, lportPosition, lportPort }
        ::= { inaxLinePortTable 1 }

InaxLinePortEntry ::= SEQUENCE {
        lportRack
                INTEGER,
        lportModem
                INTEGER,
        lportPosition
                INTEGER,
        lportPort
                INTEGER,
        lportDataEmulationMode
                INTEGER,
        lportClockSource
                INTEGER,
        lportDataRate
                INTEGER,
        lportCRC4Generation
                INTEGER,
        lportFramingMode
                INTEGER,
        lportCodingMode
                INTEGER,
        lportLineBuiltOut
                INTEGER,
        lportPortMode
                INTEGER,
        lportCRC6Test
                INTEGER,
        lportCRC6Status
                INTEGER,
        lportCRC6Error
                Gauge
        }

lportRack OBJECT-TYPE
        SYNTAX  INTEGER
        ACCESS  read-only
        STATUS  mandatory
        DESCRIPTION
                "The index of the rack where the unit is installed."
        ::= { inaxLinePortEntry 1 }

lportModem OBJECT-TYPE
        SYNTAX  INTEGER
        ACCESS  read-only
        STATUS  mandatory
        DESCRIPTION
                "The index of the INAX unit the port belongs to."
        ::= { inaxLinePortEntry 2 }

lportPosition OBJECT-TYPE
        SYNTAX  INTEGER {
                local       (1),
                remote      (2)
                }
        ACCESS  read-only
        STATUS  mandatory
        DESCRIPTION
                "This entry displays the location of the corresponding port:
                 'local' or 'remote'. The port which is plugged into a managed
                 rack is 'local', the counterpart is 'remote'."
        ::= { inaxLinePortEntry 3 }

lportPort OBJECT-TYPE
        SYNTAX  INTEGER
        ACCESS  read-only
        STATUS  mandatory
        DESCRIPTION
                "The index of the port."
        ::= { inaxLinePortEntry 4 }

lportDataEmulationMode OBJECT-TYPE
        SYNTAX  INTEGER {
                other       (1),
                dte         (2),
                dce         (3),
                te          (4),
                nt          (5),
                unknown     (99)
        }
        ACCESS  read-only
        STATUS  mandatory
        DESCRIPTION
                "Interface mode of the port: 'te' or 'nt'."
        ::= { inaxLinePortEntry 6 }

lportClockSource OBJECT-TYPE
        SYNTAX  INTEGER {
                other       (1),
                internal    (2),
                remote      (3)
        }
        ACCESS  read-write
        STATUS  mandatory
        DESCRIPTION
                "The clock source: 'internal' or 'remote'. Port 4 can only
                 be set to 'internal'."
        ::= { inaxLinePortEntry 24 }

lportDataRate OBJECT-TYPE
        SYNTAX  INTEGER {
                off         (1)
        }
        ACCESS  read-only
        STATUS  mandatory
        DESCRIPTION
                "The data rate at the line port in bits per seconds."
        ::= { inaxLinePortEntry 25 }

lportCRC4Generation OBJECT-TYPE
        SYNTAX  INTEGER {
                other           (1),
                disable         (2),
                enable          (3),
                not-available   (100)
        }
        ACCESS  read-write
        STATUS  mandatory
        DESCRIPTION
                "This entry enables or disables the generation of a CRC4 check
                 sum. The remote unit's configuration changes
                 simultaneously. Valid for E1 units only."
        ::= { inaxLinePortEntry 41 }

lportFramingMode OBJECT-TYPE
        SYNTAX  INTEGER {
                other           (1),
                d4              (2),
                esf             (3),
                not-available   (100)
        }
        ACCESS  read-write
        STATUS  mandatory
        DESCRIPTION
                "The T1 framing mode: 'd4' or 'esf'. The remote
                 unit's configuration changes simultaneously.
                 Valid for T1 units only."
        ::= { inaxLinePortEntry 50 }

lportCodingMode OBJECT-TYPE
        SYNTAX  INTEGER {
                other           (1),
                ami             (2),
                b8zs            (3),
                not-available   (100)
        }
        ACCESS  read-write
        STATUS  mandatory
        DESCRIPTION
                "The T1 coding mode at port 4: 'ami' or 'b8zs'. The remote
                 unit's configuration changes simultaneously.
                 Valid for T1 units only."
        ::= { inaxLinePortEntry 51 }

lportLineBuiltOut OBJECT-TYPE
        SYNTAX  INTEGER {
                other               (1),
                itu-rec-g703        (2),
                dsx-1-0to133-ft     (3),
                dsx-1-133to266-ft   (4),
                dsx-1-266to399-ft   (5),
                dsx-1-399to533-ft   (6),
                dsx-1-533to655-ft   (7),
                csu-0db             (8),
                csu-7db5            (9),
                csu-15db            (10),
                csu-22db5           (11),
                not-available       (100)
        }
        ACCESS  read-write
        STATUS  mandatory
        DESCRIPTION
                "The G.703 transmission mode of the unit."
        ::= { inaxLinePortEntry 68 }

lportPortMode OBJECT-TYPE
        SYNTAX  INTEGER {
                other       (1),
                if-mode     (2),
                backup-mode (3),
                link-mode   (4)
        }
        ACCESS  read-write
        STATUS  mandatory
        DESCRIPTION
                "The operation mode at port 4: 'interface-mode', 'backup-mode',
                 or 'link-mode'."
        ::= { inaxLinePortEntry 69 }

lportCRC6Test OBJECT-TYPE
        SYNTAX  INTEGER {
                other           (1),
                start           (3),
                stop            (4),
                not-available   (100)
        }
        ACCESS  read-write
        STATUS  mandatory
        DESCRIPTION
                "This entry enables the execution of a CRC6 test. Write requests
                 with values other than 'start' or 'stop' will be rejected. Valid
                 for T1 units only."
        ::= { inaxLinePortEntry 100 }

lportCRC6Status OBJECT-TYPE
        SYNTAX  INTEGER {
                other           (1),
                never-started   (2),
                running         (5),
                stopped         (6),
                start-failed    (7),
                not-available   (100)
        }
        ACCESS  read-only
        STATUS  mandatory
        DESCRIPTION
                "This entry indicates the status of the CRC6 test.
                 Valid for T1 units only."
        ::= { inaxLinePortEntry 101 }

lportCRC6Error OBJECT-TYPE
        SYNTAX  Gauge
        ACCESS  read-only
        STATUS  mandatory
        DESCRIPTION
                "This entry indicates the number of errors detected during
                 the last 60 seconds."
        ::= { inaxLinePortEntry 102 }

-- ******************** Timeslot Table *****************************

inaxTimeslotTable OBJECT-TYPE
        SYNTAX  SEQUENCE OF InaxTimeslotEntry
        ACCESS  not-accessible
        STATUS  mandatory
        DESCRIPTION
                "This table contains information about all line ports of the
                 INAX units in all racks."
        ::= { inax 4 }

inaxTimeslotEntry OBJECT-TYPE
        SYNTAX  InaxTimeslotEntry
        ACCESS  not-accessible
        STATUS  mandatory
        DESCRIPTION
                "The index of the table."
        INDEX   { tsRack, tsModem, tsPosition, tsPort }
        ::= { inaxTimeslotTable 1 }

InaxTimeslotEntry ::= SEQUENCE {
        tsRack
                INTEGER,
        tsModem
                INTEGER,
        tsPosition
                INTEGER,
        tsPort
                INTEGER,
        tsTimeslot1
                INTEGER,
        tsTimeslot2
                INTEGER,
        tsTimeslot3
                INTEGER,
        tsTimeslot4
                INTEGER,
        tsTimeslot5
                INTEGER,
        tsTimeslot6
                INTEGER,
        tsTimeslot7
                INTEGER,
        tsTimeslot8
                INTEGER,
        tsTimeslot9
                INTEGER,
        tsTimeslot10
                INTEGER,
        tsTimeslot11
                INTEGER,
        tsTimeslot12
                INTEGER,
        tsTimeslot13
                INTEGER,
        tsTimeslot14
                INTEGER,
        tsTimeslot15
                INTEGER,
        tsTimeslot16
                INTEGER,
        tsTimeslot17
                INTEGER,
        tsTimeslot18
                INTEGER,
        tsTimeslot19
                INTEGER,
        tsTimeslot20
                INTEGER,
        tsTimeslot21
                INTEGER,
        tsTimeslot22
                INTEGER,
        tsTimeslot23
                INTEGER,
        tsTimeslot24
                INTEGER,
        tsTimeslot25
                INTEGER,
        tsTimeslot26
                INTEGER,
        tsTimeslot27
                INTEGER,
        tsTimeslot28
                INTEGER,
        tsTimeslot29
                INTEGER,
        tsTimeslot30
                INTEGER,
        tsTimeslot31
                INTEGER
        }

tsRack OBJECT-TYPE
        SYNTAX  INTEGER
        ACCESS  read-only
        STATUS  mandatory
        DESCRIPTION
                "The index of the rack where the unit is installed."
        ::= { inaxTimeslotEntry 1 }

tsModem OBJECT-TYPE
        SYNTAX  INTEGER
        ACCESS  read-only
        STATUS  mandatory
        DESCRIPTION
                "The index of the INAX unit the port belongs to."
        ::= { inaxTimeslotEntry 2 }

tsPosition OBJECT-TYPE
        SYNTAX  INTEGER {
                local       (1),
                remote      (2)
                }
        ACCESS  read-only
        STATUS  mandatory
        DESCRIPTION
                "This entry displays the location of the corresponding port:
                 'local' or 'remote'. The port which is plugged into a managed
                 rack is 'local', the counterpart is 'remote'."
        ::= { inaxTimeslotEntry 3 }

tsPort OBJECT-TYPE
        SYNTAX  INTEGER
        ACCESS  read-only
        STATUS  mandatory
        DESCRIPTION
                "The index of the port."
        ::= { inaxTimeslotEntry 4 }

tsTimeslot1 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 1. 'port-4' is available only if IportPortmode is set
                 to 'interface-mode'. If the time slot is assigned for remote management
                 (see mdmRemoteAccessMode)."
        ::= { inaxTimeslotEntry 301 }

tsTimeslot2 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 2. 'port-4' is available only if IportPortmode is set
                 to 'interface-mode'. If the time slot is assigned for remote management
                 (see mdmRemoteAccessMode)."
        ::= { inaxTimeslotEntry 302 }

tsTimeslot3 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 3. 'port-4' is available only if IportPortmode is set
                 to 'interface-mode'. If the time slot is assigned for remote management
                 (see mdmRemoteAccessMode)."
        ::= { inaxTimeslotEntry 303 }

tsTimeslot4 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 4. 'port-4' is available only if IportPortmode is set
                 to 'interface-mode'. If the time slot is assigned for remote management
                 (see mdmRemoteAccessMode)."
        ::= { inaxTimeslotEntry 304 }

tsTimeslot5 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 5. 'port-4' is available only if IportPortmode is set
                 to 'interface-mode'. If the time slot is assigned for remote management
                 (see mdmRemoteAccessMode)."
        ::= { inaxTimeslotEntry 305 }

tsTimeslot6 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 6. 'port-4' is available only if IportPortmode is set
                 to 'interface-mode'. If the time slot is assigned for remote management
                 (see mdmRemoteAccessMode)."
        ::= { inaxTimeslotEntry 306 }

tsTimeslot7 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 7. 'port-4' is available only if IportPortmode is set
                 to 'interface-mode'. If the time slot is assigned for remote management
                 (see mdmRemoteAccessMode)."
        ::= { inaxTimeslotEntry 307 }

tsTimeslot8 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 8. 'port-4' is available only if IportPortmode is set
                 to 'interface-mode'. If the time slot is assigned for remote management
                 (see mdmRemoteAccessMode)."
        ::= { inaxTimeslotEntry 308 }

tsTimeslot9 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 9. 'port-4' is available only if IportPortmode is set
                 to 'interface-mode'. If the time slot is assigned for remote management
                 (see mdmRemoteAccessMode)."
        ::= { inaxTimeslotEntry 309 }

tsTimeslot10 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 10. 'port-4' is available only if IportPortmode is set
                 to 'interface-mode'. If the time slot is assigned for remote management
                 (see mdmRemoteAccessMode)."
        ::= { inaxTimeslotEntry 310 }

tsTimeslot11 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 11. 'port-4' is available only if IportPortmode is set
                 to 'interface-mode'. If the time slot is assigned for remote management
                 (see mdmRemoteAccessMode)."
        ::= { inaxTimeslotEntry 311 }

tsTimeslot12 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 12. 'port-4' is available only if IportPortmode is set
                 to 'interface-mode'. If the time slot is assigned for remote management
                 (see mdmRemoteAccessMode)."
        ::= { inaxTimeslotEntry 312 }

tsTimeslot13 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 13. 'port-4' is available only if IportPortmode is set
                 to 'interface-mode'. If the time slot is assigned for remote management
                 (see mdmRemoteAccessMode)."
        ::= { inaxTimeslotEntry 313 }

tsTimeslot14 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 14. 'port-4' is available only if IportPortmode is set
                 to 'interface-mode'. If the time slot is assigned for remote management
                 (see mdmRemoteAccessMode)."
        ::= { inaxTimeslotEntry 314 }

tsTimeslot15 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 15. 'port-4' is available only if IportPortmode is set
                 to 'interface-mode'. If the time slot is assigned for remote management
                 (see mdmRemoteAccessMode)."
        ::= { inaxTimeslotEntry 315 }

tsTimeslot16 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 16. 'port-4' is available only if IportPortmode is set
                 to 'interface-mode'. If the time slot is assigned for remote management
                 (see mdmRemoteAccessMode)."
        ::= { inaxTimeslotEntry 316 }

tsTimeslot17 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 17. 'port-4' is available only if IportPortmode is set
                 to 'interface-mode'. If the time slot is assigned for remote management
                 (see mdmRemoteAccessMode)."
        ::= { inaxTimeslotEntry 317 }

tsTimeslot18 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 18. 'port-4' is available only if IportPortmode is set
                 to 'interface-mode'. If the time slot is assigned for remote management
                 (see mdmRemoteAccessMode)."
        ::= { inaxTimeslotEntry 318 }

tsTimeslot19 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 19. 'port-4' is available only if IportPortmode is set
                 to 'interface-mode'. If the time slot is assigned for remote management
                 (see mdmRemoteAccessMode)."
        ::= { inaxTimeslotEntry 319 }

tsTimeslot20 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 20. 'port-4' is available only if IportPortmode is set
                 to 'interface-mode'. If the time slot is assigned for remote management
                 (see mdmRemoteAccessMode)."
        ::= { inaxTimeslotEntry 320 }

tsTimeslot21 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 21. 'port-4' is available only if IportPortmode is set
                 to 'interface-mode'. If the time slot is assigned for remote management
                 (see mdmRemoteAccessMode)."
        ::= { inaxTimeslotEntry 321 }

tsTimeslot22 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 22. 'port-4' is available only if IportPortmode is set
                 to 'interface-mode'. If the time slot is assigned for remote management
                 (see mdmRemoteAccessMode)."
        ::= { inaxTimeslotEntry 322 }

tsTimeslot23 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 23. 'port-4' is available only if IportPortmode is set
                 to 'interface-mode'. If the time slot is assigned for remote management
                 (see mdmRemoteAccessMode)."
        ::= { inaxTimeslotEntry 323 }

tsTimeslot24 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 24. 'port-4' is available only if IportPortmode is set
                 to 'interface-mode'. If the time slot is assigned for remote management
                 (see mdmRemoteAccessMode)."
        ::= { inaxTimeslotEntry 324 }

tsTimeslot25 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 25. 'port-4' is available only if IportPortmode is set
                 to 'interface-mode'. If the time slot is assigned for remote management
                 (see mdmRemoteAccessMode). Valid for E1 units only."
        ::= { inaxTimeslotEntry 325 }

tsTimeslot26 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 26. 'port-4' is available only if IportPortmode is set
                 to 'interface-mode'. If the time slot is assigned for remote management
                 (see mdmRemoteAccessMode). Valid for E1 units only."
        ::= { inaxTimeslotEntry 326 }

tsTimeslot27 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 27. 'port-4' is available only if IportPortmode is set
                 to 'interface-mode'. If the time slot is assigned for remote management
                 (see mdmRemoteAccessMode). Valid for E1 units only."
        ::= { inaxTimeslotEntry 327 }

tsTimeslot28 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 28. 'port-4' is available only if IportPortmode is set
                 to 'interface-mode'. If the time slot is assigned for remote management
                 (see mdmRemoteAccessMode). Valid for E1 units only."
        ::= { inaxTimeslotEntry 328 }

tsTimeslot29 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 29. 'port-4' is available only if IportPortmode is set
                 to 'interface-mode'. If the time slot is assigned for remote management
                 (see mdmRemoteAccessMode). Valid for E1 units only."
        ::= { inaxTimeslotEntry 329 }

tsTimeslot30 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 30. 'port-4' is available only if IportPortmode is set
                 to 'interface-mode'. If the time slot is assigned for remote management
                 (see mdmRemoteAccessMode). Valid for E1 units only."
        ::= { inaxTimeslotEntry 330 }

tsTimeslot31 OBJECT-TYPE
        SYNTAX  INTEGER {
                port-1          (1),
                port-2          (2),
                port-3          (3),
                port-4          (4),
                remote-access   (97),
                off             (98),
                other           (99),
                not-available   (100)
        }
        ACCESS  read-write
        STATUS  mandatory
        DESCRIPTION
                "This entry defines the port number used for the transmission
                 of time slot 31. 'port-4' is available only if IportPortmode is set
                 to 'interface-mode'. If the time slot is assigned for remote management
                 (see mdmRemoteAccessMode). Valid for E1 units only."
        ::= { inaxTimeslotEntry 331 }

END
