Nortel-Magellan-Passport-OamEthernetMIB
DEFINITIONS ::= BEGIN



IMPORTS

      OBJECT-TYPE
   FROM RFC-1212

      passportMIBs
   FROM Nortel-Magellan-Passport-UsefulDefinitionsMIB

      Counter32,
      DisplayString,
      StorageType,
      RowStatus,
      InterfaceIndex,
      Integer32,
      MacAddress,
      Unsigned32
   FROM Nortel-Magellan-Passport-StandardTextualConventionsMIB

      AsciiString,
      NonReplicated,
      Link
   FROM Nortel-Magellan-Passport-TextualConventionsMIB

      lpIndex,
      lp
   FROM Nortel-Magellan-Passport-LogicalProcessorMIB;




-- LAST-UPDATED   "9907300000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     OamEthernet Enterprise MIB."

oamEthernetMIB OBJECT IDENTIFIER ::= { passportMIBs 79 }










-- Lp/0 OamEthernet
-- This component represents an Ethernet port on the control 
-- processor. Only one instance of this component may be created 
-- corresponding to the one hardware port on the control processor. 
-- This port is designed specifically and exclusively for Passport 
-- Operations, Administration and Maintenance purposes; any other 
-- use of this port is unsupported and not advised.

lpOamEnet OBJECT IDENTIFIER ::= { lp 27 }



lpOamEnetRowStatusTable OBJECT-TYPE
   SYNTAX     SEQUENCE OF LpOamEnetRowStatusEntry
   ACCESS     not-accessible
   STATUS     mandatory
   DESCRIPTION
     "This entry controls the addition and deletion of 
      lpOamEnet components."
::= { lpOamEnet 1 }

lpOamEnetRowStatusEntry OBJECT-TYPE
   SYNTAX     LpOamEnetRowStatusEntry
   ACCESS     not-accessible
   STATUS     mandatory
   DESCRIPTION
     "A single entry in the table represents a single 
      lpOamEnet component."
   INDEX {
      lpIndex,
      lpOamEnetIndex }
::= { lpOamEnetRowStatusTable 1 }

LpOamEnetRowStatusEntry ::= SEQUENCE {
   lpOamEnetRowStatus
      RowStatus,
   lpOamEnetComponentName
      DisplayString,
   lpOamEnetStorageType
      StorageType,
   lpOamEnetIndex
      Integer32 }

lpOamEnetRowStatus OBJECT-TYPE
   SYNTAX     RowStatus 
   ACCESS     read-write
   STATUS     mandatory
   DESCRIPTION
     "This variable is used as the basis for SNMP naming of
      lpOamEnet components.
      These components can be added and deleted."
::= { lpOamEnetRowStatusEntry 1 }

lpOamEnetComponentName OBJECT-TYPE
   SYNTAX     DisplayString 
   ACCESS     read-only
   STATUS     mandatory
   DESCRIPTION
     "This variable provides the component's string name for
      use with the ASCII Console Interface"
::= { lpOamEnetRowStatusEntry 2 }

lpOamEnetStorageType OBJECT-TYPE
   SYNTAX     StorageType 
   ACCESS     read-only
   STATUS     mandatory
   DESCRIPTION
     "This variable represents the storage type value for the
      lpOamEnet tables."
::= { lpOamEnetRowStatusEntry 4 }

lpOamEnetIndex OBJECT-TYPE
   SYNTAX     Integer32 (0..0)
   ACCESS     not-accessible
   STATUS     mandatory
   DESCRIPTION
     "This variable represents the index for the lpOamEnet tables."
::= { lpOamEnetRowStatusEntry 10 }

lpOamEnetCidDataTable OBJECT-TYPE
   SYNTAX     SEQUENCE OF LpOamEnetCidDataEntry
   ACCESS     not-accessible
   STATUS     mandatory
   DESCRIPTION
     "This group contains the attribute for a component's Customer 
      Identifier (CID). Refer to the attribute description for a detailed 
      explanation of CIDs."
::= { lpOamEnet 10 }

lpOamEnetCidDataEntry OBJECT-TYPE
   SYNTAX     LpOamEnetCidDataEntry
   ACCESS     not-accessible
   STATUS     mandatory
   DESCRIPTION
     "An entry in the lpOamEnetCidDataTable."
   INDEX {
      lpIndex,
      lpOamEnetIndex }
::= { lpOamEnetCidDataTable 1 }

LpOamEnetCidDataEntry ::= SEQUENCE {
   lpOamEnetCustomerIdentifier
      Unsigned32 }

lpOamEnetCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpOamEnetCidDataEntry 1 }

lpOamEnetIfEntryTable OBJECT-TYPE
   SYNTAX     SEQUENCE OF LpOamEnetIfEntryEntry
   ACCESS     not-accessible
   STATUS     mandatory
   DESCRIPTION
     "This group contains the provisionable attributes for the ifEntry."
::= { lpOamEnet 11 }

lpOamEnetIfEntryEntry OBJECT-TYPE
   SYNTAX     LpOamEnetIfEntryEntry
   ACCESS     not-accessible
   STATUS     mandatory
   DESCRIPTION
     "An entry in the lpOamEnetIfEntryTable."
   INDEX {
      lpIndex,
      lpOamEnetIndex }
::= { lpOamEnetIfEntryTable 1 }

LpOamEnetIfEntryEntry ::= SEQUENCE {
   lpOamEnetIfAdminStatus
      INTEGER,
   lpOamEnetIfIndex
      InterfaceIndex }

lpOamEnetIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpOamEnetIfEntryEntry 1 }

lpOamEnetIfIndex OBJECT-TYPE
   SYNTAX     InterfaceIndex (1..65535)
   ACCESS     read-only
   STATUS     mandatory
   DESCRIPTION
     "This is the index for the IfEntry. Its value is automatically initialized 
      during the provisioning process."
::= { lpOamEnetIfEntryEntry 2 }

lpOamEnetProvTable OBJECT-TYPE
   SYNTAX     SEQUENCE OF LpOamEnetProvEntry
   ACCESS     not-accessible
   STATUS     mandatory
   DESCRIPTION
     "This group contains provisioned attributes for the OamEthernet 
      component."
::= { lpOamEnet 12 }

lpOamEnetProvEntry OBJECT-TYPE
   SYNTAX     LpOamEnetProvEntry
   ACCESS     not-accessible
   STATUS     mandatory
   DESCRIPTION
     "An entry in the lpOamEnetProvTable."
   INDEX {
      lpIndex,
      lpOamEnetIndex }
::= { lpOamEnetProvTable 1 }

LpOamEnetProvEntry ::= SEQUENCE {
   lpOamEnetApplicationFramerName
      Link,
   lpOamEnetSwitchoverOnFailure
      INTEGER,
   lpOamEnetExtendedStatistics
      INTEGER }

lpOamEnetApplicationFramerName OBJECT-TYPE
   SYNTAX     Link 
   ACCESS     read-write
   STATUS     mandatory
   DESCRIPTION
     "This attribute specifies which Lan Application is running on this 
      port."
::= { lpOamEnetProvEntry 1 }

lpOamEnetSwitchoverOnFailure OBJECT-TYPE
   SYNTAX     INTEGER  {
                 enabled(1),
                 disabled(2) }
   ACCESS     read-write
   STATUS     mandatory
   DESCRIPTION
     "This attribute specifies if a CP switchover event should occur if a 
      port or link failure is detected by the initial test process or if a 
      steady state link failure is observed.
      
      This attribute can be set to one of the following values:
      enabled: This value indicates that a switchover will take place if a 
      port or link failure is detected.
      
      disabled: This value indicates that a switchover will not take place 
      if a port or link failure is detected."
   DEFVAL     { enabled }
::= { lpOamEnetProvEntry 3 }

lpOamEnetExtendedStatistics OBJECT-TYPE
   SYNTAX     INTEGER  {
                 enabled(1),
                 disabled(2) }
   ACCESS     read-write
   STATUS     mandatory
   DESCRIPTION
     "This attribute specifies if extended statistics are to be collected for 
      the OamEthernet component.
      
      The extended statistics include: singleCollisionFrames, 
      multipleCollisionFrames, lateCollisions, excessiveCollisions, 
      carrierSenseErrors, and clearToSendSignalLoss. These statistics all 
      require extra processing to gather and store which may have a 
      negative impact on the overall performance of the OAM Ethernet 
      port.
      
      If extendedStatistics is set to disabled, then these particular 
      statistical attributes will be suppressed from display operations."
   DEFVAL     { disabled }
::= { lpOamEnetProvEntry 4 }

lpOamEnetAdminInfoTable OBJECT-TYPE
   SYNTAX     SEQUENCE OF LpOamEnetAdminInfoEntry
   ACCESS     not-accessible
   STATUS     mandatory
   DESCRIPTION
     "This group contains the attributes pertaining to the vendor of the 
      equipment."
::= { lpOamEnet 13 }

lpOamEnetAdminInfoEntry OBJECT-TYPE
   SYNTAX     LpOamEnetAdminInfoEntry
   ACCESS     not-accessible
   STATUS     mandatory
   DESCRIPTION
     "An entry in the lpOamEnetAdminInfoTable."
   INDEX {
      lpIndex,
      lpOamEnetIndex }
::= { lpOamEnetAdminInfoTable 1 }

LpOamEnetAdminInfoEntry ::= SEQUENCE {
   lpOamEnetVendor
      AsciiString,
   lpOamEnetCommentText
      AsciiString }

lpOamEnetVendor OBJECT-TYPE
   SYNTAX     AsciiString (SIZE (0..20))
   ACCESS     read-write
   STATUS     mandatory
   DESCRIPTION
     "This is the name of the vendor supplying the facility."
::= { lpOamEnetAdminInfoEntry 1 }

lpOamEnetCommentText OBJECT-TYPE
   SYNTAX     AsciiString (SIZE (0..60))
   ACCESS     read-write
   STATUS     mandatory
   DESCRIPTION
     "Any miscellaneous text about the facility."
::= { lpOamEnetAdminInfoEntry 2 }

lpOamEnetStateTable OBJECT-TYPE
   SYNTAX     SEQUENCE OF LpOamEnetStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpOamEnet 15 }

lpOamEnetStateEntry OBJECT-TYPE
   SYNTAX     LpOamEnetStateEntry
   ACCESS     not-accessible
   STATUS     mandatory
   DESCRIPTION
     "An entry in the lpOamEnetStateTable."
   INDEX {
      lpIndex,
      lpOamEnetIndex }
::= { lpOamEnetStateTable 1 }

LpOamEnetStateEntry ::= SEQUENCE {
   lpOamEnetAdminState
      INTEGER,
   lpOamEnetOperationalState
      INTEGER,
   lpOamEnetUsageState
      INTEGER }

lpOamEnetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpOamEnetStateEntry 1 }

lpOamEnetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpOamEnetStateEntry 2 }

lpOamEnetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpOamEnetStateEntry 3 }

lpOamEnetOperStatusTable OBJECT-TYPE
   SYNTAX     SEQUENCE OF LpOamEnetOperStatusEntry
   ACCESS     not-accessible
   STATUS     mandatory
   DESCRIPTION
     "This group includes the Operational Status attribute. This attribute 
      defines the current operational state of this component."
::= { lpOamEnet 16 }

lpOamEnetOperStatusEntry OBJECT-TYPE
   SYNTAX     LpOamEnetOperStatusEntry
   ACCESS     not-accessible
   STATUS     mandatory
   DESCRIPTION
     "An entry in the lpOamEnetOperStatusTable."
   INDEX {
      lpIndex,
      lpOamEnetIndex }
::= { lpOamEnetOperStatusTable 1 }

LpOamEnetOperStatusEntry ::= SEQUENCE {
   lpOamEnetSnmpOperStatus
      INTEGER }

lpOamEnetSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpOamEnetOperStatusEntry 1 }

lpOamEnetOperTable OBJECT-TYPE
   SYNTAX     SEQUENCE OF LpOamEnetOperEntry
   ACCESS     not-accessible
   STATUS     mandatory
   DESCRIPTION
     "This group contains the operational attributes of the OamEthernet 
      component."
::= { lpOamEnet 17 }

lpOamEnetOperEntry OBJECT-TYPE
   SYNTAX     LpOamEnetOperEntry
   ACCESS     not-accessible
   STATUS     mandatory
   DESCRIPTION
     "An entry in the lpOamEnetOperTable."
   INDEX {
      lpIndex,
      lpOamEnetIndex }
::= { lpOamEnetOperTable 1 }

LpOamEnetOperEntry ::= SEQUENCE {
   lpOamEnetMacAddress
      MacAddress,
   lpOamEnetActiveStatus
      INTEGER,
   lpOamEnetStandbyStatus
      INTEGER }

lpOamEnetMacAddress OBJECT-TYPE
   SYNTAX     MacAddress (SIZE (6))
   ACCESS     read-only
   STATUS     mandatory
   DESCRIPTION
     "This attribute indicates the medium access controller (MAC) 
      address automatically assigned to the OAM Ethernet port by the 
      system. The MAC address is displayed in canonical format."
::= { lpOamEnetOperEntry 1 }

lpOamEnetActiveStatus OBJECT-TYPE
   SYNTAX     INTEGER  {
                 available(1),
                 notAvailable(2) }
   ACCESS     read-only
   STATUS     mandatory
   DESCRIPTION
     "This attribute indicates the status of the Oam Ethernet port on the 
      active CP."
::= { lpOamEnetOperEntry 2 }

lpOamEnetStandbyStatus OBJECT-TYPE
   SYNTAX     INTEGER  {
                 available(1),
                 notAvailable(2) }
   ACCESS     read-only
   STATUS     mandatory
   DESCRIPTION
     "This attribute indicates the status of the Oam Ethernet port on the 
      standby CP."
::= { lpOamEnetOperEntry 3 }

lpOamEnetOamEnetStatsTable OBJECT-TYPE
   SYNTAX     SEQUENCE OF LpOamEnetOamEnetStatsEntry
   ACCESS     not-accessible
   STATUS     mandatory
   DESCRIPTION
     "This group contains statistical attributes for the		 OamEthernet 
      component."
::= { lpOamEnet 18 }

lpOamEnetOamEnetStatsEntry OBJECT-TYPE
   SYNTAX     LpOamEnetOamEnetStatsEntry
   ACCESS     not-accessible
   STATUS     mandatory
   DESCRIPTION
     "An entry in the lpOamEnetOamEnetStatsTable."
   INDEX {
      lpIndex,
      lpOamEnetIndex }
::= { lpOamEnetOamEnetStatsTable 1 }

LpOamEnetOamEnetStatsEntry ::= SEQUENCE {
   lpOamEnetClearToSendSignalLoss
      Counter32,
   lpOamEnetFrameTooShort
      Counter32,
   lpOamEnetNumberOfRxCollisions
      Counter32,
   lpOamEnetLackOfResourcesDiscards
      Counter32,
   lpOamEnetOverrunErrors
      Counter32 }

lpOamEnetClearToSendSignalLoss OBJECT-TYPE
   SYNTAX     Counter32 
   ACCESS     read-only
   STATUS     mandatory
   DESCRIPTION
     "This attribute indicates the number of times that the clear to send 
      signal was lost when attempting to transmit a frame. This counter 
      wraps to zero when it exceeds its maximum value.
      
      This attribute is only active if the extendedStatistics attribute is 
      enabled."
::= { lpOamEnetOamEnetStatsEntry 14 }

lpOamEnetFrameTooShort OBJECT-TYPE
   SYNTAX     Counter32 
   ACCESS     read-only
   STATUS     mandatory
   DESCRIPTION
     "This attribute indicates the number of frames received whose length 
      is less than the allowed minimum frame length. This counter wraps 
      to zero when it exceeds its maximum value."
::= { lpOamEnetOamEnetStatsEntry 15 }

lpOamEnetNumberOfRxCollisions OBJECT-TYPE
   SYNTAX     Counter32 
   ACCESS     read-only
   STATUS     mandatory
   DESCRIPTION
     "This attribute indicates the number of collisions detected during 
      reception. This counter wraps to zero when it exceeds its maximum 
      value."
::= { lpOamEnetOamEnetStatsEntry 17 }

lpOamEnetLackOfResourcesDiscards OBJECT-TYPE
   SYNTAX     Counter32 
   ACCESS     read-only
   STATUS     mandatory
   DESCRIPTION
     "This attribute indicates the number of good frames discarded 
      because of a lack of resources available to contain them on the 
      system. This counter wraps to zero when it exceeds its maximum 
      value."
::= { lpOamEnetOamEnetStatsEntry 18 }

lpOamEnetOverrunErrors OBJECT-TYPE
   SYNTAX     Counter32 
   ACCESS     read-only
   STATUS     mandatory
   DESCRIPTION
     "This attribute indicates the number of frames known to be lost 
      because the local system bus was not available. This counter wraps 
      to zero when it exceeds its maximum value."
::= { lpOamEnetOamEnetStatsEntry 19 }

lpOamEnetStatsTable OBJECT-TYPE
   SYNTAX     SEQUENCE OF LpOamEnetStatsEntry
   ACCESS     not-accessible
   STATUS     mandatory
   DESCRIPTION
     "This group contains statistical attributes for the		 Ethernet component."
::= { lpOamEnet 19 }

lpOamEnetStatsEntry OBJECT-TYPE
   SYNTAX     LpOamEnetStatsEntry
   ACCESS     not-accessible
   STATUS     mandatory
   DESCRIPTION
     "An entry in the lpOamEnetStatsTable."
   INDEX {
      lpIndex,
      lpOamEnetIndex }
::= { lpOamEnetStatsTable 1 }

LpOamEnetStatsEntry ::= SEQUENCE {
   lpOamEnetAlignmentErrors
      Counter32,
   lpOamEnetFcsErrors
      Counter32,
   lpOamEnetSingleCollisionFrames
      Counter32,
   lpOamEnetMultipleCollisionFrames
      Counter32,
   lpOamEnetSqeTestErrors
      Counter32,
   lpOamEnetDeferredTransmissions
      Counter32,
   lpOamEnetLateCollisions
      Counter32,
   lpOamEnetExcessiveCollisions
      Counter32,
   lpOamEnetMacTransmitErrors
      Counter32,
   lpOamEnetCarrierSenseErrors
      Counter32,
   lpOamEnetFrameTooLongs
      Counter32,
   lpOamEnetMacReceiveErrors
      Counter32 }

lpOamEnetAlignmentErrors OBJECT-TYPE
   SYNTAX     Counter32 
   ACCESS     read-only
   STATUS     mandatory
   DESCRIPTION
     "The alignmentErrors counter indicates the number of frames received 
      which were not an integral number of octets in length. Frames will be 
      checked for alignmentErrors before they are checked for Frame Check 
      Sequence (FCS) errors. If there is an alignment error, the error will only 
      be counted here and not in fcsErrors. This counter will wrap around 
      after it reaches its maximum value."
::= { lpOamEnetStatsEntry 2 }

lpOamEnetFcsErrors OBJECT-TYPE
   SYNTAX     Counter32 
   ACCESS     read-only
   STATUS     mandatory
   DESCRIPTION
     "The fcsErrors, Frame Check Sequence (FCS) error, counter indicates the 
      number of frames received which were an integral number of octets in 
      length and did not pass the FCS check. This counter will wrap around 
      after it reaches its maximum value."
::= { lpOamEnetStatsEntry 3 }

lpOamEnetSingleCollisionFrames OBJECT-TYPE
   SYNTAX     Counter32 
   ACCESS     read-only
   STATUS     mandatory
   DESCRIPTION
     "The singleCollisionFrames counter indicates the number of frames 
      successfully transmitted which experienced exactly one collision. This 
      counter will wrap around after it reaches its maximum value."
::= { lpOamEnetStatsEntry 4 }

lpOamEnetMultipleCollisionFrames OBJECT-TYPE
   SYNTAX     Counter32 
   ACCESS     read-only
   STATUS     mandatory
   DESCRIPTION
     "The multipleCollisionFrames counter indicates the number of frames 
      successfully transmitted which experienced more than one collision. 
      This counter will wrap around after it reaches its maximum value."
::= { lpOamEnetStatsEntry 5 }

lpOamEnetSqeTestErrors OBJECT-TYPE
   SYNTAX     Counter32 
   ACCESS     read-only
   STATUS     mandatory
   DESCRIPTION
     "The sqeTestErrors, Signal Quality Error (SQE) Test errors, counter 
      indicates the number of times the 'SQE Test Error' message has been 
      generated for the station. This counter will wrap around after it reaches 
      its maximum value."
::= { lpOamEnetStatsEntry 6 }

lpOamEnetDeferredTransmissions OBJECT-TYPE
   SYNTAX     Counter32 
   ACCESS     read-only
   STATUS     mandatory
   DESCRIPTION
     "The deferredTransmissions counter indicates the number of frames 
      which experienced a transmission delay because the medium was busy. 
      This counter will wrap around after it reaches its maximum value."
::= { lpOamEnetStatsEntry 7 }

lpOamEnetLateCollisions OBJECT-TYPE
   SYNTAX     Counter32 
   ACCESS     read-only
   STATUS     mandatory
   DESCRIPTION
     "The lateCollisions counter indicates the number of times a collision was 
      detected later than 512 bit-times into the transmission of a packet. This 
      counter will wrap around after it reaches its maximum value."
::= { lpOamEnetStatsEntry 8 }

lpOamEnetExcessiveCollisions OBJECT-TYPE
   SYNTAX     Counter32 
   ACCESS     read-only
   STATUS     mandatory
   DESCRIPTION
     "The excessiveCollisions counter indicates the number of frames which 
      failed to get transmitted due to excessive collisions. This counter will 
      wrap around after it reaches its maximum value."
::= { lpOamEnetStatsEntry 9 }

lpOamEnetMacTransmitErrors OBJECT-TYPE
   SYNTAX     Counter32 
   ACCESS     read-only
   STATUS     mandatory
   DESCRIPTION
     "The Medium Access Controller (MAC) transmit error counter indicates 
      the number of times that a transmission failed due to internal MAC 
      transmit errors. This counter will wrap around after it reaches its 
      maximum value."
::= { lpOamEnetStatsEntry 10 }

lpOamEnetCarrierSenseErrors OBJECT-TYPE
   SYNTAX     Counter32 
   ACCESS     read-only
   STATUS     mandatory
   DESCRIPTION
     "The carrier sense error counter indicates the number of times that the 
      carrier sense condition was lost or never asserted when attempting to 
      transmit a frame. This counter will wrap around after it reaches its 
      maximum value."
::= { lpOamEnetStatsEntry 11 }

lpOamEnetFrameTooLongs OBJECT-TYPE
   SYNTAX     Counter32 
   ACCESS     read-only
   STATUS     mandatory
   DESCRIPTION
     "The frame too long counter indicates the number of frames received 
      which exceeded the maximum frame size. This counter will wrap 
      around after it reaches its maximum value."
::= { lpOamEnetStatsEntry 12 }

lpOamEnetMacReceiveErrors OBJECT-TYPE
   SYNTAX     Counter32 
   ACCESS     read-only
   STATUS     mandatory
   DESCRIPTION
     "The Medium Access Controller (MAC) receive error counter indicates 
      the number of times a receive failed due to internal MAC receive errors. 
      This counter will wrap around after it reaches its maximum value."
::= { lpOamEnetStatsEntry 13 }


-- Lp/0 OamEthernet Test
-- The Test component is used to run the port test for the OAM 
-- Ethernet port on CP cards.

lpOamEnetTest OBJECT IDENTIFIER ::= { lpOamEnet 2 }



lpOamEnetTestRowStatusTable OBJECT-TYPE
   SYNTAX     SEQUENCE OF LpOamEnetTestRowStatusEntry
   ACCESS     not-accessible
   STATUS     mandatory
   DESCRIPTION
     "This entry controls the addition and deletion of 
      lpOamEnetTest components."
::= { lpOamEnetTest 1 }

lpOamEnetTestRowStatusEntry OBJECT-TYPE
   SYNTAX     LpOamEnetTestRowStatusEntry
   ACCESS     not-accessible
   STATUS     mandatory
   DESCRIPTION
     "A single entry in the table represents a single 
      lpOamEnetTest component."
   INDEX {
      lpIndex,
      lpOamEnetIndex,
      lpOamEnetTestIndex }
::= { lpOamEnetTestRowStatusTable 1 }

LpOamEnetTestRowStatusEntry ::= SEQUENCE {
   lpOamEnetTestRowStatus
      RowStatus,
   lpOamEnetTestComponentName
      DisplayString,
   lpOamEnetTestStorageType
      StorageType,
   lpOamEnetTestIndex
      NonReplicated }

lpOamEnetTestRowStatus OBJECT-TYPE
   SYNTAX     RowStatus 
   ACCESS     read-only
   STATUS     mandatory
   DESCRIPTION
     "This variable is used as the basis for SNMP naming of
      lpOamEnetTest components.
      These components cannot be added nor deleted."
::= { lpOamEnetTestRowStatusEntry 1 }

lpOamEnetTestComponentName OBJECT-TYPE
   SYNTAX     DisplayString 
   ACCESS     read-only
   STATUS     mandatory
   DESCRIPTION
     "This variable provides the component's string name for
      use with the ASCII Console Interface"
::= { lpOamEnetTestRowStatusEntry 2 }

lpOamEnetTestStorageType OBJECT-TYPE
   SYNTAX     StorageType 
   ACCESS     read-only
   STATUS     mandatory
   DESCRIPTION
     "This variable represents the storage type value for the
      lpOamEnetTest tables."
::= { lpOamEnetTestRowStatusEntry 4 }

lpOamEnetTestIndex OBJECT-TYPE
   SYNTAX     NonReplicated 
   ACCESS     not-accessible
   STATUS     mandatory
   DESCRIPTION
     "This variable represents the index for the lpOamEnetTest tables."
::= { lpOamEnetTestRowStatusEntry 10 }

lpOamEnetTestOperTable OBJECT-TYPE
   SYNTAX     SEQUENCE OF LpOamEnetTestOperEntry
   ACCESS     not-accessible
   STATUS     mandatory
   DESCRIPTION
     "This group contains the operational data for the Test component."
::= { lpOamEnetTest 10 }

lpOamEnetTestOperEntry OBJECT-TYPE
   SYNTAX     LpOamEnetTestOperEntry
   ACCESS     not-accessible
   STATUS     mandatory
   DESCRIPTION
     "An entry in the lpOamEnetTestOperTable."
   INDEX {
      lpIndex,
      lpOamEnetIndex,
      lpOamEnetTestIndex }
::= { lpOamEnetTestOperTable 1 }

LpOamEnetTestOperEntry ::= SEQUENCE {
   lpOamEnetTestType
      INTEGER }

lpOamEnetTestType OBJECT-TYPE
   SYNTAX     INTEGER  {
                 hardwareLogic(0),
                 configuration(1),
                 memoryMap(2),
                 tdr(3) }
   ACCESS     read-write
   STATUS     mandatory
   DESCRIPTION
     "This attribute is the type of test to be run. The four types of tests 
      available are: the port hardware logic test, the configure and dump 
      memory registers test, the memory mapping test and the Time 
      Domain Reflectometry (TDR) test.
      
      The possible values of this attribute are:
      hardwareLogic: this test checks the port hardware controller for 
      logic errors in some of the on-chip counters and shift registers.
      
      configuration: this test configures the memory registers of the 
      hardware controller in a predetermined way and then dumps the 
      registers and checks their contents for errors.
      
      memoryMap: this test does an extensive test of the memory 
      structures used by the OAM Ethernet port to verify that they are 
      configured correctly and are error-free.
      
      tdr: this test is used to detect and locate cable faults caused by either 
      a short or an open circuit on the coaxial cable."
::= { lpOamEnetTestOperEntry 1 }

lpOamEnetTestResultsTable OBJECT-TYPE
   SYNTAX     SEQUENCE OF LpOamEnetTestResultsEntry
   ACCESS     not-accessible
   STATUS     mandatory
   DESCRIPTION
     "This group contains all the statistics related attributes of the Test 
      component."
::= { lpOamEnetTest 11 }

lpOamEnetTestResultsEntry OBJECT-TYPE
   SYNTAX     LpOamEnetTestResultsEntry
   ACCESS     not-accessible
   STATUS     mandatory
   DESCRIPTION
     "An entry in the lpOamEnetTestResultsTable."
   INDEX {
      lpIndex,
      lpOamEnetIndex,
      lpOamEnetTestIndex }
::= { lpOamEnetTestResultsTable 1 }

LpOamEnetTestResultsEntry ::= SEQUENCE {
   lpOamEnetTestCauseOfTermination
      INTEGER,
   lpOamEnetTestTestResult
      INTEGER }

lpOamEnetTestCauseOfTermination OBJECT-TYPE
   SYNTAX     INTEGER  {
                 testTimeExpired(0),
                 stoppedByOperator(1),
                 unknown(2),
                 neverStarted(3),
                 testRunning(4),
                 testComplete(5) }
   ACCESS     read-only
   STATUS     mandatory
   DESCRIPTION
     "This attribute records the reason why the test terminated.
      
      The possible values of this attribute are:
      testTimeExpired: this value indicates the time allotted for the test to 
      run has expired which caused the test terminate. If the port is locked 
      without the forever option then it will remain locked for only five 
      minutes before being automatically unlocked. If the port unlocks 
      itself after five minutes while the test is running then this attribute 
      will be set to testTimeExpired. If the forever option is used then the 
      test will run until completion, failure, or a Stop command.
      
      stoppedByOperator: this value indicates that the test was terminated 
      when an operator issued a Stop command.
      
      unknown: this value indicates that the test terminated for an 
      unknown reason.
      
      neverStarted: this value indicates that the test never started because 
      the port could not be locked or because there is a hardware failure 
      preventing the tests from running.
      
      testRunning: this value indicates that the test is currently running.
      
      testComplete: this value indicates that the test completed normally."
   DEFVAL     { neverStarted }
::= { lpOamEnetTestResultsEntry 1 }

lpOamEnetTestTestResult OBJECT-TYPE
   SYNTAX     INTEGER  {
                 neverRun(0),
                 fail(1),
                 pass(2),
                 running(3) }
   ACCESS     read-only
   STATUS     mandatory
   DESCRIPTION
     "This attribute records the result of last port test executed on the 
      OAM Ethernet port. The result can be one of the following values.
      pass: the test passed
      fail: the test failed
      neverRun: the test has not been run
      running: the test is running"
::= { lpOamEnetTestResultsEntry 2 }




-- 
-- Version and Compliance statements
-- 



-- Object-Group Statement:
-- A list of all current accessible leaf objects.

-- OBJECTS { lpOamEnetCommentText,
--           lpOamEnetLateCollisions,
--           lpOamEnetComponentName,
--           lpOamEnetStandbyStatus,
--           lpOamEnetTestTestResult,
--           lpOamEnetStorageType,
--           lpOamEnetAlignmentErrors,
--           lpOamEnetExtendedStatistics,
--           lpOamEnetSqeTestErrors,
--           lpOamEnetRowStatus,
--           lpOamEnetTestCauseOfTermination,
--           lpOamEnetOperationalState,
--           lpOamEnetTestStorageType,
--           lpOamEnetExcessiveCollisions,
--           lpOamEnetLackOfResourcesDiscards,
--           lpOamEnetTestComponentName,
--           lpOamEnetFcsErrors,
--           lpOamEnetMacReceiveErrors,
--           lpOamEnetIfIndex,
--           lpOamEnetActiveStatus,
--           lpOamEnetTestType,
--           lpOamEnetAdminState,
--           lpOamEnetDeferredTransmissions,
--           lpOamEnetCarrierSenseErrors,
--           lpOamEnetFrameTooShort,
--           lpOamEnetApplicationFramerName,
--           lpOamEnetMacTransmitErrors,
--           lpOamEnetIfAdminStatus,
--           lpOamEnetFrameTooLongs,
--           lpOamEnetMacAddress,
--           lpOamEnetMultipleCollisionFrames,
--           lpOamEnetTestRowStatus,
--           lpOamEnetCustomerIdentifier,
--           lpOamEnetOverrunErrors,
--           lpOamEnetVendor,
--           lpOamEnetSwitchoverOnFailure,
--           lpOamEnetSnmpOperStatus,
--           lpOamEnetClearToSendSignalLoss,
--           lpOamEnetNumberOfRxCollisions,
--           lpOamEnetSingleCollisionFrames,
--           lpOamEnetUsageState }
-- STATUS  mandatory
-- DESCRIPTION
--   "A list of all current accessible leaf objects."

oamEthernetGroup OBJECT IDENTIFIER ::= { oamEthernetMIB 1 }
oamEthernetGroupCA OBJECT IDENTIFIER ::= { oamEthernetGroup 27 }
oamEthernetGroupCA01 OBJECT IDENTIFIER ::= { oamEthernetGroupCA 2 }
oamEthernetGroupCA01A OBJECT IDENTIFIER ::= { oamEthernetGroupCA01 2 }



-- Agent-Capabilities Statement:

-- PRODUCT-RELEASE "Passport Release 7.0 OamEthernet."
-- STATUS          mandatory
-- DESCRIPTION     "OamEthernet MIB: MIB Version CA01A,
--                  Software Version BG00S4C."
-- SUPPORTS        Nortel-Magellan-Passport-OamEthernetMIB
--    INCLUDES     { oamEthernetGroupCA01A }

oamEthernetCapabilities OBJECT IDENTIFIER ::= { oamEthernetMIB 3 }
oamEthernetCapabilitiesCA OBJECT IDENTIFIER ::= { oamEthernetCapabilities 27 }
oamEthernetCapabilitiesCA01 OBJECT IDENTIFIER ::= { oamEthernetCapabilitiesCA 2 }
oamEthernetCapabilitiesCA01A OBJECT IDENTIFIER ::= { oamEthernetCapabilitiesCA01 2 }





END
