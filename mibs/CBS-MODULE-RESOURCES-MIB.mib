CBS-MODULE-RESOURCES-MIB DEFINITIONS ::= BEGIN

IMPORTS
   Gauge32, MODULE-IDENTITY, OBJECT-TYPE, 
   NOTIFICATION-TYPE, Integer32             FROM SNMPv2-SMI
 
   TEXTUAL-CONVENTION,
   DisplayString, TruthValue                FROM SNMPv2-TC

   ProductID, KBytes                        FROM HOST-RESOURCES-MIB

   cbsMIBs, cbsMgmt, cbsTraps               FROM CROSSBEAM-SYSTEMS-MIB

   cbsHwModuleID                            FROM CBS-HARDWARE-MIB;


cbsModuleResourcesMIB MODULE-IDENTITY
   LAST-UPDATED "200103020000Z"     -- 2 March 2001
   ORGANIZATION "Crossbeam Systems, Inc."
   CONTACT-INFO "Email:  mib-admin@crossbeamsys.com
                 Postal: 200 Baker Avenue
                         Concord MA 01742"
   DESCRIPTION  "This MIB module defines the objects monitor the
                 performance and utilization of Module resources."

   REVISION     "200203180000Z"     -- 18 March 2002
   DESCRIPTION  "Initial Revision"

   REVISION     "200208010000Z"     -- 1 August 2002
   DESCRIPTION  "Obsoleted cbsModuleMemoryUsageExceeded and
                cbsModuleMemoryUsageNormal notification types"

   REVISION     "200212110000Z"     -- 11 December 2002
   DESCRIPTION  "Added cbsModuleCPUUtil objects. Obsoleted cpuLoad
                exceeded/normal notification types in favor of
                cpuUtil notification types"

::= { cbsMIBs 3 }


cbsModuleResources       OBJECT IDENTIFIER ::= { cbsMgmt 3 }
cbsModuleResourceTraps   OBJECT IDENTIFIER ::= { cbsTraps 2 }


-- Table of processor CPU utilization

cbsModuleCPULoadTable OBJECT-TYPE
   SYNTAX       SEQUENCE OF CbsModuleCPULoadEntry
   MAX-ACCESS   not-accessible
   STATUS       current
   DESCRIPTION
      "This table contains information about the CPU utilization of
      the processor modules."
   ::= { cbsModuleResources 1 }

cbsModuleCPULoadEntry OBJECT-TYPE
   SYNTAX     CbsModuleCPULoadEntry
   MAX-ACCESS not-accessible
   STATUS     current
   DESCRIPTION
      "An entry in the CPU laod table."
   INDEX { cbsHwModuleID }
   ::= { cbsModuleCPULoadTable 1 }

CbsModuleCPULoadEntry ::= SEQUENCE {
   cbsModuleCPUSpeed             Integer32,
   cbsModuleCPUCount             Integer32,
   cbsModuleCPULoad1             Gauge32,
   cbsModuleCPULoad5             Gauge32,
   cbsModuleCPULoad15            Gauge32,
   cbsModuleCPUUtil1             Gauge32,
   cbsModuleCPUUtil5             Gauge32,
   cbsModuleCPUUtil15            Gauge32
}

cbsModuleCPUSpeed OBJECT-TYPE
   SYNTAX     Integer32
   MAX-ACCESS read-only
   STATUS     current
   DESCRIPTION
      "The speed of the processor(s) in MHz."
   ::= { cbsModuleCPULoadEntry 1 }

cbsModuleCPUCount OBJECT-TYPE
   SYNTAX     Integer32
   MAX-ACCESS read-only
   STATUS     current
   DESCRIPTION
      "The number of CPUs on the module"
   ::= { cbsModuleCPULoadEntry 2 }

cbsModuleCPULoad1 OBJECT-TYPE
   SYNTAX     Gauge32
   MAX-ACCESS read-only
   STATUS     current
   DESCRIPTION
      "The average number of processes ready to run in the last
       minute."
   ::= { cbsModuleCPULoadEntry 3 }

cbsModuleCPULoad5 OBJECT-TYPE
   SYNTAX     Gauge32
   MAX-ACCESS read-only
   STATUS     current
   DESCRIPTION
      "The average number of processes ready to run in the last
       5 minutes."
   ::= { cbsModuleCPULoadEntry 4 }

cbsModuleCPULoad15 OBJECT-TYPE
   SYNTAX     Gauge32
   MAX-ACCESS read-only
   STATUS     current
   DESCRIPTION
      "The average number of processes ready to run in the last
       5 minutes."
   ::= { cbsModuleCPULoadEntry 5 }

cbsModuleCPUUtil1 OBJECT-TYPE
   SYNTAX     Gauge32 (0..100)
   MAX-ACCESS read-only
   STATUS     current
   DESCRIPTION
      "CPU utilization averaged over last 1 minute."
   ::= { cbsModuleCPULoadEntry 6 }

cbsModuleCPUUtil5 OBJECT-TYPE
   SYNTAX     Gauge32 (0..100)
   MAX-ACCESS read-only
   STATUS     current
   DESCRIPTION
      "CPU utilization averaged over last 5 minutes."
   ::= { cbsModuleCPULoadEntry 7 }

cbsModuleCPUUtil15 OBJECT-TYPE
   SYNTAX     Gauge32 (0..100)
   MAX-ACCESS read-only
   STATUS     current
   DESCRIPTION
      "CPU utilization averaged over last 15 minutes."
   ::= { cbsModuleCPULoadEntry 8 }


-- Table of processor Memory utilization

cbsModuleMemoryTable OBJECT-TYPE
   SYNTAX       SEQUENCE OF CbsModuleMemoryEntry
   MAX-ACCESS   not-accessible
   STATUS       current
   DESCRIPTION
      "This table contains information about the memory utilization of the
       processor modules."
   ::= { cbsModuleResources 2 }

cbsModuleMemoryEntry OBJECT-TYPE
   SYNTAX     CbsModuleMemoryEntry
   MAX-ACCESS not-accessible
   STATUS     current
   DESCRIPTION
      "An entry in the memory utilization table."
   INDEX { cbsHwModuleID }
   ::= { cbsModuleMemoryTable 1 }

CbsModuleMemoryEntry ::= SEQUENCE {
   cbsModuleMemoryTotal          KBytes,
   cbsModuleMemoryUsed           KBytes,
   cbsModuleMemoryFree           KBytes
}

cbsModuleMemoryTotal OBJECT-TYPE
   SYNTAX     KBytes
   MAX-ACCESS read-only
   STATUS     current
   DESCRIPTION
      "Total memory that can be utilized by the operating system."
   ::= { cbsModuleMemoryEntry 1 }

cbsModuleMemoryUsed OBJECT-TYPE
   SYNTAX     KBytes
   MAX-ACCESS read-only
   STATUS     current
   DESCRIPTION
      "The amount of memory in use."
   ::= { cbsModuleMemoryEntry 2 }

cbsModuleMemoryFree OBJECT-TYPE
   SYNTAX     KBytes
   MAX-ACCESS read-only
   STATUS     current
   DESCRIPTION
      "Amount of memory available for use."
   ::= { cbsModuleMemoryEntry 3 }


-- Table of processor swap utilization

cbsModuleSwapTable OBJECT-TYPE
   SYNTAX       SEQUENCE OF CbsModuleSwapEntry
   MAX-ACCESS   not-accessible
   STATUS       current
   DESCRIPTION
      "This table contains information about the swap utilization of the
       processor modules."
   ::= { cbsModuleResources 3 }

cbsModuleSwapEntry OBJECT-TYPE
   SYNTAX     CbsModuleSwapEntry
   MAX-ACCESS not-accessible
   STATUS     current
   DESCRIPTION
      "An entry in the memory utilization table."
   INDEX { cbsHwModuleID }
   ::= { cbsModuleSwapTable 1 }

CbsModuleSwapEntry ::= SEQUENCE {
   cbsModuleSwapTotal          KBytes,
   cbsModuleSwapUsed           KBytes,
   cbsModuleSwapFree           KBytes
}

cbsModuleSwapTotal OBJECT-TYPE
   SYNTAX     KBytes
   MAX-ACCESS read-only
   STATUS     current
   DESCRIPTION
      "Total swap space available to the operating system."
   ::= { cbsModuleSwapEntry 1 }

cbsModuleSwapUsed OBJECT-TYPE
   SYNTAX     KBytes
   MAX-ACCESS read-only
   STATUS     current
   DESCRIPTION
      "The amount of swap space in use."
   ::= { cbsModuleSwapEntry 2 }

cbsModuleSwapFree OBJECT-TYPE
   SYNTAX     KBytes
   MAX-ACCESS read-only
   STATUS     current
   DESCRIPTION
      "Amount of free swap space."
   ::= { cbsModuleSwapEntry 3 }


-- The traps

cbsModuleCPULoadExceeded NOTIFICATION-TYPE
   OBJECTS { cbsModuleCPULoad1 }
   STATUS  obsolete
   DESCRIPTION
     "The CPU load on one of the processor modules is excessive. The
      current value of the one minute load on the CPU module
      that is experinceing excessive load is sent."
   ::= { cbsModuleResourceTraps 1 }

cbsModuleCPULoadNormal NOTIFICATION-TYPE
   OBJECTS { cbsModuleCPULoad1 }
   STATUS  obsolete
   DESCRIPTION
     "The CPU load on one of the processor modules has returned to
      normal. The current value of the one minute load on the CPU module
      that has returned to normal is sent."
   ::= { cbsModuleResourceTraps 2 }

cbsModuleMemoryUsageExceeded NOTIFICATION-TYPE
   OBJECTS { cbsModuleMemoryTotal, cbsModuleMemoryUsed }
   STATUS  obsolete
   DESCRIPTION
     "The memory usage on the processor modules is excessive. The
      current values of total and free memory for the module are
      sent."
   ::= { cbsModuleResourceTraps 3 }

cbsModuleMemoryUsageNormal NOTIFICATION-TYPE
   OBJECTS { cbsModuleMemoryTotal, cbsModuleMemoryUsed }
   STATUS  obsolete
   DESCRIPTION
     "The memory usage on the processor modules that was excessive
      has returned to normal. The current values of total and free
      memory for the module are sent."
   ::= { cbsModuleResourceTraps 4 }

cbsModuleCPUUtilExceeded NOTIFICATION-TYPE
   OBJECTS { cbsModuleCPUUtil1 }
   STATUS  current
   DESCRIPTION
     "The CPU utilization on one of the processor modules is excessive. The
      current value of the one minute utilization on the CPU module
      that is experinceing excessive load is sent."
   ::= { cbsModuleResourceTraps 5 }

cbsModuleCPUUtilNormal NOTIFICATION-TYPE
   OBJECTS { cbsModuleCPUUtil1 }
   STATUS  current
   DESCRIPTION
     "The CPU utilization on one of the processor modules has returned to
      normal. The current value of the one minute utilization on the CPU module
      that has returned to normal is sent."
   ::= { cbsModuleResourceTraps 6 }

END
