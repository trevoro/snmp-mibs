--
-- Copyright Copyright 2003 Sun Microsystems, Inc. All rights reserved.
--
-- U.S. Government Rights - Commercial software. Government users are subject
-- to the Sun Microsystems, Inc. standard license agreement and applicable
-- provisions of the FAR and its supplements.
--
-- Use is subject to license terms.
--
-- This distribution may include materials developed by third parties. Sun,
-- Sun Microsystems, the Sun logo and Solaris are trademarks or registered
-- trademarks of Sun Microsystems, Inc. in the U.S. and other countries.
--
--

SMA-NOTIFICATION-MIB DEFINITIONS ::= BEGIN

IMPORTS
    MODULE-IDENTITY, OBJECT-TYPE, Counter32, Gauge32, Counter64,
    Integer32, TimeTicks, mib-2,
    NOTIFICATION-TYPE, enterprises           FROM SNMPv2-SMI
    TEXTUAL-CONVENTION, DisplayString,
    PhysAddress, TruthValue, RowStatus,
    TimeStamp, AutonomousType, TestAndIncr   FROM SNMPv2-TC
    MODULE-COMPLIANCE, OBJECT-GROUP,
    NOTIFICATION-GROUP                       FROM SNMPv2-CONF
    snmpTraps                                FROM SNMPv2-MIB
    IANAifType                               FROM IANAifType-MIB;

notifications MODULE-IDENTITY
    LAST-UPDATED "9808040000Z"
    ORGANIZATION "Sun Microsystems Inc."
    CONTACT-INFO
        " Sun Microsystems Inc
	  4150 Network Circle
          Santa Clara, CA 95054
	  e-mail: service@sun.com
	"
	DESCRIPTION
        "This MIB module defines notifications that are
         generated by some monitoring modules loaded on
         System Management Agent (SMA)."
    ::= { sma 3 }

sun OBJECT IDENTIFIER ::= { enterprises 42 } 
products OBJECT IDENTIFIER ::= { sun 2 }
management OBJECT IDENTIFIER ::= { products 2 }
sma OBJECT IDENTIFIER ::= { management 4 }

traps OBJECT IDENTIFIER ::= { notifications 0 }
trapInfo OBJECT IDENTIFIER ::= {  notifications 1 }

statusChange NOTIFICATION-TYPE
OBJECTS { hostName, moduleName, statusOID, statusOIDContext, status, description , dataValue, dataValueType } 
STATUS current 
DESCRIPTION "A statusChange trap signifies that the status of an object has changed." ::= { traps 1 }

hostName OBJECT-TYPE 
SYNTAX       DisplayString (SIZE (0..255))
MAX-ACCESS accessible-for-notify 
STATUS current 
DESCRIPTION "The name of the host on which the event occurred." 
::= { trapInfo 1 }

moduleName OBJECT-TYPE 
SYNTAX       DisplayString (SIZE (0..255))
MAX-ACCESS accessible-for-notify 
STATUS current 
DESCRIPTION "The name of the module on which the event has occured."
::= { trapInfo 2 }

statusOID  OBJECT-TYPE
SYNTAX OBJECT IDENTIFIER
MAX-ACCESS accessible-for-notify
STATUS current
DESCRIPTION "The identification of the object for which the status changed."
::= { trapInfo 3 }

statusOIDContext OBJECT-TYPE
SYNTAX       DisplayString (SIZE (0..255))
MAX-ACCESS accessible-for-notify
STATUS current
DESCRIPTION "The name of context incase the status OID is registered under a particular
             context. If there is no special context, the value for this field will be null."
::= { trapInfo 4 }

status OBJECT-TYPE 
SYNTAX       DisplayString (SIZE (0..255))
MAX-ACCESS accessible-for-notify 
STATUS current 
DESCRIPTION "The current status of the object. One of OK, INFO, WARNING, ERROR." 
::= { trapInfo 5 }

description OBJECT-TYPE 
SYNTAX       DisplayString (SIZE (0..255))
MAX-ACCESS accessible-for-notify 
STATUS current 
DESCRIPTION "The detailed description of the event." 
::= { trapInfo 6 }

dataValue OBJECT-TYPE
SYNTAX       DisplayString (SIZE (0..255))
MAX-ACCESS accessible-for-notify
STATUS current
DESCRIPTION "The current value of the object, that generates the event."
::= { trapInfo 7 }

dataValueType OBJECT-TYPE
SYNTAX INTEGER {
        none(0),
        integer(1),
        octetString(2),
        objectIdentifier(3),
        integer32(4),
        ipAddress(5),
        counter32(6),
        gauge32(7),
        unsigned32(8),
        timeTicks(9),
        opaque(10),
        counter64(11),
        displayString(12),
        physAddress(13),
        macAddress(14),
        truthValue(15),
        testAndIncr(16),
        autonomousType(17),
        variablePointer(18),
        rowPointer(19),
        rowStatus(20),
        storageType(21),
        tDomain(22),
        tAddress(23),
        other(100)
    }
MAX-ACCESS accessible-for-notify
STATUS current
DESCRIPTION "The data type of the value that is present in dataValue varbind"
::= { trapInfo 8 }

END
