--
-- This SMIv2 module has been generated by smidump 0.2-cvs. Do not edit.
--

SONUS-CAS-MIB DEFINITIONS ::= BEGIN

IMPORTS
    Integer32, MODULE-IDENTITY, NOTIFICATION-TYPE, OBJECT-TYPE
        FROM SNMPv2-SMI
    DisplayString, RowStatus
        FROM SNMPv2-TC
    sonusEventClass, sonusEventDescription, sonusEventLevel
        FROM SONUS-COMMON-MIB
    sonusSignallingMIBs
        FROM SONUS-SMI
    SonusAdminAction, SonusAdminState, SonusName, SonusNameReference, 
    SonusServiceState
        FROM SONUS-TC;

sonusCasMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for CAS Service Group Management."
    ::= { sonusSignallingMIBs 5 }


sonusCasMIBObjects OBJECT IDENTIFIER
    ::= { sonusCasMIB 1 }

sonusCasServiceGroup OBJECT IDENTIFIER
    ::= { sonusCasMIBObjects 1 }

sonusCasServiceGroupNextIndex OBJECT-TYPE
    SYNTAX          Integer32
    MAX-ACCESS      read-only
    STATUS          current
    DESCRIPTION     
            "The next valid index to use when creating a new sonusCasServiceGroupAdmnEntry"
    ::= { sonusCasServiceGroup 1 }

sonusCasServiceGroupAdmnTable OBJECT-TYPE
    SYNTAX          SEQUENCE OF SonusCasServiceGroupAdmnEntry
    MAX-ACCESS      not-accessible
    STATUS          current
    DESCRIPTION     
            ""
    ::= { sonusCasServiceGroup 2 }

sonusCasServiceGroupAdmnEntry OBJECT-TYPE
    SYNTAX          SonusCasServiceGroupAdmnEntry
    MAX-ACCESS      not-accessible
    STATUS          current
    DESCRIPTION     
            ""
    INDEX           { sonusCassgServiceGroupIndex }
    ::= { sonusCasServiceGroupAdmnTable 1 }

SonusCasServiceGroupAdmnEntry ::=
    SEQUENCE {
        sonusCassgServiceGroupIndex     Integer32,
        sonusCassgServiceGroupName      SonusName,
        sonusCassgServiceGroupProfileName SonusNameReference,
        sonusCassgServiceGroupTG        SonusNameReference,
        sonusCassgServiceGroupHuntAlgorithm   INTEGER,
        sonusCassgServiceGroupCost      Integer32,
        sonusCassgServiceGroupSignalType INTEGER,
        sonusCassgServiceGroupIngressSSP SonusNameReference,
        sonusCassgServiceGroupEgressSSP SonusNameReference,
        sonusCassgServiceGroupHookflashSSP  SonusNameReference,
        sonusCassgServiceGroupPscSSP    SonusNameReference,
        sonusCassgServiceGroupMaintBusy SonusAdminState,
        sonusCassgServiceGroupAutoBusyThreshold       Integer32,
        sonusCassgServiceGroupRequiresCPTone    SonusAdminState,
        sonusCassgServiceGroupProvidesCPTone    SonusAdminState,
        sonusCassgServiceGroupDTMFProfileName     SonusNameReference,
        sonusCassgServiceGroupMFProfileName   SonusNameReference,
        sonusCassgServiceGroupCPTonePkgName   SonusNameReference,
        sonusCassgServiceGroupMinRxWinkTime   Integer32,
        sonusCassgServiceGroupMaxRxWinkTime   Integer32,
        sonusCassgServiceGroupMinRxFlashTime    Integer32,
        sonusCassgServiceGroupMaxRxFlashTime    Integer32,
        sonusCassgServiceGroupTxWinkTime Integer32,
        sonusCassgServiceGroupTxFlashTime Integer32,
        sonusCassgServiceGroupGuardTime Integer32,
        sonusCassgServiceGroupOperation INTEGER,
        sonusCassgServiceGroupAdminState SonusAdminState,
        sonusCassgServiceGroupMode      SonusServiceState,
        sonusCassgServiceGroupAction    SonusAdminAction,
        sonusCassgServiceGroupTimeout   Integer32,
        sonusCassgServiceGroupAlertToneName   SonusNameReference,
        sonusCassgServiceGroupRowStatus RowStatus,
        sonusCassgServiceGroupDTProfileName   SonusNameReference
    }

sonusCassgServiceGroupIndex OBJECT-TYPE
    SYNTAX          Integer32 (1..128)
    MAX-ACCESS      read-only
    STATUS          current
    DESCRIPTION     
            "The index for the CAS Service Group"
    ::= { sonusCasServiceGroupAdmnEntry 1 }

sonusCassgServiceGroupName OBJECT-TYPE
    SYNTAX          SonusName
    MAX-ACCESS      read-write
    STATUS          current
    DESCRIPTION     
            "The name of this CAS Service Group."
    ::= { sonusCasServiceGroupAdmnEntry 2 }

sonusCassgServiceGroupProfileName OBJECT-TYPE
    SYNTAX          SonusNameReference
    MAX-ACCESS      read-write
    STATUS          current
    DESCRIPTION     
            "The last CAS Service Group profile applied"
    ::= { sonusCasServiceGroupAdmnEntry 3 }

sonusCassgServiceGroupTG OBJECT-TYPE
    SYNTAX          SonusNameReference
    MAX-ACCESS      read-write
    STATUS          current
    DESCRIPTION     
            "The trunk group that the CAS Service Group in contained"
    ::= { sonusCasServiceGroupAdmnEntry 4 }

sonusCassgServiceGroupHuntAlgorithm OBJECT-TYPE
    SYNTAX          INTEGER { bottom2Top(1), top2Bottom(2), 
                        circularBottom2Top(3), circularTop2Bottom(4) }
    MAX-ACCESS      read-write
    STATUS          current
    DESCRIPTION     
            "The method in which channels are hunted for outgoing calls"
    DEFVAL          { bottom2Top }
    ::= { sonusCasServiceGroupAdmnEntry 5 }

sonusCassgServiceGroupCost OBJECT-TYPE
    SYNTAX          Integer32 (0..100)
    MAX-ACCESS      read-write
    STATUS          current
    DESCRIPTION     
            "Relative cost parameter used to augment the hunt algorithm"
    DEFVAL          { 0 }
    ::= { sonusCasServiceGroupAdmnEntry 6 }

sonusCassgServiceGroupSignalType OBJECT-TYPE
    SYNTAX          INTEGER { eM(1), gsFxo(2), gsFxs(3), lsFxo(4), 
                        lsFxs(5), e1Mfr2(6) }
    MAX-ACCESS      read-write
    STATUS          current
    DESCRIPTION     
            "The channel associated signaling type"
    DEFVAL          { eM }
    ::= { sonusCasServiceGroupAdmnEntry 7 }

sonusCassgServiceGroupIngressSSP OBJECT-TYPE
    SYNTAX          SonusNameReference
    MAX-ACCESS      read-write
    STATUS          current
    DESCRIPTION     
            "The SSP which defines the protocol for ingress calls"
    ::= { sonusCasServiceGroupAdmnEntry 8 }

sonusCassgServiceGroupEgressSSP OBJECT-TYPE
    SYNTAX          SonusNameReference
    MAX-ACCESS      read-write
    STATUS          current
    DESCRIPTION     
            "The SSP which defines the protocol for egress calls"
    ::= { sonusCasServiceGroupAdmnEntry 9 }

sonusCassgServiceGroupHookflashSSP OBJECT-TYPE
    SYNTAX          SonusNameReference
    MAX-ACCESS      read-write
    STATUS          current
    DESCRIPTION     
            "The SSP which defines the protocol when a hookflash is received on an egress call"
    ::= { sonusCasServiceGroupAdmnEntry 10 }

sonusCassgServiceGroupPscSSP OBJECT-TYPE
    SYNTAX          SonusNameReference
    MAX-ACCESS      read-write
    STATUS          current
    DESCRIPTION     
            "The SSP which defines Permenant Signal Condition actions to perform to force a call onhook"
    ::= { sonusCasServiceGroupAdmnEntry 11 }

sonusCassgServiceGroupMaintBusy OBJECT-TYPE
    SYNTAX          SonusAdminState
    MAX-ACCESS      read-write
    STATUS          current
    DESCRIPTION     
            "Determines if a channel is taken offhook when it is removed from service"
    DEFVAL          { enabled }
    ::= { sonusCasServiceGroupAdmnEntry 12 }

sonusCassgServiceGroupAutoBusyThreshold OBJECT-TYPE
    SYNTAX          Integer32 (0..255)
    MAX-ACCESS      read-write
    STATUS          current
    DESCRIPTION     
            "Determines the number of signaling errors which can occur before the channel is removed from service"
    DEFVAL          { 0 }
    ::= { sonusCasServiceGroupAdmnEntry 13 }

sonusCassgServiceGroupRequiresCPTone OBJECT-TYPE
    SYNTAX          SonusAdminState
    MAX-ACCESS      read-write
    STATUS          current
    DESCRIPTION     
            "Determines if ingress calls require call progress tones"
    DEFVAL          { disabled }
    ::= { sonusCasServiceGroupAdmnEntry 14 }

sonusCassgServiceGroupProvidesCPTone OBJECT-TYPE
    SYNTAX          SonusAdminState
    MAX-ACCESS      read-write
    STATUS          current
    DESCRIPTION     
            "Determines if the far end switch will provide call progress tones"
    DEFVAL          { disabled }
    ::= { sonusCasServiceGroupAdmnEntry 15 }

sonusCassgServiceGroupDTMFProfileName OBJECT-TYPE
    SYNTAX          SonusNameReference
    MAX-ACCESS      read-write
    STATUS          current
    DESCRIPTION     
            "Name reference to DTMF collection/generation profile"
    ::= { sonusCasServiceGroupAdmnEntry 16 }

sonusCassgServiceGroupMFProfileName OBJECT-TYPE
    SYNTAX          SonusNameReference
    MAX-ACCESS      read-write
    STATUS          current
    DESCRIPTION     
            "Name reference to MF collection/generation profile"
    ::= { sonusCasServiceGroupAdmnEntry 17 }

sonusCassgServiceGroupCPTonePkgName OBJECT-TYPE
    SYNTAX          SonusNameReference
    MAX-ACCESS      read-write
    STATUS          current
    DESCRIPTION     
            "Name reference to Call Progress tone package"
    ::= { sonusCasServiceGroupAdmnEntry 18 }

sonusCassgServiceGroupMinRxWinkTime OBJECT-TYPE
    SYNTAX          Integer32 (100..800)
    MAX-ACCESS      read-write
    STATUS          current
    DESCRIPTION     
            "Minimum duration for a receive wink event"
    DEFVAL          { 100 }
    ::= { sonusCasServiceGroupAdmnEntry 19 }

sonusCassgServiceGroupMaxRxWinkTime OBJECT-TYPE
    SYNTAX          Integer32 (100..800)
    MAX-ACCESS      read-write
    STATUS          current
    DESCRIPTION     
            "Maximum duration for a receive wink event"
    DEFVAL          { 700 }
    ::= { sonusCasServiceGroupAdmnEntry 20 }

sonusCassgServiceGroupMinRxFlashTime OBJECT-TYPE
    SYNTAX          Integer32 (300..1100)
    MAX-ACCESS      read-write
    STATUS          current
    DESCRIPTION     
            "Minimum duration for a receive flash event"
    DEFVAL          { 300 }
    ::= { sonusCasServiceGroupAdmnEntry 21 }

sonusCassgServiceGroupMaxRxFlashTime OBJECT-TYPE
    SYNTAX          Integer32 (300..1100)
    MAX-ACCESS      read-write
    STATUS          current
    DESCRIPTION     
            "Maximum duration for a receive flash event"
    DEFVAL          { 700 }
    ::= { sonusCasServiceGroupAdmnEntry 22 }

sonusCassgServiceGroupTxWinkTime OBJECT-TYPE
    SYNTAX          Integer32 (100..800)
    MAX-ACCESS      read-write
    STATUS          current
    DESCRIPTION     
            "Duration for a transmit wink"
    DEFVAL          { 200 }
    ::= { sonusCasServiceGroupAdmnEntry 23 }

sonusCassgServiceGroupTxFlashTime OBJECT-TYPE
    SYNTAX          Integer32 (300..1100)
    MAX-ACCESS      read-write
    STATUS          current
    DESCRIPTION     
            "Duration for a transmit flash"
    DEFVAL          { 500 }
    ::= { sonusCasServiceGroupAdmnEntry 24 }

sonusCassgServiceGroupGuardTime OBJECT-TYPE
    SYNTAX          Integer32 (100..1500)
    MAX-ACCESS      read-write
    STATUS          current
    DESCRIPTION     
            "Duration for the line to clear after disconnect"
    DEFVAL          { 700 }
    ::= { sonusCasServiceGroupAdmnEntry 25 }

sonusCassgServiceGroupOperation OBJECT-TYPE
    SYNTAX          INTEGER { noAction(1), resetStats(2) }
    MAX-ACCESS      read-write
    STATUS          current
    DESCRIPTION     
            "This objects always reads as noAction(1).  Setting this object to
             resetStats(2) causes the statistics for the channels in the Service Group to be reset."
    DEFVAL          { noAction }
    ::= { sonusCasServiceGroupAdmnEntry 26 }

sonusCassgServiceGroupAdminState OBJECT-TYPE
    SYNTAX          SonusAdminState
    MAX-ACCESS      read-write
    STATUS          current
    DESCRIPTION     
            "The admin state of the CAS Service Group"
    DEFVAL          { disabled }
    ::= { sonusCasServiceGroupAdmnEntry 27 }

sonusCassgServiceGroupMode OBJECT-TYPE
    SYNTAX          SonusServiceState
    MAX-ACCESS      read-write
    STATUS          current
    DESCRIPTION     
            "The mode of operation of channels in the CAS Service Group"
    DEFVAL          { inService }
    ::= { sonusCasServiceGroupAdmnEntry 28 }

sonusCassgServiceGroupAction OBJECT-TYPE
    SYNTAX          SonusAdminAction
    MAX-ACCESS      read-write
    STATUS          current
    DESCRIPTION     
            "The action taken on the channels in the CAS Service Group"
    DEFVAL          { force }
    ::= { sonusCasServiceGroupAdmnEntry 29 }

sonusCassgServiceGroupTimeout OBJECT-TYPE
    SYNTAX          Integer32 (1..1440)
    MAX-ACCESS      read-write
    STATUS          current
    DESCRIPTION     
            "The timeout value in minutes for dryup action on the CAS Service Group"
    DEFVAL          { 1 }
    ::= { sonusCasServiceGroupAdmnEntry 30 }

sonusCassgServiceGroupAlertToneName OBJECT-TYPE
    SYNTAX          SonusNameReference
    MAX-ACCESS      read-write
    STATUS          current
    DESCRIPTION     
            "Specifies a named reference to a tone to play for ring back."
    ::= { sonusCasServiceGroupAdmnEntry 31 }

sonusCassgServiceGroupRowStatus OBJECT-TYPE
    SYNTAX          RowStatus
    MAX-ACCESS      read-write
    STATUS          current
    DESCRIPTION     
            ""
    ::= { sonusCasServiceGroupAdmnEntry 32 }

sonusCassgServiceGroupDTProfileName OBJECT-TYPE
    SYNTAX          SonusNameReference
    MAX-ACCESS      read-write
    STATUS          current
    DESCRIPTION     
            "Name reference to Disconnect Treatment profile"
    ::= { sonusCasServiceGroupAdmnEntry 33 }

sonusCasSvcGrpProfileAdmn OBJECT IDENTIFIER
    ::= { sonusCasMIBObjects 2 }

sonusCasSvcGrpProfileNextIndex OBJECT-TYPE
    SYNTAX          Integer32
    MAX-ACCESS      read-only
    STATUS          current
    DESCRIPTION     
            "The next valid index to use when creating a new sonusCasSvcGrpProfileAdmnEntry"
    ::= { sonusCasSvcGrpProfileAdmn 1 }

sonusCasSvcGrpProfileAdmnTable OBJECT-TYPE
    SYNTAX          SEQUENCE OF SonusCasSvcGrpProfileAdmnEntry
    MAX-ACCESS      not-accessible
    STATUS          current
    DESCRIPTION     
            ""
    ::= { sonusCasSvcGrpProfileAdmn 2 }

sonusCasSvcGrpProfileAdmnEntry OBJECT-TYPE
    SYNTAX          SonusCasSvcGrpProfileAdmnEntry
    MAX-ACCESS      not-accessible
    STATUS          current
    DESCRIPTION     
            ""
    INDEX           { sonusCassgSvcGrpProfileIndex }
    ::= { sonusCasSvcGrpProfileAdmnTable 1 }

SonusCasSvcGrpProfileAdmnEntry ::=
    SEQUENCE {
        sonusCassgSvcGrpProfileIndex    Integer32,
        sonusCassgSvcGrpProfileName     SonusName,
        sonusCassgSvcGrpProfileTG       SonusNameReference,
        sonusCassgSvcGrpProfileHuntAlgorithm    INTEGER,
        sonusCassgSvcGrpProfileCost     Integer32,
        sonusCassgSvcGrpProfileSignalType INTEGER,
        sonusCassgSvcGrpProfileIngressSSP SonusNameReference,
        sonusCassgSvcGrpProfileEgressSSP SonusNameReference,
        sonusCassgSvcGrpProfileHookflashSSP   SonusNameReference,
        sonusCassgSvcGrpProfilePscSSP   SonusNameReference,
        sonusCassgSvcGrpProfileMaintBusy SonusAdminState,
        sonusCassgSvcGrpProfileAutoBusyThreshold        Integer32,
        sonusCassgSvcGrpProfileRequiresCPTone     SonusAdminState,
        sonusCassgSvcGrpProfileProvidesCPTone     SonusAdminState,
        sonusCassgSvcGrpProfileDTMFProfileName      SonusNameReference,
        sonusCassgSvcGrpProfileMFProfileName    SonusNameReference,
        sonusCassgSvcGrpProfileCPTonePkgName    SonusNameReference,
        sonusCassgSvcGrpProfileMinRxWinkTime    Integer32,
        sonusCassgSvcGrpProfileMaxRxWinkTime    Integer32,
        sonusCassgSvcGrpProfileMinRxFlashTime     Integer32,
        sonusCassgSvcGrpProfileMaxRxFlashTime     Integer32,
        sonusCassgSvcGrpProfileTxWinkTime Integer32,
        sonusCassgSvcGrpProfileTxFlashTime  Integer32,
        sonusCassgSvcGrpProfileGuardTime Integer32,
        sonusCassgSvcGrpProfileAdminState SonusAdminState,
        sonusCassgSvcGrpProfileAlertToneName    SonusNameReference,
        sonusCassgSvcGrpProfileRowStatus RowStatus,
        sonusCassgSvcGrpProfileDTProfileName    SonusNameReference
    }

sonusCassgSvcGrpProfileIndex OBJECT-TYPE
    SYNTAX          Integer32 (1..128)
    MAX-ACCESS      read-only
    STATUS          current
    DESCRIPTION     
            "The index for the CAS Service Group Profile"
    ::= { sonusCasSvcGrpProfileAdmnEntry 1 }

sonusCassgSvcGrpProfileName OBJECT-TYPE
    SYNTAX          SonusName
    MAX-ACCESS      read-write
    STATUS          current
    DESCRIPTION     
            "The name of this CAS Service Group profile."
    ::= { sonusCasSvcGrpProfileAdmnEntry 2 }

sonusCassgSvcGrpProfileTG OBJECT-TYPE
    SYNTAX          SonusNameReference
    MAX-ACCESS      read-write
    STATUS          current
    DESCRIPTION     
            "The trunk group that the CAS Service Group in contained"
    ::= { sonusCasSvcGrpProfileAdmnEntry 3 }

sonusCassgSvcGrpProfileHuntAlgorithm OBJECT-TYPE
    SYNTAX          INTEGER { bottom2Top(1), top2Bottom(2), 
                        circularBottom2Top(3), circularTop2Bottom(4) }
    MAX-ACCESS      read-write
    STATUS          current
    DESCRIPTION     
            "The method in which channels are hunted for outgoing calls"
    DEFVAL          { bottom2Top }
    ::= { sonusCasSvcGrpProfileAdmnEntry 4 }

sonusCassgSvcGrpProfileCost OBJECT-TYPE
    SYNTAX          Integer32 (0..100)
    MAX-ACCESS      read-write
    STATUS          current
    DESCRIPTION     
            "Relative cost parameter used to augment the hunt algorithm"
    DEFVAL          { 0 }
    ::= { sonusCasSvcGrpProfileAdmnEntry 5 }

sonusCassgSvcGrpProfileSignalType OBJECT-TYPE
    SYNTAX          INTEGER { eM(1), gsFxo(2), gsFxs(3), lsFxo(4), 
                        lsFxs(5), e1Mfr2(6) }
    MAX-ACCESS      read-write
    STATUS          current
    DESCRIPTION     
            "The channel associated signaling type"
    DEFVAL          { eM }
    ::= { sonusCasSvcGrpProfileAdmnEntry 6 }

sonusCassgSvcGrpProfileIngressSSP OBJECT-TYPE
    SYNTAX          SonusNameReference
    MAX-ACCESS      read-write
    STATUS          current
    DESCRIPTION     
            "The SSP which defines the protocol for ingress calls"
    ::= { sonusCasSvcGrpProfileAdmnEntry 7 }

sonusCassgSvcGrpProfileEgressSSP OBJECT-TYPE
    SYNTAX          SonusNameReference
    MAX-ACCESS      read-write
    STATUS          current
    DESCRIPTION     
            "The SSP which defines the protocol for egress calls"
    ::= { sonusCasSvcGrpProfileAdmnEntry 8 }

sonusCassgSvcGrpProfileHookflashSSP OBJECT-TYPE
    SYNTAX          SonusNameReference
    MAX-ACCESS      read-write
    STATUS          current
    DESCRIPTION     
            "The SSP which defines the protocol when a hookflash is received on an egress call"
    ::= { sonusCasSvcGrpProfileAdmnEntry 9 }

sonusCassgSvcGrpProfilePscSSP OBJECT-TYPE
    SYNTAX          SonusNameReference
    MAX-ACCESS      read-write
    STATUS          current
    DESCRIPTION     
            "The SSP which defines Permenant Signal Condition actions to perform to force a call onhook"
    ::= { sonusCasSvcGrpProfileAdmnEntry 10 }

sonusCassgSvcGrpProfileMaintBusy OBJECT-TYPE
    SYNTAX          SonusAdminState
    MAX-ACCESS      read-write
    STATUS          current
    DESCRIPTION     
            "Determines if a channel is taken offhook when it is removed from service"
    DEFVAL          { enabled }
    ::= { sonusCasSvcGrpProfileAdmnEntry 11 }

sonusCassgSvcGrpProfileAutoBusyThreshold OBJECT-TYPE
    SYNTAX          Integer32 (0..255)
    MAX-ACCESS      read-write
    STATUS          current
    DESCRIPTION     
            "Determines the number of signaling errors which can occur before the channel is removed from service"
    DEFVAL          { 0 }
    ::= { sonusCasSvcGrpProfileAdmnEntry 12 }

sonusCassgSvcGrpProfileRequiresCPTone OBJECT-TYPE
    SYNTAX          SonusAdminState
    MAX-ACCESS      read-write
    STATUS          current
    DESCRIPTION     
            "Determines if ingress calls require call progress tones"
    DEFVAL          { disabled }
    ::= { sonusCasSvcGrpProfileAdmnEntry 13 }

sonusCassgSvcGrpProfileProvidesCPTone OBJECT-TYPE
    SYNTAX          SonusAdminState
    MAX-ACCESS      read-write
    STATUS          current
    DESCRIPTION     
            "Determines if the far end switch will provide call progress tones"
    DEFVAL          { disabled }
    ::= { sonusCasSvcGrpProfileAdmnEntry 14 }

sonusCassgSvcGrpProfileDTMFProfileName OBJECT-TYPE
    SYNTAX          SonusNameReference
    MAX-ACCESS      read-write
    STATUS          current
    DESCRIPTION     
            "Name reference to DTMF collection/generation profile"
    ::= { sonusCasSvcGrpProfileAdmnEntry 15 }

sonusCassgSvcGrpProfileMFProfileName OBJECT-TYPE
    SYNTAX          SonusNameReference
    MAX-ACCESS      read-write
    STATUS          current
    DESCRIPTION     
            "Name reference to MF collection/generation profile"
    ::= { sonusCasSvcGrpProfileAdmnEntry 16 }

sonusCassgSvcGrpProfileCPTonePkgName OBJECT-TYPE
    SYNTAX          SonusNameReference
    MAX-ACCESS      read-write
    STATUS          current
    DESCRIPTION     
            "Name reference to Call Progress tone package"
    ::= { sonusCasSvcGrpProfileAdmnEntry 17 }

sonusCassgSvcGrpProfileMinRxWinkTime OBJECT-TYPE
    SYNTAX          Integer32 (100..800)
    MAX-ACCESS      read-write
    STATUS          current
    DESCRIPTION     
            "Minimum duration for a receive wink event"
    DEFVAL          { 100 }
    ::= { sonusCasSvcGrpProfileAdmnEntry 18 }

sonusCassgSvcGrpProfileMaxRxWinkTime OBJECT-TYPE
    SYNTAX          Integer32 (100..800)
    MAX-ACCESS      read-write
    STATUS          current
    DESCRIPTION     
            "Maximum duration for a receive wink event"
    DEFVAL          { 700 }
    ::= { sonusCasSvcGrpProfileAdmnEntry 19 }

sonusCassgSvcGrpProfileMinRxFlashTime OBJECT-TYPE
    SYNTAX          Integer32 (300..1100)
    MAX-ACCESS      read-write
    STATUS          current
    DESCRIPTION     
            "Minimum duration for a receive flash event"
    DEFVAL          { 300 }
    ::= { sonusCasSvcGrpProfileAdmnEntry 20 }

sonusCassgSvcGrpProfileMaxRxFlashTime OBJECT-TYPE
    SYNTAX          Integer32 (300..1100)
    MAX-ACCESS      read-write
    STATUS          current
    DESCRIPTION     
            "Maximum duration for a receive flash event"
    DEFVAL          { 700 }
    ::= { sonusCasSvcGrpProfileAdmnEntry 21 }

sonusCassgSvcGrpProfileTxWinkTime OBJECT-TYPE
    SYNTAX          Integer32 (100..800)
    MAX-ACCESS      read-write
    STATUS          current
    DESCRIPTION     
            "Duration for a transmit wink"
    DEFVAL          { 200 }
    ::= { sonusCasSvcGrpProfileAdmnEntry 22 }

sonusCassgSvcGrpProfileTxFlashTime OBJECT-TYPE
    SYNTAX          Integer32 (300..1100)
    MAX-ACCESS      read-write
    STATUS          current
    DESCRIPTION     
            "Duration for a transmit flash"
    DEFVAL          { 500 }
    ::= { sonusCasSvcGrpProfileAdmnEntry 23 }

sonusCassgSvcGrpProfileGuardTime OBJECT-TYPE
    SYNTAX          Integer32 (100..1500)
    MAX-ACCESS      read-write
    STATUS          current
    DESCRIPTION     
            "Duration for the line to clear after disconnect"
    DEFVAL          { 700 }
    ::= { sonusCasSvcGrpProfileAdmnEntry 24 }

sonusCassgSvcGrpProfileAdminState OBJECT-TYPE
    SYNTAX          SonusAdminState
    MAX-ACCESS      read-write
    STATUS          current
    DESCRIPTION     
            "The admin state of the CAS Service Group"
    DEFVAL          { disabled }
    ::= { sonusCasSvcGrpProfileAdmnEntry 25 }

sonusCassgSvcGrpProfileAlertToneName OBJECT-TYPE
    SYNTAX          SonusNameReference
    MAX-ACCESS      read-write
    STATUS          current
    DESCRIPTION     
            "Specifies a named reference to a tone to play for ring back"
    ::= { sonusCasSvcGrpProfileAdmnEntry 26 }

sonusCassgSvcGrpProfileRowStatus OBJECT-TYPE
    SYNTAX          RowStatus
    MAX-ACCESS      read-write
    STATUS          current
    DESCRIPTION     
            ""
    ::= { sonusCasSvcGrpProfileAdmnEntry 27 }

sonusCassgSvcGrpProfileDTProfileName OBJECT-TYPE
    SYNTAX          SonusNameReference
    MAX-ACCESS      read-write
    STATUS          current
    DESCRIPTION     
            "Name reference to Disconnect Treatment profile"
    ::= { sonusCasSvcGrpProfileAdmnEntry 28 }

sonusCasChannelAdmnTable OBJECT-TYPE
    SYNTAX          SEQUENCE OF SonusCasChannelAdmnEntry
    MAX-ACCESS      not-accessible
    STATUS          current
    DESCRIPTION     
            ""
    ::= { sonusCasMIBObjects 3 }

sonusCasChannelAdmnEntry OBJECT-TYPE
    SYNTAX          SonusCasChannelAdmnEntry
    MAX-ACCESS      not-accessible
    STATUS          current
    DESCRIPTION     
            ""
    INDEX           { sonusCassgChannelServiceIndex, 
                      sonusCassgChannelShelfIndex, 
                      sonusCassgChannelSlotIndex, 
                      sonusCassgChannelPortIndex, 
                      sonusCassgChannelDs3Index, 
                      sonusCassgChannelDs1Index, sonusCassgChannelIndex }
    ::= { sonusCasChannelAdmnTable 1 }

SonusCasChannelAdmnEntry ::=
    SEQUENCE {
        sonusCassgChannelServiceIndex   Integer32,
        sonusCassgChannelShelfIndex     Integer32,
        sonusCassgChannelSlotIndex      Integer32,
        sonusCassgChannelPortIndex      Integer32,
        sonusCassgChannelDs3Index       Integer32,
        sonusCassgChannelDs1Index       Integer32,
        sonusCassgChannelIndex          Integer32,
        sonusCassgChannelCircuitProfileName   SonusNameReference,
        sonusCassgChannelDirection      INTEGER,
        sonusCassgChannelMode           SonusServiceState,
        sonusCassgChannelAction         SonusAdminAction,
        sonusCassgChannelTimeout        Integer32,
        sonusCassgChannelAdminState     SonusAdminState,
        sonusCassgChannelRowStatus      RowStatus
    }

sonusCassgChannelServiceIndex OBJECT-TYPE
    SYNTAX          Integer32
    MAX-ACCESS      read-only
    STATUS          current
    DESCRIPTION     
            "The index of the CAS Service Group in which the channel is contained"
    ::= { sonusCasChannelAdmnEntry 1 }

sonusCassgChannelShelfIndex OBJECT-TYPE
    SYNTAX          Integer32
    MAX-ACCESS      read-only
    STATUS          current
    DESCRIPTION     
            "The shelf in which the channel is contained"
    ::= { sonusCasChannelAdmnEntry 2 }

sonusCassgChannelSlotIndex OBJECT-TYPE
    SYNTAX          Integer32
    MAX-ACCESS      read-only
    STATUS          current
    DESCRIPTION     
            "The slot in which the channel is contained"
    ::= { sonusCasChannelAdmnEntry 3 }

sonusCassgChannelPortIndex OBJECT-TYPE
    SYNTAX          Integer32
    MAX-ACCESS      read-only
    STATUS          current
    DESCRIPTION     
            "The port in which the channel is contained"
    ::= { sonusCasChannelAdmnEntry 4 }

sonusCassgChannelDs3Index OBJECT-TYPE
    SYNTAX          Integer32
    MAX-ACCESS      read-only
    STATUS          current
    DESCRIPTION     
            "The DS3 in which the channel is contained"
    ::= { sonusCasChannelAdmnEntry 5 }

sonusCassgChannelDs1Index OBJECT-TYPE
    SYNTAX          Integer32
    MAX-ACCESS      read-only
    STATUS          current
    DESCRIPTION     
            "The DS1 in which the channel is contained"
    ::= { sonusCasChannelAdmnEntry 6 }

sonusCassgChannelIndex OBJECT-TYPE
    SYNTAX          Integer32 (1..32)
    MAX-ACCESS      read-only
    STATUS          current
    DESCRIPTION     
            "The relative channel number within the port"
    ::= { sonusCasChannelAdmnEntry 7 }

sonusCassgChannelCircuitProfileName OBJECT-TYPE
    SYNTAX          SonusNameReference
    MAX-ACCESS      read-write
    STATUS          current
    DESCRIPTION     
            "Name reference to the circuit profile"
    ::= { sonusCasChannelAdmnEntry 8 }

sonusCassgChannelDirection OBJECT-TYPE
    SYNTAX          INTEGER { twoWay(1), oneWayIn(2), oneWayOut(3) }
    MAX-ACCESS      read-write
    STATUS          current
    DESCRIPTION     
            "Direction of call traffic allowed on the channel"
    DEFVAL          { twoWay }
    ::= { sonusCasChannelAdmnEntry 9 }

sonusCassgChannelMode OBJECT-TYPE
    SYNTAX          SonusServiceState
    MAX-ACCESS      read-write
    STATUS          current
    DESCRIPTION     
            "The mode of operation of the channel"
    DEFVAL          { inService }
    ::= { sonusCasChannelAdmnEntry 10 }

sonusCassgChannelAction OBJECT-TYPE
    SYNTAX          SonusAdminAction
    MAX-ACCESS      read-write
    STATUS          current
    DESCRIPTION     
            "The action taken on the channel"
    DEFVAL          { dryUp }
    ::= { sonusCasChannelAdmnEntry 11 }

sonusCassgChannelTimeout OBJECT-TYPE
    SYNTAX          Integer32 (1..1440)
    MAX-ACCESS      read-write
    STATUS          current
    DESCRIPTION     
            "The timeout in minutes for dryup action on the channel"
    ::= { sonusCasChannelAdmnEntry 12 }

sonusCassgChannelAdminState OBJECT-TYPE
    SYNTAX          SonusAdminState
    MAX-ACCESS      read-write
    STATUS          current
    DESCRIPTION     
            "The administrative state of the object.  The object must
             be disabled in order to modify other objects in this row."
    DEFVAL          { disabled }
    ::= { sonusCasChannelAdmnEntry 13 }

sonusCassgChannelRowStatus OBJECT-TYPE
    SYNTAX          RowStatus
    MAX-ACCESS      read-write
    STATUS          current
    DESCRIPTION     
            ""
    ::= { sonusCasChannelAdmnEntry 14 }

sonusCasChannelStatTable OBJECT-TYPE
    SYNTAX          SEQUENCE OF SonusCasChannelStatEntry
    MAX-ACCESS      not-accessible
    STATUS          current
    DESCRIPTION     
            ""
    ::= { sonusCasMIBObjects 4 }

sonusCasChannelStatEntry OBJECT-TYPE
    SYNTAX          SonusCasChannelStatEntry
    MAX-ACCESS      not-accessible
    STATUS          current
    DESCRIPTION     
            ""
    INDEX           { sonusCassgChannelStatServiceIndex, 
                      sonusCassgChannelStatShelfIndex, 
                      sonusCassgChannelStatSlotIndex, 
                      sonusCassgChannelStatPortIndex, 
                      sonusCassgChannelStatIndex }
    ::= { sonusCasChannelStatTable 1 }

SonusCasChannelStatEntry ::=
    SEQUENCE {
        sonusCassgChannelStatServiceIndex Integer32,
        sonusCassgChannelStatShelfIndex Integer32,
        sonusCassgChannelStatSlotIndex  Integer32,
        sonusCassgChannelStatPortIndex  Integer32,
        sonusCassgChannelStatIndex      Integer32,
        sonusCassgChannelStatUsage      INTEGER,
        sonusCassgChannelStatLocalMaint INTEGER,
        sonusCassgChannelStatLocalHw    INTEGER,
        sonusCassgChannelStatRemoteMaint INTEGER,
        sonusCassgChannelStatIngressAttempts    Integer32,
        sonusCassgChannelStatIngressFailures    Integer32,
        sonusCassgChannelStatEgressAttempts   Integer32,
        sonusCassgChannelStatEgressFailures   Integer32,
        sonusCassgChannelStatMakeBusyFailures     Integer32,
        sonusCassgChannelStatIngressCompletions       Integer32,
        sonusCassgChannelStatEgressCompletions      Integer32
    }

sonusCassgChannelStatServiceIndex OBJECT-TYPE
    SYNTAX          Integer32
    MAX-ACCESS      read-only
    STATUS          current
    DESCRIPTION     
            "The index of the CAS Service Group in which the channel is contained"
    ::= { sonusCasChannelStatEntry 1 }

sonusCassgChannelStatShelfIndex OBJECT-TYPE
    SYNTAX          Integer32
    MAX-ACCESS      read-only
    STATUS          current
    DESCRIPTION     
            "The shelf in which the channel is contained"
    ::= { sonusCasChannelStatEntry 2 }

sonusCassgChannelStatSlotIndex OBJECT-TYPE
    SYNTAX          Integer32
    MAX-ACCESS      read-only
    STATUS          current
    DESCRIPTION     
            "The slot in which the channel is contained"
    ::= { sonusCasChannelStatEntry 3 }

sonusCassgChannelStatPortIndex OBJECT-TYPE
    SYNTAX          Integer32
    MAX-ACCESS      read-only
    STATUS          current
    DESCRIPTION     
            "The port in which the channel is contained"
    ::= { sonusCasChannelStatEntry 4 }

sonusCassgChannelStatIndex OBJECT-TYPE
    SYNTAX          Integer32
    MAX-ACCESS      read-only
    STATUS          current
    DESCRIPTION     
            "The relative channel number within the por"
    ::= { sonusCasChannelStatEntry 5 }

sonusCassgChannelStatUsage OBJECT-TYPE
    SYNTAX          INTEGER { unequipped(1), idle(2), inBusy(3), 
                        outBusy(4), transientSetup(5), 
                        transientRelease(6) }
    MAX-ACCESS      read-only
    STATUS          current
    DESCRIPTION     
            "The usage state of the channel"
    ::= { sonusCasChannelStatEntry 6 }

sonusCassgChannelStatLocalMaint OBJECT-TYPE
    SYNTAX          INTEGER { outOfServiceManual(1), outOfServiceAuto(2), 
                        inService(3) }
    MAX-ACCESS      read-only
    STATUS          current
    DESCRIPTION     
            "The local maintenance state of the channel"
    ::= { sonusCasChannelStatEntry 7 }

sonusCassgChannelStatLocalHw OBJECT-TYPE
    SYNTAX          INTEGER { outOfService(1), inService(2) }
    MAX-ACCESS      read-only
    STATUS          current
    DESCRIPTION     
            "The local hardware state of the channel"
    ::= { sonusCasChannelStatEntry 8 }

sonusCassgChannelStatRemoteMaint OBJECT-TYPE
    SYNTAX          INTEGER { outOfService(1), inService(2) }
    MAX-ACCESS      read-only
    STATUS          current
    DESCRIPTION     
            "The remote status of the channel"
    ::= { sonusCasChannelStatEntry 9 }

sonusCassgChannelStatIngressAttempts OBJECT-TYPE
    SYNTAX          Integer32
    MAX-ACCESS      read-only
    STATUS          current
    DESCRIPTION     
            "The number of incoming call attempts"
    ::= { sonusCasChannelStatEntry 10 }

sonusCassgChannelStatIngressFailures OBJECT-TYPE
    SYNTAX          Integer32
    MAX-ACCESS      read-only
    STATUS          current
    DESCRIPTION     
            "The number of incoming call failures"
    ::= { sonusCasChannelStatEntry 11 }

sonusCassgChannelStatEgressAttempts OBJECT-TYPE
    SYNTAX          Integer32
    MAX-ACCESS      read-only
    STATUS          current
    DESCRIPTION     
            "The number of outgoing call attempts"
    ::= { sonusCasChannelStatEntry 12 }

sonusCassgChannelStatEgressFailures OBJECT-TYPE
    SYNTAX          Integer32
    MAX-ACCESS      read-only
    STATUS          current
    DESCRIPTION     
            "The number of outgoing call failures"
    ::= { sonusCasChannelStatEntry 13 }

sonusCassgChannelStatMakeBusyFailures OBJECT-TYPE
    SYNTAX          Integer32
    MAX-ACCESS      read-only
    STATUS          current
    DESCRIPTION     
            "The number of failures which are considered in the auto busy threshold processing"
    ::= { sonusCasChannelStatEntry 14 }

sonusCassgChannelStatIngressCompletions OBJECT-TYPE
    SYNTAX          Integer32
    MAX-ACCESS      read-only
    STATUS          current
    DESCRIPTION     
            "The number of incoming calls which have completed the Ingress SSP"
    ::= { sonusCasChannelStatEntry 15 }

sonusCassgChannelStatEgressCompletions OBJECT-TYPE
    SYNTAX          Integer32
    MAX-ACCESS      read-only
    STATUS          current
    DESCRIPTION     
            "The number of outgoing calls which have completed the Egress SSP"
    ::= { sonusCasChannelStatEntry 16 }

sonusCasCollectionProfileAdmn OBJECT IDENTIFIER
    ::= { sonusCasMIBObjects 5 }

sonusCasCollectionProfileNextIndex OBJECT-TYPE
    SYNTAX          Integer32
    MAX-ACCESS      read-only
    STATUS          current
    DESCRIPTION     
            "The next valid index to use when creating a new sonusCasCollectionProfileAdmnEntry"
    ::= { sonusCasCollectionProfileAdmn 1 }

sonusCasCollectionProfileAdmnTable OBJECT-TYPE
    SYNTAX          SEQUENCE OF SonusCasCollectionProfileAdmnEntry
    MAX-ACCESS      not-accessible
    STATUS          current
    DESCRIPTION     
            ""
    ::= { sonusCasCollectionProfileAdmn 2 }

sonusCasCollectionProfileAdmnEntry OBJECT-TYPE
    SYNTAX          SonusCasCollectionProfileAdmnEntry
    MAX-ACCESS      not-accessible
    STATUS          current
    DESCRIPTION     
            ""
    INDEX           { sonusCassgCollectProfileIndex }
    ::= { sonusCasCollectionProfileAdmnTable 1 }

SonusCasCollectionProfileAdmnEntry ::=
    SEQUENCE {
        sonusCassgCollectProfileIndex   Integer32,
        sonusCassgCollectProfileName    SonusName,
        sonusCassgCollectProfileCollectId INTEGER,
        sonusCassgCollectProfileCollectType   INTEGER,
        sonusCassgCollectProfileMinDigits Integer32,
        sonusCassgCollectProfileMaxDigits Integer32,
        sonusCassgCollectProfileFirstDigitTime      Integer32,
        sonusCassgCollectProfileInterDigitTime      Integer32,
        sonusCassgCollectProfileFieldTime Integer32,
        sonusCassgCollectProfileTermDigit INTEGER,
        sonusCassgCollectProfileRestartDigit    DisplayString,
        sonusCassgCollectProfileReinputDigit    DisplayString,
        sonusCassgCollectProfileReportDigits    Integer32,
        sonusCassgCollectProfileFirstDigitQuiet       SonusAdminState,
        sonusCassgCollectProfileAnnouncementPrompt          Integer32,
        sonusCassgCollectProfileTonePrompt  DisplayString,
        sonusCassgCollectProfileRowStatus RowStatus
    }

sonusCassgCollectProfileIndex OBJECT-TYPE
    SYNTAX          Integer32
    MAX-ACCESS      read-only
    STATUS          current
    DESCRIPTION     
            "The index of the collection profile"
    ::= { sonusCasCollectionProfileAdmnEntry 1 }

sonusCassgCollectProfileName OBJECT-TYPE
    SYNTAX          SonusName
    MAX-ACCESS      read-write
    STATUS          current
    DESCRIPTION     
            "The name of the collection profile"
    ::= { sonusCasCollectionProfileAdmnEntry 2 }

sonusCassgCollectProfileCollectId OBJECT-TYPE
    SYNTAX          INTEGER { calledParty(1), callingParty(2), ani(3), 
                        iani(4), iiani(5), dnis(6), carrierId(7), 
                        internationalCountryCode(8) }
    MAX-ACCESS      read-write
    STATUS          current
    DESCRIPTION     
            "Identifies the collection and where to store digits"
    DEFVAL          { calledParty }
    ::= { sonusCasCollectionProfileAdmnEntry 3 }

sonusCassgCollectProfileCollectType OBJECT-TYPE
    SYNTAX          INTEGER { dtmf(1), mf(2) }
    MAX-ACCESS      read-write
    STATUS          current
    DESCRIPTION     
            "Type of digits to be collected"
    DEFVAL          { dtmf }
    ::= { sonusCasCollectionProfileAdmnEntry 4 }

sonusCassgCollectProfileMinDigits OBJECT-TYPE
    SYNTAX          Integer32 (0..30)
    MAX-ACCESS      read-write
    STATUS          current
    DESCRIPTION     
            "Minimum number of digits to collect"
    DEFVAL          { 0 }
    ::= { sonusCasCollectionProfileAdmnEntry 5 }

sonusCassgCollectProfileMaxDigits OBJECT-TYPE
    SYNTAX          Integer32 (1..30)
    MAX-ACCESS      read-write
    STATUS          current
    DESCRIPTION     
            "Maximum number of digits to collect"
    DEFVAL          { 1 }
    ::= { sonusCasCollectionProfileAdmnEntry 6 }

sonusCassgCollectProfileFirstDigitTime OBJECT-TYPE
    SYNTAX          Integer32 (0..30000)
    MAX-ACCESS      read-write
    STATUS          current
    DESCRIPTION     
            "Duration in milliseconds to allow for the first digit"
    DEFVAL          { 0 }
    ::= { sonusCasCollectionProfileAdmnEntry 7 }

sonusCassgCollectProfileInterDigitTime OBJECT-TYPE
    SYNTAX          Integer32 (0..30000)
    MAX-ACCESS      read-write
    STATUS          current
    DESCRIPTION     
            "Duration in milliseconds allowed between digits"
    DEFVAL          { 0 }
    ::= { sonusCasCollectionProfileAdmnEntry 8 }

sonusCassgCollectProfileFieldTime OBJECT-TYPE
    SYNTAX          Integer32 (0..30000)
    MAX-ACCESS      read-write
    STATUS          current
    DESCRIPTION     
            "The duration in milliseconds allowed for the complete collection"
    DEFVAL          { 0 }
    ::= { sonusCasCollectionProfileAdmnEntry 9 }

sonusCassgCollectProfileTermDigit OBJECT-TYPE
    SYNTAX          INTEGER { none(1), star(2), pound(3), dtmfA(4), 
                        dtmfB(5), dtmfC(6), dtmfD(7) }
    MAX-ACCESS      read-write
    STATUS          current
    DESCRIPTION     
            "Specifies a digit to terminate a DTMF collection"
    DEFVAL          { none }
    ::= { sonusCasCollectionProfileAdmnEntry 10 }

sonusCassgCollectProfileRestartDigit OBJECT-TYPE
    SYNTAX          DisplayString (SIZE(0..3))
    MAX-ACCESS      read-write
    STATUS          current
    DESCRIPTION     
            "Specifies a digit sequence which will restart the collection and announcement prompt"
    ::= { sonusCasCollectionProfileAdmnEntry 11 }

sonusCassgCollectProfileReinputDigit OBJECT-TYPE
    SYNTAX          DisplayString (SIZE(0..3))
    MAX-ACCESS      read-write
    STATUS          current
    DESCRIPTION     
            "Specifies a digit sequence which will restart the collection but not the announcement"
    ::= { sonusCasCollectionProfileAdmnEntry 12 }

sonusCassgCollectProfileReportDigits OBJECT-TYPE
    SYNTAX          Integer32 (0..23)
    MAX-ACCESS      read-write
    STATUS          current
    DESCRIPTION     
            ""
    DEFVAL          { 0 }
    ::= { sonusCasCollectionProfileAdmnEntry 13 }

sonusCassgCollectProfileFirstDigitQuiet OBJECT-TYPE
    SYNTAX          SonusAdminState
    MAX-ACCESS      read-write
    STATUS          current
    DESCRIPTION     
            "Determines if announcement should be terminated when the first digit is entered"
    DEFVAL          { disabled }
    ::= { sonusCasCollectionProfileAdmnEntry 14 }

sonusCassgCollectProfileAnnouncementPrompt OBJECT-TYPE
    SYNTAX          Integer32 (0..65535)
    MAX-ACCESS      read-write
    STATUS          current
    DESCRIPTION     
            "Numeric identifier for the announcement"
    DEFVAL          { 0 }
    ::= { sonusCasCollectionProfileAdmnEntry 15 }

sonusCassgCollectProfileTonePrompt OBJECT-TYPE
    SYNTAX          DisplayString (SIZE(0..23))
    MAX-ACCESS      read-write
    STATUS          current
    DESCRIPTION     
            "Named reference to the tone prompt"
    ::= { sonusCasCollectionProfileAdmnEntry 16 }

sonusCassgCollectProfileRowStatus OBJECT-TYPE
    SYNTAX          RowStatus
    MAX-ACCESS      read-write
    STATUS          current
    DESCRIPTION     
            ""
    ::= { sonusCasCollectionProfileAdmnEntry 17 }

sonusCasSspGroupAdmn OBJECT IDENTIFIER
    ::= { sonusCasMIBObjects 6 }

sonusCasSspNextIndex OBJECT-TYPE
    SYNTAX          Integer32
    MAX-ACCESS      read-only
    STATUS          current
    DESCRIPTION     
            "The next valid index to use when creating a new sonusCasSspGroupAdmnEntry"
    ::= { sonusCasSspGroupAdmn 1 }

sonusCasSspAdmnTable OBJECT-TYPE
    SYNTAX          SEQUENCE OF SonusCasSspAdmnEntry
    MAX-ACCESS      not-accessible
    STATUS          current
    DESCRIPTION     
            ""
    ::= { sonusCasSspGroupAdmn 2 }

sonusCasSspAdmnEntry OBJECT-TYPE
    SYNTAX          SonusCasSspAdmnEntry
    MAX-ACCESS      not-accessible
    STATUS          current
    DESCRIPTION     
            ""
    INDEX           { sonusCassgSigSeqProfileIndex }
    ::= { sonusCasSspAdmnTable 1 }

SonusCasSspAdmnEntry ::=
    SEQUENCE {
        sonusCassgSigSeqProfileIndex    Integer32,
        sonusCassgSigSeqProfileName     SonusName,
        sonusCassgSigSeqProfileRowStatus RowStatus
    }

sonusCassgSigSeqProfileIndex OBJECT-TYPE
    SYNTAX          Integer32
    MAX-ACCESS      read-only
    STATUS          current
    DESCRIPTION     
            "The index of the SSP"
    ::= { sonusCasSspAdmnEntry 1 }

sonusCassgSigSeqProfileName OBJECT-TYPE
    SYNTAX          SonusName
    MAX-ACCESS      read-write
    STATUS          current
    DESCRIPTION     
            "Name of the SSP"
    ::= { sonusCasSspAdmnEntry 2 }

sonusCassgSigSeqProfileRowStatus OBJECT-TYPE
    SYNTAX          RowStatus
    MAX-ACCESS      read-write
    STATUS          current
    DESCRIPTION     
            ""
    ::= { sonusCasSspAdmnEntry 3 }

sonusCasSignalSeqAdmnTable OBJECT-TYPE
    SYNTAX          SEQUENCE OF SonusCasSignalSeqAdmnEntry
    MAX-ACCESS      not-accessible
    STATUS          current
    DESCRIPTION     
            ""
    ::= { sonusCasMIBObjects 7 }

sonusCasSignalSeqAdmnEntry OBJECT-TYPE
    SYNTAX          SonusCasSignalSeqAdmnEntry
    MAX-ACCESS      not-accessible
    STATUS          current
    DESCRIPTION     
            ""
    INDEX           { sonusCassgSigSequenceProfileIndex, 
                      sonusCassgSigSequenceIndex }
    ::= { sonusCasSignalSeqAdmnTable 1 }

SonusCasSignalSeqAdmnEntry ::=
    SEQUENCE {
        sonusCassgSigSequenceProfileIndex Integer32,
        sonusCassgSigSequenceIndex      Integer32,
        sonusCassgSigSequencePosition   Integer32,
        sonusCassgSigSequenceToken      INTEGER,
        sonusCassgSigSequenceParam1     DisplayString,
        sonusCassgSigSequenceParam2     DisplayString,
        sonusCassgSigSequenceSigCondProfileName       SonusNameReference,
        sonusCassgSigSequenceAdminState SonusAdminState,
        sonusCassgSigSequenceRowStatus  RowStatus
    }

sonusCassgSigSequenceProfileIndex OBJECT-TYPE
    SYNTAX          Integer32
    MAX-ACCESS      read-only
    STATUS          current
    DESCRIPTION     
            "Index of SSP in which the Signal Sequence is contained"
    ::= { sonusCasSignalSeqAdmnEntry 1 }

sonusCassgSigSequenceIndex OBJECT-TYPE
    SYNTAX          Integer32
    MAX-ACCESS      read-only
    STATUS          current
    DESCRIPTION     
            "Index of the Signal Sequence"
    ::= { sonusCasSignalSeqAdmnEntry 2 }

sonusCassgSigSequencePosition OBJECT-TYPE
    SYNTAX          Integer32 (0..31)
    MAX-ACCESS      read-write
    STATUS          current
    DESCRIPTION     
            "Relative position of the Signal Sequence"
    DEFVAL          { 0 }
    ::= { sonusCasSignalSeqAdmnEntry 3 }

sonusCassgSigSequenceToken OBJECT-TYPE
    SYNTAX          INTEGER { seize(1), wink(2), flash(3), dialMF(4), 
                        dialDTMF(5), dialDigit(6), playTone(7), 
                        playAnn(8), delay(9), waitWink(10), 
                        waitFlash(11), waitAnswer(12), collectField(13), 
                        collectDigit(14), report(15), clear(16), 
                        exec(17) }
    MAX-ACCESS      read-write
    STATUS          current
    DESCRIPTION     
            "Signaling action to perform"
    DEFVAL          { seize }
    ::= { sonusCasSignalSeqAdmnEntry 4 }

sonusCassgSigSequenceParam1 OBJECT-TYPE
    SYNTAX          DisplayString (SIZE(0..31))
    MAX-ACCESS      read-write
    STATUS          current
    DESCRIPTION     
            "First general parameter field specific to the signaling token"
    ::= { sonusCasSignalSeqAdmnEntry 5 }

sonusCassgSigSequenceParam2 OBJECT-TYPE
    SYNTAX          DisplayString (SIZE(0..31))
    MAX-ACCESS      read-write
    STATUS          current
    DESCRIPTION     
            "Second general parameter field specific to the signaling token"
    ::= { sonusCasSignalSeqAdmnEntry 6 }

sonusCassgSigSequenceSigCondProfileName OBJECT-TYPE
    SYNTAX          SonusNameReference
    MAX-ACCESS      read-write
    STATUS          current
    DESCRIPTION     
            "Name reference to SCP to execute when an error occurs"
    ::= { sonusCasSignalSeqAdmnEntry 7 }

sonusCassgSigSequenceAdminState OBJECT-TYPE
    SYNTAX          SonusAdminState
    MAX-ACCESS      read-write
    STATUS          current
    DESCRIPTION     
            "Admin state of the Signal Sequence"
    DEFVAL          { disabled }
    ::= { sonusCasSignalSeqAdmnEntry 8 }

sonusCassgSigSequenceRowStatus OBJECT-TYPE
    SYNTAX          RowStatus
    MAX-ACCESS      read-write
    STATUS          current
    DESCRIPTION     
            ""
    ::= { sonusCasSignalSeqAdmnEntry 9 }

sonusCasScpAdmn OBJECT IDENTIFIER
    ::= { sonusCasMIBObjects 8 }

sonusCasScpNextIndex OBJECT-TYPE
    SYNTAX          Integer32
    MAX-ACCESS      read-only
    STATUS          current
    DESCRIPTION     
            "The next valid index to use when creating a new sonusCasScpAdmnEntry"
    ::= { sonusCasScpAdmn 1 }

sonusCasScpAdmnTable OBJECT-TYPE
    SYNTAX          SEQUENCE OF SonusCasScpAdmnEntry
    MAX-ACCESS      not-accessible
    STATUS          current
    DESCRIPTION     
            ""
    ::= { sonusCasScpAdmn 2 }

sonusCasScpAdmnEntry OBJECT-TYPE
    SYNTAX          SonusCasScpAdmnEntry
    MAX-ACCESS      not-accessible
    STATUS          current
    DESCRIPTION     
            ""
    INDEX           { sonusCassgSigCondProfileIndex }
    ::= { sonusCasScpAdmnTable 1 }

SonusCasScpAdmnEntry ::=
    SEQUENCE {
        sonusCassgSigCondProfileIndex   Integer32,
        sonusCassgSigCondProfileName    SonusName,
        sonusCassgSigCondProfileRowStatus RowStatus
    }

sonusCassgSigCondProfileIndex OBJECT-TYPE
    SYNTAX          Integer32
    MAX-ACCESS      read-only
    STATUS          current
    DESCRIPTION     
            "The index of the SCP"
    ::= { sonusCasScpAdmnEntry 1 }

sonusCassgSigCondProfileName OBJECT-TYPE
    SYNTAX          SonusName
    MAX-ACCESS      read-write
    STATUS          current
    DESCRIPTION     
            "Name of the SCP"
    ::= { sonusCasScpAdmnEntry 2 }

sonusCassgSigCondProfileRowStatus OBJECT-TYPE
    SYNTAX          RowStatus
    MAX-ACCESS      read-write
    STATUS          current
    DESCRIPTION     
            ""
    ::= { sonusCasScpAdmnEntry 3 }

sonusCasSignalCondAdmnTable OBJECT-TYPE
    SYNTAX          SEQUENCE OF SonusCasSignalCondAdmnEntry
    MAX-ACCESS      not-accessible
    STATUS          current
    DESCRIPTION     
            ""
    ::= { sonusCasScpAdmn 3 }

sonusCasSignalCondAdmnEntry OBJECT-TYPE
    SYNTAX          SonusCasSignalCondAdmnEntry
    MAX-ACCESS      not-accessible
    STATUS          current
    DESCRIPTION     
            ""
    INDEX           { sonusCassgSigConditionProfileIndex, 
                      sonusCassgSigConditionIndex }
    ::= { sonusCasSignalCondAdmnTable 1 }

SonusCasSignalCondAdmnEntry ::=
    SEQUENCE {
        sonusCassgSigConditionProfileIndex  Integer32,
        sonusCassgSigConditionIndex     Integer32,
        sonusCassgSigConditionToken     INTEGER,
        sonusCassgSigConditionControl   INTEGER,
        sonusCassgSigConditionParam     DisplayString,
        sonusCassgSigConditionAdminState SonusAdminState,
        sonusCassgSigConditionRowStatus RowStatus
    }

sonusCassgSigConditionProfileIndex OBJECT-TYPE
    SYNTAX          Integer32
    MAX-ACCESS      read-only
    STATUS          current
    DESCRIPTION     
            "Index of the SCP in which the Signal Condition is contained"
    ::= { sonusCasSignalCondAdmnEntry 1 }

sonusCassgSigConditionIndex OBJECT-TYPE
    SYNTAX          Integer32
    MAX-ACCESS      read-only
    STATUS          current
    DESCRIPTION     
            "Index of the Signal Condition"
    ::= { sonusCasSignalCondAdmnEntry 2 }

sonusCassgSigConditionToken OBJECT-TYPE
    SYNTAX          INTEGER { default(1), firstDigitTimeout(2), 
                        interDigitTimeout(3), fieldTimeout(4), 
                        shortCollection(5), unexpectedDigit(6), 
                        rxWink(7), rxFlash(8), rxAnswer(9), 
                        winkTimeout(10), flashTimeout(11), 
                        answerTimeout(12), cutThrough(13) }
    MAX-ACCESS      read-write
    STATUS          current
    DESCRIPTION     
            "Token which defines error condition which occurred"
    DEFVAL          { default }
    ::= { sonusCasSignalCondAdmnEntry 3 }

sonusCassgSigConditionControl OBJECT-TYPE
    SYNTAX          INTEGER { proceed(1), exec(2), abort(3), abortMB(4) }
    MAX-ACCESS      read-write
    STATUS          current
    DESCRIPTION     
            "Defines how processing of the SSP should continue"
    DEFVAL          { proceed }
    ::= { sonusCasSignalCondAdmnEntry 4 }

sonusCassgSigConditionParam OBJECT-TYPE
    SYNTAX          DisplayString (SIZE(0..31))
    MAX-ACCESS      read-write
    STATUS          current
    DESCRIPTION     
            "General parameter for Signal Condition specific to token and control"
    ::= { sonusCasSignalCondAdmnEntry 5 }

sonusCassgSigConditionAdminState OBJECT-TYPE
    SYNTAX          SonusAdminState
    MAX-ACCESS      read-write
    STATUS          current
    DESCRIPTION     
            "The admin state of the Signal Condition"
    DEFVAL          { disabled }
    ::= { sonusCasSignalCondAdmnEntry 6 }

sonusCassgSigConditionRowStatus OBJECT-TYPE
    SYNTAX          RowStatus
    MAX-ACCESS      read-write
    STATUS          current
    DESCRIPTION     
            ""
    ::= { sonusCasSignalCondAdmnEntry 7 }

sonusCasDisconnectTreatAdmnTable OBJECT-TYPE
    SYNTAX          SEQUENCE OF SonusCasDisconnectTreatAdmnEntry
    MAX-ACCESS      not-accessible
    STATUS          deprecated
    DESCRIPTION     
            ""
    ::= { sonusCasMIBObjects 9 }

sonusCasDisconnectTreatAdmnEntry OBJECT-TYPE
    SYNTAX          SonusCasDisconnectTreatAdmnEntry
    MAX-ACCESS      not-accessible
    STATUS          deprecated
    DESCRIPTION     
            ""
    INDEX           { sonusCassgDiscTreatmentIndex }
    ::= { sonusCasDisconnectTreatAdmnTable 1 }

SonusCasDisconnectTreatAdmnEntry ::=
    SEQUENCE {
        sonusCassgDiscTreatmentIndex    Integer32,
        sonusCassgDiscTreatmentReason   Integer32,
        sonusCassgDiscTreatmentSigSeqProfileName        SonusNameReference,
        sonusCassgDiscTreatmentRowStatus RowStatus
    }

sonusCassgDiscTreatmentIndex OBJECT-TYPE
    SYNTAX          Integer32
    MAX-ACCESS      read-only
    STATUS          deprecated
    DESCRIPTION     
            ""
    ::= { sonusCasDisconnectTreatAdmnEntry 1 }

sonusCassgDiscTreatmentReason OBJECT-TYPE
    SYNTAX          Integer32 (0..255)
    MAX-ACCESS      read-only
    STATUS          deprecated
    DESCRIPTION     
            ""
    ::= { sonusCasDisconnectTreatAdmnEntry 2 }

sonusCassgDiscTreatmentSigSeqProfileName OBJECT-TYPE
    SYNTAX          SonusNameReference
    MAX-ACCESS      read-write
    STATUS          deprecated
    DESCRIPTION     
            ""
    ::= { sonusCasDisconnectTreatAdmnEntry 3 }

sonusCassgDiscTreatmentRowStatus OBJECT-TYPE
    SYNTAX          RowStatus
    MAX-ACCESS      read-write
    STATUS          deprecated
    DESCRIPTION     
            ""
    ::= { sonusCasDisconnectTreatAdmnEntry 4 }

sonusCasServiceGroupMIBNotifications OBJECT IDENTIFIER
    ::= { sonusCasMIBObjects 10 }

sonusCasServiceGroupMIBNotificationsPrefix OBJECT IDENTIFIER
    ::= { sonusCasServiceGroupMIBNotifications 0 }

sonusCasServiceGroupMIBNotificationsObjects OBJECT IDENTIFIER
    ::= { sonusCasServiceGroupMIBNotifications 1 }

sonusCasSvcGrpName OBJECT-TYPE
    SYNTAX          DisplayString (SIZE(0..23))
    MAX-ACCESS      read-only
    STATUS          current
    DESCRIPTION     
            "Name of the CAS service group."
    ::= { sonusCasServiceGroupMIBNotificationsObjects 1 }

sonusCasSvcGrpInServiceNotification NOTIFICATION-TYPE
    OBJECTS         { sonusCasSvcGrpName, sonusEventDescription, 
                      sonusEventClass, sonusEventLevel }
    STATUS          current
    DESCRIPTION     
            "This trap indicates that the CAS Service Group was put in service 
             by maintenance staff."
    ::= { sonusCasServiceGroupMIBNotificationsPrefix 1 }

sonusCasSvcGrpOutOfServiceNotification NOTIFICATION-TYPE
    OBJECTS         { sonusCasSvcGrpName, sonusEventDescription, 
                      sonusEventClass, sonusEventLevel }
    STATUS          current
    DESCRIPTION     
            "This trap indicates that the CAS Service Group was taken out of 
             service by maintenance staff."
    ::= { sonusCasServiceGroupMIBNotificationsPrefix 2 }

sonusCasChannelInServiceNotification NOTIFICATION-TYPE
    OBJECTS         { sonusCasSvcGrpName, sonusCassgChannelShelfIndex, 
                      sonusCassgChannelSlotIndex, 
                      sonusCassgChannelPortIndex, sonusCassgChannelIndex, 
                      sonusEventDescription, sonusEventClass, 
                      sonusEventLevel }
    STATUS          current
    DESCRIPTION     
            "This trap indicates that a CAS channel was put in service by CAS."
    ::= { sonusCasServiceGroupMIBNotificationsPrefix 3 }

sonusCasChannelOutOfServiceNotification NOTIFICATION-TYPE
    OBJECTS         { sonusCasSvcGrpName, sonusCassgChannelShelfIndex, 
                      sonusCassgChannelSlotIndex, 
                      sonusCassgChannelPortIndex, sonusCassgChannelIndex, 
                      sonusEventDescription, sonusEventClass, 
                      sonusEventLevel }
    STATUS          current
    DESCRIPTION     
            "This trap indicates that a channel was taken out of service by 
             the CAS SG due to signaling errors exceeding a configured 
             threshold."
    ::= { sonusCasServiceGroupMIBNotificationsPrefix 4 }

END -- end of module SONUS-CAS-MIB.
