-- *****************************************************************
-- IPMC-SNOOPING-MIB:  Cisco private MIB
-- ****************************************************************

CIE1000-IPMC-SNOOPING-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000DisplayString FROM CIE1000-TC
    CIE1000InterfaceIndex FROM CIE1000-TC
    CIE1000PortList FROM CIE1000-TC
    CIE1000RowEditorState FROM CIE1000-TC
    CIE1000Unsigned8 FROM CIE1000-TC
    InetAddressIPv6 FROM INET-ADDRESS-MIB
    Integer32 FROM SNMPv2-SMI
    IpAddress FROM SNMPv2-SMI
    Unsigned32 FROM SNMPv2-SMI
    TruthValue FROM SNMPv2-TC
    ;

cie1000IpmcSnoopingMib MODULE-IDENTITY
    LAST-UPDATED "201407010000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of the IPMC Snooping MIB"
    REVISION    "201407010000Z"
    DESCRIPTION
        "Initial version"
    ::= { cie1000SwitchMgmt 69 }


CIE1000IpmcSnoopingIgmpGroupSrcListGroupFilterModeEnum ::= TEXTUAL-CONVENTION
    STATUS      current
    DESCRIPTION
        "This enumeration indicates the group filter mode for a IGMP group
         address."
    SYNTAX      INTEGER { exclude(0), include(1), none(2) }

CIE1000IpmcSnoopingIgmpGroupSrcListSourceTypeEnum ::= TEXTUAL-CONVENTION
    STATUS      current
    DESCRIPTION
        "This enumeration indicates the source filtering type from IGMP
         snooping."
    SYNTAX      INTEGER { deny(0), permit(1) }

CIE1000IpmcSnoopingIgmpInterfaceCompatibilityEnum ::= TEXTUAL-CONVENTION
    STATUS      current
    DESCRIPTION
        "This enumeration indicates the version compatibility for IGMP snooping
         VLAN interface."
    SYNTAX      INTEGER { auto(0), igmpv1(1), igmpv2(2), igmpv3(3) }

CIE1000IpmcSnoopingIgmpRouterPortStatusEnum ::= TEXTUAL-CONVENTION
    STATUS      current
    DESCRIPTION
        "This enumeration indicates the router port status from IGMP snooping."
    SYNTAX      INTEGER { none(0), static(1), dynamic(2), both(3) }

CIE1000IpmcSnoopingIgmpVlanStatusQuerierStatusEnum ::= TEXTUAL-CONVENTION
    STATUS      current
    DESCRIPTION
        "This enumeration indicates the querier status for IGMP snooping VLAN
         interface."
    SYNTAX      INTEGER { disabled(0), initial(1), idle(2), active(3) }

CIE1000IpmcSnoopingMldGroupSrcListGroupFilterModeEnum ::= TEXTUAL-CONVENTION
    STATUS      current
    DESCRIPTION
        "This enumeration indicates the group filter mode for a MLD group
         address."
    SYNTAX      INTEGER { exclude(0), include(1), none(2) }

CIE1000IpmcSnoopingMldGroupSrcListSourceEnum ::= TEXTUAL-CONVENTION
    STATUS      current
    DESCRIPTION
        "This enumeration indicates the source filtering type from MLD snooping."
    SYNTAX      INTEGER { deny(0), permit(1) }

CIE1000IpmcSnoopingMldInterfaceCompatibilityEnum ::= TEXTUAL-CONVENTION
    STATUS      current
    DESCRIPTION
        "This enumeration indicates the version compatibility for MLD snooping
         VLAN interface."
    SYNTAX      INTEGER { auto(0), mldv1(1), mldv2(2) }

CIE1000IpmcSnoopingMldRouterPortStatusEnum ::= TEXTUAL-CONVENTION
    STATUS      current
    DESCRIPTION
        "This enumeration indicates the router port status from MLD snooping."
    SYNTAX      INTEGER { none(0), static(1), dynamic(2), both(3) }

CIE1000IpmcSnoopingMldVlanStatusQuerierStatusEnum ::= TEXTUAL-CONVENTION
    STATUS      current
    DESCRIPTION
        "This enumeration indicates the querier status for MLD snooping VLAN
         interface."
    SYNTAX      INTEGER { disabled(0), initial(1), idle(2), active(3) }

cie1000IpmcSnoopingMibObjects OBJECT IDENTIFIER
    ::= { cie1000IpmcSnoopingMib 1 }

cie1000IpmcSnoopingConfig OBJECT IDENTIFIER
    ::= { cie1000IpmcSnoopingMibObjects 2 }

cie1000IpmcSnoopingConfigIgmpGlobals OBJECT IDENTIFIER
    ::= { cie1000IpmcSnoopingConfig 1 }

cie1000IpmcSnoopingConfigIgmpGlobalsAdminState OBJECT-TYPE
    SYNTAX      TruthValue
    MAX-ACCESS  read-write
    STATUS      current
    DESCRIPTION
        "Enable/Disable the IGMP snooping global functionality."
    ::= { cie1000IpmcSnoopingConfigIgmpGlobals 1 }

cie1000IpmcSnoopingConfigIgmpGlobalsUnregisteredFlooding OBJECT-TYPE
    SYNTAX      TruthValue
    MAX-ACCESS  read-write
    STATUS      current
    DESCRIPTION
        "Enable/Disable the control for flooding unregistered IPv4 multicast
         traffic."
    ::= { cie1000IpmcSnoopingConfigIgmpGlobals 2 }

cie1000IpmcSnoopingConfigIgmpGlobalsSsmRangeAddress OBJECT-TYPE
    SYNTAX      IpAddress
    MAX-ACCESS  read-write
    STATUS      current
    DESCRIPTION
        "The address prefix value defined for IGMP SSM service model."
    ::= { cie1000IpmcSnoopingConfigIgmpGlobals 3 }

cie1000IpmcSnoopingConfigIgmpGlobalsSsmRangeMask OBJECT-TYPE
    SYNTAX      Unsigned32
    MAX-ACCESS  read-write
    STATUS      current
    DESCRIPTION
        "The address prefix length defined for IGMP SSM service model."
    ::= { cie1000IpmcSnoopingConfigIgmpGlobals 4 }

cie1000IpmcSnoopingConfigIgmpGlobalsProxy OBJECT-TYPE
    SYNTAX      TruthValue
    MAX-ACCESS  read-write
    STATUS      current
    DESCRIPTION
        "Enable/Disable the IGMP proxy functionality."
    ::= { cie1000IpmcSnoopingConfigIgmpGlobals 5 }

cie1000IpmcSnoopingConfigIgmpGlobalsLeaveProxy OBJECT-TYPE
    SYNTAX      TruthValue
    MAX-ACCESS  read-write
    STATUS      current
    DESCRIPTION
        "Enable/Disable the IGMP leave-proxy functionality."
    ::= { cie1000IpmcSnoopingConfigIgmpGlobals 6 }

cie1000IpmcSnoopingConfigIgmpPortTable OBJECT-TYPE
    SYNTAX      SEQUENCE OF CIE1000IpmcSnoopingConfigIgmpPortEntry
    MAX-ACCESS  not-accessible
    STATUS      current
    DESCRIPTION
        "This is a table for managing extra IGMP snooping helper features per
         port basis"
    ::= { cie1000IpmcSnoopingConfig 2 }

cie1000IpmcSnoopingConfigIgmpPortEntry OBJECT-TYPE
    SYNTAX      CIE1000IpmcSnoopingConfigIgmpPortEntry
    MAX-ACCESS  not-accessible
    STATUS      current
    DESCRIPTION
        "Each port has a set of parameters"
    INDEX       { cie1000IpmcSnoopingConfigIgmpPortPortIndex }
    ::= { cie1000IpmcSnoopingConfigIgmpPortTable 1 }

CIE1000IpmcSnoopingConfigIgmpPortEntry ::= SEQUENCE {
    cie1000IpmcSnoopingConfigIgmpPortPortIndex         CIE1000InterfaceIndex,
    cie1000IpmcSnoopingConfigIgmpPortAsRouterPort      TruthValue,
    cie1000IpmcSnoopingConfigIgmpPortDoFastLeave       TruthValue,
    cie1000IpmcSnoopingConfigIgmpPortThrottlingNumber  Integer32,
    cie1000IpmcSnoopingConfigIgmpPortFilteringProfile  CIE1000DisplayString
}

cie1000IpmcSnoopingConfigIgmpPortPortIndex OBJECT-TYPE
    SYNTAX      CIE1000InterfaceIndex
    MAX-ACCESS  accessible-for-notify
    STATUS      current
    DESCRIPTION
        "Logical interface number of the physical port."
    ::= { cie1000IpmcSnoopingConfigIgmpPortEntry 1 }

cie1000IpmcSnoopingConfigIgmpPortAsRouterPort OBJECT-TYPE
    SYNTAX      TruthValue
    MAX-ACCESS  read-write
    STATUS      current
    DESCRIPTION
        "Enable/Disable the IGMP static router port functionality."
    ::= { cie1000IpmcSnoopingConfigIgmpPortEntry 2 }

cie1000IpmcSnoopingConfigIgmpPortDoFastLeave OBJECT-TYPE
    SYNTAX      TruthValue
    MAX-ACCESS  read-write
    STATUS      current
    DESCRIPTION
        "Enable/Disable the IGMP fast leave functionality."
    ::= { cie1000IpmcSnoopingConfigIgmpPortEntry 3 }

cie1000IpmcSnoopingConfigIgmpPortThrottlingNumber OBJECT-TYPE
    SYNTAX      Integer32
    MAX-ACCESS  read-write
    STATUS      current
    DESCRIPTION
        "The maximum number of groups to be registered on the specific port."
    ::= { cie1000IpmcSnoopingConfigIgmpPortEntry 4 }

cie1000IpmcSnoopingConfigIgmpPortFilteringProfile OBJECT-TYPE
    SYNTAX      CIE1000DisplayString (SIZE(0..16))
    MAX-ACCESS  read-write
    STATUS      current
    DESCRIPTION
        "The profile used for IGMP filtering per-port basis."
    ::= { cie1000IpmcSnoopingConfigIgmpPortEntry 5 }

cie1000IpmcSnoopingConfigIgmpIfTable OBJECT-TYPE
    SYNTAX      SEQUENCE OF CIE1000IpmcSnoopingConfigIgmpIfEntry
    MAX-ACCESS  not-accessible
    STATUS      current
    DESCRIPTION
        "This is a table for managing IGMP Snooping VLAN interface entries."
    ::= { cie1000IpmcSnoopingConfig 3 }

cie1000IpmcSnoopingConfigIgmpIfEntry OBJECT-TYPE
    SYNTAX      CIE1000IpmcSnoopingConfigIgmpIfEntry
    MAX-ACCESS  not-accessible
    STATUS      current
    DESCRIPTION
        "Each entry has a set of parameters"
    INDEX       { cie1000IpmcSnoopingConfigIgmpIfIfIndex }
    ::= { cie1000IpmcSnoopingConfigIgmpIfTable 1 }

CIE1000IpmcSnoopingConfigIgmpIfEntry ::= SEQUENCE {
    cie1000IpmcSnoopingConfigIgmpIfIfIndex          CIE1000InterfaceIndex,
    cie1000IpmcSnoopingConfigIgmpIfAdminState       TruthValue,
    cie1000IpmcSnoopingConfigIgmpIfQuerierElection  TruthValue,
    cie1000IpmcSnoopingConfigIgmpIfQuerierAddress   IpAddress,
    cie1000IpmcSnoopingConfigIgmpIfCompatibility    CIE1000IpmcSnoopingIgmpInterfaceCompatibilityEnum,
    cie1000IpmcSnoopingConfigIgmpIfPriority         CIE1000Unsigned8,
    cie1000IpmcSnoopingConfigIgmpIfRv               Unsigned32,
    cie1000IpmcSnoopingConfigIgmpIfQi               Unsigned32,
    cie1000IpmcSnoopingConfigIgmpIfQri              Unsigned32,
    cie1000IpmcSnoopingConfigIgmpIfLmqi             Unsigned32,
    cie1000IpmcSnoopingConfigIgmpIfUri              Unsigned32,
    cie1000IpmcSnoopingConfigIgmpIfAction           CIE1000RowEditorState
}

cie1000IpmcSnoopingConfigIgmpIfIfIndex OBJECT-TYPE
    SYNTAX      CIE1000InterfaceIndex
    MAX-ACCESS  accessible-for-notify
    STATUS      current
    DESCRIPTION
        "Logical interface number of the VLAN interface."
    ::= { cie1000IpmcSnoopingConfigIgmpIfEntry 1 }

cie1000IpmcSnoopingConfigIgmpIfAdminState OBJECT-TYPE
    SYNTAX      TruthValue
    MAX-ACCESS  read-write
    STATUS      current
    DESCRIPTION
        "Enable/Disable the IGMP snooping per-VLAN functionality."
    ::= { cie1000IpmcSnoopingConfigIgmpIfEntry 2 }

cie1000IpmcSnoopingConfigIgmpIfQuerierElection OBJECT-TYPE
    SYNTAX      TruthValue
    MAX-ACCESS  read-write
    STATUS      current
    DESCRIPTION
        "Enable/Disable the capability to run IGMP Querier election per-VLAN
         basis."
    ::= { cie1000IpmcSnoopingConfigIgmpIfEntry 3 }

cie1000IpmcSnoopingConfigIgmpIfQuerierAddress OBJECT-TYPE
    SYNTAX      IpAddress
    MAX-ACCESS  read-write
    STATUS      current
    DESCRIPTION
        "The static IPv4 source address of the specific IGMP interface for
         seding IGMP Query message with respect to IGMP Querier election."
    ::= { cie1000IpmcSnoopingConfigIgmpIfEntry 4 }

cie1000IpmcSnoopingConfigIgmpIfCompatibility OBJECT-TYPE
    SYNTAX      CIE1000IpmcSnoopingIgmpInterfaceCompatibilityEnum
    MAX-ACCESS  read-write
    STATUS      current
    DESCRIPTION
        "The compatibility control for IGMP snooping to run the corresponding
         protocol version."
    ::= { cie1000IpmcSnoopingConfigIgmpIfEntry 5 }

cie1000IpmcSnoopingConfigIgmpIfPriority OBJECT-TYPE
    SYNTAX      CIE1000Unsigned8
    MAX-ACCESS  read-write
    STATUS      current
    DESCRIPTION
        "This setting is used for prioritizing the IGMP control frames to be
         sent for IGMP snooping."
    ::= { cie1000IpmcSnoopingConfigIgmpIfEntry 6 }

cie1000IpmcSnoopingConfigIgmpIfRv OBJECT-TYPE
    SYNTAX      Unsigned32
    MAX-ACCESS  read-write
    STATUS      current
    DESCRIPTION
        "This setting Robustness Variable is used to control IGMP protocol stack
         as stated in RFC-3376 8.1."
    ::= { cie1000IpmcSnoopingConfigIgmpIfEntry 7 }

cie1000IpmcSnoopingConfigIgmpIfQi OBJECT-TYPE
    SYNTAX      Unsigned32
    MAX-ACCESS  read-write
    STATUS      current
    DESCRIPTION
        "This setting Query Interval is used to control IGMP protocol stack as
         stated in RFC-3376 8.2."
    ::= { cie1000IpmcSnoopingConfigIgmpIfEntry 8 }

cie1000IpmcSnoopingConfigIgmpIfQri OBJECT-TYPE
    SYNTAX      Unsigned32
    MAX-ACCESS  read-write
    STATUS      current
    DESCRIPTION
        "This setting Query Response Intervalis used to control IGMP protocol
         stack as stated in RFC-3376 8.3."
    ::= { cie1000IpmcSnoopingConfigIgmpIfEntry 9 }

cie1000IpmcSnoopingConfigIgmpIfLmqi OBJECT-TYPE
    SYNTAX      Unsigned32
    MAX-ACCESS  read-write
    STATUS      current
    DESCRIPTION
        "This setting Last Member Query Interval is used to control IGMP
         protocol stack as stated in RFC-3376 8.8."
    ::= { cie1000IpmcSnoopingConfigIgmpIfEntry 10 }

cie1000IpmcSnoopingConfigIgmpIfUri OBJECT-TYPE
    SYNTAX      Unsigned32
    MAX-ACCESS  read-write
    STATUS      current
    DESCRIPTION
        "This setting Unsolicited Report Interval is used to control IGMP
         protocol stack as stated in RFC-3376 8.11."
    ::= { cie1000IpmcSnoopingConfigIgmpIfEntry 11 }

cie1000IpmcSnoopingConfigIgmpIfAction OBJECT-TYPE
    SYNTAX      CIE1000RowEditorState
    MAX-ACCESS  read-write
    STATUS      current
    DESCRIPTION
        "Action"
    ::= { cie1000IpmcSnoopingConfigIgmpIfEntry 100 }

cie1000IpmcSnoopingConfigIgmpIfTableRowEditor OBJECT IDENTIFIER
    ::= { cie1000IpmcSnoopingConfig 4 }

cie1000IpmcSnoopingConfigIgmpIfTableRowEditorIfIndex OBJECT-TYPE
    SYNTAX      CIE1000InterfaceIndex
    MAX-ACCESS  read-write
    STATUS      current
    DESCRIPTION
        "Logical interface number of the VLAN interface."
    ::= { cie1000IpmcSnoopingConfigIgmpIfTableRowEditor 1 }

cie1000IpmcSnoopingConfigIgmpIfTableRowEditorAdminState OBJECT-TYPE
    SYNTAX      TruthValue
    MAX-ACCESS  read-write
    STATUS      current
    DESCRIPTION
        "Enable/Disable the IGMP snooping per-VLAN functionality."
    ::= { cie1000IpmcSnoopingConfigIgmpIfTableRowEditor 2 }

cie1000IpmcSnoopingConfigIgmpIfTableRowEditorQuerierElection OBJECT-TYPE
    SYNTAX      TruthValue
    MAX-ACCESS  read-write
    STATUS      current
    DESCRIPTION
        "Enable/Disable the capability to run IGMP Querier election per-VLAN
         basis."
    ::= { cie1000IpmcSnoopingConfigIgmpIfTableRowEditor 3 }

cie1000IpmcSnoopingConfigIgmpIfTableRowEditorQuerierAddress OBJECT-TYPE
    SYNTAX      IpAddress
    MAX-ACCESS  read-write
    STATUS      current
    DESCRIPTION
        "The static IPv4 source address of the specific IGMP interface for
         seding IGMP Query message with respect to IGMP Querier election."
    ::= { cie1000IpmcSnoopingConfigIgmpIfTableRowEditor 4 }

cie1000IpmcSnoopingConfigIgmpIfTableRowEditorCompatibility OBJECT-TYPE
    SYNTAX      CIE1000IpmcSnoopingIgmpInterfaceCompatibilityEnum
    MAX-ACCESS  read-write
    STATUS      current
    DESCRIPTION
        "The compatibility control for IGMP snooping to run the corresponding
         protocol version."
    ::= { cie1000IpmcSnoopingConfigIgmpIfTableRowEditor 5 }

cie1000IpmcSnoopingConfigIgmpIfTableRowEditorPriority OBJECT-TYPE
    SYNTAX      CIE1000Unsigned8
    MAX-ACCESS  read-write
    STATUS      current
    DESCRIPTION
        "This setting is used for prioritizing the IGMP control frames to be
         sent for IGMP snooping."
    ::= { cie1000IpmcSnoopingConfigIgmpIfTableRowEditor 6 }

cie1000IpmcSnoopingConfigIgmpIfTableRowEditorRv OBJECT-TYPE
    SYNTAX      Unsigned32
    MAX-ACCESS  read-write
    STATUS      current
    DESCRIPTION
        "This setting Robustness Variable is used to control IGMP protocol stack
         as stated in RFC-3376 8.1."
    ::= { cie1000IpmcSnoopingConfigIgmpIfTableRowEditor 7 }

cie1000IpmcSnoopingConfigIgmpIfTableRowEditorQi OBJECT-TYPE
    SYNTAX      Unsigned32
    MAX-ACCESS  read-write
    STATUS      current
    DESCRIPTION
        "This setting Query Interval is used to control IGMP protocol stack as
         stated in RFC-3376 8.2."
    ::= { cie1000IpmcSnoopingConfigIgmpIfTableRowEditor 8 }

cie1000IpmcSnoopingConfigIgmpIfTableRowEditorQri OBJECT-TYPE
    SYNTAX      Unsigned32
    MAX-ACCESS  read-write
    STATUS      current
    DESCRIPTION
        "This setting Query Response Intervalis used to control IGMP protocol
         stack as stated in RFC-3376 8.3."
    ::= { cie1000IpmcSnoopingConfigIgmpIfTableRowEditor 9 }

cie1000IpmcSnoopingConfigIgmpIfTableRowEditorLmqi OBJECT-TYPE
    SYNTAX      Unsigned32
    MAX-ACCESS  read-write
    STATUS      current
    DESCRIPTION
        "This setting Last Member Query Interval is used to control IGMP
         protocol stack as stated in RFC-3376 8.8."
    ::= { cie1000IpmcSnoopingConfigIgmpIfTableRowEditor 10 }

cie1000IpmcSnoopingConfigIgmpIfTableRowEditorUri OBJECT-TYPE
    SYNTAX      Unsigned32
    MAX-ACCESS  read-write
    STATUS      current
    DESCRIPTION
        "This setting Unsolicited Report Interval is used to control IGMP
         protocol stack as stated in RFC-3376 8.11."
    ::= { cie1000IpmcSnoopingConfigIgmpIfTableRowEditor 11 }

cie1000IpmcSnoopingConfigIgmpIfTableRowEditorAction OBJECT-TYPE
    SYNTAX      CIE1000RowEditorState
    MAX-ACCESS  read-write
    STATUS      current
    DESCRIPTION
        "Action"
    ::= { cie1000IpmcSnoopingConfigIgmpIfTableRowEditor 100 }

cie1000IpmcSnoopingConfigMldGlobals OBJECT IDENTIFIER
    ::= { cie1000IpmcSnoopingConfig 5 }

cie1000IpmcSnoopingConfigMldGlobalsAdminState OBJECT-TYPE
    SYNTAX      TruthValue
    MAX-ACCESS  read-write
    STATUS      current
    DESCRIPTION
        "Enable/Disable the MLD snooping global functionality."
    ::= { cie1000IpmcSnoopingConfigMldGlobals 1 }

cie1000IpmcSnoopingConfigMldGlobalsUnregisteredFlooding OBJECT-TYPE
    SYNTAX      TruthValue
    MAX-ACCESS  read-write
    STATUS      current
    DESCRIPTION
        "Enable/Disable the control for flooding unregistered IPv6 multicast
         traffic."
    ::= { cie1000IpmcSnoopingConfigMldGlobals 2 }

cie1000IpmcSnoopingConfigMldGlobalsSsmRangeAddress OBJECT-TYPE
    SYNTAX      InetAddressIPv6
    MAX-ACCESS  read-write
    STATUS      current
    DESCRIPTION
        "The address prefix value defined for MLD SSM service model."
    ::= { cie1000IpmcSnoopingConfigMldGlobals 3 }

cie1000IpmcSnoopingConfigMldGlobalsSsmRangeMask OBJECT-TYPE
    SYNTAX      Unsigned32
    MAX-ACCESS  read-write
    STATUS      current
    DESCRIPTION
        "The address prefix length defined for MLD SSM service model."
    ::= { cie1000IpmcSnoopingConfigMldGlobals 4 }

cie1000IpmcSnoopingConfigMldGlobalsProxy OBJECT-TYPE
    SYNTAX      TruthValue
    MAX-ACCESS  read-write
    STATUS      current
    DESCRIPTION
        "Enable/Disable the MLD proxy functionality."
    ::= { cie1000IpmcSnoopingConfigMldGlobals 5 }

cie1000IpmcSnoopingConfigMldGlobalsLeaveProxy OBJECT-TYPE
    SYNTAX      TruthValue
    MAX-ACCESS  read-write
    STATUS      current
    DESCRIPTION
        "Enable/Disable the MLD leave-proxy functionality."
    ::= { cie1000IpmcSnoopingConfigMldGlobals 6 }

cie1000IpmcSnoopingConfigMldPortTable OBJECT-TYPE
    SYNTAX      SEQUENCE OF CIE1000IpmcSnoopingConfigMldPortEntry
    MAX-ACCESS  not-accessible
    STATUS      current
    DESCRIPTION
        "This is a table for managing extra MLD snooping helper features per
         port basis"
    ::= { cie1000IpmcSnoopingConfig 6 }

cie1000IpmcSnoopingConfigMldPortEntry OBJECT-TYPE
    SYNTAX      CIE1000IpmcSnoopingConfigMldPortEntry
    MAX-ACCESS  not-accessible
    STATUS      current
    DESCRIPTION
        "Each port has a set of parameters"
    INDEX       { cie1000IpmcSnoopingConfigMldPortPortIndex }
    ::= { cie1000IpmcSnoopingConfigMldPortTable 1 }

CIE1000IpmcSnoopingConfigMldPortEntry ::= SEQUENCE {
    cie1000IpmcSnoopingConfigMldPortPortIndex         CIE1000InterfaceIndex,
    cie1000IpmcSnoopingConfigMldPortAsRouterPort      TruthValue,
    cie1000IpmcSnoopingConfigMldPortDoFastLeave       TruthValue,
    cie1000IpmcSnoopingConfigMldPortThrottlingNumber  Integer32,
    cie1000IpmcSnoopingConfigMldPortFilteringProfile  CIE1000DisplayString
}

cie1000IpmcSnoopingConfigMldPortPortIndex OBJECT-TYPE
    SYNTAX      CIE1000InterfaceIndex
    MAX-ACCESS  accessible-for-notify
    STATUS      current
    DESCRIPTION
        "Logical interface number of the physical port."
    ::= { cie1000IpmcSnoopingConfigMldPortEntry 1 }

cie1000IpmcSnoopingConfigMldPortAsRouterPort OBJECT-TYPE
    SYNTAX      TruthValue
    MAX-ACCESS  read-write
    STATUS      current
    DESCRIPTION
        "Enable/Disable the MLD static router port functionality."
    ::= { cie1000IpmcSnoopingConfigMldPortEntry 2 }

cie1000IpmcSnoopingConfigMldPortDoFastLeave OBJECT-TYPE
    SYNTAX      TruthValue
    MAX-ACCESS  read-write
    STATUS      current
    DESCRIPTION
        "Enable/Disable the MLD fast leave functionality."
    ::= { cie1000IpmcSnoopingConfigMldPortEntry 3 }

cie1000IpmcSnoopingConfigMldPortThrottlingNumber OBJECT-TYPE
    SYNTAX      Integer32
    MAX-ACCESS  read-write
    STATUS      current
    DESCRIPTION
        "The maximum number of groups to be registered on the specific port."
    ::= { cie1000IpmcSnoopingConfigMldPortEntry 4 }

cie1000IpmcSnoopingConfigMldPortFilteringProfile OBJECT-TYPE
    SYNTAX      CIE1000DisplayString (SIZE(0..16))
    MAX-ACCESS  read-write
    STATUS      current
    DESCRIPTION
        "The profile used for MLD filtering per-port basis."
    ::= { cie1000IpmcSnoopingConfigMldPortEntry 5 }

cie1000IpmcSnoopingConfigMldIfTable OBJECT-TYPE
    SYNTAX      SEQUENCE OF CIE1000IpmcSnoopingConfigMldIfEntry
    MAX-ACCESS  not-accessible
    STATUS      current
    DESCRIPTION
        "This is a table for managing MLD Snooping VLAN interface entries."
    ::= { cie1000IpmcSnoopingConfig 7 }

cie1000IpmcSnoopingConfigMldIfEntry OBJECT-TYPE
    SYNTAX      CIE1000IpmcSnoopingConfigMldIfEntry
    MAX-ACCESS  not-accessible
    STATUS      current
    DESCRIPTION
        "Each entry has a set of parameters"
    INDEX       { cie1000IpmcSnoopingConfigMldIfIfIndex }
    ::= { cie1000IpmcSnoopingConfigMldIfTable 1 }

CIE1000IpmcSnoopingConfigMldIfEntry ::= SEQUENCE {
    cie1000IpmcSnoopingConfigMldIfIfIndex          CIE1000InterfaceIndex,
    cie1000IpmcSnoopingConfigMldIfAdminState       TruthValue,
    cie1000IpmcSnoopingConfigMldIfQuerierElection  TruthValue,
    cie1000IpmcSnoopingConfigMldIfCompatibility    CIE1000IpmcSnoopingMldInterfaceCompatibilityEnum,
    cie1000IpmcSnoopingConfigMldIfPriority         CIE1000Unsigned8,
    cie1000IpmcSnoopingConfigMldIfRv               Unsigned32,
    cie1000IpmcSnoopingConfigMldIfQi               Unsigned32,
    cie1000IpmcSnoopingConfigMldIfQri              Unsigned32,
    cie1000IpmcSnoopingConfigMldIfLlqi             Unsigned32,
    cie1000IpmcSnoopingConfigMldIfUri              Unsigned32,
    cie1000IpmcSnoopingConfigMldIfAction           CIE1000RowEditorState
}

cie1000IpmcSnoopingConfigMldIfIfIndex OBJECT-TYPE
    SYNTAX      CIE1000InterfaceIndex
    MAX-ACCESS  accessible-for-notify
    STATUS      current
    DESCRIPTION
        "Logical interface number of the VLAN interface."
    ::= { cie1000IpmcSnoopingConfigMldIfEntry 1 }

cie1000IpmcSnoopingConfigMldIfAdminState OBJECT-TYPE
    SYNTAX      TruthValue
    MAX-ACCESS  read-write
    STATUS      current
    DESCRIPTION
        "Enable/Disable the MLD snooping per-VLAN functionality."
    ::= { cie1000IpmcSnoopingConfigMldIfEntry 2 }

cie1000IpmcSnoopingConfigMldIfQuerierElection OBJECT-TYPE
    SYNTAX      TruthValue
    MAX-ACCESS  read-write
    STATUS      current
    DESCRIPTION
        "Enable/Disable the capability to run MLD Querier election per-VLAN
         basis."
    ::= { cie1000IpmcSnoopingConfigMldIfEntry 3 }

cie1000IpmcSnoopingConfigMldIfCompatibility OBJECT-TYPE
    SYNTAX      CIE1000IpmcSnoopingMldInterfaceCompatibilityEnum
    MAX-ACCESS  read-write
    STATUS      current
    DESCRIPTION
        "The compatibility control for MLD snooping to run the corresponding
         protocol version."
    ::= { cie1000IpmcSnoopingConfigMldIfEntry 4 }

cie1000IpmcSnoopingConfigMldIfPriority OBJECT-TYPE
    SYNTAX      CIE1000Unsigned8
    MAX-ACCESS  read-write
    STATUS      current
    DESCRIPTION
        "This setting is used for prioritizing the MLD control frames to be sent
         for MLD snooping."
    ::= { cie1000IpmcSnoopingConfigMldIfEntry 5 }

cie1000IpmcSnoopingConfigMldIfRv OBJECT-TYPE
    SYNTAX      Unsigned32
    MAX-ACCESS  read-write
    STATUS      current
    DESCRIPTION
        "This setting Robustness Variableis used to control MLD protocol stack
         as stated in RFC-3810 9.1."
    ::= { cie1000IpmcSnoopingConfigMldIfEntry 6 }

cie1000IpmcSnoopingConfigMldIfQi OBJECT-TYPE
    SYNTAX      Unsigned32
    MAX-ACCESS  read-write
    STATUS      current
    DESCRIPTION
        "This setting Query Intervalis used to control MLD protocol stack as
         stated in RFC-3810 9.2."
    ::= { cie1000IpmcSnoopingConfigMldIfEntry 7 }

cie1000IpmcSnoopingConfigMldIfQri OBJECT-TYPE
    SYNTAX      Unsigned32
    MAX-ACCESS  read-write
    STATUS      current
    DESCRIPTION
        "This setting Query Response Intervalis used to control MLD protocol
         stack as stated in RFC-3810 9.3."
    ::= { cie1000IpmcSnoopingConfigMldIfEntry 8 }

cie1000IpmcSnoopingConfigMldIfLlqi OBJECT-TYPE
    SYNTAX      Unsigned32
    MAX-ACCESS  read-write
    STATUS      current
    DESCRIPTION
        "This setting Last Listener Query Interval is used to control MLD
         protocol stack as stated in RFC-3810 9.8."
    ::= { cie1000IpmcSnoopingConfigMldIfEntry 9 }

cie1000IpmcSnoopingConfigMldIfUri OBJECT-TYPE
    SYNTAX      Unsigned32
    MAX-ACCESS  read-write
    STATUS      current
    DESCRIPTION
        "This setting Unsolicited Report Intervalis used to control MLD protocol
         stack as stated in RFC-3810 9.11."
    ::= { cie1000IpmcSnoopingConfigMldIfEntry 10 }

cie1000IpmcSnoopingConfigMldIfAction OBJECT-TYPE
    SYNTAX      CIE1000RowEditorState
    MAX-ACCESS  read-write
    STATUS      current
    DESCRIPTION
        "Action"
    ::= { cie1000IpmcSnoopingConfigMldIfEntry 100 }

cie1000IpmcSnoopingConfigMldIfTableRowEditor OBJECT IDENTIFIER
    ::= { cie1000IpmcSnoopingConfig 8 }

cie1000IpmcSnoopingConfigMldIfTableRowEditorIfIndex OBJECT-TYPE
    SYNTAX      CIE1000InterfaceIndex
    MAX-ACCESS  read-write
    STATUS      current
    DESCRIPTION
        "Logical interface number of the VLAN interface."
    ::= { cie1000IpmcSnoopingConfigMldIfTableRowEditor 1 }

cie1000IpmcSnoopingConfigMldIfTableRowEditorAdminState OBJECT-TYPE
    SYNTAX      TruthValue
    MAX-ACCESS  read-write
    STATUS      current
    DESCRIPTION
        "Enable/Disable the MLD snooping per-VLAN functionality."
    ::= { cie1000IpmcSnoopingConfigMldIfTableRowEditor 2 }

cie1000IpmcSnoopingConfigMldIfTableRowEditorQuerierElection OBJECT-TYPE
    SYNTAX      TruthValue
    MAX-ACCESS  read-write
    STATUS      current
    DESCRIPTION
        "Enable/Disable the capability to run MLD Querier election per-VLAN
         basis."
    ::= { cie1000IpmcSnoopingConfigMldIfTableRowEditor 3 }

cie1000IpmcSnoopingConfigMldIfTableRowEditorCompatibility OBJECT-TYPE
    SYNTAX      CIE1000IpmcSnoopingMldInterfaceCompatibilityEnum
    MAX-ACCESS  read-write
    STATUS      current
    DESCRIPTION
        "The compatibility control for MLD snooping to run the corresponding
         protocol version."
    ::= { cie1000IpmcSnoopingConfigMldIfTableRowEditor 4 }

cie1000IpmcSnoopingConfigMldIfTableRowEditorPriority OBJECT-TYPE
    SYNTAX      CIE1000Unsigned8
    MAX-ACCESS  read-write
    STATUS      current
    DESCRIPTION
        "This setting is used for prioritizing the MLD control frames to be sent
         for MLD snooping."
    ::= { cie1000IpmcSnoopingConfigMldIfTableRowEditor 5 }

cie1000IpmcSnoopingConfigMldIfTableRowEditorRv OBJECT-TYPE
    SYNTAX      Unsigned32
    MAX-ACCESS  read-write
    STATUS      current
    DESCRIPTION
        "This setting Robustness Variableis used to control MLD protocol stack
         as stated in RFC-3810 9.1."
    ::= { cie1000IpmcSnoopingConfigMldIfTableRowEditor 6 }

cie1000IpmcSnoopingConfigMldIfTableRowEditorQi OBJECT-TYPE
    SYNTAX      Unsigned32
    MAX-ACCESS  read-write
    STATUS      current
    DESCRIPTION
        "This setting Query Intervalis used to control MLD protocol stack as
         stated in RFC-3810 9.2."
    ::= { cie1000IpmcSnoopingConfigMldIfTableRowEditor 7 }

cie1000IpmcSnoopingConfigMldIfTableRowEditorQri OBJECT-TYPE
    SYNTAX      Unsigned32
    MAX-ACCESS  read-write
    STATUS      current
    DESCRIPTION
        "This setting Query Response Intervalis used to control MLD protocol
         stack as stated in RFC-3810 9.3."
    ::= { cie1000IpmcSnoopingConfigMldIfTableRowEditor 8 }

cie1000IpmcSnoopingConfigMldIfTableRowEditorLlqi OBJECT-TYPE
    SYNTAX      Unsigned32
    MAX-ACCESS  read-write
    STATUS      current
    DESCRIPTION
        "This setting Last Listener Query Interval is used to control MLD
         protocol stack as stated in RFC-3810 9.8."
    ::= { cie1000IpmcSnoopingConfigMldIfTableRowEditor 9 }

cie1000IpmcSnoopingConfigMldIfTableRowEditorUri OBJECT-TYPE
    SYNTAX      Unsigned32
    MAX-ACCESS  read-write
    STATUS      current
    DESCRIPTION
        "This setting Unsolicited Report Intervalis used to control MLD protocol
         stack as stated in RFC-3810 9.11."
    ::= { cie1000IpmcSnoopingConfigMldIfTableRowEditor 10 }

cie1000IpmcSnoopingConfigMldIfTableRowEditorAction OBJECT-TYPE
    SYNTAX      CIE1000RowEditorState
    MAX-ACCESS  read-write
    STATUS      current
    DESCRIPTION
        "Action"
    ::= { cie1000IpmcSnoopingConfigMldIfTableRowEditor 100 }

cie1000IpmcSnoopingStatus OBJECT IDENTIFIER
    ::= { cie1000IpmcSnoopingMibObjects 3 }

cie1000IpmcSnoopingStatusGroupAddressCount OBJECT IDENTIFIER
    ::= { cie1000IpmcSnoopingStatus 1 }

cie1000IpmcSnoopingStatusGroupAddressCountFromIgmp OBJECT-TYPE
    SYNTAX      Unsigned32
    MAX-ACCESS  read-only
    STATUS      current
    DESCRIPTION
        "It is used to denote the total number of registered multicast group
         address from IGMP snooping."
    ::= { cie1000IpmcSnoopingStatusGroupAddressCount 1 }

cie1000IpmcSnoopingStatusGroupAddressCountFromMld OBJECT-TYPE
    SYNTAX      Unsigned32
    MAX-ACCESS  read-only
    STATUS      current
    DESCRIPTION
        "It is used to denote the total number of registered multicast group
         address from MLD snooping."
    ::= { cie1000IpmcSnoopingStatusGroupAddressCount 2 }

cie1000IpmcSnoopingStatusIgmpRouterPortTable OBJECT-TYPE
    SYNTAX      SEQUENCE OF CIE1000IpmcSnoopingStatusIgmpRouterPortEntry
    MAX-ACCESS  not-accessible
    STATUS      current
    DESCRIPTION
        "This is a table for displaying the router port status from IGMP
         snooping configuration."
    ::= { cie1000IpmcSnoopingStatus 2 }

cie1000IpmcSnoopingStatusIgmpRouterPortEntry OBJECT-TYPE
    SYNTAX      CIE1000IpmcSnoopingStatusIgmpRouterPortEntry
    MAX-ACCESS  not-accessible
    STATUS      current
    DESCRIPTION
        "Each entry has a set of parameters."
    INDEX       { cie1000IpmcSnoopingStatusIgmpRouterPortPortIndex }
    ::= { cie1000IpmcSnoopingStatusIgmpRouterPortTable 1 }

CIE1000IpmcSnoopingStatusIgmpRouterPortEntry ::= SEQUENCE {
    cie1000IpmcSnoopingStatusIgmpRouterPortPortIndex  CIE1000InterfaceIndex,
    cie1000IpmcSnoopingStatusIgmpRouterPortStatus     CIE1000IpmcSnoopingIgmpRouterPortStatusEnum
}

cie1000IpmcSnoopingStatusIgmpRouterPortPortIndex OBJECT-TYPE
    SYNTAX      CIE1000InterfaceIndex
    MAX-ACCESS  accessible-for-notify
    STATUS      current
    DESCRIPTION
        "Logical interface number of the physical port."
    ::= { cie1000IpmcSnoopingStatusIgmpRouterPortEntry 1 }

cie1000IpmcSnoopingStatusIgmpRouterPortStatus OBJECT-TYPE
    SYNTAX      CIE1000IpmcSnoopingIgmpRouterPortStatusEnum
    MAX-ACCESS  read-only
    STATUS      current
    DESCRIPTION
        "The IGMP snooping router port status."
    ::= { cie1000IpmcSnoopingStatusIgmpRouterPortEntry 2 }

cie1000IpmcSnoopingStatusIgmpVlanTable OBJECT-TYPE
    SYNTAX      SEQUENCE OF CIE1000IpmcSnoopingStatusIgmpVlanEntry
    MAX-ACCESS  not-accessible
    STATUS      current
    DESCRIPTION
        "This is a table for displaying the per VLAN interface status in IGMP
         snooping configuration."
    ::= { cie1000IpmcSnoopingStatus 3 }

cie1000IpmcSnoopingStatusIgmpVlanEntry OBJECT-TYPE
    SYNTAX      CIE1000IpmcSnoopingStatusIgmpVlanEntry
    MAX-ACCESS  not-accessible
    STATUS      current
    DESCRIPTION
        "Each entry has a set of parameters."
    INDEX       { cie1000IpmcSnoopingStatusIgmpVlanIfIndex }
    ::= { cie1000IpmcSnoopingStatusIgmpVlanTable 1 }

CIE1000IpmcSnoopingStatusIgmpVlanEntry ::= SEQUENCE {
    cie1000IpmcSnoopingStatusIgmpVlanIfIndex                 CIE1000InterfaceIndex,
    cie1000IpmcSnoopingStatusIgmpVlanQuerierStatus           CIE1000IpmcSnoopingIgmpVlanStatusQuerierStatusEnum,
    cie1000IpmcSnoopingStatusIgmpVlanActiveQuerierAddress    IpAddress,
    cie1000IpmcSnoopingStatusIgmpVlanQuerierUptime           Unsigned32,
    cie1000IpmcSnoopingStatusIgmpVlanQueryInterval           Unsigned32,
    cie1000IpmcSnoopingStatusIgmpVlanStartupQueryCount       Unsigned32,
    cie1000IpmcSnoopingStatusIgmpVlanQuerierExpiryTime       Unsigned32,
    cie1000IpmcSnoopingStatusIgmpVlanQuerierVersion          CIE1000Unsigned8,
    cie1000IpmcSnoopingStatusIgmpVlanQuerierPresentTimeout   Unsigned32,
    cie1000IpmcSnoopingStatusIgmpVlanHostVersion             CIE1000Unsigned8,
    cie1000IpmcSnoopingStatusIgmpVlanHostPresentTimeout      Unsigned32,
    cie1000IpmcSnoopingStatusIgmpVlanCounterTxQuery          Unsigned32,
    cie1000IpmcSnoopingStatusIgmpVlanCounterTxSpecificQuery  Unsigned32,
    cie1000IpmcSnoopingStatusIgmpVlanCounterRxQuery          Unsigned32,
    cie1000IpmcSnoopingStatusIgmpVlanCounterRxV1Join         Unsigned32,
    cie1000IpmcSnoopingStatusIgmpVlanCounterRxV2Join         Unsigned32,
    cie1000IpmcSnoopingStatusIgmpVlanCounterRxV2Leave        Unsigned32,
    cie1000IpmcSnoopingStatusIgmpVlanCounterRxV3Join         Unsigned32,
    cie1000IpmcSnoopingStatusIgmpVlanCounterRxErrors         Unsigned32
}

cie1000IpmcSnoopingStatusIgmpVlanIfIndex OBJECT-TYPE
    SYNTAX      CIE1000InterfaceIndex
    MAX-ACCESS  accessible-for-notify
    STATUS      current
    DESCRIPTION
        "Logical interface number of the VLAN interface."
    ::= { cie1000IpmcSnoopingStatusIgmpVlanEntry 1 }

cie1000IpmcSnoopingStatusIgmpVlanQuerierStatus OBJECT-TYPE
    SYNTAX      CIE1000IpmcSnoopingIgmpVlanStatusQuerierStatusEnum
    MAX-ACCESS  read-only
    STATUS      current
    DESCRIPTION
        "The IGMP Querier status of the specific VLAN interface."
    ::= { cie1000IpmcSnoopingStatusIgmpVlanEntry 2 }

cie1000IpmcSnoopingStatusIgmpVlanActiveQuerierAddress OBJECT-TYPE
    SYNTAX      IpAddress
    MAX-ACCESS  read-only
    STATUS      current
    DESCRIPTION
        "The active IGMP Querier address on the specific VLAN interface."
    ::= { cie1000IpmcSnoopingStatusIgmpVlanEntry 3 }

cie1000IpmcSnoopingStatusIgmpVlanQuerierUptime OBJECT-TYPE
    SYNTAX      Unsigned32
    MAX-ACCESS  read-only
    STATUS      current
    DESCRIPTION
        "It presents the in operation timer for the specific interface act as a
         IGMP Querier."
    ::= { cie1000IpmcSnoopingStatusIgmpVlanEntry 4 }

cie1000IpmcSnoopingStatusIgmpVlanQueryInterval OBJECT-TYPE
    SYNTAX      Unsigned32
    MAX-ACCESS  read-only
    STATUS      current
    DESCRIPTION
        "This setting is used to control IGMP protocol stack as stated in
         RFC-3376 8.2."
    ::= { cie1000IpmcSnoopingStatusIgmpVlanEntry 5 }

cie1000IpmcSnoopingStatusIgmpVlanStartupQueryCount OBJECT-TYPE
    SYNTAX      Unsigned32
    MAX-ACCESS  read-only
    STATUS      current
    DESCRIPTION
        "This setting is used to control IGMP protocol stack as stated in
         RFC-3376 8.7."
    ::= { cie1000IpmcSnoopingStatusIgmpVlanEntry 6 }

cie1000IpmcSnoopingStatusIgmpVlanQuerierExpiryTime OBJECT-TYPE
    SYNTAX      Unsigned32
    MAX-ACCESS  read-only
    STATUS      current
    DESCRIPTION
        "This setting is used to control IGMP protocol stack as stated in
         RFC-3376 8.5."
    ::= { cie1000IpmcSnoopingStatusIgmpVlanEntry 7 }

cie1000IpmcSnoopingStatusIgmpVlanQuerierVersion OBJECT-TYPE
    SYNTAX      CIE1000Unsigned8
    MAX-ACCESS  read-only
    STATUS      current
    DESCRIPTION
        "It presents the current IGMP version that the IGMP interface should
         behave in running IGMP protocol as a router."
    ::= { cie1000IpmcSnoopingStatusIgmpVlanEntry 8 }

cie1000IpmcSnoopingStatusIgmpVlanQuerierPresentTimeout OBJECT-TYPE
    SYNTAX      Unsigned32
    MAX-ACCESS  read-only
    STATUS      current
    DESCRIPTION
        "This setting is used to control IGMP protocol stack as stated in
         RFC-3376 8.12."
    ::= { cie1000IpmcSnoopingStatusIgmpVlanEntry 9 }

cie1000IpmcSnoopingStatusIgmpVlanHostVersion OBJECT-TYPE
    SYNTAX      CIE1000Unsigned8
    MAX-ACCESS  read-only
    STATUS      current
    DESCRIPTION
        "It presents the current IGMP version that the IGMP interface should
         behave in running IGMP protocol as a host."
    ::= { cie1000IpmcSnoopingStatusIgmpVlanEntry 10 }

cie1000IpmcSnoopingStatusIgmpVlanHostPresentTimeout OBJECT-TYPE
    SYNTAX      Unsigned32
    MAX-ACCESS  read-only
    STATUS      current
    DESCRIPTION
        "This setting is used to control IGMP protocol stack as stated in
         RFC-3376 8.13."
    ::= { cie1000IpmcSnoopingStatusIgmpVlanEntry 11 }

cie1000IpmcSnoopingStatusIgmpVlanCounterTxQuery OBJECT-TYPE
    SYNTAX      Unsigned32
    MAX-ACCESS  read-only
    STATUS      current
    DESCRIPTION
        "It presents the current packet count on the specific IGMP interface for
         transmitting IGMP Query control frames."
    ::= { cie1000IpmcSnoopingStatusIgmpVlanEntry 12 }

cie1000IpmcSnoopingStatusIgmpVlanCounterTxSpecificQuery OBJECT-TYPE
    SYNTAX      Unsigned32
    MAX-ACCESS  read-only
    STATUS      current
    DESCRIPTION
        "It presents the current packet count on the specific IGMP interface for
         transmitting IGMP Specific Query control frames."
    ::= { cie1000IpmcSnoopingStatusIgmpVlanEntry 13 }

cie1000IpmcSnoopingStatusIgmpVlanCounterRxQuery OBJECT-TYPE
    SYNTAX      Unsigned32
    MAX-ACCESS  read-only
    STATUS      current
    DESCRIPTION
        "It presents the current packet count on the specific IGMP interface for
         receiving IGMP Query control frames."
    ::= { cie1000IpmcSnoopingStatusIgmpVlanEntry 14 }

cie1000IpmcSnoopingStatusIgmpVlanCounterRxV1Join OBJECT-TYPE
    SYNTAX      Unsigned32
    MAX-ACCESS  read-only
    STATUS      current
    DESCRIPTION
        "It presents the current packet count on the specific IGMP interface for
         receiving IGMPv1 Join control frames."
    ::= { cie1000IpmcSnoopingStatusIgmpVlanEntry 15 }

cie1000IpmcSnoopingStatusIgmpVlanCounterRxV2Join OBJECT-TYPE
    SYNTAX      Unsigned32
    MAX-ACCESS  read-only
    STATUS      current
    DESCRIPTION
        "It presents the current packet count on the specific IGMP interface for
         receiving IGMPv2 Join control frames."
    ::= { cie1000IpmcSnoopingStatusIgmpVlanEntry 16 }

cie1000IpmcSnoopingStatusIgmpVlanCounterRxV2Leave OBJECT-TYPE
    SYNTAX      Unsigned32
    MAX-ACCESS  read-only
    STATUS      current
    DESCRIPTION
        "It presents the current packet count on the specific IGMP interface for
         receiving IGMPv2 Leave control frames."
    ::= { cie1000IpmcSnoopingStatusIgmpVlanEntry 17 }

cie1000IpmcSnoopingStatusIgmpVlanCounterRxV3Join OBJECT-TYPE
    SYNTAX      Unsigned32
    MAX-ACCESS  read-only
    STATUS      current
    DESCRIPTION
        "It presents the current packet count on the specific IGMP interface for
         receiving IGMPv3 Join control frames."
    ::= { cie1000IpmcSnoopingStatusIgmpVlanEntry 18 }

cie1000IpmcSnoopingStatusIgmpVlanCounterRxErrors OBJECT-TYPE
    SYNTAX      Unsigned32
    MAX-ACCESS  read-only
    STATUS      current
    DESCRIPTION
        "It presents the current packet count on the specific IGMP interface for
         receiving invalid IGMP control frames."
    ::= { cie1000IpmcSnoopingStatusIgmpVlanEntry 19 }

cie1000IpmcSnoopingStatusIgmpGroupAddressTable OBJECT-TYPE
    SYNTAX      SEQUENCE OF CIE1000IpmcSnoopingStatusIgmpGroupAddressEntry
    MAX-ACCESS  not-accessible
    STATUS      current
    DESCRIPTION
        "This is a table for displaying the registered IPv4 multicast group
         address status from IGMP snooping."
    ::= { cie1000IpmcSnoopingStatus 4 }

cie1000IpmcSnoopingStatusIgmpGroupAddressEntry OBJECT-TYPE
    SYNTAX      CIE1000IpmcSnoopingStatusIgmpGroupAddressEntry
    MAX-ACCESS  not-accessible
    STATUS      current
    DESCRIPTION
        "Each entry has a set of parameters."
    INDEX       { cie1000IpmcSnoopingStatusIgmpGroupAddressIfIndex,
                  cie1000IpmcSnoopingStatusIgmpGroupAddressGroupAddress }
    ::= { cie1000IpmcSnoopingStatusIgmpGroupAddressTable 1 }

CIE1000IpmcSnoopingStatusIgmpGroupAddressEntry ::= SEQUENCE {
    cie1000IpmcSnoopingStatusIgmpGroupAddressIfIndex         CIE1000InterfaceIndex,
    cie1000IpmcSnoopingStatusIgmpGroupAddressGroupAddress    IpAddress,
    cie1000IpmcSnoopingStatusIgmpGroupAddressMemberPorts     CIE1000PortList,
    cie1000IpmcSnoopingStatusIgmpGroupAddressHardwareSwitch  TruthValue
}

cie1000IpmcSnoopingStatusIgmpGroupAddressIfIndex OBJECT-TYPE
    SYNTAX      CIE1000InterfaceIndex
    MAX-ACCESS  accessible-for-notify
    STATUS      current
    DESCRIPTION
        "Logical interface number of the VLAN interface."
    ::= { cie1000IpmcSnoopingStatusIgmpGroupAddressEntry 1 }

cie1000IpmcSnoopingStatusIgmpGroupAddressGroupAddress OBJECT-TYPE
    SYNTAX      IpAddress
    MAX-ACCESS  accessible-for-notify
    STATUS      current
    DESCRIPTION
        "Assigned IPv4 multicast address."
    ::= { cie1000IpmcSnoopingStatusIgmpGroupAddressEntry 2 }

cie1000IpmcSnoopingStatusIgmpGroupAddressMemberPorts OBJECT-TYPE
    SYNTAX      CIE1000PortList
    MAX-ACCESS  read-only
    STATUS      current
    DESCRIPTION
        "It is used to denote the memberships of the registered multicast group
         address from IGMP snooping."
    ::= { cie1000IpmcSnoopingStatusIgmpGroupAddressEntry 3 }

cie1000IpmcSnoopingStatusIgmpGroupAddressHardwareSwitch OBJECT-TYPE
    SYNTAX      TruthValue
    MAX-ACCESS  read-only
    STATUS      current
    DESCRIPTION
        "It is used to denote whether the multicast traffic destined to the
         registered group address could be forwarding by switch hardware or not."
    ::= { cie1000IpmcSnoopingStatusIgmpGroupAddressEntry 4 }

cie1000IpmcSnoopingStatusIgmpGroupSrcListTable OBJECT-TYPE
    SYNTAX      SEQUENCE OF CIE1000IpmcSnoopingStatusIgmpGroupSrcListEntry
    MAX-ACCESS  not-accessible
    STATUS      current
    DESCRIPTION
        "This is a table for displaying the address SFM (a.k.a Source List
         Multicast) status in source list of the registered IPv4 multicast group
         from IGMP snooping."
    ::= { cie1000IpmcSnoopingStatus 5 }

cie1000IpmcSnoopingStatusIgmpGroupSrcListEntry OBJECT-TYPE
    SYNTAX      CIE1000IpmcSnoopingStatusIgmpGroupSrcListEntry
    MAX-ACCESS  not-accessible
    STATUS      current
    DESCRIPTION
        "Each entry has a set of parameters."
    INDEX       { cie1000IpmcSnoopingStatusIgmpGroupSrcListIfIndex,
                  cie1000IpmcSnoopingStatusIgmpGroupSrcListGroupAddress,
                  cie1000IpmcSnoopingStatusIgmpGroupSrcListPortIndex,
                  cie1000IpmcSnoopingStatusIgmpGroupSrcListHostAddress }
    ::= { cie1000IpmcSnoopingStatusIgmpGroupSrcListTable 1 }

CIE1000IpmcSnoopingStatusIgmpGroupSrcListEntry ::= SEQUENCE {
    cie1000IpmcSnoopingStatusIgmpGroupSrcListIfIndex          CIE1000InterfaceIndex,
    cie1000IpmcSnoopingStatusIgmpGroupSrcListGroupAddress     IpAddress,
    cie1000IpmcSnoopingStatusIgmpGroupSrcListPortIndex        CIE1000InterfaceIndex,
    cie1000IpmcSnoopingStatusIgmpGroupSrcListHostAddress      IpAddress,
    cie1000IpmcSnoopingStatusIgmpGroupSrcListGroupFilterMode  CIE1000IpmcSnoopingIgmpGroupSrcListGroupFilterModeEnum,
    cie1000IpmcSnoopingStatusIgmpGroupSrcListFilterTimer      Unsigned32,
    cie1000IpmcSnoopingStatusIgmpGroupSrcListSourceType       CIE1000IpmcSnoopingIgmpGroupSrcListSourceTypeEnum,
    cie1000IpmcSnoopingStatusIgmpGroupSrcListSourceTimer      Unsigned32,
    cie1000IpmcSnoopingStatusIgmpGroupSrcListHardwareFilter   TruthValue
}

cie1000IpmcSnoopingStatusIgmpGroupSrcListIfIndex OBJECT-TYPE
    SYNTAX      CIE1000InterfaceIndex
    MAX-ACCESS  accessible-for-notify
    STATUS      current
    DESCRIPTION
        "Logical interface number of the VLAN interface."
    ::= { cie1000IpmcSnoopingStatusIgmpGroupSrcListEntry 1 }

cie1000IpmcSnoopingStatusIgmpGroupSrcListGroupAddress OBJECT-TYPE
    SYNTAX      IpAddress
    MAX-ACCESS  accessible-for-notify
    STATUS      current
    DESCRIPTION
        "Assigned IPv4 multicast address."
    ::= { cie1000IpmcSnoopingStatusIgmpGroupSrcListEntry 2 }

cie1000IpmcSnoopingStatusIgmpGroupSrcListPortIndex OBJECT-TYPE
    SYNTAX      CIE1000InterfaceIndex
    MAX-ACCESS  accessible-for-notify
    STATUS      current
    DESCRIPTION
        "Logical interface number of the physical port."
    ::= { cie1000IpmcSnoopingStatusIgmpGroupSrcListEntry 3 }

cie1000IpmcSnoopingStatusIgmpGroupSrcListHostAddress OBJECT-TYPE
    SYNTAX      IpAddress
    MAX-ACCESS  accessible-for-notify
    STATUS      current
    DESCRIPTION
        "Assigned IPv4 source address."
    ::= { cie1000IpmcSnoopingStatusIgmpGroupSrcListEntry 4 }

cie1000IpmcSnoopingStatusIgmpGroupSrcListGroupFilterMode OBJECT-TYPE
    SYNTAX      CIE1000IpmcSnoopingIgmpGroupSrcListGroupFilterModeEnum
    MAX-ACCESS  read-only
    STATUS      current
    DESCRIPTION
        "It is used to denote the source filtering mode of the specific
         registered multicast group address from IGMP snooping."
    ::= { cie1000IpmcSnoopingStatusIgmpGroupSrcListEntry 5 }

cie1000IpmcSnoopingStatusIgmpGroupSrcListFilterTimer OBJECT-TYPE
    SYNTAX      Unsigned32
    MAX-ACCESS  read-only
    STATUS      current
    DESCRIPTION
        "It is used to count down the timer for the specific multicast group's
         filtering mode transition."
    ::= { cie1000IpmcSnoopingStatusIgmpGroupSrcListEntry 6 }

cie1000IpmcSnoopingStatusIgmpGroupSrcListSourceType OBJECT-TYPE
    SYNTAX      CIE1000IpmcSnoopingIgmpGroupSrcListSourceTypeEnum
    MAX-ACCESS  read-only
    STATUS      current
    DESCRIPTION
        "It is used to denote the filtering type of the specific source address
         in multicasting to the registered group address."
    ::= { cie1000IpmcSnoopingStatusIgmpGroupSrcListEntry 7 }

cie1000IpmcSnoopingStatusIgmpGroupSrcListSourceTimer OBJECT-TYPE
    SYNTAX      Unsigned32
    MAX-ACCESS  read-only
    STATUS      current
    DESCRIPTION
        "It is used to count down the timer for purging the specific source
         address from the registered multicast group's source list."
    ::= { cie1000IpmcSnoopingStatusIgmpGroupSrcListEntry 8 }

cie1000IpmcSnoopingStatusIgmpGroupSrcListHardwareFilter OBJECT-TYPE
    SYNTAX      TruthValue
    MAX-ACCESS  read-only
    STATUS      current
    DESCRIPTION
        "It is used to denote whether the traffic destined to the multicast
         group address from the specific source address could be forwarding by
         switch hardware or not."
    ::= { cie1000IpmcSnoopingStatusIgmpGroupSrcListEntry 9 }

cie1000IpmcSnoopingStatusMldRouterPortTable OBJECT-TYPE
    SYNTAX      SEQUENCE OF CIE1000IpmcSnoopingStatusMldRouterPortEntry
    MAX-ACCESS  not-accessible
    STATUS      current
    DESCRIPTION
        "This is a table for displaying the router port status from MLD snooping
         configuration."
    ::= { cie1000IpmcSnoopingStatus 6 }

cie1000IpmcSnoopingStatusMldRouterPortEntry OBJECT-TYPE
    SYNTAX      CIE1000IpmcSnoopingStatusMldRouterPortEntry
    MAX-ACCESS  not-accessible
    STATUS      current
    DESCRIPTION
        "Each entry has a set of parameters."
    INDEX       { cie1000IpmcSnoopingStatusMldRouterPortPortIndex }
    ::= { cie1000IpmcSnoopingStatusMldRouterPortTable 1 }

CIE1000IpmcSnoopingStatusMldRouterPortEntry ::= SEQUENCE {
    cie1000IpmcSnoopingStatusMldRouterPortPortIndex  CIE1000InterfaceIndex,
    cie1000IpmcSnoopingStatusMldRouterPortStatus     CIE1000IpmcSnoopingMldRouterPortStatusEnum
}

cie1000IpmcSnoopingStatusMldRouterPortPortIndex OBJECT-TYPE
    SYNTAX      CIE1000InterfaceIndex
    MAX-ACCESS  accessible-for-notify
    STATUS      current
    DESCRIPTION
        "Logical interface number of the physical port."
    ::= { cie1000IpmcSnoopingStatusMldRouterPortEntry 1 }

cie1000IpmcSnoopingStatusMldRouterPortStatus OBJECT-TYPE
    SYNTAX      CIE1000IpmcSnoopingMldRouterPortStatusEnum
    MAX-ACCESS  read-only
    STATUS      current
    DESCRIPTION
        "The MLD snooping router port status."
    ::= { cie1000IpmcSnoopingStatusMldRouterPortEntry 2 }

cie1000IpmcSnoopingStatusMldVlanTable OBJECT-TYPE
    SYNTAX      SEQUENCE OF CIE1000IpmcSnoopingStatusMldVlanEntry
    MAX-ACCESS  not-accessible
    STATUS      current
    DESCRIPTION
        "This is a table for displaying the per VLAN interface status in MLD
         snooping configuration."
    ::= { cie1000IpmcSnoopingStatus 7 }

cie1000IpmcSnoopingStatusMldVlanEntry OBJECT-TYPE
    SYNTAX      CIE1000IpmcSnoopingStatusMldVlanEntry
    MAX-ACCESS  not-accessible
    STATUS      current
    DESCRIPTION
        "Each entry has a set of parameters."
    INDEX       { cie1000IpmcSnoopingStatusMldVlanIfIndex }
    ::= { cie1000IpmcSnoopingStatusMldVlanTable 1 }

CIE1000IpmcSnoopingStatusMldVlanEntry ::= SEQUENCE {
    cie1000IpmcSnoopingStatusMldVlanIfIndex                 CIE1000InterfaceIndex,
    cie1000IpmcSnoopingStatusMldVlanQuerierStatus           CIE1000IpmcSnoopingMldVlanStatusQuerierStatusEnum,
    cie1000IpmcSnoopingStatusMldVlanActiveQuerierAddress    InetAddressIPv6,
    cie1000IpmcSnoopingStatusMldVlanQuerierUptime           Unsigned32,
    cie1000IpmcSnoopingStatusMldVlanQueryInterval           Unsigned32,
    cie1000IpmcSnoopingStatusMldVlanStartupQueryCount       Unsigned32,
    cie1000IpmcSnoopingStatusMldVlanQuerierExpiryTime       Unsigned32,
    cie1000IpmcSnoopingStatusMldVlanQuerierVersion          CIE1000Unsigned8,
    cie1000IpmcSnoopingStatusMldVlanQuerierPresentTimeout   Unsigned32,
    cie1000IpmcSnoopingStatusMldVlanHostVersion             CIE1000Unsigned8,
    cie1000IpmcSnoopingStatusMldVlanHostPresentTimeout      Unsigned32,
    cie1000IpmcSnoopingStatusMldVlanCounterTxQuery          Unsigned32,
    cie1000IpmcSnoopingStatusMldVlanCounterTxSpecificQuery  Unsigned32,
    cie1000IpmcSnoopingStatusMldVlanCounterRxQuery          Unsigned32,
    cie1000IpmcSnoopingStatusMldVlanCounterRxV1Report       Unsigned32,
    cie1000IpmcSnoopingStatusMldVlanCounterRxV1Done         Unsigned32,
    cie1000IpmcSnoopingStatusMldVlanCounterRxV2Report       Unsigned32,
    cie1000IpmcSnoopingStatusMldVlanCounterRxErrors         Unsigned32
}

cie1000IpmcSnoopingStatusMldVlanIfIndex OBJECT-TYPE
    SYNTAX      CIE1000InterfaceIndex
    MAX-ACCESS  accessible-for-notify
    STATUS      current
    DESCRIPTION
        "Logical interface number of the VLAN interface."
    ::= { cie1000IpmcSnoopingStatusMldVlanEntry 1 }

cie1000IpmcSnoopingStatusMldVlanQuerierStatus OBJECT-TYPE
    SYNTAX      CIE1000IpmcSnoopingMldVlanStatusQuerierStatusEnum
    MAX-ACCESS  read-only
    STATUS      current
    DESCRIPTION
        "The MLD Querier status of the specific VLAN interface."
    ::= { cie1000IpmcSnoopingStatusMldVlanEntry 2 }

cie1000IpmcSnoopingStatusMldVlanActiveQuerierAddress OBJECT-TYPE
    SYNTAX      InetAddressIPv6
    MAX-ACCESS  read-only
    STATUS      current
    DESCRIPTION
        "The active MLD Querier address on the specific VLAN interface."
    ::= { cie1000IpmcSnoopingStatusMldVlanEntry 3 }

cie1000IpmcSnoopingStatusMldVlanQuerierUptime OBJECT-TYPE
    SYNTAX      Unsigned32
    MAX-ACCESS  read-only
    STATUS      current
    DESCRIPTION
        "It presents the in operation timer for the specific interface act as a
         MLD Querier."
    ::= { cie1000IpmcSnoopingStatusMldVlanEntry 4 }

cie1000IpmcSnoopingStatusMldVlanQueryInterval OBJECT-TYPE
    SYNTAX      Unsigned32
    MAX-ACCESS  read-only
    STATUS      current
    DESCRIPTION
        "This setting is used to control MLD protocol stack as stated in
         RFC-3810 9.2."
    ::= { cie1000IpmcSnoopingStatusMldVlanEntry 5 }

cie1000IpmcSnoopingStatusMldVlanStartupQueryCount OBJECT-TYPE
    SYNTAX      Unsigned32
    MAX-ACCESS  read-only
    STATUS      current
    DESCRIPTION
        "This setting is used to control MLD protocol stack as stated in
         RFC-3810 9.7."
    ::= { cie1000IpmcSnoopingStatusMldVlanEntry 6 }

cie1000IpmcSnoopingStatusMldVlanQuerierExpiryTime OBJECT-TYPE
    SYNTAX      Unsigned32
    MAX-ACCESS  read-only
    STATUS      current
    DESCRIPTION
        "This setting is used to control MLD protocol stack as stated in
         RFC-3810 9.5."
    ::= { cie1000IpmcSnoopingStatusMldVlanEntry 7 }

cie1000IpmcSnoopingStatusMldVlanQuerierVersion OBJECT-TYPE
    SYNTAX      CIE1000Unsigned8
    MAX-ACCESS  read-only
    STATUS      current
    DESCRIPTION
        "It presents the current MLD version that the MLD interface should
         behave in running MLD protocol as a router."
    ::= { cie1000IpmcSnoopingStatusMldVlanEntry 8 }

cie1000IpmcSnoopingStatusMldVlanQuerierPresentTimeout OBJECT-TYPE
    SYNTAX      Unsigned32
    MAX-ACCESS  read-only
    STATUS      current
    DESCRIPTION
        "This setting is used to control MLD protocol stack as stated in
         RFC-3810 9.12."
    ::= { cie1000IpmcSnoopingStatusMldVlanEntry 9 }

cie1000IpmcSnoopingStatusMldVlanHostVersion OBJECT-TYPE
    SYNTAX      CIE1000Unsigned8
    MAX-ACCESS  read-only
    STATUS      current
    DESCRIPTION
        "It presents the current MLD version that the MLD interface should
         behave in running MLD protocol as a host."
    ::= { cie1000IpmcSnoopingStatusMldVlanEntry 10 }

cie1000IpmcSnoopingStatusMldVlanHostPresentTimeout OBJECT-TYPE
    SYNTAX      Unsigned32
    MAX-ACCESS  read-only
    STATUS      current
    DESCRIPTION
        "This setting is used to control MLD protocol stack as stated in
         RFC-3810 9.13."
    ::= { cie1000IpmcSnoopingStatusMldVlanEntry 11 }

cie1000IpmcSnoopingStatusMldVlanCounterTxQuery OBJECT-TYPE
    SYNTAX      Unsigned32
    MAX-ACCESS  read-only
    STATUS      current
    DESCRIPTION
        "It presents the current packet count on the specific MLD interface for
         transmitting MLD Query control frames."
    ::= { cie1000IpmcSnoopingStatusMldVlanEntry 12 }

cie1000IpmcSnoopingStatusMldVlanCounterTxSpecificQuery OBJECT-TYPE
    SYNTAX      Unsigned32
    MAX-ACCESS  read-only
    STATUS      current
    DESCRIPTION
        "It presents the current packet count on the specific MLD interface for
         transmitting MLD Specific Query control frames."
    ::= { cie1000IpmcSnoopingStatusMldVlanEntry 13 }

cie1000IpmcSnoopingStatusMldVlanCounterRxQuery OBJECT-TYPE
    SYNTAX      Unsigned32
    MAX-ACCESS  read-only
    STATUS      current
    DESCRIPTION
        "It presents the current packet count on the specific MLD interface for
         receiving MLD Query control frames."
    ::= { cie1000IpmcSnoopingStatusMldVlanEntry 14 }

cie1000IpmcSnoopingStatusMldVlanCounterRxV1Report OBJECT-TYPE
    SYNTAX      Unsigned32
    MAX-ACCESS  read-only
    STATUS      current
    DESCRIPTION
        "It presents the current packet count on the specific MLD interface for
         receiving MLDv1 Report control frames."
    ::= { cie1000IpmcSnoopingStatusMldVlanEntry 15 }

cie1000IpmcSnoopingStatusMldVlanCounterRxV1Done OBJECT-TYPE
    SYNTAX      Unsigned32
    MAX-ACCESS  read-only
    STATUS      current
    DESCRIPTION
        "It presents the current packet count on the specific MLD interface for
         receiving MLDv1 Done control frames."
    ::= { cie1000IpmcSnoopingStatusMldVlanEntry 16 }

cie1000IpmcSnoopingStatusMldVlanCounterRxV2Report OBJECT-TYPE
    SYNTAX      Unsigned32
    MAX-ACCESS  read-only
    STATUS      current
    DESCRIPTION
        "It presents the current packet count on the specific MLD interface for
         receiving MLDv2 Report control frames."
    ::= { cie1000IpmcSnoopingStatusMldVlanEntry 17 }

cie1000IpmcSnoopingStatusMldVlanCounterRxErrors OBJECT-TYPE
    SYNTAX      Unsigned32
    MAX-ACCESS  read-only
    STATUS      current
    DESCRIPTION
        "It presents the current packet count on the specific MLD interface for
         receiving invalid MLD control frames."
    ::= { cie1000IpmcSnoopingStatusMldVlanEntry 18 }

cie1000IpmcSnoopingStatusMldGroupAddressTable OBJECT-TYPE
    SYNTAX      SEQUENCE OF CIE1000IpmcSnoopingStatusMldGroupAddressEntry
    MAX-ACCESS  not-accessible
    STATUS      current
    DESCRIPTION
        "This is a table for displaying the registered IPv6 multicast group
         address status from MLD snooping."
    ::= { cie1000IpmcSnoopingStatus 8 }

cie1000IpmcSnoopingStatusMldGroupAddressEntry OBJECT-TYPE
    SYNTAX      CIE1000IpmcSnoopingStatusMldGroupAddressEntry
    MAX-ACCESS  not-accessible
    STATUS      current
    DESCRIPTION
        "Each entry has a set of parameters."
    INDEX       { cie1000IpmcSnoopingStatusMldGroupAddressIfIndex,
                  cie1000IpmcSnoopingStatusMldGroupAddressGroupAddress }
    ::= { cie1000IpmcSnoopingStatusMldGroupAddressTable 1 }

CIE1000IpmcSnoopingStatusMldGroupAddressEntry ::= SEQUENCE {
    cie1000IpmcSnoopingStatusMldGroupAddressIfIndex         CIE1000InterfaceIndex,
    cie1000IpmcSnoopingStatusMldGroupAddressGroupAddress    InetAddressIPv6,
    cie1000IpmcSnoopingStatusMldGroupAddressMemberPorts     CIE1000PortList,
    cie1000IpmcSnoopingStatusMldGroupAddressHardwareSwitch  TruthValue
}

cie1000IpmcSnoopingStatusMldGroupAddressIfIndex OBJECT-TYPE
    SYNTAX      CIE1000InterfaceIndex
    MAX-ACCESS  accessible-for-notify
    STATUS      current
    DESCRIPTION
        "Logical interface number of the VLAN interface."
    ::= { cie1000IpmcSnoopingStatusMldGroupAddressEntry 1 }

cie1000IpmcSnoopingStatusMldGroupAddressGroupAddress OBJECT-TYPE
    SYNTAX      InetAddressIPv6
    MAX-ACCESS  accessible-for-notify
    STATUS      current
    DESCRIPTION
        "Assigned IPv6 multicast address."
    ::= { cie1000IpmcSnoopingStatusMldGroupAddressEntry 2 }

cie1000IpmcSnoopingStatusMldGroupAddressMemberPorts OBJECT-TYPE
    SYNTAX      CIE1000PortList
    MAX-ACCESS  read-only
    STATUS      current
    DESCRIPTION
        "It is used to denote the memberships of the registered multicast group
         address from MLD snooping."
    ::= { cie1000IpmcSnoopingStatusMldGroupAddressEntry 3 }

cie1000IpmcSnoopingStatusMldGroupAddressHardwareSwitch OBJECT-TYPE
    SYNTAX      TruthValue
    MAX-ACCESS  read-only
    STATUS      current
    DESCRIPTION
        "It is used to denote whether the multicast traffic destined to the
         registered group address could be forwarding by switch hardware or not."
    ::= { cie1000IpmcSnoopingStatusMldGroupAddressEntry 4 }

cie1000IpmcSnoopingStatusMldGroupSrcListTable OBJECT-TYPE
    SYNTAX      SEQUENCE OF CIE1000IpmcSnoopingStatusMldGroupSrcListEntry
    MAX-ACCESS  not-accessible
    STATUS      current
    DESCRIPTION
        "This is a table for displaying the address SFM (a.k.a Source List
         Multicast) status in source list of the registered IPv6 multicast group
         from MLD snooping."
    ::= { cie1000IpmcSnoopingStatus 9 }

cie1000IpmcSnoopingStatusMldGroupSrcListEntry OBJECT-TYPE
    SYNTAX      CIE1000IpmcSnoopingStatusMldGroupSrcListEntry
    MAX-ACCESS  not-accessible
    STATUS      current
    DESCRIPTION
        "Each entry has a set of parameters."
    INDEX       { cie1000IpmcSnoopingStatusMldGroupSrcListIfIndex,
                  cie1000IpmcSnoopingStatusMldGroupSrcListGroupAddress,
                  cie1000IpmcSnoopingStatusMldGroupSrcListPortIndex,
                  cie1000IpmcSnoopingStatusMldGroupSrcListHostAddress }
    ::= { cie1000IpmcSnoopingStatusMldGroupSrcListTable 1 }

CIE1000IpmcSnoopingStatusMldGroupSrcListEntry ::= SEQUENCE {
    cie1000IpmcSnoopingStatusMldGroupSrcListIfIndex          CIE1000InterfaceIndex,
    cie1000IpmcSnoopingStatusMldGroupSrcListGroupAddress     InetAddressIPv6,
    cie1000IpmcSnoopingStatusMldGroupSrcListPortIndex        CIE1000InterfaceIndex,
    cie1000IpmcSnoopingStatusMldGroupSrcListHostAddress      InetAddressIPv6,
    cie1000IpmcSnoopingStatusMldGroupSrcListGroupFilterMode  CIE1000IpmcSnoopingMldGroupSrcListGroupFilterModeEnum,
    cie1000IpmcSnoopingStatusMldGroupSrcListFilterTimer      Unsigned32,
    cie1000IpmcSnoopingStatusMldGroupSrcListSourceType       CIE1000IpmcSnoopingMldGroupSrcListSourceEnum,
    cie1000IpmcSnoopingStatusMldGroupSrcListSourceTimer      Unsigned32,
    cie1000IpmcSnoopingStatusMldGroupSrcListHardwareFilter   TruthValue
}

cie1000IpmcSnoopingStatusMldGroupSrcListIfIndex OBJECT-TYPE
    SYNTAX      CIE1000InterfaceIndex
    MAX-ACCESS  accessible-for-notify
    STATUS      current
    DESCRIPTION
        "Logical interface number of the VLAN interface."
    ::= { cie1000IpmcSnoopingStatusMldGroupSrcListEntry 1 }

cie1000IpmcSnoopingStatusMldGroupSrcListGroupAddress OBJECT-TYPE
    SYNTAX      InetAddressIPv6
    MAX-ACCESS  accessible-for-notify
    STATUS      current
    DESCRIPTION
        "Assigned IPv6 multicast address."
    ::= { cie1000IpmcSnoopingStatusMldGroupSrcListEntry 2 }

cie1000IpmcSnoopingStatusMldGroupSrcListPortIndex OBJECT-TYPE
    SYNTAX      CIE1000InterfaceIndex
    MAX-ACCESS  accessible-for-notify
    STATUS      current
    DESCRIPTION
        "Logical interface number of the physical port."
    ::= { cie1000IpmcSnoopingStatusMldGroupSrcListEntry 3 }

cie1000IpmcSnoopingStatusMldGroupSrcListHostAddress OBJECT-TYPE
    SYNTAX      InetAddressIPv6
    MAX-ACCESS  accessible-for-notify
    STATUS      current
    DESCRIPTION
        "Assigned IPv6 source address."
    ::= { cie1000IpmcSnoopingStatusMldGroupSrcListEntry 4 }

cie1000IpmcSnoopingStatusMldGroupSrcListGroupFilterMode OBJECT-TYPE
    SYNTAX      CIE1000IpmcSnoopingMldGroupSrcListGroupFilterModeEnum
    MAX-ACCESS  read-only
    STATUS      current
    DESCRIPTION
        "It is used to denote the source filtering mode of the specific
         registered multicast group address from MLD snooping."
    ::= { cie1000IpmcSnoopingStatusMldGroupSrcListEntry 5 }

cie1000IpmcSnoopingStatusMldGroupSrcListFilterTimer OBJECT-TYPE
    SYNTAX      Unsigned32
    MAX-ACCESS  read-only
    STATUS      current
    DESCRIPTION
        "It is used to count down the timer for the specific multicast group's
         filtering mode transition."
    ::= { cie1000IpmcSnoopingStatusMldGroupSrcListEntry 6 }

cie1000IpmcSnoopingStatusMldGroupSrcListSourceType OBJECT-TYPE
    SYNTAX      CIE1000IpmcSnoopingMldGroupSrcListSourceEnum
    MAX-ACCESS  read-only
    STATUS      current
    DESCRIPTION
        "It is used to denote the filtering type of the specific source address
         in multicasting to the registered group address."
    ::= { cie1000IpmcSnoopingStatusMldGroupSrcListEntry 7 }

cie1000IpmcSnoopingStatusMldGroupSrcListSourceTimer OBJECT-TYPE
    SYNTAX      Unsigned32
    MAX-ACCESS  read-only
    STATUS      current
    DESCRIPTION
        "It is used to count down the timer for purging the specific source
         address from the registered multicast group's source list."
    ::= { cie1000IpmcSnoopingStatusMldGroupSrcListEntry 8 }

cie1000IpmcSnoopingStatusMldGroupSrcListHardwareFilter OBJECT-TYPE
    SYNTAX      TruthValue
    MAX-ACCESS  read-only
    STATUS      current
    DESCRIPTION
        "It is used to denote whether the traffic destined to the multicast
         group address from the specific source address could be forwarding by
         switch hardware or not."
    ::= { cie1000IpmcSnoopingStatusMldGroupSrcListEntry 9 }

cie1000IpmcSnoopingControl OBJECT IDENTIFIER
    ::= { cie1000IpmcSnoopingMibObjects 4 }

cie1000IpmcSnoopingControlStatistics OBJECT IDENTIFIER
    ::= { cie1000IpmcSnoopingControl 1 }

cie1000IpmcSnoopingControlStatisticsIgmpClearByIfIndex OBJECT IDENTIFIER
    ::= { cie1000IpmcSnoopingControlStatistics 1 }

cie1000IpmcSnoopingControlStatisticsIgmpClearByIfIndexIfIndex OBJECT-TYPE
    SYNTAX      CIE1000InterfaceIndex
    MAX-ACCESS  read-write
    STATUS      current
    DESCRIPTION
        "Logical interface number of the VLAN interface."
    ::= { cie1000IpmcSnoopingControlStatisticsIgmpClearByIfIndex 1 }

cie1000IpmcSnoopingControlStatisticsMldClearByIfIndex OBJECT IDENTIFIER
    ::= { cie1000IpmcSnoopingControlStatistics 2 }

cie1000IpmcSnoopingControlStatisticsMldClearByIfIndexIfIndex OBJECT-TYPE
    SYNTAX      CIE1000InterfaceIndex
    MAX-ACCESS  read-write
    STATUS      current
    DESCRIPTION
        "Logical interface number of the VLAN interface."
    ::= { cie1000IpmcSnoopingControlStatisticsMldClearByIfIndex 1 }

cie1000IpmcSnoopingMibConformance OBJECT IDENTIFIER
    ::= { cie1000IpmcSnoopingMib 2 }

cie1000IpmcSnoopingMibCompliances OBJECT IDENTIFIER
    ::= { cie1000IpmcSnoopingMibConformance 1 }

cie1000IpmcSnoopingMibGroups OBJECT IDENTIFIER
    ::= { cie1000IpmcSnoopingMibConformance 2 }

cie1000IpmcSnoopingConfigIgmpGlobalsInfoGroup OBJECT-GROUP
    OBJECTS     { cie1000IpmcSnoopingConfigIgmpGlobalsAdminState,
                  cie1000IpmcSnoopingConfigIgmpGlobalsUnregisteredFlooding,
                  cie1000IpmcSnoopingConfigIgmpGlobalsSsmRangeAddress,
                  cie1000IpmcSnoopingConfigIgmpGlobalsSsmRangeMask,
                  cie1000IpmcSnoopingConfigIgmpGlobalsProxy,
                  cie1000IpmcSnoopingConfigIgmpGlobalsLeaveProxy }
    STATUS      current
    DESCRIPTION
        "A collection of objects."
    ::= { cie1000IpmcSnoopingMibGroups 1 }

cie1000IpmcSnoopingConfigIgmpPortTableInfoGroup OBJECT-GROUP
    OBJECTS     { cie1000IpmcSnoopingConfigIgmpPortPortIndex,
                  cie1000IpmcSnoopingConfigIgmpPortAsRouterPort,
                  cie1000IpmcSnoopingConfigIgmpPortDoFastLeave,
                  cie1000IpmcSnoopingConfigIgmpPortThrottlingNumber,
                  cie1000IpmcSnoopingConfigIgmpPortFilteringProfile }
    STATUS      current
    DESCRIPTION
        "A collection of objects."
    ::= { cie1000IpmcSnoopingMibGroups 2 }

cie1000IpmcSnoopingConfigIgmpIfTableInfoGroup OBJECT-GROUP
    OBJECTS     { cie1000IpmcSnoopingConfigIgmpIfIfIndex,
                  cie1000IpmcSnoopingConfigIgmpIfAdminState,
                  cie1000IpmcSnoopingConfigIgmpIfQuerierElection,
                  cie1000IpmcSnoopingConfigIgmpIfQuerierAddress,
                  cie1000IpmcSnoopingConfigIgmpIfCompatibility,
                  cie1000IpmcSnoopingConfigIgmpIfPriority,
                  cie1000IpmcSnoopingConfigIgmpIfRv,
                  cie1000IpmcSnoopingConfigIgmpIfQi,
                  cie1000IpmcSnoopingConfigIgmpIfQri,
                  cie1000IpmcSnoopingConfigIgmpIfLmqi,
                  cie1000IpmcSnoopingConfigIgmpIfUri,
                  cie1000IpmcSnoopingConfigIgmpIfAction }
    STATUS      current
    DESCRIPTION
        "A collection of objects."
    ::= { cie1000IpmcSnoopingMibGroups 3 }

cie1000IpmcSnoopingConfigIgmpIfTableRowEditorInfoGroup OBJECT-GROUP
    OBJECTS     {                   cie1000IpmcSnoopingConfigIgmpIfTableRowEditorIfIndex,
                  cie1000IpmcSnoopingConfigIgmpIfTableRowEditorAdminState,
                  cie1000IpmcSnoopingConfigIgmpIfTableRowEditorQuerierElection,
                  cie1000IpmcSnoopingConfigIgmpIfTableRowEditorQuerierAddress,
                  cie1000IpmcSnoopingConfigIgmpIfTableRowEditorCompatibility,
                  cie1000IpmcSnoopingConfigIgmpIfTableRowEditorPriority,
                  cie1000IpmcSnoopingConfigIgmpIfTableRowEditorRv,
                  cie1000IpmcSnoopingConfigIgmpIfTableRowEditorQi,
                  cie1000IpmcSnoopingConfigIgmpIfTableRowEditorQri,
                  cie1000IpmcSnoopingConfigIgmpIfTableRowEditorLmqi,
                  cie1000IpmcSnoopingConfigIgmpIfTableRowEditorUri,
                  cie1000IpmcSnoopingConfigIgmpIfTableRowEditorAction }
    STATUS      current
    DESCRIPTION
        "A collection of objects."
    ::= { cie1000IpmcSnoopingMibGroups 4 }

cie1000IpmcSnoopingConfigMldGlobalsInfoGroup OBJECT-GROUP
    OBJECTS     { cie1000IpmcSnoopingConfigMldGlobalsAdminState,
                  cie1000IpmcSnoopingConfigMldGlobalsUnregisteredFlooding,
                  cie1000IpmcSnoopingConfigMldGlobalsSsmRangeAddress,
                  cie1000IpmcSnoopingConfigMldGlobalsSsmRangeMask,
                  cie1000IpmcSnoopingConfigMldGlobalsProxy,
                  cie1000IpmcSnoopingConfigMldGlobalsLeaveProxy }
    STATUS      current
    DESCRIPTION
        "A collection of objects."
    ::= { cie1000IpmcSnoopingMibGroups 5 }

cie1000IpmcSnoopingConfigMldPortTableInfoGroup OBJECT-GROUP
    OBJECTS     { cie1000IpmcSnoopingConfigMldPortPortIndex,
                  cie1000IpmcSnoopingConfigMldPortAsRouterPort,
                  cie1000IpmcSnoopingConfigMldPortDoFastLeave,
                  cie1000IpmcSnoopingConfigMldPortThrottlingNumber,
                  cie1000IpmcSnoopingConfigMldPortFilteringProfile }
    STATUS      current
    DESCRIPTION
        "A collection of objects."
    ::= { cie1000IpmcSnoopingMibGroups 6 }

cie1000IpmcSnoopingConfigMldIfTableInfoGroup OBJECT-GROUP
    OBJECTS     { cie1000IpmcSnoopingConfigMldIfIfIndex,
                  cie1000IpmcSnoopingConfigMldIfAdminState,
                  cie1000IpmcSnoopingConfigMldIfQuerierElection,
                  cie1000IpmcSnoopingConfigMldIfCompatibility,
                  cie1000IpmcSnoopingConfigMldIfPriority,
                  cie1000IpmcSnoopingConfigMldIfRv,
                  cie1000IpmcSnoopingConfigMldIfQi,
                  cie1000IpmcSnoopingConfigMldIfQri,
                  cie1000IpmcSnoopingConfigMldIfLlqi,
                  cie1000IpmcSnoopingConfigMldIfUri,
                  cie1000IpmcSnoopingConfigMldIfAction }
    STATUS      current
    DESCRIPTION
        "A collection of objects."
    ::= { cie1000IpmcSnoopingMibGroups 7 }

cie1000IpmcSnoopingConfigMldIfTableRowEditorInfoGroup OBJECT-GROUP
    OBJECTS     {                   cie1000IpmcSnoopingConfigMldIfTableRowEditorIfIndex,
                  cie1000IpmcSnoopingConfigMldIfTableRowEditorAdminState,
                  cie1000IpmcSnoopingConfigMldIfTableRowEditorQuerierElection,
                  cie1000IpmcSnoopingConfigMldIfTableRowEditorCompatibility,
                  cie1000IpmcSnoopingConfigMldIfTableRowEditorPriority,
                  cie1000IpmcSnoopingConfigMldIfTableRowEditorRv,
                  cie1000IpmcSnoopingConfigMldIfTableRowEditorQi,
                  cie1000IpmcSnoopingConfigMldIfTableRowEditorQri,
                  cie1000IpmcSnoopingConfigMldIfTableRowEditorLlqi,
                  cie1000IpmcSnoopingConfigMldIfTableRowEditorUri,
                  cie1000IpmcSnoopingConfigMldIfTableRowEditorAction }
    STATUS      current
    DESCRIPTION
        "A collection of objects."
    ::= { cie1000IpmcSnoopingMibGroups 8 }

cie1000IpmcSnoopingStatusGroupAddressCountInfoGroup OBJECT-GROUP
    OBJECTS     {                   cie1000IpmcSnoopingStatusGroupAddressCountFromIgmp,
                  cie1000IpmcSnoopingStatusGroupAddressCountFromMld }
    STATUS      current
    DESCRIPTION
        "A collection of objects."
    ::= { cie1000IpmcSnoopingMibGroups 9 }

cie1000IpmcSnoopingStatusIgmpRouterPortTableInfoGroup OBJECT-GROUP
    OBJECTS     { cie1000IpmcSnoopingStatusIgmpRouterPortPortIndex,
                  cie1000IpmcSnoopingStatusIgmpRouterPortStatus }
    STATUS      current
    DESCRIPTION
        "A collection of objects."
    ::= { cie1000IpmcSnoopingMibGroups 10 }

cie1000IpmcSnoopingStatusIgmpVlanTableInfoGroup OBJECT-GROUP
    OBJECTS     { cie1000IpmcSnoopingStatusIgmpVlanIfIndex,
                  cie1000IpmcSnoopingStatusIgmpVlanQuerierStatus,
                  cie1000IpmcSnoopingStatusIgmpVlanActiveQuerierAddress,
                  cie1000IpmcSnoopingStatusIgmpVlanQuerierUptime,
                  cie1000IpmcSnoopingStatusIgmpVlanQueryInterval,
                  cie1000IpmcSnoopingStatusIgmpVlanStartupQueryCount,
                  cie1000IpmcSnoopingStatusIgmpVlanQuerierExpiryTime,
                  cie1000IpmcSnoopingStatusIgmpVlanQuerierVersion,
                  cie1000IpmcSnoopingStatusIgmpVlanQuerierPresentTimeout,
                  cie1000IpmcSnoopingStatusIgmpVlanHostVersion,
                  cie1000IpmcSnoopingStatusIgmpVlanHostPresentTimeout,
                  cie1000IpmcSnoopingStatusIgmpVlanCounterTxQuery,
                  cie1000IpmcSnoopingStatusIgmpVlanCounterTxSpecificQuery,
                  cie1000IpmcSnoopingStatusIgmpVlanCounterRxQuery,
                  cie1000IpmcSnoopingStatusIgmpVlanCounterRxV1Join,
                  cie1000IpmcSnoopingStatusIgmpVlanCounterRxV2Join,
                  cie1000IpmcSnoopingStatusIgmpVlanCounterRxV2Leave,
                  cie1000IpmcSnoopingStatusIgmpVlanCounterRxV3Join,
                  cie1000IpmcSnoopingStatusIgmpVlanCounterRxErrors }
    STATUS      current
    DESCRIPTION
        "A collection of objects."
    ::= { cie1000IpmcSnoopingMibGroups 11 }

cie1000IpmcSnoopingStatusIgmpGroupAddressTableInfoGroup OBJECT-GROUP
    OBJECTS     { cie1000IpmcSnoopingStatusIgmpGroupAddressIfIndex,
                  cie1000IpmcSnoopingStatusIgmpGroupAddressGroupAddress,
                  cie1000IpmcSnoopingStatusIgmpGroupAddressMemberPorts,
                  cie1000IpmcSnoopingStatusIgmpGroupAddressHardwareSwitch }
    STATUS      current
    DESCRIPTION
        "A collection of objects."
    ::= { cie1000IpmcSnoopingMibGroups 12 }

cie1000IpmcSnoopingStatusIgmpGroupSrcListTableInfoGroup OBJECT-GROUP
    OBJECTS     { cie1000IpmcSnoopingStatusIgmpGroupSrcListIfIndex,
                  cie1000IpmcSnoopingStatusIgmpGroupSrcListGroupAddress,
                  cie1000IpmcSnoopingStatusIgmpGroupSrcListPortIndex,
                  cie1000IpmcSnoopingStatusIgmpGroupSrcListHostAddress,
                  cie1000IpmcSnoopingStatusIgmpGroupSrcListGroupFilterMode,
                  cie1000IpmcSnoopingStatusIgmpGroupSrcListFilterTimer,
                  cie1000IpmcSnoopingStatusIgmpGroupSrcListSourceType,
                  cie1000IpmcSnoopingStatusIgmpGroupSrcListSourceTimer,
                  cie1000IpmcSnoopingStatusIgmpGroupSrcListHardwareFilter }
    STATUS      current
    DESCRIPTION
        "A collection of objects."
    ::= { cie1000IpmcSnoopingMibGroups 13 }

cie1000IpmcSnoopingStatusMldRouterPortTableInfoGroup OBJECT-GROUP
    OBJECTS     { cie1000IpmcSnoopingStatusMldRouterPortPortIndex,
                  cie1000IpmcSnoopingStatusMldRouterPortStatus }
    STATUS      current
    DESCRIPTION
        "A collection of objects."
    ::= { cie1000IpmcSnoopingMibGroups 14 }

cie1000IpmcSnoopingStatusMldVlanTableInfoGroup OBJECT-GROUP
    OBJECTS     { cie1000IpmcSnoopingStatusMldVlanIfIndex,
                  cie1000IpmcSnoopingStatusMldVlanQuerierStatus,
                  cie1000IpmcSnoopingStatusMldVlanActiveQuerierAddress,
                  cie1000IpmcSnoopingStatusMldVlanQuerierUptime,
                  cie1000IpmcSnoopingStatusMldVlanQueryInterval,
                  cie1000IpmcSnoopingStatusMldVlanStartupQueryCount,
                  cie1000IpmcSnoopingStatusMldVlanQuerierExpiryTime,
                  cie1000IpmcSnoopingStatusMldVlanQuerierVersion,
                  cie1000IpmcSnoopingStatusMldVlanQuerierPresentTimeout,
                  cie1000IpmcSnoopingStatusMldVlanHostVersion,
                  cie1000IpmcSnoopingStatusMldVlanHostPresentTimeout,
                  cie1000IpmcSnoopingStatusMldVlanCounterTxQuery,
                  cie1000IpmcSnoopingStatusMldVlanCounterTxSpecificQuery,
                  cie1000IpmcSnoopingStatusMldVlanCounterRxQuery,
                  cie1000IpmcSnoopingStatusMldVlanCounterRxV1Report,
                  cie1000IpmcSnoopingStatusMldVlanCounterRxV1Done,
                  cie1000IpmcSnoopingStatusMldVlanCounterRxV2Report,
                  cie1000IpmcSnoopingStatusMldVlanCounterRxErrors }
    STATUS      current
    DESCRIPTION
        "A collection of objects."
    ::= { cie1000IpmcSnoopingMibGroups 15 }

cie1000IpmcSnoopingStatusMldGroupAddressTableInfoGroup OBJECT-GROUP
    OBJECTS     { cie1000IpmcSnoopingStatusMldGroupAddressIfIndex,
                  cie1000IpmcSnoopingStatusMldGroupAddressGroupAddress,
                  cie1000IpmcSnoopingStatusMldGroupAddressMemberPorts,
                  cie1000IpmcSnoopingStatusMldGroupAddressHardwareSwitch }
    STATUS      current
    DESCRIPTION
        "A collection of objects."
    ::= { cie1000IpmcSnoopingMibGroups 16 }

cie1000IpmcSnoopingStatusMldGroupSrcListTableInfoGroup OBJECT-GROUP
    OBJECTS     { cie1000IpmcSnoopingStatusMldGroupSrcListIfIndex,
                  cie1000IpmcSnoopingStatusMldGroupSrcListGroupAddress,
                  cie1000IpmcSnoopingStatusMldGroupSrcListPortIndex,
                  cie1000IpmcSnoopingStatusMldGroupSrcListHostAddress,
                  cie1000IpmcSnoopingStatusMldGroupSrcListGroupFilterMode,
                  cie1000IpmcSnoopingStatusMldGroupSrcListFilterTimer,
                  cie1000IpmcSnoopingStatusMldGroupSrcListSourceType,
                  cie1000IpmcSnoopingStatusMldGroupSrcListSourceTimer,
                  cie1000IpmcSnoopingStatusMldGroupSrcListHardwareFilter }
    STATUS      current
    DESCRIPTION
        "A collection of objects."
    ::= { cie1000IpmcSnoopingMibGroups 17 }

cie1000IpmcSnoopingControlStatisticsIgmpClearByIfIndexInfoGroup OBJECT-GROUP
    OBJECTS     {                   cie1000IpmcSnoopingControlStatisticsIgmpClearByIfIndexIfIndex }
    STATUS      current
    DESCRIPTION
        "A collection of objects."
    ::= { cie1000IpmcSnoopingMibGroups 18 }

cie1000IpmcSnoopingControlStatisticsMldClearByIfIndexInfoGroup OBJECT-GROUP
    OBJECTS     {                   cie1000IpmcSnoopingControlStatisticsMldClearByIfIndexIfIndex }
    STATUS      current
    DESCRIPTION
        "A collection of objects."
    ::= { cie1000IpmcSnoopingMibGroups 19 }

cie1000IpmcSnoopingMibCompliance MODULE-COMPLIANCE
    STATUS      current
    DESCRIPTION
        "The compliance statement for the implementation."

    MODULE      -- this module

    MANDATORY-GROUPS {                        cie1000IpmcSnoopingConfigIgmpGlobalsInfoGroup,
                       cie1000IpmcSnoopingConfigIgmpPortTableInfoGroup,
                       cie1000IpmcSnoopingConfigIgmpIfTableInfoGroup,
                       cie1000IpmcSnoopingConfigIgmpIfTableRowEditorInfoGroup,
                       cie1000IpmcSnoopingConfigMldGlobalsInfoGroup,
                       cie1000IpmcSnoopingConfigMldPortTableInfoGroup,
                       cie1000IpmcSnoopingConfigMldIfTableInfoGroup,
                       cie1000IpmcSnoopingConfigMldIfTableRowEditorInfoGroup,
                       cie1000IpmcSnoopingStatusGroupAddressCountInfoGroup,
                       cie1000IpmcSnoopingStatusIgmpRouterPortTableInfoGroup,
                       cie1000IpmcSnoopingStatusIgmpVlanTableInfoGroup,
                       cie1000IpmcSnoopingStatusIgmpGroupAddressTableInfoGroup,
                       cie1000IpmcSnoopingStatusIgmpGroupSrcListTableInfoGroup,
                       cie1000IpmcSnoopingStatusMldRouterPortTableInfoGroup,
                       cie1000IpmcSnoopingStatusMldVlanTableInfoGroup,
                       cie1000IpmcSnoopingStatusMldGroupAddressTableInfoGroup,
                       cie1000IpmcSnoopingStatusMldGroupSrcListTableInfoGroup,
                       cie1000IpmcSnoopingControlStatisticsIgmpClearByIfIndexInfoGroup,
                       cie1000IpmcSnoopingControlStatisticsMldClearByIfIndexInfoGroup }

    ::= { cie1000IpmcSnoopingMibCompliances 1 }

END
