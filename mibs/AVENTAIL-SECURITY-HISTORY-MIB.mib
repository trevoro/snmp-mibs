-- File Name : AVENTAIL-SECURITY-HISTORY


AVENTAIL-SECURITY-HISTORY-MIB	DEFINITIONS ::= BEGIN
	IMPORTS
		aventail
			FROM AVENTAIL-MIB
		InternationalDisplayString 
			FROM HOST-RESOURCES-MIB
		OBJECT-TYPE, Integer32,MODULE-IDENTITY
			FROM SNMPv2-SMI;


	aventailSecurityHistory MODULE-IDENTITY
             LAST-UPDATED       "200409071432Z" 
             ORGANIZATION      "Aventail"
             CONTACT-INFO "email:   support@aventail.com"
             DESCRIPTION    "This Aventail MIB provides Security History Info"
        	::= {aventail 4}

	numOfLoginDenials	OBJECT-TYPE	
		SYNTAX			Integer32
		MAX-ACCESS	read-only
		STATUS			current
		DESCRIPTION	"The number of login denials since the last reset \
		                            interval; where reset interval is 24 hours"
		::=  {  aventailSecurityHistory  1  }

	lastLoginDenial	OBJECT IDENTIFIER
		::=  {  aventailSecurityHistory  2  }

	numOfAccessDenials	OBJECT-TYPE	
		SYNTAX			Integer32
		MAX-ACCESS	read-only
		STATUS			current
		DESCRIPTION	"The number of access denials since the last reset \
		                             interval; where reset interval is 24 hours."
		::=  {  aventailSecurityHistory  3  }

	lastAccessDenial	OBJECT IDENTIFIER
		::=  {  aventailSecurityHistory  4  }

	lastLoginDeniedUser	OBJECT-TYPE	
		SYNTAX			InternationalDisplayString
		MAX-ACCESS	read-only
		STATUS			current
		DESCRIPTION	"The user@realm who last was denied authentication"
		::=  {  lastLoginDenial  1  }

	lastLoginDeniedTime	OBJECT-TYPE	
		SYNTAX			InternationalDisplayString
		MAX-ACCESS	read-only
		STATUS			current
		DESCRIPTION	"The time the last user was denied authentication in a \
		                            string of the form Wed Jun 30 21:49:08 1993."
		::=  {  lastLoginDenial  2  }

	lastAccessDeniedUser	OBJECT-TYPE	
		SYNTAX			InternationalDisplayString
		MAX-ACCESS	read-only
		STATUS			current
		DESCRIPTION		"The last user who was denied access in the form \
		                             user@realm."
		::=  {  lastAccessDenial  1  }

	lastAccessDeniedResource	OBJECT-TYPE	
		SYNTAX			InternationalDisplayString
		MAX-ACCESS	read-only
		STATUS			current
		DESCRIPTION	"The URI resource that was denied access to"
		::=  {  lastAccessDenial  2  }

	lastAccessDeniedTime	OBJECT-TYPE	
		SYNTAX			InternationalDisplayString
		MAX-ACCESS	read-only
		STATUS			current
		DESCRIPTION	"The time the last user was denied access in a string \
		                             of the form Wed Jun 30 21:49:08 1993"
		::=  {  lastAccessDenial  3  }

END
