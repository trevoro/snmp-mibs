-- Avaya Aura Serviceability Agent MIB
-- Copyright (c) 2010-2011 by Avaya Inc. All rights reserved. 
-- MIB version 1.0.2  
-- Avaya Compas ID: 152291

AV-AURA-SERVICEABILITY-AGENT-MIB DEFINITIONS ::= BEGIN

IMPORTS

    MODULE-IDENTITY, OBJECT-TYPE, enterprises
        FROM SNMPv2-SMI    
    MODULE-COMPLIANCE, OBJECT-GROUP
        FROM SNMPv2-CONF;
      

avAuraServAgentMibs MODULE-IDENTITY
       LAST-UPDATED "201207171758Z" -- YYYYMMDDHHMMSS (17 July 2012)
       
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"

       DESCRIPTION "This MIB module is used by Serviceability Agent for sending optional varbinds for
                    the completeness of trap message."
       
       REVISION 	"201207171758Z" -- 17 July 2012
       DESCRIPTION "MIB Version 1.0.2 - AVAYA. Generated via the MIBTOOL. Updated to comply with validate tool."
       
       
       REVISION 	"201105300000Z" -- YYYYMMDDHHMMSS (30th May 2011)
       DESCRIPTION "MIB Version 1.0.1 - Birendra Sinha. OID suffix for avAuraServAgentMibNotifications MIB item is changed to zero. 
       				Updated description of avAuraServAgentNotificationMsg MIB item."
       
       REVISION     "201105260000Z" -- YYYYMMDDHHMMSS (26th May 2011)
       DESCRIPTION  "Revision 1.0.0 - Birendra Sinha. Initial version of the Avaya Serviceability Agent MIB."
       				
       
       
       ::= { mibs 53 }
       
       
--
-- The following are defined in AV-AURA-SERVICEABILITY-AGENT-MIB
--
avaya              OBJECT IDENTIFIER ::= { enterprises 6889 }
products           OBJECT IDENTIFIER ::= { avaya 1 }
mibs               OBJECT IDENTIFIER ::= { avaya 2 }
       
avAuraServAgentProd OBJECT IDENTIFIER ::= { products 53 }
       
       
--
-- Top level components of AV-AURA-SERVICEABILITY-AGENT-MIB
--
avAuraServAgentMibNotifications       OBJECT IDENTIFIER ::= { avAuraServAgentMibs 0 } -- Notification group
avAuraServAgentMibObjects OBJECT IDENTIFIER ::= { avAuraServAgentMibs 1 } -- Objects
avAuraServAgentMibConformance   OBJECT IDENTIFIER ::= { avAuraServAgentMibs 2 } -- Conformance

--
-- Common Object groups for  MIB
-------------------------------------------------------------------------------------------
-- Leaving 1 to 8 as buffer for defining other MIB objects in future.
-- avAuraServAgentNotificationVBsObj will carry informations about notification varbinds
-- populated by the serviceability agent
------------------------------------------------------------------------------------------- 
avAuraServAgentNotificationVBsObj OBJECT IDENTIFIER ::= { avAuraServAgentMibObjects 9 }


--
-- List of Varbinds (avAuraServAgentNotificationVBsObj)used to send extra information as part of 
-- notifications by System Manager Serviceability agent.
--
    
avAuraServAgentNotificationLogEventId OBJECT-TYPE
    SYNTAX     OCTET STRING (SIZE(1..100))
    MAX-ACCESS accessible-for-notify
    STATUS     current
    DESCRIPTION "Log event ID used by the application for log messages. This information can be 
    			used as an index to the log file harvested using System manager log harvester for anlysing faults. 
    			This information is populated by the serviceability agent via tailing the application log file."
    ::= { avAuraServAgentNotificationVBsObj 1 }

avAuraServAgentNotificationLogEventTime OBJECT-TYPE
    SYNTAX     OCTET STRING (SIZE(1..50))
    MAX-ACCESS accessible-for-notify
    STATUS     current
    DESCRIPTION "Log event time is the time when a log message is persisted in the log file which is tailed by 
    the serviceability agent. This information can also be used as an index to the log file harvested using 
    System manager log harvester for anlysing faults. 
    This information is populated by the serviceability agent via tailing the application log file."
    ::= { avAuraServAgentNotificationVBsObj 2 }

--    
-- Conformance information
-------------------------------------------------------------------------------------------
avAuraServAgentMibCompliances    OBJECT IDENTIFIER ::= { avAuraServAgentMibConformance 1 }
avAuraServAgentMibGroups         OBJECT IDENTIFIER ::= { avAuraServAgentMibConformance 2 }

avAuraServAgentMibCompliance   MODULE-COMPLIANCE
    STATUS       current
    DESCRIPTION
    "The compliance statement for Avaya Aura Serviceability Agent MIB entities"
    MODULE	
    MANDATORY-GROUPS { avAuraServAgentObjGroup }
    ::= { avAuraServAgentMibCompliances 1 }

avAuraServAgentObjGroup    OBJECT-GROUP
    OBJECTS     { avAuraServAgentNotificationLogEventId, avAuraServAgentNotificationLogEventTime }
    STATUS      current
    DESCRIPTION
      "Avaya Aura Serviceability Agent MIB objects"
    ::= { avAuraServAgentMibGroups 1 }
                                                                                         
END
