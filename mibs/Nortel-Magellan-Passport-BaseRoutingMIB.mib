Nortel-Magellan-Passport-BaseRoutingMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      Gauge32,
      Integer32,
      Unsigned32
   FROM Nortel-Magellan-Passport-StandardTextualConventionsMIB

      NonReplicated,
      FixedPoint1,
      AsciiStringIndex,
      DigitString
   FROM Nortel-Magellan-Passport-TextualConventionsMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     BaseRouting Enterprise MIB."

baseRoutingMIB OBJECT IDENTIFIER ::= { passportMIBs 18 }










-- Routing
-- This is the description for the Routing system component. This is 
-- the top level component of the routing hierarchy.

rtg OBJECT IDENTIFIER ::= { components 40 }



rtgRowStatusTable OBJECT-TYPE
   SYNTAX     SEQUENCE OF RtgRowStatusEntry
   ACCESS     not-accessible
   STATUS     mandatory
   DESCRIPTION
     "This entry controls the addition and deletion of 
      rtg components."
::= { rtg 1 }

rtgRowStatusEntry OBJECT-TYPE
   SYNTAX     RtgRowStatusEntry
   ACCESS     not-accessible
   STATUS     mandatory
   DESCRIPTION
     "A single entry in the table represents a single 
      rtg component."
   INDEX {
      rtgIndex }
::= { rtgRowStatusTable 1 }

RtgRowStatusEntry ::= SEQUENCE {
   rtgRowStatus
      RowStatus,
   rtgComponentName
      DisplayString,
   rtgStorageType
      StorageType,
   rtgIndex
      NonReplicated }

rtgRowStatus OBJECT-TYPE
   SYNTAX     RowStatus 
   ACCESS     read-write
   STATUS     mandatory
   DESCRIPTION
     "This variable is used as the basis for SNMP naming of
      rtg components.
      These components can be added."
::= { rtgRowStatusEntry 1 }

rtgComponentName OBJECT-TYPE
   SYNTAX     DisplayString 
   ACCESS     read-only
   STATUS     mandatory
   DESCRIPTION
     "This variable provides the component's string name for
      use with the ASCII Console Interface"
::= { rtgRowStatusEntry 2 }

rtgStorageType OBJECT-TYPE
   SYNTAX     StorageType 
   ACCESS     read-only
   STATUS     mandatory
   DESCRIPTION
     "This variable represents the storage type value for the
      rtg tables."
::= { rtgRowStatusEntry 4 }

rtgIndex OBJECT-TYPE
   SYNTAX     NonReplicated 
   ACCESS     not-accessible
   STATUS     mandatory
   DESCRIPTION
     "This variable represents the index for the rtg tables."
::= { rtgRowStatusEntry 10 }

rtgProvTable OBJECT-TYPE
   SYNTAX     SEQUENCE OF RtgProvEntry
   ACCESS     not-accessible
   STATUS     mandatory
   DESCRIPTION
     "This group contains the provisioning data for the routing system."
::= { rtg 12 }

rtgProvEntry OBJECT-TYPE
   SYNTAX     RtgProvEntry
   ACCESS     not-accessible
   STATUS     mandatory
   DESCRIPTION
     "An entry in the rtgProvTable."
   INDEX {
      rtgIndex }
::= { rtgProvTable 1 }

RtgProvEntry ::= SEQUENCE {
   rtgTandemTraffic
      INTEGER }

rtgTandemTraffic OBJECT-TYPE
   SYNTAX     INTEGER  {
                 allowed(0),
                 denied(1) }
   ACCESS     read-write
   STATUS     mandatory
   DESCRIPTION
     "This attribute specifies whether tandem traffic is permitted through 
      the node. 
      
      Tandem traffic is traffic which arrives at the node on a trunk and 
      leaves the node on a trunk. Traffic to or from a gateway (internal or 
      external) is not affected by the setting of this attribute.
      
      The default value of this attribute is allowed, which permits tandem 
      traffic to be routed through the node. When this attribute is set to 
      denied, DPN, VNS, and PORS traffic are not permitted to tandem 
      through the node. 
      
      Changing this attribute has no effect on PORS calls which were set 
      up before the change. These calls can be manually forced to reroute 
      using the new setting by clearing the calls or locking the trunks on 
      which they are routed."
   DEFVAL     { allowed }
::= { rtgProvEntry 1 }

rtgSplittingRegionIdsTable OBJECT-TYPE
   SYNTAX     SEQUENCE OF RtgSplittingRegionIdsEntry
   ACCESS     not-accessible
   STATUS     mandatory
   DESCRIPTION
     "This attribute is used only when splitting or merging existing 
      topology regions. It specifies which topology regions are in a 
      migration status. A node will only exchange topological 
      information with a connected node under the following conditions: 
      (i) the nodes belong to the same topology region, (ii) one of the 
      nodes is provisioned with the default regionId of 0, (iii) the 
      connected node's splittingRegionIds attribute is provisioned to 
      contain the local node's regionId value and the local node's 
      splittingRegionIds is also provisioned to contain the connected 
      node's regionId value when both two nodes' regionIds are different 
      and non-zero. 
      
      When this attribute is used during migration of regions, values for 
      the attribute are normally the old and new regionIds for the node. 
      Use of this attribute makes it possible to migrate existing topology 
      regions in the following cases: (i) splitting a topology region into 
      two without isolating a node, (ii) merging two different topology 
      regions into one without introducing an extra topological barrier.
      
      The attribute should be cleaned when all migration activities are 
      complete. At this point, the region boundary will take effect."
::= { rtg 407 }

rtgSplittingRegionIdsEntry OBJECT-TYPE
   SYNTAX     RtgSplittingRegionIdsEntry
   ACCESS     not-accessible
   STATUS     mandatory
   DESCRIPTION
     "An entry in the rtgSplittingRegionIdsTable."
   INDEX {
      rtgIndex,
      rtgSplittingRegionIdsValue }
::= { rtgSplittingRegionIdsTable 1 }

RtgSplittingRegionIdsEntry ::= SEQUENCE {
   rtgSplittingRegionIdsValue
      Integer32,
   rtgSplittingRegionIdsRowStatus
      RowStatus }

rtgSplittingRegionIdsValue OBJECT-TYPE
   SYNTAX     Integer32 (1..126)
   ACCESS     read-write
   STATUS     mandatory
   DESCRIPTION
     "This variable represents both the value and the index for the
      rtgSplittingRegionIdsTable."
::= { rtgSplittingRegionIdsEntry 1 }

rtgSplittingRegionIdsRowStatus OBJECT-TYPE
   SYNTAX     RowStatus 
   ACCESS     write-only
   STATUS     mandatory
   DESCRIPTION
     "This variable is used to control the addition and deletion 
      of individual values of the rtgSplittingRegionIdsTable."
::= { rtgSplittingRegionIdsEntry 2 }


-- Rtg Topology 
-- This component is a subcomponent of Routing. It resides on all 
-- Passport modules and is responsible for maintaining a topological 
-- database describing the Passport network topology in terms of 
-- nodes and connectivity between them. It computes the reachability 
-- costs to each Passport node for multiple address plans taking into 
-- account the underlying transport attributes of interest to them.

rtgTop OBJECT IDENTIFIER ::= { rtg 5 }



rtgTopRowStatusTable OBJECT-TYPE
   SYNTAX     SEQUENCE OF RtgTopRowStatusEntry
   ACCESS     not-accessible
   STATUS     mandatory
   DESCRIPTION
     "This entry controls the addition and deletion of 
      rtgTop components."
::= { rtgTop 1 }

rtgTopRowStatusEntry OBJECT-TYPE
   SYNTAX     RtgTopRowStatusEntry
   ACCESS     not-accessible
   STATUS     mandatory
   DESCRIPTION
     "A single entry in the table represents a single 
      rtgTop component."
   INDEX {
      rtgIndex,
      rtgTopIndex }
::= { rtgTopRowStatusTable 1 }

RtgTopRowStatusEntry ::= SEQUENCE {
   rtgTopRowStatus
      RowStatus,
   rtgTopComponentName
      DisplayString,
   rtgTopStorageType
      StorageType,
   rtgTopIndex
      NonReplicated }

rtgTopRowStatus OBJECT-TYPE
   SYNTAX     RowStatus 
   ACCESS     read-only
   STATUS     mandatory
   DESCRIPTION
     "This variable is used as the basis for SNMP naming of
      rtgTop components.
      These components cannot be added nor deleted."
::= { rtgTopRowStatusEntry 1 }

rtgTopComponentName OBJECT-TYPE
   SYNTAX     DisplayString 
   ACCESS     read-only
   STATUS     mandatory
   DESCRIPTION
     "This variable provides the component's string name for
      use with the ASCII Console Interface"
::= { rtgTopRowStatusEntry 2 }

rtgTopStorageType OBJECT-TYPE
   SYNTAX     StorageType 
   ACCESS     read-only
   STATUS     mandatory
   DESCRIPTION
     "This variable represents the storage type value for the
      rtgTop tables."
::= { rtgTopRowStatusEntry 4 }

rtgTopIndex OBJECT-TYPE
   SYNTAX     NonReplicated 
   ACCESS     not-accessible
   STATUS     mandatory
   DESCRIPTION
     "This variable represents the index for the rtgTop tables."
::= { rtgTopRowStatusEntry 10 }

rtgTopStatsTable OBJECT-TYPE
   SYNTAX     SEQUENCE OF RtgTopStatsEntry
   ACCESS     not-accessible
   STATUS     mandatory
   DESCRIPTION
     "Rtg Top Statistics
      This group contains operational data stored and maintained by this 
      component for recording statistics of Passport routing control 
      packets which have been sent or received by Topology."
::= { rtgTop 11 }

rtgTopStatsEntry OBJECT-TYPE
   SYNTAX     RtgTopStatsEntry
   ACCESS     not-accessible
   STATUS     mandatory
   DESCRIPTION
     "An entry in the rtgTopStatsTable."
   INDEX {
      rtgIndex,
      rtgTopIndex }
::= { rtgTopStatsTable 1 }

RtgTopStatsEntry ::= SEQUENCE {
   rtgTopControlPktRx
      Counter32,
   rtgTopControlBytesRx
      Counter32,
   rtgTopControlPktTx
      Counter32,
   rtgTopControlBytesTx
      Counter32 }

rtgTopControlPktRx OBJECT-TYPE
   SYNTAX     Counter32 
   ACCESS     read-only
   STATUS     mandatory
   DESCRIPTION
     "This attribute shows the total number of topology routing control 
      packets which have been received by this node from other Passport 
      nodes in the network."
::= { rtgTopStatsEntry 1 }

rtgTopControlBytesRx OBJECT-TYPE
   SYNTAX     Counter32 
   ACCESS     read-only
   STATUS     mandatory
   DESCRIPTION
     "This attribute shows the total number of topology routing control 
      packet bytes received by this node from other Passport nodes in the 
      network."
::= { rtgTopStatsEntry 2 }

rtgTopControlPktTx OBJECT-TYPE
   SYNTAX     Counter32 
   ACCESS     read-only
   STATUS     mandatory
   DESCRIPTION
     "This attribute shows the total number of topology routing control 
      packets which have been sent by this node to other Passport nodes 
      in the network."
::= { rtgTopStatsEntry 3 }

rtgTopControlBytesTx OBJECT-TYPE
   SYNTAX     Counter32 
   ACCESS     read-only
   STATUS     mandatory
   DESCRIPTION
     "This attribute shows the total number of topology routing control 
      packet bytes sent by this node to other Passport nodes in the 
      network."
::= { rtgTopStatsEntry 4 }

-- 
-- *** THIS SUBTREE CURRENTLY NOT IMPLEMENTED ***
-- 

-- Rtg Top Node/<neighborNodeName>
-- This component is a dynamic subcomponent of Topology. There is 
-- one instance of this component for each reachable node in the 
-- topological database. It describes this node's view of 
-- interconnections to its neighbour Passport modules.

rtgTopNode OBJECT IDENTIFIER ::= { rtgTop 2 }



rtgTopNodeRowStatusTable OBJECT-TYPE
   SYNTAX     SEQUENCE OF RtgTopNodeRowStatusEntry
   ACCESS     not-accessible
   STATUS     mandatory
   DESCRIPTION
     "*** THIS TABLE CURRENTLY NOT IMPLEMENTED ***

      This entry controls the addition and deletion of 
      rtgTopNode components."
::= { rtgTopNode 1 }

rtgTopNodeRowStatusEntry OBJECT-TYPE
   SYNTAX     RtgTopNodeRowStatusEntry
   ACCESS     not-accessible
   STATUS     mandatory
   DESCRIPTION
     "A single entry in the table represents a single 
      rtgTopNode component."
   INDEX {
      rtgIndex,
      rtgTopIndex,
      rtgTopNodeIndex }
::= { rtgTopNodeRowStatusTable 1 }

RtgTopNodeRowStatusEntry ::= SEQUENCE {
   rtgTopNodeRowStatus
      RowStatus,
   rtgTopNodeComponentName
      DisplayString,
   rtgTopNodeStorageType
      StorageType,
   rtgTopNodeIndex
      AsciiStringIndex }

rtgTopNodeRowStatus OBJECT-TYPE
   SYNTAX     RowStatus 
   ACCESS     read-only
   STATUS     mandatory
   DESCRIPTION
     "This variable is used as the basis for SNMP naming of
      rtgTopNode components.
      These components cannot be added nor deleted."
::= { rtgTopNodeRowStatusEntry 1 }

rtgTopNodeComponentName OBJECT-TYPE
   SYNTAX     DisplayString 
   ACCESS     read-only
   STATUS     mandatory
   DESCRIPTION
     "This variable provides the component's string name for
      use with the ASCII Console Interface"
::= { rtgTopNodeRowStatusEntry 2 }

rtgTopNodeStorageType OBJECT-TYPE
   SYNTAX     StorageType 
   ACCESS     read-only
   STATUS     mandatory
   DESCRIPTION
     "This variable represents the storage type value for the
      rtgTopNode tables."
::= { rtgTopNodeRowStatusEntry 4 }

rtgTopNodeIndex OBJECT-TYPE
   SYNTAX     AsciiStringIndex (SIZE (1..12))
   ACCESS     not-accessible
   STATUS     mandatory
   DESCRIPTION
     "This variable represents the index for the rtgTopNode tables."
::= { rtgTopNodeRowStatusEntry 10 }

rtgTopNodeOperTable OBJECT-TYPE
   SYNTAX     SEQUENCE OF RtgTopNodeOperEntry
   ACCESS     not-accessible
   STATUS     mandatory
   DESCRIPTION
     "*** THIS TABLE CURRENTLY NOT IMPLEMENTED ***

      Rtg Top Node/<neighborNodeName> Operational
      This group contains operational data about each node in the 
      Passport network and its connectivity to its neighbours."
::= { rtgTopNode 10 }

rtgTopNodeOperEntry OBJECT-TYPE
   SYNTAX     RtgTopNodeOperEntry
   ACCESS     not-accessible
   STATUS     mandatory
   DESCRIPTION
     "An entry in the rtgTopNodeOperTable."
   INDEX {
      rtgIndex,
      rtgTopIndex,
      rtgTopNodeIndex }
::= { rtgTopNodeOperTable 1 }

RtgTopNodeOperEntry ::= SEQUENCE {
   rtgTopNodeNodeId
      Unsigned32 }

rtgTopNodeNodeId OBJECT-TYPE
   SYNTAX     Unsigned32 (1..4095)
   ACCESS     read-only
   STATUS     mandatory
   DESCRIPTION
     "The nodeId is a number that uniquely identifies the Node 
      component instance in the Passport network. It is the identifier used 
      in the routing control packets sent by this node to other Passport 
      nodes in the network.
      
      The nodeId, for each node in the network, is learned from the 
      Passport routing protocol packets."
::= { rtgTopNodeOperEntry 1 }

-- 
-- *** THIS SUBTREE CURRENTLY NOT IMPLEMENTED ***
-- 

-- Rtg Top Node/<neighborNodeName> LinkGroup/ 
-- <neighborNodeName>
-- This component is a dynamic subcomponent of the Node 
-- component. For each node, there is one instance of this component 
-- for each trunk group that this node has (i.e. the number of active 
-- neighbours the node has). It shows the operational attributes of the 
-- trunk group.

rtgTopNodeLg OBJECT IDENTIFIER ::= { rtgTopNode 2 }



rtgTopNodeLgRowStatusTable OBJECT-TYPE
   SYNTAX     SEQUENCE OF RtgTopNodeLgRowStatusEntry
   ACCESS     not-accessible
   STATUS     mandatory
   DESCRIPTION
     "*** THIS TABLE CURRENTLY NOT IMPLEMENTED ***

      This entry controls the addition and deletion of 
      rtgTopNodeLg components."
::= { rtgTopNodeLg 1 }

rtgTopNodeLgRowStatusEntry OBJECT-TYPE
   SYNTAX     RtgTopNodeLgRowStatusEntry
   ACCESS     not-accessible
   STATUS     mandatory
   DESCRIPTION
     "A single entry in the table represents a single 
      rtgTopNodeLg component."
   INDEX {
      rtgIndex,
      rtgTopIndex,
      rtgTopNodeIndex,
      rtgTopNodeLgIndex }
::= { rtgTopNodeLgRowStatusTable 1 }

RtgTopNodeLgRowStatusEntry ::= SEQUENCE {
   rtgTopNodeLgRowStatus
      RowStatus,
   rtgTopNodeLgComponentName
      DisplayString,
   rtgTopNodeLgStorageType
      StorageType,
   rtgTopNodeLgIndex
      AsciiStringIndex }

rtgTopNodeLgRowStatus OBJECT-TYPE
   SYNTAX     RowStatus 
   ACCESS     read-only
   STATUS     mandatory
   DESCRIPTION
     "This variable is used as the basis for SNMP naming of
      rtgTopNodeLg components.
      These components cannot be added nor deleted."
::= { rtgTopNodeLgRowStatusEntry 1 }

rtgTopNodeLgComponentName OBJECT-TYPE
   SYNTAX     DisplayString 
   ACCESS     read-only
   STATUS     mandatory
   DESCRIPTION
     "This variable provides the component's string name for
      use with the ASCII Console Interface"
::= { rtgTopNodeLgRowStatusEntry 2 }

rtgTopNodeLgStorageType OBJECT-TYPE
   SYNTAX     StorageType 
   ACCESS     read-only
   STATUS     mandatory
   DESCRIPTION
     "This variable represents the storage type value for the
      rtgTopNodeLg tables."
::= { rtgTopNodeLgRowStatusEntry 4 }

rtgTopNodeLgIndex OBJECT-TYPE
   SYNTAX     AsciiStringIndex (SIZE (1..12))
   ACCESS     not-accessible
   STATUS     mandatory
   DESCRIPTION
     "This variable represents the index for the rtgTopNodeLg tables."
::= { rtgTopNodeLgRowStatusEntry 10 }

rtgTopNodeLgOperTable OBJECT-TYPE
   SYNTAX     SEQUENCE OF RtgTopNodeLgOperEntry
   ACCESS     not-accessible
   STATUS     mandatory
   DESCRIPTION
     "*** THIS TABLE CURRENTLY NOT IMPLEMENTED ***

      Rtg Top Node/<neighborNodeName> LinkGroup/
      <neighborNodeName> Operational
      This group contains the operational data stored and maintained by 
      TrunkGroup component for each trunk group attached to a node in 
      the Passport network."
::= { rtgTopNodeLg 10 }

rtgTopNodeLgOperEntry OBJECT-TYPE
   SYNTAX     RtgTopNodeLgOperEntry
   ACCESS     not-accessible
   STATUS     mandatory
   DESCRIPTION
     "An entry in the rtgTopNodeLgOperTable."
   INDEX {
      rtgIndex,
      rtgTopIndex,
      rtgTopNodeIndex,
      rtgTopNodeLgIndex }
::= { rtgTopNodeLgOperTable 1 }

RtgTopNodeLgOperEntry ::= SEQUENCE {
   rtgTopNodeLgDelayMetric
      Unsigned32,
   rtgTopNodeLgTputMetric
      Unsigned32 }

rtgTopNodeLgDelayMetric OBJECT-TYPE
   SYNTAX     Unsigned32 (1..2147483647)
   ACCESS     read-only
   STATUS     mandatory
   DESCRIPTION
     "This attribute specifies the outbound cost to forward packets across 
      the trunk group for a delay class of service. It represents the trunk in 
      the trunk group with the lowest round trip delay. A low outbound 
      cost is preferable to a higher value as it is associated with higher 
      speed facilities.
      
      A metric value of 2147483647 means that the trunk group is 
      unusable for the delay class of service."
::= { rtgTopNodeLgOperEntry 1 }

rtgTopNodeLgTputMetric OBJECT-TYPE
   SYNTAX     Unsigned32 (1..2147483647)
   ACCESS     read-only
   STATUS     mandatory
   DESCRIPTION
     "This attribute specifies the outbound cost to forward packets across 
      the trunk group for a throughput class of service. It is computed 
      from the combined speed of each link in the trunk group. A low 
      outbound cost is preferable to a higher value as it is associated with 
      higher speed facilities.
      
      A metric value of 2147483647 means that the trunk group is 
      unusable for the throughput class of service."
::= { rtgTopNodeLgOperEntry 2 }

rtgTopNodeLgLnnTable OBJECT-TYPE
   SYNTAX     SEQUENCE OF RtgTopNodeLgLnnEntry
   ACCESS     not-accessible
   STATUS     mandatory
   DESCRIPTION
     "*** THIS TABLE CURRENTLY NOT IMPLEMENTED ***

      This attribute is a list of integers which specify the logical network 
      numbers supported by the trunk group. 
      
      Each of these numbers corresponds with a particular instance of 
      network protocol supported on this switch. LNN 0 is present on all 
      trunks by default to allow Passport control traffic on the trunk."
::= { rtgTopNodeLg 235 }

rtgTopNodeLgLnnEntry OBJECT-TYPE
   SYNTAX     RtgTopNodeLgLnnEntry
   ACCESS     not-accessible
   STATUS     mandatory
   DESCRIPTION
     "An entry in the rtgTopNodeLgLnnTable."
   INDEX {
      rtgIndex,
      rtgTopIndex,
      rtgTopNodeIndex,
      rtgTopNodeLgIndex,
      rtgTopNodeLgLnnValue }
::= { rtgTopNodeLgLnnTable 1 }

RtgTopNodeLgLnnEntry ::= SEQUENCE {
   rtgTopNodeLgLnnValue
      Integer32 }

rtgTopNodeLgLnnValue OBJECT-TYPE
   SYNTAX     Integer32 (0..2047)
   ACCESS     read-only
   STATUS     mandatory
   DESCRIPTION
     "This variable represents both the value and the index for the
      rtgTopNodeLgLnnTable."
::= { rtgTopNodeLgLnnEntry 1 }

-- 
-- *** THIS SUBTREE CURRENTLY NOT IMPLEMENTED ***
-- 

-- Rtg Top Node/<neighborNodeName> LinkGroup/
-- <neighborNodeName> Trunk/<Trm Lk Id>
-- This component corresponds to a trunk object stored in topological 
-- database. There is one instance of this component for every 
-- TplPorTrunk that the TplTrunkGroup component consists of. The 
-- TplPorTrunk instance is the same as link instance allocated by Trm 
-- to a Trunk which can carry PORS traffic. Display command applied 
-- to this component shows PORS data of the trunk object in 
-- topological database. 

rtgTopNodeLgTrkObj OBJECT IDENTIFIER ::= { rtgTopNodeLg 2 }



rtgTopNodeLgTrkObjRowStatusTable OBJECT-TYPE
   SYNTAX     SEQUENCE OF RtgTopNodeLgTrkObjRowStatusEntry
   ACCESS     not-accessible
   STATUS     mandatory
   DESCRIPTION
     "*** THIS TABLE CURRENTLY NOT IMPLEMENTED ***

      This entry controls the addition and deletion of 
      rtgTopNodeLgTrkObj components."
::= { rtgTopNodeLgTrkObj 1 }

rtgTopNodeLgTrkObjRowStatusEntry OBJECT-TYPE
   SYNTAX     RtgTopNodeLgTrkObjRowStatusEntry
   ACCESS     not-accessible
   STATUS     mandatory
   DESCRIPTION
     "A single entry in the table represents a single 
      rtgTopNodeLgTrkObj component."
   INDEX {
      rtgIndex,
      rtgTopIndex,
      rtgTopNodeIndex,
      rtgTopNodeLgIndex,
      rtgTopNodeLgTrkObjIndex }
::= { rtgTopNodeLgTrkObjRowStatusTable 1 }

RtgTopNodeLgTrkObjRowStatusEntry ::= SEQUENCE {
   rtgTopNodeLgTrkObjRowStatus
      RowStatus,
   rtgTopNodeLgTrkObjComponentName
      DisplayString,
   rtgTopNodeLgTrkObjStorageType
      StorageType,
   rtgTopNodeLgTrkObjIndex
      Integer32 }

rtgTopNodeLgTrkObjRowStatus OBJECT-TYPE
   SYNTAX     RowStatus 
   ACCESS     read-only
   STATUS     mandatory
   DESCRIPTION
     "This variable is used as the basis for SNMP naming of
      rtgTopNodeLgTrkObj components.
      These components cannot be added nor deleted."
::= { rtgTopNodeLgTrkObjRowStatusEntry 1 }

rtgTopNodeLgTrkObjComponentName OBJECT-TYPE
   SYNTAX     DisplayString 
   ACCESS     read-only
   STATUS     mandatory
   DESCRIPTION
     "This variable provides the component's string name for
      use with the ASCII Console Interface"
::= { rtgTopNodeLgTrkObjRowStatusEntry 2 }

rtgTopNodeLgTrkObjStorageType OBJECT-TYPE
   SYNTAX     StorageType 
   ACCESS     read-only
   STATUS     mandatory
   DESCRIPTION
     "This variable represents the storage type value for the
      rtgTopNodeLgTrkObj tables."
::= { rtgTopNodeLgTrkObjRowStatusEntry 4 }

rtgTopNodeLgTrkObjIndex OBJECT-TYPE
   SYNTAX     Integer32 (1..1023)
   ACCESS     not-accessible
   STATUS     mandatory
   DESCRIPTION
     "This variable represents the index for the rtgTopNodeLgTrkObj tables."
::= { rtgTopNodeLgTrkObjRowStatusEntry 10 }

rtgTopNodeLgTrkObjOperTable OBJECT-TYPE
   SYNTAX     SEQUENCE OF RtgTopNodeLgTrkObjOperEntry
   ACCESS     not-accessible
   STATUS     mandatory
   DESCRIPTION
     "*** THIS TABLE CURRENTLY NOT IMPLEMENTED ***

      Rtg Top Node/<neighborNodeName> LinkGroup/
      <neighborNodeName> Trunk/<Trm Lk Id> Operational
      This group contains the operational data stored and maintained by 
      TplPorTrunk component."
::= { rtgTopNodeLgTrkObj 10 }

rtgTopNodeLgTrkObjOperEntry OBJECT-TYPE
   SYNTAX     RtgTopNodeLgTrkObjOperEntry
   ACCESS     not-accessible
   STATUS     mandatory
   DESCRIPTION
     "An entry in the rtgTopNodeLgTrkObjOperTable."
   INDEX {
      rtgIndex,
      rtgTopIndex,
      rtgTopNodeIndex,
      rtgTopNodeLgIndex,
      rtgTopNodeLgTrkObjIndex }
::= { rtgTopNodeLgTrkObjOperTable 1 }

RtgTopNodeLgTrkObjOperEntry ::= SEQUENCE {
   rtgTopNodeLgTrkObjMaxReservableBwOut
      Gauge32,
   rtgTopNodeLgTrkObjTrunkCost
      Unsigned32,
   rtgTopNodeLgTrkObjTrunkDelay
      Unsigned32,
   rtgTopNodeLgTrkObjTrunkSecurity
      Unsigned32,
   rtgTopNodeLgTrkObjSupportedTrafficTypes
      OCTET STRING,
   rtgTopNodeLgTrkObjTrunkType
      INTEGER,
   rtgTopNodeLgTrkObjCustomerParameter
      Unsigned32,
   rtgTopNodeLgTrkObjFarEndTrmLkInstance
      Unsigned32 }

rtgTopNodeLgTrkObjMaxReservableBwOut OBJECT-TYPE
   SYNTAX     Gauge32 (0..4294967295)
   ACCESS     read-only
   STATUS     mandatory
   DESCRIPTION
     "This attribute displays trunk bandwidth which can be used for 
      reservations on behalf of connections requiring path oriented 
      routing. This bandwidth is displayed in bit/s and has been calculated 
      by concerned trunk path administrator from the trunk bandwidth 
      and from the percentage of trunk bandwidth provisioned for 
      reservations by PORS."
::= { rtgTopNodeLgTrkObjOperEntry 1 }

rtgTopNodeLgTrkObjTrunkCost OBJECT-TYPE
   SYNTAX     Unsigned32 (1..255)
   ACCESS     read-only
   STATUS     mandatory
   DESCRIPTION
     "This attribute displays trunk cost metric provisioned as trunkCost 
      attribute of a concerned trunk path administrator."
::= { rtgTopNodeLgTrkObjOperEntry 2 }

rtgTopNodeLgTrkObjTrunkDelay OBJECT-TYPE
   SYNTAX     Unsigned32 (0..65535)
   ACCESS     read-only
   STATUS     mandatory
   DESCRIPTION
     "This attribute displays one-directional trunk delay measured by 
      trunk during staging. This is half (rounded down to an integer) of 
      delay displayable by attribute of ID aTrmLinkDelay_c."
::= { rtgTopNodeLgTrkObjOperEntry 3 }

rtgTopNodeLgTrkObjTrunkSecurity OBJECT-TYPE
   SYNTAX     Unsigned32 (0..7)
   ACCESS     read-only
   STATUS     mandatory
   DESCRIPTION
     "This attribute displays trunk security metric provisioned as 
      trunkSecurity attribute of a concerned trunk path administrator."
::= { rtgTopNodeLgTrkObjOperEntry 4 }

rtgTopNodeLgTrkObjSupportedTrafficTypes OBJECT-TYPE
   SYNTAX     OCTET STRING (SIZE (1))
   ACCESS     read-only
   STATUS     mandatory
   DESCRIPTION
     "This attribute indicates the type of traffic that can be transmitted on 
      the trunk. There are eight(8) possible traffic types, and the trunk can 
      transmit all of them if desired. The voice, data and video traffic 
      types are defined, and five(5) other traffic types can be defined in 
      concerned trunk path administrator. This attribute is used in the 
      route selection process to limit the route to trunks that support the 
      traffic to be carried by the path.

      Description of bits:
      voice(0)
      data(1)
      video(2)
      trafficType1(3)
      trafficType2(4)
      trafficType3(5)
      trafficType4(6)
      trafficType5(7)"
::= { rtgTopNodeLgTrkObjOperEntry 5 }

rtgTopNodeLgTrkObjTrunkType OBJECT-TYPE
   SYNTAX     INTEGER  {
                 terrestrial(0),
                 satellite(1),
                 trunkType1(2),
                 trunkType2(3),
                 trunkType3(4),
                 trunkType4(5),
                 trunkType5(6),
                 trunkType6(7) }
   ACCESS     read-only
   STATUS     mandatory
   DESCRIPTION
     "This attribute lists the type of the trunk. There can be up to eight(8) 
      types of trunks. The terrestrial and satellite trunk types have been 
      defined, leaving six(6) remaining types that can be defined by the 
      network administration. The set of allowed trunk types for a path is 
      indicated in the permittedTrunkType attribute of the PLC. When 
      selecting a route, PORS only chooses trunks whose PA trunkType 
      are in the permittedTrunkTypes set of the path."
::= { rtgTopNodeLgTrkObjOperEntry 6 }

rtgTopNodeLgTrkObjCustomerParameter OBJECT-TYPE
   SYNTAX     Unsigned32 (0..7)
   ACCESS     read-only
   STATUS     mandatory
   DESCRIPTION
     "This attribute indicates the customer defined parameter for the 
      trunk. Its value, a number from zero(0) to seven(7), is chosen by a 
      network administration to have a meaning specific to their network, 
      thus allowing them to customize the use of their trunks. A 
      complementary PLC attribute, requiredCustomerParameter, also has 
      a value from zero(0) to seven(7). The Route Selector does not 
      consider trunks whose PA customerParameter is greater than the 
      requiredCustomParameter of the path."
::= { rtgTopNodeLgTrkObjOperEntry 7 }

rtgTopNodeLgTrkObjFarEndTrmLkInstance OBJECT-TYPE
   SYNTAX     Unsigned32 (1..1023)
   ACCESS     read-only
   STATUS     mandatory
   DESCRIPTION
     "This attribute indicates identification of the corresponding trunk 
      providing the reverse direction of transmission."
::= { rtgTopNodeLgTrkObjOperEntry 8 }

rtgTopNodeLgTrkObjUnresTable OBJECT-TYPE
   SYNTAX     SEQUENCE OF RtgTopNodeLgTrkObjUnresEntry
   ACCESS     not-accessible
   STATUS     mandatory
   DESCRIPTION
     "*** THIS TABLE CURRENTLY NOT IMPLEMENTED ***

      This attribute displays a table. In the first row there are setup 
      priorities. In the second row there are numerators of parts of 
      unreserved bandwidth corresponding to setup priority 0 (first 
      column) through 4 (fifth column). The denominator is 255."
::= { rtgTopNodeLgTrkObj 234 }

rtgTopNodeLgTrkObjUnresEntry OBJECT-TYPE
   SYNTAX     RtgTopNodeLgTrkObjUnresEntry
   ACCESS     not-accessible
   STATUS     mandatory
   DESCRIPTION
     "An entry in the rtgTopNodeLgTrkObjUnresTable."
   INDEX {
      rtgIndex,
      rtgTopIndex,
      rtgTopNodeIndex,
      rtgTopNodeLgIndex,
      rtgTopNodeLgTrkObjIndex,
      rtgTopNodeLgTrkObjUnresSetupPriorityIndex,
      rtgTopNodeLgTrkObjUnresUnreservedBwPartsIndex }
::= { rtgTopNodeLgTrkObjUnresTable 1 }

RtgTopNodeLgTrkObjUnresEntry ::= SEQUENCE {
   rtgTopNodeLgTrkObjUnresSetupPriorityIndex
      INTEGER,
   rtgTopNodeLgTrkObjUnresUnreservedBwPartsIndex
      Integer32,
   rtgTopNodeLgTrkObjUnresValue
      Unsigned32 }

rtgTopNodeLgTrkObjUnresSetupPriorityIndex OBJECT-TYPE
   SYNTAX     INTEGER  {
                 bwPartOver255(0) }
   ACCESS     not-accessible
   STATUS     mandatory
   DESCRIPTION
     "This variable represents the next to last index for the 
      rtgTopNodeLgTrkObjUnresTable."
::= { rtgTopNodeLgTrkObjUnresEntry 1 }

rtgTopNodeLgTrkObjUnresUnreservedBwPartsIndex OBJECT-TYPE
   SYNTAX     Integer32 (0..4)
   ACCESS     not-accessible
   STATUS     mandatory
   DESCRIPTION
     "This variable represents the final index for the 
      rtgTopNodeLgTrkObjUnresTable."
::= { rtgTopNodeLgTrkObjUnresEntry 2 }

rtgTopNodeLgTrkObjUnresValue OBJECT-TYPE
   SYNTAX     Unsigned32 (0..255)
   ACCESS     read-only
   STATUS     mandatory
   DESCRIPTION
     "This variable represents an individual value for the
      rtgTopNodeLgTrkObjUnresTable."
::= { rtgTopNodeLgTrkObjUnresEntry 3 }


-- TransportResource
-- This component resides on all Passport modules and is responsible 
-- for managing link resources. It acts as an intermediary between a 
-- link and all the routing systems that use the link.

trm OBJECT IDENTIFIER ::= { components 41 }



trmRowStatusTable OBJECT-TYPE
   SYNTAX     SEQUENCE OF TrmRowStatusEntry
   ACCESS     not-accessible
   STATUS     mandatory
   DESCRIPTION
     "This entry controls the addition and deletion of 
      trm components."
::= { trm 1 }

trmRowStatusEntry OBJECT-TYPE
   SYNTAX     TrmRowStatusEntry
   ACCESS     not-accessible
   STATUS     mandatory
   DESCRIPTION
     "A single entry in the table represents a single 
      trm component."
   INDEX {
      trmIndex }
::= { trmRowStatusTable 1 }

TrmRowStatusEntry ::= SEQUENCE {
   trmRowStatus
      RowStatus,
   trmComponentName
      DisplayString,
   trmStorageType
      StorageType,
   trmIndex
      NonReplicated }

trmRowStatus OBJECT-TYPE
   SYNTAX     RowStatus 
   ACCESS     read-only
   STATUS     mandatory
   DESCRIPTION
     "This variable is used as the basis for SNMP naming of
      trm components.
      These components cannot be added nor deleted."
::= { trmRowStatusEntry 1 }

trmComponentName OBJECT-TYPE
   SYNTAX     DisplayString 
   ACCESS     read-only
   STATUS     mandatory
   DESCRIPTION
     "This variable provides the component's string name for
      use with the ASCII Console Interface"
::= { trmRowStatusEntry 2 }

trmStorageType OBJECT-TYPE
   SYNTAX     StorageType 
   ACCESS     read-only
   STATUS     mandatory
   DESCRIPTION
     "This variable represents the storage type value for the
      trm tables."
::= { trmRowStatusEntry 4 }

trmIndex OBJECT-TYPE
   SYNTAX     NonReplicated 
   ACCESS     not-accessible
   STATUS     mandatory
   DESCRIPTION
     "This variable represents the index for the trm tables."
::= { trmRowStatusEntry 10 }

-- 
-- *** THIS SUBTREE CURRENTLY NOT IMPLEMENTED ***
-- 

-- Trm Link/<n> 
-- This component is a dynamic subcomponent of TransportResource. 
-- It has operational attributes only which are stored and maintained 
-- by this component for listing links.

trmLk OBJECT IDENTIFIER ::= { trm 2 }



trmLkRowStatusTable OBJECT-TYPE
   SYNTAX     SEQUENCE OF TrmLkRowStatusEntry
   ACCESS     not-accessible
   STATUS     mandatory
   DESCRIPTION
     "*** THIS TABLE CURRENTLY NOT IMPLEMENTED ***

      This entry controls the addition and deletion of 
      trmLk components."
::= { trmLk 1 }

trmLkRowStatusEntry OBJECT-TYPE
   SYNTAX     TrmLkRowStatusEntry
   ACCESS     not-accessible
   STATUS     mandatory
   DESCRIPTION
     "A single entry in the table represents a single 
      trmLk component."
   INDEX {
      trmIndex,
      trmLkIndex }
::= { trmLkRowStatusTable 1 }

TrmLkRowStatusEntry ::= SEQUENCE {
   trmLkRowStatus
      RowStatus,
   trmLkComponentName
      DisplayString,
   trmLkStorageType
      StorageType,
   trmLkIndex
      Integer32 }

trmLkRowStatus OBJECT-TYPE
   SYNTAX     RowStatus 
   ACCESS     read-only
   STATUS     mandatory
   DESCRIPTION
     "This variable is used as the basis for SNMP naming of
      trmLk components.
      These components cannot be added nor deleted."
::= { trmLkRowStatusEntry 1 }

trmLkComponentName OBJECT-TYPE
   SYNTAX     DisplayString 
   ACCESS     read-only
   STATUS     mandatory
   DESCRIPTION
     "This variable provides the component's string name for
      use with the ASCII Console Interface"
::= { trmLkRowStatusEntry 2 }

trmLkStorageType OBJECT-TYPE
   SYNTAX     StorageType 
   ACCESS     read-only
   STATUS     mandatory
   DESCRIPTION
     "This variable represents the storage type value for the
      trmLk tables."
::= { trmLkRowStatusEntry 4 }

trmLkIndex OBJECT-TYPE
   SYNTAX     Integer32 (1..1023)
   ACCESS     not-accessible
   STATUS     mandatory
   DESCRIPTION
     "This variable represents the index for the trmLk tables."
::= { trmLkRowStatusEntry 10 }

trmLkOperTable OBJECT-TYPE
   SYNTAX     SEQUENCE OF TrmLkOperEntry
   ACCESS     not-accessible
   STATUS     mandatory
   DESCRIPTION
     "*** THIS TABLE CURRENTLY NOT IMPLEMENTED ***

      Trm Lk/<n> Operational
      This group of attributes is used to list links. These links are all 
      registered with Transport Resource Manager. They have a status 
      which reflects the current view of the link."
::= { trmLk 10 }

trmLkOperEntry OBJECT-TYPE
   SYNTAX     TrmLkOperEntry
   ACCESS     not-accessible
   STATUS     mandatory
   DESCRIPTION
     "An entry in the trmLkOperTable."
   INDEX {
      trmIndex,
      trmLkIndex }
::= { trmLkOperTable 1 }

TrmLkOperEntry ::= SEQUENCE {
   trmLkStatus
      INTEGER,
   trmLkThroughput
      Gauge32,
   trmLkDelay
      Gauge32,
   trmLkMaxTxUnit
      Unsigned32,
   trmLkLinkComponentName
      RowPointer,
   trmLkDelayUsec
      FixedPoint1 }

trmLkStatus OBJECT-TYPE
   SYNTAX     INTEGER  {
                 inactive(1),
                 joining(2),
                 online(3) }
   ACCESS     read-only
   STATUS     mandatory
   DESCRIPTION
     "This attribute indicates if the inactive link is disabled, joining, 
      waiting to join, or in standby mode.
      
      inactive - The link is known to TRM but is not active. This can 
      mean that it is disabled, or has not yet started to join.
      joining - The link has requested to join the routing systems.
      online- The link is active and has joined one or more routing 
      systems."
::= { trmLkOperEntry 1 }

trmLkThroughput OBJECT-TYPE
   SYNTAX     Gauge32 (1..640000000)
   ACCESS     read-only
   STATUS     mandatory
   DESCRIPTION
     "This attribute indicates the throughput of the link in kbit/s. This 
      value represents a nominal bandwidth available for connectionless 
      traffic, after the maximum reserved for path-oriented traffic has 
      been subtracted from trunk bandwidth. If a trunk speed override is 
      specified, it is used instead. The 'throughput' value can be 
      exceeded by connectionless traffic whenever path-oriented traffic is 
      not using it's reserved bandwidth."
::= { trmLkOperEntry 2 }

trmLkDelay OBJECT-TYPE
   SYNTAX     Gauge32 (1..1500)
   ACCESS     read-only
   STATUS     obsolete
   DESCRIPTION
     "This is the round trip delay of the link in milliseconds. This value 
      represents a nominal delay for connectionless traffic. 
      Connectionless traffic is biased away from trunks carrying path-
      oriented traffic by increasing this value. The value of this attribute is 
      a function of the percentage of reserved path-oriented bandwidth 
      and takes a maximum value of 1500 msec for 100% path-oriented 
      trunks. If an override delay is specified, it will be used instead."
::= { trmLkOperEntry 3 }

trmLkMaxTxUnit OBJECT-TYPE
   SYNTAX     Unsigned32 (1..65535)
   ACCESS     read-only
   STATUS     mandatory
   DESCRIPTION
     "This attribute indicates the maximum data unit in bytes of this link. 
      It represents the maximum frame length (including user data and 
      routing headers) that can be sent on the link."
::= { trmLkOperEntry 4 }

trmLkLinkComponentName OBJECT-TYPE
   SYNTAX     RowPointer 
   ACCESS     read-only
   STATUS     mandatory
   DESCRIPTION
     "This attribute indicates the link's component name. A link is either 
      a trunk or a gateway to another module. The component name may 
      be used to obtain additional information from the link system."
::= { trmLkOperEntry 5 }

trmLkDelayUsec OBJECT-TYPE
   SYNTAX     FixedPoint1 (10..15000)
   ACCESS     read-only
   STATUS     mandatory
   DESCRIPTION
     "This attribute indicates the round trip delay of the link in 
      milliseconds. This value represents a nominal delay for 
      connectionless traffic. Connectionless traffic is biased away from 
      trunks carrying path-oriented traffic by increasing this value. The 
      value of this attribute is a function of the percentage of reserved 
      path-oriented bandwidth and takes a maximum value of 1500 msec 
      for 100% path-oriented trunks. If a delay override is specified, it 
      will be used instead."
::= { trmLkOperEntry 6 }

trmLkFwdStatsTable OBJECT-TYPE
   SYNTAX     SEQUENCE OF TrmLkFwdStatsEntry
   ACCESS     not-accessible
   STATUS     mandatory
   DESCRIPTION
     "*** THIS TABLE CURRENTLY NOT IMPLEMENTED ***

      This group of attributes is used to display egress statistics collected 
      by packet forwarding on this link. The statistics can be used to 
      monitor congestion conditions and packet discards on a link."
::= { trmLk 11 }

trmLkFwdStatsEntry OBJECT-TYPE
   SYNTAX     TrmLkFwdStatsEntry
   ACCESS     not-accessible
   STATUS     mandatory
   DESCRIPTION
     "An entry in the trmLkFwdStatsTable."
   INDEX {
      trmIndex,
      trmLkIndex }
::= { trmLkFwdStatsTable 1 }

TrmLkFwdStatsEntry ::= SEQUENCE {
   trmLkFciSet
      Counter32,
   trmLkOverflowAttempts
      Counter32,
   trmLkPathOverflowAttempts
      Counter32 }

trmLkFciSet OBJECT-TYPE
   SYNTAX     Counter32 
   ACCESS     read-only
   STATUS     mandatory
   DESCRIPTION
     "This attribute counts the packets whose FCI bits are set by packet 
      forwarding due to congestion on this link, and when the 
      forwardingPolicy attribute of Routing DpnAddressPlan is set to 
      loadshare or loadspread. This counter wraps around to zero when 
      the maximum value is reached."
::= { trmLkFwdStatsEntry 1 }

trmLkOverflowAttempts OBJECT-TYPE
   SYNTAX     Counter32 
   ACCESS     read-only
   STATUS     mandatory
   DESCRIPTION
     "This attribute counts the number of times DPRS packet forwarding 
      attempts to overflow packets to another link in a link group due to 
      congestion on this link. It is used only when the attribute 
      forwardingPolicy in component rtg dpn is set to the value 
      loadspreading. This counter wraps around to zero when the 
      maximum value is reached."
::= { trmLkFwdStatsEntry 2 }

trmLkPathOverflowAttempts OBJECT-TYPE
   SYNTAX     Counter32 
   ACCESS     read-only
   STATUS     mandatory
   DESCRIPTION
     "This attribute counts the number of times DPRS packet forwarding 
      attempts to overflow packets to another link group due to 
      congestion on the link group of this link. This counter wraps around 
      to zero when the maximum value is reached."
::= { trmLkFwdStatsEntry 3 }

trmLkDiscardCongestedTable OBJECT-TYPE
   SYNTAX     SEQUENCE OF TrmLkDiscardCongestedEntry
   ACCESS     not-accessible
   STATUS     mandatory
   DESCRIPTION
     "*** THIS TABLE CURRENTLY NOT IMPLEMENTED ***

      This attribute counts the packets that have been discarded by packet 
      forwarding due to congestion on this link and when the 
      forwardingPolicy attribute of Routing DpnAddressPlan is set to 
      loadshare or loadspread. 
      
      This attribute is a vector with three entries. Each entry corresponds 
      to a discard priority of the packet. The first entry represents the 
      discard count of packets with discard priority 1, the second entry 
      discard priority 2, and the third entry discard priority 3. Each entry 
      (counter) wraps around to zero when the maximum value is 
      reached."
::= { trmLk 280 }

trmLkDiscardCongestedEntry OBJECT-TYPE
   SYNTAX     TrmLkDiscardCongestedEntry
   ACCESS     not-accessible
   STATUS     mandatory
   DESCRIPTION
     "An entry in the trmLkDiscardCongestedTable."
   INDEX {
      trmIndex,
      trmLkIndex,
      trmLkDiscardCongestedIndex }
::= { trmLkDiscardCongestedTable 1 }

TrmLkDiscardCongestedEntry ::= SEQUENCE {
   trmLkDiscardCongestedIndex
      INTEGER,
   trmLkDiscardCongestedValue
      Counter32 }

trmLkDiscardCongestedIndex OBJECT-TYPE
   SYNTAX     INTEGER  {
                 discardPriority1(0),
                 discardPriority2(1),
                 discardPriority3(2) }
   ACCESS     not-accessible
   STATUS     mandatory
   DESCRIPTION
     "This variable represents the trmLkDiscardCongestedTable
      specific index for the trmLkDiscardCongestedTable."
::= { trmLkDiscardCongestedEntry 1 }

trmLkDiscardCongestedValue OBJECT-TYPE
   SYNTAX     Counter32 
   ACCESS     read-only
   STATUS     mandatory
   DESCRIPTION
     "This variable represents an individual value for the
      trmLkDiscardCongestedTable."
::= { trmLkDiscardCongestedEntry 2 }

-- 
-- *** THIS SUBTREE CURRENTLY NOT IMPLEMENTED ***
-- 

-- Trm LinkGroup /<neighborNodeName>
-- This component is a dynamic subcomponent of TransportResource. 
-- It has operational attributes only which are stored and maintained 
-- by this component for the purpose of displaying link groups.
-- 
-- A link group contains 1 to 4 links, all of which are active.
-- 
-- The neighbour node name is the node name provisioned in the 
-- Module component on the remote Passport module if the link group 
-- connects to a Passport switch. Otherwise it is the remote module 
-- node name provisioned in the components of gateways in this link 
-- group.
-- 
-- Links in a link group can have differing throughputs and round trip 
-- delays. If the difference within the set of throughputs, or within the 
-- set of delays is significant, some links may not be used. The rule 
-- that is applied is that links within 50% of the throughput of the 
-- highest throughput link are used for the throughput RCOS. 
-- Similiarily links within 50% of the delay of the lowest delay link 
-- are used for the throughput RCOS. As links are added or removed 
-- from the link group, the set of links which are used is re-evaluated.

trmLg OBJECT IDENTIFIER ::= { trm 3 }



trmLgRowStatusTable OBJECT-TYPE
   SYNTAX     SEQUENCE OF TrmLgRowStatusEntry
   ACCESS     not-accessible
   STATUS     mandatory
   DESCRIPTION
     "*** THIS TABLE CURRENTLY NOT IMPLEMENTED ***

      This entry controls the addition and deletion of 
      trmLg components."
::= { trmLg 1 }

trmLgRowStatusEntry OBJECT-TYPE
   SYNTAX     TrmLgRowStatusEntry
   ACCESS     not-accessible
   STATUS     mandatory
   DESCRIPTION
     "A single entry in the table represents a single 
      trmLg component."
   INDEX {
      trmIndex,
      trmLgIndex }
::= { trmLgRowStatusTable 1 }

TrmLgRowStatusEntry ::= SEQUENCE {
   trmLgRowStatus
      RowStatus,
   trmLgComponentName
      DisplayString,
   trmLgStorageType
      StorageType,
   trmLgIndex
      AsciiStringIndex }

trmLgRowStatus OBJECT-TYPE
   SYNTAX     RowStatus 
   ACCESS     read-only
   STATUS     mandatory
   DESCRIPTION
     "This variable is used as the basis for SNMP naming of
      trmLg components.
      These components cannot be added nor deleted."
::= { trmLgRowStatusEntry 1 }

trmLgComponentName OBJECT-TYPE
   SYNTAX     DisplayString 
   ACCESS     read-only
   STATUS     mandatory
   DESCRIPTION
     "This variable provides the component's string name for
      use with the ASCII Console Interface"
::= { trmLgRowStatusEntry 2 }

trmLgStorageType OBJECT-TYPE
   SYNTAX     StorageType 
   ACCESS     read-only
   STATUS     mandatory
   DESCRIPTION
     "This variable represents the storage type value for the
      trmLg tables."
::= { trmLgRowStatusEntry 4 }

trmLgIndex OBJECT-TYPE
   SYNTAX     AsciiStringIndex (SIZE (1..12))
   ACCESS     not-accessible
   STATUS     mandatory
   DESCRIPTION
     "This variable represents the index for the trmLg tables."
::= { trmLgRowStatusEntry 10 }

-- 
-- *** THIS SUBTREE CURRENTLY NOT IMPLEMENTED ***
-- 

-- Trm Lg/<neighborNodeName> Link /<linkInstance> 
-- This component is a dynamic subcomponent of LinkGroup. It has 
-- operational attributes only which are stored and maintained by this 
-- component for displaying links in a link group. There are 1 to 4 
-- active links in a link group. A link group object is not created until 
-- there is at least one active link in the group. Inactive links are not 
-- shown in a link group.

trmLgLk OBJECT IDENTIFIER ::= { trmLg 2 }



trmLgLkRowStatusTable OBJECT-TYPE
   SYNTAX     SEQUENCE OF TrmLgLkRowStatusEntry
   ACCESS     not-accessible
   STATUS     mandatory
   DESCRIPTION
     "*** THIS TABLE CURRENTLY NOT IMPLEMENTED ***

      This entry controls the addition and deletion of 
      trmLgLk components."
::= { trmLgLk 1 }

trmLgLkRowStatusEntry OBJECT-TYPE
   SYNTAX     TrmLgLkRowStatusEntry
   ACCESS     not-accessible
   STATUS     mandatory
   DESCRIPTION
     "A single entry in the table represents a single 
      trmLgLk component."
   INDEX {
      trmIndex,
      trmLgIndex,
      trmLgLkIndex }
::= { trmLgLkRowStatusTable 1 }

TrmLgLkRowStatusEntry ::= SEQUENCE {
   trmLgLkRowStatus
      RowStatus,
   trmLgLkComponentName
      DisplayString,
   trmLgLkStorageType
      StorageType,
   trmLgLkIndex
      Integer32 }

trmLgLkRowStatus OBJECT-TYPE
   SYNTAX     RowStatus 
   ACCESS     read-only
   STATUS     mandatory
   DESCRIPTION
     "This variable is used as the basis for SNMP naming of
      trmLgLk components.
      These components cannot be added nor deleted."
::= { trmLgLkRowStatusEntry 1 }

trmLgLkComponentName OBJECT-TYPE
   SYNTAX     DisplayString 
   ACCESS     read-only
   STATUS     mandatory
   DESCRIPTION
     "This variable provides the component's string name for
      use with the ASCII Console Interface"
::= { trmLgLkRowStatusEntry 2 }

trmLgLkStorageType OBJECT-TYPE
   SYNTAX     StorageType 
   ACCESS     read-only
   STATUS     mandatory
   DESCRIPTION
     "This variable represents the storage type value for the
      trmLgLk tables."
::= { trmLgLkRowStatusEntry 4 }

trmLgLkIndex OBJECT-TYPE
   SYNTAX     Integer32 (1..1023)
   ACCESS     not-accessible
   STATUS     mandatory
   DESCRIPTION
     "This variable represents the index for the trmLgLk tables."
::= { trmLgLkRowStatusEntry 10 }

trmLgLkOperTable OBJECT-TYPE
   SYNTAX     SEQUENCE OF TrmLgLkOperEntry
   ACCESS     not-accessible
   STATUS     mandatory
   DESCRIPTION
     "*** THIS TABLE CURRENTLY NOT IMPLEMENTED ***

      Trm Lk/<n> Operational
      This group of attributes is used to list links. These links are all 
      registered with Transport Resource Manager. They have a status 
      which reflects the current view of the link."
::= { trmLgLk 10 }

trmLgLkOperEntry OBJECT-TYPE
   SYNTAX     TrmLgLkOperEntry
   ACCESS     not-accessible
   STATUS     mandatory
   DESCRIPTION
     "An entry in the trmLgLkOperTable."
   INDEX {
      trmIndex,
      trmLgIndex,
      trmLgLkIndex }
::= { trmLgLkOperTable 1 }

TrmLgLkOperEntry ::= SEQUENCE {
   trmLgLkStatus
      INTEGER,
   trmLgLkThroughput
      Gauge32,
   trmLgLkDelay
      Gauge32,
   trmLgLkMaxTxUnit
      Unsigned32,
   trmLgLkLinkComponentName
      RowPointer,
   trmLgLkDelayUsec
      FixedPoint1 }

trmLgLkStatus OBJECT-TYPE
   SYNTAX     INTEGER  {
                 inactive(1),
                 joining(2),
                 online(3) }
   ACCESS     read-only
   STATUS     mandatory
   DESCRIPTION
     "This attribute indicates if the inactive link is disabled, joining, 
      waiting to join, or in standby mode.
      
      inactive - The link is known to TRM but is not active. This can 
      mean that it is disabled, or has not yet started to join.
      joining - The link has requested to join the routing systems.
      online- The link is active and has joined one or more routing 
      systems."
::= { trmLgLkOperEntry 1 }

trmLgLkThroughput OBJECT-TYPE
   SYNTAX     Gauge32 (1..640000000)
   ACCESS     read-only
   STATUS     mandatory
   DESCRIPTION
     "This attribute indicates the throughput of the link in kbit/s. This 
      value represents a nominal bandwidth available for connectionless 
      traffic, after the maximum reserved for path-oriented traffic has 
      been subtracted from trunk bandwidth. If a trunk speed override is 
      specified, it is used instead. The 'throughput' value can be 
      exceeded by connectionless traffic whenever path-oriented traffic is 
      not using it's reserved bandwidth."
::= { trmLgLkOperEntry 2 }

trmLgLkDelay OBJECT-TYPE
   SYNTAX     Gauge32 (1..1500)
   ACCESS     read-only
   STATUS     obsolete
   DESCRIPTION
     "This is the round trip delay of the link in milliseconds. This value 
      represents a nominal delay for connectionless traffic. 
      Connectionless traffic is biased away from trunks carrying path-
      oriented traffic by increasing this value. The value of this attribute is 
      a function of the percentage of reserved path-oriented bandwidth 
      and takes a maximum value of 1500 msec for 100% path-oriented 
      trunks. If an override delay is specified, it will be used instead."
::= { trmLgLkOperEntry 3 }

trmLgLkMaxTxUnit OBJECT-TYPE
   SYNTAX     Unsigned32 (1..65535)
   ACCESS     read-only
   STATUS     mandatory
   DESCRIPTION
     "This attribute indicates the maximum data unit in bytes of this link. 
      It represents the maximum frame length (including user data and 
      routing headers) that can be sent on the link."
::= { trmLgLkOperEntry 4 }

trmLgLkLinkComponentName OBJECT-TYPE
   SYNTAX     RowPointer 
   ACCESS     read-only
   STATUS     mandatory
   DESCRIPTION
     "This attribute indicates the link's component name. A link is either 
      a trunk or a gateway to another module. The component name may 
      be used to obtain additional information from the link system."
::= { trmLgLkOperEntry 5 }

trmLgLkDelayUsec OBJECT-TYPE
   SYNTAX     FixedPoint1 (10..15000)
   ACCESS     read-only
   STATUS     mandatory
   DESCRIPTION
     "This attribute indicates the round trip delay of the link in 
      milliseconds. This value represents a nominal delay for 
      connectionless traffic. Connectionless traffic is biased away from 
      trunks carrying path-oriented traffic by increasing this value. The 
      value of this attribute is a function of the percentage of reserved 
      path-oriented bandwidth and takes a maximum value of 1500 msec 
      for 100% path-oriented trunks. If a delay override is specified, it 
      will be used instead."
::= { trmLgLkOperEntry 6 }

trmLgLkFwdStatsTable OBJECT-TYPE
   SYNTAX     SEQUENCE OF TrmLgLkFwdStatsEntry
   ACCESS     not-accessible
   STATUS     mandatory
   DESCRIPTION
     "*** THIS TABLE CURRENTLY NOT IMPLEMENTED ***

      This group of attributes is used to display egress statistics collected 
      by packet forwarding on this link. The statistics can be used to 
      monitor congestion conditions and packet discards on a link."
::= { trmLgLk 11 }

trmLgLkFwdStatsEntry OBJECT-TYPE
   SYNTAX     TrmLgLkFwdStatsEntry
   ACCESS     not-accessible
   STATUS     mandatory
   DESCRIPTION
     "An entry in the trmLgLkFwdStatsTable."
   INDEX {
      trmIndex,
      trmLgIndex,
      trmLgLkIndex }
::= { trmLgLkFwdStatsTable 1 }

TrmLgLkFwdStatsEntry ::= SEQUENCE {
   trmLgLkFciSet
      Counter32,
   trmLgLkOverflowAttempts
      Counter32,
   trmLgLkPathOverflowAttempts
      Counter32 }

trmLgLkFciSet OBJECT-TYPE
   SYNTAX     Counter32 
   ACCESS     read-only
   STATUS     mandatory
   DESCRIPTION
     "This attribute counts the packets whose FCI bits are set by packet 
      forwarding due to congestion on this link, and when the 
      forwardingPolicy attribute of Routing DpnAddressPlan is set to 
      loadshare or loadspread. This counter wraps around to zero when 
      the maximum value is reached."
::= { trmLgLkFwdStatsEntry 1 }

trmLgLkOverflowAttempts OBJECT-TYPE
   SYNTAX     Counter32 
   ACCESS     read-only
   STATUS     mandatory
   DESCRIPTION
     "This attribute counts the number of times DPRS packet forwarding 
      attempts to overflow packets to another link in a link group due to 
      congestion on this link. It is used only when the attribute 
      forwardingPolicy in component rtg dpn is set to the value 
      loadspreading. This counter wraps around to zero when the 
      maximum value is reached."
::= { trmLgLkFwdStatsEntry 2 }

trmLgLkPathOverflowAttempts OBJECT-TYPE
   SYNTAX     Counter32 
   ACCESS     read-only
   STATUS     mandatory
   DESCRIPTION
     "This attribute counts the number of times DPRS packet forwarding 
      attempts to overflow packets to another link group due to 
      congestion on the link group of this link. This counter wraps around 
      to zero when the maximum value is reached."
::= { trmLgLkFwdStatsEntry 3 }

trmLgLkDiscardCongestedTable OBJECT-TYPE
   SYNTAX     SEQUENCE OF TrmLgLkDiscardCongestedEntry
   ACCESS     not-accessible
   STATUS     mandatory
   DESCRIPTION
     "*** THIS TABLE CURRENTLY NOT IMPLEMENTED ***

      This attribute counts the packets that have been discarded by packet 
      forwarding due to congestion on this link and when the 
      forwardingPolicy attribute of Routing DpnAddressPlan is set to 
      loadshare or loadspread. 
      
      This attribute is a vector with three entries. Each entry corresponds 
      to a discard priority of the packet. The first entry represents the 
      discard count of packets with discard priority 1, the second entry 
      discard priority 2, and the third entry discard priority 3. Each entry 
      (counter) wraps around to zero when the maximum value is 
      reached."
::= { trmLgLk 280 }

trmLgLkDiscardCongestedEntry OBJECT-TYPE
   SYNTAX     TrmLgLkDiscardCongestedEntry
   ACCESS     not-accessible
   STATUS     mandatory
   DESCRIPTION
     "An entry in the trmLgLkDiscardCongestedTable."
   INDEX {
      trmIndex,
      trmLgIndex,
      trmLgLkIndex,
      trmLgLkDiscardCongestedIndex }
::= { trmLgLkDiscardCongestedTable 1 }

TrmLgLkDiscardCongestedEntry ::= SEQUENCE {
   trmLgLkDiscardCongestedIndex
      INTEGER,
   trmLgLkDiscardCongestedValue
      Counter32 }

trmLgLkDiscardCongestedIndex OBJECT-TYPE
   SYNTAX     INTEGER  {
                 discardPriority1(0),
                 discardPriority2(1),
                 discardPriority3(2) }
   ACCESS     not-accessible
   STATUS     mandatory
   DESCRIPTION
     "This variable represents the trmLgLkDiscardCongestedTable
      specific index for the trmLgLkDiscardCongestedTable."
::= { trmLgLkDiscardCongestedEntry 1 }

trmLgLkDiscardCongestedValue OBJECT-TYPE
   SYNTAX     Counter32 
   ACCESS     read-only
   STATUS     mandatory
   DESCRIPTION
     "This variable represents an individual value for the
      trmLgLkDiscardCongestedTable."
::= { trmLgLkDiscardCongestedEntry 2 }

-- 
-- *** THIS SUBTREE CURRENTLY NOT IMPLEMENTED ***
-- 

-- Trm Lg/<neighborNodeName> LNN /<logical network number> 
-- This component is a dynamic subcomponent of LinkGroup. It has 
-- operational attributes only which are stored and maintained by this 
-- component for displaying address plans supported over this link 
-- group. A logical network number (which is used as an instance to 
-- this component) uniquely identifies an address plan and its traffic in 
-- a Passport network.

trmLgLNN OBJECT IDENTIFIER ::= { trmLg 3 }



trmLgLNNRowStatusTable OBJECT-TYPE
   SYNTAX     SEQUENCE OF TrmLgLNNRowStatusEntry
   ACCESS     not-accessible
   STATUS     mandatory
   DESCRIPTION
     "*** THIS TABLE CURRENTLY NOT IMPLEMENTED ***

      This entry controls the addition and deletion of 
      trmLgLNN components."
::= { trmLgLNN 1 }

trmLgLNNRowStatusEntry OBJECT-TYPE
   SYNTAX     TrmLgLNNRowStatusEntry
   ACCESS     not-accessible
   STATUS     mandatory
   DESCRIPTION
     "A single entry in the table represents a single 
      trmLgLNN component."
   INDEX {
      trmIndex,
      trmLgIndex,
      trmLgLNNIndex }
::= { trmLgLNNRowStatusTable 1 }

TrmLgLNNRowStatusEntry ::= SEQUENCE {
   trmLgLNNRowStatus
      RowStatus,
   trmLgLNNComponentName
      DisplayString,
   trmLgLNNStorageType
      StorageType,
   trmLgLNNIndex
      Integer32 }

trmLgLNNRowStatus OBJECT-TYPE
   SYNTAX     RowStatus 
   ACCESS     read-only
   STATUS     mandatory
   DESCRIPTION
     "This variable is used as the basis for SNMP naming of
      trmLgLNN components.
      These components cannot be added nor deleted."
::= { trmLgLNNRowStatusEntry 1 }

trmLgLNNComponentName OBJECT-TYPE
   SYNTAX     DisplayString 
   ACCESS     read-only
   STATUS     mandatory
   DESCRIPTION
     "This variable provides the component's string name for
      use with the ASCII Console Interface"
::= { trmLgLNNRowStatusEntry 2 }

trmLgLNNStorageType OBJECT-TYPE
   SYNTAX     StorageType 
   ACCESS     read-only
   STATUS     mandatory
   DESCRIPTION
     "This variable represents the storage type value for the
      trmLgLNN tables."
::= { trmLgLNNRowStatusEntry 4 }

trmLgLNNIndex OBJECT-TYPE
   SYNTAX     Integer32 (0..2047)
   ACCESS     not-accessible
   STATUS     mandatory
   DESCRIPTION
     "This variable represents the index for the trmLgLNN tables."
::= { trmLgLNNRowStatusEntry 10 }

trmLgLNNOperTable OBJECT-TYPE
   SYNTAX     SEQUENCE OF TrmLgLNNOperEntry
   ACCESS     not-accessible
   STATUS     mandatory
   DESCRIPTION
     "*** THIS TABLE CURRENTLY NOT IMPLEMENTED ***

      Trm Lg/<neighborNodeName> LNN/<logical network number> 
      Operational
      This group of attributes is the information associated with an 
      address plan."
::= { trmLgLNN 10 }

trmLgLNNOperEntry OBJECT-TYPE
   SYNTAX     TrmLgLNNOperEntry
   ACCESS     not-accessible
   STATUS     mandatory
   DESCRIPTION
     "An entry in the trmLgLNNOperTable."
   INDEX {
      trmIndex,
      trmLgIndex,
      trmLgLNNIndex }
::= { trmLgLNNOperTable 1 }

TrmLgLNNOperEntry ::= SEQUENCE {
   trmLgLNNLinkType
      INTEGER,
   trmLgLNNAddressPlanComponentName
      RowPointer }

trmLgLNNLinkType OBJECT-TYPE
   SYNTAX     INTEGER  {
                 trunk(0),
                 internalGateway(1),
                 externalGateway(2) }
   ACCESS     read-only
   STATUS     mandatory
   DESCRIPTION
     "This attribute indicates how the LNN is transported over the link 
      group. It can be one of three types:
      trunk - the LNN is supported by Topology over a Passport to 
      Passport link
      internal gateway - the LNN is supported by an address plan (but not 
      Topology) over a Passport to Passport link
      external gateway - the LNN is supported by an address plan (but not 
      Topology) over a Passport to non-Passport link"
::= { trmLgLNNOperEntry 1 }

trmLgLNNAddressPlanComponentName OBJECT-TYPE
   SYNTAX     RowPointer 
   ACCESS     read-only
   STATUS     mandatory
   DESCRIPTION
     "This attribute indicates the component name of the address plan 
      which owns the logical network number of this component."
::= { trmLgLNNOperEntry 2 }


-- NumberingPlanIndicator / <x121,e164>
-- This component collects all DNAs for a particular numbering plan 
-- indicator e.g., X.121. 

npi OBJECT IDENTIFIER ::= { components 43 }



npiRowStatusTable OBJECT-TYPE
   SYNTAX     SEQUENCE OF NpiRowStatusEntry
   ACCESS     not-accessible
   STATUS     mandatory
   DESCRIPTION
     "This entry controls the addition and deletion of 
      npi components."
::= { npi 1 }

npiRowStatusEntry OBJECT-TYPE
   SYNTAX     NpiRowStatusEntry
   ACCESS     not-accessible
   STATUS     mandatory
   DESCRIPTION
     "A single entry in the table represents a single 
      npi component."
   INDEX {
      npiIndex }
::= { npiRowStatusTable 1 }

NpiRowStatusEntry ::= SEQUENCE {
   npiRowStatus
      RowStatus,
   npiComponentName
      DisplayString,
   npiStorageType
      StorageType,
   npiIndex
      INTEGER }

npiRowStatus OBJECT-TYPE
   SYNTAX     RowStatus 
   ACCESS     read-only
   STATUS     mandatory
   DESCRIPTION
     "This variable is used as the basis for SNMP naming of
      npi components.
      These components cannot be added nor deleted."
::= { npiRowStatusEntry 1 }

npiComponentName OBJECT-TYPE
   SYNTAX     DisplayString 
   ACCESS     read-only
   STATUS     mandatory
   DESCRIPTION
     "This variable provides the component's string name for
      use with the ASCII Console Interface"
::= { npiRowStatusEntry 2 }

npiStorageType OBJECT-TYPE
   SYNTAX     StorageType 
   ACCESS     read-only
   STATUS     mandatory
   DESCRIPTION
     "This variable represents the storage type value for the
      npi tables."
::= { npiRowStatusEntry 4 }

npiIndex OBJECT-TYPE
   SYNTAX     INTEGER  {
                 x121(0),
                 e164(1) }
   ACCESS     not-accessible
   STATUS     mandatory
   DESCRIPTION
     "This variable represents the index for the npi tables."
::= { npiRowStatusEntry 10 }

npiStatsTable OBJECT-TYPE
   SYNTAX     SEQUENCE OF NpiStatsEntry
   ACCESS     not-accessible
   STATUS     mandatory
   DESCRIPTION
     "Npi/<x121,e164> Statistics
      This group of attributes contains the statistics kept for a particular 
      numbering plan indicator. The only statistic present is the total 
      number of DNAs provisioned for the numbering plan."
::= { npi 10 }

npiStatsEntry OBJECT-TYPE
   SYNTAX     NpiStatsEntry
   ACCESS     not-accessible
   STATUS     mandatory
   DESCRIPTION
     "An entry in the npiStatsTable."
   INDEX {
      npiIndex }
::= { npiStatsTable 1 }

NpiStatsEntry ::= SEQUENCE {
   npiTotalDnas
      Unsigned32 }

npiTotalDnas OBJECT-TYPE
   SYNTAX     Unsigned32 (0..4294967295)
   ACCESS     read-only
   STATUS     mandatory
   DESCRIPTION
     "This attribute holds the total number of Dnas that are in the 
      numbering plan. If this attribute is displayed in provisioning mode, 
      the number includes the Dnas that have been added/deleted in that 
      provisioning session, otherwise the number only includes the Dnas 
      that have been activated."
   DEFVAL     { 0 }
::= { npiStatsEntry 1 }

-- 
-- *** THIS SUBTREE CURRENTLY NOT IMPLEMENTED ***
-- 

-- Npi/<x121,e164> Dna/<BCD(1..15)>
-- This component is a dynamic subcomponent of 
-- NumberingPlanIndicator. This subcomponent represents a DNA in 
-- the numbering plan. 

npiDna OBJECT IDENTIFIER ::= { npi 2 }



npiDnaRowStatusTable OBJECT-TYPE
   SYNTAX     SEQUENCE OF NpiDnaRowStatusEntry
   ACCESS     not-accessible
   STATUS     mandatory
   DESCRIPTION
     "*** THIS TABLE CURRENTLY NOT IMPLEMENTED ***

      This entry controls the addition and deletion of 
      npiDna components."
::= { npiDna 1 }

npiDnaRowStatusEntry OBJECT-TYPE
   SYNTAX     NpiDnaRowStatusEntry
   ACCESS     not-accessible
   STATUS     mandatory
   DESCRIPTION
     "A single entry in the table represents a single 
      npiDna component."
   INDEX {
      npiIndex,
      npiDnaIndex }
::= { npiDnaRowStatusTable 1 }

NpiDnaRowStatusEntry ::= SEQUENCE {
   npiDnaRowStatus
      RowStatus,
   npiDnaComponentName
      DisplayString,
   npiDnaStorageType
      StorageType,
   npiDnaIndex
      DigitString }

npiDnaRowStatus OBJECT-TYPE
   SYNTAX     RowStatus 
   ACCESS     read-only
   STATUS     mandatory
   DESCRIPTION
     "This variable is used as the basis for SNMP naming of
      npiDna components.
      These components cannot be added nor deleted."
::= { npiDnaRowStatusEntry 1 }

npiDnaComponentName OBJECT-TYPE
   SYNTAX     DisplayString 
   ACCESS     read-only
   STATUS     mandatory
   DESCRIPTION
     "This variable provides the component's string name for
      use with the ASCII Console Interface"
::= { npiDnaRowStatusEntry 2 }

npiDnaStorageType OBJECT-TYPE
   SYNTAX     StorageType 
   ACCESS     read-only
   STATUS     mandatory
   DESCRIPTION
     "This variable represents the storage type value for the
      npiDna tables."
::= { npiDnaRowStatusEntry 4 }

npiDnaIndex OBJECT-TYPE
   SYNTAX     DigitString (SIZE (1..15))
   ACCESS     not-accessible
   STATUS     mandatory
   DESCRIPTION
     "This variable represents the index for the npiDna tables."
::= { npiDnaRowStatusEntry 10 }

npiDnaInfoTable OBJECT-TYPE
   SYNTAX     SEQUENCE OF NpiDnaInfoEntry
   ACCESS     not-accessible
   STATUS     mandatory
   DESCRIPTION
     "*** THIS TABLE CURRENTLY NOT IMPLEMENTED ***

      Npi/<x121,e164> Dna/<BCD(1..15)> Information
      This group of attributes contains the attributes for a DNA in the 
      numbering plan."
::= { npiDna 10 }

npiDnaInfoEntry OBJECT-TYPE
   SYNTAX     NpiDnaInfoEntry
   ACCESS     not-accessible
   STATUS     mandatory
   DESCRIPTION
     "An entry in the npiDnaInfoTable."
   INDEX {
      npiIndex,
      npiDnaIndex }
::= { npiDnaInfoTable 1 }

NpiDnaInfoEntry ::= SEQUENCE {
   npiDnaDestinationName
      RowPointer }

npiDnaDestinationName OBJECT-TYPE
   SYNTAX     RowPointer 
   ACCESS     read-only
   STATUS     mandatory
   DESCRIPTION
     "This attribute holds the Component Name of the application to 
      which the DNA belongs."
::= { npiDnaInfoEntry 1 }




-- 
-- Version and Compliance statements
-- 



-- Object-Group Statement:
-- A list of all current accessible leaf objects.

-- OBJECTS { npiDnaStorageType,
--           rtgTopNodeLgTrkObjTrunkCost,
--           trmStorageType,
--           rtgTopNodeLgTrkObjTrunkSecurity,
--           rtgSplittingRegionIdsValue,
--           trmLkComponentName,
--           npiRowStatus,
--           trmLgStorageType,
--           rtgTopNodeLgTrkObjStorageType,
--           npiDnaRowStatus,
--           rtgTopControlPktRx,
--           rtgRowStatus,
--           rtgComponentName,
--           rtgTopNodeLgTrkObjCustomerParameter,
--           rtgTopNodeStorageType,
--           trmLgLNNComponentName,
--           trmLkLinkComponentName,
--           trmLgComponentName,
--           rtgTopNodeLgTrkObjTrunkType,
--           trmRowStatus,
--           rtgTopControlBytesTx,
--           trmLkOverflowAttempts,
--           rtgTopNodeLgLnnValue,
--           trmLgLkPathOverflowAttempts,
--           trmLkFciSet,
--           npiDnaDestinationName,
--           trmLkMaxTxUnit,
--           rtgTopNodeLgTrkObjRowStatus,
--           rtgTopNodeLgStorageType,
--           trmLgLNNLinkType,
--           trmLgLkThroughput,
--           trmLgLkStorageType,
--           npiComponentName,
--           trmLgLkMaxTxUnit,
--           trmLgRowStatus,
--           rtgTopNodeLgTrkObjMaxReservableBwOut,
--           npiTotalDnas,
--           rtgTopRowStatus,
--           rtgTandemTraffic,
--           trmLgLkRowStatus,
--           rtgTopNodeLgTrkObjUnresValue,
--           rtgTopNodeLgTrkObjComponentName,
--           trmLgLkOverflowAttempts,
--           rtgTopNodeLgTrkObjTrunkDelay,
--           rtgTopControlBytesRx,
--           trmLgLNNRowStatus,
--           trmLkStorageType,
--           rtgSplittingRegionIdsRowStatus,
--           rtgTopNodeLgRowStatus,
--           rtgTopNodeComponentName,
--           rtgTopNodeLgTrkObjSupportedTrafficTypes,
--           trmLkThroughput,
--           trmLkStatus,
--           rtgTopNodeRowStatus,
--           trmLkDiscardCongestedValue,
--           rtgTopNodeLgDelayMetric,
--           trmLgLkDiscardCongestedValue,
--           trmLgLkLinkComponentName,
--           trmLgLNNStorageType,
--           rtgTopNodeLgTputMetric,
--           rtgTopNodeLgTrkObjFarEndTrmLkInstance,
--           trmLgLkFciSet,
--           npiStorageType,
--           rtgTopNodeLgComponentName,
--           rtgTopStorageType,
--           rtgTopControlPktTx,
--           trmLgLkStatus,
--           trmLkRowStatus,
--           trmComponentName,
--           trmLgLkDelayUsec,
--           rtgStorageType,
--           trmLkDelayUsec,
--           npiDnaComponentName,
--           trmLgLNNAddressPlanComponentName,
--           rtgTopNodeNodeId,
--           trmLkPathOverflowAttempts,
--           rtgTopComponentName,
--           trmLgLkComponentName }
-- STATUS  mandatory
-- DESCRIPTION
--   "A list of all current accessible leaf objects."

baseRoutingGroup OBJECT IDENTIFIER ::= { baseRoutingMIB 1 }
baseRoutingGroupBE OBJECT IDENTIFIER ::= { baseRoutingGroup 5 }
baseRoutingGroupBE00 OBJECT IDENTIFIER ::= { baseRoutingGroupBE 1 }
baseRoutingGroupBE00A OBJECT IDENTIFIER ::= { baseRoutingGroupBE00 2 }



-- Agent-Capabilities Statement:

-- PRODUCT-RELEASE "Passport Release 7.0 BaseRouting."
-- STATUS          mandatory
-- DESCRIPTION     "BaseRouting MIB: MIB Version BE00A,
--                  Software Version BG00S4C."
-- SUPPORTS        Nortel-Magellan-Passport-BaseRoutingMIB
--    INCLUDES     { baseRoutingGroupBE00A }

baseRoutingCapabilities OBJECT IDENTIFIER ::= { baseRoutingMIB 3 }
baseRoutingCapabilitiesBE OBJECT IDENTIFIER ::= { baseRoutingCapabilities 5 }
baseRoutingCapabilitiesBE00 OBJECT IDENTIFIER ::= { baseRoutingCapabilitiesBE 1 }
baseRoutingCapabilitiesBE00A OBJECT IDENTIFIER ::= { baseRoutingCapabilitiesBE00 2 }





END
