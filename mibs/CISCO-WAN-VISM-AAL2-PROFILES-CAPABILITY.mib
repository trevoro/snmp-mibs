-- *****************************************************************
-- ciscoWanVismAal2ProfilesCapabilities MIB
--
-- AGENT-CAPABILITIES mib for CISCO-WAN-AAL2-PROFILES-MIB in the VISM product
--
-- Copyright(c) 2000 by Cisco Systems,Inc.
--
-- Author: Siana Smith
-- *****************************************************************

CISCO-WAN-VISM-AAL2-PROFILES-CAPABILITY DEFINITIONS ::= BEGIN

IMPORTS
        MODULE-IDENTITY
                FROM SNMPv2-SMI
        AGENT-CAPABILITIES
                FROM SNMPv2-CONF
        ciscoWanAgentCapability
                FROM CISCOWAN-SMI;

ciscoWanVismAal2ProfilesCapability MODULE-IDENTITY
        LAST-UPDATED    "200012180000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
                "The Agent Capabilities for CISCO-WAN-AAL2-PROFILES-MIB."

        REVISION        "200012180000Z"
        DESCRIPTION
                "Initial version of this MIB module"
        ::= { ciscoWanAgentCapability 334 }

ciscoWanVismAal2ProfilesCapabilityV2R00 AGENT-CAPABILITIES
    PRODUCT-RELEASE      "VISM Release2.1"
    STATUS               current
    DESCRIPTION          "CISCO-WAN-AAL2-PROFILES-MIB Capabilities"

    SUPPORTS CISCO-WAN-AAL2-PROFILES-MIB
    INCLUDES { aal2ProfileGroup }

        VARIATION   aal2ProfilePreference
        SYNTAX      INTEGER (0..9)
        DESCRIPTION "Valid range is 0 - 9."

    ::= { ciscoWanVismAal2ProfilesCapability 1 }

END
