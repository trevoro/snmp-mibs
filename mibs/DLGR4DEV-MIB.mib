-- ****************************************************************************
--
--              Dialogic Release 4 Device Information
--         Management Information Base for SNMP Network Management
--
--
--      Copyright 1997, Dialogic Corporation.
--      All Rights Reserved.
--
--      The information in this document is subject to change without notice.
--
--      The Dialogic Enterprise number is 3028.
--      The ASN.1 prefix to, and including the Dialogic Enterprise is:
--           1.3.6.1.4.1.3028
--
-- ****************************************************************************

DLGR4DEV-MIB DEFINITIONS ::= BEGIN

    IMPORTS
		DisplayString FROM SNMPv2-TC
        Gauge, Counter                 FROM RFC1155-SMI
        OBJECT-TYPE             FROM RFC1155-SMI
        TRAP-TYPE               FROM RFC-1215
        dlgR4Resources          FROM DLGC-GLOBAL-REG;

    dlgR4ResObj       OBJECT IDENTIFIER ::= { dlgR4Resources 1 }
    dlgR4MibRev       OBJECT IDENTIFIER ::= { dlgR4ResObj 1 }
    dlgR4DeviceInfo   OBJECT IDENTIFIER ::= { dlgR4ResObj 2 }
    dlgR4SrlInfo      OBJECT IDENTIFIER ::= { dlgR4ResObj 3 }

-- ****************************************************************************
-- Release 4 Device MIB Revision
-- =============================
--
-- The dialogic enterprise              (1.3.6.1.4.1.3028)
--      dlgResource Group               (1.3.6.1.4.1.3028.2)
--        dlgR4Resources Group          (1.3.6.1.4.1.3028.2.1)
--         dlgR4ResObj Group            (1.3.6.1.4.1.3028.2.1.1)
--           dlgR4MibRev Group          (1.3.6.1.4.1.3028.2.1.1.1)
--
--     An Agent conforming to this document will return a mibRevMajor
--     of one (1) and a mibRevMinor of zero (0).
--
--
-- ****************************************************************************

    dlgR4MibRevMajor OBJECT-TYPE
       SYNTAX  INTEGER (1..65535)
       ACCESS  read-only
       STATUS  mandatory
       DESCRIPTION
           "The Major Revision level.

            A change in the major revision level represents a major change
            in the architecture of the MIB.  A change in the major revision
            level may indicate a significant change in the information
            supported and/or the meaning of the supported information,
            correct interpretation of data may require a MIB document with
            the same major revision level."
       ::= { dlgR4MibRev 1 }

       dlgR4MibRevMinor OBJECT-TYPE
       SYNTAX  INTEGER (0..65535)
       ACCESS  read-only
       STATUS  mandatory
       DESCRIPTION
           "The Minor Revision level.

            A change in the minor revision level may represent some minor
            additional support. no changes to any pre-existing information
            has occurred."
       ::= { dlgR4MibRev 2 }


-- ****************************************************************************
--    Release 4 Device Info Tables
--    ============================
--
-- The dialogic enterprise              (1.3.6.1.4.1.3028)
--      dlgResource Group               (1.3.6.1.4.1.3028.2)
--        dlgR4Resources Group          (1.3.6.1.4.1.3028.2.1)
--         dlgR4ResObj Group            (1.3.6.1.4.1.3028.2.1.1)
--           dlgR4DeviceInfo Group      (1.3.6.1.4.1.3028.2.1.1.2)
--
--  This group consists of a series of tables as described below
--    dlgR4DeviceTable contains attributes common to all Release 4 Devices
--    dlgR4VoiceTable  contains attributes specific to Voice Channel devices
--    dlgR4DTITable    contains attributes specific to T1/E1 Timeslot devices
--    dlgR4ISDNTable   contains attributes specific to ISDN line devices
--    dlgR4MSITable    contains attributes specific to MSI station devices
--
-- Each table shares a common table index.
-- ****************************************************************************

--
-- Release 4 Common device table. Attributes common to all devices
--
    dlgR4DeviceTable OBJECT-TYPE
        SYNTAX  SEQUENCE OF DlgR4DeviceEntry
        ACCESS  not-accessible
        STATUS  mandatory
        DESCRIPTION
           "Table of Attributes common to all Release 4 style port
            level devices. This covers devices like the Voice Channel,
            DTI Timeslot, ISDN line device, MSI station set device, etc."

        ::= { dlgR4DeviceInfo 1 }

     dlgR4DeviceEntry OBJECT-TYPE
        SYNTAX  DlgR4DeviceEntry
        ACCESS  not-accessible
        STATUS  mandatory
        DESCRIPTION
           "A description of the attributes common to all Release 4 
            style port level devices. This covers devices like the 
            Voice Channel, DTI Timeslot, ISDN line device, MSI 
            station set device, etc."
        INDEX   { dlgR4DeviceIndex }

        ::= { dlgR4DeviceTable 1 }

        DlgR4DeviceEntry ::= SEQUENCE {
            dlgR4DeviceIndex          INTEGER,
            dlgR4DeviceName           DisplayString,
            dlgR4DeviceType           INTEGER,
            dlgR4DeviceHiIdentIndex   INTEGER,
            dlgR4DeviceOpenCount      Gauge,
            dlgR4DeviceXmitCTbusSlot  INTEGER,
            dlgR4DeviceRcvrCTbusSlot  INTEGER
        }


     dlgR4DeviceIndex OBJECT-TYPE
       SYNTAX INTEGER (1..2147483647)
       ACCESS read-only
       STATUS mandatory
       DESCRIPTION
           "A unique value for each Release 4 device contained by the
            host.  The value for each Release 4 device must remain
            constant at least from one re-initialization of the
            agent to the next re-initialization."

       ::= { dlgR4DeviceEntry 1 }


     dlgR4DeviceName OBJECT-TYPE
        SYNTAX  DisplayString
        ACCESS  read-only
        STATUS  mandatory
        DESCRIPTION
           "Release 4 Device Name. This is the name the application will
            use when opening the device (e.g. dxxxB1C1, dtiB1T1, msiB1C1)"

        ::= { dlgR4DeviceEntry 2 }


     dlgR4DeviceType  OBJECT-TYPE
       SYNTAX INTEGER {
                 unknown(1),
                 voice(2),
                 dti(3),
                 isdn(4),
                 msi(5)
                 }

       ACCESS read-only
       STATUS mandatory
       DESCRIPTION
           "An indication of the type of the device.

            other(1) - some other type of device unknown to the agent.

            voice(2) - A voice channel device. An entry exits in the
                       dlgR4VoiceTable for this device.

            dti(3)   - A DTI timeslot device. An entry exits in the
                       dlgR4DTITable for this device.

            isdn(4)  - An ISDN B-Channel device. An entry exits in the
                       dlgR4ISDNTable for this device.

            msi(5)   - An MSI station set device. An entry exits in the
                       dlgR4MSITable for this device.  "

       ::= { dlgR4DeviceEntry 3 }


     dlgR4DeviceHiIdentIndex OBJECT-TYPE
        SYNTAX  INTEGER
        ACCESS  read-only
        STATUS  mandatory
        DESCRIPTION
           "Index into the Hardware information table for the
            board to which the Release 4 device is bound to.

            This can be used to determine the relationship between
            a release 4 device and the hardware platform on which
            the corresponding firmware implementing the resource is
            resident.

            For example, if this value is a 1, then performing a get of
            the table entry dlgHiIdentTable columnar objects with index
            1 will retrieve the physical hardware identification 
            information"

        ::= { dlgR4DeviceEntry 4 }


     dlgR4DeviceOpenCount OBJECT-TYPE
        SYNTAX  Gauge
        ACCESS  read-only
        STATUS  mandatory
        DESCRIPTION
           "An indication of how many instances of this device is
            currently opened"

        ::= { dlgR4DeviceEntry 5 }


     dlgR4DeviceXmitCTbusSlot OBJECT-TYPE
        SYNTAX  INTEGER
        ACCESS  read-only
        STATUS  mandatory
        DESCRIPTION
           "An indication of which timeslot on the CTbus this
            device is currently transmitting on."

        ::= { dlgR4DeviceEntry 6 }


     dlgR4DeviceRcvrCTbusSlot OBJECT-TYPE
        SYNTAX  INTEGER
        ACCESS  read-only
        STATUS  mandatory
        DESCRIPTION
           "An indication of which timeslot on the CTbus this
            device is currently receiving from (listening to).

            A value of -1 indicates this information is not available"

        ::= { dlgR4DeviceEntry 7 }



--
-- Release 4 Voice device table. Attributes common to all devices
--
    dlgR4VoiceTable OBJECT-TYPE
        SYNTAX  SEQUENCE OF DlgR4VoiceEntry
        ACCESS  not-accessible
        STATUS  mandatory
        DESCRIPTION
           "Table of Attributes for Release 4 voice channel devices. This
            tables 'augments' the R4DeviceTable by sharing a common index"

        ::= { dlgR4DeviceInfo 2 }

     dlgR4VoiceEntry OBJECT-TYPE
        SYNTAX  DlgR4VoiceEntry
        ACCESS  not-accessible
        STATUS  mandatory
        DESCRIPTION
           "A description of the attributes for Release 4 voice channel 
            devices."
        INDEX   { dlgR4VoiceChannelIndex }

        ::= { dlgR4VoiceTable 1 }

        DlgR4VoiceEntry ::= SEQUENCE {
            dlgR4VoiceChannelIndex    INTEGER,
            dlgR4VoiceChannelStatus   INTEGER,
            dlgR4VoiceLineStatus      INTEGER,
            dlgR4VoiceNumberOfDigits  Gauge,
            dlgR4VoiceE2PROMFeatures  INTEGER
        }

     dlgR4VoiceChannelIndex OBJECT-TYPE
       SYNTAX INTEGER (1..2147483647)
       ACCESS read-only
       STATUS mandatory
       DESCRIPTION
           "A unique value for each Release 4 voice device contained by the
            host.  This is the same as dlgR4DeviceIndex in the device
            table"

       ::= { dlgR4VoiceEntry 1 }

     dlgR4VoiceChannelStatus OBJECT-TYPE
        SYNTAX  INTEGER {
                  idle(1),
                  playing(2),
                  recording(3),
                  dialing(4),
                  gettingDigits(5),
                  playTone(6),
                  sendingFax(8),
                  receivingFax(9),
                  betweenFAXPages(10),
                  hookState(11),
                  winking(12),
                  callProgess(13),
                  gettingR2MF(14),
                  blocked(16)
             }
        ACCESS  read-only
        STATUS  mandatory
        DESCRIPTION
           "Indicates current activity status on the channel:

              idle(1)          - Channel not active
              playing(2)       - Playing Audio Data   
              recording(3)     - Recording Audio Data
              dialing(4)       - Dialing Digits
              gettingDigits(5) - Collecting DTMF digits
              playTone(6)      - Playing a tone
              sendingFax(8)    - Sending a FAX (VFX boards)
              receivingFax(9)  - Receiving a FAX (VFX boards)
              betweenFAXPages(10) - Between FAX pages (VFX boards)
              hookState(11)    - Changing hook status to onhook or offhook
              winking(12)      - Performing a wink
              callProgess(13)  - Performing Call progress analysis
              gettingR2MF(14)  - retrieving R2MF digits
              blocked(16)      - Blocked"

        ::= { dlgR4VoiceEntry 2 }

     dlgR4VoiceLineStatus OBJECT-TYPE
        SYNTAX  INTEGER {
                  unknown(0),    -- this is the value if no frontend
                  onhook(1),     -- channel is onhook
                  offhook(2),    -- channel is offhook
                  lcDetected(3)  -- channel is offhook and loop currrent detected
                }
        ACCESS  read-write
        STATUS  mandatory
        DESCRIPTION
           "Indicates current line status of the channel

            unknown(0)   - indicates no analog frontend or status unknown
            onhook(1)    - indicates channel is onhook. 
                           Setting the variable to this value will initiate 
                           putting the channel onhook
            offhook(2)   - indicates channel is offhook.
                           Setting the variable to this value initiates 
                           setting the channel offhook.
            lcDetected(3)- indicates loop current detected and the channel
                           is offhook."

        ::= { dlgR4VoiceEntry 3 }


     dlgR4VoiceNumberOfDigits OBJECT-TYPE
        SYNTAX  INTEGER
        ACCESS  read-only
        STATUS  mandatory
        DESCRIPTION
           "Indicates number of uncollected digits in this channel's
            digit queue."

        ::= { dlgR4VoiceEntry 4 }


     dlgR4VoiceE2PROMFeatures OBJECT-TYPE
        SYNTAX  INTEGER
        ACCESS  read-only
        STATUS  mandatory
        DESCRIPTION
           "Indicates some static features for this channel enabled
            in the E2PROM.

            This value is actually a bit mask as follows where a
            value of 1 indicates the feature is present:
              0x0001  - Not used
              0x0002  - Call Progress
              0x0004  - MF Digit Detection/Generation
              0x0008  - Not used
              0x0010  - Not used
              0x0020  - Dial Pulse Digit Detection
              0x0040  - reserved bit
              0x0080  - Echo Cancellation Resource
           "

        ::= { dlgR4VoiceEntry 5 }


--
-- Release 4 DTI device table. Attributes common to all devices
--
    dlgR4DTITable OBJECT-TYPE
        SYNTAX  SEQUENCE OF DlgR4DTIEntry
        ACCESS  not-accessible
        STATUS  mandatory
        DESCRIPTION
           "Table of Attributes for Release 4 DTI timeslot devices. This
            tables 'augments' the R4DeviceTable by sharing a common index"

        ::= { dlgR4DeviceInfo 3 }

     dlgR4DTIEntry OBJECT-TYPE
        SYNTAX  DlgR4DTIEntry
        ACCESS  not-accessible
        STATUS  mandatory
        DESCRIPTION
           "A description of the attributes for Release 4 DTI timeslot devices."
        INDEX   { d }
        ::= { dlgR4DTITable 1 }

        DlgR4DTIEntry ::= SEQUENCE {
            dlgR4DTITimeslotIndex     INTEGER,
            dlgR4DTIProtocol          DisplayString,
            dlgR4DTITimeslotStatus    INTEGER,
            dlgR4DTIRcvSigBits        INTEGER,
            dlgR4DTIXmitSigBits       INTEGER
        }

     dlgR4DTITimeslotIndex OBJECT-TYPE
       SYNTAX INTEGER (1..2147483647)
       ACCESS read-only
       STATUS mandatory
       DESCRIPTION
           "A unique value for each Release 4 DTI device contained by the
            host.  This is the same as dlgR4DeviceIndex in the device
            table"

       ::= { dlgR4DTIEntry 1 }

     dlgR4DTIProtocol OBJECT-TYPE
        SYNTAX  DisplayString
        ACCESS  read-only
        STATUS  mandatory
        DESCRIPTION
           "Indicates active protocol on this timeslot

            T-1 - indicates T1 protocol
            E-1 - indicates E1 protocol"

        ::= { dlgR4DTIEntry 2 }


     dlgR4DTITimeslotStatus OBJECT-TYPE
        SYNTAX  INTEGER {
                  idle(0),
                  dialing(1),
                  winking(2),
                  waitingForCall(3)
             }
        ACCESS  read-only
        STATUS  mandatory
        DESCRIPTION
           "Indicates current activity status on the timeslot

              idle(0)           - no DTI multitasking function active
              dialing(1)        - Dialing digits using dt_dial() function.
              winking(2)        - performing a wink using dt_xmitwink() function.
              waitingForCall(3) - waiting for a call using dt_mtfcn(..,DEMT_WTCALL ..)"

        ::= { dlgR4DTIEntry 3 }

     dlgR4DTIRcvSigBits OBJECT-TYPE
        SYNTAX  INTEGER
        ACCESS  read-only
        STATUS  mandatory
        DESCRIPTION
           "Indicates current state of the Receive signaling bits

            Bit 0 (0x01) - A Receive signaling bit
            Bit 1 (0x02) - B Receive signaling bit
            Bit 2 (0x04) - C Receive signaling bit
            Bit 3 (0x08) - D Receive signaling bit "

        ::= { dlgR4DTIEntry 4 }


     dlgR4DTIXmitSigBits OBJECT-TYPE
        SYNTAX  INTEGER
        ACCESS  read-write
        STATUS  mandatory
        DESCRIPTION
           "Indicates current state of the Transmit signaling bits

            Bit 0 (0x01) - A Transmit signaling bit
            Bit 1 (0x02) - B Transmit signaling bit
            Bit 2 (0x04) - C Transmit signaling bit
            Bit 3 (0x08) - D Transmit signaling bit 

            This variable may also be written to using the following bit mask
            values (multiple values may be OR'ed together). In order to leave
            a bit unaffected don't specify either the ON or OFF value

            0x10 - Turn A Transmit signaling bit off
            0x11 - turn A Transmit signaling bit on
            0x20 - Turn B Transmit signaling bit off
            0x22 - turn B Transmit signaling bit on
            0x40 - Turn C Transmit signaling bit off
            0x44 - turn C Transmit signaling bit on
            0x80 - Turn D Transmit signaling bit off
            0x88 - turn D Transmit signaling bit on 

            As an example to turn the A bit off and the B bit on at the same time 
            'OR' 0x10 with 0x22 to get 0x32. This will turn A off and B on"

        ::= { dlgR4DTIEntry 5 }



--
-- Release 4 ISDN device table. Attributes common to all devices
--
    dlgR4ISDNTable OBJECT-TYPE
        SYNTAX  SEQUENCE OF DlgR4ISDNEntry
        ACCESS  not-accessible
        STATUS  mandatory
        DESCRIPTION
           "Table of Attributes for Release 4 ISDN B-channel devices. This
            tables 'augments' the R4DeviceTable by sharing a common index"

        ::= { dlgR4DeviceInfo 4 }

     dlgR4ISDNEntry OBJECT-TYPE
        SYNTAX  DlgR4ISDNEntry
        ACCESS  not-accessible
        STATUS  mandatory
        DESCRIPTION
           "A description of the attributes for Release 4 ISDN B-channel devices"
        INDEX   { dlgR4ISDNBChannelIndex }
        ::= { dlgR4ISDNTable 1 }

        DlgR4ISDNEntry ::= SEQUENCE {
            dlgR4ISDNBChannelIndex     INTEGER,
            dlgR4ISDNProtocol          DisplayString,
            dlgR4ISDNBChannelStatus    INTEGER
        }

     dlgR4ISDNBChannelIndex OBJECT-TYPE
       SYNTAX INTEGER (1..2147483647)
       ACCESS read-only
       STATUS mandatory
       DESCRIPTION
           "A unique value for each Release 4 ISDN device contained by the
            host.  This is the same as dlgR4DeviceIndex in the device
            table"

       ::= { dlgR4ISDNEntry 1 }

     dlgR4ISDNProtocol OBJECT-TYPE
        SYNTAX  DisplayString
        ACCESS  read-write
        STATUS  mandatory
        DESCRIPTION
           "Indicates active protocol on this timeslot"

        ::= { dlgR4ISDNEntry 2 }


     dlgR4ISDNBChannelStatus OBJECT-TYPE
        SYNTAX  INTEGER {
                  inService(0),
                  maintenance(1),
                  outOfService(2)
             }
        ACCESS  read-write
        STATUS  mandatory
        DESCRIPTION
           "Indicates current B Channel status:

            inService(0)       - B Channel is in service
            maintenance(1)     - B Channel is in maintenance mode
            outOfService(2)    - B Channel is out of service

            This variable may also be written to. Writing to this variable will fail
            if the board is not connected to the Central Office."

        ::= { dlgR4ISDNEntry 3 }


--
-- Release 4 MSI Station set device table.
--
    dlgR4MSITable OBJECT-TYPE
        SYNTAX  SEQUENCE OF DlgR4MSIEntry
        ACCESS  not-accessible
        STATUS  mandatory
        DESCRIPTION
           "Table of Attributes for Release 4 MSI Station devices. This
            tables 'augments' the R4DeviceTable by sharing a common index"

        ::= { dlgR4DeviceInfo 5 }

     dlgR4MSIEntry OBJECT-TYPE
        SYNTAX  DlgR4MSIEntry
        ACCESS  not-accessible
        STATUS  mandatory
        DESCRIPTION
           "A description of the attributes for Release 4 MSI Station devices."
        INDEX   { dlgR4MSIStationIndex }
        ::= { dlgR4MSITable 1 }

        DlgR4MSIEntry ::= SEQUENCE {
            dlgR4MSIStationIndex         INTEGER,
            dlgR4MSIStationLineStatus    INTEGER
        }

     dlgR4MSIStationIndex OBJECT-TYPE
       SYNTAX INTEGER (1..2147483647)
       ACCESS read-only
       STATUS mandatory
       DESCRIPTION
           "A unique value for each Release 4 MSI device contained by the
            host.  This is the same as dlgR4DeviceIndex in the device
            table"

       ::= { dlgR4MSIEntry 1 }

     dlgR4MSIStationLineStatus OBJECT-TYPE
        SYNTAX  INTEGER {
                 onhook(0),
                 offhook(16)
             }
        ACCESS  read-only
        STATUS  mandatory
        DESCRIPTION
           "Indicates current MSI Station line status

            onhook(0)    - Station is onhook (agent not connected)
            offhook(16)  - Station if offhook (agent connected)"

        ::= { dlgR4MSIEntry 2 }


-- ****************************************************************************
--    Release 4 Srl Info Table
--    =========================
--
-- The dialogic enterprise              (1.3.6.1.4.1.3028)
--      dlgResource Group               (1.3.6.1.4.1.3028.2)
--        dlgR4Resources Group          (1.3.6.1.4.1.3028.2.1)
--         dlgR4ResObj Group            (1.3.6.1.4.1.3028.2.1.1)
--           dlgR4SrlInfo Group         (1.3.6.1.4.1.3028.2.1.1.3)
--             dlgR4SrlTable            (1.3.6.1.4.1.3028.2.1.1.3.1)
--
--  This table contains Information about the SRL library for each
--  process which has enabled statistics collection.
-- ****************************************************************************
    dlgR4SrlTable OBJECT-TYPE
        SYNTAX  SEQUENCE OF DlgR4SrlEntry
        ACCESS  not-accessible
        STATUS  mandatory
        DESCRIPTION
           "A Table of attributes related to the Dialogic Standard Runtime Eventing
            library. This is the library used by many Dialogic based CT applications
            providing an interface for collecting events from the various CT 
            technologies. Each active process which has the SRL loaded and which have
            enabled SRL statistics monitoring will have an entry in this table"
        ::= { dlgR4SrlInfo 1 }

     dlgR4SrlEntry OBJECT-TYPE
        SYNTAX  DlgR4SrlEntry
        ACCESS  not-accessible
        STATUS  mandatory
        DESCRIPTION
           "A description of the attributes related to the Dialogic Standard 
            Runtime Eventing library."
        INDEX   { dlgR4SrlIndex }
        ::= { dlgR4SrlTable 1 }

        DlgR4SrlEntry ::= SEQUENCE {
            dlgR4SrlIndex               INTEGER,
            dlgR4SrlApplicationName     DisplayString,
            dlgR4SrlNumberOfOpens       Counter,
            dlgR4SrlNumberOfCloses      Counter,
            dlgR4SrlEventQSize          INTEGER,
            dlgR4SrlCurrentEventsOnQ    Gauge,
            dlgR4SrlMaxEventsOnQ        Gauge,
            dlgR4SrlTotalQueuedEvents   Counter,
            dlgR4SrlNumberOfHandlers    Gauge
         }

     dlgR4SrlIndex OBJECT-TYPE
        SYNTAX  INTEGER
        ACCESS  read-only
        STATUS  mandatory
        DESCRIPTION
           "Index into the table. Each process with a copy of the SRL
            DLL loaded will get a unique index"

        ::= { dlgR4SrlEntry 1 }

     dlgR4SrlApplicationName OBJECT-TYPE
        SYNTAX  DisplayString
        ACCESS  read-only
        STATUS  mandatory
        DESCRIPTION
           "Application or Process Name which the SRL DLL is attached"

        ::= { dlgR4SrlEntry 2 }

     dlgR4SrlNumberOfOpens OBJECT-TYPE
        SYNTAX  Counter
        ACCESS  read-only
        STATUS  mandatory
        DESCRIPTION
           "Total Number of times any Dialogic Release 4 device
            was opened by the application using the SRL.

            To calculate the number of currently opened devices
            subtract the dlgR4SrlNumberOfCloses value from this
            value. "

        ::= { dlgR4SrlEntry 3 }

     dlgR4SrlNumberOfCloses OBJECT-TYPE
        SYNTAX  Counter
        ACCESS  read-only
        STATUS  mandatory
        DESCRIPTION
           "Total Number of times any Dialogic Release 4 device
            was closed.

            To calculate the number of currently opened devices
            subtract this value from the dlgR4SrlNumberOfOpens
            value"

        ::= { dlgR4SrlEntry 4 }

     dlgR4SrlEventQSize OBJECT-TYPE
        SYNTAX  INTEGER
        ACCESS  read-only
        STATUS  mandatory
        DESCRIPTION
           "This is the current size of the Dialogic SRL event
            Queue"

        ::= { dlgR4SrlEntry 5 }

     dlgR4SrlCurrentEventsOnQ OBJECT-TYPE
        SYNTAX  Gauge
        ACCESS  read-only
        STATUS  mandatory
        DESCRIPTION
           "This is the number of events that are currently on the
            Queue.

            If this value keeps growing it indicates that the
            application is not properly removing events from the
            Queue. This may occur in applications written using the
            Synchronous multithreaded programming model"

        ::= { dlgR4SrlEntry 6 }

     dlgR4SrlMaxEventsOnQ OBJECT-TYPE
        SYNTAX  Gauge
        ACCESS  read-only
        STATUS  mandatory
        DESCRIPTION
           "This is the maximum number of events that was ever
	         on the queue at a particular instance while the application using the
	 	   SRL is running."

        ::= { dlgR4SrlEntry 7 }

     dlgR4SrlTotalQueuedEvents OBJECT-TYPE
        SYNTAX  Counter
        ACCESS  read-only
        STATUS  mandatory
        DESCRIPTION
           "This indicates the total number of events queued since
            the agents started gathering statistics for this
            application"

        ::= { dlgR4SrlEntry 8 }

     dlgR4SrlNumberOfHandlers OBJECT-TYPE
        SYNTAX  Gauge
        ACCESS  read-only
        STATUS  mandatory
        DESCRIPTION
           "This indicates the number of SRL callback event handlers that are
            currently enabled"

        ::= { dlgR4SrlEntry 9 }


END
