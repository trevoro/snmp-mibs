-- (C)  COPYRIGHT HEWLETT-PACKARD COMPANY 1997.
--
-- LaserJet 5Si Mopier Printer Model Specific MIB.
--
-- Generated on August 4, 1997.
--
-- Company names and product names mentioned herein may be
-- trademarks, and/or registered trademarks of their respective
-- companies.
--
-- For interal and external use.
--
-- This MIB describes all the printer model specific
-- objects suppported by the LaserJet 5Si Mopier printer
-- when networked connected using a JetDirect print
-- server.
--
-- The following MIB also contain objects supported
-- by a JetDirect connected LaserJet 5Si Mopier printer:
--
-- rfc 1213 MIB II
--
-- This MIB complies with the following RFCs:
--
-- rfc 1157 Simple Network Management Protocol
-- rfc 1155 Structure of Management Information
--
-- Notes:
--
-- 1) At the time this MIB was published, a
--    defect existed where the printer would not correctly
--    handle an SNMP get next request.  The printer
--    behavior is correct for tabular objects, but not
--    scalar objects.  For example, energy-star, sleep-mode,
--    and on-off-line are all scalars with OIDS:
--
--    energy-star { dm 1 1 1 1 }
--    sleep-mode  { dm 1 1 1 2 }
--    on-off-line { dm 1 2 2 5 }
--
--    These three objects are the first three objects supported
--    under the dm tree.
--
--    The printer operation (using OpenView tools as an
--    example) is:
--
--      snmpnext hpb18207 .1.3.6.1.4.1.11.2.3.9.4.2.1.1.1.2.0
--
--    with a reply of:
--
--      hp.nm.hpsystem.net-peripheral.netdm.dm.device.system.status-system.
--      on-off-line.0 : INTEGER: eOnline
--
--    which the printer handles correctly.
--
--    However, if the zero is left off the end, then the printer operation
--    is:
--
--      snmpnext hpb18207 .1.3.6.1.4.1.11.2.3.9.4.2.1.1.1.2
--
--    with a reply of:
--
--      hp.nm.hpsystem.net-peripheral.netdm.dm.device.system.status-system.
--      on-off-line.0 : INTEGER: eOnline
--
--    which is incorrect.  The object that should have been returned is
--    the energy-star object, not the on-off-line object.
--
--    Since the OpenView MIB Browser uses the get next command in an
--    attempt to retrieve all the supported objects under the specified OID
--                                                  =======================
--    (object identifier) and the printer returns an object that is not under
--    the specified OID, the MIB Browser assumes there are no objects
--    supported under the specified OID and reports "no value (s) returned for
--    query".
--
--    If you use an SNMP tool other than OpenView MIB Browser to do a get,
--    the printer properly responds.
--
--    Retrieving tables using the OpenView MIB Browser works fine.  Only
--    retrieving scalar objects fails.
--
-- 2) Proprietary objects containing a string which are defined in this MIB use the
--    first two bytes to hold the symbol set used to encode the string.
--    The Roman-8 symbol set has a hex encoding of 0x0115.  Other
--    symbol sets are listed in the PCL 5 Comparison Guide in table
--    C-1 Symbol Set Values.  Standard Printer MIB (prt...objects) and Host 
--    Resources MIB (hr...objects) strings do not contain symbol set 
--    information.
--
-- 3) Some of the objects included are only supported if an accessory
--    is installed.  These accessories include:
--      MIO/EIO based accessories
--      SIMM/DIMM based accessories
--      Mass storage devices 
--      Paper handling accessories
--      Adobe PostScript accessory
--

LaserJet5Si-Mopier-MIB DEFINITIONS ::= BEGIN

IMPORTS OBJECT-TYPE, enterprises FROM RFC1155-SMI;

hp OBJECT IDENTIFIER ::= { enterprises 11 }
nm OBJECT IDENTIFIER ::= { hp 2 }
hpsystem OBJECT IDENTIFIER ::= { nm 3 }
net-peripheral OBJECT IDENTIFIER ::= { hpsystem 9 }
netdm OBJECT IDENTIFIER ::= { net-peripheral 4 }
dm OBJECT IDENTIFIER ::= {  netdm 2}

DisplayString ::= OCTET STRING

device                                 OBJECT IDENTIFIER ::=  { dm 1 } 
system                                 OBJECT IDENTIFIER ::=  { device 1 } 
settings-system                        OBJECT IDENTIFIER ::=  { system 1 } 
status-system                          OBJECT IDENTIFIER ::=  { system 2 } 
background-message                     OBJECT IDENTIFIER ::=  { status-system 37 } 
background-message1                    OBJECT IDENTIFIER ::=  { background-message 1 } 
background-message2                    OBJECT IDENTIFIER ::=  { background-message 2 } 
id                                     OBJECT IDENTIFIER ::=  { system 3 } 
interface                              OBJECT IDENTIFIER ::=  { system 4 } 
simm                                   OBJECT IDENTIFIER ::=  { interface 1 } 
simm1                                  OBJECT IDENTIFIER ::=  { simm 1 } 
simm2                                  OBJECT IDENTIFIER ::=  { simm 2 } 
simm3                                  OBJECT IDENTIFIER ::=  { simm 3 } 
simm4                                  OBJECT IDENTIFIER ::=  { simm 4 } 
mio                                    OBJECT IDENTIFIER ::=  { interface 3 } 
mio1                                   OBJECT IDENTIFIER ::=  { mio 1 } 
mio2                                   OBJECT IDENTIFIER ::=  { mio 2 } 
phd                                    OBJECT IDENTIFIER ::=  { interface 5 } 
phd1                                   OBJECT IDENTIFIER ::=  { phd 1 } 
phd2                                   OBJECT IDENTIFIER ::=  { phd 2 } 
phd3                                   OBJECT IDENTIFIER ::=  { phd 3 } 
phd4                                   OBJECT IDENTIFIER ::=  { phd 4 } 
phd5                                   OBJECT IDENTIFIER ::=  { phd 5 } 
phd6                                   OBJECT IDENTIFIER ::=  { phd 6 } 
test                                   OBJECT IDENTIFIER ::=  { system 5 } 
job                                    OBJECT IDENTIFIER ::=  { system 6 } 
settings-job                           OBJECT IDENTIFIER ::=  { job 1 } 
active-print-jobs                      OBJECT IDENTIFIER ::=  { job 2 } 
job-being-parsed                       OBJECT IDENTIFIER ::=  { active-print-jobs 1 } 
job-info                               OBJECT IDENTIFIER ::=  { job 5 } 
job-info-attribute                     OBJECT IDENTIFIER ::=  { job-info 23 } 
errorlog                               OBJECT IDENTIFIER ::=  { system 11 } 
error1                                 OBJECT IDENTIFIER ::=  { errorlog 1 } 
error2                                 OBJECT IDENTIFIER ::=  { errorlog 2 } 
error3                                 OBJECT IDENTIFIER ::=  { errorlog 3 } 
error4                                 OBJECT IDENTIFIER ::=  { errorlog 4 } 
error5                                 OBJECT IDENTIFIER ::=  { errorlog 5 } 
error6                                 OBJECT IDENTIFIER ::=  { errorlog 6 } 
error7                                 OBJECT IDENTIFIER ::=  { errorlog 7 } 
error8                                 OBJECT IDENTIFIER ::=  { errorlog 8 } 
error9                                 OBJECT IDENTIFIER ::=  { errorlog 9 } 
error10                                OBJECT IDENTIFIER ::=  { errorlog 10 } 
error11                                OBJECT IDENTIFIER ::=  { errorlog 11 } 
error12                                OBJECT IDENTIFIER ::=  { errorlog 12 } 
error13                                OBJECT IDENTIFIER ::=  { errorlog 13 } 
error14                                OBJECT IDENTIFIER ::=  { errorlog 14 } 
error15                                OBJECT IDENTIFIER ::=  { errorlog 15 } 
error16                                OBJECT IDENTIFIER ::=  { errorlog 16 } 
error17                                OBJECT IDENTIFIER ::=  { errorlog 17 } 
error18                                OBJECT IDENTIFIER ::=  { errorlog 18 } 
error19                                OBJECT IDENTIFIER ::=  { errorlog 19 } 
error20                                OBJECT IDENTIFIER ::=  { errorlog 20 } 
error21                                OBJECT IDENTIFIER ::=  { errorlog 21 } 
error22                                OBJECT IDENTIFIER ::=  { errorlog 22 } 
error23                                OBJECT IDENTIFIER ::=  { errorlog 23 } 
error24                                OBJECT IDENTIFIER ::=  { errorlog 24 } 
error25                                OBJECT IDENTIFIER ::=  { errorlog 25 } 
error26                                OBJECT IDENTIFIER ::=  { errorlog 26 } 
error27                                OBJECT IDENTIFIER ::=  { errorlog 27 } 
error28                                OBJECT IDENTIFIER ::=  { errorlog 28 } 
error29                                OBJECT IDENTIFIER ::=  { errorlog 29 } 
error30                                OBJECT IDENTIFIER ::=  { errorlog 30 } 
error31                                OBJECT IDENTIFIER ::=  { errorlog 31 } 
error32                                OBJECT IDENTIFIER ::=  { errorlog 32 } 
error33                                OBJECT IDENTIFIER ::=  { errorlog 33 } 
error34                                OBJECT IDENTIFIER ::=  { errorlog 34 } 
error35                                OBJECT IDENTIFIER ::=  { errorlog 35 } 
error36                                OBJECT IDENTIFIER ::=  { errorlog 36 } 
error37                                OBJECT IDENTIFIER ::=  { errorlog 37 } 
error38                                OBJECT IDENTIFIER ::=  { errorlog 38 } 
error39                                OBJECT IDENTIFIER ::=  { errorlog 39 } 
error40                                OBJECT IDENTIFIER ::=  { errorlog 40 } 
error41                                OBJECT IDENTIFIER ::=  { errorlog 41 } 
error42                                OBJECT IDENTIFIER ::=  { errorlog 42 } 
error43                                OBJECT IDENTIFIER ::=  { errorlog 43 } 
error44                                OBJECT IDENTIFIER ::=  { errorlog 44 } 
error45                                OBJECT IDENTIFIER ::=  { errorlog 45 } 
error46                                OBJECT IDENTIFIER ::=  { errorlog 46 } 
error47                                OBJECT IDENTIFIER ::=  { errorlog 47 } 
error48                                OBJECT IDENTIFIER ::=  { errorlog 48 } 
error49                                OBJECT IDENTIFIER ::=  { errorlog 49 } 
error50                                OBJECT IDENTIFIER ::=  { errorlog 50 } 
source-subsystem                       OBJECT IDENTIFIER ::=  { device 2 } 
io                                     OBJECT IDENTIFIER ::=  { source-subsystem 1 } 
settings-io                            OBJECT IDENTIFIER ::=  { io 1 } 
ports                                  OBJECT IDENTIFIER ::=  { io 3 } 
port1                                  OBJECT IDENTIFIER ::=  { ports 1 } 
processing-subsystem                   OBJECT IDENTIFIER ::=  { device 3 } 
pdl                                    OBJECT IDENTIFIER ::=  { processing-subsystem 3 } 
settings-pdl                           OBJECT IDENTIFIER ::=  { pdl 1 } 
status-pdl                             OBJECT IDENTIFIER ::=  { pdl 2 } 
pdl-pcl                                OBJECT IDENTIFIER ::=  { pdl 3 } 
pdl-postscript                         OBJECT IDENTIFIER ::=  { pdl 4 } 
pjl                                    OBJECT IDENTIFIER ::=  { processing-subsystem 5 } 
destination-subsystem                  OBJECT IDENTIFIER ::=  { device 4 } 
print-engine                           OBJECT IDENTIFIER ::=  { destination-subsystem 1 } 
settings-prt-eng                       OBJECT IDENTIFIER ::=  { print-engine 1 } 
status-prt-eng                         OBJECT IDENTIFIER ::=  { print-engine 2 } 
intray                                 OBJECT IDENTIFIER ::=  { print-engine 3 } 
settings-intray                        OBJECT IDENTIFIER ::=  { intray 1 } 
intrays                                OBJECT IDENTIFIER ::=  { intray 3 } 
intray4                                OBJECT IDENTIFIER ::=  { intrays 4 } 
intray5                                OBJECT IDENTIFIER ::=  { intrays 5 } 
outbin                                 OBJECT IDENTIFIER ::=  { print-engine 4 } 
settings-outbin                        OBJECT IDENTIFIER ::=  { outbin 1 } 
outbins                                OBJECT IDENTIFIER ::=  { outbin 3 } 
outbin1                                OBJECT IDENTIFIER ::=  { outbins 1 } 
outbin3                                OBJECT IDENTIFIER ::=  { outbins 3 } 
outbin4                                OBJECT IDENTIFIER ::=  { outbins 4 } 
outbin5                                OBJECT IDENTIFIER ::=  { outbins 5 } 
outbin6                                OBJECT IDENTIFIER ::=  { outbins 6 } 
outbin7                                OBJECT IDENTIFIER ::=  { outbins 7 } 
outbin8                                OBJECT IDENTIFIER ::=  { outbins 8 } 
outbin9                                OBJECT IDENTIFIER ::=  { outbins 9 } 
outbin10                               OBJECT IDENTIFIER ::=  { outbins 10 }
outbin11                               OBJECT IDENTIFIER ::=  { outbins 11 }
marking-agent                          OBJECT IDENTIFIER ::=  { print-engine 5 } 
settings-marking-agent                 OBJECT IDENTIFIER ::=  { marking-agent 1 } 
imaging                                OBJECT IDENTIFIER ::=  { print-engine 6 } 
ph                                     OBJECT IDENTIFIER ::=  { print-engine 7 } 
ph-devices                             OBJECT IDENTIFIER ::=  { ph 3 } 
ph2                                    OBJECT IDENTIFIER ::=  { ph-devices 2 } 
ph3                                    OBJECT IDENTIFIER ::=  { ph-devices 3 } 
ph4                                    OBJECT IDENTIFIER ::=  { ph-devices 4 } 
print-media                            OBJECT IDENTIFIER ::=  { print-engine 8 } 
settings-print-media                   OBJECT IDENTIFIER ::=  { print-media 1 } 
media-info                             OBJECT IDENTIFIER ::=  { print-media 3 } 
media1                                 OBJECT IDENTIFIER ::=  { media-info 1 } 
media2                                 OBJECT IDENTIFIER ::=  { media-info 2 } 
media3                                 OBJECT IDENTIFIER ::=  { media-info 3 } 
media4                                 OBJECT IDENTIFIER ::=  { media-info 4 } 
media5                                 OBJECT IDENTIFIER ::=  { media-info 5 } 
media6                                 OBJECT IDENTIFIER ::=  { media-info 6 } 
media7                                 OBJECT IDENTIFIER ::=  { media-info 7 } 
media8                                 OBJECT IDENTIFIER ::=  { media-info 8 } 
media9                                 OBJECT IDENTIFIER ::=  { media-info 9 } 
media10                                OBJECT IDENTIFIER ::=  { media-info 10 } 
media11                                OBJECT IDENTIFIER ::=  { media-info 11 } 
media12                                OBJECT IDENTIFIER ::=  { media-info 12 } 
media13                                OBJECT IDENTIFIER ::=  { media-info 13 } 
media14                                OBJECT IDENTIFIER ::=  { media-info 14 } 
media15                                OBJECT IDENTIFIER ::=  { media-info 15 } 
tables                                 OBJECT IDENTIFIER ::=  { device 7 } 
channel-table                          OBJECT IDENTIFIER ::=  { tables 2 } 
channel-entry                          OBJECT IDENTIFIER ::=  { channel-table 1 } 
file-system                            OBJECT IDENTIFIER ::=  { system 10 } 
settings-file-system                   OBJECT IDENTIFIER ::=  { file-system 1 } 
status-file-system                     OBJECT IDENTIFIER ::=  { file-system 2 } 
file-systems                           OBJECT IDENTIFIER ::=  { file-system 3 } 
file-system2                           OBJECT IDENTIFIER ::=  { file-systems 2 } 
resource-manager                       OBJECT IDENTIFIER ::=  { system 12 } 
mass-storage-resources                 OBJECT IDENTIFIER ::=  { resource-manager 3 } 
remote-procedure-call                  OBJECT IDENTIFIER ::=  { system 13 } 
settings-rpc                           OBJECT IDENTIFIER ::=  { remote-procedure-call 1 } 
status-rpc                             OBJECT IDENTIFIER ::=  { remote-procedure-call 2 } 
rpc-services                           OBJECT IDENTIFIER ::=  { remote-procedure-call 3 } 
mount                                  OBJECT IDENTIFIER ::=  { rpc-services 1 } 
settings-mount                         OBJECT IDENTIFIER ::=  { mount 1 } 
nfs-server                             OBJECT IDENTIFIER ::=  { rpc-services 2 } 
settings-nfs-server                    OBJECT IDENTIFIER ::=  { nfs-server 1 } 
status-nfs-server                      OBJECT IDENTIFIER ::=  { nfs-server 2 } 
rpc-bind                               OBJECT IDENTIFIER ::=  { rpc-services 3 } 
settings-rpc-bind                      OBJECT IDENTIFIER ::=  { rpc-bind 1 } 
status-rpc-bind                        OBJECT IDENTIFIER ::=  { rpc-bind 2 } 
xport-interface                        OBJECT IDENTIFIER ::=  { system 14 } 
status-xip                             OBJECT IDENTIFIER ::=  { xport-interface 2 } 
mass-storage-block-driver              OBJECT IDENTIFIER ::=  { system 15 } 
mass-storage-block-drivers             OBJECT IDENTIFIER ::=  { mass-storage-block-driver 3 } 
mass-storage-bd2                       OBJECT IDENTIFIER ::=  { mass-storage-block-drivers 2 } 
settings-msbd2                         OBJECT IDENTIFIER ::=  { mass-storage-bd2 1 } 
hrm                                    OBJECT IDENTIFIER ::=  { dm 3 } 
hrStorage                              OBJECT IDENTIFIER ::=  { hrm 2 } 
hrStorageTable                         OBJECT IDENTIFIER ::=  { hrStorage 3 } 
hrStorageEntry                         OBJECT IDENTIFIER ::=  { hrStorageTable 1 } 
hrDevice                               OBJECT IDENTIFIER ::=  { hrm 3 } 
hrDeviceTable                          OBJECT IDENTIFIER ::=  { hrDevice 2 } 
hrDeviceEntry                          OBJECT IDENTIFIER ::=  { hrDeviceTable 1 } 
hrPrinterTable                         OBJECT IDENTIFIER ::=  { hrDevice 5 } 
hrPrinterEntry                         OBJECT IDENTIFIER ::=  { hrPrinterTable 1 } 
printmib                               OBJECT IDENTIFIER ::=  { dm 2 } 
prtGeneral                             OBJECT IDENTIFIER ::=  { printmib 5 } 
prtGeneralTable                        OBJECT IDENTIFIER ::=  { prtGeneral 1 } 
prtGeneralEntry                        OBJECT IDENTIFIER ::=  { prtGeneralTable 1 } 
prtCover                               OBJECT IDENTIFIER ::=  { printmib 6 } 
prtCoverTable                          OBJECT IDENTIFIER ::=  { prtCover 1 } 
prtCoverEntry                          OBJECT IDENTIFIER ::=  { prtCoverTable 1 } 
prtLocalization                        OBJECT IDENTIFIER ::=  { printmib 7 } 
prtLocalizationTable                   OBJECT IDENTIFIER ::=  { prtLocalization 1 } 
prtLocalizationEntry                   OBJECT IDENTIFIER ::=  { prtLocalizationTable 1 } 
prtStorageRefTable                     OBJECT IDENTIFIER ::=  { prtGeneral 2 } 
prtStorageRefEntry                     OBJECT IDENTIFIER ::=  { prtStorageRefTable 1 } 
prtDeviceRefTable                      OBJECT IDENTIFIER ::=  { prtGeneral 3 } 
prtDeviceRefEntry                      OBJECT IDENTIFIER ::=  { prtDeviceRefTable 1 } 
prtInput                               OBJECT IDENTIFIER ::=  { printmib 8 } 
prtInputTable                          OBJECT IDENTIFIER ::=  { prtInput 2 } 
prtInputEntry                          OBJECT IDENTIFIER ::=  { prtInputTable 1 } 
prtOutput                              OBJECT IDENTIFIER ::=  { printmib 9 } 
prtOutputTable                         OBJECT IDENTIFIER ::=  { prtOutput 2 } 
prtOutputEntry                         OBJECT IDENTIFIER ::=  { prtOutputTable 1 } 
prtMarker                              OBJECT IDENTIFIER ::=  { printmib 10 } 
prtMarkerTable                         OBJECT IDENTIFIER ::=  { prtMarker 2 } 
prtMarkerEntry                         OBJECT IDENTIFIER ::=  { prtMarkerTable 1 } 
prtMarkerSupplies                      OBJECT IDENTIFIER ::=  { printmib 11 } 
prtMarkerSuppliesTable                 OBJECT IDENTIFIER ::=  { prtMarkerSupplies 1 } 
prtMarkerSuppliesEntry                 OBJECT IDENTIFIER ::=  { prtMarkerSuppliesTable 1 } 
prtMediaPath                           OBJECT IDENTIFIER ::=  { printmib 13 } 
prtMediaPathTable                      OBJECT IDENTIFIER ::=  { prtMediaPath 4 } 
prtMediaPathEntry                      OBJECT IDENTIFIER ::=  { prtMediaPathTable 1 } 
prtChannel                             OBJECT IDENTIFIER ::=  { printmib 14 } 
prtChannelTable                        OBJECT IDENTIFIER ::=  { prtChannel 1 } 
prtChannelEntry                        OBJECT IDENTIFIER ::=  { prtChannelTable 1 } 
prtInterpreter                         OBJECT IDENTIFIER ::=  { printmib 15 } 
prtInterpreterTable                    OBJECT IDENTIFIER ::=  { prtInterpreter 1 } 
prtInterpreterEntry                    OBJECT IDENTIFIER ::=  { prtInterpreterTable 1 } 
prtConsoleDisplayBuffer                OBJECT IDENTIFIER ::=  { printmib 16 } 
prtConsoleDisplayBufferTable           OBJECT IDENTIFIER ::=  { prtConsoleDisplayBuffer 5 } 
prtConsoleDisplayBufferEntry           OBJECT IDENTIFIER ::=  { prtConsoleDisplayBufferTable 1 } 
prtConsoleLights                       OBJECT IDENTIFIER ::=  { printmib 17 } 
prtConsoleLightTable                   OBJECT IDENTIFIER ::=  { prtConsoleLights 6 } 
prtConsoleLightEntry                   OBJECT IDENTIFIER ::=  { prtConsoleLightTable 1 } 
prtAlert                               OBJECT IDENTIFIER ::=  { printmib 18 } 
prtAlertTable                          OBJECT IDENTIFIER ::=  { prtAlert 1 } 
prtAlertEntry                          OBJECT IDENTIFIER ::=  { prtAlertTable 1 } 


energy-star OBJECT-TYPE
    SYNTAX  INTEGER
    ACCESS  read-write
    STATUS  optional
    DESCRIPTION
                "Returns or changes the Energy Star sleep value.  If the
                value is greater than zero, then the device will go into
                energy saving sleep mode after the print engine has been
                idle for the number of seconds specified by this object.
                A value of zero means Energy Star is disabled and the
                device will not go to sleep based on print engine idle
                time.  The value must be non-negative.
                Additional information:
                Returns or changes the Energy Star sleep value. 
                The device will go into energy saving sleep 
                mode after the print engine has been idle for 
                the number of seconds specified by this 
                object. LaserJet 5Si supports values of 0, 900, 1800, 
                3600, 7200, and 10800; additionally, a value of 10 is
                supported in Service Mode. A value of 0 means  
                never go to sleep based on print engine idle 
                time.  Setting to an unsupported value causes  
                the printer to substitute a value (listed 
                below) and to return <noError> 
                status.  
                The values for normal operation are as follow:  
                <=0 snap to 0  
                >= 1 and <= 1349 snap to 900 (15 minutes)  
                >= 1350 and <= 2699 snap to 1800 (30 minutes)  
                >= 2700 and <= 5399 snap to 3600 (60 minutes)  
                >= 5400 and <= 8999 snap to 7200 (120 minutes)  
                >= 9000 snap to 10800  (180 minutes)  
                The values for Service Mode operation are the same as 
                above except 10 is a legal value (no snapping). When 
                the printer exits Service Mode the default value is 
                restored."
::= { settings-system 1 }
               
               
sleep-mode OBJECT-TYPE
    SYNTAX  INTEGER {
		   eFalse(1),
		   eTrue(2)
		   }
    ACCESS  read-write
    STATUS  optional
    DESCRIPTION
                "Returns eTrue if the device is in energy saving sleep
                mode, otherwise returns eFalse.  Setting SLEEP-MODE to
                eFalse causes the device to wake up, if it is in sleep
                mode.  Setting SLEEP-MODE to eTrue causes the device to
                go into sleep mode.
                Additional information:
                Setting to this object to eTrue while printer is 
                awake will not change the 
                printer's current state and will return 
                <genErr> status.  
                Setting to this object to eTrue while printer is 
                already in  the Sleep Mode will not change the 
                printer's current state and will return <noError> status.  
                Setting to eFalse while printer is already awake  
                will not change the printer's 
                current state and will return <noError> status."
::= { settings-system 2 }
               
               
on-off-line OBJECT-TYPE
    SYNTAX  INTEGER {
		   eOnline(1),
		   eOffline(2),
		   eOfflineAtEndOfJob(3)
		   }
    ACCESS  read-write
    STATUS  optional
    DESCRIPTION
                "To bring the PDL processing sub-system on or off line.
                If the device is a printer, then the printer does not
                process print job data when the printer is off line.
                PML communication persists.
                Additional information:
                When the printer is in the Offline state, 
                printing will stop as soon as possible (no more sheets 
                of media are pulled from input trays). All I/O 
                communication continues (no change from the Online 
                state).  
                
                Setting to eOnline has the following affect:  
                Printer will immediately go to or remain in the Online 
                state; <noError> status is returned.  
                If the printer's current state 
                is Offline with a pending error condition that 
                prevents the printer from going to the Online 
                state, the printer will remain in the Offline state; 
                <genErr> status is returned. 
                
                Setting to eOffline has the following affect:  
                Printer will immediately go to or remain in the 
                Offline state; <noError> status is returned.  
                If pages are being printed, those pages will complete 
                with the printer in the Offline state.  
                
                Setting to eOfflineAtEndOfJob has the following 
                affect:  
                If not in a job or already in the Offline state, the 
                printer will immediately go to or remain in the 
                Offline state; <noError> status is returned.  
                If in a job and the current state is Online, the 
                printer will remain in the Online state, with the 
                value of this object as eOfflineAtEndOfJob, until the 
                end of the job; <noError> status is returned. At the end of 
                the job, the printer goes to the Offline state and the 
                value of this object becomes eOffline.  
                Setting this object to eOffline or eOnline before the 
                end of the job causes the action for that value to be 
                taken immediately."
::= { status-system 5 }
               
               
continue OBJECT-TYPE
    SYNTAX  INTEGER {
		   eInitiateAction(1)
		   }
    ACCESS  write-only
    STATUS  optional
    DESCRIPTION
                "A device can support a class of errors called
                continuable errors.  When a continuable error is
                encountered, the device requires a continue event to
                occur before the device will continue operation.  One
                continue event is setting the CONTINUE object to
                eInitiateAction.  Devices can support other continue
                events, like auto-continue.  A continue event causes the
                continuable error to be acknowledged, thus allowing the
                device to continue.  Each device needs to list the
                continuable errors.  If the device doesn't currently
                have an unacknowledged continuable error, the response
                will contain <genErr>.
                Additional information:
                 If LaserJet 5Si doesn't currently  
                have an unacknowledged continuable error, the  
                response will contain <noError> status.   
                Since LaserJet 5Si does not have a CONTINUE key, the SELECT key is used to perform 
                the continue operation at the control panel. "  
::= { status-system 6 }
               
               
auto-continue OBJECT-TYPE
    SYNTAX  INTEGER {
		   eOff(1),
		   eOn(2)
		   }
    ACCESS  read-write
    STATUS  optional
    DESCRIPTION
                "Indicates if the device will automatically continue
                after encountering a continuable error.  If AUTO-
                CONTINUE is set to eOn, the device will automatically
                generate continue event to acknowledge continuable
                errors.  If AUTO-CONTINUE is set to eOff, then some
                other continue event will have to acknowledge the
                continuable error."
::= { status-system 7 }
               
               
job-input-auto-continue-timeout OBJECT-TYPE
    SYNTAX  INTEGER(-1..3600)
    ACCESS  read-write
    STATUS  optional
    DESCRIPTION
                "The number of seconds the device waits after a job
                related continuable error occurs before automatically
                continuing.  An example job related continuable error is
                the job requesting a media size that is not available.
                After the timeout expires, the device will continue
                processing the job as if a continue event occurred, such
                as the front panel continue key being pressed.  If the
                value is -1, the device does not automatically continue
                after a job related continuable error occurs.  If the
                value is 0, the device immediately continues.  If the
                value is greater than 0, the value represents the
                timeout value in seconds.
                Additional information:
                This object is used only for media requests 
                (size and/or name).  
                LaserJet 5Si supports any value in the range of -1 to 3600. Setting to a value 
                outside of that range causes  
                the printer to substitute a value (listed 
                below) and to return <noError> 
                status.  
                The values are as follow:  
                <-1 snaps to -1  
                >3600 snaps to 3600  (60 minutes)  
                The action that occurs when this timeout expires is explained by
                JOB-INPUT-AUTO-CONTINUE-MODE. It is not the same as the CONTINUE 
                object being set to eInitiateAction or the Select key being pressed on
                the control panel. " 
::= { status-system 35 }
               
               
job-input-auto-continue-mode OBJECT-TYPE
    SYNTAX  OCTET STRING
    ACCESS  read-write
    STATUS  optional
    DESCRIPTION
                "Returns or sets the device behavior when the desired
                media is not currently available.
                  cCancelJob - The device cancels the job.  The device
                POS should explain what happens if this item is not the
                only item in the collection.
                  cAutoMediaSizeOverride - The device is allowed to
                substitute a different size media.
                  cAutoMediaNameOverride - The device is allowed to
                substitute a different media name.
                Additional information:
                If cCancelJob is set, the current print job will 
                be canceled regardless of other item settings. At least one bit of the 
                collection must be set; setting this object to zero will cause a status of
                <badValue> to be returned.  
                This object applies to all media requests, including Manual Feed Requests.  
                This object describes the action that is performed when the 
                JOB-INPUT-AUTO-CONTINUE-TIMEOUT expires. The action performed by the CONTINUE 
                object being set to eInitiateAction or the Select key being pressed on
                the control panel may cause different actions. "
::= { status-system 36 }
               
               
background-status-msg-line1-part1 OBJECT-TYPE
    SYNTAX  DisplayString
    ACCESS  read-write
    STATUS  optional
    DESCRIPTION
                "The string displayed on the device's front panel in
                place of the printer's built-in background status
                string.  An example built-in background status string is
                '00 READY'.
                Additional information:
                This object allows a message to be displayed when 
                it is the highest priority message. Setting this 
                objedct does not guarantee the message will be 
                displayed; and reading it returns the value last 
                written, not the currently displayed message (use 
                prtConsoleDisplayBufferText to read the 
                display).  
                The priority assigned for displaying this message 
                is one lower than the PJL RDYMSG.  
                To clear the message, write a null string to this 
                object.  
                While the object prtConsoleLocalization controls the 
                localization and symbol set usage of printer generated messages, this 
                object's message is displayed using the symbol set 
                specified with the string. The default symbol set is Roman-8; additional 
                legal symbol sets are ISOLatin5, ISOLatin2 and Windows31J.  
                When either BACKGROUND-STATUS-MSG-LINE1-PART1 or 
                BACKGROUND-STATUS-MSG-LINE2-PART1 contains a non-null value, both will be 
                displayed."
::= { background-message1 1 }
               
               
background-status-msg-line2-part1 OBJECT-TYPE
    SYNTAX  DisplayString
    ACCESS  read-write
    STATUS  optional
    DESCRIPTION
                "The string displayed on the device's front panel in
                place of the printer's built-in background status
                string.  An example built-in background status string is
                '00 READY'.
                Additional information:
                See BACKGROUND-STATUS-MSG-LINE1-PART1"
::= { background-message2 1 }
               
               
error-log-clear OBJECT-TYPE
    SYNTAX  INTEGER {
		   eClearErrorLog(1)
		   }
    ACCESS  write-only
    STATUS  optional
    DESCRIPTION
                "Setting this object clears all the entries in the error
                log sub-tree."
::= { status-system 38 }
               
               
job-output-auto-continue-timeout OBJECT-TYPE
    SYNTAX  INTEGER(-1..3600)
    ACCESS  read-write
    STATUS  optional
    DESCRIPTION
                "Returns or sets the time that the printer will wait
                after an output bin becomes full and the printer is
                trying to deliver a sheet of media to that output bin.
                When the timeout expires, the job is processed according
                to the OUTBINn-OVERRIDE-MODE.  A value of -1 indicates
                that the printer will wait for a continue event.  A non-
                negative value is the number of seconds to wait.
                Additional information:
                A value of zero means to continue immediately."
::= { status-system 40 }
               
               
model-number OBJECT-TYPE
    SYNTAX  DisplayString
    ACCESS  read-only
    STATUS  optional
    DESCRIPTION
                "Identifies the device model number as listed in the HP
                corporate price list (e.g.  C2121A for DeskJet 500C).
                The string is as specific as possible.  Products should
                note in POS if the model number on the CPL changes but
                the device reports the previous model number.  If the
                model number changes based on the installed options, the
                POS should indicate if only the base model number is
                returned, or if the device senses the installed options
                and returns the correct model number.  If possible,
                encode the model number in a symbol set (like Roman-8)
                that matches the ASCII character set and limit the
                characters used to ASCII characters.
                Additional information:
                The value of this object does not change based on
                the installed options."
::= { id 1 }
               
               
model-name OBJECT-TYPE
    SYNTAX  DisplayString
    ACCESS  read-only
    STATUS  optional
    DESCRIPTION
                "Identifies the device model name (e.g.  ''DeskJet
                1200C'').  The string is as specific as possible.
                Capitalization and spacing should match family naming
                conventions.  Products should note in POS if the model
                name on the HP corporate price list changes but the
                device reports the previous device name.  If the model
                name changes based on the installed options, the POS
                should indicate if only the base model name is returned,
                or if the device senses the installed options and
                returns the correct model name.  If possible, encode the
                model name in a symbol set (like Roman-8) that matches
                the ASCII character set and limit the characters used to
                ASCII characters.
                Additional information:
                The value of this object does not change based on
                the installed options.  
                Since the value of this object is frequently used in displaying a list of 
                printers, it is kept relatively short in case systems have limited width 
                for their display area."
::= { id 2 }
               
               
serial-number OBJECT-TYPE
    SYNTAX  DisplayString
    ACCESS  read-only
    STATUS  optional
    DESCRIPTION
                "Identifies the serial number for the device.  If the
                SERIAL-NUMBER object is set by the user, then setting
                the object does not need to be protected.  If the
                SERIAL-NUMBER object is set at the factory, then the
                SERVICE-PASSWORD object must be set correctly before the
                SERIAL-NUMBER object is writable.  If this is a writable
                object, the POS should indicate the maximum supported
                string length.  If possible, encode the serial number in
                a symbol set (like Roman-8) that matches the ASCII
                character set and limit the characters used to ASCII
                characters.
                Additional information:
                The format of the LaserJet 5Si serial number is:  
                aaxxyynnnn  
                where: aa=A-Z, xx=A..Z & 0..9, yy=0..9 & A..Z, nn=0..9  
                This object is read-only so the SERVICE-PASSWORD object is not used."
::= { id 3 }
               
               
device-name OBJECT-TYPE
    SYNTAX  DisplayString
    ACCESS  read-write
    STATUS  optional
    DESCRIPTION
                "User defined device name.  The POS should indicate the
                maximum supported string length.  If the user entered
                string is too long, the device will store as much as
                possible and will return the <noError>.

                Additional information:
                This object is stored in NVRAM.   
                The maximum supported string length is 32  
                characters.  If the user entered string is too long, 
                the device will store the first 32 characters and will 
                return the <noError> status."
::= { id 10 }
               
               
device-location OBJECT-TYPE
    SYNTAX  DisplayString
    ACCESS  read-write
    STATUS  optional
    DESCRIPTION
                "User defined device location.  The POS should indicate
                the maximum supported string length.  If the user
                entered string is too long, the device will store as
                much as possible and will return the <noError>.

                Additional information:
                The maximum supported string length is 16 
                characters.  If the user entered string is too long, 
                the device will store the first 16 characters and will 
                return the <noError> status.  
                This object is saved in NVRAM."
::= { id 11 }
               
               
asset-number OBJECT-TYPE
    SYNTAX  DisplayString
    ACCESS  read-write
    STATUS  optional
    DESCRIPTION
                "User defined asset number.  The POS should indicate the
                maximum supported string length.  If the user entered
                string is too long, the device will store as much as
                possible and will return the <noError>.

                Additional information:
                The maximum supported string length is 8 
                characters.  If the user entered string is too long, 
                the device will store the first 8 characters and will  
                return the <noError> status.  
                This object is saved in NVRAM."
::= { id 12 }
               
               
simm1-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 1.
                  eEmpty means the device did not detect any option
                installed in the interface slot.
                  eUnknown means the device doesn't recognize the
                installed option.
                  eUnSupported means the device recognizes the installed
                option, but does not support the option.
                  eReadOnlyMemory means the installed option contains
                ROM Ics.
                  eVolatileRandomAccessMemory means the installed option
                contains RAM ICs that loose data when the power is
                turned off.
                  eNonVolatileRandomAccessMemory means that the
                installed option contains RAM ICs that do not loose data
                when the power is turned off.
                  eFlashMemory means that the installed option contains
                a type of non-volatile RAM that needs to be erased
                before it can be written.
                  eDiskDrive means the installed option contains a disk
                drive.  eRamRom means the installed option contains both
                volatile random access memory and read only memory.
                  eInputPHD means the installed option is an input paper
                handling device.
                  eOutputPHD means the installed option is an output
                paper handling device.
                  eIOCard means the installed option is an I/O card."
::= { simm1 4 }
               
               
simm1-capacity OBJECT-TYPE
    SYNTAX  INTEGER
    ACCESS  read-only
    STATUS  optional
    DESCRIPTION
                "Returns an indication of the capacity of the SIMM
                installed in SIMM slot 1.  The capacity is dependent on
                the type of option, as indicated by the SIMM1-TYPE
                object.  This object has no meaning if the installed
                option type is eUnknown or eReadOnlyMemory.  This object
                contains the size, in bytes, if the installed option
                type is eVolatileRandomAccessMemory,
                eNonVolatileRandomAccessMemory, eFlashMemory, or
                eDiskDrive.  If the type of the installed option is
                eRamRom, this object contains the size, in bytes, of the
                random access memory.  If the type of the installed
                option is eInputPHD, the capacity indicates the number
                of input trays supported by the installed option.  If
                the type of the installed option is eOutputPHD, the
                capacity indicates the number of output bins supported
                by the installed option.  If the type of the installed
                option is eIOCard, the capacity indicates the number of
                logical I/O ports supported by the I/O card.
                Additional information:
                Returns an indication of the capacity of the 
                installed option in bytes.  This object is not 
                supported unless the SIMM1-TYPE type is 
                eVolatileRandomAccessMemory."
::= { simm1 5 }
               
               
simm2-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 2.  See SIMM1-TYPE for a description."
::= { simm2 4 }
               
               
simm2-capacity OBJECT-TYPE
    SYNTAX  INTEGER
    ACCESS  read-only
    STATUS  optional
    DESCRIPTION
                "Returns an indication of the capacity of the SIMM
                installed in SIMM slot 2.  See SIMM1-CAPACITY for a
                description.
                Additional information:
                Returns an indication of the capacity of the 
                installed option in bytes.  This object is not 
                supported unless the SIMM2-TYPE type is 
                eVolatileRandomAccessMemory."
::= { simm2 5 }
               
               
simm3-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 3.  See SIMM1-TYPE for a description."
::= { simm3 4 }
               
               
simm3-capacity OBJECT-TYPE
    SYNTAX  INTEGER
    ACCESS  read-only
    STATUS  optional
    DESCRIPTION
                "Returns an indication of the capacity of the SIMM
                installed in SIMM slot 3.  See SIMM1-CAPACITY for a
                description.
                Additional information:
                Returns an indication of the capacity of the 
                installed option in bytes.  This object is not 
                supported unless the SIMM3-TYPE type is 
                eVolatileRandomAccessMemory."
::= { simm3 5 }
               
               
simm4-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 4.  See SIMM1-TYPE for a description."
::= { simm4 4 }
               
               
simm4-capacity OBJECT-TYPE
    SYNTAX  INTEGER
    ACCESS  read-only
    STATUS  optional
    DESCRIPTION
                "Returns an indication of the capacity of the SIMM
                installed in SIMM slot 4.  See SIMM1-CAPACITY for a
                description.
                Additional information:
                Returns an indication of the capacity of the 
                installed option in bytes.  This object is not 
                supported unless the SIMM4-TYPE type is 
                eVolatileRandomAccessMemory."
::= { simm4 5 }
               
               
mio1-manufacturing-info OBJECT-TYPE
    SYNTAX  DisplayString
    ACCESS  read-only
    STATUS  optional
    DESCRIPTION
                "Returns information describing the manufacture of the
                I/O card installed in MIO interface 1.  May include
                serial number and firmware revision.
                Additional information:
                The format of the string returned is determined by 
                the manufacturer of the MIO card. There is no standard for content of the 
                string. If no card is installed, a null string is returned."
::= { mio1 3 }
               
               
mio1-type OBJECT-TYPE
    SYNTAX  INTEGER {
		   eEmpty(1),
		   eIOCard(12)
		   }
    ACCESS  read-only
    STATUS  optional
    DESCRIPTION
                "Returns an indication of the type of option installed in
                MIO interface 1.  See SIMM1-TYPE for an explanation of
                the enumerations."
::= { mio1 4 }
               
               
mio2-manufacturing-info OBJECT-TYPE
    SYNTAX  DisplayString
    ACCESS  read-only
    STATUS  optional
    DESCRIPTION
                "Returns information describing the manufacture of the
                I/O card installed in MIO interface 2.  May include
                serial number and firmware revision.
                Additional information:
                The format of the string returned is determined by 
                the manufacturer of the MIO card. There is no standard for content of the 
                string. If no card is installed, a null string is returned."
::= { mio2 3 }
               
               
mio2-type OBJECT-TYPE
    SYNTAX  INTEGER {
		   eEmpty(1),
		   eIOCard(12)
		   }
    ACCESS  read-only
    STATUS  optional
    DESCRIPTION
                "Returns an indication of the type of option installed in
                MIO interface 2.  See SIMM1-TYPE for an explanation of
                the enumerations."
::= { mio2 4 }
               
               
phd1-model OBJECT-TYPE
    SYNTAX  DisplayString
    ACCESS  read-only
    STATUS  optional
    DESCRIPTION
                "Returns product information identifying the PHD device.
                Example: XXXX"
::= { phd1 1 }
               
               
phd1-manufacturing-info OBJECT-TYPE
    SYNTAX  DisplayString
    ACCESS  read-only
    STATUS  optional
    DESCRIPTION
                "Returns information describing the manufacture of this
                particular PHD.  May include serial number and firmware
                revision."
::= { phd1 2 }
               
               
phd1-type OBJECT-TYPE
    SYNTAX  INTEGER {
		   eEmpty(1),
		   eInputPHD(10)
		   }
    ACCESS  read-only
    STATUS  optional
    DESCRIPTION
                "Returns an indication of the type of option installed in
                this particular SIMM interface  See SIMM1-TYPE for an
                explanation of the enumerations.
                Additional information:
                Returns an indication of whether or not the high 
                capacity envelope feeder is installed on the printer. A value of eEmpty means 
                that the envelope feeder is not installed."
::= { phd1 3 }
               
               
phd1-capacity OBJECT-TYPE
    SYNTAX  INTEGER
    ACCESS  read-only
    STATUS  optional
    DESCRIPTION
                "Returns an indication of the capacity of the installed
                option.  See SIMM1-CAPACITY for an explanation of the
                meaning of the value of this object.
                Additional information:
                The LaserJet 5Si high capacity envelope feeder has a 
                single tray."
::= { phd1 4 }
               
               
phd2-model OBJECT-TYPE
    SYNTAX  DisplayString
    ACCESS  read-only
    STATUS  optional
    DESCRIPTION
                "Returns product information identifying PHD device 2.
                Example: XXXX"
::= { phd2 1 }
               
               
phd2-manufacturing-info OBJECT-TYPE
    SYNTAX  DisplayString
    ACCESS  read-only
    STATUS  optional
    DESCRIPTION
                "Returns information describing the manufacture of PHD 2.
                May include serial number and firmware revision."
::= { phd2 2 }
               
               
phd2-type OBJECT-TYPE
    SYNTAX  INTEGER {
		   eEmpty(1),
		   eInputPHD(10),
		   eOutputPHD(11)
		   }
    ACCESS  read-only
    STATUS  optional
    DESCRIPTION
                "Returns an indication of the type of option installed in
                PHD interface 2.  See SIMM1-TYPE for an explanation of
                the enumerations.
                Additional information:
                External paper handling devices are connected to 
                the printer in a daisy-chained fashion. PHD2 refers to the first device that 
                is connected. Returns eEmpty if no paper handling devices are 
                installed.  
                If the HCI is attached, the value will be eInputPHD. If the HCO is the first 
                connected device, the value will be 
                eOutputPHD."
::= { phd2 3 }
               
               
phd2-capacity OBJECT-TYPE
    SYNTAX  INTEGER
    ACCESS  read-only
    STATUS  optional
    DESCRIPTION
                "Returns an indication of the capacity of the installed
                option.  See SIMM1-CAPACITY for an explanation of the
                meaning of the value of this object.
                Additional information:
                The LaserJet 5Si high capacity input device has a 
                single tray."
::= { phd2 4 }
               
               
phd3-model OBJECT-TYPE
    SYNTAX  DisplayString
    ACCESS  read-only
    STATUS  optional
    DESCRIPTION
                "Returns product information identifying PHD device 3.
                Additional information:
                The value returned by Tlatoani depends on the current 
                mode of the device. The possible values are as follows:  
                MULTIBIN MAILBOX C3764A  [BNPxxxx.x]  
                MULTIBIN STACKER C3764A  [BNPxxxx.x]  
                MULTIBIN SEPARATOR C3764A[BNPxxxx.x]."
::= { phd3 1 }
               
               
phd3-manufacturing-info OBJECT-TYPE
    SYNTAX  DisplayString
    ACCESS  read-only
    STATUS  optional
    DESCRIPTION
                "Returns information describing the manufacture of PHD 3.
                May include serial number and firmware revision."
::= { phd3 2 }
               
               
phd3-type OBJECT-TYPE
    SYNTAX  INTEGER {
		   eEmpty(1),
		   eInputPHD(10),
		   eOutputPHD(11)
		   }
    ACCESS  read-only
    STATUS  optional
    DESCRIPTION
                "Returns an indication of the type of option installed in
                PHD interface 3.  See SIMM1-TYPE for an explanation of
                the enumerations.
                Additional information:
                External paper handling devices are connected to 
                the printer in a daisy-chained fashion. PHD3 refers to the second device that 
                is connected. Returns eEmpty if only one paper handling device 
                is installed.  
                If the HCO is attached (second on the chain), the value will be eOutputPHD. 
                If the HCI is the second connected device, the 
                value will be eInputPHD."
::= { phd3 3 }
               
               
phd3-capacity OBJECT-TYPE
    SYNTAX  INTEGER
    ACCESS  read-only
    STATUS  optional
    DESCRIPTION
                "Returns an indication of the capacity of the installed
                option.  See SIMM1-CAPACITY for an explanation of the
                meaning of the value of this object.
                Additional information:
                This is the number of logical bins provided by the device."
::= { phd3 4 }
               
               
phd4-model OBJECT-TYPE
    SYNTAX  DisplayString
    ACCESS  read-only
    STATUS  optional
    DESCRIPTION
                "Returns product information identifying PHD device 4.
                Additional information:
                Returns product information identifying the PHD4 device.   
                Example: OUTBIN STAPLER CXXXXA."
::= { phd4 1 }
               
               
phd4-manufacturing-info OBJECT-TYPE
    SYNTAX  DisplayString
    ACCESS  read-only
    STATUS  optional
    DESCRIPTION
                "Returns information describing the manufacture of PHD 4.
                May include serial number and firmware revision.
                Additional information:
                Returns information describing the manufacturer of PHD 4.   
                May include serial number and firmware revision."
::= { phd4 2 }
               
               
phd4-type OBJECT-TYPE
    SYNTAX  INTEGER {
		   eEmpty(1),
		   eInputPHD(10),
		   eOutputPHD(11),
		   eBindingPHD(13)
		   }
    ACCESS  read-only
    STATUS  optional
    DESCRIPTION
                "Returns an indication of the type of option installed in
                PHD interface 4.  See SIMM1-TYPE for an explanation of
                the enumerations.
                Additional information:
                The envelope feeder is PHD1.  The remaining   
                external paper handling devices are connected to  
                the printer in a daisy-chained fashion. PHD4   
                refers to the third device that is connected.   
                Returns the type of the 3 rd party device in this  
                chain, otherwise, eEmpty if only two paper   
                handling devices are installed."
::= { phd4 3 }
               
               
phd4-capacity OBJECT-TYPE
    SYNTAX  INTEGER
    ACCESS  read-only
    STATUS  optional
    DESCRIPTION
                "Returns an indication of the capacity of the installed
                option.  See SIMM1-CAPACITY for an explanation of the
                meaning of the value of this object.
                Additional information:
                Returns an indication of the capacity of the installed   
                option.  See SIMM1-CAPACITY for an explanation of the   
                meaning of the value of this object."
::= { phd4 4 }
               
               
phd5-type OBJECT-TYPE
    SYNTAX  INTEGER {
		   eEmpty(1),
		   eInputPHD(10),
		   eOutputPHD(11)
		   }
    ACCESS  read-only
    STATUS  optional
    DESCRIPTION
                "Returns an indication of the type of option installed in
                PHD interface 5.  See SIMM1-TYPE for an explanation of
                the enumerations.
                Additional information:
                External paper handling devices are connected to 
                the printer in a daisy-chained fashion. PHD5 refers to the fourth device that 
                is connected. Returns eEmpty if only three paper handling devices 
                are installed.  
                At introduction, there is no planned configuration that would cause the value 
                of this object to be anything other than eEmpty."
::= { phd5 3 }
               
               
phd6-type OBJECT-TYPE
    SYNTAX  INTEGER {
		   eEmpty(1),
		   eInputPHD(10),
		   eOutputPHD(11)
		   }
    ACCESS  read-only
    STATUS  optional
    DESCRIPTION
                "Returns an indication of the type of option installed in
                PHD interface 6.  See SIMM1-TYPE for an explanation of
                the enumerations.
                Additional information:
                External paper handling devices are connected to 
                the printer in a daisy-chained fashion. PHD6 refers to the fifth device that 
                is connected. Returns eEmpty if only three paper handling devices 
                are installed.  
                At introduction, there is no planned configuration that would cause the value 
                of this object to be anything other than eEmpty."
::= { phd6 3 }
               
               
self-test OBJECT-TYPE
    SYNTAX  INTEGER {
		   eNotInASelfTest(1),
		   eNonDestructiveSelfTest(4)
		   }
    ACCESS  read-write
    STATUS  optional
    DESCRIPTION
                "Writing this object allows a device self test to be
                started.  Reading this object provides an indication
                what self-test is currently executing, if any.  Actual
                self-test operation is device specific.  A self test may
                not be allowed at any arbitrary time.  If the device
                supports the requested self test, but can not start the
                execution of the self test when requested, the device
                will respond with <genErr>.  
                If a non-destructive self test is being started, the device
                will generate a response before the self test is
                completed.
                RECOMMENDATION:  If the device is ready (i.e. the NOT-
                READY-PRINTER object does not contain any items, except
                maybe being off-line) and is idle (i.e. the NOT-IDLE
                object does not contain any items), this request should
                always succeed.  This provides a mechanism for driver
                writers to always determine if the action will succeed
                or not.
                Additional information:
                The eNonDestructiveSelfTest performs limited 
                testing on the printer and its attached paper handling 
                devices. After the self-test is complete a 
                configuration page is printed. The recommended 
                way to cause a configuration page to be printed is to 
                use the PRINT-INTERNAL-PAGE object. 
                A continuous self test cannot be started 
                or terminated using this OID.  
                
                The printer must be idle before it can execute a 
                self test. The best method to assure that the 
                printer is idle is to set the object ON-OFF-LINE to 
                eOfflineAtEndOfJob, wait for the printer to be 
                offline and then execute the self test. The printer 
                will put itself online to print the page.
                
                When the printer is idle, setting this object to 
                eNonDestructiveSelfTest results in a status of <noError> 
                and a value of eNonDestructiveSelfTest being returned. 
                If the printer is not idle (whether printing an 
                external job, printing an internal page or running 
                self test), a status of 
                <genErr> status will be 
                returned with a value of eNotInASelfTest.
                
                When the printer is idle, setting this object to 
                eNonDestructiveSelfTestcauses some internal testing, 
                the page to be formatted and put in the printer's 
                print queue. Before the page is in the print queue, a 
                get on this object will return eNonDestructiveSelfTest 
                (it is currently estimated that the time to format the 
                page is one millisecond). 
                Attempting to set this object before the page has 
                completed being formatted and printed will cause 
                <genErr> status to be 
                returned with a value of eNotInASelfTest.  
                
                After the page is in the queue, a get on this object 
                will return a value of eNotInASelfTest. 
                Setting this object to eNonDestructiveSelfTest 
                before the first page has completed results in 
                a status of <genErr> status 
                with a value of eNotInASelfTest.  
                
                Likewise, if the PRINT-INTERNAL-PAGE object is set to 
                a valid value and that page has not printed 
                when this object is set to eNonDestructiveSelfTest, a 
                status of <genErr> status 
                with a value of eNotInASelfTest will be 
                returned until the internal page has printed."
::= { test 1 }
               
               
print-internal-page OBJECT-TYPE
    SYNTAX  INTEGER {
		   eNotPrintingAnInternalPage(1),
		   ePrintingAnUnknownInternalPage(2),
		   eDeviceDemoPage2(4),
		   eDeviceDemoPage5ErrorLog(7),
		   eDeviceDemoPage6FileSystemDirectoryListing(8),
		   ePCLDemoPage1ConfigurationPage(300),
		   ePCLFontList1(350),
		   ePostScriptDemoPage1ConfigurationPage(400),
		   ePostScriptFontList1(450)
		   }
    ACCESS  read-write
    STATUS  optional
    DESCRIPTION
                "Writing this object to a value other than
                eNotPrintingAnInternalPage causes the device to attempt
                to print an internally generated page.  Reading this
                object provides an indication what internally generated
                page is currently being printed, if any.  The actual
                page is device specific.  Some devices may support
                continuously printing an internally generated page.
                Setting this object to eNotPrintingAnInternalPage
                terminates continuously printing internally generated
                pages.  An internally generated page may not be allowed
                to be printed at any arbitrary time; under what
                conditions it will succeed or fail is device specific.
                If the device supports the requested page, but can not
                start printing the page when requested, the device will
                respond with <genErr>.
                RECOMMENDATION:  If the device is ready (i.e. the NOT-
                READY-PRINTER object does not contain any items, except
                maybe being off-line) and is idle (i.e. the NOT-IDLE
                object does not contain any items), this request should
                always succeed.  This provides a mechanism for driver
                writers to always determine if the action will succeed
                or not.
                Additional information:
                eDeviceDemoPage2 is the printer demo page. 
                ePCLFontList1 is the PCL typeface list. 
                eDeviceDemoPage5ErrorLog is the printer's error log. 
                LaserJet 5Si does not support continuously printing a demo 
                page.   
                
                The value eDeviceDemoPage6FileSystemDirectoryListing 
                can only be set when the disk option is installed; 
                values ePostScriptDemoPage1ConfigurationPage and 
                ePostScriptFontList1 can be set only when PostScript 
                is installed. Attempting to set these values without 
                the proper option installed will result in a status of 
                <badValue> being returned.  
                
                The printer must be idle before it will print an 
                internal page. The best method to assure that the 
                printer is idle is to set the object ON-OFF-LINE to 
                eOfflineAtEndOfJob, wait for the printer to be 
                offline and then print the internal page. The printer 
                will put itself online to print the page.
                
                When this object is set to a valid value and the 
                printer is idle, the status returned is <noError> and the 
                value returned is ePrintingAnUnknownInternalPage. If 
                the printer is not idle (whether printing an external 
                job, printing an internal page or executing a self 
                test), a status of <genErr> 
                status will be returned with a value of 
                eNotPrintingAnInternalPage.
                
                Setting this object to a valid value causes the 
                desired page to be formatted and put in the printer's 
                print queue. While the page is being formatted a get 
                on this object will return the value 
                ePrintingAnUnknownInternalPage, if 
                the time to format the page is long enough (it is 
                currently estimated that the time to format some pages 
                is as short as one millisecond). 
                Attempting to set this object before the page has 
                completed being formatted and printed will cause 
                <genErr> status to be 
                returned with a value of 
                eNotPrintingAnInternalPage.  
                
                After the page is in the queue, a get on this object 
                will return a value of eNotPrintingAnInternalPage. 
                Setting this object to cause another page to be 
                printed before the first page has completed results in 
                a status of <genErr> status 
                with a value of eNotPrintingAnInternalPage.  
                
                Likewise, if the SELF-TEST object is set to 
                eNonDestructiveSelfTest and that page has not printed 
                when this object is set to print a page, a status of 
                <genErr> status 
                with a value of eNotPrintingAnInternalPage will be 
                returned until the self test page has printed."
::= { test 2 }
               
               
cancel-job OBJECT-TYPE
    SYNTAX  INTEGER(0..32767)
    ACCESS  write-only
    STATUS  optional
    DESCRIPTION
                "Cancels the print job whose ID matches the value written
                to the CANCEL-JOB object.  The host first learns the job
                ID using the CURRENT-JOB-PARSING-ID command.  If the
                printer has completely processed the job, the printer
                responds with <badValue>.  If the
                value of the CURRENT-JOB-PARSING-ID is smaller than the
                value written to the CANCEL-JOB object, then the printer
                responds with <badValue>.  When
                read, returns the value of the last job ID what was
                canceled, or -1 to indicate no job has been canceled.
                Additional information:
                If the value written matches the ID of a job that is 
                currently being canceled (for any reason), the printer responds with <noError>.  
                LaserJet 5Si uses job ID's in the range of 0..32767. 
                Because the ID number can wrap to zero, 
                CURRENT-JOB-PARSING-ID may be smaller than the value 
                written to this object; when this occurs, no error 
                will result as long as the ID is for a currently 
                processing job."
::= { settings-job 2 }
               
               
job-info-change-id OBJECT-TYPE
    SYNTAX  OCTET STRING (SIZE(16))
    ACCESS  read-only
    STATUS  optional
    DESCRIPTION
                "Returns the current value of an object in the job-info
                sub-tree whose value has changed.  Define the object
                identifier for the object whose value has changed as
                job-info.required-field.optional-field.job-id.  job-info
                represents the OID prefix of all objects in the job-info
                sub-tree.  Required-field represents the OID field value
                that follows the job-info prefix.  Since some objects in
                the job-info sub-tree have two OID fields between the
                job-info prefix and the job-id, the optional-field
                represents the OID field between the required-field and
                the job-id field, if present.  Using this definition,
                the format for the JOB-INFO-CHANGE-ID binary value can
                be described as follows:   
                  Bytes  0-3 :  required-field  
                  Bytes  4-7 :  optional-field, or all zeros if there   
                                is no optional field  
                  Bytes  8-11: Job ID.  
                  Bytes 12-n : The value of the object job-info.   
                               required-field.optional-field.job-id.
                All multi-byte values stored in Motorola (big-endian)
                format, where the most significant byte occurs first.
                Additional information:
                LaserJet 5Si will use this object to report changes of the 
                job-info-pages-printed and job-info-state objects. 
                Therefore, the optional-field will always be zeroes 
                and, because both of these are integers, the value 
                portion of the data will always be four bytes."
::= { settings-job 3 }
               
               
current-job-parsing-id OBJECT-TYPE
    SYNTAX  INTEGER(-1..32767)
    ACCESS  read-only
    STATUS  optional
    DESCRIPTION
                "Contains the printer assigned job identification for the
                job currently being processed by the processing PDL sub-
                system.  The job ID is a monotonically increasing
                number.  The job ID may be reset to zero at power-up and
                may roll over to zero after reaching some maximum
                value.
                Additional information:
                A value of -1 is returned when the printer is
                not parsing a job.  
                When data for a new job is detected, this object is updated (the job may or 
                may not turn out to be a Null Job); however, the trap does not occur until the 
                printer determines that it is not a Null Job (a trapped value will differ from 
                the previous value by one or more).  
                Some JOB-INFO- objects are created when the first data bytes are received. If 
                the printer determines that the job is a Null Job, the JOB-INFO- objects 
                related to the Null Job are deleted. LaserJet 5Si retains the JOB-INFO- objects for 
                the 32 most recent jobs that are not Null Jobs.  
                LaserJet 5Si resets the job ID to zero at power-up and will increment it to 32767 
                before rolling it to zero. To distinguish whether a power cycle or a rollover 
                caused an id of zero, the object prtGeneralConfigChanges can be watched and if 
                it increments at the same time as CURRENT-JOB-PARSING-ID goes to zero, then a 
                power cycle is the most likely cause."
::= { job-being-parsed 1 }
               
               
job-info-name1 OBJECT-TYPE
    SYNTAX  DisplayString
    ACCESS  read-only
    STATUS  optional
    DESCRIPTION
                "Contains the first part of this print job's name.  The
                last OID field for this dynamic object contains the job
                ID.
                Additional information:
                The job name is the string specified by the
                NAME= parameter of the @PJL JOB command which  
                allows a maximum of 80 characters. The first 40 characters are in this object 
                and the second 40 are in JOB-INFO-NAME2. The symbol set is Roman-8.  
                When jobs are nested, the value assigned to this object is the name provided
                by the most recent @PJL JOB NAME= command. If no name is is provided, a null
                string is returned. Whenever a @PJL JOB NAME= command is received, the trap 
                occurs even if the name is the same."
::= { job-info 1 }
               
               
job-info-name2 OBJECT-TYPE
    SYNTAX  DisplayString
    ACCESS  read-only
    STATUS  optional
    DESCRIPTION
                "Contains the second part of this print job's name.  The
                last OID field for this dynamic object contains the job
                ID.
                Additional information:
                See JOB-INFO-NAME1."
::= { job-info 2 }
               
               
job-info-stage OBJECT-TYPE
    SYNTAX  OCTET STRING
    ACCESS  read-only
    STATUS  optional
    DESCRIPTION
                "Indicates what printer sub-systems are currently
                processing this print job.  The last OID field for this
                dynamic object contains the job ID.
                  cSourceSubsystem -  some of the job is in the printer
                I/O subsystem.
                  cProcessingSubsystem - some of the job is in the
                printer imaging processing subsystem.
                  cDestinationSubsystem -  some of the job is being
                printed.
                Additional information:
                For LaserJet 5Si cSourceSubsystem and cProcessingSubsystem 
                will always be set and cleared together.  
                A non-printing job will never set cDestinationSubsystem.  
                When a page is ready to be printed, 
                cDestinationSubsystem will be set even if
                a page of a previous job is currently being printed. cDestinationSubsystem 
                remains set until the last page of the job has reached an output bin.  
                If a 
                page requires extensive processing and allows all the previous pages of a 
                job to complete printing cDestinationSubsystem will remain set 
                until the last page of the job is closed."
::= { job-info 10 }
               
               
job-info-io-source OBJECT-TYPE
    SYNTAX  INTEGER
    ACCESS  read-only
    STATUS  optional
    DESCRIPTION
                "Indicates which I/O source, the print job was received
                over.  The value maps to port numbering scheme supported
                in the DEVICE/SOURCE-SUBSYSTEM/IO/PORTS sub-tree."
::= { job-info 11 }
               
               
job-info-pages-processed OBJECT-TYPE
    SYNTAX  INTEGER
    ACCESS  read-only
    STATUS  optional
    DESCRIPTION
                "Indicates the number of pages processed by the
                processing subsystem.  If neither the cSourceSubsystem
                or the cProcessingSubsystem items are in the associated
                JOB-INFO-STAGE object, then this object contains the
                total number of pages processed for this job.  The last
                OID field for this dynamic object contains the job ID.
                Additional information:
                This object is incremented by one when a page is 
                processed, regardless of the number of pages that are printed as a result of 
                the single page processed. In other words, it does not matter how many 
                identical copies of a page are printed, or no pages may be printed if 
                operating in silent run mode, this count is incremented only once.  
                A page is considered processed when all of the input data has been processed 
                for a page; the image of the page is not 
                necessarily completely formed."
::= { job-info 12 }
               
               
job-info-pages-printed OBJECT-TYPE
    SYNTAX  INTEGER
    ACCESS  read-only
    STATUS  optional
    DESCRIPTION
                "Indicates the number of pages printed by the destination
                subsystem.  If non of the cSourceSubsystem,
                cProcessingSubsystem or cDestinationSubsystem items are
                in the associated JOB-INFO-STAGE object, then this
                object contains the total number of pages printed for
                this job.  This value may increase by two each time for
                duplex jobs.  The last OID field for this dynamic object
                contains the job ID.
                Additional information:
                If multiple copies of a page are printed, each copy
                is counted individually."
::= { job-info 13 }
               
               
job-info-size OBJECT-TYPE
    SYNTAX  INTEGER
    ACCESS  read-only
    STATUS  optional
    DESCRIPTION
                "Indicates the number of bytes of data processed by the
                processing subsystem.  If neither of the
                cSourceSubsystem or cProcessingSubsystem items are in
                the associated JOB-INFO-STAGE object, then this object
                contains the size of this job, in bytes.  The last OID
                field for this dynamic object contains the job ID.
                Additional information:
                This count may be incremented by values other than one 
                as blocks of data are processed; blocks of data (which may be as large as 2K 
                bytes) will be processed in a varying amount of time.  
                When a job completes, this count may not be the same as the 
                total number of bytes sent to the printer since some data before or after the 
                job may be considered to be outside the job. Also, for ill-formed PostScript 
                jobs (ones that do not use the ENTER LANGUAGE command) will be reported as 
                having approximately 256 extra bytes due to the way the language switching 
                is accomplished."
::= { job-info 14 }
               
               
job-info-state OBJECT-TYPE
    SYNTAX  INTEGER {
		   eAborted(3),
		   eWaitingForResources(4),
		   ePrinted(5),
		   eTerminating(7),
		   eCancelled(10),
		   eProcessing(11)
		   }
    ACCESS  read-only
    STATUS  optional
    DESCRIPTION
                "Indicates the state of the job.  The last OID field for
                this dynamic object contains the job ID.  
                  eAborted - the print job was aborted.  
                  eWaitingForResources - the print job requires
                resources that are not currently available.  
                  ePrinted - the job has printed.  The related JOB-INFO-
                OUTCOME object indicates if any problems were
                encountered while the job was processed.  
                  eRetained - the job can be reprinted.  
                  eTerminating - the job was aborted or cancelled and is
                currently is terminating.  
                  eInterrupted - the job has been interrupted.  The job
                can be continued.  
                  ePaused - the job has been paused.  The job can be
                continuted.  
                  eCancelled - the job has been cancelled.  
                  eProcessing - the job is currently being printed
                normally.
                Additional information:
                "
::= { job-info 15 }
               
               
job-info-outcome OBJECT-TYPE
    SYNTAX  INTEGER {
		   eOk(3),
		   eWarningsEncountered(4),
		   eErrorsEncountered(5)
		   }
    ACCESS  read-only
    STATUS  optional
    DESCRIPTION
                "Indicates if any warning or error conditions were
                encountered while processing the assoicated job.  The
                last OID field for this dynamic object contains the job
                ID."
::= { job-info 19 }
               
               
job-info-outbins-used OBJECT-TYPE
    SYNTAX  OCTET STRING
    ACCESS  read-only
    STATUS  optional
    DESCRIPTION
                "Indicates which output bins this job has delivered
                printed pages to.  The last OID field for this dynamic
                object contains the job ID.
                Additional information:
                This is the logical bin. If a bin is used as an
                overflow bin, then its bit will be set as well.  
                cOutbin1 is the top/face-down bin.  
                cOutbin2 is the left/face-up bin."
::= { job-info 20 }
               
               
job-info-physical-outbins-used OBJECT-TYPE
    SYNTAX  OCTET STRING
    ACCESS  read-only
    STATUS  optional
    DESCRIPTION
                "Indicates which physical output bins this job has
                delivered printed pages to.  The last OID field for this
                dynamic object contains the job ID.
                Additional information:
                Bits in this object are set only if printed pages were 
                delivered to an external paper handling device. This object is supported 
                regardless of whether or not an external device is installed. The bits set map 
                to the 
                device's bins in a device specific manner. If the device does not report to 
                the formatter which bins are used, then no bits will be set.
                For the HCO, the bins map to the bits as follows:  
                cOutbin1--Face-up bin  
                cOutbin2--Bin1  
                cOutbin3--Bin2  
                cOutbin4--Bin3  
                cOutbin5--Bin4  
                cOutbin6--Bin5  
                cOutbin7--Bin6  
                cOutbin8--Bin7  
                cOutbin9--Bin8"
::= { job-info 22 }
               
               
job-info-attr-1 OBJECT-TYPE
    SYNTAX  OCTET STRING (SIZE(1..80))
    ACCESS  read-only
    STATUS  optional
    DESCRIPTION
                "Returns the value that was set in PJL via the SET
                JOBATTR= command.  Attribute objects are saved
                sequentially, starting with 1, after the start of a job.
                If more attributes are set than there are objects to
                store them, the excess JOBATTR values are ignored.  If
                the corresponding SET JOBATTR= command has not been
                received when a get is done for this object, a status of
                <noSuchName> will be returned."
::= { job-info-attribute 1 }
               
               
job-info-attr-2 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 2 }
               
               
job-info-attr-3 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 3 }
               
               
job-info-attr-4 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 4 }
               
               
job-info-attr-5 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 5 }
               
               
job-info-attr-6 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 6 }
               
               
job-info-attr-7 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 7 }
               
               
job-info-attr-8 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 8 }
               
               
job-info-attr-9 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 9 }
               
               
job-info-attr-10 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 10 }
               
               
job-info-attr-11 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 11 }
               
               
job-info-attr-12 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 12 }
               
               
job-info-attr-13 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 13 }
               
               
job-info-attr-14 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 14 }
               
               
job-info-attr-15 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 15 }
               
               
job-info-attr-16 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 16 }
               
               
job-info-attr-17 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 17 }
               
               
job-info-attr-18 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 18 }
               
               
job-info-attr-19 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 19 }
               
               
job-info-attr-20 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 20 }
               
               
job-info-attr-21 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 21 }
               
               
job-info-attr-22 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 22 }
               
               
job-info-attr-23 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 23 }
               
               
job-info-attr-24 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 24 }
               
               
job-info-attr-25 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 25 }
               
               
job-info-attr-26 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 26 }
               
               
job-info-attr-27 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 27 }
               
               
job-info-attr-28 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 28 }
               
               
job-info-attr-29 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 29 }
               
               
job-info-attr-30 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 30 }
               
               
job-info-attr-31 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 31 }
               
               
job-info-attr-32 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 32 }
               
               
error1-time-stamp OBJECT-TYPE
    SYNTAX  INTEGER
    ACCESS  read-only
    STATUS  optional
    DESCRIPTION
                "Contains a time stamp indicating when error 1
                occurred.  Example time stamps include the actual time
                the error occurred (in seconds since Jan. 1, 1970), and
                the total engine page count.  The device POS documents
                the meaning of the time stamp.
                Additional information:
                In LaserJet 5Si this item contains the engine  
                page count when the error occurred. A value of zero
                means 'no error'.  
                See ERROR1-CODE for an explanation of the order used 
                for storing errors."
::= { error1 1 }
               
               
error1-code OBJECT-TYPE
    SYNTAX  INTEGER
    ACCESS  read-only
    STATUS  optional
    DESCRIPTION
                "Contains a device specific error code.  Each device POS
                should list what errors are logged to the error log and
                the meaning of each supported error code value.
                Additional information:
                Contains a device specific error code.  A value 
                of zero means 'no error'. 
                
                The error number is returned in the upper 16 bits. 
                If it is 68,69,79, 
                or 80, then the sub code is returned in the lower 16 bits (eg. 68 0019, where 
                the subcode is already a hexadecimal value). 
                If the error number is any other number, then the 1st sub code (XX) 
                will be in bits 15-8 and the 2nd sub code (YY) will be in bits 7-0 (eg.
                55.04.02) where XX=04 and YY=02).  
                
                Example: If the error is 68 001A, then the value returned will be 4456474.  
                To break it down: 4456474 = 0x0044001A  
                The upper 16 bits: 0x0044 = 68  
                The lower 16 bits: 0x001A = 001A
                Which is the error: 68 001A  
                
                Example: If the error is 55.04.241, then the error code will be 3605745.  
                To break it down: 3605745 = 0x003704F1  
                The upper 16 bits: 0x0037 = 55  
                The upper byte of the lower 16 bits: 0x04 = 04  
                The lower byte of the lower 16 bits: 0xF1 = 241  
                Which is the error: 55.04.241  
                
                ERROR1- is the oldest error in the log. Errors are added until ERROR50- is 
                reached. If more errors occur, ERROR1- is replaced by moving all error entries 
                down one position and adding the newest error as ERROR50-"
::= { error1 2 }
               
               
error2-time-stamp OBJECT-TYPE
    SYNTAX  INTEGER
    ACCESS  read-only
    STATUS  optional
    DESCRIPTION
                "Contains a time stamp indicating when error 2
                occurred.  Example time stamps include the actual time
                the error occurred (in seconds since Jan. 1, 1970), and
                the total engine page count.  The device POS documents
                the meaning of the time stamp.
                Additional information:
                See ERROR1-TIME-STAMP."
::= { error2 1 }
               
               
error2-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error2 2 }
               
               
error3-time-stamp OBJECT-TYPE
    SYNTAX  INTEGER
    ACCESS  read-only
    STATUS  optional
    DESCRIPTION
                "Contains a time stamp indicating when error 3
                occurred.  Example time stamps include the actual time
                the error occurred (in seconds since Jan. 1, 1970), and
                the total engine page count.  The device POS documents
                the meaning of the time stamp.
                Additional information:
                See ERROR1-TIME-STAMP."
::= { error3 1 }
               
               
error3-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error3 2 }
               
               
error4-time-stamp OBJECT-TYPE
    SYNTAX  INTEGER
    ACCESS  read-only
    STATUS  optional
    DESCRIPTION
                "Contains a time stamp indicating when error 4
                occurred.  Example time stamps include the actual time
                the error occurred (in seconds since Jan. 1, 1970), and
                the total engine page count.  The device POS documents
                the meaning of the time stamp.
                Additional information:
                See ERROR1-TIME-STAMP."
::= { error4 1 }
               
               
error4-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error4 2 }
               
               
error5-time-stamp OBJECT-TYPE
    SYNTAX  INTEGER
    ACCESS  read-only
    STATUS  optional
    DESCRIPTION
                "Contains a time stamp indicating when error 5
                occurred.  Example time stamps include the actual time
                the error occurred (in seconds since Jan. 1, 1970), and
                the total engine page count.  The device POS documents
                the meaning of the time stamp.
                Additional information:
                See ERROR1-TIME-STAMP."
::= { error5 1 }
               
               
error5-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error5 2 }
               
               
error6-time-stamp OBJECT-TYPE
    SYNTAX  INTEGER
    ACCESS  read-only
    STATUS  optional
    DESCRIPTION
                "Contains a time stamp indicating when error 6
                occurred.  Example time stamps include the actual time
                the error occurred (in seconds since Jan. 1, 1970), and
                the total engine page count.  The device POS documents
                the meaning of the time stamp.
                Additional information:
                See ERROR1-TIME-STAMP."
::= { error6 1 }
               
               
error6-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error6 2 }
               
               
error7-time-stamp OBJECT-TYPE
    SYNTAX  INTEGER
    ACCESS  read-only
    STATUS  optional
    DESCRIPTION
                "Contains a time stamp indicating when error 7
                occurred.  Example time stamps include the actual time
                the error occurred (in seconds since Jan. 1, 1970), and
                the total engine page count.  The device POS documents
                the meaning of the time stamp.
                Additional information:
                See ERROR1-TIME-STAMP."
::= { error7 1 }
               
               
error7-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error7 2 }
               
               
error8-time-stamp OBJECT-TYPE
    SYNTAX  INTEGER
    ACCESS  read-only
    STATUS  optional
    DESCRIPTION
                "Contains a time stamp indicating when error 8
                occurred.  Example time stamps include the actual time
                the error occurred (in seconds since Jan. 1, 1970), and
                the total engine page count.  The device POS documents
                the meaning of the time stamp.
                Additional information:
                See ERROR1-TIME-STAMP."
::= { error8 1 }
               
               
error8-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error8 2 }
               
               
error9-time-stamp OBJECT-TYPE
    SYNTAX  INTEGER
    ACCESS  read-only
    STATUS  optional
    DESCRIPTION
                "Contains a time stamp indicating when error 9
                occurred.  Example time stamps include the actual time
                the error occurred (in seconds since Jan. 1, 1970), and
                the total engine page count.  The device POS documents
                the meaning of the time stamp.
                Additional information:
                See ERROR1-TIME-STAMP."
::= { error9 1 }
               
               
error9-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error9 2 }
               
               
error10-time-stamp OBJECT-TYPE
    SYNTAX  INTEGER
    ACCESS  read-only
    STATUS  optional
    DESCRIPTION
                "Contains a time stamp indicating when error
                10 occurred.  Example time stamps include the actual
                time the error occurred (in seconds since Jan. 1, 1970),
                and the total engine page count.  The device POS
                documents the meaning of the time stamp.
                Additional information:
                See ERROR1-TIME-STAMP."
::= { error10 1 }
               
               
error10-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error10 2 }
               
               
error11-time-stamp OBJECT-TYPE
    SYNTAX  INTEGER
    ACCESS  read-only
    STATUS  optional
    DESCRIPTION
                "Contains a time stamp indicating when error
                11 occurred.  Example time stamps include the actual
                time the error occurred (in seconds since Jan. 1, 1970),
                and the total engine page count.  The device POS
                documents the meaning of the time stamp.
                Additional information:
                See ERROR1-TIME-STAMP."
::= { error11 1 }
               
               
error11-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error11 2 }
               
               
error12-time-stamp OBJECT-TYPE
    SYNTAX  INTEGER
    ACCESS  read-only
    STATUS  optional
    DESCRIPTION
                "Contains a time stamp indicating when error
                12 occurred.  Example time stamps include the actual
                time the error occurred (in seconds since Jan. 1, 1970),
                and the total engine page count.  The device POS
                documents the meaning of the time stamp.
                Additional information:
                See ERROR1-TIME-STAMP."
::= { error12 1 }
               
               
error12-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error12 2 }
               
               
error13-time-stamp OBJECT-TYPE
    SYNTAX  INTEGER
    ACCESS  read-only
    STATUS  optional
    DESCRIPTION
                "Contains a time stamp indicating when error
                13 occurred.  Example time stamps include the actual
                time the error occurred (in seconds since Jan. 1, 1970),
                and the total engine page count.  The device POS
                documents the meaning of the time stamp.
                Additional information:
                See ERROR1-TIME-STAMP."
::= { error13 1 }
               
               
error13-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error13 2 }
               
               
error14-time-stamp OBJECT-TYPE
    SYNTAX  INTEGER
    ACCESS  read-only
    STATUS  optional
    DESCRIPTION
                "Contains a time stamp indicating when error
                14 occurred.  Example time stamps include the actual
                time the error occurred (in seconds since Jan. 1, 1970),
                and the total engine page count.  The device POS
                documents the meaning of the time stamp.
                Additional information:
                See ERROR1-TIME-STAMP."
::= { error14 1 }
               
               
error14-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error14 2 }
               
               
error15-time-stamp OBJECT-TYPE
    SYNTAX  INTEGER
    ACCESS  read-only
    STATUS  optional
    DESCRIPTION
                "Contains a time stamp indicating when error
                15 occurred.  Example time stamps include the actual
                time the error occurred (in seconds since Jan. 1, 1970),
                and the total engine page count.  The device POS
                documents the meaning of the time stamp.
                Additional information:
                See ERROR1-TIME-STAMP."
::= { error15 1 }
               
               
error15-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error15 2 }
               
               
error16-time-stamp OBJECT-TYPE
    SYNTAX  INTEGER
    ACCESS  read-only
    STATUS  optional
    DESCRIPTION
                "Contains a time stamp indicating when error
                16 occurred.  Example time stamps include the actual
                time the error occurred (in seconds since Jan. 1, 1970),
                and the total engine page count.  The device POS
                documents the meaning of the time stamp.
                Additional information:
                See ERROR1-TIME-STAMP."
::= { error16 1 }
               
               
error16-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error16 2 }
               
               
error17-time-stamp OBJECT-TYPE
    SYNTAX  INTEGER
    ACCESS  read-only
    STATUS  optional
    DESCRIPTION
                "Contains a time stamp indicating when error
                17 occurred.  Example time stamps include the actual
                time the error occurred (in seconds since Jan. 1, 1970),
                and the total engine page count.  The device POS
                documents the meaning of the time stamp.
                Additional information:
                See ERROR1-TIME-STAMP."
::= { error17 1 }
               
               
error17-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error17 2 }
               
               
error18-time-stamp OBJECT-TYPE
    SYNTAX  INTEGER
    ACCESS  read-only
    STATUS  optional
    DESCRIPTION
                "Contains a time stamp indicating when error
                18 occurred.  Example time stamps include the actual
                time the error occurred (in seconds since Jan. 1, 1970),
                and the total engine page count.  The device POS
                documents the meaning of the time stamp.
                Additional information:
                See ERROR1-TIME-STAMP."
::= { error18 1 }
               
               
error18-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error18 2 }
               
               
error19-time-stamp OBJECT-TYPE
    SYNTAX  INTEGER
    ACCESS  read-only
    STATUS  optional
    DESCRIPTION
                "Contains a time stamp indicating when error
                19 occurred.  Example time stamps include the actual
                time the error occurred (in seconds since Jan. 1, 1970),
                and the total engine page count.  The device POS
                documents the meaning of the time stamp.
                Additional information:
                See ERROR1-TIME-STAMP."
::= { error19 1 }
               
               
error19-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error19 2 }
               
               
error20-time-stamp OBJECT-TYPE
    SYNTAX  INTEGER
    ACCESS  read-only
    STATUS  optional
    DESCRIPTION
                "Contains a time stamp indicating when error
                20 occurred.  Example time stamps include the actual
                time the error occurred (in seconds since Jan. 1, 1970),
                and the total engine page count.  The device POS
                documents the meaning of the time stamp.
                Additional information:
                See ERROR1-TIME-STAMP."
::= { error20 1 }
               
               
error20-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error20 2 }
               
               
error21-time-stamp OBJECT-TYPE
    SYNTAX  INTEGER
    ACCESS  read-only
    STATUS  optional
    DESCRIPTION
                "Contains a time stamp indicating when error
                21 occurred.  Example time stamps include the actual
                time the error occurred (in seconds since Jan. 1, 1970),
                and the total engine page count.  The device POS
                documents the meaning of the time stamp.
                Additional information:
                See ERROR1-TIME-STAMP."
::= { error21 1 }
               
               
error21-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error21 2 }
               
               
error22-time-stamp OBJECT-TYPE
    SYNTAX  INTEGER
    ACCESS  read-only
    STATUS  optional
    DESCRIPTION
                "Contains a time stamp indicating when error
                22 occurred.  Example time stamps include the actual
                time the error occurred (in seconds since Jan. 1, 1970),
                and the total engine page count.  The device POS
                documents the meaning of the time stamp.
                Additional information:
                See ERROR1-TIME-STAMP."
::= { error22 1 }
               
               
error22-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error22 2 }
               
               
error23-time-stamp OBJECT-TYPE
    SYNTAX  INTEGER
    ACCESS  read-only
    STATUS  optional
    DESCRIPTION
                "Contains a time stamp indicating when error
                23 occurred.  Example time stamps include the actual
                time the error occurred (in seconds since Jan. 1, 1970),
                and the total engine page count.  The device POS
                documents the meaning of the time stamp.
                Additional information:
                See ERROR1-TIME-STAMP."
::= { error23 1 }
               
               
error23-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error23 2 }
               
               
error24-time-stamp OBJECT-TYPE
    SYNTAX  INTEGER
    ACCESS  read-only
    STATUS  optional
    DESCRIPTION
                "Contains a time stamp indicating when error
                24 occurred.  Example time stamps include the actual
                time the error occurred (in seconds since Jan. 1, 1970),
                and the total engine page count.  The device POS
                documents the meaning of the time stamp.
                Additional information:
                See ERROR1-TIME-STAMP."
::= { error24 1 }
               
               
error24-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error24 2 }
               
               
error25-time-stamp OBJECT-TYPE
    SYNTAX  INTEGER
    ACCESS  read-only
    STATUS  optional
    DESCRIPTION
                "Contains a time stamp indicating when error
                25 occurred.  Example time stamps include the actual
                time the error occurred (in seconds since Jan. 1, 1970),
                and the total engine page count.  The device POS
                documents the meaning of the time stamp.
                Additional information:
                See ERROR1-TIME-STAMP."
::= { error25 1 }
               
               
error25-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error25 2 }
               
               
error26-time-stamp OBJECT-TYPE
    SYNTAX  INTEGER
    ACCESS  read-only
    STATUS  optional
    DESCRIPTION
                "Contains a time stamp indicating when error
                26 occurred.  Example time stamps include the actual
                time the error occurred (in seconds since Jan. 1, 1970),
                and the total engine page count.  The device POS
                documents the meaning of the time stamp.
                Additional information:
                See ERROR1-TIME-STAMP."
::= { error26 1 }
               
               
error26-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error26 2 }
               
               
error27-time-stamp OBJECT-TYPE
    SYNTAX  INTEGER
    ACCESS  read-only
    STATUS  optional
    DESCRIPTION
                "Contains a time stamp indicating when error
                27 occurred.  Example time stamps include the actual
                time the error occurred (in seconds since Jan. 1, 1970),
                and the total engine page count.  The device POS
                documents the meaning of the time stamp.
                Additional information:
                See ERROR1-TIME-STAMP."
::= { error27 1 }
               
               
error27-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error27 2 }
               
               
error28-time-stamp OBJECT-TYPE
    SYNTAX  INTEGER
    ACCESS  read-only
    STATUS  optional
    DESCRIPTION
                "Contains a time stamp indicating when error
                28 occurred.  Example time stamps include the actual
                time the error occurred (in seconds since Jan. 1, 1970),
                and the total engine page count.  The device POS
                documents the meaning of the time stamp.
                Additional information:
                See ERROR1-TIME-STAMP."
::= { error28 1 }
               
               
error28-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error28 2 }
               
               
error29-time-stamp OBJECT-TYPE
    SYNTAX  INTEGER
    ACCESS  read-only
    STATUS  optional
    DESCRIPTION
                "Contains a time stamp indicating when error
                29 occurred.  Example time stamps include the actual
                time the error occurred (in seconds since Jan. 1, 1970),
                and the total engine page count.  The device POS
                documents the meaning of the time stamp.
                Additional information:
                See ERROR1-TIME-STAMP."
::= { error29 1 }
               
               
error29-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error29 2 }
               
               
error30-time-stamp OBJECT-TYPE
    SYNTAX  INTEGER
    ACCESS  read-only
    STATUS  optional
    DESCRIPTION
                "Contains a time stamp indicating when error
                30 occurred.  Example time stamps include the actual
                time the error occurred (in seconds since Jan. 1, 1970),
                and the total engine page count.  The device POS
                documents the meaning of the time stamp.
                Additional information:
                See ERROR1-TIME-STAMP."
::= { error30 1 }
               
               
error30-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error30 2 }
               
               
error31-time-stamp OBJECT-TYPE
    SYNTAX  INTEGER
    ACCESS  read-only
    STATUS  optional
    DESCRIPTION
                "Contains a time stamp indicating when error
                31 occurred.  Example time stamps include the actual
                time the error occurred (in seconds since Jan. 1, 1970),
                and the total engine page count.  The device POS
                documents the meaning of the time stamp.
                Additional information:
                See ERROR1-TIME-STAMP."
::= { error31 1 }
               
               
error31-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error31 2 }
               
               
error32-time-stamp OBJECT-TYPE
    SYNTAX  INTEGER
    ACCESS  read-only
    STATUS  optional
    DESCRIPTION
                "Contains a time stamp indicating when error
                32 occurred.  Example time stamps include the actual
                time the error occurred (in seconds since Jan. 1, 1970),
                and the total engine page count.  The device POS
                documents the meaning of the time stamp.
                Additional information:
                See ERROR1-TIME-STAMP."
::= { error32 1 }
               
               
error32-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error32 2 }
               
               
error33-time-stamp OBJECT-TYPE
    SYNTAX  INTEGER
    ACCESS  read-only
    STATUS  optional
    DESCRIPTION
                "Contains a time stamp indicating when error
                33 occurred.  Example time stamps include the actual
                time the error occurred (in seconds since Jan. 1, 1970),
                and the total engine page count.  The device POS
                documents the meaning of the time stamp.
                Additional information:
                See ERROR1-TIME-STAMP."
::= { error33 1 }
               
               
error33-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error33 2 }
               
               
error34-time-stamp OBJECT-TYPE
    SYNTAX  INTEGER
    ACCESS  read-only
    STATUS  optional
    DESCRIPTION
                "Contains a time stamp indicating when error
                34 occurred.  Example time stamps include the actual
                time the error occurred (in seconds since Jan. 1, 1970),
                and the total engine page count.  The device POS
                documents the meaning of the time stamp.
                Additional information:
                See ERROR1-TIME-STAMP."
::= { error34 1 }
               
               
error34-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error34 2 }
               
               
error35-time-stamp OBJECT-TYPE
    SYNTAX  INTEGER
    ACCESS  read-only
    STATUS  optional
    DESCRIPTION
                "Contains a time stamp indicating when error
                35 occurred.  Example time stamps include the actual
                time the error occurred (in seconds since Jan. 1, 1970),
                and the total engine page count.  The device POS
                documents the meaning of the time stamp.
                Additional information:
                See ERROR1-TIME-STAMP."
::= { error35 1 }
               
               
error35-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error35 2 }
               
               
error36-time-stamp OBJECT-TYPE
    SYNTAX  INTEGER
    ACCESS  read-only
    STATUS  optional
    DESCRIPTION
                "Contains a time stamp indicating when error
                36 occurred.  Example time stamps include the actual
                time the error occurred (in seconds since Jan. 1, 1970),
                and the total engine page count.  The device POS
                documents the meaning of the time stamp.
                Additional information:
                See ERROR1-TIME-STAMP."
::= { error36 1 }
               
               
error36-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error36 2 }
               
               
error37-time-stamp OBJECT-TYPE
    SYNTAX  INTEGER
    ACCESS  read-only
    STATUS  optional
    DESCRIPTION
                "Contains a time stamp indicating when error
                37 occurred.  Example time stamps include the actual
                time the error occurred (in seconds since Jan. 1, 1970),
                and the total engine page count.  The device POS
                documents the meaning of the time stamp.
                Additional information:
                See ERROR1-TIME-STAMP."
::= { error37 1 }
               
               
error37-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error37 2 }
               
               
error38-time-stamp OBJECT-TYPE
    SYNTAX  INTEGER
    ACCESS  read-only
    STATUS  optional
    DESCRIPTION
                "Contains a time stamp indicating when error
                38 occurred.  Example time stamps include the actual
                time the error occurred (in seconds since Jan. 1, 1970),
                and the total engine page count.  The device POS
                documents the meaning of the time stamp.
                Additional information:
                See ERROR1-TIME-STAMP."
::= { error38 1 }
               
               
error38-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error38 2 }
               
               
error39-time-stamp OBJECT-TYPE
    SYNTAX  INTEGER
    ACCESS  read-only
    STATUS  optional
    DESCRIPTION
                "Contains a time stamp indicating when error
                39 occurred.  Example time stamps include the actual
                time the error occurred (in seconds since Jan. 1, 1970),
                and the total engine page count.  The device POS
                documents the meaning of the time stamp.
                Additional information:
                See ERROR1-TIME-STAMP."
::= { error39 1 }
               
               
error39-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error39 2 }
               
               
error40-time-stamp OBJECT-TYPE
    SYNTAX  INTEGER
    ACCESS  read-only
    STATUS  optional
    DESCRIPTION
                "Contains a time stamp indicating when error
                40 occurred.  Example time stamps include the actual
                time the error occurred (in seconds since Jan. 1, 1970),
                and the total engine page count.  The device POS
                documents the meaning of the time stamp.
                Additional information:
                See ERROR1-TIME-STAMP."
::= { error40 1 }
               
               
error40-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error40 2 }
               
               
error41-time-stamp OBJECT-TYPE
    SYNTAX  INTEGER
    ACCESS  read-only
    STATUS  optional
    DESCRIPTION
                "Contains a time stamp indicating when error
                41 occurred.  Example time stamps include the actual
                time the error occurred (in seconds since Jan. 1, 1970),
                and the total engine page count.  The device POS
                documents the meaning of the time stamp.
                Additional information:
                See ERROR1-TIME-STAMP."
::= { error41 1 }
               
               
error41-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error41 2 }
               
               
error42-time-stamp OBJECT-TYPE
    SYNTAX  INTEGER
    ACCESS  read-only
    STATUS  optional
    DESCRIPTION
                "Contains a time stamp indicating when error
                42 occurred.  Example time stamps include the actual
                time the error occurred (in seconds since Jan. 1, 1970),
                and the total engine page count.  The device POS
                documents the meaning of the time stamp.
                Additional information:
                See ERROR1-TIME-STAMP."
::= { error42 1 }
               
               
error42-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error42 2 }
               
               
error43-time-stamp OBJECT-TYPE
    SYNTAX  INTEGER
    ACCESS  read-only
    STATUS  optional
    DESCRIPTION
                "Contains a time stamp indicating when error
                43 occurred.  Example time stamps include the actual
                time the error occurred (in seconds since Jan. 1, 1970),
                and the total engine page count.  The device POS
                documents the meaning of the time stamp.
                Additional information:
                See ERROR1-TIME-STAMP."
::= { error43 1 }
               
               
error43-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error43 2 }
               
               
error44-time-stamp OBJECT-TYPE
    SYNTAX  INTEGER
    ACCESS  read-only
    STATUS  optional
    DESCRIPTION
                "Contains a time stamp indicating when error
                44 occurred.  Example time stamps include the actual
                time the error occurred (in seconds since Jan. 1, 1970),
                and the total engine page count.  The device POS
                documents the meaning of the time stamp.
                Additional information:
                See ERROR1-TIME-STAMP."
::= { error44 1 }
               
               
error44-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error44 2 }
               
               
error45-time-stamp OBJECT-TYPE
    SYNTAX  INTEGER
    ACCESS  read-only
    STATUS  optional
    DESCRIPTION
                "Contains a time stamp indicating when error
                45 occurred.  Example time stamps include the actual
                time the error occurred (in seconds since Jan. 1, 1970),
                and the total engine page count.  The device POS
                documents the meaning of the time stamp.
                Additional information:
                See ERROR1-TIME-STAMP."
::= { error45 1 }
               
               
error45-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error45 2 }
               
               
error46-time-stamp OBJECT-TYPE
    SYNTAX  INTEGER
    ACCESS  read-only
    STATUS  optional
    DESCRIPTION
                "Contains a time stamp indicating when error
                46 occurred.  Example time stamps include the actual
                time the error occurred (in seconds since Jan. 1, 1970),
                and the total engine page count.  The device POS
                documents the meaning of the time stamp.
                Additional information:
                See ERROR1-TIME-STAMP."
::= { error46 1 }
               
               
error46-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error46 2 }
               
               
error47-time-stamp OBJECT-TYPE
    SYNTAX  INTEGER
    ACCESS  read-only
    STATUS  optional
    DESCRIPTION
                "Contains a time stamp indicating when error
                47 occurred.  Example time stamps include the actual
                time the error occurred (in seconds since Jan. 1, 1970),
                and the total engine page count.  The device POS
                documents the meaning of the time stamp.
                Additional information:
                See ERROR1-TIME-STAMP."
::= { error47 1 }
               
               
error47-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error47 2 }
               
               
error48-time-stamp OBJECT-TYPE
    SYNTAX  INTEGER
    ACCESS  read-only
    STATUS  optional
    DESCRIPTION
                "Contains a time stamp indicating when error
                48 occurred.  Example time stamps include the actual
                time the error occurred (in seconds since Jan. 1, 1970),
                and the total engine page count.  The device POS
                documents the meaning of the time stamp.
                Additional information:
                See ERROR1-TIME-STAMP."
::= { error48 1 }
               
               
error48-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error48 2 }
               
               
error49-time-stamp OBJECT-TYPE
    SYNTAX  INTEGER
    ACCESS  read-only
    STATUS  optional
    DESCRIPTION
                "Contains a time stamp indicating when error
                49 occurred.  Example time stamps include the actual
                time the error occurred (in seconds since Jan. 1, 1970),
                and the total engine page count.  The device POS
                documents the meaning of the time stamp.
                Additional information:
                See ERROR1-TIME-STAMP."
::= { error49 1 }
               
               
error49-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error49 2 }
               
               
error50-time-stamp OBJECT-TYPE
    SYNTAX  INTEGER
    ACCESS  read-only
    STATUS  optional
    DESCRIPTION
                "Contains a time stamp indicating when error
                50 occurred.  Example time stamps include the actual
                time the error occurred (in seconds since Jan. 1, 1970),
                and the total engine page count.  The device POS
                documents the meaning of the time stamp.
                Additional information:
                See ERROR1-TIME-STAMP."
::= { error50 1 }
               
               
error50-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error50 2 }
               
               
io-timeout OBJECT-TYPE
    SYNTAX  INTEGER(5..300)
    ACCESS  read-write
    STATUS  optional
    DESCRIPTION
                "The amount of time, in seconds, to wait for more print
                job data to be received before an I/O timeout occurs.
                The I/O channel being timed is the I/O channel that
                received the data associated with the current print job.
                If an I/O timeout occurs, the PDL processing sub-system
                assumes all the data associated with the current print
                job has been received, and processes the end of job in
                an PDL specific manner.  The POS specifies the supported
                values.
                Additional information:
                If an I/O timeout occurs, the PDL processing 
                sub-system will consider it an end of job condition only if there is data from 
                another I/O subsystem waiting to be processed.  
                The supported values are 5 to 300 seconds. 
                Setting to a value outside the supported range returns 
                <badValue> status.  
                Although the Control Panel restricts the values that may be set, any value
                within the limits may be set by this object."
::= { settings-io 1 }
               
               
io-switch OBJECT-TYPE
    SYNTAX  INTEGER {
		   eYes(1)
		   }
    ACCESS  read-only
    STATUS  optional
    DESCRIPTION
                "Indicates if the device will switch between I/O channels
                when a job boundary is encountered and print job data is
                available on another I/O channel."
::= { settings-io 2 }
               
               
io-buffering OBJECT-TYPE
    SYNTAX  INTEGER {
		   eOff(1),
		   eOn(2),
		   eAuto(3)
		   }
    ACCESS  read-write
    STATUS  optional
    DESCRIPTION
                "Returns or controls the manner in which the device
                performs I/O data buffering.  I/O data buffering allows
                additional print job data to be buffered by the I/O sub-
                system in an effort to allow the computer sending the
                data to perform other tasks and to keep the PDL
                processing sub-system busy.  eOff, I/O buffering is
                disabled.  When eOn, I/O buffering is enabled and the
                IO-BUFFER-SIZE object controls the amount of memory set
                aside for I/O buffer.  When eAuto, I/O buffering is
                enabled and the I/O buffer size is determined
                automatically by the device and the IO-BUFFER-SIZE
                object is not used.
                Additional information:
                In a PCL-only printer, all values may be set at any 
                time.  
                
                When PostScript is installed and there is less than 
                12M of memory installed, setting this object to eOn or eAuto will cause 
                <badValue> to be returned.  
                
                When PostScript and a duplex unit are installed and there is less than 
                23M of memory installed, setting this object to eOn or eAuto will cause 
                <badValue> to be returned.  
                
                When PostScript and 12M (23M with duplex unit) or more are installed, all 
                values are valid, provided Resource Saving has not consumed the needed 
                memory."
::= { settings-io 5 }
               
               
io-buffer-size OBJECT-TYPE
    SYNTAX  INTEGER
    ACCESS  read-write
    STATUS  optional
    DESCRIPTION
                "Returns or configures the amount of memory, in bytes,
                dedicated to I/O print job data buffering.  Attempting
                to set to an unsupported value causes the device to use
                the closest supported value.  Each device POS should
                document the list of supported values.
                Additional information:
                When IO-BUFFERING is eOff, reading this object will 
                return a value of zero. Attempting to set this object when IO-BUFFERING is 
                eOff will cause a status of <genErr> to be 
                returned.  
                
                When IO-BUFFERING is eAuto, the printer determines the 
                value of this object. Attempting to set this object when IO-BUFFERING is eAuto 
                will cause a status of <genErr> to be returned. 
                Reading this object when 
                IO-BUFFERING is eAuto will return the value that is currently being used by 
                the printer; the value is based on the printer configuration and 
                is as follows:  
                PCL-only: If 4M installed, 10240; if >4M installed, 102400 for each 1M 
                over 4M.  
                PCL & PS: If <12M installed, eAuto cannot be set; if 12M installed, 10240; if 
                >12M installed, 102400 for each 1M over 12M.  
                PCL, PS & Duplex Unit: If <23M installed, eAuto cannot be set; if 23M 
                installed, 10240; if 
                >23M installed, 102400 for each 1M over 23M.  
                
                When IO-BUFFERING is eOn, the range of values supported by this object varies 
                depending on the printer's configuration. The minimum value is 10240; the 
                maximum value is the current value of this object plus the value of 
                MAXIMUM-IO-BUFFERING-MEMORY. Supported values are multiples of 10240 for 
                values less or equal to 97280 and multiples of 102400 for values greater than 
                97280. Setting to an unsupported value causes the printer to substitute the 
                nearest supported value and to return <noError> 
                status."
::= { settings-io 6 }
               
               
maximum-io-buffering-memory OBJECT-TYPE
    SYNTAX  INTEGER
    ACCESS  read-only
    STATUS  optional
    DESCRIPTION
                "Returns the maximum amount of additional memory, in
                bytes, that can be dedicated to buffering print job
                data.
                Additional information:
                Memory for I/O Buffering is allocated in increments of 
                102400 bytes. Therefore, for each 1M (1048576 bytes) of memory added to the 
                printer, 1024000 bytes are made available to resource saving (and I/O 
                buffering) and 24576 bytes are retained until an additional 102400 byte block 
                can be made available. The value reported by this object is always rounded 
                down to the nearest multiple of 102400.  
                
                The values listed below assume that IO-BUFFERING=eOff; if 
                IO-BUFFERING=eOn, the value returned by this object will be reduced by 
                the amount of memory used by the IO-BUFFERING object.  
                
                For a PCL-only printer, the value of this object is 
                102400 if 4M memory is installed or all the memory over 4M.  
                
                If PostScript is installed without a duplex unit, the value of this object is 
                as follows:  
                0K if <12M memory is installed.  
                102400 if 12M memory is installed.  
                All over 12M memory installed.  
                
                If PostScript is installed with a duplex unit, the value of this object is as 
                follows:  
                0K if <23M memory is installed.  
                102400 if 23M memory is installed.  
                All over 23M memory installed."
::= { settings-io 7 }
               
               
port1-parallel-speed OBJECT-TYPE
    SYNTAX  INTEGER {
		   eSlow(1),
		   eFast(2)
		   }
    ACCESS  read-write
    STATUS  optional
    DESCRIPTION
                "Returns or changes the maximum parallel I/O port speed,
                for port 1.  This object is only supported if this port
                is a parallel port.  An eSlow setting causes a 10 us
                busy pulse per received byte of data.  An eFast setting
                causes a 1.5 us busy pulse per received byte of data.
                In rare cases, setting this value to eFast can cause the
                parallel port to no longer transfer data reliably."
::= { port1 4 }
               
               
port1-parallel-bidirectionality OBJECT-TYPE
    SYNTAX  INTEGER {
		   eUnidirectional(1),
		   eBidirectional(2)
		   }
    ACCESS  read-write
    STATUS  optional
    DESCRIPTION
                "Returns or changes whether the parallel I/O port
                supports bidirectional communication for port 1.  This
                object is only supported if this port is a parallel
                port.
                Additional information:
                A get on this object returns the current mode 
                for the parallel port. Setting this object specifies whether or not 
                bidirectional communications will be allowed."
::= { port1 5 }
               
               
default-copies OBJECT-TYPE
    SYNTAX  INTEGER(1..999)
    ACCESS  read-write
    STATUS  optional
    DESCRIPTION
                "Returns or changes default copies.  Default copies is
                the default values used by the PDL to control the number
                of copies of each page in the print job that are
                printed.  The print job can override this value.  The
                list of supported values should be documented in the
                device POS.
                Additional information:
                 The supported values are 1 
                through 999. Setting to an unsupported value causes  
                the printer to substitute in a snap value  
                and to return  
                <noError> status.  
                The snap values are as follow:  
                <1 snaps to 1  
                >999 snaps to 999"
::= { settings-pdl 4 }
               
               
form-feed OBJECT-TYPE
    SYNTAX  INTEGER {
		   eInitiateAction(1)
		   }
    ACCESS  write-only
    STATUS  optional
    DESCRIPTION
                "Instructs the PDL processing sub-system to finishing
                processing the current page of the current job.  Form
                feed is also known as close page or eject page.  If the
                PDL processing sub-system is in a FORM-FEED-NEEDED
                state, this causes the device to flush or finish
                processing the current page of the current job.  If the
                device is not in the FORM-FEED-NEEDED state, an
                <genErr> will occur.
                Additional information:
                The  printer must be offline before attempting 
                to perform a form feed, otherwise a status 
                <genErr> will be returned."
::= { settings-pdl 5 }
               
               
resource-saving OBJECT-TYPE
    SYNTAX  INTEGER {
		   eOff(1),
		   eOn(2),
		   eAuto(3)
		   }
    ACCESS  read-write
    STATUS  optional
    DESCRIPTION
                "Returns or changes PDL resource saving.  Resource saving
                stores a PDL's permanent soft resources, like fonts,
                even when another PDL is active.  Resource saving is
                also called environment saving.  When eOff, resource
                saving is disabled.  When ON, resource saving is enabled
                and memory is set aside for each PDL based on that PDL's
                resource saving memory size object, to store that PDL's
                permanent soft resources.  When eAuto, resource saving
                is enabled and memory space for each installed PDL is
                determined automatically.  The device POS should
                document what values are legal when only one PDL is
                installed.
                Additional information:
                When PCL is the only PDL installed in 
                LaserJet 5Si, all resource saving memory is dedicated to 
                PCL so eOff is the only valid value.  Attempting to set this object to eAuto 
                or eOn with a PCL-only printer will result in a status of 
                <badValue> being returned.  
                
                When PostScript is installed and there is less than 
                13M of memory installed, the only valid value for this object is eOff. 
                Attempting to set this object to eOn or eAuto will cause 
                <badValue> to be returned.  
                
                When PostScript and a duplex unit are installed and there is less than 
                24M of memory installed, the only valid value for this object is eOff. 
                Attempting to set this object to eOn or eAuto will cause 
                <badValue> to be returned.  
                
                When PostScript and 13M (24M with duplex unit) or more are installed, all 
                values are valid, provided I/O Buffering has not consumed the needed 
                memory."
::= { settings-pdl 6 }
               
               
maximum-resource-saving-memory OBJECT-TYPE
    SYNTAX  INTEGER
    ACCESS  read-only
    STATUS  optional
    DESCRIPTION
                "Returns the maximum amount of additional memory, in
                bytes, that can be dedicated to holding PDL permanent
                soft resources.
                Additional information:
                The following numbers assume that IO-BUFFERING=eOff; 
                if IO-BUFFERING<>eOff, the following numbers will be reduced by the value of 
                IO-BUFFER-SIZE.  
                
                Memory for resource saving is allocated in increments of 102400 bytes. 
                Therefore, for each 1M (1048576 bytes) of memory added to the printer, 1024000 
                bytes are made available to resource saving (and I/O buffering) and 24576 
                bytes are retained until an additional 102400 byte block can be made 
                available. The value reported by this object is always rounded down to the 
                nearest multiple of 102400.
                
                For a PCL-only printer, the value of this object is zero (all resource saving 
                memory is dedicated to PCL).  
                
                If PostScript is installed without a duplex unit, the value of this object is 
                as follows:  
                Zero if <13M memory is installed.  
                1024000 if 13M memory is installed and RESOURCE-SAVING=eOff.  
                1024000 if 13M memory is installed and RESOURCE-SAVING=eOn (note that this 
                value will be reduced by the amount of memory allocated to 
                PCL-RESOURCE-SAVING-MEMORY-SIZE and POSTSCRIPT-RESOURCE-SAVING-MEMORY-SIZE).  
                204800 if 13M memory is installed and RESOURCE-SAVING=eAuto.  
                When RESOURCE-SAVING=eAuto, 204800 bytes of each 1M over 13M memory installed 
                are allocated to PCL and PostScript (102400 each) with the remaining bytes 
                added to this object.  
                When RESOURCE-SAVING=eOn or eOff, all bytes over 13M memory installed are 
                added to this object.  
                
                If PostScript is installed with a duplex unit, the value of this object is as 
                follows:  
                Zero if <24M memory is installed.  
                1024000 if 24M memory is installed and RESOURCE-SAVING=eOff.  
                1024000 if 24M memory is installed and RESOURCE-SAVING=eOn (note that this 
                value will be reduced by the amount of memory allocated to 
                PCL-RESOURCE-SAVING-MEMORY-SIZE and POSTSCRIPT-RESOURCE-SAVING-MEMORY-SIZE).  
                204800 if 24M memory is installed and RESOURCE-SAVING=eAuto.  
                When RESOURCE-SAVING=eAuto, 204800 bytes of each 1M over 24M memory installed 
                are allocated to PCL and PostScript (102400 each) with the remaining bytes 
                added to this object.  
                When RESOURCE-SAVING=eOn or eOff, all bytes over 24M memory installed are 
                added to this object.  
                
                The above listed values returned by this object will be reduced by the amount 
                of memory added to PCL-RESOURCE-SAVING-MEMORY-SIZE and 
                POSTSCRIPT-RESOURCE-SAVING-MEMORY-SIZE when RESOURCE-SAVING=eOn."
::= { settings-pdl 7 }
               
               
default-vertical-black-resolution OBJECT-TYPE
    SYNTAX  INTEGER
    ACCESS  read-write
    STATUS  optional
    DESCRIPTION
                "Returns or changes the value of the default vertical
                black resolution.  The units are dots per inch.
                Additional information:
                In LaserJet 5Si changing this OID also causes  
                DEFAULT-HORIZONTAL-BLACK RESOLUTION to change.   
                DEFAULT-HORIZONTAL-BLACK-RESOLUTION and 
                DEFAULT-VERTICAL-BLACK-RESOLUTION must always be the  
                same.  The supported values are 300 and 600.   
                Setting to an unsupported value causes the printer 
                to substitute in a snap value and  
                to return <noError> status.  
                The snap values are as follow:  
                <450 snap to 300  
                >=450 snap to 600"
::= { settings-pdl 8 }
               
               
default-horizontal-black-resolution OBJECT-TYPE
    SYNTAX  INTEGER
    ACCESS  read-write
    STATUS  optional
    DESCRIPTION
                "Returns or changes the value of the default horizontal
                black resolution.  The units are dots per inch.
                Additional information:
                In LaserJet 5Si changing this OID also causes  
                DEFAULT- VERTICAL-BLACK RESOLUTION to change.   
                DEFAULT- HORIZONTAL-BLACK-RESOLUTION and 
                DEFAULT-VERTICAL-BLACK-RESOLUTION must always be the  
                same.  The supported values are 300 and 600. 
                Setting to an unsupported value causes the printer 
                to substitute in a snap value and to 
                return <noError> status.  
                The snap values are as follow:  
                <450 snap to 300  
                >=450 snap to 600"
::= { settings-pdl 9 }
               
               
default-page-protect OBJECT-TYPE
    SYNTAX  INTEGER {
		   eOn(2),
		   eAuto(3)
		   }
    ACCESS  read-write
    STATUS  optional
    DESCRIPTION
                "Returns or changes the default page protection behavior.
                If eOff, the device does not reserve memory for holding
                the entire raster form of a processed page.  If eOn,
                then memory is reserved.  If eAuto, the device
                determines the amount of memory to reserve.
                Additional information:
                Setting to eOn causes MET to be more conservative, but 
                it will not allocate memory to hold an entire 
                rasterized page."
::= { settings-pdl 10 }
               
               
default-lines-per-page OBJECT-TYPE
    SYNTAX  INTEGER
    ACCESS  read-write
    STATUS  optional
    DESCRIPTION
                "Returns or changes the default number of lines per page.
                The POS indicates the supported values.  An unsupported
                value causes the printer to use the closest supported
                value, causing the printer to return the
                <noError>.
                Additional information:
                The supported values in LaserJet 5Si are 5 to 128. 
                Setting to an unsupported value causes the  
                the printer to substitute in a snap value and to return 
                <noError> 
                status.  
                The snap values are as follow:  
                <5 snaps to 5  
                >128 snaps to 128"
::= { settings-pdl 11 }
               
               
default-vmi OBJECT-TYPE
    SYNTAX  INTEGER
    ACCESS  read-write
    STATUS  optional
    DESCRIPTION
                "Returns or changes the default vertical motion index.
                The unit of measure for VMI is centipoints per line.
                The POS indicates the supported values.  An unsupported
                value causes the printer to use the closest supported
                value, causing the printer to return
                <noError>."
::= { settings-pdl 12 }
               
               
default-media-size OBJECT-TYPE
    SYNTAX  INTEGER {
		   eUSExecutive(1),
		   eUSLetter(2),
		   eUSLegal(3),
		   eLedger(11),
		   eISOandJISA4(26),
		   eISOandJISA3(27),
		   eJISB5(45),
		   eJISB4(46),
		   eJapanesePostcardDouble(72),
		   eMonarch(80),
		   eCommercial10(81),
		   eInternationalDL(90),
		   eInternationalC5(91),
		   eInternationalB5(100),
		   eCustom(101)
		   }
    ACCESS  read-write
    STATUS  optional
    DESCRIPTION
                "This indicates the default media size.  A write of an
                unsupported value cases an <badValue>.
  Complete list of supported media sizes along
                with their dimensions are listed in the ''Media Size
                Table'' near the end of this document."
::= { settings-pdl 13 }
               
               
cold-reset-media-size OBJECT-TYPE
    SYNTAX  INTEGER {
		   eUSLetter(2),
		   eISOandJISA4(26)
		   }
    ACCESS  read-write
    STATUS  optional
    DESCRIPTION
                "Returns or sets the media size that is used as the
                DEFAULT-MEDIA-SIZE when a cold reset occurs."
::= { settings-pdl 19 }
               
               
default-media-name OBJECT-TYPE
    SYNTAX  DisplayString
    ACCESS  read-write
    STATUS  optional
    DESCRIPTION
                "Returns or sets the media name that is used until the
                media name is changed by a print job command.
                Additional information:
                This string must be one of the
                MEDIAn-NAME objects."
::= { settings-pdl 22 }
               
               
form-feed-needed OBJECT-TYPE
    SYNTAX  INTEGER {
		   eFalse(1),
		   eTrue(2)
		   }
    ACCESS  read-only
    STATUS  optional
    DESCRIPTION
                "Indicates if the PDL processing sub-system has made
                marks on the current page and the source subsystem has
                been idle for a device specific amount of time.
                Additional information:
                LaserJet 5Si will set this object to eTrue when a 
                personality has made marks on the current page, the personality timeout has 
                expired and no data is pending on another I/O. Once it is set to eTrue, more 
                data on the same I/O will cause this object to be set to eFalse, until the 
                above conditions are met again."
::= { status-pdl 2 }
               
               
pcl-resource-saving-memory-size OBJECT-TYPE
    SYNTAX  INTEGER
    ACCESS  read-write
    STATUS  optional
    DESCRIPTION
                "Returns or changes the amount of resource saving memory
                set aside to hold permanent soft PCL resources.
                Additional information:
                The value returned by this object is the amount of 
                Resource Saving memory currently dedicated to PCL, regardless of the value of 
                RESOURCE-SAVING.  
                
                For a PCL-only printer, the value of this object is zero. All memory is 
                dedicated to PCL, but it is not shown as such.  
                
                If PostScript is installed without a duplex unit, the default value of this 
                object is as follows:  
                Zero if <13M memory is installed.  
                Zero if 13M memory is installed and RESOURCE-SAVING=eOff.  
                409600 if 13M memory is installed and RESOURCE-SAVING=eOn.  
                409600 if 13M memory is installed and RESOURCE-SAVING=eAuto; plus 102400 for 
                each 1M over 13M memory installed.  
                
                If PostScript is installed with a duplex unit, the default value of this 
                object is as follows:  
                Zero if <24M memory is installed.  
                Zero if 24M memory is installed and RESOURCE-SAVING=eOff.  
                409600 if 24M memory is installed and RESOURCE-SAVING=eOn.  
                409600 if 24M memory is installed and RESOURCE-SAVING=eAuto; plus 102400 for 
                each 1M over 24M memory installed.  
                
                If RESOURCE-SAVING=eOn, this object can be used to set the amount of Resource 
                Saving memory currently dedicated to PCL. The values supported are zero (to 
                turn resource saving off for PCL) and 409600 through 409600 plus the value of 
                MAXIMUM-RESOURCE-SAVING-MEMORY, in increments of 102400. 
                If a value is received that is between 1 and 409599, it will be snapped to 
                409600 and a status of <noError> returned. 
                If an unsupported value greater than 409600 is received,
                it will be snapped down to the nearest 102400 value 
                and a status of <noError> returned.  
                
                Attempting to set this object when RESOURCE-SAVING 
                is eAuto or eOff will cause a status of <genErr> to 
                be returned."
::= { pdl-pcl 2 }
               
               
pcl-total-page-count OBJECT-TYPE
    SYNTAX  INTEGER
    ACCESS  read-only
    STATUS  optional
    DESCRIPTION
                "Total number of PCL pages printed by the device.
                Additional information:
                In LaserJet 5Si the PCL page count is kept in
                NVRAM however the NVRAM value is only updated every 10
                pages.  NOTE: The value returned by this OID will be
                incremented every page but if power is lost between
                NVRAM updates, up to 9 pages of the page count may be
                lost.  The page count counter will be reset to zero
                after 16,777,215 (2^24-1) pages.  
                The page count is incremented when a sheet of media is pulled from an input
                tray. A duplex printed sheet will cause this counter to be incremented by
                two."
::= { pdl-pcl 5 }
               
               
pcl-default-font-height OBJECT-TYPE
    SYNTAX  INTEGER
    ACCESS  read-write
    STATUS  optional
    DESCRIPTION
                "Returns or changes the default PCL height.  Height is an
                approximate measure of the body of the type in
                centipoints.  A centipoint is 1/7200 inch.  Height
                applies only to proportional fonts.  Point size, in
                points, can be converted to font height, in centipoints,
                by multiplying the point size by 100.  The POS indicates
                the supported values.  An unsupported value causes the
                printer to use the closest supported value, causing the
                printer to return <noError>.''Closest'' means the smallest absolute difference.
                Additional information:
                Setting to an unsupported value causes the 
                printer to 
                substitute in a snap value and to 
                return <noError> status.  
                The snap values are as follow:  
                <=400 snaps to 400  
                >=99975 snaps to 99975  
                Unsupported values in the range 400 to 99975 snaps  
                DOWN to the previous supported value 
                (i.e 25293 snaps to 25275 or 75038 snaps to 75025)."
::= { pdl-pcl 13 }
               
               
pcl-default-font-source OBJECT-TYPE
    SYNTAX  INTEGER {
		   eInternal(1),
		   ePermanentSoft(2),
		   eRomSimm1(10),
		   eRomSimm2(11),
		   eRomSimm3(12),
		   eRomSimm4(13)
		   }
    ACCESS  read-write
    STATUS  optional
    DESCRIPTION
                "Returns or changes the value of the default font source
                variable in NVRAM."
::= { pdl-pcl 14 }
               
               
pcl-default-font-number OBJECT-TYPE
    SYNTAX  INTEGER(0..52)
    ACCESS  read-write
    STATUS  optional
    DESCRIPTION
                "Returns or changes the value of the default font number
                variable in NVRAM.  Writing an unsupported value causes
                the printer to generate an
                <badValue>."
::= { pdl-pcl 15 }
               
               
pcl-default-font-width OBJECT-TYPE
    SYNTAX  INTEGER
    ACCESS  read-write
    STATUS  optional
    DESCRIPTION
                "Returns or changes the default PCL font width.  Width is
                expressed as the width of a character in centipoints.  A
                centipoint is 1/7200 inch.  Width applies only to fixed
                space fonts.  Pitch, in character per inch, can be
                converted to font width, in centipoints, by dividing
                7200 by the pitch.  The POS indicates the supported
                values.  An unsupported value causes the printer to use
                the closest supported value, causing the printer to
                return <noError>.  ''Closest''
                means the smallest absolute difference.
                Additional information:
                Setting to an unsupported value causes the 
                printer  
                to substitute in a snap value (listed below) and to  
                return <noError> status.  
                The snap values are as follow:  
                <=44 snaps to 44  
                >=9999 snaps to 9999"
::= { pdl-pcl 16 }
               
               
postscript-resource-saving-memory-size OBJECT-TYPE
    SYNTAX  INTEGER
    ACCESS  read-write
    STATUS  optional
    DESCRIPTION
                "Returns or changes the amount of resource saving memory
                set aside to hold permanent soft PostScript resources.
                Additional information:
                The value returned by this object is the amount of 
                Resource Saving memory currently dedicated to PostScript, regardless of the 
                value of RESOURCE-SAVING.  
                
                If PostScript is installed without a duplex unit, the default value of this 
                object is as follows:  
                Zero if <13M memory is installed.  
                Zero if 13M memory is installed and RESOURCE-SAVING=eOff.  
                409600 if 13M memory is installed and RESOURCE-SAVING=eOn.  
                409600 if 13M memory is installed and RESOURCE-SAVING=eAuto; plus 102400 for 
                each 1M over 13M memory installed.  
                
                If PostScript is installed with a duplex unit, the default value of this 
                object is as follows:  
                Zero if <24M memory is installed.  
                Zero if 24M memory is installed and RESOURCE-SAVING=eOff.  
                409600 if 24M memory is installed and RESOURCE-SAVING=eOn.  
                409600 if 24M memory is installed and RESOURCE-SAVING=eAuto; plus 102400 for 
                each 1M over 24M memory installed.  
                
                If RESOURCE-SAVING=eOn, this object can be used to set the amount of Resource 
                Saving memory currently dedicated to PostScript. The values supported are zero 
                (to turn resource saving off for PCL) and 409600 through 409600 plus 
                MAXIMUM-RESOURCE-SAVING-MEMORY, in increments of 102400. If a value is 
                received that is between 1 and 409599, it will be snapped to 
                409600 and a status of <noError> returned. 
                If an unsupported value greater than 409600 is received,
                it will be snapped down to the nearest 102400 value 
                and a status of <noError> returned.  
                
                
                Attempting to set this object when RESOURCE-SAVING 
                is eAuto or eOff will cause a status of <genErr> to 
                be returned."
::= { pdl-postscript 2 }
               
               
postscript-total-page-count OBJECT-TYPE
    SYNTAX  INTEGER
    ACCESS  read-only
    STATUS  optional
    DESCRIPTION
                "Total number of PostScript pages printed by the device.
                Additional information:
                This object is only supported if PostScript 
                option is installed.  
                In LaserJet 5Si the count is kept in 
                NVRAM however the NVRAM value is only updated every 10 
                sheets.  NOTE: The value returned by this OID will be 
                incremented every sheet but if power is lost between 
                NVRAM updates up to 9 sheets of the count may be 
                lost.  The counter will be reset to zero 
                after 16,777,215 (2^24-1) pages. "
::= { pdl-postscript 5 }
               
               
postscript-print-errors OBJECT-TYPE
    SYNTAX  INTEGER {
		   eOff(1),
		   eOn(2)
		   }
    ACCESS  read-write
    STATUS  optional
    DESCRIPTION
                "Returns or changes the value of the print PostScript
                errors setting.  If eOn, PostScript prints an error page
                showing the error encountered and the stack at the time
                of the error.
                Additional information:
                This object is only supported if PostScript  
                option is installed."
::= { pdl-postscript 11 }
               
               
postscript-jam-recovery OBJECT-TYPE
    SYNTAX  INTEGER {
		   eOff(1),
		   eOn(2)
		   }
    ACCESS  read-write
    STATUS  optional
    DESCRIPTION
                "Returns or changes the PostScript jam recovery setting.
                If eOn, then the device will reprint PostScript pages,
                if those pages jam.
                Additional information:
                This object is only supported if PostScript 
                option is installed."
::= { pdl-postscript 12 }
               
               
pjl-password OBJECT-TYPE
    SYNTAX  INTEGER
    ACCESS  read-only
    STATUS  optional
    DESCRIPTION
                "Returns PJL password, if the password is not set (zero).
                If the password is set, then attempting to retrieve the
                password causes an <genErr> to occur
                and will return the <NullValue>."
::= { pjl 1 }
               
               
override-media-name OBJECT-TYPE
    SYNTAX  DisplayString
    ACCESS  read-write
    STATUS  optional
    DESCRIPTION
                "Sets a string identifying the media name that is to be
                used in place of the currently requested media.  The
                substitution will continue until another media is
                selected.  If set to a named media that is not currently
                available the requested media is not overridden.
                Additional information:
                When a request is received to print on a size and 
                type of media that is not currently available, this object contains the 
                desired media name as set by the print job. This object should be set to a 
                media name that is currently available in the printer.  
                If a paper mount request is not 
                pending, attempting to get or set this object will cause 
                <noSuchName> to be returned.  
                Setting this object to a string other than one of the MEDIAn-NAME objects 
                (MEDIA-NAMES-AVAILABLE is applied) 
                will cause a status of <badValue> to be returned."
::= { settings-prt-eng 2 }
               
               
override-media-size OBJECT-TYPE
    SYNTAX  INTEGER {
		   eUSExecutive(1),
		   eUSLetter(2),
		   eUSLegal(3),
		   eLedger(11),
		   eISOandJISA4(26),
		   eISOandJISA3(27),
		   eJISB5(45),
		   eJISB4(46),
		   eJapanesePostcardDouble(72),
		   eMonarch(80),
		   eCommercial10(81),
		   eInternationalDL(90),
		   eInternationalC5(91),
		   eInternationalB5(100),
		   eCustom(101)
		   }
    ACCESS  read-write
    STATUS  optional
    DESCRIPTION
                "Sets the media size that is to be used in place of the
                currently requested media size.
                Additional information:
                When a request is received to print on a size and 
                type of media that is not currently available, this object contains the 
                desired size as set by the print job. This object should be set to a media 
                size that is currently available to the printer.  
                If a paper mount request is not 
                pending, attempting to get or set this object will cause 
                <noSuchName> to be returned."
::= { settings-prt-eng 3 }
               
               
print-density OBJECT-TYPE
    SYNTAX  INTEGER(1..5)
    ACCESS  read-write
    STATUS  optional
    DESCRIPTION
                "Returns or sets the print density setting.  Print
                density is the instantaneous amount of marking agent
                applied to the paper while printing.  A value of zero
                has the lowest print density, yielding a lighter page.
                A value of 10 has the highest print density, yielding a
                darker page.  Each POS should document what values in
                the 0 to 10 range are supported.
                Additional information:
                When this value is written, the page pipeline 
                will be flushed (all pages being printed are 
                completed, no new ones are started), the new density 
                setting is set and printing resumes. The actual change 
                in print density may be gradual over several pages.  
                The supported values are 1 
                through 5. Setting to an unsupported value causes 
                the printer to substitute in a snap value 
                and to return 
                <noError> status.  
                The snap values are as follow:  
                <1 snaps to 1  
                >5 snaps to 5"
::= { settings-prt-eng 5 }
               
               
duplex-page-count OBJECT-TYPE
    SYNTAX  INTEGER
    ACCESS  read-only
    STATUS  optional
    DESCRIPTION
                "Total number of sheets of media that have been duplex
                printed.  A sheet is counted if it travels through the
                duplex page path, regardless of whether or not marks are
                made on the page.  The POS will indicate if the value is
                kept in NVRAM.
                Additional information:
                In LaserJet 5Si the count is kept in 
                NVRAM however the NVRAM value is only updated every 10 
                sheets.  NOTE: The value returned by this OID will be 
                incremented every sheet but if power is lost between 
                NVRAM updates up to 9 sheets of the count may be 
                lost.  The counter will be reset to zero 
                after 16,777,215 (2^24-1) pages. "
::= { status-prt-eng 22 }
               
               
mp-tray OBJECT-TYPE
    SYNTAX  INTEGER {
		   eCassette(2)
		   }
    ACCESS  read-only
    STATUS  optional
    DESCRIPTION
                "Returns or changes the value of the multi-purpose (MP)
                tray configuration variable.  The MP tray can be
                configured to operate as an additional input tray
                (eCassette), a manual feed slot (eManual), or in a
                manner compatible with the LaserJet III manual feed slot
                (eFirst).  If configured for eFirst, if media is present
                in the MP tray, that media is used (assuming the size
                matches and the print job didn't specify another tray)
                until the MP tray is empty.
                Additional information:
                LaserJet 5Si supports a slightly modified version of 
                Cassette mode. The difference is that media will be pulled from Tray 1 (the 
                MP tray) if there is a sheet present and it matches the needed size and type."
::= { settings-intray 5 }
               
               
tray4-phd OBJECT-TYPE
    SYNTAX  INTEGER
    ACCESS  read-only
    STATUS  optional
    DESCRIPTION
                "Provides the number of the Paper Handling Device that
                contains this input tray."
::= { intray4 12 }
               
               
tray5-phd OBJECT-TYPE
    SYNTAX  INTEGER
    ACCESS  read-only
    STATUS  optional
    DESCRIPTION
                "Provides the number of the Paper Handling Device that
                contains this input tray."
::= { intray5 12 }
               
               
overflow-bin OBJECT-TYPE
    SYNTAX  INTEGER
    ACCESS  read-write
    STATUS  optional
    DESCRIPTION
                "Returns or sets the bin that will be used for additional
                sheets of media when the current bin is full and
                printing is allowed to continue.
                Additional information:
                If this object is set to zero, overflowing to another 
                bin is not allowed."
::= { settings-outbin 4 }
               
               
outbin1-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                If cCancelJob is set, the current print job will 
                be cancelled regardless of other item settings.  
                If cOutbinFullOverride is set and this bin is the designated overflow bin 
                (OVERFLOW-BIN = 1), then the bit is ignored.
                This object describes the action that is performed when the 
                JOB-OUTPUT-AUTO-CONTINUE-TIMEOUT expires. If no bits are set, no override 
                action is taken (the printer will continue to wait).  
                The action performed by the CONTINUE 
                object being set to eInitiateAction or the Select key being pressed on
                the control panel may cause different actions. 
                See CONTINUE object 
                description for information on the actions that occur for those conditions."
::= { outbin1 9 }
               
               
outbin3-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                If cCancelJob is set, the current print job will 
                be cancelled regardless of other item settings.   
                This object describes the action that is performed when the 
                JOB-OUTPUT-AUTO-CONTINUE-TIMEOUT expires. The action performed by the CONTINUE 
                object being set to eInitiateAction or the Select key being pressed on
                the control panel may cause different actions. 
                See CONTINUE object 
                description for information on the actions that occur for those conditions"
::= { outbin3 9 }
               
               
outbin3-phd OBJECT-TYPE
    SYNTAX  INTEGER
    ACCESS  read-only
    STATUS  optional
    DESCRIPTION
                "Provides the number of the Paper Handling Device that
                contains this output bin."
::= { outbin3 11 }
               
               
outbin4-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin4 9 }
               
               
outbin4-phd OBJECT-TYPE
    SYNTAX  INTEGER
    ACCESS  read-only
    STATUS  optional
    DESCRIPTION
                "Provides the number of the Paper Handling Device that
                contains this output bin."
::= { outbin4 11 }
               
               
outbin5-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin5 9 }
               
               
outbin5-phd OBJECT-TYPE
    SYNTAX  INTEGER
    ACCESS  read-only
    STATUS  optional
    DESCRIPTION
                "Provides the number of the Paper Handling Device that
                contains this output bin."
::= { outbin5 11 }
               
               
outbin6-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin6 9 }
               
               
outbin6-phd OBJECT-TYPE
    SYNTAX  INTEGER
    ACCESS  read-only
    STATUS  optional
    DESCRIPTION
                "Provides the number of the Paper Handling Device that
                contains this output bin."
::= { outbin6 11 }
               
               
outbin7-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin7 9 }
               
               
outbin7-phd OBJECT-TYPE
    SYNTAX  INTEGER
    ACCESS  read-only
    STATUS  optional
    DESCRIPTION
                "Provides the number of the Paper Handling Device that
                contains this output bin."
::= { outbin7 11 }
               
               
outbin8-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin8 9 }
               
               
outbin8-phd OBJECT-TYPE
    SYNTAX  INTEGER
    ACCESS  read-only
    STATUS  optional
    DESCRIPTION
                "Provides the number of the Paper Handling Device that
                contains this output bin."
::= { outbin8 11 }
               
               
outbin9-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin9 9 }
               
               
outbin9-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                This value indicates the maximum number of pages that   
                can be bound by the Outbin.  For LaserJet 5Si Mopier, the stapler can   
                bind/staple 20 sheets."
::= { outbin9 10 }
               
               
outbin9-phd OBJECT-TYPE
    SYNTAX  INTEGER
    ACCESS  read-only
    STATUS  optional
    DESCRIPTION
                "Provides the number of the Paper Handling Device that
                contains this output bin."
::= { outbin9 11 }
               

outbin10-override-mode OBJECT-TYPE
    SYNTAX  OCTET STRING  
    ACCESS  read-write
    STATUS  optional
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing.
                Additional information:
                See OUTBIN3-OVERRIDE-MODE."
::= { outbin10 9 }

       
outbin10-phd OBJECT-TYPE
    SYNTAX  INTEGER
    ACCESS  read-only
    STATUS  optional
    DESCRIPTION
                "Provides the number of the Paper Handling Device that
                contains this output bin."
::= { outbin10 11 }


outbin11-override-mode OBJECT-TYPE
    SYNTAX  OCTET STRING 
    ACCESS  read-write
    STATUS  optional
    DESCRIPTION
                "Returns or sets the device behavior when this output bin
                condition causes printing to stop.
                  cCancelJob - The device cancels the job.
                  cOutbinFullOverride - The device sends subsequent
                media to the overflow bin.
                  cOutbinAttentionOverride - The device ignores the
                attention condition and continues printing.
                  cBinderAttentionOverride - The device ignores the
                binder attention condition and continues printing. 
                Additional information:
                See OUTBIN9-OVERRIDE-MODE."
::= { outbin11 9 }        



outbin11-phd OBJECT-TYPE
    SYNTAX  INTEGER
    ACCESS  read-only
    STATUS  optional
    DESCRIPTION
                "Provides the number of the Paper Handling Device that
                contains this output bin."
::= { outbin11 11 }


low-marking-agent-processing OBJECT-TYPE
    SYNTAX  INTEGER {
		   eStop(1),
		   eCont(2)
		   }
    ACCESS  read-write
    STATUS  optional
    DESCRIPTION
                "Returns or changes how the device processes a low
                marking agent event.  If eCont, then the device
                continues to print.  If eStop, then the device stops
                until a continue event occurs."
::= { settings-marking-agent 3 }
               
               
default-ret OBJECT-TYPE
    SYNTAX  INTEGER {
		   eOff(1),
		   eLight(2),
		   eMedium(3),
		   eDark(4)
		   }
    ACCESS  read-write
    STATUS  optional
    DESCRIPTION
                "Returns or changes the Resolution Enhancement Technology
                setting.  Devices that only support eOff and on should
                map all other values to on and always return the same
                non-eOff value to indicate on.  The list of supported
                values should be documented in the device POS.
                Additional information:
                Setting this object to eLight or eDark will cause
                the object to be set to eMedium and a status of 
                <noError> will be returned."
::= { imaging 5 }
               
               
default-print-quality OBJECT-TYPE
    SYNTAX  INTEGER(0..100)
    ACCESS  read-write
    STATUS  optional
    DESCRIPTION
                "Returns or sets the default print quality.  A value of
                zero has the lowest print quality.  A value of 100 has
                the highest print quality.  Each POS should document
                what values in the 0 to 100 range are supported.
                Additional information:
                In LaserJet 5Si, the supported values are 0 
                and 100.  A value of zero corresponds to ECONOMODE=ON, 
                minimizing the toner 
                used.  A value of 100 corresponds to ECONOMODE=OFF. 
                Setting 
                to an unsupported value outside of the 0 to 100 range 
                causes the printer to return  
                <badValue> status.  Setting 
                to an unsupported value inside of the 0 to 100 range 
                causes the printer to substitute in a snap value  
                (listed below) and to return  
                <noError> status.  
                The snap values are as follow:  
                0 to 50 snap to 0  
                51 to 100 snap to 100"
::= { imaging 7 }
               
               
phd2-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> will
                be returned.  If the device accepts the command, it may
                still be processing the command after the response has
                been returned.  Depending on the device, the application
                may need to query PHDx-DEVICE-MEMORY to see when the
                command has completed.
                Additional information:
                The device-specific binary strings that may be sent to the
                paper handling device. For LaserJet 5Si Mopier PHD2, the data is meaningless."
::= { ph2 2 }
               
               
phd2-device-memory OBJECT-TYPE
    SYNTAX  OCTET STRING (SIZE(16))
    ACCESS  read-only
    STATUS  optional
    DESCRIPTION
                "This object is used to read the current values stored in
                shared memory available from the paper handling device.
                Additional information:
                This object returns the 16 bytes of NVRAM data that the 
                formatter saves for the paper handling device. For the HCI, 
                the data is meaningless."
::= { ph2 4 }
               
               
phd3-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> will
                be returned.  If the device accepts the command, it may
                still be processing the command after the response has
                been returned.  Depending on the device, the application
                may need to query PHDx-DEVICE-MEMORY to see when the
                command has completed.
                Additional information:
                For Tlatoani, the device-specific binary 
                strings that may be sent to the paper handling device are described 
                below.  
                The value returned in reponse to the set request is the HCO mode (note that 
                it is the current mode, which is not necessarily the same as the mode just 
                set). The format 
                of the response is the same as the command format, including the command 
                byte.  
                The general format of the binary string is: 
                <command> <option> <parameters>. The current HCO implementation does not 
                require any <parameters>.  
                
                BYTE 1 is Command {Valid value: 1 .. 2}  
                1 = Set HCO Mode  
                2 = Return HCO Mode  
                
                BYTE 2 is Set HCO Mode Option {Valid values: 1 .. 4}  
                1 = Stacker  
                2 = Separator  
                3 = Collator <<Not used for Tlatoani>>  
                4 = Mailbox  
                
                Mailbox 1 is the TOP mailbox.  
                
                
                Example for setting the mode:   
                
                BYTE number:  
                1  2    
                
                1  1  Set mode to Stacker.  
                
                1  2  Set mode to Separator.  
                
                1  4  Set mode to Mailbox.  
                
                Example for getting the current mode:   
                
                BYTE number:  
                1  2  
                
                2  0  Command to return the mode.  
                
                2  1  Current mode is Stacker.  
                
                2  2  Current mode is Separator.  
                
                2  4  Current mode is Mailbox."
::= { ph3 2 }
               
               
phd3-device-memory OBJECT-TYPE
    SYNTAX  OCTET STRING (SIZE(16))
    ACCESS  read-only
    STATUS  optional
    DESCRIPTION
                "This object is used to read the current values stored in
                shared memory available from the paper handling device.
                Additional information:
                This object returns the 16 bytes of NVRAM data that the 
                formatter saves for the paper handling device. For Tlatoani, 
                the data includes the current mode of the device. The format 
                is as follows:  
                Byte 1: Always 1  
                Byte 2: HCO Mode (see PHD3-DEVICE-SPECIFIC-COMMAND)  
                Byte 3: Sum of bytes 1 and 2"
::= { ph3 4 }
               
               
phd4-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> will
                be returned.  If the device accepts the command, it may
                still be processing the command after the response has
                been returned.  Depending on the device, the application
                may need to query PHDx-DEVICE-MEMORY to see when the
                command has completed.
                Additional information:
                The device-specific binary strings that may be sent to the
                paper handling device. "
::= { ph4 2 }
               
               
phd4-device-memory OBJECT-TYPE
    SYNTAX  OCTET STRING (SIZE(16))
    ACCESS  read-only
    STATUS  optional
    DESCRIPTION
                "This object is used to read the current values stored in
                shared memory available from the paper handling device.
                Additional information:
                This object returns the 16 bytes of NVRAM data that the 
                formatter saves for the paper handling device. For the STAPLER, 
                the data is meaningless."
::= { ph4 4 }
               
               
media-names-available OBJECT-TYPE
    SYNTAX  OCTET STRING
    ACCESS  read-write
    STATUS  optional
    DESCRIPTION
                "The value of this object controls which of the MEDIAx-
                NAME objects are supported.  If a bit is set to zero,
                then attempting to get or set the corresponding MEDIAx-
                NAME objects will return
                <noSuchName>.
                Additional information:
                Setting a bit to one will cause the corresponding
                MEDIAn- objects to be available (attempting to access an unavailable object 
                will return <noSuchName>).
                MEDIA1- objects are always present in LaserJet 5Si, as this is the default media. 
                If this object is 
                set to a value that does not include cMediaName1Available, that bit will be 
                set and a status of <noError> will be returned."
::= { settings-print-media 1 }
               
               
media1-name OBJECT-TYPE
    SYNTAX  DisplayString
    ACCESS  read-only
    STATUS  optional
    DESCRIPTION
                "Media 1 name.
                Additional information:
                The symbol set for this string is Roman-8."
::= { media1 1 }
               
               
media1-short-name OBJECT-TYPE
    SYNTAX  DisplayString
    ACCESS  read-only
    STATUS  optional
    DESCRIPTION
                "Length restricted version of the media name 1.  The
                length restriction is required to allow the media name
                to be displayed on the device's control panel.  The
                device POS must state the maximum number of characters
                allowed.  If the device also has a limitation on what
                characters in a character set can be used (e.g. only
                uppercase characters allowed), the POS should also state
                character restrictions."
::= { media1 2 }
               
               
media1-page-count OBJECT-TYPE
    SYNTAX  INTEGER
    ACCESS  read-only
    STATUS  optional
    DESCRIPTION
                "Number of sheets of media 1 that have been printed.  The
                device POS should state whether this value is lost
                across a power cycle or kept in NVRAM.
                Additional information:
                In LaserJet 5Si the media page count saved in NVRAM after every 10 
                pages. The maximum value is 4,294,967,295 which will never be reached in 
                normal operation.  
                The page count is incremented when a sheet of media is pulled from an input 
                tray. A duplex printed sheet will cause this counter to be incremented by 
                one."
::= { media1 3 }
               
               
media2-name OBJECT-TYPE
    SYNTAX  DisplayString
    ACCESS  read-only
    STATUS  optional
    DESCRIPTION
                "Media 2 name.
                Additional information:
                See MEDIA1-NAME."
::= { media2 1 }
               
               
media2-short-name OBJECT-TYPE
    SYNTAX  DisplayString
    ACCESS  read-only
    STATUS  optional
    DESCRIPTION
                "Length restricted version of the media name 2.  See
                MEDIA1-SHORT-NAME for details."
::= { media2 2 }
               
               
media2-page-count OBJECT-TYPE
    SYNTAX  INTEGER
    ACCESS  read-only
    STATUS  optional
    DESCRIPTION
                "Number of sheets of media 2 that have been printed.  See
                MEDIA1-PAGE-COUNT for details.
                Additional information:
                See MEDIA1-PAGE-COUNT."
::= { media2 3 }
               
               
media3-name OBJECT-TYPE
    SYNTAX  DisplayString
    ACCESS  read-only
    STATUS  optional
    DESCRIPTION
                "Media 3 name.
                Additional information:
                See MEDIA1-NAME."
::= { media3 1 }
               
               
media3-short-name OBJECT-TYPE
    SYNTAX  DisplayString
    ACCESS  read-only
    STATUS  optional
    DESCRIPTION
                "Length restricted version of the media name 3.  See
                MEDIA1-SHORT-NAME for details."
::= { media3 2 }
               
               
media3-page-count OBJECT-TYPE
    SYNTAX  INTEGER
    ACCESS  read-only
    STATUS  optional
    DESCRIPTION
                "Number of sheets of media 3 that have been printed.  See
                MEDIA1-PAGE-COUNT for details.
                Additional information:
                See MEDIA1-PAGE-COUNT."
::= { media3 3 }
               
               
media4-name OBJECT-TYPE
    SYNTAX  DisplayString
    ACCESS  read-only
    STATUS  optional
    DESCRIPTION
                "Media 4 name.
                Additional information:
                See MEDIA1-NAME."
::= { media4 1 }
               
               
media4-short-name OBJECT-TYPE
    SYNTAX  DisplayString
    ACCESS  read-only
    STATUS  optional
    DESCRIPTION
                "Length restricted version of the media name 4.  See
                MEDIA1-SHORT-NAME for details."
::= { media4 2 }
               
               
media4-page-count OBJECT-TYPE
    SYNTAX  INTEGER
    ACCESS  read-only
    STATUS  optional
    DESCRIPTION
                "Number of sheets of media 4 that have been printed.  See
                MEDIA1-PAGE-COUNT for details.
                Additional information:
                See MEDIA1-PAGE-COUNT."
::= { media4 3 }
               
               
media5-name OBJECT-TYPE
    SYNTAX  DisplayString
    ACCESS  read-only
    STATUS  optional
    DESCRIPTION
                "Media 5 name.
                Additional information:
                See MEDIA1-NAME."
::= { media5 1 }
               
               
media5-short-name OBJECT-TYPE
    SYNTAX  DisplayString
    ACCESS  read-only
    STATUS  optional
    DESCRIPTION
                "Length restricted version of the media name 5.  See
                MEDIA1-SHORT-NAME for details."
::= { media5 2 }
               
               
media5-page-count OBJECT-TYPE
    SYNTAX  INTEGER
    ACCESS  read-only
    STATUS  optional
    DESCRIPTION
                "Number of sheets of media 5 that have been printed.  See
                MEDIA1-PAGE-COUNT for details.
                Additional information:
                See MEDIA1-PAGE-COUNT."
::= { media5 3 }
               
               
media6-name OBJECT-TYPE
    SYNTAX  DisplayString
    ACCESS  read-only
    STATUS  optional
    DESCRIPTION
                "Media 6 name.
                Additional information:
                See MEDIA1-NAME."
::= { media6 1 }
               
               
media6-short-name OBJECT-TYPE
    SYNTAX  DisplayString
    ACCESS  read-only
    STATUS  optional
    DESCRIPTION
                "Length restricted version of the media name 6.  See
                MEDIA1-SHORT-NAME for details."
::= { media6 2 }
               
               
media6-page-count OBJECT-TYPE
    SYNTAX  INTEGER
    ACCESS  read-only
    STATUS  optional
    DESCRIPTION
                "Number of sheets of media 6 that have been printed.  See
                MEDIA1-PAGE-COUNT for details.
                Additional information:
                See MEDIA1-PAGE-COUNT."
::= { media6 3 }
               
               
media7-name OBJECT-TYPE
    SYNTAX  DisplayString
    ACCESS  read-only
    STATUS  optional
    DESCRIPTION
                "Media 7 name.
                Additional information:
                See MEDIA1-NAME."
::= { media7 1 }
               
               
media7-short-name OBJECT-TYPE
    SYNTAX  DisplayString
    ACCESS  read-only
    STATUS  optional
    DESCRIPTION
                "Length restricted version of the media name 7.  See
                MEDIA1-SHORT-NAME for details."
::= { media7 2 }
               
               
media7-page-count OBJECT-TYPE
    SYNTAX  INTEGER
    ACCESS  read-only
    STATUS  optional
    DESCRIPTION
                "Number of sheets of media 7 that have been printed.  See
                MEDIA1-PAGE-COUNT for details.
                Additional information:
                See MEDIA1-PAGE-COUNT."
::= { media7 3 }
               
               
media8-name OBJECT-TYPE
    SYNTAX  DisplayString
    ACCESS  read-only
    STATUS  optional
    DESCRIPTION
                "Media 8 name.
                Additional information:
                See MEDIA1-NAME."
::= { media8 1 }
               
               
media8-short-name OBJECT-TYPE
    SYNTAX  DisplayString
    ACCESS  read-only
    STATUS  optional
    DESCRIPTION
                "Length restricted version of the media name 8.  See
                MEDIA1-SHORT-NAME for details."
::= { media8 2 }
               
               
media8-page-count OBJECT-TYPE
    SYNTAX  INTEGER
    ACCESS  read-only
    STATUS  optional
    DESCRIPTION
                "Number of sheets of media 8 that have been printed.  See
                MEDIA1-PAGE-COUNT for details.
                Additional information:
                See MEDIA1-PAGE-COUNT."
::= { media8 3 }
               
               
media9-name OBJECT-TYPE
    SYNTAX  DisplayString
    ACCESS  read-only
    STATUS  optional
    DESCRIPTION
                "Media 9 name.
                Additional information:
                See MEDIA1-NAME."
::= { media9 1 }
               
               
media9-short-name OBJECT-TYPE
    SYNTAX  DisplayString
    ACCESS  read-only
    STATUS  optional
    DESCRIPTION
                "Length restricted version of the media name 9.  See
                MEDIA1-SHORT-NAME for details."
::= { media9 2 }
               
               
media9-page-count OBJECT-TYPE
    SYNTAX  INTEGER
    ACCESS  read-only
    STATUS  optional
    DESCRIPTION
                "Number of sheets of media 9 that have been printed.  See
                MEDIA1-PAGE-COUNT for details.
                Additional information:
                See MEDIA1-PAGE-COUNT."
::= { media9 3 }
               
               
media10-name OBJECT-TYPE
    SYNTAX  DisplayString
    ACCESS  read-only
    STATUS  optional
    DESCRIPTION
                "Media 10 name.
                Additional information:
                See MEDIA1-NAME."
::= { media10 1 }
               
               
media10-short-name OBJECT-TYPE
    SYNTAX  DisplayString
    ACCESS  read-only
    STATUS  optional
    DESCRIPTION
                "Length restricted version of the media name 10.  See
                MEDIA1-SHORT-NAME for details."
::= { media10 2 }
               
               
media10-page-count OBJECT-TYPE
    SYNTAX  INTEGER
    ACCESS  read-only
    STATUS  optional
    DESCRIPTION
                "Number of sheets of media 10 that have been printed.
                See MEDIA1-PAGE-COUNT for details.
                Additional information:
                See MEDIA1-PAGE-COUNT."
::= { media10 3 }
               
               
media11-name OBJECT-TYPE
    SYNTAX  DisplayString (SIZE(1..24))
    ACCESS  read-write
    STATUS  optional
    DESCRIPTION
                "Media 11 name.
                Additional information:
                The maximum supported string length is 24
                bytes.  If the user entered string is too long, 
                the device will store the first 24 bytes and 
                return the <noError> status. 
                See CAUTION statement under Product Specific Use."
::= { media11 1 }
               
               
media11-short-name OBJECT-TYPE
    SYNTAX  DisplayString (SIZE(1..10))
    ACCESS  read-write
    STATUS  optional
    DESCRIPTION
                "Length restricted version of the media name 11.  See
                MEDIA1-SHORT-NAME for details.
                Additional information:
                 The maximum supported string length is 10  
                characters.  If the user entered string is too long, 
                the device will store the first 10 characters and will 
                return the <noError> status.  
                The characters must be in the range 20H to 7FH except 5C cannot be used. The 
                default symbol set is Roman-8 for English; additional 
                legal symbol sets are ISOLatin5, ISOLatin2 and Windows31J. Setting this 
                object with characters outside of the range or an illegal symbol set will 
                cause an error status of <badValue> to be returned."
::= { media11 2 }
               
               
media11-page-count OBJECT-TYPE
    SYNTAX  INTEGER
    ACCESS  read-only
    STATUS  optional
    DESCRIPTION
                "Number of sheets of media 11 that have been printed.
                See MEDIA1-PAGE-COUNT for details.
                Additional information:
                See MEDIA1-PAGE-COUNT."
::= { media11 3 }
               
               
media12-name OBJECT-TYPE
    SYNTAX  DisplayString (SIZE(1..24))
    ACCESS  read-write
    STATUS  optional
    DESCRIPTION
                "Media 12 name.
                Additional information:
                See MEDIA11-NAME."
::= { media12 1 }
               
               
media12-short-name OBJECT-TYPE
    SYNTAX  DisplayString (SIZE(1..10))
    ACCESS  read-write
    STATUS  optional
    DESCRIPTION
                "Length restricted version of the media name 12.  See
                MEDIA1-SHORT-NAME for details.
                Additional information:
                See MEDIA11-SHORT-NAME."
::= { media12 2 }
               
               
media12-page-count OBJECT-TYPE
    SYNTAX  INTEGER
    ACCESS  read-only
    STATUS  optional
    DESCRIPTION
                "Number of sheets of media 12 that have been printed.
                See MEDIA1-PAGE-COUNT for details.
                Additional information:
                See MEDIA11-PAGE-COUNT."
::= { media12 3 }
               
               
media13-name OBJECT-TYPE
    SYNTAX  DisplayString (SIZE(1..24))
    ACCESS  read-write
    STATUS  optional
    DESCRIPTION
                "Media 13 name.
                Additional information:
                See MEDIA11-NAME."
::= { media13 1 }
               
               
media13-short-name OBJECT-TYPE
    SYNTAX  DisplayString (SIZE(1..10))
    ACCESS  read-write
    STATUS  optional
    DESCRIPTION
                "Length restricted version of the media name 13.  See
                MEDIA1-SHORT-NAME for details.
                Additional information:
                See MEDIA11-SHORT-NAME."
::= { media13 2 }
               
               
media13-page-count OBJECT-TYPE
    SYNTAX  INTEGER
    ACCESS  read-only
    STATUS  optional
    DESCRIPTION
                "Number of sheets of media 13 that have been printed.
                See MEDIA1-PAGE-COUNT for details.
                Additional information:
                See MEDIA11-PAGE-COUNT."
::= { media13 3 }
               
               
media14-name OBJECT-TYPE
    SYNTAX  DisplayString (SIZE(1..24))
    ACCESS  read-write
    STATUS  optional
    DESCRIPTION
                "Media 14 name.
                Additional information:
                See MEDIA11-NAME."
::= { media14 1 }
               
               
media14-short-name OBJECT-TYPE
    SYNTAX  DisplayString (SIZE(1..10))
    ACCESS  read-write
    STATUS  optional
    DESCRIPTION
                "Length restricted version of the media name 14.  See
                MEDIA1-SHORT-NAME for details.
                Additional information:
                See MEDIA11-SHORT-NAME."
::= { media14 2 }
               
               
media14-page-count OBJECT-TYPE
    SYNTAX  INTEGER
    ACCESS  read-only
    STATUS  optional
    DESCRIPTION
                "Number of sheets of media 14 that have been printed.
                See MEDIA1-PAGE-COUNT for details.
                Additional information:
                See MEDIA11-PAGE-COUNT."
::= { media14 3 }
               
               
media15-name OBJECT-TYPE
    SYNTAX  DisplayString (SIZE(1..24))
    ACCESS  read-write
    STATUS  optional
    DESCRIPTION
                "Media 15 name.
                Additional information:
                See MEDIA11-NAME."
::= { media15 1 }
               
               
media15-short-name OBJECT-TYPE
    SYNTAX  DisplayString (SIZE(1..10))
    ACCESS  read-write
    STATUS  optional
    DESCRIPTION
                "Length restricted version of the media name 15.  See
                MEDIA1-SHORT-NAME for details.
                Additional information:
                See MEDIA11-SHORT-NAME."
::= { media15 2 }
               
               
media15-page-count OBJECT-TYPE
    SYNTAX  INTEGER
    ACCESS  read-only
    STATUS  optional
    DESCRIPTION
                "Number of sheets of media 15 that have been printed.
                See MEDIA1-PAGE-COUNT for details.
                Additional information:
                See MEDIA11-PAGE-COUNT."
::= { media15 3 }
               
               
channel-bytes-sent OBJECT-TYPE
    SYNTAX  INTEGER
    ACCESS  read-only
    STATUS  optional
    DESCRIPTION
                "The low order 31 bits of the number of bytes sent from
                the printer to the host on this logical channel."
::= { channel-entry 2 }
               
               
channel-bytes-received OBJECT-TYPE
    SYNTAX  INTEGER
    ACCESS  read-only
    STATUS  optional
    DESCRIPTION
                "The low order 31 bits of the number of bytes received by
                the printer from the host on this logical channel."
::= { channel-entry 3 }
               
               
channel-io-errors OBJECT-TYPE
    SYNTAX  INTEGER
    ACCESS  read-only
    STATUS  optional
    DESCRIPTION
                "The low order 31 bits of the number of I/O errors which
                have occured on this logical channel."
::= { channel-entry 4 }
               
               
channel-jobs-received OBJECT-TYPE
    SYNTAX  INTEGER
    ACCESS  read-only
    STATUS  optional
    DESCRIPTION
                "The low order 31 bits of the number of print jobs which
                have been received on this logical channel."
::= { channel-entry 5 }
               
               
channel-mio OBJECT-TYPE
    SYNTAX  INTEGER
    ACCESS  read-only
    STATUS  optional
    DESCRIPTION
                "The number of the MIO card associated with this logical
                channel.  If this logical channel is not associated with
                an MIO card a zero is returned.  The value 1 is returned
                if this logical channel is associated with an MIO card
                in slot 1.  The value 2 is returned if this logical
                channel is associated with an MIO card in slot 2.
                Additional information:
                The value returned will be zero for channel one.  
                If an MIOA card is installed, channels 2..8 will 
                return a value of one or two and, 
                if an MIOB card is installed, 9-15 will return a 
                value of one or two, but not the same as channels 
                2..8. When two MIO cards are installed, the value 
                returned by any channel 2-15 may change after the 
                printer is power cycled."
::= { channel-entry 6 }
               
               
file-system-memory OBJECT-TYPE
    SYNTAX  INTEGER
    ACCESS  read-only
    STATUS  optional
    DESCRIPTION
                "The amount of memory, in bytes, used by the file system
                to buffer file data.
                Additional information:
                Reports the amount of memory, in bytes,
                reserved for use by the file system.  Returns
                <noSuchName> status if attempting
                to access this object and there is no storage device
                is installed."
::= { settings-file-system 1 }
               
               
file-system-max-open-files OBJECT-TYPE
    SYNTAX  INTEGER(32..512)
    ACCESS  read-write
    STATUS  optional
    DESCRIPTION
                "The number of open files allowed at one time. Opening a
                file when the maximum number of files are currently open
                will fail.
                Additional information:
                Indicates the number of open files a
                personality (e.g. PCL or PostScript) is guaranteed to be
                able to open before the file system runs out of file handles.
                After writing this object, the printer
                must be rebooted before the change takes effect.
                Performing a cold reset sets this object 
                back to the factory default value.  Returns 
                <noSuchName>
                status if attempting to access this object and there
                is no storage device is installed."
::= { settings-file-system 2 }
               
               
file-system-statistic-read-open OBJECT-TYPE
    SYNTAX  INTEGER
    ACCESS  read-only
    STATUS  optional
    DESCRIPTION
                "The number of times the file system has received
                requests to open a file for reading.  Opening a file for
                both reading and writing will cause this value to
                change.  The POS should state if a power cycle causes
                the counter is be reset to zero.
                Additional information:
                Reset to the factory default value after
                a power cycle.  
                Returns <noSuchName>
                status if attempting to access this object and there
                is no storage device is installed."
::= { status-file-system 1 }
               
               
file-system-statistic-write-open OBJECT-TYPE
    SYNTAX  INTEGER
    ACCESS  read-only
    STATUS  optional
    DESCRIPTION
                "The number of times the file system has received
                requests to open a file for writing.  Opening a file for
                both reading and writing will cause this value to
                change.  The POS should state if a power cycle causes
                the counter is be reset to zero.
                Additional information:
                Reset to the factory default value after
                a power cycle.  
                Returns <noSuchName>
                status if attempting to access this object and there
                is no storage device is installed."
::= { status-file-system 2 }
               
               
file-system-statistic-successful OBJECT-TYPE
    SYNTAX  INTEGER
    ACCESS  read-only
    STATUS  optional
    DESCRIPTION
                "A counter indicating the number of file system requests
                that completed successfully.  The POS should state if a
                power cycle causes the counter is be reset to zero.
                Additional information:
                Reset to the factory default value after
                a power cycle.  
                Returns <noSuchName>
                status if attempting to access this object and there
                is no storage device is installed."
::= { status-file-system 3 }
               
               
file-system-statistic-unsuccessful OBJECT-TYPE
    SYNTAX  INTEGER
    ACCESS  read-only
    STATUS  optional
    DESCRIPTION
                "A counter indicating the number of file system requests
                that completed unsuccessfully.  The POS should state if
                a power cycle causes the counter is be reset to zero.
                Additional information:
                Reset to the factory default value after
                a power cycle.  
                Returns <noSuchName>
                status if attempting to access this object and there
                is no storage device is installed."
::= { status-file-system 4 }
               
               
file-system-statistic-current-memory-usage OBJECT-TYPE
    SYNTAX  INTEGER
    ACCESS  read-only
    STATUS  optional
    DESCRIPTION
                "A value indicating the number of bytes of RAM currently
                used by the file system firmware.
                Additional information:
                Reset to the factory default value after
                a power cycle.  
                Returns <noSuchName>
                status if attempting to access this object and there
                is no storage device is installed."
::= { status-file-system 5 }
               
               
file-system-statistic-max-memory-usage OBJECT-TYPE
    SYNTAX  INTEGER
    ACCESS  read-only
    STATUS  optional
    DESCRIPTION
                "A value indicating the maximum number of bytes of RAM
                used by the file system firmware.  The POS should state
                if the value is reset to zero after a power cycle.
                Additional information:
                Reset to the factory default value after
                a power cycle.  
                Returns <noSuchName>
                status if attempting to access this object and there
                is no storage device is installed."
::= { status-file-system 6 }
               
               
file-system2-initialize-volume OBJECT-TYPE
    SYNTAX  INTEGER {
		   eInitializing(2)
		   }
    ACCESS  write-only
    STATUS  optional
    DESCRIPTION
                "Setting this object to eInitializing causes file system
                2 to be initialized.  Reading this object indicates if
                the file system is currently being initialized.
                Additional information:
                The hrDeviceIndex value for the mass storage
                device is the same value that is used to index into the
                FILE-SYSTEM sub-tree.  Since this product only supports
                one mass storage device, and since the hrDeviceIndex
                for the mass storage device will be 2 if the mass storage device is 
                installed, the FILE-SYSTEM2-INITIALIZE-VOLUME object
                will be the object that allows the mass storage device to be 
                initialized."
::= { file-system2 6 }
               
               
mass-storage-resource-change-counter OBJECT-TYPE
    SYNTAX  INTEGER
    ACCESS  read-only
    STATUS  optional
    DESCRIPTION
                "A counter which changes when a mass storage based
                resource has been added or deleted.
                Additional information:
                The value of this counter changes 
                each time the MASS-STORAGE-RESOURCE-CHANGED object
                is set to eTrue.  The value also changes when the 
                mass storage device is initialized.  However, the value does not
                change when a mass storage device is removed and a different
                mass storage device is installed.  Performing a cold reset sets 
                this object back to the factory default value. 
                Returns <noSuchName>
                status if attempting to access this object and there
                is no storage device is installed."
::= { mass-storage-resources 1 }
               
               
mass-storage-resource-changed OBJECT-TYPE
    SYNTAX  INTEGER {
		   eTrue(2)
		   }
    ACCESS  write-only
    STATUS  optional
    DESCRIPTION
                "Setting to eTrue causes MASS-STORAGE-RESOURCE-CHANGE-
                COUNTER to be incremented.
                Additional information:
                Returns <noSuchName>
                status if attempting to access this object and there
                is no storage device is installed."
::= { mass-storage-resources 2 }
               
               
rpc-test-return-code OBJECT-TYPE
    SYNTAX  OCTET STRING
    ACCESS  write-only
    STATUS  optional
    DESCRIPTION
                "This test object that will not be supported in any
                released product.  Setting this object allows the next
                RPC call return code to be specified.  The POS will
                specify the binary format.
                Additional information:
                The format of the binary data is a one
                of three formats.  The first format is no binary
                data, which indicates the next RPC reply should not
                be modified.  The other two formats are described in
                RFC 1057 and encoded using XDR (i.e.  the value is
                the data used to instead of the actual RPC reply).
                The second format is when reply_stat is MSG_ACCEPTED
                and accept_stat is something other than SUCCESS.
                The third format is when reply_stat is MSG_DENIED.
                Notice that all RPC replies that do not contain any
                'results' are supported."
::= { settings-rpc 1 }
               
               
rpc-bind-protocol-address OBJECT-TYPE
    SYNTAX  OCTET STRING
    ACCESS  read-write
    STATUS  optional
    DESCRIPTION
                "Array of Berkeley sockets style protocol addresses used
                to bind RPC to a communications protocol family.
                Setting an instance of this array object to a zero
                length binary value disables the transport protocol
                indicated by that instance.  All multi-bytes fields are
                in network (or big-endian) order.  Bytes 1 and 2
                indicate the transport protocol.  Some of the transport
                protocol mapping information can be found in RFC 1010
                Assigned Numbers.  A list of interesting transport
                protocol number mappings include:  
                Protocol | Number   
                ---------+-------   
                 UDP/IP  |  17   
                  IPX    |  1000   
                Bytes 3 and 4 indicate the address family.  The address
                family uses the same mapping as the BSD sockets address
                family.  A list of interesting address family mappings
                include:  
                Address Family | Number   
                ---------------+-------   
                    Internet   |   2   
                    NetWare    |   6   
                The format the fifth and following bytes is dependent on
                the address family.  For the Internet address family,
                bytes 5 and 6 contain the port number, bytes 7 through
                10 contain the IP address, and the following eight bytes
                are unused.  For NetWare, bytes 5 through 8 are the
                network number, bytes 9 through 14 are the node number,
                and bytes 15 and 16 are the socket number.
                Additional information:
                The length of the binary value is zero
                if the instance of an object in the rpc-bind-protocol-address
                array is not in use.   A side effect of the 
                implementation is initializing the mass storage device sets this object 
                back to the factory default value.  
                Returns <noSuchName>
                status if attempting to access this object and there
                is no storage device is installed."
::= { settings-rpc 2 }
               
               
rpc-statistic-successful OBJECT-TYPE
    SYNTAX  INTEGER
    ACCESS  read-only
    STATUS  optional
    DESCRIPTION
                "A counter indicating the number of RPC requests that
                completed successfully (reply_data stat is SUCCESS).
                The POS should state if a power cycle causes the counter
                is be reset to zero.
                Additional information:
                Reset to the factory default value after
                a power cycle.  
                Returns <noSuchName>
                status if attempting to access this object and there
                is no storage device is installed."
::= { status-rpc 1 }
               
               
rpc-statistic-unsuccessful OBJECT-TYPE
    SYNTAX  INTEGER
    ACCESS  read-only
    STATUS  optional
    DESCRIPTION
                "A counter indicating the number of RPC requests that
                completed unsuccessfully. 
                The POS should state if a power cycle causes
                the counter is be reset to zero.
                Additional information:
                Reset to the factory default value after
                a power cycle.  
                Returns <noSuchName>
                status if attempting to access this object and there
                is no storage device is installed."
::= { status-rpc 2 }
               
               
rpc-bound-protocol-address OBJECT-TYPE
    SYNTAX  OCTET STRING
    ACCESS  read-only
    STATUS  optional
    DESCRIPTION
                "An array of Berkeley sockets style protocol addresses
                that the NFS service has been bound to successful.  The
                format is that same as the array of RPC-BIND-PROTOCOL-
                ADDRESS of objects.
                Additional information:
                Returns <noSuchName>
                status if attempting to access this object and there
                is no storage device is installed."
::= { status-rpc 3 }
               
               
mount-test-return-code OBJECT-TYPE
    SYNTAX  OCTET STRING
    ACCESS  write-only
    STATUS  optional
    DESCRIPTION
                "This test object that will not be supported in any
                released product.  Setting this object allows the next
                mount call return code to be specified.  The POS will
                specify the binary format.
                Additional information:
                A one byte binary value.  The
                byte indicates what procedure is being effected by
                this set.  
                value | function  
                ------+------------------  
                1   | Mount will return an fhstatus of 0.  
                2   | Dump will return an empty table."
::= { settings-mount 1 }
               
               
nfs-server-memory OBJECT-TYPE
    SYNTAX  INTEGER
    ACCESS  read-only
    STATUS  optional
    DESCRIPTION
                "The amount of memory, in bytes, used by the Network File
                System server to buffer file data.
                Additional information:
                Reports the amount of memory, in bytes,
                reserved for use by the NFS server.  A
                side effect of the implementation is initializing
                the mass storage device sets this object back to the factory
                default value.  Also includes the memory used by
                other firmware components in addition to the NFS
                server.  Returns <noSuchName>
                status if attempting to access this object and there
                is no storage device is installed."
::= { settings-nfs-server 1 }
               
               
nfs-server-read-size OBJECT-TYPE
    SYNTAX  INTEGER(256..1500)
    ACCESS  read-write
    STATUS  optional
    DESCRIPTION
                "The maximum amount of data transferred in one NFS server
                read data call.
                Additional information:
                A side effect of the 
                implementation is initializing the mass storage device sets this object 
                back to the factory default value.  
                Returns <noSuchName>
                status if attempting to access this object and there
                is no storage device is installed."
::= { settings-nfs-server 2 }
               
               
nfs-server-write-size OBJECT-TYPE
    SYNTAX  INTEGER(256..1500)
    ACCESS  read-write
    STATUS  optional
    DESCRIPTION
                "The maximum amount of data transferred in one NFS server
                write data call.
                Additional information:
                A side effect of the 
                implementation is initializing the mass storage device sets this object 
                back to the factory default value.  
                Returns <noSuchName>
                status if attempting to access this object and there
                is no storage device is installed."
::= { settings-nfs-server 3 }
               
               
nfs-server-statistic-successful OBJECT-TYPE
    SYNTAX  INTEGER
    ACCESS  read-only
    STATUS  optional
    DESCRIPTION
                "A counter indicating the number of NFS requests that
                completed without error.  The POS should state if a
                power cycle causes the counter is be reset to zero.
                Additional information:
                Reset to the factory default value after
                a power cycle.  
                Returns <noSuchName>
                status if attempting to access this object and there
                is no storage device is installed."
::= { status-nfs-server 1 }
               
               
nfs-server-statistic-unsuccessful OBJECT-TYPE
    SYNTAX  INTEGER
    ACCESS  read-only
    STATUS  optional
    DESCRIPTION
                "A counter indicating the number of NFS requests that
                completed with an NFS status other than NFS_OK (0).  The
                POS should state if a power cycle causes the counter is
                be reset to zero.
                Additional information:
                Reset to the factory default value after
                a power cycle.  
                Returns <noSuchName>
                status if attempting to access this object and there
                is no storage device is installed."
::= { status-nfs-server 2 }
               
               
nfs-server-statistic-current-memory-usage OBJECT-TYPE
    SYNTAX  INTEGER
    ACCESS  read-only
    STATUS  optional
    DESCRIPTION
                "A value indicating the number of bytes of RAM currently
                used by the NFS firmware.
                Additional information:
                Reset to the factory default value after
                a power cycle.  
                Returns <noSuchName>
                status if attempting to access this object and there
                is no storage device is installed."
::= { status-nfs-server 4 }
               
               
nfs-server-statistic-max-memory-usage OBJECT-TYPE
    SYNTAX  INTEGER
    ACCESS  read-only
    STATUS  optional
    DESCRIPTION
                "A value indicating the maximum number of bytes of RAM
                used by the NFS firmware.  The POS should state if the
                value is reset to zero after a power cycle.
                Additional information:
                Reset to the factory default value after
                a power cycle.  
                Returns <noSuchName>
                status if attempting to access this object and there
                is no storage device is installed."
::= { status-nfs-server 5 }
               
               
rpc-bind-test-return-code OBJECT-TYPE
    SYNTAX  OCTET STRING
    ACCESS  write-only
    STATUS  optional
    DESCRIPTION
                "This test object that will not be supported in any
                released product.  Setting this object allows the next
                RPC bind call return code to be specified.  The POS will
                specify the binary format.
                Additional information:
                A one byte value.  
                value | meaning  
                ------+------------------  
                1   | Next GetPort or GetAddr will receive port 0  
                | (indicating the service is not supported).  
                2   | Next Dump will receive an empty table."
::= { settings-rpc-bind 1 }
               
               
rpc-bind-statistic-successful OBJECT-TYPE
    SYNTAX  INTEGER
    ACCESS  read-only
    STATUS  optional
    DESCRIPTION
                "A counter indicating the number of RPC bind (RPC program
                number 100000, version 2) requests that completed
                successfully.  The POS should state if a power cycle
                causes the counter is be reset to zero.
                Additional information:
                Reset to the factory default value after
                a power cycle.  
                Returns <noSuchName>
                status if attempting to access this object and there
                is no storage device is installed."
::= { status-rpc-bind 1 }
               
               
rpc-bind-statistic-unsuccessful OBJECT-TYPE
    SYNTAX  INTEGER
    ACCESS  read-only
    STATUS  optional
    DESCRIPTION
                "A counter indicating the number of RPC bind (RPC program
                number 100000, version 2) requests that completed
                unsuccessfully.  The POS should state if a power cycle
                causes the counter is be reset to zero.
                Additional information:
                Reset to the factory default value after
                a power cycle.  
                Returns <noSuchName>
                status if attempting to access this object and there
                is no storage device is installed."
::= { status-rpc-bind 2 }
               
               
xip-statistic-processed OBJECT-TYPE
    SYNTAX  INTEGER
    ACCESS  read-only
    STATUS  optional
    DESCRIPTION
                "A counter indicating the number of XIP requests that
                were processed.  The POS should state if a power cycle
                causes the counter is be reset to zero.
                Additional information:
                The number of XIP datagrams that have
                been received by the XIP service.  Reset to the
                factory default value after a power cycle.  Returns
                <noSuchName> status if attempting
                to access this object and there is no storage device
                is installed."
::= { status-xip 1 }
               
               
xip-statistic-data-in-dropped OBJECT-TYPE
    SYNTAX  INTEGER
    ACCESS  read-only
    STATUS  optional
    DESCRIPTION
                "A counter indicating the number of XIP data in datagrams
                that were dropped (typically due to the printer being
                flooded with XIP requests ).  The POS should state if a
                power cycle causes the counter is be reset to zero.
                Additional information:
                Reset to the factory default value after
                a power cycle.  
                Returns <noSuchName>
                status if attempting to access this object and there
                is no storage device is installed."
::= { status-xip 2 }
               
               
disk-storage-block-driver2-test-return-code OBJECT-TYPE
    SYNTAX  OCTET STRING
    ACCESS  write-only
    STATUS  optional
    DESCRIPTION
                "This test object will not be supported in any released
                product.  Setting this object allows the next call to
                the mass storage block driver 2 to return the specified
                code.  The POS will specify the binary format.
                Additional information:
                The hrDeviceIndex value for the mass storage
                device is the same value that is used to index into the
                DISK-STORAGE-BLOCK-DRIVERS sub-tree.  Since this product 
                only supports one mass storage device, the hrDeviceIndex 
                for the mass storage device will be 2 if the mass storage device is 
                installed.  The value is a two byte value.  The value
                of the first byte indicates the return code, as described
                in the following table:  
                value | meaning  
                ------+------------------  
                1   | After the next power cycle, indicate the  
                | mass storage device is not installed.  Only affects the
                | printer state after the next power cycle.  
                2   | After the next power cycle, indicate the  
                | mass storage device is not initialized.  Changes the
                | contents of the mass storage device so the mass storage device becomes
                | uninitialized.  
                3   | After the next power cycle, indicate the  
                | mass storage device is defective.  Only affects the
                | printer state after the next power cycle.  
                4   | Cause the specified call to the read block  
                | routine to indicate read failure.  
                5   | Cause the specified call to the write block  
                | routine to indicate write failure.  
                6   |  After the next power cycle, indicate the  
                | mass storage device failed the power-on self-test, but  
                | completed the initialization sequence  
                | successfully.  Only affects the
                | printer state after the next power cycle.  
                7   | Cause the driver to behave, after the next power  
                | cycle, as if the mass storage device had the serial number  
                | 'SN00000000'.  This is a one-shot effect and the  
                | driver reverts to normal behavior if the printer  
                | is power cycled a second time.  
                The second byte indicates on which call to the specified
                block driver the failure will start to occur.
                If the value of the first bytes is four or five, then the
                value of the second byte in indicates which call to the
                specified block driver routine will  fail.  A value of one
                means the first call will fail. A value of two means the
                second call will fail, and so on.  If the value of the 
                first byte is one, two, three, six, or seven, then the 
                value of the second byte is ignored.  Writing this object
                causes any previous write to this object to be invalidated."
::= { settings-msbd2 1 }
               
               
hrmemorysize OBJECT-TYPE
    SYNTAX  INTEGER
    ACCESS  read-only
    STATUS  mandatory
    DESCRIPTION
                "The amount of physical main memory contained by
              the host.
                Additional information:
                The unit of measure for this object is 1024 bytes.  
                The default value assumes the base printer with no 
                additional memory."
::= { hrStorage 2 }
               
               
hrstorageindex OBJECT-TYPE
    SYNTAX  INTEGER(1..2147483647)
    ACCESS  read-only
    STATUS  mandatory
    DESCRIPTION
                "A unique value for each logical storage area
              contained by the host."
::= { hrStorageEntry 1 }
               
               
hrstoragetype OBJECT-TYPE
    SYNTAX  OBJECT IDENTIFIER
    ACCESS  read-only
    STATUS  mandatory
    DESCRIPTION
                "The type of storage represented by this entry."
::= { hrStorageEntry 2 }
               
               
hrstoragedescr OBJECT-TYPE
    SYNTAX  OCTET STRING
    ACCESS  read-only
    STATUS  mandatory
    DESCRIPTION
                "A description of the type and instance of the
              storage described by this entry.
                Additional information:
                This object is not localized."
::= { hrStorageEntry 3 }
               
               
hrstorageallocationunits OBJECT-TYPE
    SYNTAX  INTEGER(1..2147483647)
    ACCESS  read-only
    STATUS  mandatory
    DESCRIPTION
                "The size, in bytes, of the data objects allocated
               from this pool.  If this entry is monitoring
               sectors, blocks, buffers, or packets, for example,
               this number will commonly be greater than one.
               Otherwise this number will typically be one.
                Additional information:
                Unit is one byte."
::= { hrStorageEntry 4 }
               
               
hrstoragesize OBJECT-TYPE
    SYNTAX  INTEGER(0..2147483647)
    ACCESS  read-only
    STATUS  mandatory
    DESCRIPTION
                "The size of the storage represented by this entry,
              in units of hrStorageAllocationUnits.
                Additional information:
                Total formatter RAM."
::= { hrStorageEntry 5 }
               
               
hrstorageused OBJECT-TYPE
    SYNTAX  INTEGER(0..2147483647)
    ACCESS  read-only
    STATUS  mandatory
    DESCRIPTION
                "The amount of the storage represented by this
              entry that is allocated, in units of
              hrStorageAllocationUnits.
                Additional information:
                This object should not be used when creating a print
                job for the device because the amount of memory in use will
                likely be different when the printer processes the print job."
::= { hrStorageEntry 6 }
               
               
hrstorageallocationfailures OBJECT-TYPE
    SYNTAX  INTEGER
    ACCESS  read-only
    STATUS  mandatory
    DESCRIPTION
                "The number of requests for storage represented by
              this entry that could not be honored due to not
              enough storage.  It should be noted that as this
              object has a SYNTAX of Counter, that it does not
              have a defined initial value.  However, it is
              recommended that this object be initialized to
              zero.
                Additional information:
                This object is set to zero at power on and when any 
                reset is done via prtGeneralReset.  
                This object is incremented whenever the printer is 
                short on memory."
::= { hrStorageEntry 7 }
               
               
hrdeviceindex OBJECT-TYPE
    SYNTAX  INTEGER(1..2147483647)
    ACCESS  read-only
    STATUS  mandatory
    DESCRIPTION
                "A unique value for each device contained by the
              host.  The value for each device must remain
              constant at least from one re-initialization of the
              agent to the next re-initialization.
                Additional information:
                The entry in the Device Table which
                describes the printer. "
::= { hrDeviceEntry 1 }
               
               
hrdevicetype OBJECT-TYPE
    SYNTAX  OBJECT IDENTIFIER
    ACCESS  read-only
    STATUS  mandatory
    DESCRIPTION
                "An indication of the type of device.
              If this value is `hrDeviceProcessor { hrDeviceTypes
              3 }' then an entry exists in the hrProcessorTable
              which corresponds to this device.
              If this value is `hrDeviceNetwork { hrDeviceTypes 4
              }', then an entry exists in the hrNetworkTable
              which corresponds to this device.
              If this value is `hrDevicePrinter { hrDeviceTypes 5
              }', then an entry exists in the hrPrinterTable
              which corresponds to this device.
              If this value is `hrDeviceDiskStorage {
              hrDeviceTypes 6 }', then an entry exists in the
              hrDiskStorageTable which corresponds to this
              device."
::= { hrDeviceEntry 2 }
               
               
hrdevicedescr OBJECT-TYPE
    SYNTAX  OCTET STRING (SIZE(0..64))
    ACCESS  read-only
    STATUS  mandatory
    DESCRIPTION
                "A textual description of this device, including
              the device's manufacturer and revision, and
              optionally, its serial number.
                Additional information:
                This object is not localized."
::= { hrDeviceEntry 3 }
               
               
hrdeviceid OBJECT-TYPE
    SYNTAX  OBJECT IDENTIFIER
    ACCESS  read-only
    STATUS  mandatory
    DESCRIPTION
                "The product ID for this device.
                Additional information:
                The complete OID reported by this object is:  
                .1.3.6.1.4.1.11.2.3.9.1.2.1"
::= { hrDeviceEntry 4 }
               
               
hrdevicestatus OBJECT-TYPE
    SYNTAX  INTEGER {
		   eHrunning(2),
		   eHwarning(3),
		   eHdown(5)
		   }
    ACCESS  read-only
    STATUS  mandatory
    DESCRIPTION
                "The current operational state of the device
              described by this row of the table.  A value
              unknown(1) indicates that the current state of the
              device is unknown.  running(2) indicates that the
              device is up and running and that no unusual error
              conditions are known.  The warning(3) state
              indicates that agent has been informed of an
              unusual error condition by the operational software
              (e.g., a disk device driver) but that the device is
              still 'operational'.  An example would be high
              number of soft errors on a disk.  A value of
              testing(4), indicates that the device is not
              available for use because it is in the testing
              state.  The state of down(5) is used only when the
              agent has been informed that the device is not
              available for any use.
                Additional information:
                The printer's condition is mapped as follows:  
                eHrunning -- Printer ready to print or is printing.
                May be in power save mode.  
                eHwarning -- A condition exists that needs attention but it is
                not currently preventing printing. A non-critical alert is
                active.  
                eHtesting -- Printer is printing an internal page.  
                eHdown -- Printer is not printing due to an error condition. A
                critical alert is active, human interaction is needed to bring the printer to
                a ready state or the printer is offline."
::= { hrDeviceEntry 5 }
               
               
hrdeviceerrors OBJECT-TYPE
    SYNTAX  INTEGER
    ACCESS  read-only
    STATUS  mandatory
    DESCRIPTION
                "The number of errors detected on this device.  It
               should be noted that as this object has a SYNTAX
               of Counter, that it does not have a defined
               initial value.  However, it is recommended that
               this object be initialized to zero.
                Additional information:
                This is the number of critical alerts that have been 
                entered into the alert table since the device was powered on.
                The maximum value for this object is 2^32-1."
::= { hrDeviceEntry 6 }
               
               
hrprinterstatus OBJECT-TYPE
    SYNTAX  INTEGER {
		   eHother(1),
		   eHidle(3),
		   eHprinting(4),
		   eHwarmup(5)
		   }
    ACCESS  read-only
    STATUS  mandatory
    DESCRIPTION
                "The current status of this printer device.  When
               in the idle(1), printing(2), or warmup(3) state,
               the corresponding hrDeviceStatus should be
               running(2) or warning(3).  When in the unknown
               state, the corresponding hrDeviceStatus should be
               unknown(1).
                Additional information:
                The printer's condition is mapped as follows:  
                eHidle -- The printer is not doing any of the items listed below
                for eHprinting status.  
                eHprinting -- The printer is processing PJL or PDL data, waiting
                for an error condition to be cleared, processing a control
                panel request, waiting for the engine to become ready or
                printing images.   
                eHwarmup -- If hrDeviceStatus is eHdown, then the printer is
                currently offline but is resolving
                the condition that caused it be offline it will be online
                when it is ready to print. If hrDeviceStatus is eHrunning,
                then the printer was in power save mode and is now becoming
                ready to print."
::= { hrPrinterEntry 1 }
               
               
hrprinterdetectederrorstate OBJECT-TYPE
    SYNTAX  OCTET STRING
    ACCESS  read-only
    STATUS  mandatory
    DESCRIPTION
                "This object represents any error conditions
               detected by the printer.  The error conditions are
               encoded as bits in an octet string, with the
               following definitions:
                    Condition         Bit #    hrDeviceStatus
                    lowPaper          0        warning(3)
                    noPaper           1        down(5)
                    lowToner          2        warning(3)
                    noToner           3        down(5)
                    doorOpen          4        down(5)
                    jammed            5        down(5)
                    offline           6        down(5)
                    serviceRequested  7        warning(3)
               If multiple conditions are currently detected and
               the hrDeviceStatus would not otherwise be
               unknown(1) or testing(4), the hrDeviceStatus shall
               correspond to the worst state of those indicated,
               where down(5) is worse than warning(3) which is
               worse than running(2).
               Bits are numbered starting with the most
               significant bit of the first byte being bit 0, the
               least significant bit of the first byte being bit
               7, the most significant bit of the second byte
               being bit 8, and so on.  A one bit encodes that
               the condition was detected, while a zero bit
               encodes that the condition was not detected.
               This object is useful for alerting an operator to
               specific warning or error conditions that may
               occur, especially those requiring human
               intervention.
                Additional information:
                LaserJet 5Si reports error conditions as follows:  
                lowPaper -- A tray is empty, but the media to be loaded is not
                currently needed.
                hrDeviceStatus = eHwarning;
                hrPrinterStatus = eHidle or eHprinting;
                a non-critical alert is active.  
                noPaper -- A tray is empty and must be filled for printing to
                continue.
                hrDeviceStatus = eHdown;
                hrPrinterStatus = eHother;
                a non-critical alert is active.  
                lowToner -- A toner low condition has been detected.
                hrDeviceStatus = eHwarning;
                hrPrinterStatus = eHidle or eHprinting;
                a non-critical alert is active.  
                noToner -- LaserJet 5Si does not report this condition.  
                doorOpen -- A door is open.
                hrDeviceStatus = eHdown;
                hrPrinterStatus = eHother;
                a non-critical alert is active.  
                jammed -- A jam condition is preventing printing.
                hrDeviceStatus = eHdown;
                hrPrinterStatus = eHother;
                a non-critical alert is active.  
                offline -- Printer is offline.
                hrDeviceStatus = eHdown;
                hrPrinterStatus = eHother;
                a non-critical alert is active.  
                serviceRequested -- Any status or error condition not listed
                above. If the condition prevents printing, the 'offline'
                bit is also set and its hrDeviceStatus and hrPrinterStatus
                would prevail.
                hrDeviceStatus = eHwarning;
                hrPrinterStatus = eHidle or eHprinting;
                a non-critical alert is active."
::= { hrPrinterEntry 2 }
               
               
prtgeneralconfigchanges OBJECT-TYPE
    SYNTAX  INTEGER
    ACCESS  read-only
    STATUS  optional
    DESCRIPTION
                "Counts configuration changes that change the capabilities of
        a printer, such as the addition/deletion of input/output bins,
        the addition/deletion of interpreters, or changes in media
        size.  Such changes will often affect the capability of the
        printer to service certain types of print jobs.
        Management applications may cache infrequently changed
        configuration  information about sub-units on the printer.
        This object should be incremented whenever the agent wishes
        such applications to invalidate that cache and re-download
        all of this configuration information, thereby signalling a
        change in the printer's configuration.
        For example, if an input tray that contained paper of
        different dimensions was added, this counter would be
        incremented.
        As an additional example, this counter would not be
        incremented when an input tray is removed or the level of an
        input device changes.
                Additional information:
                This is a 32 bit counter (unsigned). When it reaches 
                its maximum value, it will roll to zero. 
                This object is stored in NVRAM."
::= { prtGeneralEntry 1 }
               
               
prtgeneralcurrentlocalization OBJECT-TYPE
    SYNTAX  INTEGER(1..14)
    ACCESS  read-write
    STATUS  optional
    DESCRIPTION
                "The value of the prtLocalizationIndex corresponding to the
        current language, country, and character set to be used for
        localized string values that are identified as being dependent
        on the value of this object.  Note that this object does not
        apply to localized strings in the prtConsole group or any
        object that is not identified as above.
                Additional information:
                The value of this object is saved in NVRAM."
::= { prtGeneralEntry 2 }
               
               
prtgeneralreset OBJECT-TYPE
    SYNTAX  INTEGER {
		   ePnotResetting(3),
		   ePpowerCycleReset(4),
		   ePresetToNVRAM(5),
		   ePresetToFactoryDefaults(6)
		   }
    ACCESS  read-write
    STATUS  optional
    DESCRIPTION
                "Setting this value to `powerCycleReset', `resetToNVRAM', or
        `resetToFactoryDefaults' will result in the resetting of the
        printer.  When read, this object will always have the value
        `notResetting(3)', and a SET of the value `notResetting' shall
        have no effect on the printer.  Some of the defined values are
        optional.  However, every implementation must support at least
        the values `notResetting' and resetToNVRAM'.
                Additional information:
                All resets follow the same sequence of events except that a 
                a value of ePresetToFactoryDefaults first makes a call to reset the NVRAM to 
                factory defaults. Then, the following sequence of events occur:  
                1. A 1 second delay is initiated while a reply is returned to the requestor 
                indicating OK. The printer waits for the second to elapse.  
                2. The printer goes off-line.  
                3. The control panel is disabled.  
                4. The paper path is flushed.  
                5. The printer is reset per the request. The printer will respond to PML 
                requests up to this point in time.  
                
                Setting this object to ePpowerCycleReset causes LaserJet 5Si to perform its power
                on initialization routines. I/O cards are reset (NVRAM on the cards is not 
                changed; all I/O buffers are flushed). 
                The tests normally run at power on time are executed.  
                
                Setting this object to ePresetToNVRAM causes the printer to reset itself to 
                its power on state without doing its normal power on testing. The I/O cards 
                are not reset and I/O buffers remain intact.  
                
                Setting this object to ePresetToFactoryDefaults causes the same action as a 
                Cold Reset operation performed at the control panel (except power on testing 
                is not performed).  
                The I/O cards 
                are not reset and I/O buffers remain intact."
::= { prtGeneralEntry 3 }
               
               
prtcoverdescription OBJECT-TYPE
    SYNTAX  OCTET STRING (SIZE(0..255))
    ACCESS  read-only
    STATUS  optional
    DESCRIPTION
                "The manufacturer provided cover sub-mechanism  name in the
        localization specified by prtGeneralCurrentLocalization."
::= { prtCoverEntry 2 }
               
               
prtcoverstatus OBJECT-TYPE
    SYNTAX  INTEGER {
		   ePdoorOpen(3),
		   ePdoorClosed(4)
		   }
    ACCESS  read-only
    STATUS  optional
    DESCRIPTION
                "The status of this cover sub-unit.
                Additional information:
                LaserJet 5Si detects a door open condition only when
                printing."
::= { prtCoverEntry 3 }
               
               
prtlocalizationlanguage OBJECT-TYPE
    SYNTAX  OCTET STRING (SIZE(0..2))
    ACCESS  read-only
    STATUS  optional
    DESCRIPTION
                "A two character language code from ISO 639.  Examples EN, GB,
        CA, FR, DE.
                Additional information:
                The languages supported by LaserJet 5Si are English,
                French, German, Italian, Spanish, Swedish, Danish, Norwegian, Dutch, Finnish,
                Portuguese, Turkish, Polish and Japanese."
::= { prtLocalizationEntry 2 }
               
               
prtlocalizationcountry OBJECT-TYPE
    SYNTAX  OCTET STRING (SIZE(0..2))
    ACCESS  read-only
    STATUS  optional
    DESCRIPTION
                "A two character country code from ISO 3166, a blank string
        (two space characters) shall indicate that the country is
        not defined.  Examples: US, FR, DE, ...
                Additional information:
                The languages supported by LaserJet 5Si (and corresponding
                country) are English (United States), French (France), German (Germany),
                Italian (Italy), Spanish (Spain), Swedish (Sweden), Danish (Denmark),
                Norwegian (Norway), Dutch (Netherlands), Finnish (Finland), Portuguese
                (Portugal), Turkish (Turkey), Polish (Poland) and Japanese (Japan)."
::= { prtLocalizationEntry 3 }
               
               
prtlocalizationcharacterset OBJECT-TYPE
    SYNTAX  INTEGER {
		   ePcsHPRoman8(2004),
		   ePcsISOLatin5(12),
		   ePcsISOLatin2(5),
		   ePcsWindows31J(2024)
		   }
    ACCESS  read-only
    STATUS  optional
    DESCRIPTION
                "The coded character set used for this localization."
::= { prtLocalizationEntry 4 }
               
               
prtstoragerefindex OBJECT-TYPE
    SYNTAX  INTEGER(0..65535)
    ACCESS  read-only
    STATUS  optional
    DESCRIPTION
                "The value of the hrDeviceIndex of the printer device that this
        storageEntry is associated with."
::= { prtStorageRefEntry 2 }
               
               
prtdevicerefindex OBJECT-TYPE
    SYNTAX  INTEGER(0..65535)
    ACCESS  read-only
    STATUS  optional
    DESCRIPTION
                "The value of the hrDeviceIndex of the printer device that this
        deviceEntry is associated with."
::= { prtDeviceRefEntry 2 }
               
               
prtgeneralcurrentoperator OBJECT-TYPE
    SYNTAX  OCTET STRING (SIZE(0..32))
    ACCESS  read-write
    STATUS  optional
    DESCRIPTION
                "The name of the current human operator responsible for
        operating this printer. It is suggested that this string
        include information that would enable other humans to reach
        the operator, such as a phone number.
                Additional information:
                The maximum
                supported string length is 32 characters.  If the user
                entered string is too long, the device will store as
                much as possible and will return the
                <noError> status.  
                This object is saved in NVRAM."
::= { prtGeneralEntry 4 }
               
               
prtgeneralserviceperson OBJECT-TYPE
    SYNTAX  OCTET STRING (SIZE(0..32))
    ACCESS  read-write
    STATUS  optional
    DESCRIPTION
                "The name of the last human responsible for servicing
        this printer. It is suggested that this string
        include information that would enable other humans to reach
        the service person, such as a phone number.
                Additional information:
                The maximum
                supported string length is 32 characters.  If the user
                entered string is too long, the device will store as
                much as possible and will return the
                <noError> status.  
                This object is saved in NVRAM."
::= { prtGeneralEntry 5 }
               
               
prtinputdefaultindex OBJECT-TYPE
    SYNTAX  INTEGER(1..65535)
    ACCESS  read-only
    STATUS  optional
    DESCRIPTION
                "The value of prtInputIndex corresponding to the default input
        sub-unit: that is, this object selects the default source of
        input media.
                Additional information:
                The default input tray is determined by the printer 
                based on DEFAULT-MEDIA-SIZE and DEFAULT-MEDIA-NAME. If multiple trays have 
                qualifying media, tray 1 is selected first, then the non-empty tray with the 
                highest capacity is selected; trays of equal capacity are selected by lower 
                tray number.   
                Trays 1-3 refer to the printer's trays that are so labeled. Tray 4 is the 
                envelope feeder, which may or may not be present. Tray 5 is the first tray of 
                the first external input paper handling device."
::= { prtGeneralEntry 6 }
               
               
prtinputtype OBJECT-TYPE
    SYNTAX  INTEGER {
		   ePother(1),
		   ePunknown(2),
		   ePsheetFeedAutoRemovableTray(3),
		   ePsheetFeedAutoNonRemovableTray(4),
		   ePsheetFeedManual(5),
		   ePcontinuousRoll(6),
		   ePcontinuousFanFold(7)
		   }
    ACCESS  read-only
    STATUS  optional
    DESCRIPTION
                "The type of technology (discriminated primarily according to
        	feeder mechanism type) employed by the input sub-unit.  Note,
        	the Optional Input Class provides for a descriptor field to
        	further qualify the other choice.
                Additional information:
                Tray 1 is the right side tray and is always present. 
                Tray 1 can operate in manual feed mode but is 
                typically treated as a normal input source. Therefore, 
                its type is ePsheetFeedAutoNonRemovableTray.  
                Trays 2 and 3 are the drawers and, although they are 
                usually not removed from the printer, the printer 
                cannot distinguish the open and removed conditions. 
                Therefore, when they are open, they are considered to 
                be removed and, for this object, they are considered 
                to be of type ePsheetFeedAutoRemovableTray.  
                Tray 4 is the envelope feeder, which is removable at 
                any time.  
                Tray 5 is the high capacity input device. ."
::= { prtInputEntry 2 }
               
               
prtinputdimunit OBJECT-TYPE
    SYNTAX  INTEGER {
		   ePtenThousandthsOfInches(3),
		   ePmicrometers(4)
		   }
    ACCESS  read-only
    STATUS  optional
    DESCRIPTION
                "The unit of measurement for use calculating and relaying
        dimensional values for this input sub-unit."
::= { prtInputEntry 3 }
               
               
prtinputmediadimfeeddirdeclared OBJECT-TYPE
    SYNTAX  INTEGER
    ACCESS  read-write
    STATUS  optional
    DESCRIPTION
                "This object provides the value of the declared dimension, in
        the feed direction, of the media that is (or, if empty, was or
        will be) in this input sub-unit.  The feed direction is the
        direction in which the media is fed on this sub-unit.  This
        dimension is measured in input sub-unit dimensional units
        (prtInputDimUnit).  If this input sub-unit can reliably sense
        this value, the value is sensed by the printer and may not be
        changed by management requests.  Otherwise, the value may be
        changed. The value (-1) means other and specifically means
        that this sub-unit places no restriction on this parameter.
        The value (-2) indicates unknown.
                Additional information:
                For trays 2, 3 and 5 (which can reliably sense this 
                value) the objects behave exactly the same as prtInputMediaDimFeedDirChosen. 
                Attempting to set this object for trays 2, 3 and 5 will cause 
                <noSuchName> to be returned.
                The default values assume the trays are configured for 
                letter size paper.  
                For tray 1 the value is the dimension for the media size currently declared."
::= { prtInputEntry 4 }
               
               
prtinputmediadimxfeeddirdeclared OBJECT-TYPE
    SYNTAX  INTEGER
    ACCESS  read-write
    STATUS  optional
    DESCRIPTION
                "This object provides the value of the declared dimension, in
        the cross feed direction, of the media that is (or, if empty,
        was or will be) in this input sub-unit.  The cross  feed
        direction is ninety degrees relative to the feed direction
        associated with this sub-unit. This dimension is measured in
        input sub-unit dimensional units (prtInputDimUnit).  If this
        input sub-unit can reliably sense this value, the value is
        sensed by the printer and may not be changed by management
        requests. Otherwise, the value may be changed. The value (-1)
        means other and specifically means that this sub-unit places
        no restriction on this parameter. The value (-2) indicates
        unknown.
                Additional information:
                For trays 2, 3 and 5 (which can reliably sense this 
                value) the objects behave exactly the same as prtInputMediaDimFeedDirChosen. 
                Attempting to set this object for trays 2, 3 and 5 will cause 
                <noSuchName> to be returned.
                The default values assume the trays are configured for 
                letter size paper.  
                For tray 1 the value is the dimension for the media size currently declared."
::= { prtInputEntry 5 }
               
               
prtinputmediadimfeeddirchosen OBJECT-TYPE
    SYNTAX  INTEGER
    ACCESS  read-only
    STATUS  optional
    DESCRIPTION
                "The printer will act as if media of the chosen dimension (in
        the feed direction) is present in this input source.  Note
        that this value will be used even if the input tray is empty.
        Feed dimension measurements
        are taken parallel relative to the feed direction
        associated with that sub-unit and are in input sub-unit
        dimensional units (DimUnit). If the printer supports the
        declared dimension, the granted dimension is the same as
        the declared dimension. If not, the granted dimension is
        set to the closest dimension that the printer supports
        when the declared dimension is set. The value (-1) means
        other and specifically indicates that this sub-unit
        places no restriction on this parameter. The value (-2)
        indicates unknown.
                Additional information:
                The objects for trays 2, 3 and 5 reflect the 
                configuration of the corresponding drawers. When the drawer is open, a value 
                of -2 is returned. The default values assume the trays are configured for 
                letter size paper.  
                The object for trays 1 and 4 return the value of the media size for which the 
                tray is currently configured."
::= { prtInputEntry 6 }
               
               
prtinputmediadimxfeeddirchosen OBJECT-TYPE
    SYNTAX  INTEGER
    ACCESS  read-only
    STATUS  optional
    DESCRIPTION
                "The printer will act as if media of the chosen dimension (in
        the cross feed direction) is present in this input source.
        Note that this value will be used even if the input tray is
        empty.  The cross feed direction is ninety degrees relative
        to the feed direction associated with this sub-unit. This
        dimension is measured in input sub-unit dimensional units
        (DimUnit).  If the printer supports the declared
        dimension, the granted dimension is the same as the
        declared dimension. If not, the granted dimension is set
        to the closest dimension that the printer supports when
        the declared dimension is set. The value (-1) means other
        and specifically indicates that this sub-unit places no
        restriction on this parameter.  The value (-2) indicates
        unknown.
                Additional information:
                The objects for trays 2, 3 and 5 reflect the 
                configuration of the corresponding drawers. When the drawer is open, a value 
                of -2 is returned. The default values assume the trays are configured for 
                letter size paper.  
                The object for trays 1 and 4 return the value of the media size for which the 
                tray is currently configured."
::= { prtInputEntry 7 }
               
               
prtinputcapacityunit OBJECT-TYPE
    SYNTAX  INTEGER {
		   ePtenThousandthsOfInches(3),
		   ePmicrometers(4),
		   ePsheets(8),
		   ePfeet(16),
		   ePmeters(17)
		   }
    ACCESS  read-only
    STATUS  optional
    DESCRIPTION
                "The unit of measurement for use in calculating and relaying
        	capacity values for this input sub-unit.
                Additional information:
                A sheet is a single piece of 20 pound paper. For tray 
                4, the envelope feeder, a sheet is one envelope."
::= { prtInputEntry 8 }
               
               
prtinputmaxcapacity OBJECT-TYPE
    SYNTAX  INTEGER
    ACCESS  read-only
    STATUS  optional
    DESCRIPTION
                "The maximum capacity of the input sub-unit in input
        sub-unit capacity units (CapacityUnit).  There is no
        convention associated with the media itself so this value
        reflects claimed capacity. If this input sub-unit can
        reliably sense this value, the value is sensed by the
        printer and may not be changed by management requests;
        otherwise, the value may be written (by a Remote
        Contol Panel or a Management Application).
        The value (-1) means other and specifically
        indicates that the sub-unit places no restrictions
        on this parameter.  The value (-2) means unknown."
::= { prtInputEntry 9 }
               
               
prtinputcurrentlevel OBJECT-TYPE
    SYNTAX  INTEGER
    ACCESS  read-only
    STATUS  optional
    DESCRIPTION
                "The current capacity of the input sub-unit in input
        sub-unit capacity units (CapacityUnit). If this input
        sub-unit can reliably sense this value, the value is
        sensed by the printer and may not be changed by
        management requests; otherwise, the value may
        be written (by a Remote Contol Panel or a
        Management Application).  The value (-1) means other and
        specifically indicates that the sub-unit places no
        restrictions on this parameter. The value (-2) means unknown.
        The value (-3) means that the printer knows that at least one
        unit remains.
                Additional information:
                For trays 1 and 4, LaserJet 5Si can only detect empty/not 
                empty trays. It returns -3 for not empty and 0 for 
                empty.  
                
                For trays 2 and 3, LaserJet 5Si can detect approximately the amount of media. The
                value returned is based on the amount detected as follows:  
                0 - empty   
                1 - 1-110 sheets  
                50 - 50-260 sheets  
                200 - 200-490 sheets  
                430 - 430 sheets or more  
                
                For tray 5, LaserJet 5Si can detect approximately the amount of media. The
                value returned is based on the amount detected as follows:  
                0 - empty   
                1 - 1 sheet to 25% of capacity  
                500 - 26% to 50% of capacity  
                1000 - 51% to 75% of capacity  
                1500 - 76% to 100% of capacity  
                If the tray drawer is open, a value of -2 (unknown) will  be returned."
::= { prtInputEntry 10 }
               
               
prtinputstatus OBJECT-TYPE
    SYNTAX  INTEGER
    ACCESS  read-only
    STATUS  optional
    DESCRIPTION
                "The current status of this input sub-unit.
         The status is an integer that is the sum of 5
         distinct values, Availability, Non-Critical, Critical,
         On-line, and Transitioning. These values are:
         Availability                           value       
            Available and Idle              0       000'b       
            Available and Standby           2       010'b       
            Available and Active            4       100'b       
            Available and Busy              6       110'b       
            Unavailable and OnRequest       1       001'b       
            Unavailable because Broken      3       011'b       
            Unknown                         5       101'b       
         Non-Critical       
            No Non-Critical Alerts          0       
            Non-Critical Alerts             8       
         Critical       
            No Critical Alerts              0       
            Critical Alerts                 16       
         On-Line       
            Intended state is On-Line       0       
            Intended state is Off-Line      32       
         Transitioning       
            At intended state               0       
            Transitioning to intended state 64       
        
                Additional information:
                See SubUnitStatus in RFC1759 Printer MIB for details on values reported by 
                this object. LaserJet 5Si will not include values Available and Standby (2), 
                Available and Active (4) or Unknown (5)."
::= { prtInputEntry 11 }
               
               
prtinputmedianame OBJECT-TYPE
    SYNTAX  OCTET STRING (SIZE(0..63))
    ACCESS  read-write
    STATUS  optional
    DESCRIPTION
                "A description of the media contained in this input sub-unit;
        This description is intended for display to a human operator.
        This description is not processed by the printer.  It is used
        to provide information not expressible in terms of the other
        media attributes (e.g. prtInputMediaDimFeedDirChosen,
        prtInputMediaDimXFeedDirChosen, prtInputMediaWeight,
        prtInputMediaType). An example would be `legal tender bond
        paper'.
                Additional information:
                If set to a string other than one contained by a  
                MEDIAn-NAME object, a status of   
                <badValue> is returned.  
                NOTE: For trays 2, 3, and 5 the following media types  
                are not available via the front panel:  
                TRANSPARENCY, LABELS, CARDSTOCK"
::= { prtInputEntry 12 }
               
               
prtinputname OBJECT-TYPE
    SYNTAX  OCTET STRING (SIZE(0..63))
    ACCESS  read-only
    STATUS  optional
    DESCRIPTION
                "The name assigned to this input sub-unit."
::= { prtInputEntry 13 }
               
               
prtinputvendorname OBJECT-TYPE
    SYNTAX  OCTET STRING (SIZE(0..63))
    ACCESS  read-only
    STATUS  optional
    DESCRIPTION
                "The vendor name of this input sub-unit."
::= { prtInputEntry 14 }
               
               
prtinputmodel OBJECT-TYPE
    SYNTAX  OCTET STRING (SIZE(0..63))
    ACCESS  read-only
    STATUS  optional
    DESCRIPTION
                "The model name of this input sub-unit."
::= { prtInputEntry 15 }
               
               
prtinputversion OBJECT-TYPE
    SYNTAX  OCTET STRING (SIZE(0..63))
    ACCESS  read-only
    STATUS  optional
    DESCRIPTION
                "The version of this input sub-unit."
::= { prtInputEntry 16 }
               
               
prtinputserialnumber OBJECT-TYPE
    SYNTAX  OCTET STRING (SIZE(0..32))
    ACCESS  read-only
    STATUS  optional
    DESCRIPTION
                "The serial number assigned to this input sub-unit."
::= { prtInputEntry 17 }
               
               
prtinputdescription OBJECT-TYPE
    SYNTAX  OCTET STRING (SIZE(0..255))
    ACCESS  read-only
    STATUS  optional
    DESCRIPTION
                "A free-form text description of this input
        sub-unit in the localization specified by
        prtGeneralCurrentLocalization.
                Additional information:
                "
::= { prtInputEntry 18 }
               
               
prtinputsecurity OBJECT-TYPE
    SYNTAX  INTEGER {
		   ePother(1),
		   ePon(3),
		   ePoff(4),
		   ePnotPresent(5)
		   }
    ACCESS  read-only
    STATUS  optional
    DESCRIPTION
                "Indicates if this input sub-unit has some security
        associated with it.
                Additional information:
                No security mechanism provided."
::= { prtInputEntry 19 }
               
               
prtoutputdefaultindex OBJECT-TYPE
    SYNTAX  INTEGER
    ACCESS  read-write
    STATUS  optional
    DESCRIPTION
                "The  value of prtOutputIndex  corresponding to the default
        output sub-unit; that is, this object selects the default
        output destination."
::= { prtGeneralEntry 7 }
               
               
prtoutputtype OBJECT-TYPE
    SYNTAX  INTEGER {
		   ePother(1),
		   ePunknown(2),
		   ePremovableBin(3),
		   ePunRemovableBin(4),
		   ePcontinuousRollDevice(5),
		   ePmailBox(6),
		   ePcontinuousFanFold(7)
		   }
    ACCESS  read-only
    STATUS  optional
    DESCRIPTION
                "The type of technology supported by this output sub-unit."
::= { prtOutputEntry 2 }
               
               
prtoutputcapacityunit OBJECT-TYPE
    SYNTAX  INTEGER {
		   ePtenThousandthsOfInches(3),
		   ePmicrometers(4),
		   ePsheets(8),
		   ePfeet(16),
		   ePmeters(17)
		   }
    ACCESS  read-only
    STATUS  optional
    DESCRIPTION
                "The unit of measurement for use in calculating and relaying
        capacity values for this output sub-unit.
                Additional information:
                A sheet is a single piece of 20 pound paper."
::= { prtOutputEntry 3 }
               
               
prtoutputmaxcapacity OBJECT-TYPE
    SYNTAX  INTEGER
    ACCESS  read-only
    STATUS  optional
    DESCRIPTION
                "The maximum capacity of this output sub-unit in output
        sub-unit capacity units (CapacityUnit). There is no
        convention associated with the media itself so this value
        essentially reflects claimed capacity. If this output
        sub-unit can reliably sense this value, the value is
        sensed by the printer and may not be changed by management
        requests; otherwise, the value may be written
        (by a Remote Contol Panel or a Management Application).
        The value (-1) means other and specifically indicates
        that the sub-unit places no restrictions on this parameter.
        The value (-2) means unknown.
                Additional information:
                Output sub-unit 2 is not supported if any output paper handling
                device is attached.  
                The capacity of sub-unit 4 depends on the mode of operation. The capcities are
                as follows:  
                Stacker: OutBin1: 125   
                OutBin2: 1250   
                OutBin3: 300 (sub-units 5-9 do not exist)  
                Job Separator: OutBin1: 125   
                OutBin2: 1250   
                OutBin3: 300 (sub-units 5-9 do not exist)  
                Mailbox: OutBin1: 125 (this is the default mode)
                OutBin2: 250 
                OutBin3: 250 
                OutBin4: 250 
                OutBin5: 250 
                OutBin6: 250 
                OutBin7: 300"
::= { prtOutputEntry 4 }
               
               
prtoutputremainingcapacity OBJECT-TYPE
    SYNTAX  INTEGER
    ACCESS  read-only
    STATUS  optional
    DESCRIPTION
                "The remaining capacity of the possible output sub-unit
        capacity in output sub-unit capacity units (CapacityUnit)
        of this output sub-unit. If this output sub-unit can
        reliably sense this value, the value is sensed by the
        printer and may not be modified by management requests;
        otherwise, the value may be written (by
        a Remote Contol Panel or a Management
        Application).  The value (-1) means other and
        specifically indicates that the sub-unit places no
        restrictions on this parameter.  The value (-2) means
        unknown.  The value (-3) means that the printer knows that
        there remains capacity for at least one unit.
                Additional information:
                The values reported for output sub-unit 1 (face-down, top bin) will be 
                either (-3) (ie, unknown) if it is not full or (0) if it is full.   
                
                Output sub-unit 2 (face-up, left side bin) does 
                not have any sensing, so it will always report unknown (-2).  
                
                The first output sub-unit (3) of the HCO reports 
                either (-3) (ie, unknown) if it is not full or (0) if it is full.  
                
                In mailbox mode,   
                the HCO sub-units (4-8) will report (250) when empty, (125) 
                when there's room for <250 sheets and (0) when full. The  
                STAPLER sub-unit (9) will report (-3) when not full and (0) when full.
                
                In stacker and job separator modes all bins are treated as a single output 
                bin so sub-unit 4 will report (1250) when all bins are empty. A value of (0) 
                is reported when the topmost bin is full (stacker mode) or when all bins are 
                full (separator mode).  
                
                When the stacker or separator has started filling, the value reported is based 
                on the number of bins that are empty, partially filled and full. 
                A percentage is calculated based on the status of each bin. Each full 
                bin counts 1, each not empty/not full bin counts 0.5 and each empty bin 
                counts 0. The result is mapped to an estimate of the remaining capacity as 
                follows (percent full is included here for completeness, since that is how the 
                HCO reports it to the printer):  
                0.0    0  (100%)  
                0.5  200  ( 90%)  
                1.0  300  ( 85%)  
                1.5  400  ( 80%)  
                2.0  500  ( 75%)  
                2.5  700  ( 65%)  
                3.0  800  ( 60%)  
                3.5  900  ( 55%)  
                4.0 1000  ( 50%)  
                4.5 1200  ( 40%)  
                5.0 1300  ( 35%)  
                5.5 1400  ( 30%)  
                6.0 1500  ( 25%)  
                6.5 1700  ( 15%)  
                7.0 1800  ( 10%)  
                7.5 1900  (  5%)  
                8.0 2000  (  0%)  
                
                Note: Due to HCO mechanism limitations, the value reported may not always be 
                accurate (the bin status is detected only when the media 
                delivery head is moved to or past a physical bin). Also, for stacker mode a 
                bin is considered full as long as any bin above it is not empty.  
                Default values assume all sub-units are empty and the HCO is in mailbox mode."
::= { prtOutputEntry 5 }
               
               
prtoutputstatus OBJECT-TYPE
    SYNTAX  INTEGER
    ACCESS  read-only
    STATUS  optional
    DESCRIPTION
                "The current status of this output sub-unit.
         The status is an integer that is the sum of 5
         distinct values, Availability, Non-Critical, Critical,
         On-line, and Transitioning. These values are:     
         Availability                           value     
            Available and Idle              0       000'b     
            Available and Standby           2       010'b     
            Available and Active            4       100'b     
            Available and Busy              6       110'b     
            Unavailable and OnRequest       1       001'b     
            Unavailable because Broken      3       011'b     
            Unknown                         5       101'b     
         Non-Critical     
            No Non-Critical Alerts          0     
            Non-Critical Alerts             8     
         Critical     
            No Critical Alerts              0     
            Critical Alerts                 16     
         On-Line     
            Intended state is On-Line       0     
            Intended state is Off-Line      32     
         Transitioning     
            At intended state               0     
            Transitioning to intended state 64     
         
                Additional information:
                The default values assume all bins are empty.   
                See SubUnitStatus in RFC1759 Printer MIB for details on values reported by 
                this object. LaserJet 5Si will not include values Available and Standby (2), 
                Available and Active (4), Unknown (5) or Transitioning to intended state 
                (64)."
::= { prtOutputEntry 6 }
               
               
prtoutputname OBJECT-TYPE
    SYNTAX  OCTET STRING (SIZE(0..19))
    ACCESS  read-write
    STATUS  optional
    DESCRIPTION
                "The name assigned to this output sub-unit.
                Additional information:
                The characters must be in the range 20H to 7FH except 5C cannot be used. When 
                this string is displayed on the control panel the Roman-8 symbol set is 
                used.  
                The object for bin 2 is not available when the HCO is attached."
::= { prtOutputEntry 7 }
               
               
prtoutputvendorname OBJECT-TYPE
    SYNTAX  OCTET STRING (SIZE(0..63))
    ACCESS  read-only
    STATUS  optional
    DESCRIPTION
                "The vendor name of this output sub-unit.
                Additional information:
                "
::= { prtOutputEntry 8 }
               
               
prtoutputmodel OBJECT-TYPE
    SYNTAX  OCTET STRING (SIZE(0..63))
    ACCESS  read-only
    STATUS  optional
    DESCRIPTION
                "The name assigned to this output sub-unit.
                Additional information:
                The value returned by Tlatoani depends on the current 
                mode of the device. The possible values are as follows:  
                MULTIBIN MAILBOX C3764A  [BNPxxxx.x]  
                MULTIBIN STACKER C3764A  [BNPxxxx.x]  
                MULTIBIN SEPARATOR C3764A[BNPxxxx.x]   
                STAPLER MODULE C3766A [XX.XX.XX.XX]"
::= { prtOutputEntry 9 }
               
               
prtoutputversion OBJECT-TYPE
    SYNTAX  OCTET STRING (SIZE(0..63))
    ACCESS  read-only
    STATUS  optional
    DESCRIPTION
                "The version of this output sub-unit.
                Additional information:
                Returns device-specific information about the configuration 
                of the output bin. May include information about the type of 
                processing that can be done to media sent to this bin; 
                processing includes but is not limited to binding, punching, 
                folding and sealing. Format of this object is specified by 
                the output device documentation."
::= { prtOutputEntry 10 }
               
               
prtoutputserialnumber OBJECT-TYPE
    SYNTAX  OCTET STRING (SIZE(0..63))
    ACCESS  read-only
    STATUS  optional
    DESCRIPTION
                "The serial number assigned to this output sub-unit."
::= { prtOutputEntry 11 }
               
               
prtoutputdescription OBJECT-TYPE
    SYNTAX  OCTET STRING (SIZE(0..255))
    ACCESS  read-only
    STATUS  optional
    DESCRIPTION
                "  A free-form text description of this output sub-unit in the
        localization specified by prtGeneralCurrentLocalization."
::= { prtOutputEntry 12 }
               
               
prtoutputsecurity OBJECT-TYPE
    SYNTAX  INTEGER {
		   ePother(1),
		   ePon(3),
		   ePoff(4),
		   ePnotPresent(5)
		   }
    ACCESS  read-only
    STATUS  optional
    DESCRIPTION
                "Indicates if this output sub-unit has some security associated
        with it and if that security is enabled or not.
                Additional information:
                No security mechanism provided."
::= { prtOutputEntry 13 }
               
               
prtoutputstackingorder OBJECT-TYPE
    SYNTAX  INTEGER {
		   ePunknown(2),
		   ePfirstToLast(3),
		   ePlastToFirst(4)
		   }
    ACCESS  read-only
    STATUS  optional
    DESCRIPTION
                "The current state of the stacking order for the
        associated output sub-unit. `FirstToLast' means
        that as pages are output the front of the next page is
        placed against the back of the previous page.
        `LasttoFirst' means that as pages are output the back
        of the next page is placed against the front of the
        previous page. "
::= { prtOutputEntry 19 }
               
               
prtoutputpagedeliveryorientation OBJECT-TYPE
    SYNTAX  INTEGER {
		   ePfaceUp(3),
		   ePfaceDown(4)
		   }
    ACCESS  read-only
    STATUS  optional
    DESCRIPTION
                "The reading surface that will be `up' when pages are
        delivered to the associated output sub-unit. Values are
        Face-Up and Face-Down. (Note: interpretation of these
        values is in general context-dependent based on locale;
        presentation of these values to an end-user should be
        normalized to the expectations of the user)."
::= { prtOutputEntry 20 }
               
               
prtoutputbursting OBJECT-TYPE
    SYNTAX  INTEGER {
		   ePother(1),
		   ePon(3),
		   ePoff(4),
		   ePnotPresent(5)
		   }
    ACCESS  read-only
    STATUS  optional
    DESCRIPTION
                "This object indicates that the outputing sub-unit
        supports bursting, and if so, whether the feature is enabled.
        Bursting is the process by which continuous media is separated
        into individual sheets, typically by bursting along pre-formed
        perforations."
::= { prtOutputEntry 21 }
               
               
prtoutputdecollating OBJECT-TYPE
    SYNTAX  INTEGER {
		   ePother(1),
		   ePon(3),
		   ePoff(4),
		   ePnotPresent(5)
		   }
    ACCESS  read-only
    STATUS  optional
    DESCRIPTION
                "This object indicates that the output supports
        supports decollating, and if so, whether the feature
        is enabled. Decollating is the process by which the
        individual parts within a multi-part form are separated
        and sorted into separate stacks for each part."
::= { prtOutputEntry 22 }
               
               
prtoutputpagecollated OBJECT-TYPE
    SYNTAX  INTEGER {
		   ePother(1),
		   ePon(3),
		   ePoff(4),
		   ePnotPresent(5)
		   }
    ACCESS  read-only
    STATUS  optional
    DESCRIPTION
                "This object indicates that the output sub-unit
        supports page collation, and if so, whether the feature is
        enabled."
::= { prtOutputEntry 23 }
               
               
prtoutputoffsetstacking OBJECT-TYPE
    SYNTAX  INTEGER {
		   ePother(1),
		   ePon(3),
		   ePoff(4),
		   ePnotPresent(5)
		   }
    ACCESS  read-only
    STATUS  optional
    DESCRIPTION
                "This object indicates that the output supports
        supports offset stacking, and if so, whether the feature is
        enabled."
::= { prtOutputEntry 24 }
               
               
prtmarkerdefaultindex OBJECT-TYPE
    SYNTAX  INTEGER(1..65535)
    ACCESS  read-only
    STATUS  optional
    DESCRIPTION
                "The value of prtMarkerIndex  corresponding to the
        default markersub-unit; that is, this object selects the
        default marker."
::= { prtGeneralEntry 8 }
               
               
prtmarkermarktech OBJECT-TYPE
    SYNTAX  INTEGER {
		   ePother(1),
		   ePunknown(2),
		   ePelectrophotographicLED(3),
		   ePelectrophotographicLaser(4),
		   ePelectrophotographicOther(5),
		   ePimpactMovingHeadDotMatrix9pin(6),
		   ePimpactMovingHeadDotMatrix24pin(7),
		   ePimpactMovingHeadDotMatrixOther(8),
		   ePimpactMovingHeadFullyFormed(9),
		   ePimpactBand(10),
		   ePimpactOther(11),
		   ePinkjetAqueous(12),
		   ePinkjetSolid(13),
		   ePinkjetOther(14),
		   ePpen(15),
		   ePthermalTransfer(16),
		   ePthermalSensitive(17),
		   ePthermalDiffusion(18),
		   ePthermalOther(19),
		   ePelectroerosion(20),
		   ePelectrostatic(21),
		   ePphotographicMicrofiche(22),
		   ePphotographicImagesetter(23),
		   ePphotographicOther(24),
		   ePionDeposition(25),
		   ePeBeam(26),
		   ePtypesetter(27)
		   }
    ACCESS  read-only
    STATUS  optional
    DESCRIPTION
                "The type of marking technology used for this marking sub-unit."
::= { prtMarkerEntry 2 }
               
               
prtmarkercounterunit OBJECT-TYPE
    SYNTAX  INTEGER {
		   ePtenThousandthsOfInches(3),
		   ePmicrometers(4),
		   ePcharacters(5),
		   ePlines(6),
		   ePimpressions(7),
		   ePsheets(8),
		   ePdotRow(9),
		   ePhours(11),
		   ePfeet(16),
		   ePmeters(17)
		   }
    ACCESS  read-only
    STATUS  optional
    DESCRIPTION
                "The unit that will be used by the printer when reporting
        counter values for this marking sub-unit.  The
        time units of measure are provided for a device like a
        strip recorder that does not or cannot track the physical
        dimensions of the media and does not use characters,
        lines or sheets."
::= { prtMarkerEntry 3 }
               
               
prtmarkerlifecount OBJECT-TYPE
    SYNTAX  INTEGER
    ACCESS  read-only
    STATUS  optional
    DESCRIPTION
                "The count of the number of units of measure counted during
        the life of printer using units of measure as specified by
        CounterUnit.
                Additional information:
                In LaserJet 5Si the total engine page count is kept in
                NVRAM however the NVRAM value is only updated every 10
                impressions.  NOTE: The value returned by this OID will be
                incremented every page but if power is lost between
                NVRAM updates, up to 9 impressions of the page count 
                may be lost.  The counter will be reset to 
                zero after 16,777,215 ( 2^24-1) pages.  
                The page count is incremented when a sheet of media is pulled from an input
                tray. A duplex printed sheet will cause this counter to be incremented by
                two."
::= { prtMarkerEntry 4 }
               
               
prtmarkerpoweroncount OBJECT-TYPE
    SYNTAX  INTEGER
    ACCESS  read-only
    STATUS  optional
    DESCRIPTION
                "The count of the number of units of measure counted since the
        equipment was most recently powered on using units of measure as
        specified by CounterUnit."
::= { prtMarkerEntry 5 }
               
               
prtmarkerprocesscolorants OBJECT-TYPE
    SYNTAX  INTEGER(0..65535)
    ACCESS  read-only
    STATUS  optional
    DESCRIPTION
                "The number of process colors supported by this marker.  A
        process color of 1 implies monochrome.  The value of this
        object and SpotColorants cannot both be 0.  Must be 0 or
        greater."
::= { prtMarkerEntry 6 }
               
               
prtmarkerspotcolorants OBJECT-TYPE
    SYNTAX  INTEGER(0..65535)
    ACCESS  read-only
    STATUS  optional
    DESCRIPTION
                "The number of spot colors supported by this marker.  The
        value of this object and ProcessColorants cannot
        both be 0.  Must be 0 or greater."
::= { prtMarkerEntry 7 }
               
               
prtmarkeraddressabilityunit OBJECT-TYPE
    SYNTAX  INTEGER {
		   ePtenThousandthsOfInches(3),
		   ePmicrometers(4)
		   }
    ACCESS  read-only
    STATUS  optional
    DESCRIPTION
                "The unit of measure of distances."
::= { prtMarkerEntry 8 }
               
               
prtmarkeraddressabilityfeeddir OBJECT-TYPE
    SYNTAX  INTEGER
    ACCESS  read-only
    STATUS  optional
    DESCRIPTION
                "The  number of addressable marking positions in the feed
        direction per 10000 units of measure specified by
        AddressabilityUnit.  A value of (-1) implies 'other' or
        'infinite' while a value of (-2) implies 'unknown'."
::= { prtMarkerEntry 9 }
               
               
prtmarkeraddressabilityxfeeddir OBJECT-TYPE
    SYNTAX  INTEGER
    ACCESS  read-only
    STATUS  optional
    DESCRIPTION
                "The number of addressable marking positions in the cross
        feed direction in 10000 units of measure specified by
        AddressabilityUnit.  A value of (-1) implies 'other' or
        'infinite' while a value of (-2) implies 'unknown'."
::= { prtMarkerEntry 10 }
               
               
prtmarkernorthmargin OBJECT-TYPE
    SYNTAX  INTEGER
    ACCESS  read-only
    STATUS  optional
    DESCRIPTION
                "The margin, in units identified by AddressabilityUnit,
        from the leading edge of the medium as the medium flows
        throught the marking engine with the side to be imaged
        facing the observer. The leading edge is the North edge
        and the other edges are defined by the normal compass
        layout of  directions with the compass facing the
        observer.  Printing within the area bounded by all four
        margins is guaranteed for all interpreters.   The value
        (-2) means unknown."
::= { prtMarkerEntry 11 }
               
               
prtmarkersouthmargin OBJECT-TYPE
    SYNTAX  INTEGER
    ACCESS  read-only
    STATUS  optional
    DESCRIPTION
                "The margin from the South edge  (see NorthMargin)
        of the medium in units identified by
        AddressabilityUnit.  Printing within the area bounded by
        all four margins  is guaranteed for all interpreters.
        The value (-2) means unknown."
::= { prtMarkerEntry 12 }
               
               
prtmarkerwestmargin OBJECT-TYPE
    SYNTAX  INTEGER
    ACCESS  read-only
    STATUS  optional
    DESCRIPTION
                "The margin from the West edge (see NorthMargin) of the
        medium in units identified by AddressabilityUnit.
        Printing within the area bouned by all four margins is
        guaranteed for all interpreters.   The value (-2) means
        unknown."
::= { prtMarkerEntry 13 }
               
               
prtmarkereastmargin OBJECT-TYPE
    SYNTAX  INTEGER
    ACCESS  read-only
    STATUS  optional
    DESCRIPTION
                "The margin from the East edge (see NorthMargin) of the
        medium in units identified by AddressabilityUnit.
        Printing within the area bounded by all four margins is
        guaranteed for all interpreters. The value (-2) means
        unknown."
::= { prtMarkerEntry 14 }
               
               
prtmarkerstatus OBJECT-TYPE
    SYNTAX  INTEGER
    ACCESS  read-only
    STATUS  optional
    DESCRIPTION
                "The current status of this marker sub-unit.
         The status is an integer that is the sum of 5
         distinct values, Availability, Non-Critical, Critical,
         On-line, and Transitioning. These values are:     
         Availability                           value     
            Available and Idle              0       000'b     
            Available and Standby           2       010'b     
            Available and Active            4       100'b     
            Available and Busy              6       110'b     
            Unavailable and OnRequest       1       001'b     
            Unavailable because Broken      3       011'b     
            Unknown                         5       101'b     
         Non-Critical     
            No Non-Critical Alerts          0     
            Non-Critical Alerts             8     
         Critical     
            No Critical Alerts              0     
            Critical Alerts                 16     
         On-Line     
            Intended state is On-Line       0     
            Intended state is Off-Line      32     
         Transitioning     
            At intended state               0     
            Transitioning to intended state 64     
        
                Additional information:
                See SubUnitStatus in RFC1759 Printer MIB for details on values reported by 
                this object. LaserJet 5Si will not include values
                Available and Active (4) or Unknown (5)."
::= { prtMarkerEntry 15 }
               
               
prtmarkersuppliesmarkerindex OBJECT-TYPE
    SYNTAX  INTEGER(0..65535)
    ACCESS  read-only
    STATUS  optional
    DESCRIPTION
                "The value of prtMarkerIndex corresponding to the
        marking sub-unit with which this marker supply
        sub-unit is associated."
::= { prtMarkerSuppliesEntry 2 }
               
               
prtmarkersuppliescolorantindex OBJECT-TYPE
    SYNTAX  INTEGER(0..65535)
    ACCESS  read-only
    STATUS  optional
    DESCRIPTION
                "The value of prtMarkerColorantIndex
        corresponding to the colorant with which this
        marker supply sub-unit is associated.  This value
        shall be 0 if there is no colorant table."
::= { prtMarkerSuppliesEntry 3 }
               
               
prtmarkersuppliesclass OBJECT-TYPE
    SYNTAX  INTEGER {
		   ePother(1),
		   ePsupplyThatIsConsumed(3),
		   ePreceptacleThatIsFilled(4)
		   }
    ACCESS  read-only
    STATUS  optional
    DESCRIPTION
                "Indicates whether this supply entity represents a supply
        container that is consumed or a receptacle that is filled."
::= { prtMarkerSuppliesEntry 4 }
               
               
prtmarkersuppliestype OBJECT-TYPE
    SYNTAX  INTEGER {
		   ePother(1),
		   ePunknown(2),
		   ePtoner(3),
		   ePwasteToner(4),
		   ePink(5),
		   ePinkCartridge(6),
		   ePinkRibbon(7),
		   ePwasteInk(8),
		   ePopc(9),
		   ePdeveloper(10),
		   ePfuserOil(11),
		   ePsolidWax(12),
		   ePribbonWax(13),
		   ePwasteWax(14)
		   }
    ACCESS  read-only
    STATUS  optional
    DESCRIPTION
                "The type of this supply."
::= { prtMarkerSuppliesEntry 5 }
               
               
prtmarkersuppliesdescription OBJECT-TYPE
    SYNTAX  OCTET STRING (SIZE(0..255))
    ACCESS  read-only
    STATUS  optional
    DESCRIPTION
                "The description of this supply container/receptacle in the
        localization specified by prtGeneralCurrentLocalization."
::= { prtMarkerSuppliesEntry 6 }
               
               
prtmarkersuppliessupplyunit OBJECT-TYPE
    SYNTAX  INTEGER {
		   ePtenThousandthsOfInches(3),
		   ePmicrometers(4),
		   ePthousandthsOfOunces(12),
		   ePtenthsOfGrams(13),
		   ePhundrethsOfFluidOunces(14),
		   ePtenthsOfMilliliters(15)
		   }
    ACCESS  read-only
    STATUS  optional
    DESCRIPTION
                "Unit of this marker supply container/receptacle."
::= { prtMarkerSuppliesEntry 7 }
               
               
prtmarkersuppliesmaxcapacity OBJECT-TYPE
    SYNTAX  INTEGER
    ACCESS  read-only
    STATUS  optional
    DESCRIPTION
                "The maximum capacity of this supply container/receptacle
        expressed in SupplyUnit. If this supply
        container/receptacle can reliably sense this value, the
        value is sensed by the printer and is read-only;
        otherwise, the value may be written (by a Remote Contol
        Panel or a Management Application). The value (-1) means
        other and specifically indicates that the sub-unit places
        no restrictions on this parameter. The value (-2) means
        unknown."
::= { prtMarkerSuppliesEntry 8 }
               
               
prtmarkersupplieslevel OBJECT-TYPE
    SYNTAX  INTEGER
    ACCESS  read-only
    STATUS  optional
    DESCRIPTION
                "The current level if this supply is a container; the
        remaining space if this supply is a receptacle. If this
        supply container/receptacle can reliably sense this
        value, the value is sensed by the printer and is
        read-only; otherwise, the value may be written (by a
        Remote Contol Panel or a Management Application). The
        value (-1) means other and specifically indicates that
        the sub-unit places no restrictions on this parameter.
        The value (-2) means unknown.  A value of (-3) means that the
        printer knows that there is some supply/remaining space,
        respectively.
                Additional information:
                LaserJet 5Si detects the toner level as being either
                above or below the 'LOW' sensor. Therefore, a value
                of -3 is returned when the level is above the 'LOW'
                sensor and a value of -2 is returned when the toner
                cartridge detects the 'LOW' condition."
::= { prtMarkerSuppliesEntry 9 }
               
               
prtmediapathdefaultindex OBJECT-TYPE
    SYNTAX  INTEGER(1..3)
    ACCESS  read-write
    STATUS  optional
    DESCRIPTION
                "The value of prtMediaPathIndex corresponding to
        the default media path; that is, the selection of the
        default media path."
::= { prtGeneralEntry 9 }
               
               
prtmediapathmaxspeedprintunit OBJECT-TYPE
    SYNTAX  INTEGER {
		   ePtenThousandthsOfInchesPerHour(3),
		   ePmicrometersPerHour(4),
		   ePcharactersPerHour(5),
		   ePlinesPerHour(6),
		   ePimpressionsPerHour(7),
		   ePsheetsPerHour(8),
		   ePdotRowPerHour(9),
		   ePfeetPerHour(16),
		   ePmetersPerHour(17)
		   }
    ACCESS  read-only
    STATUS  optional
    DESCRIPTION
                "The unit of measure used in specifying the speed of all media
        paths in the printer."
::= { prtMediaPathEntry 2 }
               
               
prtmediapathmediasizeunit OBJECT-TYPE
    SYNTAX  INTEGER {
		   ePtenThousandthsOfInches(3),
		   ePmicrometers(4)
		   }
    ACCESS  read-only
    STATUS  optional
    DESCRIPTION
                "The units of measure of media size for use in calculating and
        relaying dimensional values for all media paths in the printer."
::= { prtMediaPathEntry 3 }
               
               
prtmediapathmaxspeed OBJECT-TYPE
    SYNTAX  INTEGER
    ACCESS  read-only
    STATUS  optional
    DESCRIPTION
                "The maximum printing speed of this media path expressed in
        prtMediaPathMaxSpeedUnit's.  A value of (-1) implies
        'other'.
                Additional information:
                The page size for this performance is 8.5x11. The 
                duplex speed is based on 9.5 ppm."
::= { prtMediaPathEntry 4 }
               
               
prtmediapathmaxmediafeeddir OBJECT-TYPE
    SYNTAX  INTEGER
    ACCESS  read-only
    STATUS  optional
    DESCRIPTION
                "The maximum physical media size in the feed direction of this
        media path expressed in units of measure specified by
        MediaSizeUnit.  A value of (-1) implies 'unlimited'.  A value
        of (-2) implies 'unknown'
                Additional information:
                The value returned by this object depends on the value 
                of prtMediaPathMediaSizeUnit. It is 177000 if prtMediaPathMediaSizeUnit is 
                ePtenThousandthsOfInches or 449600 if prtMediaPathMediaSizeUnit is 
                ePmicrometers."
::= { prtMediaPathEntry 5 }
               
               
prtmediapathmaxmediaxfeeddir OBJECT-TYPE
    SYNTAX  INTEGER
    ACCESS  read-only
    STATUS  optional
    DESCRIPTION
                "The maximum physical media size across the feed direction of
        this media path expressed in units of measure specified by
        MediaSizeUnit.  A value of (-2) implies 'unknown'.
                Additional information:
                The value returned by this object depends on the value 
                of prtMediaPathMediaSizeUnit. It is 117000 if prtMediaPathMediaSizeUnit is 
                ePtenThousandthsOfInches or 297000 if prtMediaPathMediaSizeUnit is 
                ePmicrometers."
::= { prtMediaPathEntry 6 }
               
               
prtmediapathminmediafeeddir OBJECT-TYPE
    SYNTAX  INTEGER
    ACCESS  read-only
    STATUS  optional
    DESCRIPTION
                "The minimum physical media size in the feed direction of this
        media path expressed in units of measure specified by
        MediaSizeUnit. A value of (-2) implies 'unknown'.
                Additional information:
                The value returned by this object depends on the value 
                of prtMediaPathMediaSizeUnit. For the simplex paper path it is 75000 if 
                prtMediaPathMediaSizeUnit is 
                ePtenThousandthsOfInches or 190500 if prtMediaPathMediaSizeUnit is 
                ePmicrometers. For the duplex paper path it is 105000 if 
                prtMediaPathMediaSizeUnit is 
                ePtenThousandthsOfInches or 266700 if prtMediaPathMediaSizeUnit is 
                ePmicrometers.  
                This sizes correspond to a Monarch envelope length for simplex, Executive 
                paper length for duplex. ( Note: When printing on Custom size media, the 
                engine will allow a paper size smaller than Executive for the duplex path, 
                but Executive is the smallest supported size.)"
::= { prtMediaPathEntry 7 }
               
               
prtmediapathminmediaxfeeddir OBJECT-TYPE
    SYNTAX  INTEGER
    ACCESS  read-only
    STATUS  optional
    DESCRIPTION
                "The minimum physical media size across the feed direction of
        this media path expressed in units of measure specified by
        MediaSizeUnit.  A value of (-2) implies 'unknown'.
                Additional information:
                The value returned by this object depends on the value 
                of prtMediaPathMediaSizeUnit. It is 38750 if prtMediaPathMediaSizeUnit is 
                ePtenThousandthsOfInches or 98425 if prtMediaPathMediaSizeUnit is 
                ePmicrometers.  
                This size corresponds to a Monarch envelope for the simplex path, Executive 
                size for the duplex path. ( Note: When printing on Custom size media, the 
                engine will allow a paper size smaller than Executive for the duplex path, 
                but Executive is the smallest supported size.)"
::= { prtMediaPathEntry 8 }
               
               
prtmediapathtype OBJECT-TYPE
    SYNTAX  INTEGER {
		   ePlongEdgeBindingDuplex(3),
		   ePshortEdgeBindingDuplex(4),
		   ePsimplex(5)
		   }
    ACCESS  read-only
    STATUS  optional
    DESCRIPTION
                "The type of the media path for this media path. "
::= { prtMediaPathEntry 9 }
               
               
prtmediapathdescription OBJECT-TYPE
    SYNTAX  OCTET STRING (SIZE(0..255))
    ACCESS  read-only
    STATUS  optional
    DESCRIPTION
                "The manufacturer-provided description of this media path in
        the localization specified by prtGeneralCurrentLocalization."
::= { prtMediaPathEntry 10 }
               
               
prtmediapathstatus OBJECT-TYPE
    SYNTAX  INTEGER
    ACCESS  read-only
    STATUS  optional
    DESCRIPTION
                "The current status of this media path.
         The status is an integer that is the sum of 5
         distinct values, Availability, Non-Critical, Critical,
         On-line, and Transitioning. These values are:     
         Availability                           value     
            Available and Idle              0       000'b     
            Available and Standby           2       010'b     
            Available and Active            4       100'b     
            Available and Busy              6       110'b     
            Unavailable and OnRequest       1       001'b     
            Unavailable because Broken      3       011'b     
            Unknown                         5       101'b     
         Non-Critical     
            No Non-Critical Alerts          0     
            Non-Critical Alerts             8     
         Critical     
            No Critical Alerts              0     
            Critical Alerts                 16     
         On-Line     
            Intended state is On-Line       0     
            Intended state is Off-Line      32     
         Transitioning     
            At intended state               0     
            Transitioning to intended state 64     
         
                Additional information:
                The default values assume the printer is idle.   
                See SubUnitStatus in RFC1759 Printer MIB for details on values reported by 
                this object. LaserJet 5Si will not include values Available and Standby (2), 
                Available and Active (4), Unknown (5), Non-CriticalAlerts (8) or Transitioning 
                to intended state (64)."
::= { prtMediaPathEntry 11 }
               
               
prtchanneltype OBJECT-TYPE
    SYNTAX  INTEGER {
		   ePother(1),
		   ePchIEEE1284Port(5),
		   ePchAppleTalkPAP(7),
		   ePchNetwarePServer(10),
		   ePchPort9100(11),
		   ePchDLCLLCPort(15)
		   }
    ACCESS  read-only
    STATUS  optional
    DESCRIPTION
                "The type of this print data channel.  This
        object provides the linkage to ChannelType-specific
        groups that may (conceptually) extend the prtChannelTable
        with additional details about that channel.
                Additional information:
                MIO-based channels provide their own values."
::= { prtChannelEntry 2 }
               
               
prtchannelprotocolversion OBJECT-TYPE
    SYNTAX  OCTET STRING (SIZE(0..63))
    ACCESS  read-only
    STATUS  optional
    DESCRIPTION
                "The version of the protocol used on this
        channel.  The format used for version numbering depends
        on prtChannelType.
                Additional information:
                MIO-based channels provide their own values.  
                The channel 1 value includes (separated by semi colons) different aspects of 
                the spec: electrical;logical; and physical connector."
::= { prtChannelEntry 3 }
               
               
prtchannelcurrentjobcntllangindex OBJECT-TYPE
    SYNTAX  INTEGER
    ACCESS  read-only
    STATUS  optional
    DESCRIPTION
                "The value of prtInterpreterIndex  corresponding to the
        Control Language Interpreter for this channel. This
        interpreter defines the syntax used for control
        functions, such as querying or changing environment
        variables and identifying job boundaries (e.g. PJL,
        PostScript, NPAP). Must be 1 or greater.
                Additional information:
                This object points to the PJL language. It is 
                read-only because PJL is the printer's only job 
                control language. It is the same for all channels."
::= { prtChannelEntry 4 }
               
               
prtchanneldefaultpagedesclangindex OBJECT-TYPE
    SYNTAX  INTEGER
    ACCESS  read-write
    STATUS  optional
    DESCRIPTION
                "The value of prtInterpreterIndex  corresponding to the
        Page Description Language Interpreter for this channel.
        This interpreter defines the default Page Description
        Language interpreter to be used for the print data unless
        the Control Language is used to select a specific
        interpreter (e.g.,  PCL, PostScript Language,
        auto-sense). Must be 1 or greater.
                Additional information:
                The default points to the automatic language switcher. If this object 
                is changed for one channel, all channels will be 
                changed."
::= { prtChannelEntry 5 }
               
               
prtchannelstate OBJECT-TYPE
    SYNTAX  INTEGER {
		   ePother(1),
		   ePprintDataAccepted(3),
		   ePnoDataAccepted(4)
		   }
    ACCESS  read-only
    STATUS  optional
    DESCRIPTION
                "The state of this print data channel.  The value determines
        whether control information and print data is allowed through
        this channel or not.
                Additional information:
                MIO-based channels provide their own values for this 
                object.  
                The base-printer's port always reports a value of ePprintDataAccepted. If 
                the printer is offline, that is detected by reading the Host Resources General 
                Printer Status objects, not by reading this object."
::= { prtChannelEntry 6 }
               
               
prtchannelifindex OBJECT-TYPE
    SYNTAX  INTEGER
    ACCESS  read-only
    STATUS  optional
    DESCRIPTION
                "The value of ifIndex (in the ifTable; see the interface
        section of MIB-2/RFC 1213) which corresponds to this channel.
        When more than one row of the ifTable is relevant, this is
        the index of the row representing the topmost layer in the
        interface hierarchy.  A value of zero indicates that no
        interface is associated with this channel.
                Additional information:
                MIO-based channels provide their own values for this 
                object."
::= { prtChannelEntry 7 }
               
               
prtchannelstatus OBJECT-TYPE
    SYNTAX  INTEGER
    ACCESS  read-only
    STATUS  optional
    DESCRIPTION
                "The current status of the channel.
         The status is an integer that is the sum of 5
         distinct values, Availability, Non-Critical, Critical,
         On-line, and Transitioning. These values are:     
         Availability                           value     
            Available and Idle              0       000'b     
            Available and Standby           2       010'b     
            Available and Active            4       100'b     
            Available and Busy              6       110'b     
            Unavailable and OnRequest       1       001'b     
            Unavailable because Broken      3       011'b     
            Unknown                         5       101'b     
         Non-Critical     
            No Non-Critical Alerts          0     
            Non-Critical Alerts             8     
         Critical     
            No Critical Alerts              0     
            Critical Alerts                 16     
         On-Line     
            Intended state is On-Line       0     
            Intended state is Off-Line      32     
         Transitioning     
            At intended state               0     
            Transitioning to intended state 64     
        
                Additional information:
                See SubUnitStatus in RFC1759 Printer MIB for details 
                on values reported by this object. MIO-based channels provide their own values 
                for this object. Status for LaserJet 5Si's parallel port will not include   
                values Available and Standby (2), Available and Active (4), Non-Critical 
                Alerts (8) or Transitioning to intended state (64)."
::= { prtChannelEntry 8 }
               
               
prtinterpreterlangfamily OBJECT-TYPE
    SYNTAX  INTEGER {
		   ePlangPCL(3),
		   ePlangPJL(5),
		   ePlangPS(6),
		   ePlangAutomatic(37)
		   }
    ACCESS  read-only
    STATUS  optional
    DESCRIPTION
                "The family name of a Page Description Language (PDL) or
        control language which this interpreter in the printer can
        interpret or emulate.  This type 2 list of enumerations
        requires review before additional entries are made.
                Additional information:
                Also provides a place to supply PJL information and
                overall ROM information ( by using the language
                switcher as a separate language)."
::= { prtInterpreterEntry 2 }
               
               
prtinterpreterlanglevel OBJECT-TYPE
    SYNTAX  OCTET STRING (SIZE(0..31))
    ACCESS  read-only
    STATUS  optional
    DESCRIPTION
                "The level of the language which this interpreter is
        interpreting or emulating.  This might contain a value like
        '5e' for an interpreter which is emulating level 5e of the PCL
        language.  It might contain '2' for an interpreter which is
        emulating level 2 of the PostScript language.  Similarly it
        might contain '2' for an interpreter which is emulating level
        2 of the HPGL language."
::= { prtInterpreterEntry 3 }
               
               
prtinterpreterlangversion OBJECT-TYPE
    SYNTAX  OCTET STRING (SIZE(0..31))
    ACCESS  read-only
    STATUS  optional
    DESCRIPTION
                "The date code or version of the language which this interpreter
        is interpreting or emulating.
                Additional information:
                For PostScript, this is more detailed revision 
                information."
::= { prtInterpreterEntry 4 }
               
               
prtinterpreterdescription OBJECT-TYPE
    SYNTAX  OCTET STRING (SIZE(0..255))
    ACCESS  read-only
    STATUS  optional
    DESCRIPTION
                "A string to identify this interpreter in the localization
        specified by prtGeneralCurrentLocalization as opposed to the
        language which is being interpreted.  It is anticipated that
        this string will allow manufacturers to unambiguously identify
        their interpreters.
                Additional information:
                None of these strings are localized."
::= { prtInterpreterEntry 5 }
               
               
prtinterpreterversion OBJECT-TYPE
    SYNTAX  OCTET STRING (SIZE(0..31))
    ACCESS  read-only
    STATUS  optional
    DESCRIPTION
                "The date code, version number, or other product specific
        information tied to this interpreter.  This value is
        associated with the interpreter, rather than with the version
        of the language which is being interpreted or emulated.
                Additional information:
                Same as prtInterpreterLangVersion."
::= { prtInterpreterEntry 6 }
               
               
prtinterpreterdefaultorientation OBJECT-TYPE
    SYNTAX  INTEGER {
		   ePportrait(3),
		   ePlandscape(4)
		   }
    ACCESS  read-write
    STATUS  optional
    DESCRIPTION
                "The current orientation default for this interpreter.  This
        value may be overridden for a particular job (e.g., by a
        command in the input data stream).
                Additional information:
                Setting this object for one interpreter will change it 
                for all installed interpreters.  
                Interpreters 1, 2 and 4 ignore the value of this 
                object."
::= { prtInterpreterEntry 7 }
               
               
prtinterpreterfeedaddressability OBJECT-TYPE
    SYNTAX  INTEGER
    ACCESS  read-only
    STATUS  optional
    DESCRIPTION
                "The maximum interpreter addressability in the feed
        direction in 10000 prtMarkerAddressabilityUnit s (see
        prtMarkerAddressabilityFeedDir ) for this interpreter.
        The value (-1) means other and specifically indicates
        that the sub-unit places no restrictions on this parameter."
::= { prtInterpreterEntry 8 }
               
               
prtinterpreterxfeedaddressability OBJECT-TYPE
    SYNTAX  INTEGER
    ACCESS  read-only
    STATUS  optional
    DESCRIPTION
                "The maximum interpreter addressability in the cross feed
        direction in 10000 prtMarkerAddressabilityUnit s (see
        prtMarkerAddressabilityXFeedDir) for this interpreter.
        The value (-1) means other and specifically indicates
        that the sub-unit places no restrictions on this
        parameter."
::= { prtInterpreterEntry 9 }
               
               
prtinterpreterdefaultcharsetin OBJECT-TYPE
    SYNTAX  INTEGER {
		   ePcsASCII(3),
		   ePcsISOLatin1(4),
		   ePcsISOLatin2(5),
		   ePcsISOLatin5(12),
		   ePcsISO4UnitedKingdom(20),
		   ePcsISO11SwedishforNames(21),
		   ePcsISO15Italian(22),
		   ePcsISO17Spanish(23),
		   ePcsISO21German(24),
		   ePcsISO60DanishNorwegian(25),
		   ePcsISO69French(26),
		   ePcsWindows30Latin1(2000),
		   ePcsWindows31Latin1(2001),
		   ePcsWindows31Latin2(2002),
		   ePcsWindows31Latin5(2003),
		   ePcsHPRoman8(2004),
		   ePcsAdobeStandardEncoding(2005),
		   ePcsVenturaUS(2006),
		   ePcsVenturaInternational(2007),
		   ePcsPC850Multilingual(2009),
		   ePcsPCp852(2010),
		   ePcsPC8CodePage437(2011),
		   ePcsPC8DNDanishNorwegian(2012),
		   ePcsHPPC8Turkish(2014),
		   ePcsHPLegal(2017),
		   ePcsHPPiFont(2018),
		   ePcsHPMath8(2019),
		   ePcsHPPSMath(2020),
		   ePcsHPDeskTop(2021),
		   ePcsVenturaMath(2022),
		   ePcsMicrosoftPublishing(2023),
		   ePcsWindows31J(2024)
		   }
    ACCESS  read-write
    STATUS  optional
    DESCRIPTION
                "The default coded character set for input octets
        encountered outside a context in which the Page
        Description Language established the interpretation
        of the octets.
        This value shall be (2) if there is no default.
                Additional information:
                ePcsAdobeStandardEncoding is the same as PSText 
                ( 10J).  
                The object corresponding to PCL has read-write access; 
                all others are read-only."
::= { prtInterpreterEntry 10 }
               
               
prtinterpreterdefaultcharsetout OBJECT-TYPE
    SYNTAX  INTEGER {
		   ePcsNoDefault(2),
		   ePcsASCII(3),
		   ePcsHPRoman8(2004),
		   ePcsAdobeStandardEncoding(2005)
		   }
    ACCESS  read-only
    STATUS  optional
    DESCRIPTION
                "The default character set for data coming from this interpreter
        through the printer's output channel.
        This value shall be (2) if there is no default.
                Additional information:
                "
::= { prtInterpreterEntry 11 }
               
               
prtinterpretertwoway OBJECT-TYPE
    SYNTAX  INTEGER {
		   ePyes(3),
		   ePno(4)
		   }
    ACCESS  read-only
    STATUS  optional
    DESCRIPTION
                "Indicates whether or not this interpreter returns information
        back to the host."
::= { prtInterpreterEntry 12 }
               
               
prtconsolelocalization OBJECT-TYPE
    SYNTAX  INTEGER(1..14)
    ACCESS  read-write
    STATUS  optional
    DESCRIPTION
                "The value of the prtLocalizationIndex corresponding to
        the language, country, and character set to be used for the
        console.  This localization applies both to the actual display
        on the console as well as the encoding of these console
        objects in management operations.
                Additional information:
                The value of this object is saved in NVRAM.  
                If a localized string is currently being
                displayed on the control panel by the device, changing this object will cause
                the displayed string to be changed to its new value. If this object is changed 
                while the printer is processing a page that 
                contains localized strings has started, the results are undefined."
::= { prtGeneralEntry 10 }
               
               
prtconsolenumberofdisplaylines OBJECT-TYPE
    SYNTAX  INTEGER(0..65535)
    ACCESS  read-only
    STATUS  optional
    DESCRIPTION
                "The number of lines on the printer's physical
        display.  This value is 0 if there are no lines on the
        physical display or if there is no physical display."
::= { prtGeneralEntry 11 }
               
               
prtconsolenumberofdisplaychars OBJECT-TYPE
    SYNTAX  INTEGER(0..65535)
    ACCESS  read-only
    STATUS  optional
    DESCRIPTION
                "The number of characters per line displayed on the physical
        display.  This value is 0 if there are no lines on the
        physical display or if there is no physical display."
::= { prtGeneralEntry 12 }
               
               
prtconsoledisable OBJECT-TYPE
    SYNTAX  INTEGER {
		   ePenabled(3),
		   ePdisabled(4)
		   }
    ACCESS  read-write
    STATUS  optional
    DESCRIPTION
                "This object enables or disables manual input from the
        operators console.
                Additional information:
                If the object prtConsoleDisable has value 'disabled' 
                then manual input is not accepted from the operator 
                console.  If the object prtConsoleDisable has the 
                value 'enabled' then manual input is accepted from the 
                operator console.  
                Service Mode is not changed by this object."
::= { prtGeneralEntry 13 }
               
               
prtconsoledisplaybuffertext OBJECT-TYPE
    SYNTAX  OCTET STRING (SIZE(0..255))
    ACCESS  read-write
    STATUS  optional
    DESCRIPTION
                "The content of a line in the logical display buffer of
        the operator's console of the printer.  When a write
        operation occurs, normally a critical message, to one of
        the LineText strings, the agent should make that line
        displayable if a physical display is present.  Writing
        a zero length string clears the line.  It is an
        implementation-specific matter as to whether the agent allows
        a line to be overwritten before it has been cleared.
        Printer generated strings shall be in the localization
        specified by ConsoleLocalization.  Management Application
        generated strings should be localized by the Management
        Application.
                Additional information:
                This object does not have to be cleared before a new string is written; the 
                new string immediately replaces the old one.  
                When a 79 SERVICE message is displayed, it is not possible to write to this 
                object ( or any other object for that matter)."
::= { prtConsoleDisplayBufferEntry 2 }
               
               
prtconsoleontime OBJECT-TYPE
    SYNTAX  INTEGER
    ACCESS  read-only
    STATUS  optional
    DESCRIPTION
                "The on time in milliseconds of blinking of this light; 0
        indicates off always.  If both prtConsoleOnTime
        and prtConsoleOffTime are 0, then the light is
        always off.
                Additional information:
                There are three control panel LED's: Online ( index 1), 
                Data ( index 2) 
                and Attention ( index 3). When an LED blinks, it is typically on for one half 
                second and off for one half second; the value used for this object is 500 
                whether the LED is on or blinking.  "
::= { prtConsoleLightEntry 2 }
               
               
prtconsoleofftime OBJECT-TYPE
    SYNTAX  INTEGER
    ACCESS  read-only
    STATUS  optional
    DESCRIPTION
                "The off time in milliseconds of blinking of this light; 0
        indicates on always.  If both prtConsoleOnTime
        and prtConsoleOffTime are 0, then the light is
        always off.
                Additional information:
                There are three control panel LED's: Online ( index 1), 
                Data ( index 2) 
                and Attention ( index 3). When an LED blinks, it is typically on for one half 
                second and off for one half second; the value used for this object is 500 
                when the LED is blinking, otherwise it is zero.  "
::= { prtConsoleLightEntry 3 }
               
               
prtconsolecolor OBJECT-TYPE
    SYNTAX  INTEGER {
		   ePother(1),
		   ePunknown(2),
		   ePwhite(3),
		   ePred(4),
		   ePgreen(5),
		   ePblue(6),
		   ePcyan(7),
		   ePmagenta(8),
		   ePyellow(9)
		   }
    ACCESS  read-only
    STATUS  optional
    DESCRIPTION
                "The color of this light."
::= { prtConsoleLightEntry 4 }
               
               
prtconsoledescription OBJECT-TYPE
    SYNTAX  OCTET STRING (SIZE(0..255))
    ACCESS  read-only
    STATUS  optional
    DESCRIPTION
                "The vendor description or label of this light in the
        localization specified by prtConsoleLocalization."
::= { prtConsoleLightEntry 5 }
               
               
prtalertseveritylevel OBJECT-TYPE
    SYNTAX  INTEGER {
		   ePother(1),
		   ePcritical(3),
		   ePwarning(4)
		   }
    ACCESS  read-only
    STATUS  optional
    DESCRIPTION
                "The level of severity of this alert table entry.  The printer
        determines the severity level assigned to each entry into the
        table."
::= { prtAlertEntry 2 }
               
               
prtalerttraininglevel OBJECT-TYPE
    SYNTAX  INTEGER {
		   ePother(1),
		   ePuntrained(3),
		   ePtrained(4),
		   ePfieldService(5),
		   ePmanagement(6)
		   }
    ACCESS  read-only
    STATUS  optional
    DESCRIPTION
                "The level of training required to handle this alert. The
        training level is an enumeration that is determined and
        assigned by the printer manufacturer based on the information
        or the training required to handle this alert.  The printer
        will break alerts into these different training levels.  It is
        the responsibility of the management application in the system
        to determine how a particular alert is handled and how and to
        whom that alert is routed.  The following are the four
        training levels of alerts:     
               Field Service - Alerts that typically require advanced     
                      training and technical knowledge of the printer     
                      and its sub-units. An example of a technical     
                      person would be a manufacture's Field Service     
                      representative, or other person formally     
                      trained by the manufacturer or similar     
                      representative.     
               Trained - Alerts that require an intermediate or moderate     
                      level of knowledge of the printer and its     
                      sub-units. A typical examples of alerts that     
                      a trained operator can handle is replacing     
                      toner cartridges.     
               Untrained - Alerts that can be fixed without prior     
                      training either because the action to correct     
                      the alert is obvious or the printer can help the     
                      untrained person fix the problem. A typical     
                      example of such an alert is reloading paper     
                      trays and emptying output bins on a low end     
                      printer.     
               Management - Alerts that have to do with overall     
                      operation of and configuration of the printer.     
                      Examples of management events are configuration     
                      change of sub-units.     
                Additional information:
                The value of this object depends on the alert
                condition as follows:   
                ePuntrained: Paper low/out.  
                ePtrained: Toner low.  
                ePfieldService: Marker failure.  
                ePmanagement: Configuration change."
::= { prtAlertEntry 3 }
               
               
prtalertgroup OBJECT-TYPE
    SYNTAX  INTEGER {
		   ePgeneralPrinter(5),
		   ePcover(6),
		   ePinput(8),
		   ePoutput(9),
		   ePmarker(10),
		   ePchannel(14)
		   }
    ACCESS  read-only
    STATUS  optional
    DESCRIPTION
                "The type of sub-unit within the printer model that this alert
        is related.  Input, output, and markers are examples of
        printer model groups, i.e., examples of types of sub-units.
        Whereever possible, these enumerations match the
        sub-identifier that identifies the relevant table in the
        printmib."
::= { prtAlertEntry 4 }
               
               
prtalertgroupindex OBJECT-TYPE
    SYNTAX  INTEGER
    ACCESS  read-only
    STATUS  optional
    DESCRIPTION
                "An index of the row within the principle table in the
        group identified by prtAlertGroup that represents the
        sub-unit of the printer that caused this alert.  The
        combination of the Group and the GroupIndex defines
        exactly which printer sub-unit caused the alert.; for
        example, Input #3, Output #2, and Marker #1.
        Every object in this MIB is indexed with hrDeviceIndex and
        optionally, another index variable.  If this other index
        variable is present in the table that generated the alert, it
        will be used as the value for this object.  Otherwise, this
        value shall be -1."
::= { prtAlertEntry 5 }
               
               
prtalertlocation OBJECT-TYPE
    SYNTAX  INTEGER
    ACCESS  read-only
    STATUS  optional
    DESCRIPTION
                "The sub-unit location that is defined by the printer
        manufacturer to further refine the location of this alert
        within the designated sub-unit.  The location is used in
        conjunction with the Group and GroupIndex values; for
        example, there is an alert in Input #2 at location number 7."
::= { prtAlertEntry 6 }
               
               
prtalertcode OBJECT-TYPE
    SYNTAX  INTEGER {
		   ePother(1),
		   ePjam(8),
		   ePdoorOpenAlert(501),
		   ePinputMediaTrayMissing(801),
		   ePinputMediaSupplyEmpty(808),
		   ePoutputMediaTrayFull(903),
		   ePmarkerFuserUnderTemperature(1001),
		   ePmarkerFuserOverTemperature(1002),
		   ePmarkerTonerEmpty(1101),
		   ePmarkerTonerAlmostEmpty(1104)
		   }
    ACCESS  read-only
    STATUS  optional
    DESCRIPTION
                "The code that describes the type of alert for this entry in
        the table.  There are different codes for each
        sub-unit type: for example, Media Supply Low and Media
        Supply Empty are Aler codes for the Input sub-unit."
::= { prtAlertEntry 7 }
               
               
prtalertdescription OBJECT-TYPE
    SYNTAX  OCTET STRING (SIZE(0..255))
    ACCESS  read-only
    STATUS  optional
    DESCRIPTION
                "A description of this alert entry in the localization
        specified by prtGeneralCurrentLocalization.  The description is
        provided by the printer to further elaborate on the enumerated
        alert or provide information in the case where the code is
        classified ask `other' or `unknown'.  The printer is required
        to return a description string but the string may be a null
        string."
::= { prtAlertEntry 8 }
               
               
END
