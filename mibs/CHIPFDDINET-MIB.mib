--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--

CHIPFDDINET-MIB DEFINITIONS ::= BEGIN

IMPORTS
	enterprises, NetworkAddress, IpAddress,
	Counter, Gauge, TimeTicks, DisplayString
		FROM RFC1155-SMI
	OBJECT-TYPE
		FROM RFC-1212;

chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }


-- The olFDDInet Group				

olFDDIStatsModTable OBJECT-TYPE
	SYNTAX SEQUENCE OF OlFDDIStatsModEntry
	ACCESS not-accessible
	STATUS mandatory
	DESCRIPTION
		"A table of statistical information counted for each module
		in each FDDI network."
	::= { olFDDInet 2 }

olFDDIStatsModEntry OBJECT-TYPE
	SYNTAX OlFDDIStatsModEntry
	ACCESS not-accessible
	STATUS mandatory
	DESCRIPTION
		"A list of statistical information for each module
		on each FDDI network in the concentrator."
	INDEX { olFDDIStatsModSlotIndex }
	::= { olFDDIStatsModTable 1 }

OlFDDIStatsModEntry ::=
	SEQUENCE {
		olFDDIStatsModSlotIndex
			INTEGER,
		olFDDIStatsModMgtRcvErrs
			Counter,
		olFDDIStatsModMgtXmitErrs
			Counter,
		olFDDIStatsModBackplaneErrs
			Counter,
		olFDDIStatsModPllUnlockErrs
			Counter
		}

olFDDIStatsModSlotIndex OBJECT-TYPE
	SYNTAX INTEGER
	ACCESS read-only
	STATUS mandatory
	DESCRIPTION
		"The slot number that contains this module."
	::= { olFDDIStatsModEntry 1 }

olFDDIStatsModMgtRcvErrs OBJECT-TYPE
	SYNTAX Counter
	ACCESS read-only
	STATUS mandatory
	DESCRIPTION
                "The number of errors encountered while receiving data
                 on the Management Channel."
	::= { olFDDIStatsModEntry 2 }

olFDDIStatsModMgtXmitErrs OBJECT-TYPE
	SYNTAX Counter
	ACCESS read-only
	STATUS mandatory
	DESCRIPTION
                "The number of errors encountered while transmitting data
                 on the Management Channel."
	::= { olFDDIStatsModEntry 3 }

olFDDIStatsModBackplaneErrs OBJECT-TYPE
	SYNTAX Counter
	ACCESS read-only
	STATUS mandatory
	DESCRIPTION
                "The number of errors while receiving and transmitting 
                 network data on the backplane."
	::= { olFDDIStatsModEntry 4 }

olFDDIStatsModPllUnlockErrs OBJECT-TYPE
	SYNTAX Counter
	ACCESS read-only
	STATUS mandatory
	DESCRIPTION
                "The number of times the phased lock loop on the
                 backplane network data channel was lost."
	::= { olFDDIStatsModEntry 5 }


-- Port table

olFDDIStatsPortTable OBJECT-TYPE
	SYNTAX SEQUENCE OF OlFDDIStatsPortEntry
	ACCESS not-accessible
	STATUS mandatory
	DESCRIPTION
		"A table of statistical information counted for each Port
		in each FDDI network."
	::= { olFDDInet 3 }

olFDDIStatsPortEntry OBJECT-TYPE
	SYNTAX OlFDDIStatsPortEntry
	ACCESS not-accessible
	STATUS mandatory
	DESCRIPTION
		"A list of statistical information for each Port
		on each FDDI network in the concentrator."
	INDEX { olFDDIStatsPortSlotIndex, olFDDIStatsPortIndex }
	::= { olFDDIStatsPortTable 1 }

OlFDDIStatsPortEntry ::=
	SEQUENCE {
		olFDDIStatsPortSlotIndex
			INTEGER,
		olFDDIStatsPortIndex
			INTEGER,
		olFDDIStatsPortLCTFailCts
			Counter,
		olFDDIStatsPortLerEstimate
			Counter,
		olFDDIStatsPortLemRejectCts
			Counter,
		olFDDIStatsPortLemCts
			Counter
		}

olFDDIStatsPortSlotIndex OBJECT-TYPE
	SYNTAX INTEGER
	ACCESS read-only
	STATUS mandatory
	DESCRIPTION
		"The slot number that contains this Port."
	::= { olFDDIStatsPortEntry 1 }

olFDDIStatsPortIndex OBJECT-TYPE
	SYNTAX INTEGER
	ACCESS read-only
	STATUS mandatory
	DESCRIPTION
		"The Port number of this port"
	::= { olFDDIStatsPortEntry 2 }

olFDDIStatsPortLCTFailCts OBJECT-TYPE
	SYNTAX Counter
	ACCESS read-only
	STATUS mandatory
	DESCRIPTION
           "The count of the consecutive times the link
            confidence test (LCT) has failed during connection
            management. Once the connection has been established,
            the count is zeroed. (refer to ANSI 9.4.1)."
	::= { olFDDIStatsPortEntry 3 }

olFDDIStatsPortLerEstimate OBJECT-TYPE
	SYNTAX Gauge
	ACCESS read-only
	STATUS mandatory
	DESCRIPTION
            "A long term average link error rate.  It ranges
             from 10**-4 to 10**-15 and is reported as the
             absolute value of the exponent of the estimate
             (the larger the number, the smaller the value)."
	::= { olFDDIStatsPortEntry 4 }

olFDDIStatsPortLemRejectCts OBJECT-TYPE
	SYNTAX Counter
	ACCESS read-only
	STATUS mandatory
	DESCRIPTION
            "A link error monitoring count of the times that a
             link has been removed from the ring due to the
             LerCutOff threshold being exceeded."
	::= { olFDDIStatsPortEntry 5 }

olFDDIStatsPortLemCts OBJECT-TYPE
	SYNTAX Counter
	ACCESS read-only
	STATUS mandatory
	DESCRIPTION
            "The aggregate link error monitor error count, set
             to zero only on station power up. This variable's
             long term rate average is lerEstimate."
	::= { olFDDIStatsPortEntry 6 }


olFDDInetStatsTable OBJECT-TYPE
        SYNTAX SEQUENCE OF OlFDDInetStatsEntry
        ACCESS not-accessible
        STATUS mandatory
        DESCRIPTION
                "A table of statistical information counted for each FDDI
                network in the concentrator"
        ::= { olFDDInet 4 }
 
olFDDInetStatsEntry OBJECT-TYPE
        SYNTAX OlFDDInetStatsEntry
        ACCESS not-accessible
        STATUS mandatory
        DESCRIPTION
                "A list of statistical information for each FDDI
                network in the concentrator."
        INDEX { olFDDInetStatsNetID }
        ::= { olFDDInetStatsTable 1 }
 
OlFDDInetStatsEntry ::=
        SEQUENCE {
                olFDDInetStatsNetID
                        INTEGER,
                olFDDInetStatsRingOpCounts
                        Counter,
                olFDDInetStatsFrameCounts
                        Counter,
                olFDDInetStatsErrorCounts
                        Counter,
                olFDDInetStatsLostCounts
                        Counter,
                olFDDInetStatsFrameErrorRatio
                        INTEGER
        }
 
olFDDInetStatsNetID OBJECT-TYPE
        SYNTAX INTEGER {
                isolated(2), 
                fddi-1(16), 
                fddi-2(17), 
                fddi-3(18),
                fddi-4(19)
                } 
        ACCESS read-only
        STATUS mandatory
        DESCRIPTION
                "The network index that uniquely identifies this network.
                One of isolated, fddi-1, fddi-2, fddi-3, or fddi-4."
        ::= { olFDDInetStatsEntry 1 }
 
olFDDInetStatsRingOpCounts OBJECT-TYPE
        SYNTAX Counter
        ACCESS read-only
        STATUS mandatory
        DESCRIPTION
                "The number times the ring transitioned to operational."
        ::= { olFDDInetStatsEntry 2 }

olFDDInetStatsFrameCounts OBJECT-TYPE
        SYNTAX Counter
        ACCESS read-only
        STATUS mandatory
        DESCRIPTION
                "Frame_Ct (refer to ANSI MAC 2.2.1)."
        ::= { olFDDInetStatsEntry 3 }

olFDDInetStatsErrorCounts OBJECT-TYPE
        SYNTAX Counter
        ACCESS read-only
        STATUS mandatory
        DESCRIPTION
                "Error_Ct (refer to ANSI MAC 2.2.1)."
        ::= { olFDDInetStatsEntry 4 }

olFDDInetStatsLostCounts OBJECT-TYPE
        SYNTAX Counter
        ACCESS read-only
        STATUS mandatory
        DESCRIPTION
                "Lost_Ct (refer to ANSI MAC 2.2.1)."
        ::= { olFDDInetStatsEntry 5 }

olFDDInetStatsFrameErrorRatio OBJECT-TYPE
        SYNTAX INTEGER (1..65535)
        ACCESS read-only
        STATUS mandatory
        DESCRIPTION
                "This attribute is the actual ratio, ((delta
                 snmpFddiMACLostCt + delta snmpFddiMACErrorCt) /
                 (delta snmpFddiMACFrameCt + delta
                 snmpFddiMACLostCt)) x 2**16."
        ::= { olFDDInetStatsEntry 6 }


END
