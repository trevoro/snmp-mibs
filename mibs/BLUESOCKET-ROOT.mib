BLUESOCKET-ROOT DEFINITIONS ::= BEGIN

      IMPORTS
         MODULE-IDENTITY FROM SNMPv2-SMI
			enterprises
                FROM SNMPv2-SMI;

blueSocket MODULE-IDENTITY
    LAST-UPDATED "200303100000Z"
    ORGANIZATION "Bluesocket Inc."
    CONTACT-INFO
            "   Suresh Gandhi
                Bluesocket, Inc.
                Burlington, MA 01803
                sgandhi@bluesocket.com
            "
    DESCRIPTION
       "This MIB is DRAFT-ONLY and is subject to change.
        Management Information Base for Blueserver."

    ::= { enterprises 9967 }

END
