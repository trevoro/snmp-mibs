INTEL-DIAG-MIB DEFINITIONS ::= BEGIN

-- Copyright (C) 1997 Intel Corporation. All rights reserved.
--
-- Private Diagnostics MIB, 05-03-1997
--
-- This MIB provides objects for Diagnostics.
--
-- Change History:
-- <date> <change>
--

IMPORTS
	Counter FROM RFC1155-SMI
    TimeTicks                  FROM RFC1155-SMI
    mib2ext                    FROM INTEL-GEN-MIB
    OBJECT-TYPE                FROM RFC-1212
    DisplayString              FROM RFC1213-MIB;


  diag              OBJECT IDENTIFIER ::= { mib2ext 4 }
  diagList          OBJECT IDENTIFIER ::= { diag 1 }
  diagTest          OBJECT IDENTIFIER ::= { diag 2 }
  diagAutodetect    OBJECT IDENTIFIER ::= { diag 3 }


-- List group

diagListNumberOfEntries OBJECT-TYPE
    SYNTAX INTEGER
    ACCESS read-write
    STATUS mandatory
    DESCRIPTION "Number of entries in Diagnostics Table
                 (Set value to 0 to delete all entries)"
    ::= { diagList 1 }

diagListNumberOfErrorEntries OBJECT-TYPE
    SYNTAX INTEGER
    ACCESS read-only
    STATUS mandatory
    DESCRIPTION "Number of errors in Diagnostics Table"
    ::= { diagList 2 }

diagListLastUpdateTime OBJECT-TYPE
    SYNTAX TimeTicks
    ACCESS read-only
    STATUS mandatory
    DESCRIPTION "Time of last insertion in Diagnostics Table in timeticks
                 since boot (reinserting an existing entry is not
                 considered an update)."
    ::= { diagList 3 }


diagListTable OBJECT-TYPE
    SYNTAX SEQUENCE OF DiagListEntry
    ACCESS not-accessible
    STATUS mandatory
    DESCRIPTION "Diagnostics Table"
    ::= { diagList 4 }

diagListEntry OBJECT-TYPE
    SYNTAX DiagListEntry
    ACCESS not-accessible
    STATUS mandatory
    DESCRIPTION ""
    INDEX { diagListIndex }
    ::= { diagListTable 1 }

DiagListEntry ::= SEQUENCE {
                        diagListIndex
                           INTEGER,
                        diagListLevel
                           INTEGER,
                        diagListCode
                           INTEGER,
                        diagListIfindex
                           INTEGER,
                        diagListTimeStamp
                           TimeTicks,
                        diagListDescription
                           DisplayString (SIZE(240)),
                        diagListAdvice
                           DisplayString (SIZE(240)),
                        diagListAutoFixAvailable
			   INTEGER,
                        diagListAutoFixState
                           OCTET STRING
                        }

diagListIndex OBJECT-TYPE
    SYNTAX INTEGER
    ACCESS read-only
    STATUS mandatory
    DESCRIPTION "Position in table."
    ::= { diagListEntry 1 }

diagListLevel OBJECT-TYPE
    SYNTAX INTEGER {
                warning(32),
                error(64),
                fatalError(96)
        }
    ACCESS read-only
    STATUS mandatory
    DESCRIPTION "Error level."
    ::= { diagListEntry 2 }

diagListCode OBJECT-TYPE
    SYNTAX INTEGER
    ACCESS read-only
    STATUS mandatory
    DESCRIPTION "Number that uniquely identifies a specific situation.
                 Set code to zero to delete the entry."
    ::= { diagListEntry 3 }

diagListIfindex OBJECT-TYPE
    SYNTAX INTEGER
    ACCESS read-only
    STATUS mandatory
    DESCRIPTION "Interface index."
    ::= { diagListEntry 4 }

diagListTimeStamp OBJECT-TYPE
    SYNTAX TimeTicks
    ACCESS read-only
    STATUS mandatory
    DESCRIPTION "Time of (re)insertion in timeticks since boot."
    ::= { diagListEntry 5 }

diagListDescription OBJECT-TYPE
    SYNTAX DisplayString (SIZE(240))
    ACCESS read-only
    STATUS mandatory
    DESCRIPTION "Description of the problem."
    ::= { diagListEntry 6 }

diagListAdvice OBJECT-TYPE
    SYNTAX DisplayString (SIZE(240))
    ACCESS read-only
    STATUS mandatory
    DESCRIPTION "Advice"
    ::= { diagListEntry 7 }

diagListAutoFixAvailable OBJECT-TYPE
    SYNTAX INTEGER { no(1), yes(2) }
    ACCESS read-only
    STATUS mandatory
    DESCRIPTION "no:  This entry cannot be automatically fixed.
                 yes: This entry can be automatically fixed."
    ::= { diagListEntry 8 }

diagListAutoFixState OBJECT-TYPE
    SYNTAX OCTET STRING (SIZE(16))
    ACCESS read-write
    STATUS mandatory
    DESCRIPTION "When reading
                 0:   State = idle(1), autoFixInProgress(3)
                 When writing
                 0:   State = startAutoFix(2)
                 1:   Action
                 2-5: diagListCode (bigendian)
                 6-9: diagListIfindex (bigendian)
                 diagListCode and diagListIfindex are used to verify that
                 the correct entry is being fixed."
    ::= { diagListEntry 9 }




-- Test Group

diagTestTable OBJECT-TYPE
    SYNTAX SEQUENCE OF DiagTestEntry
    ACCESS not-accessible
    STATUS mandatory
    DESCRIPTION ""
    ::= { diagTest 1 }

diagTestEntry OBJECT-TYPE
    SYNTAX DiagTestEntry
    ACCESS not-accessible
    STATUS mandatory
    DESCRIPTION ""
    INDEX { diagTestType }
    ::= { diagTestTable 1 }

DiagTestEntry ::= SEQUENCE {
                        diagTestType
                           INTEGER,
                        diagTestDescription
                           OCTET STRING,
                        diagTestStatus
                           INTEGER
                        }

diagTestType OBJECT-TYPE
    SYNTAX INTEGER
    ACCESS read-only
    STATUS mandatory
    DESCRIPTION "Test type"
    ::= { diagTestEntry 1 }


diagTestDescription OBJECT-TYPE
    SYNTAX OCTET STRING (SIZE(40))
    ACCESS read-only
    STATUS mandatory
    DESCRIPTION "Test description"
    ::= { diagTestEntry 2 }


diagTestStatus OBJECT-TYPE
    SYNTAX INTEGER {
                ready(1),
                test(2),
                testing(3)
        }
    ACCESS read-write
    STATUS mandatory
    DESCRIPTION "Test status. Begin a test by setting the value to
    test(2) and then wait for it to go from testing(3) to ready(1)."
    ::= { diagTestEntry 3 }



-- Autodetect table

diagAutodetectTable OBJECT-TYPE
    SYNTAX SEQUENCE OF DiagAutodetectEntry
    ACCESS not-accessible
    STATUS mandatory
    DESCRIPTION "Autodetection table"
    ::= { diagAutodetect 1 }

diagAutodetectEntry OBJECT-TYPE
    SYNTAX DiagAutodetectEntry
    ACCESS not-accessible
    STATUS mandatory
    DESCRIPTION ""
    INDEX { diagAutodetectType, diagAutodetectIndex1,
            diagAutodetectIndex2, diagAutodetectIndex3 }
    ::= { diagAutodetectTable 1 }

DiagAutodetectEntry ::= SEQUENCE {
                        diagAutodetectType
                           INTEGER,
                        diagAutodetectIndex1
                           INTEGER,
                        diagAutodetectIndex2
                           INTEGER,
                        diagAutodetectIndex3
                           INTEGER,
                        diagAutodetectState
                           INTEGER,
                        diagAutodetectDuration
                           INTEGER,
                        diagAutodetectRes1
                           Counter,
                        diagAutodetectRes2a
                           OCTET STRING,
                        diagAutodetectRes2b
                           OCTET STRING,
                        diagAutodetectPreInput
                           OCTET STRING
                        }

diagAutodetectType OBJECT-TYPE
    SYNTAX INTEGER
    ACCESS read-only
    STATUS mandatory
    DESCRIPTION "A number that identifies the group of parameters being
                 autodetected.
                 Res2 is the concatenation of Res2a and Res2b.

                 Possible value are
                 1: IPX net numbers and frame types on LAN.
                    index = 1.plugno.0.0
                    result is in res2 with 5 bytes for each frame type in the
                    form
                        0:   protocol (1=TYPE, 2=802.2, 4=SNAP and 5=8023)
                        1-4: network number
                    So the length of res2 is 5, 10, 15 or 20 depending on the
                    number of frame types on the LAN.
                    The best candidate is the first.
                 2: ISDN Switch connection.
                    index = 2.plugno.0.0
                    result is in res1
                        res1 is 1: connection to switch
                        res1 is 0: no connection to switch
                    plugno=plug number
                 3: ISDN Local Number Test
                 4: ISDN Remote Number Test
                 5: ISDN Switch Type Test
                 6: ISDN SPID Detect
                 7: ISDN SPID Test
                 8: Frame Relay DLCMI and DLCI detection"
    ::= { diagAutodetectEntry 1 }

diagAutodetectIndex1 OBJECT-TYPE
    SYNTAX INTEGER
    ACCESS read-only
    STATUS mandatory
    DESCRIPTION "First index for autodetect situation (typically interface
                 index)."
    ::= { diagAutodetectEntry 2 }

diagAutodetectIndex2 OBJECT-TYPE
    SYNTAX INTEGER
    ACCESS read-only
    STATUS mandatory
    DESCRIPTION "Second index for autodetect situation."
    ::= { diagAutodetectEntry 3 }

diagAutodetectIndex3 OBJECT-TYPE
    SYNTAX INTEGER
    ACCESS read-only
    STATUS mandatory
    DESCRIPTION "Third index for autodetect situation."
    ::= { diagAutodetectEntry 4 }

diagAutodetectState OBJECT-TYPE
    SYNTAX INTEGER {
                     ready(1),
                     startTest(2),
                     stopTest(3),
                     testSucceeded(4),
                     testFailed(5),
                     testInProgress(6)
                   }
    ACCESS read-write
    STATUS mandatory
    DESCRIPTION "Autodetect state
                 ready(1):         Test has not been perfomed.
                 startTest(2):     Start test
                 stopTest(3):      Stop test (only supported for some types)
                 testSucceeded(4): Test succeeded and the result can be found
                                   in Res1 and Res2.
                 testFailed(5):    Test failed
                 testInProgress(6):Test is in progress. diagAutodetectDuration
                                   contains the approximate duration in seconds
                 Typical state sequences after setting state to startTest(1)
                    ->testInProgress(5)->testFailed(4)
                    ->testInProgress(5)->testSucceeded(3)"
    ::= { diagAutodetectEntry 5 }

diagAutodetectDuration OBJECT-TYPE
    SYNTAX INTEGER
    ACCESS read-only
    STATUS mandatory
    DESCRIPTION "Average duration for autodetection (s). 0 means unknown."
    ::= { diagAutodetectEntry 6 }

diagAutodetectRes1 OBJECT-TYPE
    SYNTAX Counter
    ACCESS read-only
    STATUS mandatory
    DESCRIPTION "Result of autodetection. Res1 contains valid information
                 if the value of diagAutodetectState is testSucceeded(3)."
    ::= { diagAutodetectEntry 7 }

diagAutodetectRes2a OBJECT-TYPE
    SYNTAX OCTET STRING (SIZE(255))
    ACCESS read-only
    STATUS mandatory
    DESCRIPTION "Result of autodetection. Res2 contains valid information
                 if the value of diagAutodetectState is testSucceeded(3)."
    ::= { diagAutodetectEntry 8 }

diagAutodetectRes2b OBJECT-TYPE
    SYNTAX OCTET STRING (SIZE(255))
    ACCESS read-only
    STATUS mandatory
    DESCRIPTION "If the result takes up more than 255 bytes of information
                 the rest is put in this Res2b."
    ::= { diagAutodetectEntry 9 }

diagAutodetectPreInput OBJECT-TYPE
    SYNTAX OCTET STRING (SIZE(255))
    ACCESS read-write
    STATUS mandatory
    DESCRIPTION "Input for test which is set immediately before settting
                 diagAutodetectState to startTest(1)."
    ::= { diagAutodetectEntry 10 }

END
