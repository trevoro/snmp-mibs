PANDATEL-GMD-MODEM-MIB DEFINITIONS ::= BEGIN

 -- This is the private mib group section for the GM-D modems.
 -- Because these modems must be installed in the PANDATEL modem rack
 -- the PANDATEL-MODEM-MIB also applies.

 -- Ver.1.05    Sep.13.1999

        IMPORTS
                enterprises, Gauge
                        FROM RFC1155-SMI
                DisplayString
                        FROM RFC1213-MIB
                OBJECT-TYPE
                        FROM RFC-1212
                mdmSpecifics, device-id
                        FROM PANDATEL-MODEM-MIB;

-- ********************** THE MDM-GMD SUBTREE ******************************

-- the specific identifier is identical to the modem type integer
-- of the GM-D modem entries in the PANDATEL-MODEM-MIB mdmModemTable.

gmd-modem      OBJECT IDENTIFIER ::= { device-id 203 }     -- chassis-mib

gmd            OBJECT IDENTIFIER ::= { mdmSpecifics 203 }  -- this subtree

-- * * * * * * * * * * * * MODEM TABLE (1) * * * * * * * * * * * * * * * *

gmdModemTable OBJECT-TYPE
        SYNTAX  SEQUENCE OF GmdTableEntry
        ACCESS  not-accessible
        STATUS  mandatory
        DESCRIPTION
                "This table contains information about all GM-D modems in all racks."
        ::= { gmd 1 }

gmdTableEntry OBJECT-TYPE
        SYNTAX  GmdTableEntry
        ACCESS  not-accessible
        STATUS  mandatory
        DESCRIPTION
                "The index of the table."
        INDEX   { mdmRack, mdmModem, mdmPosition }
        ::= { gmdModemTable 1 }

GmdTableEntry ::= SEQUENCE {
        mdmRack
                INTEGER,
        mdmModem
                INTEGER,
        mdmPosition
                INTEGER,
        mdmModemName
                DisplayString,
        mdmDataEquipmentEmulation
                INTEGER,
        mdmModemProperty
                INTEGER,
        mdmHDSLUnit
                INTEGER,
        mdmClockSystem
                INTEGER,
        mdmClockSource
                INTEGER,
        mdmDataRate
                INTEGER,
        mdmStartChannel
                INTEGER,
        mdmTimeslot16
                INTEGER,
        mdmCRC4Generation
                INTEGER,
        mdmHDSLFramer
                INTEGER,
        mdmCRC6Test
                INTEGER,
        mdmPair1CRC6Status
                INTEGER,
        mdmPair1CRC6Error
                Gauge,
        mdmPair2CRC6Status
                INTEGER,
        mdmPair2CRC6Error
                Gauge,
        mdmPair3CRC6Status
                INTEGER,
        mdmPair3CRC6Error
                Gauge
        }

mdmRack OBJECT-TYPE
        SYNTAX  INTEGER
        ACCESS  read-only
        STATUS  mandatory
        DESCRIPTION
                "The index of the rack where the modem is installed."
        ::= { gmdTableEntry 1 }

mdmModem OBJECT-TYPE
        SYNTAX  INTEGER
        ACCESS  read-only
        STATUS  mandatory
        DESCRIPTION
                "This entry displays the slot number where the corresponding
                 modem is installed in the rack."
        ::= { gmdTableEntry 2 }

mdmPosition OBJECT-TYPE
        SYNTAX  INTEGER {
                local       (1),
                remote      (2)
                }
        ACCESS  read-only
        STATUS  mandatory
        DESCRIPTION
                "This entry displays the location of the corresponding modem:
                 'local' or 'remote'. The modem which is plugged into a managed
                 rack is 'local', the counterpart is 'remote'."
        ::= { gmdTableEntry 3 }

mdmModemName OBJECT-TYPE
        SYNTAX  DisplayString
        ACCESS  read-only
        STATUS  mandatory
        DESCRIPTION
                "The verbal name of this modem."
        ::= { gmdTableEntry 5 }

mdmDataEquipmentEmulation OBJECT-TYPE
        SYNTAX  INTEGER {
                other       (1),
                dte         (2),
                dce         (3),
                unknown     (99)
        }
        ACCESS  read-only
        STATUS  mandatory
        DESCRIPTION
                "Interface mode of the unit: 'dte' or 'dce'."
        ::= { gmdTableEntry 6 }

mdmModemProperty OBJECT-TYPE
        SYNTAX  INTEGER {
                other           (1),
                e1              (2),
                t1              (3),
                unknown         (99)
                }
        ACCESS  read-only
        STATUS  mandatory
        DESCRIPTION
                "This entry displays the speed class of the GM-D: 'e1'."
        ::= { gmdTableEntry 7 }

mdmHDSLUnit OBJECT-TYPE
        SYNTAX  INTEGER {
                other       (1),
                ntu         (2),
                ltu         (3)
        }
        ACCESS  read-only
        STATUS  mandatory
        DESCRIPTION
                "HDSL unit type: Line Termination Unit ('LTU') or Network
                 Termination Unit ('NTU')"
        ::= { gmdTableEntry 10 }

mdmClockSystem OBJECT-TYPE
        SYNTAX  INTEGER {
                other       (1),
                dual        (2),
                single      (3)
        }
        ACCESS  read-write
        STATUS  mandatory
        DESCRIPTION
                "The clock system of the link: 'dual' or 'single'."
        ::= { gmdTableEntry 23 }

mdmClockSource OBJECT-TYPE
        SYNTAX  INTEGER {
                other       (1),
                internal    (2),
                remote      (3),
                external    (4)
        }
        ACCESS  read-write
        STATUS  mandatory
        DESCRIPTION
                "The clock source of the link: 'internal', 'external', or
                 'remote'."
        ::= { gmdTableEntry 24 }

mdmDataRate OBJECT-TYPE
        SYNTAX  INTEGER {
                other       (1)
        }
        ACCESS  read-write
        STATUS  mandatory
        DESCRIPTION
                "The data rate at the interface in bits per seconds. The data
                 rate at the remote counterpart changes simultaneously. A data
                 rate of 2.048 Mbps (E1) automatically disables CRC4, sets
                 mdmStartChannel to 'unframed' and enables time slot 16. A data
                 rate of 1.984 Mbps (E1) automatically sets mdmStartChannel
                 to 'channel-1' and enables time slot 16."
        ::= { gmdTableEntry 25 }

mdmStartChannel OBJECT-TYPE
        SYNTAX  INTEGER {
                channel-1       (1),
                channel-2       (2),
                channel-3       (3),
                channel-4       (4),
                channel-5       (5),
                channel-6       (6),
                channel-7       (7),
                channel-8       (8),
                channel-9       (9),
                channel-10      (10),
                channel-11      (11),
                channel-12      (12),
                channel-13      (13),
                channel-14      (14),
                channel-15      (15),
                channel-16      (16),
                channel-17      (17),
                channel-18      (18),
                channel-19      (19),
                channel-20      (20),
                channel-21      (21),
                channel-22      (22),
                channel-23      (23),
                channel-24      (24),
                channel-25      (25),
                channel-26      (26),
                channel-27      (27),
                channel-28      (28),
                channel-29      (29),
                channel-30      (30),
                channel-31      (31),
                unframed        (98),
                other           (99),
                not-available   (100)
        }
        ACCESS  read-write
        STATUS  mandatory
        DESCRIPTION
                "This entry determines the start channel for framing. Start
                 channel and data rate must match. A start channel which is
                 too high will be ignored. The remote unit's configuration
                 changes simultaneously."
        ::= { gmdTableEntry 26 }

mdmTimeslot16 OBJECT-TYPE
        SYNTAX  INTEGER {
                other           (1),
                disable         (2),
                enable          (3),
                not-available   (100)
                }
        ACCESS  read-write
        STATUS  mandatory
        DESCRIPTION
                "This entry enables or disables time slot 16. If it is disabled,
                it will not be used for data transmission but for framing."
        ::= { gmdTableEntry 40 }

mdmCRC4Generation OBJECT-TYPE
        SYNTAX  INTEGER {
                other       (1),
                disable     (2),
                enable      (3)
        }
        ACCESS  read-write
        STATUS  mandatory
        DESCRIPTION
                "This entry enables or disables the generation of a CRC4 check sum."
        ::= { gmdTableEntry 41 }

mdmHDSLFramer OBJECT-TYPE
        SYNTAX  INTEGER {
                other       (1),
                disable     (2),
                enable      (3)
        }
        ACCESS  read-write
        STATUS  mandatory
        DESCRIPTION
                "This entry enables or disables HDSL framing. The remote unit's
                 configuration changes simultaneously."
        ::= { gmdTableEntry 62 }

mdmCRC6Test OBJECT-TYPE
        SYNTAX  INTEGER {
                other           (1),
                start           (3),
                stop            (4),
                not-available   (100)
        }
        ACCESS  read-write
        STATUS  mandatory
        DESCRIPTION
                "This entry enables the execution of a CRC6 test. Write requests
                 with values other than 'start' or 'stop' will be rejected."
        ::= { gmdTableEntry 100 }

mdmPair1CRC6Status OBJECT-TYPE
        SYNTAX  INTEGER {
                other           (1),
                never-started   (2),
                running         (5),
                stopped         (6),
                start-failed    (7),
                not-available   (100)
        }
        ACCESS  read-only
        STATUS  mandatory
        DESCRIPTION
                "This entry indicates the status of the CRC6 test at pair 1."
        ::= { gmdTableEntry 101 }

mdmPair1CRC6Error OBJECT-TYPE
        SYNTAX  Gauge
        ACCESS  read-only
        STATUS  mandatory
        DESCRIPTION
                "This entry indicates the number of errors detected during the
                 last 60 seconds at pair 1."
        ::= { gmdTableEntry 102 }

mdmPair2CRC6Status OBJECT-TYPE
        SYNTAX  INTEGER {
                other           (1),
                never-started   (2),
                running         (5),
                stopped         (6),
                start-failed    (7),
                not-available   (100)
        }
        ACCESS  read-only
        STATUS  mandatory
        DESCRIPTION
                "This entry indicates the status of the CRC6 test at pair 2."
        ::= { gmdTableEntry 103 }

mdmPair2CRC6Error OBJECT-TYPE
        SYNTAX  Gauge
        ACCESS  read-only
        STATUS  mandatory
        DESCRIPTION
                "This entry indicates the number of errors detected during the
                 last 60 seconds at pair 2."
        ::= { gmdTableEntry 104 }

mdmPair3CRC6Status OBJECT-TYPE
        SYNTAX  INTEGER {
                other           (1),
                never-started   (2),
                running         (5),
                stopped         (6),
                start-failed    (7),
                not-available   (100)
        }
        ACCESS  read-only
        STATUS  mandatory
        DESCRIPTION
                "This entry indicates the status of the CRC6 test at pair 3."
        ::= { gmdTableEntry 105 }

mdmPair3CRC6Error OBJECT-TYPE
        SYNTAX  Gauge
        ACCESS  read-only
        STATUS  mandatory
        DESCRIPTION
                "This entry indicates the number of errors detected during the
                 last 60 seconds at pair 3."
        ::= { gmdTableEntry 106 }

END
