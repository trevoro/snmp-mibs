ChrComPmAtmATM-VP-Interval-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmAtm				FROM  Chromatis-MIB
	chrComIfifIndex					FROM  ChrComIfifTable-MIB
	atmVplVpi					FROM  ATM-MIB
	TruthValue				FROM  ChrTyp-MIB
	Gauge32				FROM  SNMPv2-SMI;

-- chrComPmAtmATM-VP-Interval Table

chrComPmAtmATM-VP-IntervalTable		OBJECT-TYPE
	SYNTAX		SEQUENCE OF ChrComPmAtmATM-VP-IntervalEntry
	MAX-ACCESS	not-accessible
	STATUS		current
	DESCRIPTION
	""
	::= { chrComPmAtm 5}

chrComPmAtmATM-VP-IntervalEntry		OBJECT-TYPE
	SYNTAX		ChrComPmAtmATM-VP-IntervalEntry
	MAX-ACCESS	not-accessible
	STATUS		current
	DESCRIPTION
	""
	INDEX  {  chrComIfifIndex, atmVplVpi, chrComPmAtmIntervalNumber }

--DEFAULT  get-function-async  MNIL_GetRoutine
--DEFAULT  set-function-async  MNIL_SetRoutine
--DEFAULT  next-function-async MNIL_NextRoutine
--DEFAULT  test-function-async MNIL_TestRoutine
--DEFAULT  cookie "ATM-VP-Interval"
	::= { chrComPmAtmATM-VP-IntervalTable  1 }

ChrComPmAtmATM-VP-IntervalEntry  ::=
	SEQUENCE  {
	chrComPmAtmIntervalNumber		Unsigned32	(1..32),
	chrComPmAtmSuspectedInterval	TruthValue,
	chrComPmAtmElapsedTime		Unsigned32	(0..4294967295),
	chrComPmAtmSuppressedIntrvls	Gauge32			(0..4294967295),
	chrComPmAtmReceivedCells		Gauge32			(0..4294967295),
	chrComPmAtmTransmittedCells	Gauge32			(0..4294967295)
}

chrComPmAtmIntervalNumber 	OBJECT-TYPE
	SYNTAX		Unsigned32	(1..32)
	MAX-ACCESS 	read-only
	STATUS 		current
	DESCRIPTION
	""
	::= { chrComPmAtmATM-VP-IntervalEntry  1 }

chrComPmAtmSuspectedInterval 	OBJECT-TYPE
	SYNTAX		TruthValue
	MAX-ACCESS 	read-only
	STATUS 		current
	DESCRIPTION
	""
	::= { chrComPmAtmATM-VP-IntervalEntry  2 }

chrComPmAtmElapsedTime 	OBJECT-TYPE
	SYNTAX		Unsigned32	(0..4294967295)
	MAX-ACCESS 	read-only
	STATUS 		current
	DESCRIPTION
	""
	::= { chrComPmAtmATM-VP-IntervalEntry  3 }

chrComPmAtmSuppressedIntrvls 	OBJECT-TYPE
	SYNTAX		Gauge32			(0..4294967295)
	MAX-ACCESS 	read-only
	STATUS 		current
	DESCRIPTION
	""
	::= { chrComPmAtmATM-VP-IntervalEntry  4 }

chrComPmAtmReceivedCells 	OBJECT-TYPE
	SYNTAX		Gauge32			(0..4294967295)
	MAX-ACCESS 	read-only
	STATUS 		current
	DESCRIPTION
	""
	::= { chrComPmAtmATM-VP-IntervalEntry  5 }

chrComPmAtmTransmittedCells 	OBJECT-TYPE
	SYNTAX		Gauge32			(0..4294967295)
	MAX-ACCESS 	read-only
	STATUS 		current
	DESCRIPTION
	""
	::= { chrComPmAtmATM-VP-IntervalEntry  6 }


END
