-- Sync Research Enterprise MIB for MFRAP                     =
--                                                            =
--                                                            =
--                      MIB VERSION 4.00                      =
--                                                            =
--                                                            =
-- internal version 4.00.17                                   =
--                                                            =
--                                                            =
-- This file contains MIB Definitions for extended management =
-- of Sync MFRAP Product (T1 product with integral agent).    =
--                                                            =
-- This MIB is copyrighted by Sync Research (1998, 1999).     =
-- Permission is granted to the general public to use this    =
-- file for management of Sync Research Products.             =
--                                                            =
-- Updates to this Enterprise MIB may be obtained from        =
-- Sync Customer Service 1-800-828-2780.                      =
--                                                            =

MFRAP-MIB DEFINITIONS ::= BEGIN

   IMPORTS

      DisplayString
         FROM SNMPv2-TC
      Counter, TimeTicks, IpAddress, internet, Gauge
         FROM RFC1155-SMI
      TRAP-TYPE
         FROM RFC-1215
      OBJECT-TYPE
         FROM RFC-1212;

   --   This MIB module uses the extended OBJECT-TYPE macro.

   private     OBJECT IDENTIFIER ::= { internet 4 }
   enterprises OBJECT IDENTIFIER ::= { private 1 }
   sync        OBJECT IDENTIFIER ::= { enterprises 485 }
   mfrap       OBJECT IDENTIFIER ::= { sync 8 }

   -- textual conventions

       --DisplayString ::=
       --    OCTET STRING
       -- This data type is used to model textual information taken
       -- from the NVT ASCII character set.  By convention, objects
       -- with this syntax are declared as having
       --
       --      SIZE (0..255)


-- *********************************************************************
--                     MFRAP ENTERPRISE SPECIFIC MIB
-- *********************************************************************


-- ======================================================================
--
--  The MFRAP MIB Tree
--      This MIB covers the Sync Research MFRAP, a T1 CSU for dedicated
--      or switched (T1) applications.  This product is managed via an
--      integral agent.
--
--  The MFRAP MIB Consists of five groups (plus Traps):
--      The SYSTEM group
--      The CONFIGURATION group
--      The DIAGNOSTICS group
--      The STATUS group
--      The PERFORMANCE group
--
--  The SYSTEM group
--      This group provides system level attributes of the node.
--
--      The group consists of the following tables:
--          mfrapSysTable           - System level attributes
--          mfrapSysFeatureTable    - System level features
--
--  The CONFIGURATION group
--      This group provides for configuration of the node.
--
--      The group consists of the following tables:
--          mfrapCfgMgmtTable     - Configuration of management features
--             mfrapCfgIpTable        - IP configuration
--             mfrapCfgTftpTable      - TFTP configuration
--             mfrapCfgSnmpTable      - SNMP configuration
--                mfrapCfgSnmpMgrTable    - SNMP managers (TRAP destinations)
--             mfrapCfgCommTable      - Communication port configuration
--             mfrapCfgFrDLCITable    - DLCI configuration
--          mfrapCfgAppTable      - Application level configuration
--          mfrapCfgT1Table       - T1 port configuration
--          mfrapCfgDteTable      - DTE port configuration
--          mfrapCfgFrTable       - Frame Relay configuration
--          mfrapCfgVnipTable     - VNIP configuration
--          mfrapCfgFrPerfTable   - Frame Relay performance configuration
--             mfrapCfgFrPerfDlciNamesTable        - Table of DLCI names
--             mfrapCfgFrPerfUserProtocolsTable    - User-specified protocols
--             mfrapCfgFrPerfLTDlciFilterTable     - LT stats: DLCI filter
--             mfrapCfgFrPerfLTProtocolFilterTable - LT stats: protocol filter
--          mfrapCfgSecurityTable - Security configuration
--          mfrapCfgConnectionTable - Connection configuration
--          mfrapCfgDandiTable - Drop & Insert port configuration
--          
--  The DIAGNOSTICS group
--      This group provides for run-time control of the node.
--
--      The group consists of the following tables:
--          mfrapDiagUnitTable  - Unit level Diagnostics
--          mfrapDiagT1Table    - T1 Port Diagnostics
--          mfrapDiagDteTable   - DTE port diagnostics
--          mfrapDiagBertTable  - BERT Diagnostics
--          mfrapDiagDandiTable - Drop & Insert Port Diagnostics
--          
--  The STATUS group
--      This group provides status information.
--
--      The group consists of the following tables:
--          mfrapStatusT1Table     - T1 status
--          mfrapStatusDteTable    - DTE status
--          mfrapStatusDandiTable  - Drop & Insert Status
--          mfrapStatusLedTable    - LED status
--          mfrapVnipTopologyTable - VNIP topology
--          mfrapStatusMgmtTable   - Status of management channel
--          mfrapStatusNestTable   - Status of chassis
--          
--  The PERFORMANCE group
--      This group provides statistical information.
--
--      The group consists of the following tables:
--          mfrapPerfPhysicalIntf     - Physical interface statistics
--             mfrapPerfT1CurrentTable     - T1 current statistics
--             mfrapPerfT1IntervalTable    - T1 interval statistics
--             mfrapPerfT1TotalTable       - T1 total statistics
--             mfrapT1PerfCmdTypeTable     - T1 statistics commands
--             mfrapPerfDandiCurrentTable     - D&I current statistics
--             mfrapPerfDandiIntervalTable    - D&I interval statistics
--             mfrapPerfDandiTotalTable       - D&I total statistics
--             mfrapDandiPerfCmdTypeTable     - D&I statistics commands
--          mfrapPerfMgmtIp           - IP protocol stack statistics
--             mfrapPerfMgmtIpIFStatsTable   - Interface statistics
--             mfrapPerfMgmtIpIPStatsTable   - IP statistics
--             mfrapPerfMgmtIpICMPStatsTable - ICMP statistics
--             mfrapPerfMgmtIpUDPStatsTable  - UDP statistics
--             mfrapPerfMgmtIpTCPStatsTable  - TCP statistics
--          mfrapPerfThruput          - Thruput statistics
--             mfrapPerfThruputPerIntfTable  - Thruput per interface
--             mfrapPerfThruputPerDlciTable  - Thruput per DLCI
--          mfrapPerfCirPercentUtilization - CIR percentage stats
--          mfrapPerfNetworkShortTerm - Short term DLCI statistics
--             mfrapPerfNetwProtoPerDlciTable   - Network protocol stats per DLCI
--             mfrapPerfNetwProtoTotalTable     - Total network protocol stats
--             mfrapPerfIpPerDlciTable          - IP stats per DLCI
--             mfrapPerfIpTotalTable            - Total IP stats
--             mfrapPerfIcmpPerDlciTable        - ICMP stats per DLCI
--             mfrapPerfIcmpTotalTable          - Total ICMP stats
--             mfrapPerfApplicationPerDlciTable - Application stats per DLCI
--             mfrapPerfApplicationTotalTable   - Total application stats
--             mfrapPerfRoutingPerDlciTable     - Routing stats per DLCI
--             mfrapPerfRoutingTotalTable       - Total Routing stats
--             mfrapPerfIpxPerDlciTable         - IPX stats per DLCI
--             mfrapPerfIpxTotalTable           - Total IPX stats
--             mfrapPerfSnaPerDlciTable         - SNA stats per DLCI
--             mfrapPerfSnaTotalTable           - Total SNA stats
--             mfrapPerfArpPerDlciTable         - ARP stats per DLCI
--             mfrapPerfArpTotalTable           - Total ARP stats
--          mfrapPerfNetworkLongTerm  - Long term DLCI statistics
--             mfrapPerfNetwLongTermTable       - Long term stats
--             mfrapPerfNetwLongTermAltTable    - Alternate format LTS
--
--  The MIB also contains enterprise trap information:
--          mfrapTrap
--
-- =======================================================================



-- ========================
-- ==   SYSTEM group     ==
-- ========================

mfrapSystem      OBJECT IDENTIFIER ::= { mfrap 1 }


--
--       The mfrapSysTable
--              This table contains the system attributes of the MFRAP 
--              CSU with enhanced support for Frame Relay Networking.
      
mfrapSysTable      OBJECT IDENTIFIER ::= { mfrapSystem 1 }

mfrapSysType       OBJECT-TYPE
          SYNTAX      DisplayString (SIZE (0..255))
          ACCESS      read-only
          STATUS      mandatory
          DESCRIPTION
             "A textual description of the system model identifier.
              for example: SYNC-MFRAP"
          ::= { mfrapSysTable 1 }

mfrapSysSoftRev    OBJECT-TYPE
          SYNTAX      DisplayString (SIZE (0..10))
          ACCESS      read-only
          STATUS      mandatory
          DESCRIPTION
             "Displays the Software Revision of the application code
              installed in this node."
          ::= { mfrapSysTable 2 }

mfrapSysHardRev    OBJECT-TYPE
          SYNTAX      DisplayString (SIZE (0..10))
          ACCESS      read-only
          STATUS      mandatory
          DESCRIPTION
             "Displays the Hardware Revision of the node."
          ::= { mfrapSysTable 3 }

mfrapSysNumT1Installed    OBJECT-TYPE
          SYNTAX      INTEGER (0..1)
          ACCESS      read-only
          STATUS      mandatory
          DESCRIPTION
             "The number of Wide Area Network (T1) ports that are
              installed.  There is 1 on the MFRAP."
          ::= { mfrapSysTable 4 }

mfrapSysNumDteInstalled    OBJECT-TYPE
          SYNTAX      INTEGER (0..1)
          ACCESS      read-only
          STATUS      mandatory
          DESCRIPTION
             "The number of user serial data channels (DTE) that are
              installed.  There is 1 on the MFRAP."
          ::= { mfrapSysTable 5 }

mfrapSysNumMaintInstalled    OBJECT-TYPE
          SYNTAX      INTEGER (0..2)
          ACCESS      read-only
          STATUS      mandatory
          DESCRIPTION
             "The number of Async Maintenance/Comm (console ports 
              that are installed.  There are 2 on the MFRAP: one
              for the console interface and one for SLIP management."
          ::= { mfrapSysTable 6 }

mfrapSysName       OBJECT-TYPE
          SYNTAX      DisplayString (SIZE (0..16))
          ACCESS      read-write
          STATUS      mandatory
          DESCRIPTION
             "The user supplied name of the node.  This object
              does not affect operation, but may be useful
              for network management."
          ::= { mfrapSysTable 7 }

mfrapSysSerialNo      OBJECT-TYPE
          SYNTAX      DisplayString (SIZE (0..12))
          ACCESS      read-only
          STATUS      mandatory
          DESCRIPTION
             "The serial number of the board."
          ::= { mfrapSysTable 8 }

mfrapSysResetNode    OBJECT-TYPE
          SYNTAX      INTEGER
          {
               reset-node (321)
          }
          ACCESS      write-only
          STATUS      mandatory
          DESCRIPTION
           "Command to reset the node. NODE WILL BE OFF-LINE AND 
           USER DATA WILL BE INTERRUPTED FOR APPROXIMATELY 15 
           SECONDS. Full network recovery may take longer. "
          ::= { mfrapSysTable 9 }

mfrapSysAmtMemoryInstalled    OBJECT-TYPE
          SYNTAX      INTEGER
          ACCESS      read-only
          STATUS      mandatory
          DESCRIPTION
             "The amount of memory (RAM) installed (in megabytes)."
          ::= { mfrapSysTable 10 }

mfrapSysLocation       OBJECT-TYPE
          SYNTAX  DisplayString (SIZE (0..16))
          ACCESS  read-write
          STATUS  mandatory
          DESCRIPTION
             "The user supplied location of the node.  This
              object does not affect operation, but may be
              useful for network management."
          ::= { mfrapSysTable 12 }

mfrapSysContact        OBJECT-TYPE
          SYNTAX      DisplayString (SIZE (0..16))
          ACCESS      read-write
          STATUS      mandatory
          DESCRIPTION
             "The user supplied contact information for the
              node.  This object does not affect operation,
              but may be useful for network management."
          ::= { mfrapSysTable 13 }                                

mfrapSysPrompt        OBJECT-TYPE
          SYNTAX      DisplayString (SIZE (0..8))
          ACCESS      read-write
          STATUS      mandatory
          DESCRIPTION
             "Configurable Command Line Interface (CLI) prompt. CLI
              is the User Interface protocol used for directly 
              attached VT100 terminal access and for remote
              access via Telnet."
          ::= { mfrapSysTable 15 }                                

mfrapSysBootRev    OBJECT-TYPE
          SYNTAX      DisplayString (SIZE (0..10))
          ACCESS      read-only
          STATUS      mandatory
          DESCRIPTION
             "Displays the Software Revision of the Bootstrapping 
            code installed in this node."
          ::= { mfrapSysTable 16 }


mfrapSysNestId     OBJECT-TYPE
          SYNTAX      DisplayString (SIZE (0..16))
          ACCESS      read-write
          STATUS      mandatory
          DESCRIPTION
             "The user supplied name of the nest where this card
              resides. This can be used to group all cards from
              the same nest together for network management. Note 
              an MFRAP standalone unit will not allow this to be
              'set' and will return the string 'standalone'."
          ::= { mfrapSysTable 17 }


mfrapSysFeatureTable      OBJECT IDENTIFIER ::= { mfrapSystem 2 }

mfrapSysSLIPSupported     OBJECT-TYPE
     SYNTAX      DisplayString (SIZE (0..10))
     ACCESS      read-only
     STATUS      mandatory
     DESCRIPTION
        "Shows whether the unit has SLIP (Serial Line IP) capability.
         SLIP is a method for out-of-band management that connects
         through the asynchronous terminal port."
     ::= { mfrapSysFeatureTable 1 }

mfrapSysPPPSupported     OBJECT-TYPE
     SYNTAX      DisplayString (SIZE (0..10))
     ACCESS      read-only
     STATUS      mandatory
     DESCRIPTION
        "Shows whether the unit has PPP (Point to Point protocol)
         capability. PPP is a method for out-of-band management 
         that connects through the asynchronous terminal port."
     ::= { mfrapSysFeatureTable 2 }

mfrapSysRDOSupported     OBJECT-TYPE
     SYNTAX      DisplayString (SIZE (0..10))
     ACCESS      read-only
     STATUS      mandatory
     DESCRIPTION
        "Shows whether the unit has Remote Dial Out capability."
     ::= { mfrapSysFeatureTable 3 }

mfrapSysETHSupported     OBJECT-TYPE
     SYNTAX      DisplayString (SIZE (0..10))
     ACCESS      read-only
     STATUS      mandatory
     DESCRIPTION
        "Shows whether the unit has Ethernet capability."
     ::= { mfrapSysFeatureTable 4 }

mfrapSysTKRSupported     OBJECT-TYPE
     SYNTAX      DisplayString (SIZE (0..10))
     ACCESS      read-only
     STATUS      mandatory
     DESCRIPTION
        "Shows whether the unit has Token Ring capability."
     ::= { mfrapSysFeatureTable 5 }

mfrapSysExtTimSupported     OBJECT-TYPE
     SYNTAX      DisplayString (SIZE (0..10))
     ACCESS      read-only
     STATUS      mandatory
     DESCRIPTION
        "Shows whether the unit has External Timing capability."
     ::= { mfrapSysFeatureTable 6 }

mfrapSysBRISupported     OBJECT-TYPE
     SYNTAX      DisplayString (SIZE (0..10))
     ACCESS      read-only
     STATUS      mandatory
     DESCRIPTION
        "Shows whether the unit has BRI (ISDN Basic Rate) capability."
     ::= { mfrapSysFeatureTable 7 }

mfrapSysSelDTESupported     OBJECT-TYPE
     SYNTAX      DisplayString (SIZE (0..10))
     ACCESS      read-only
     STATUS      mandatory
     DESCRIPTION
        "Shows whether the unit has a Selectable DTE interface."
     ::= { mfrapSysFeatureTable 8 }

mfrapSysMLSupported     OBJECT-TYPE
     SYNTAX      DisplayString (SIZE (0..10))
     ACCESS      read-only
     STATUS      mandatory
     DESCRIPTION
        "Shows whether the unit supports MLs
         (out-of-band management links)."
     ::= { mfrapSysFeatureTable 9 }

mfrapSysNumDlcisSupported     OBJECT-TYPE
     SYNTAX      INTEGER
     ACCESS      read-only
     STATUS      mandatory
     DESCRIPTION
        "Shows how many DLCIs can be monitored
         for Short Term Statistics."
     ::= { mfrapSysFeatureTable 10 }

mfrapSysLTFNumDlcis     OBJECT-TYPE
     SYNTAX      INTEGER
     ACCESS      read-only
     STATUS      mandatory
     DESCRIPTION
        "Shows how many DLCIs can be specified
         in the Long Term Statistics Filter."
     ::= { mfrapSysFeatureTable 11 }

mfrapSysLTFNumProtocols     OBJECT-TYPE
     SYNTAX      INTEGER
     ACCESS      read-only
     STATUS      mandatory
     DESCRIPTION
        "Shows how many protocols can be specified
         in the Long Term Statistics Filter."
     ::= { mfrapSysFeatureTable 12 }

mfrapSysNumUserProtocols     OBJECT-TYPE
     SYNTAX      INTEGER
     ACCESS      read-only
     STATUS      mandatory
     DESCRIPTION
        "Shows how many protocols can be defined by the user.
         The user configures TCP/UDP ports which can be monitored
         as protocols.  They are available for short term or
         long term statistics monitoring."
     ::= { mfrapSysFeatureTable 13 }

mfrapSysNumSnmpMgrs     OBJECT-TYPE
     SYNTAX      INTEGER
     ACCESS      read-only
     STATUS      mandatory
     DESCRIPTION
        "Shows how many SNMP managers can be programmed in the
         table mfrapCfgSnmpMngrTable. These managers are sent 
         TRAPs if configured to do so."
     ::= { mfrapSysFeatureTable 14 }

mfrapSysNumDlciNames     OBJECT-TYPE
     SYNTAX      INTEGER
     ACCESS      read-only
     STATUS      mandatory
     DESCRIPTION
        "Shows how many DLCI names can be defined by the user
         in the table mfrapCfgFrPerfDlciNamesTable."
     ::= { mfrapSysFeatureTable 15 }



-- =========================
-- == CONFIGURATION group ==
-- =========================

mfrapConfiguration   OBJECT IDENTIFIER ::= { mfrap 2 }


--
--       The Management Configuration Table
--              This table contains the management-related
---             Configuration information for the MFRAP T1 DSU.

mfrapCfgMgmtTable   OBJECT IDENTIFIER ::= { mfrapConfiguration 1 }

--
--       The IP Configuration Table
--              This table contains the Configuration for Internet Protocol
--              parameters for device management. These parameters include 
--              IP addressing and any configurable IP-based support options 
--              (such as Telnet).

mfrapCfgIpTable OBJECT IDENTIFIER ::= { mfrapCfgMgmtTable 1 }
 
mfrapCfgIpMyIP   OBJECT-TYPE
          SYNTAX      IpAddress
          ACCESS      read-write
          STATUS      mandatory
          DESCRIPTION
             "The IP address for this node.  This address will be unique to
              the IP network and is required for in-band or out-of-band
              ip and SNMP management."
          ::= { mfrapCfgIpTable 1 }
 
mfrapCfgIpPeerIP   OBJECT-TYPE
          SYNTAX      IpAddress
          ACCESS      read-write
          STATUS      mandatory
          DESCRIPTION
             "This parameter is not used internally by
              the unit. It is intended to identify either
              the device directly connected to the SLIP
              port or, in Frame Relay applications, the
              address of the primary network management 
              station. This should always be non-zero."
          ::= {mfrapCfgIpTable 2 }
 
mfrapCfgIpMask   OBJECT-TYPE
          SYNTAX      IpAddress
          ACCESS      read-write
          STATUS      mandatory
          DESCRIPTION
             "The IP Network Mask (eg 255.255.255.0)."
          ::= { mfrapCfgIpTable 3 }
 
mfrapCfgIpMaxMTU OBJECT-TYPE
          SYNTAX      INTEGER  (1..1024)
          ACCESS      read-write
          STATUS      mandatory
          DESCRIPTION
             "The Maximum Transmission Unit is the size of the
              largest IP packet supported.  This value should
              be set to the lowest value supported by any
              equipment in the transmission path.  A size of
              1006 (including header) is suggested."
          ::= { mfrapCfgIpTable 4 }

mfrapCfgIpChannel   OBJECT-TYPE
          SYNTAX      INTEGER
          {
              none           (1),
              slip-port      (2),
              in-band-dlci   (3)
          }
          ACCESS      read-only
          STATUS      mandatory
          DESCRIPTION
               "This is the method by which IP traffic is being carried.
                Either via the SLIP port or a DLCI.  This is how
                your InBand Managenent scheme is set up."
          ::= { mfrapCfgIpTable 5 }

mfrapCfgIpTelnetEnable   OBJECT-TYPE
          SYNTAX      INTEGER
          {
              enable-telnet  (1),
              disable-telnet (2)
          }
          ACCESS      read-write
          STATUS      mandatory
          DESCRIPTION
             "Enables/Disables the telnet feature.
              Valid values are enable-telnet (1)
              and disable-telnet (2)."
          ::= { mfrapCfgIpTable 6 }

mfrapCfgIpTelnetAutoLogOut   OBJECT-TYPE
          SYNTAX      INTEGER
          {
              autologout-at-15-minutes (1),
              disable-autologout       (2),
              autologout-at-3-minutes  (3),
              autologout-at-5-minutes  (5),
              autologout-at-10-minutes (10),
              autologout-at-30-minutes (30),
              autologout-at-60-minutes (60)
          }
          ACCESS      read-write
          STATUS      mandatory
          DESCRIPTION
             "Enables/Disables the telnet auto-logout, logging out
              the user after a certain length of idle time.
              Valid values are disable-autologout (2), and a
              number of timeout intervals including
              autologout-at-15-minutes (1), autologout-at-3-minutes (3),
              and the default autologout-at-5-minutes (5)."
          ::= { mfrapCfgIpTable 7 }


--
--       The TFTP Configuration Table
--              This table contains the Configuration for the TFTP
--              (Trivial File Transfer Protocol) support on the unit.
--              TFTP is an ip-based protocol used by the unit for 
--              software upgrades.

mfrapCfgTftpTable OBJECT IDENTIFIER ::= { mfrapCfgMgmtTable 2 }

mfrapCfgTftpInitiate OBJECT-TYPE
          SYNTAX DisplayString (SIZE (0..8))
          ACCESS write-only
          STATUS mandatory
          DESCRIPTION
            "After setting the other TFTP parameters,
             start the TFTP Flash ROM upgrade
             by entering the TFTP password."
          ::= {mfrapCfgTftpTable 1}

mfrapCfgTftpIpAddress   OBJECT-TYPE
          SYNTAX     IpAddress
          ACCESS     read-write
          STATUS     mandatory
          DESCRIPTION
             "The IP address of the TFTP host from which
              to retrieve the Flash ROM image."
          ::= {mfrapCfgTftpTable 2}
   
mfrapCfgTftpFilename OBJECT-TYPE
          SYNTAX DisplayString (SIZE (0..80))
          ACCESS read-write
          STATUS mandatory
          DESCRIPTION
            "The filename of the new ROM Image on the TFTP host."
          ::= {mfrapCfgTftpTable 3}

mfrapCfgTftpInterface OBJECT-TYPE
          SYNTAX      INTEGER
          {
              dte-interface  (1),
              t1-interface   (2),
              slip-interface (3)
          }
          ACCESS read-write
          STATUS mandatory
          DESCRIPTION
            "The interface on which TFTP data passes. This is 
             only used for in-band management modes. When a unit is
             in SLIP mode, this object is not applicable. A 'get'will 
             return a value of '3' and set is ignored.
             (1) dte-interface
             (2) t1-interface
             (3) Not applicable"
          ::= {mfrapCfgTftpTable 4}

mfrapCfgTftpDlci OBJECT-TYPE
          SYNTAX INTEGER (-1..63487)
          ACCESS read-write
          STATUS mandatory
          DESCRIPTION
            "The DLCI on which the TFTP host can be found.
             A value of -1 signifies not-applicable."
          ::= {mfrapCfgTftpTable 5}

mfrapCfgTftpStatus OBJECT-TYPE
          SYNTAX INTEGER
          {
              inactive          (1),
              requested         (2),
              transferring      (3),
              programming       (4),
              transfer-aborted  (5),
              host-no-reply     (6),
              file-not-found    (7),
              invalid-file      (8),
              corrupt-file      (9),
              successful        (10)
          }
          ACCESS read-write
          STATUS mandatory
          DESCRIPTION
            "The status of current or most recent TFTP operation.
             Download can be canceled by a Set to inactive."
          ::= {mfrapCfgTftpTable 6}


mfrapCfgTftpNumBytes OBJECT-TYPE
          SYNTAX Counter
          ACCESS      read-only
          STATUS      mandatory
          DESCRIPTION
            "The number of Bytes from the ROM image that have been 
             TFTP'd to the unit"
          ::= {mfrapCfgTftpTable 7}


--
--       The SNMP Configuration Table
--              This table contains the Configuration for the SNMP
--              support on the MFRAP T1 DSU. This includes Trap
--              destinations and any other Trap-related parameters.

mfrapCfgSnmpTable OBJECT IDENTIFIER ::= { mfrapCfgMgmtTable 3 }

mfrapCfgSnmpFrTrap   OBJECT-TYPE
          SYNTAX      INTEGER
          {
              enabled        (1),
              disabled       (2)
          }
          ACCESS      read-write
          STATUS      mandatory
          DESCRIPTION
            "Controls whether or not the Frame Relay DLCI
             status change traps are issued.  These traps are
             dfrapDLCIActiveTrap and dfrapDLCIInactiveTrap.
              (1) FR Trap enabled - a trap will be sent each time 
                  an individual DLCI changes status between active 
                  and inactive. 
              (2) FR Trap disabled -  DLCI state change traps are not sent."
          ::= { mfrapCfgSnmpTable 1 }

mfrapCfgSnmpTrapMuting    OBJECT-TYPE
          SYNTAX      INTEGER (0..10080)
          ACCESS      read-write
          STATUS      mandatory
          DESCRIPTION
            "Controls whether TRAPs are sent or muted. A value of
             0 allows TRAPs to be sent. If not 0, the value represents
             the interval (minutes) at which to send the MutingActive
             trap.  It is the only trap sent during muting.  The valid
             range for the interval is 30 to 10080 (a week)."
         ::= { mfrapCfgSnmpTable 3 }
 
mfrapCfgSnmpNestAlarmTrapEnable  OBJECT-TYPE
          SYNTAX  INTEGER
          {
              enable  (1),
              disable (2)
          }
          ACCESS  read-write
          STATUS  mandatory
          DESCRIPTION
             "Enables or disables the sending of traps for fan
              and/or power supply alarms. Note an MFRAP standalone unit 
              will not allow this to be 'set' and will return the 'disable'."
          ::= {mfrapCfgSnmpTable 4 }

mfrapCfgSnmpDandIPortTrapEnable  OBJECT-TYPE
          SYNTAX  INTEGER
          {
             enable  (1),
             disable (2)
          }
          ACCESS  read-write
          STATUS  mandatory
          DESCRIPTION
             "Enables or disables the sending of traps for the 
              Drop and Insert port.
              (1) enable the sending of traps
              (2) disable the sending of traps"
          ::= {mfrapCfgSnmpTable 5 }


mfrapCfgSnmpUtilTrapEnable  OBJECT-TYPE
         SYNTAX  INTEGER
         {
            enable  (1),
            disable (2)
         }
         ACCESS  read-write
         STATUS  mandatory
         DESCRIPTION
            "Enables or disables the sending of per-DLCI
             utilization traps.
             (1) enable utilization traps
             (2) disable utilization traps "
         ::= { mfrapCfgSnmpTable 6 }
     
mfrapCfgSnmpMgrClearN   OBJECT-TYPE
         SYNTAX  INTEGER
         ACCESS  write-only
         STATUS  mandatory
         DESCRIPTION
           " Deletes the number of entries in the mfrapCfgSnmpMgrTable
             indicated by the value.  If the value is a positive number
             the entries will be deleted starting from the first entry.
             If the value is negative the entries will be deleted 
             starting from the last entry. "
         ::= { mfrapCfgSnmpTable 7 }
         
mfrapCfgSnmpMgrTable   OBJECT-TYPE
         SYNTAX   SEQUENCE OF MfrapCfgSnmpMgrEntry
         ACCESS   not-accessible
         STATUS   mandatory
         DESCRIPTION
            "The table of IP addresses of SNMP managers to receive
             this node's TRAPs."
          ::= { mfrapCfgSnmpTable 2 }

mfrapCfgSnmpMgrEntry   OBJECT-TYPE
         SYNTAX   MfrapCfgSnmpMgrEntry
         ACCESS   not-accessible
         STATUS   mandatory
         DESCRIPTION
            "The IP address of a SNMP manager to receive this node's TRAPs."
         INDEX { mfrapCfgSnmpMgrIndex }
            ::= { mfrapCfgSnmpMgrTable 1 }

MfrapCfgSnmpMgrEntry ::=
         SEQUENCE {
             mfrapCfgSnmpMgrIndex       INTEGER,
             mfrapCfgSnmpMgrIP          IpAddress,
             mfrapCfgSnmpMgrInterface   INTEGER,
             mfrapCfgSnmpMgrDlci        INTEGER
         }

mfrapCfgSnmpMgrIndex OBJECT-TYPE
         SYNTAX   INTEGER
         ACCESS   read-only
         STATUS   mandatory
         DESCRIPTION
            "The index to the list of SNMP managers receiving TRAPs."
         ::= { mfrapCfgSnmpMgrEntry 1 }

mfrapCfgSnmpMgrIP   OBJECT-TYPE
         SYNTAX      IpAddress
         ACCESS      read-write
         STATUS      mandatory
         DESCRIPTION
           "The IP address of a SNMP manager to receive this node's TRAPs.
            Setting this value to 0.0.0.0 will disable the issuance of
            traps to the indexed manager."
         ::= { mfrapCfgSnmpMgrEntry 2 }

mfrapCfgSnmpMgrInterface OBJECT-TYPE
         SYNTAX      INTEGER
         {
              dte-interface  (1),
              t1-interface   (2),
              slip-interface (3)
         }
         ACCESS      read-write
         STATUS      mandatory
         DESCRIPTION
            "The interface out which the indexed trap manager can be
             reached. This entry is required in Piggyback and Bi-directional 
             in-band managed applications. In Local, Remote and SLIP-based
             applications, the interface is known and this parameter is
             ignored.
                 (1) Traps sent out DTE interface for this manager
                 (2) Traps sent out T1 interface for this manager
                 (3) Traps sent out SLIP interface (async maint port)

             When the node is configured for SLIP, a GET on this MIB
             object will return slip-interface(3) and a SET of this MIB
             object to slip-interface(3) is allowed but unnecessary.

             When the node is not configured for SLIP, this MIB
             object can be SET to dte-interface(1) or t1-interface(2);
             slip-interface(3) would be rejected."
         ::= { mfrapCfgSnmpMgrEntry 3 }

mfrapCfgSnmpMgrDlci OBJECT-TYPE
         SYNTAX      INTEGER
         ACCESS      read-write
         STATUS      mandatory
         DESCRIPTION
            "The DLCI to use to send TRAPs to this SNMP manager."
         ::= { mfrapCfgSnmpMgrEntry 4 }

--
--       The Communication Port Configuration Table
--              This table contains the Communications Port Configuration
--              information for the MFRAP T1 DSU.

mfrapCfgCommTable OBJECT IDENTIFIER ::= { mfrapCfgMgmtTable 4 }

   --    DESCRIPTION   
   --       "The Communication Port Configuration table contains
   --        parameters for the RS232/RJ48 Maint/Console port on the
   --        MFRAP.  The User Interface (ASCII) Port is Index=1; 

mfrapCfgCommMode      OBJECT-TYPE
     SYNTAX      INTEGER
     {
         vt100     (1),
         slip      (2),
         modem     (3)
     }
     ACCESS      read-write
     STATUS      mandatory
     DESCRIPTION
        "The protocol running on the Maintenance port. VT100 (1), for
         the User Interface, SLIP (2) for the SNMP support, 
         MODEM(3) for remote VT100 support."
     ::= { mfrapCfgCommTable 1 }

mfrapCfgCommBaud OBJECT-TYPE
     SYNTAX      INTEGER
     {
         baud-2400   (2),
         baud-9600   (4),
         baud-19200  (5),
         baud-38400  (6)
     }
     ACCESS      read-write
     STATUS      mandatory
     DESCRIPTION
        "Asynchronous baud rate for the Maintenance/Comm port 
         (Console). This must be configured to match either the 
         VT100 compatible terminal, MODEM support or the SLIP Terminal  
         Server depending upon the Comm port mode. 
         (2) baud-2400 
         (4) baud-9600
         (5) baud-19200
         (6) baud-38400"
     ::= { mfrapCfgCommTable 2 }

mfrapCfgCommDataBits OBJECT-TYPE
     SYNTAX      INTEGER
     {
         databits-7 (1),
         databits-8 (2)
     }
     ACCESS      read-write
     STATUS      mandatory
     DESCRIPTION
        "Databits for this Communication port.  Values
         are databits-7 (1) and databits-8 (2)."
     ::= { mfrapCfgCommTable 3 }

mfrapCfgCommStopBits OBJECT-TYPE
     SYNTAX      INTEGER
     {
         stopbits-1 (1),
         stopbits-1-5 (2),
         stopbits-2 (3)
     }
     ACCESS      read-write
     STATUS      mandatory
     DESCRIPTION
        "Number of Stopbits for this Communication port.
         Values are stopbits-1 (1), stopbits-1-5 (2),
         and stopbits-2 (3)."
     ::= { mfrapCfgCommTable 4 }

mfrapCfgCommParity OBJECT-TYPE
     SYNTAX      INTEGER
     {
         no-parity   (1),
         odd-parity  (2),
         even-parity (3)
     }
     ACCESS      read-write
     STATUS      mandatory
     DESCRIPTION
        "Parity for this Communication port.  Values are
         no-parity (1), odd-parity (2), even-parity (3)."
     ::= { mfrapCfgCommTable 5 }

mfrapCfgCommFlowCtrl OBJECT-TYPE
     SYNTAX      INTEGER
     {
         no-flow-control (1)
     }
     ACCESS      read-write
     STATUS      mandatory
     DESCRIPTION
        "Flow Control for this Communication port.  Values
         are no-flow-control (1)."
     ::= { mfrapCfgCommTable 6 }

mfrapCfgCommModeAutoDetect  OBJECT-TYPE
      SYNTAX  INTEGER
      {
          enable  (1),
          disable (2)
      }
      ACCESS  read-write
      STATUS  mandatory
      DESCRIPTION
         "Enables or disables the auto detection of RS-232
          data on the front MAINT port. When enabled, and data
          detected, the unit will temporarily convert to VT100 mode
          to allow a local user access when the unit is in SLIP
          or MODEM mode.
             (1) enable COMM-MAINT port auto detect
             (2) disable COMM-MAINT port auto detect "
         ::= { mfrapCfgCommTable 7 }


--
--       The DLCI Configuration Table
--              This table contains the Configuration for in-band
--              Frame Relay management. This includes in-band mode,
--              the management PVC's local DLCI address, format and 
--              parameters related to Frame Relay management frame
--              format.

mfrapCfgFrDLCITable OBJECT IDENTIFIER ::= { mfrapCfgMgmtTable 5 }

mfrapCfgFrDLCIMode  OBJECT-TYPE
          SYNTAX      INTEGER
          {
              inactive        (1),
              local           (2),
              remote          (3),
              bidirectional   (4),
              piggyback       (5),
              fixedDCE        (6)
          }
          ACCESS      read-write
          STATUS      mandatory
          DESCRIPTION
        "Shows the mode that DLCI In-band Management is set up for -
         inactive      (1) - Inband management is not enabled;
         local         (2) - Inband managed using a dedicated private
                             PVC with access exclusively through the
                             DTE interface;
         remote        (3) - Inband managed using a dedicated private
                             PVC with access exclusively through the
                             WAN interface;
         bidirectional (4) - Inband managed using a dedicated private
                             PVC with access supported through either
                             interface;
         piggyback     (5) - Inband managed using any provisioned PVC,
                             statistically multiplexed with user data;
         fixedDCE      (6) - Inband managed mode similar to piggyback
                             mode except for LMI behavior;  The unit
                             will always source LMI Responses separately
                             on each interface (emulating a Frame Relay
                             DCE device). A single PVC will be provisioned
                             and is used for both user data and management
                             traffic. This mode of operation is useful in
                             an environment that does not include a Frame
                             Relay switch but does include a pair of
                             interconnected Frame Relay FRADs or Routers
                             which can only be configured as a Frame Relay
                             DTE device."
          ::= { mfrapCfgFrDLCITable 1 }

mfrapCfgFrDLCIValue  OBJECT-TYPE
          SYNTAX      INTEGER (16..63487)
          ACCESS      read-write
          STATUS      mandatory
          DESCRIPTION
             "The DLCI identifier, the value of the DLCI field in the frame."
          ::= { mfrapCfgFrDLCITable 2 }

mfrapCfgFrDLCIEncap   OBJECT-TYPE
          SYNTAX      INTEGER
          {
              rfc1490        (1),
              rfc1490snap    (2),
              auto           (3),
              cisco          (4)
          }
          ACCESS      read-write
          STATUS      mandatory
          DESCRIPTION
             "This is the protocol used for enacapsulating and formatting
              ip data for Frame Relay transmission. This setting is specific
              to management data to and from the unit.
              (1) RFC1490 - per IETF standard with Network Level 
                  Protocol ID (NLPID) set for IP encapsulation.
              (2) RFC1490 SNAP/IP - per IETF standard with NLPID set 
                  for Sub-Network Access Protocol (SNAP).
              (3) auto - adjusts to either of these encapsulation techniques
                  as required. 
              (4) Cisco - proprietary encapsulation (4-byte header)."
          ::= { mfrapCfgFrDLCITable 3 }

mfrapCfgFrDLCIMgmtDE   OBJECT-TYPE
          SYNTAX      INTEGER
          {
              no-DE-bit-0     (1),
              yes-DE-bit-1    (2)
          }
          ACCESS      read-write
          STATUS      mandatory
          DESCRIPTION
        "Provides user control over the state of the Frame Relay Discard
         Eligibility bit of all management frames generated by
         the unit. Frames marked DE=1 are more likely to be dropped in a 
         congested Frame Relay network than those that are DE=0. Heavily 
         congested circumstances can cause both to be dropped. Additionally,
         frames marked DE=0 may get re-marked to DE=1 by intervening
         equipment.
         (1) DE bit cleared to 0: frame is not discard eligible
         (2) DE bit set to 1: frame is discard eligible"
          ::= { mfrapCfgFrDLCITable 4 }

--
--       The Application Configuration Table
--              This table contains the Application (system) Configuration
--              information for the MFRAP T1 DSU.  This includes system
--              timing and user-application type.

mfrapCfgAppTable   OBJECT IDENTIFIER ::= { mfrapConfiguration 2 }

mfrapCfgAppClockSource OBJECT-TYPE
          SYNTAX      INTEGER
          {
               internal        (1),
               network         (2),
               dte             (3),
            drop-and-insert (4)
          }
          ACCESS      read-write
          STATUS      mandatory
          DESCRIPTION
             "Default timing, or clock, source.  There must be only one
              source on a T1 line.  Node should always be network (2) 
              timed on a point-to-network application. Line
              Driver applications need one node as internal (1),
              one as network (2).  Options are given to source
              the clock from the DTE port or the D&I port. "  
          ::= { mfrapCfgAppTable 1 }

mfrapCfgAppCircuitId    OBJECT-TYPE
          SYNTAX      DisplayString (SIZE (0..30))
          ACCESS      read-write
          STATUS      mandatory
          DESCRIPTION
             "Circuit identifier provided by the service provider."
          ::= { mfrapCfgAppTable 2 }

mfrapCfgAppType    OBJECT-TYPE
          SYNTAX      INTEGER
          {
               dedicated   (1),
               frame-relay (2)   
          } 
          ACCESS      read-write
          STATUS      mandatory
          DESCRIPTION
             "Indicates type of service purchased on the attached
              network line T1.  Valid selections are
              dedicated (1) and Frame Relay (2)."
          ::= { mfrapCfgAppTable 3 }

mfrapCfgAppFormat OBJECT-TYPE
          SYNTAX      INTEGER
          {
               cbo         (1),
               hdlc        (2)
          }
          ACCESS      read-write
          STATUS      mandatory
          DESCRIPTION
          "Refer to Application Type. Frame Relay is based upon
           HDLC framing. To operate in a Frame Relay application
           the Format must be set for HDLC. To operate in a
           protocol-independent application the Format must be 
           set for Constant Bit Operation (CBO). Note - changing 
           this value will automatically change the Application 
           Type setting and vice versa
           (1) CBO: protocol-independent transparent DSU/CSU
           (2) HDLC: Frame and protocol aware DSU/CSU"
     ::= { mfrapCfgAppTable 4 }

mfrapCfgAppLpbkTimeout OBJECT-TYPE
          SYNTAX      INTEGER (0..1440)
          ACCESS      read-write
          STATUS      mandatory
          DESCRIPTION
             "The amount of time a loopback may run before
              timing out and automatically terminating.
              The timeout is in minutes and a value of 0
              means no timeout."
     ::= { mfrapCfgAppTable 5 }

mfrapCfgAppPerfBuffLimit OBJECT-TYPE
          SYNTAX      INTEGER (0..512)
          ACCESS      read-write
          STATUS      mandatory
          DESCRIPTION
             "This value represents the throttling mechanism
             used to determine the optimum level of statistical
             processing versus managability of the unit. The
             lower the value (1 - 128), the unit becomes more
             responsive to management commands during very heavy
             utilization at the possible expense of statistical 
             accuracy.  The larger the value (129 - 512), the 
             more accurate the MFRAP performs statistical analysis 
             of the frames but management may seem slow or 
             unresponsive during periods of very heavy link 
             utilization.
             NOTE: A value of 0 disables statistical
             processing entirely."
      ::= { mfrapCfgAppTable 10 }

--
--       The T1 Configuration Table
--              This table contains the T1 port Configuration
--              information for the MFRAP CSU.

mfrapCfgT1Table   OBJECT IDENTIFIER ::= { mfrapConfiguration 3 }

   --     DESCRIPTION
   --        "The T1 Port Configuration table contains
   --         parameters for the Framed TDM (T1) port on the
   --         MFRAP. "

mfrapCfgT1Framing    OBJECT-TYPE
     SYNTAX      INTEGER 
     {
        d4              (1),
        esf-54016       (2),
        esf-ansi        (3)
     }
     ACCESS        read-write
     STATUS        mandatory
     DESCRIPTION
      "Type of Framing on this T1 Line.  Check with your service 
       provider to determine value.
         (1) D4 -  also known as Superframe or SF.
         (2) ESF 54016 - Extended Superframe supporting the Facility Data 
             Link per AT&T pub 54016.  ESF provides enhanced performance
             monitoring capabilities over the FDL. 
         (3) ESF ANSI - Extended SuperFrame supporting the Facility Data 
             Link per ANSI T1.403 standard. ESF provides enhanced performance
             monitoring capabilities over the FDL."
    ::= { mfrapCfgT1Table 1 }

mfrapCfgT1LineEncoding    OBJECT-TYPE
     SYNTAX      INTEGER 
     {
        ami             (1),
        b8zs            (2)
     }
     ACCESS        read-write
     STATUS        mandatory
     DESCRIPTION
      "T1 interface bipolar encoding scheme.  Check with your 
      service provider to determine value. B8ZS, which inherently 
      provides ample 'ones-density', is recommended. AMI users 
      must pay special attention to the 'ones-density' requirements
      of the service provider.
         (1) B8ZS -  intercepts and encodes streams of 8 consecutive zeros
             and transmits them as a special pattern including Bipolar or 
             Line Code Violations. Function not supported on certain networks.
         (2) AMI - Alternate Mark Inversion - sends the user data without
             introducing controlled BPVs."
    ::= { mfrapCfgT1Table 2 }

mfrapCfgT1Density    OBJECT-TYPE
     SYNTAX      INTEGER 
     {
        no-density              (1),
        twelve-half-percent     (2),
        one-in-16               (3),
        one-in-64               (4)
     }
     ACCESS        read-write
     STATUS        mandatory
     DESCRIPTION
      "CSU 'ones density' monitor. Defines the maximum number of
      consecutive zeros that can be transmitted to the WAN. 
      If density monitoring is enabled, the composite signal 
      is guaranteed to meet the selected density threshhold at 
      the expense of user data.
         (1) No Density Monitoring - unit will transparently transmit
             user data without regard for ones density. Recommended for
             use in B8ZS applications, in nx56K applications where
             bit-7 stuffing is configured for DTE Channel Density, and 
             when an external CSU is used.
         (2) 12.5% - unit will maintain a sliding window and will assure
             a minumum of 12.5% or an average of 1 in 8 ones. 
         (3) 1 in 16 - unit will guarantee that no more than 15 consecutive
             zeros will be transmit to the WAN.
         (4) 1 in 64 - unit will guarantee that no more than 63 consecutive
             zeros will be transmit to the WAN."
     ::= { mfrapCfgT1Table 3 }

mfrapCfgT1Interface    OBJECT-TYPE
     SYNTAX      INTEGER 
     {
        dsx-1           (1),
        csu             (2)  
     }
     ACCESS        read-write
     STATUS        mandatory
     DESCRIPTION
        "Enables the unit's internal CSU functionality. Typical 
         network access requires a CSU to condition the WAN signal,
         guard against network hazards, and provide access to 
         service personnel for network maintenance.
         (1) Disables internal CSU and unit operates as a DSX-1 cross
             connect device. This should be the setting if the unit is
             cabled to an external CSU device providing network access.
             CSU.
         (2) Enables internal CSU and corresponding feature set which 
             includes density monitoring, line build-out pulse shaping,
             ESF facility data link, and certain diagnostic functions.
             This should be the seting if the unit is directly cabled
             to the service provider's equipment (such as a smart jack). "
     ::= { mfrapCfgT1Table 4 }

mfrapCfgT1LboSetting    OBJECT-TYPE
     SYNTAX      INTEGER 
     {
        zero-db         (1),
        n7-5-db         (2),
        n15-db          (3)
     }
     ACCESS        read-write
     STATUS        mandatory
     DESCRIPTION
        "CSU Line Build Out (LBO). This feature provides selectable output
         signal strength. Consult service provider for proper setting. Signal
         may require attenuation to equalize it with neighboring equipment
         or under certain cabled access conditions. Not applicable if CSU
         functions are diabled (interface type = dsx-1)
         (1) 0dB - standard output signal
         (2) -7.5dB - standard output signal attenuated by 7.5dB
         (3) -15dB - standard output signal attenuated by 15 dB."
    ::= { mfrapCfgT1Table 5 }


--
--       The DTE Configuration Table
   --      "The Dte Port Configuration table contains
   --       parameters for the Serial (DTE) port's 
   --       physical link. The DTE port typically connects
   --       to a customer's equipment such as a Router/FRAD and
   --       formats this data for appropriate WAN transmission."

mfrapCfgDteTable   OBJECT IDENTIFIER ::= { mfrapConfiguration 4 }

   --   DESCRIPTION
   --      "The Dte Port Configuration table contains
   --       parameters for the Serial (DTE) port on the
   --       MFRAP. "
     
mfrapCfgDteIntfType    OBJECT-TYPE
     SYNTAX      INTEGER  
      {
           intf-v35       (3)
--         intf-rs449     (4)
      }
     ACCESS        read-only
     STATUS        mandatory
     DESCRIPTION
      "Sets the electrical interface for the DTE port.
         (3) V.35 interface
         (4) RS-449 interface (not supported)"
     ::= { mfrapCfgDteTable 1 }

mfrapCfgDteDataMode    OBJECT-TYPE
     SYNTAX      INTEGER  
     {
         data-normal     (1),
         data-invert     (2)
     }
     ACCESS        read-write
     STATUS        mandatory
     DESCRIPTION
        "Inverts the DTE data for transfer across the WAN. Can make 
         some applications, particularly HDLC-based protocols, meet 
         density requirements even across clear channel DS0s in AMI 
         mode."
    ::= { mfrapCfgDteTable 2 }

mfrapCfgDteClockMode    OBJECT-TYPE
     SYNTAX      INTEGER  
     {
        clock-normal    (1),
        clock-invert    (2)
     }
     ACCESS        read-write
     STATUS        mandatory
     DESCRIPTION
        "This selection controls how the unit internally latches 
         the transmit data from the DTE. Normal will sample
         data with the rising edge of the selected TX Clock, 
         Invert will sample data with the falling edge of the 
         selected TX Clock. The TX Clock is selected using 
         CfgDteTiming. This clock invertion is most useful when 
         loop-2 timing is used - particularly at higher rates 
         and with long cable runs. Only in rare circumstances 
         will clock-invert be used with loop-1 timing. If the 
         DTE Interface TX statistics are indicating excessive 
         crc errors or aborts then changing this setting may have
         some benefit.
         (1) normal
         (2) invert"
    ::= { mfrapCfgDteTable 3 }

mfrapCfgDteTiming    OBJECT-TYPE
     SYNTAX      INTEGER  
     {
        loop-1  (1),
        loop-2  (2)
     }
     ACCESS        read-write
     STATUS        mandatory
     DESCRIPTION
      "Serial DTE Transmit Timing mode. Loop-1 (1) uses the clock  
      returned from the DTE (TT/TCE) to sample tx data, Loop-2 (2) 
      uses the clock (ST/TC) generated by the node to sample tx 
      data."
    ::= { mfrapCfgDteTable 4 }

mfrapCfgDteLineRate    OBJECT-TYPE
     SYNTAX      INTEGER  (0..1536000)
     ACCESS        read-only
     STATUS        mandatory
     DESCRIPTION
        "Serial DTE Data Rate in bits per second. Valid
         rates depend upon channel density selection: nX56K for 
         bit-7-stuffing, and nX64K for clear-channel (n is an 
         integer 1-24 inclusive). This read-only value is the
         value which was most recently set through CfgDteConnRate; 
         in the event of a connection failure, this field should be
         examined along with CfgDteChannelDensity and CfgDteStartDso 
         to determine the parameter mismatch that caused the connection 
         failure."
    ::= { mfrapCfgDteTable 5 }

mfrapCfgDteChannelDensity    OBJECT-TYPE
     SYNTAX      INTEGER  
     {
        bit-7-stuff     (56),
        clear-channel   (64)
     }
     ACCESS        read-only
     STATUS        mandatory
     DESCRIPTION
        "Packing of serial data into T1 DS0's. Bit-7-stuff 
         supports DTE rates of nX56Kb/s (from 56K to 1344K) and 
         provides sufficient ones-density on any circuit. 
         Clear-channel allows DTE rates of nX64Kb/s (from 64K
         to 1.536M) and may require an additional means 
         of density enforcement (eg, B8ZS). This read-only value 
         is the value which was most recently set through CfgDteConnDensity; 
         in the event of a connection failure, this field should be 
         examined along with CfgDteLineRate and CfgDteStartDso to 
         determine the parameter mismatch that caused the connection 
         failure."
    ::= { mfrapCfgDteTable 6 }

mfrapCfgDteStartDs0            OBJECT-TYPE
     SYNTAX        INTEGER
     {
         ds0-01        (1),
         ds0-02        (2),
         ds0-03        (3),
         ds0-04        (4),
         ds0-05        (5),
         ds0-06        (6),
         ds0-07        (7),
         ds0-08        (8),
         ds0-09        (9),
         ds0-10        (10),
         ds0-11        (11),
         ds0-12        (12),
         ds0-13        (13),
         ds0-14        (14),
         ds0-15        (15),
         ds0-16        (16),
         ds0-17        (17),
         ds0-18        (18),
         ds0-19        (19),
         ds0-20        (20),
         ds0-21        (21),
         ds0-22        (22),
         ds0-23        (23),
         ds0-24        (24),
         no-current-connections (40),
         non-continuous-ds0s (41)
     }
     ACCESS        read-only
     STATUS        mandatory
     DESCRIPTION
        "T1 WAN includes 24 DS0's available for user data. Each DS0
         carries either 56Kbit/sec (bit-7-stuffing) or 64KBit/sec 
         (clear-channel). This value is the starting DS0 used by the 
         node to allocate DS0s to match the DTE's data rate. Sequential, 
         contiguous DS0s are assigned as required. The number of DS0s 
         required is based upon the DTE Data Rate and DTE Channel Mapping. 
         This read-only value is the value which was most recently set 
         through DteCfgConnStartDs0; in the event of a connection failure, 
         this field should be examined along with CfgDteLineRate and 
         CfgDteChanelDensity to determine the parameter mismatch that 
         caused the connection failure."
     ::= { mfrapCfgDteTable 7 }

mfrapCfgDteConnStatus         OBJECT-TYPE  
     SYNTAX       INTEGER
     {
        connections-valid      (1),
--      incorrect-bandwidth    (2),
--      bandwidth-conflict     (3),
        no-current-connections (4)
     }
     ACCESS       read-only
     STATUS       mandatory
     DESCRIPTION
        "The current status of the WAN to DTE mappings.
         (1) connections valid and DS0s allocated to DTE data.
         (4) no connections configured between WAN and DTE."
     ::= { mfrapCfgDteTable 8 }

mfrapCfgDteConnStartDs0            OBJECT-TYPE
     SYNTAX        INTEGER
     {
         ds0-01        (1),
         ds0-02        (2),
         ds0-03        (3),
         ds0-04        (4),
         ds0-05        (5),
         ds0-06        (6),
         ds0-07        (7),
         ds0-08        (8),
         ds0-09        (9),
         ds0-10        (10),
         ds0-11        (11),
         ds0-12        (12),
         ds0-13        (13),
         ds0-14        (14),
         ds0-15        (15),
         ds0-16        (16),
         ds0-17        (17),
         ds0-18        (18),
         ds0-19        (19),
         ds0-20        (20),
         ds0-21        (21),
         ds0-22        (22),
         ds0-23        (23),
         ds0-24        (24),
         no-current-connections (40),
         non-continuous-ds0s (41)
     }
     ACCESS        read-write
     STATUS        mandatory
     DESCRIPTION
        "T1 WAN includes 24 DS0's available for user data. Each DS0
         carries either 56Kbit/sec (bit-7-stuffing) or 64KBit/sec 
         (clear-channel). This value is the starting DS0 used by the 
         node to allocate DS0s to match the DTE's data rate. Sequential, 
         contiguous DS0s are assigned as required. The number of DS0s 
         required is based upon the DTE Data Rate and DTE Channel Mapping. 
         Consult WAN service provider for the appropriate setting here in 
         a fractional T1 application."
     ::= { mfrapCfgDteTable 9 }

mfrapCfgDteConnRate             OBJECT-TYPE
     SYNTAX        INTEGER (0..1536000)
     ACCESS        read-write
     STATUS        mandatory
     DESCRIPTION
        "Serial DTE Data Rate in bits per second. Valid
         rates depend upon channel density selection: nX56K for 
         bit-7-stuffing, and nX64K for clear-channel (n is an 
         integer 1-24 inclusive). Rates are entered in bits/sec, 
         for example, 128000 for a 128Kbit/sec DTE data rate."
     ::= { mfrapCfgDteTable 10 }

mfrapCfgDteConnDensity          OBJECT-TYPE
     SYNTAX        INTEGER 
     {
         bit-7-stuff     (56),
         clear-channel   (64)
     }
     ACCESS        read-write
     STATUS        mandatory
     DESCRIPTION
        "Packing of serial data into T1 DS0's. Bit-7-stuff 
         supports DTE rates of nX56Kb/s (from 56K to 1344K) and 
         provides sufficient ones-density on any circuit. 
         Clear-channel supports DTE rates of nX64Kb/s (from 64K
         to 1.536M) and may require an additional means 
         of density enforcement (eg, B8ZS).
         (56) Bit 7 Stuffing (nx56K data rate, n=1-24)
         (64) Clear Channel (nx64K data rate, n=1-24)"
     ::= { mfrapCfgDteTable 11 }

mfrapCfgDteConnDs0Required         OBJECT-TYPE
     SYNTAX        INTEGER (0..24)
     ACCESS        read-only
     STATUS        mandatory
     DESCRIPTION
      "The number of DS0s required by the node's DTE port. 
      This is based upon the DTE data rate and channel density 
      selections."
      ::= { mfrapCfgDteTable 12 }

mfrapCfgDteConnAutoStatus         OBJECT-TYPE  
     SYNTAX       INTEGER
     {
         configuration-valid   (1),
         configuration-invalid (2),
         valid-config-updated  (3),
         invalid-cfg-no-update (4)
     }
     ACCESS       read-only
     STATUS       mandatory
     DESCRIPTION
        "There's a tight correlation among DTE data rate, starting
         DS0, and channel density. This read-only parameter reports
         the status of the most recent change to any of these connection
         parameters. If the connection request is not valid a mismatch
         among DteLineRate, DteStartDs0, and DteChannelDensity must be
         resolved
         (1) and (3) configuration valid - the previous connections profile is 
             accepted and activated
         (2) and (4) connections profile invalid, previous configuration 
             remains."
     ::= { mfrapCfgDteTable 13 }             

mfrapCfgDteConnAutoUpdate         OBJECT-TYPE  
     SYNTAX       INTEGER
     {
         config-and-connect (1)
     }
     ACCESS       write-only
     STATUS       mandatory
     DESCRIPTION
         "Updates the connection-critical parameters: line rate,
          channel density and starting ds0; drops the currect
          connection; and initiate the new connection. Following
          the issuance of this command, DteAutoStatus should be 
          queried to verify the update was successful.  The setting
          of this object updates the mfrapCfgEditTable.  In order
          for the changes to take effect in the system, the 
          mfrapCfgConnUpdateCmd must subsequently be set."
     ::= { mfrapCfgDteTable 14 }

mfrapCfgDteRts         OBJECT-TYPE  
     SYNTAX       INTEGER
     {
         internal-held-active (1),
         external-from-dte (2)
     }
     ACCESS       read-write
     STATUS       mandatory
     DESCRIPTION
     "Selects whether the RTS signal is external-from-dte (2)
      or internal-held-active (1)."
     ::= { mfrapCfgDteTable 15 }

mfrapCfgDteDtr         OBJECT-TYPE  
     SYNTAX       INTEGER
     {
         internal-held-active (1),
         external-from-dte (2)
     }
     ACCESS       read-write
     STATUS       mandatory
     DESCRIPTION
     "Selects whether the DTR signal is external-from-dte (2)
      or internal-held-active (1)."
     ::= { mfrapCfgDteTable 16 }

mfrapCfgDteDcdOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
     "Specifies the behavior of this control signal generated by 
      the M-FRAP towards the DTE.
      inactive-always (1) - signal is permanently INACTIVE.
      active-always   (2) - signal is permanently ACTIVE.
      reflect-carrier (3) - signal echoes the carrier signal status 
         from the WAN.
      inactive-with-test-mode (4) - signal is ACTIVE during normal 
         data transfer and INACTIVE during diagnostic conditions 
         that interfere with data transfer from the DTE to the WAN.
      follow-RTS (5) - signal echoes the status of RTS as processed 
         from the DTE. 
      reflect-carrier-and-RTS (6) - signal is a logical AND between 
         RTS processed from the DTE and the carrier signal status 
         from the WAN. No signal from the WAN or RTS INACTIVE 
         will cause this control signal to be asserted INACTIVE.
      reflect-sync-and-RTS (7) - signal is a logical AND between RTS 
         processed from the DTE and the frame synchronization with the WAN. 
         Red Alarm defines the threshold for declaring synchronization.
      reflect-LMI-and-carrier-and-RTS (8) - signal is a logical AND 
         between RTS processed from the DTE and the carrier signal
         status from the WAN and LMI. If the unit is in an LMI 
         passthrough state then LMI is considered Active.
         LMI Inactivity timer must be non-zero for LMI to be declared 
         Inactive.
      Note that there is a separate parameter for how the unit processes 
      RTS that is related to this function if options (4), (5), (6), or (7) 
      is selected, see CfgDteRts. "
      ::= { mfrapCfgDteTable 18 }
 
mfrapCfgDteDsrOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
     "Specifies the behavior of this control signal generated by 
      the M-FRAP towards the DTE.
      inactive-always (1) - signal is permanently INACTIVE.
      active-always   (2) - signal is permanently ACTIVE.
      reflect-carrier (3) - signal echoes the carrier signal status 
         from the WAN.
      inactive-with-test-mode (4) - signal is ACTIVE during normal 
         data transfer and INACTIVE during diagnostic conditions 
         that interfere with data transfer from the DTE to the WAN.
      follow-RTS (5) - signal echoes the status of RTS as processed 
         from the DTE. 
      reflect-carrier-and-RTS (6) - signal is a logical AND between 
         RTS processed from the DTE and the carrier signal status 
         from the WAN. No signal from the WAN or RTS INACTIVE 
         will cause this control signal to be asserted INACTIVE.
      reflect-sync-and-RTS (7) - signal is a logical AND between RTS 
         processed from the DTE and the frame synchronization with the WAN. 
         Red Alarm defines the threshold for declaring synchronization.
      reflect-LMI-and-carrier-and-RTS (8) - signal is a logical AND 
         between RTS processed from the DTE and the carrier signal
         status from the WAN and LMI. If the unit is in an LMI 
         passthrough state then LMI is considered Active.
         LMI Inactivity timer must be non-zero for LMI to be declared 
         Inactive.
      Note that there is a separate parameter for how the unit processes 
      RTS that is related to this function if options (4), (5), (6), or (7) 
      is selected, see CfgDteRts. "
     ::= { mfrapCfgDteTable 19 }
 
mfrapCfgDteCtsOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
     "Specifies the behavior of this control signal generated by 
      the M-FRAP towards the DTE.
      inactive-always (1) - signal is permanently INACTIVE.
      active-always   (2) - signal is permanently ACTIVE.
      reflect-carrier (3) - signal echoes the carrier signal status 
         from the WAN.
      inactive-with-test-mode (4) - signal is ACTIVE during normal 
         data transfer and INACTIVE during diagnostic conditions 
         that interfere with data transfer from the DTE to the WAN.
      follow-RTS (5) - signal echoes the status of RTS as processed 
         from the DTE. 
      reflect-carrier-and-RTS (6) - signal is a logical AND between 
         RTS processed from the DTE and the carrier signal status 
         from the WAN. No signal from the WAN or RTS INACTIVE 
         will cause this control signal to be asserted INACTIVE.
      reflect-sync-and-RTS (7) - signal is a logical AND between RTS 
         processed from the DTE and the frame synchronization with the WAN. 
         Red Alarm defines the threshold for declaring synchronization.
      reflect-LMI-and-carrier-and-RTS (8) - signal is a logical AND 
         between RTS processed from the DTE and the carrier signal
         status from the WAN and LMI. If the unit is in an LMI 
         passthrough state then LMI is considered Active.
         LMI Inactivity timer must be non-zero for LMI to be declared 
         Inactive.
      Note that there is a separate parameter for how the unit processes 
      RTS that is related to this function if options (4), (5), (6), or (7) 
      is selected, see CfgDteRts. "
     ::= { mfrapCfgDteTable 20 }

--
--       The FrameRelay Configuration Table
--              This table contains the Configuration for Frame Relay 
--              applications. This includes format, address resolution
--              and parameters associated with the unit's support of 
--              the Link Management Protocol (LMI).

mfrapCfgFrTable OBJECT IDENTIFIER ::= { mfrapConfiguration 5 }

mfrapCfgFrAddrLen  OBJECT-TYPE
          SYNTAX      INTEGER
          {
              twobytes       (1),
              threebytes     (2),
              fourbytes      (3)
          }
          ACCESS      read-write
          STATUS      mandatory
          DESCRIPTION
             "Defines the size of the DLCI address field of the Frame Relay
              header. This setting must correspond to the Frame Relay 
              transmission format; typically Two bytes.
              (1) two byte DLCI address field
              (2) three byte DLCI address field
              (3) four byte DLCI address field"         
          ::= { mfrapCfgFrTable 1 }
 
mfrapCfgFrCrcMode  OBJECT-TYPE
          SYNTAX      INTEGER
          {
              discard        (1),
              passthru       (2)
          }
          ACCESS      read-write
          STATUS      mandatory
          DESCRIPTION
             "This defines the manner in which the unit handles HDLC
              protocol errors (crc errors) in a Frame Relay application. 
              If Discard is selected the unit will respond to an errored 
              frame by aborting the frame if transmission has begun; or 
              simply discarding it if transmission has not begun. If 
              Passthru is selected the unit will transmit the entire frame 
              but will place an incorrect crc in it to preserve the error 
              indication.
              (1) discard
              (2) passthru"
          ::= { mfrapCfgFrTable 2 }

mfrapCfgFrLmiType  OBJECT-TYPE
          SYNTAX      INTEGER
          {
              annexd         (1),
              annexa         (2),
              type1          (3),
              autosense      (4)
          }
          ACCESS      read-write
          STATUS      mandatory
          DESCRIPTION
        "The LMI type used in a Frame Relay application. This setting
         must match the attached Frame Relay device configuration. 
         Annex-A and Annex-D use DLCI 0, and Type 1 uses DLCI 1023.
         Type 1 is alternatively referred to as Cisco, Group of four, 
         or simply LMI. Annex-D may be referred to as ANSI T1.617.
         Annex-A may be referred to as ITU or CCITT Q.933. Auto-sense
         will either use the most recently detected LMI type or, in 
         the absence of any LMI, will attempt to instigate LMI 
         communications using each protocol.     
         (1) Annnex-A: conforms to ITU (CCITT) Q.933 annex A
         (2) Annnex-D: conforms to ANSI T1.617 annex D
         (3) Type 1: conforms to the original LMI as developed by 
             the Group of Four
         (4) Auto-sense: unit will attempt to detect and synchronize
             to the LMI type of the attached equipment."
          ::= { mfrapCfgFrTable 3 }

mfrapCfgFrLmiInactivityTimeout  OBJECT-TYPE
          SYNTAX      INTEGER (0..255)
          ACCESS      read-write
          STATUS      mandatory
          DESCRIPTION
        "Timer used by the unit to determine that an attached device is
         not participating in the LMI protocol and that the unit should 
         attempt to source LMI. This timer also controls the length of 
         time that the LMI sourcing state machine remains in a particular 
         state as it attempts to locate an LMI peer.
         (0) LMI Sourcing disabled
         (2-255) LMI Inactivity timeout"
          ::= { mfrapCfgFrTable 4 }

mfrapCfgFrLmiKeepaliveTimeout  OBJECT-TYPE
          SYNTAX      INTEGER (2..255)
          ACCESS      read-write
          STATUS      mandatory
          DESCRIPTION
        "Timer used by the unit to determine the frequency at which Status
         Enquiries are issued during LMI sourcing states where the unit is 
         emulating a Frame Relay DTE device.
         (2-255) length of time between sending enquiries (in seconds)"
          ::= { mfrapCfgFrTable 5 }


mfrapCfgFrAddrResMode OBJECT-TYPE
         SYNTAX      INTEGER
         {
              inactive (1),
              arp      (2),
              inarp    (3),
              both     (4)
         }
         ACCESS      read-write
         STATUS      mandatory
         DESCRIPTION
            "Enable ARP (2), INARP (3), both (4), or neither (1)."
         ::= { mfrapCfgFrTable 6 }

mfrapCfgFrAddrResDlcis OBJECT-TYPE
         SYNTAX      INTEGER
         {
              single        (1),
              multiple      (2),
              t1multi       (3),
              dtemulti      (4)
         }
         ACCESS      read-write
         STATUS      mandatory
         DESCRIPTION
            "Address Resolution Dlcis determines which dlcis are
             used for address resolution. Multiple DLCI support 
             only applies to piggyback mode; in other management 
             modes, only the configured default dlci is used  
             (1) Support the configured Address Resolution protocol(s)
                 out both ports on the single configured default DLCI 
                 only (CfgFrDLCIValue). 
             (2) Support the configured Address Resolution protocol(s)
                 out both ports on all active DLCIs (per LMI).
             (3) Support the configured Address Resolution protocol(s)
                 out the WAN on all active DLCIs (per LMI) and out the 
                 DTE on only the single default DLCI (CfgFrDLCIValue).
             (4) Support the configured Address Resolution protocol(s)
                 out the DTE on all active DLCIs (per LMI) and out the 
                 WAN on only the single default DLCI (CfgFrDLCIValue)."
         ::= { mfrapCfgFrTable 9 }


mfrapCfgFrAddrResInarpTimer OBJECT-TYPE
         SYNTAX      INTEGER (5..86400)
         ACCESS      read-write
         STATUS      mandatory
         DESCRIPTION
            "The frequency at which the unit issues INARP 
             requests (in seconds) from 5 to 86400 (24 hours)."
         ::= { mfrapCfgFrTable 7 }


mfrapCfgFrLmiFullStatus  OBJECT-TYPE
          SYNTAX      INTEGER (0..3600)
          ACCESS      read-write
          STATUS      mandatory
          DESCRIPTION
        "Timer used by the unit to determine if an LMI Full Status
         Report is missing. In the absence of a Full Status report
         for the duration defined by this timer, the unit will
         declare all DLCI's status INACTIVE and begin logging
         down time. Data passage is not interfered with.
         (0) Full Status Timer is disabled
         (20-3600) Full Status Report Timeout in seconds."
          ::= { mfrapCfgFrTable 8 }



--
--       The VNIP Configuration Table
--              This table contains the Configuration for the VNIP
--              protocol support on the MFRAP T1 DSU.

mfrapCfgVnipTable OBJECT IDENTIFIER ::= { mfrapConfiguration 6 }

   mfrapCfgVnipMode OBJECT-TYPE
         SYNTAX      INTEGER
         {
              inactive (1),
              dte      (2),
              t1      (3),
              both     (4)
         }
         ACCESS      read-write
         STATUS      mandatory
         DESCRIPTION
            "This setting configures the unit for VNIP topology support on
             a per-interface basis. Establishing a VNIP topology is a
             fundamental prerequisite to applying the VNIP feature set which 
             includes PVC-based delay measurement, diagnostics, and congestion
             monitoring. With VNIP enabled on an interface the unit
             will attempt to locate VNIP peers out that port. As peers are 
             discovered and logged the unit will report the topology it has 
             learned on its opposite interface. If VNIP is inactive on one
             interface it will not engage in any VNIP dialog; however it will 
             continue to listen for topology messages on the inactive interface
             and will reflect these messages out the opposite interface if VNIP 
             is enabled. With VNIP inactive on both interfaces the unit will 
             transparently pass all VNIP messages. The topology database includes
             ip addresses, DLCI values, and the number of VNIP hops in between.
             (1) Topology Inactive: VNIP messages pass through unit
             (2) Topology Enabled on DTE only: unit logs VNIP peers seen
                 out the DTE interface. Unit listens for topology reports
                 from the WAN but doesn't generate any towards the WAN. Will 
                 report learned WAN topology towards the DTE.
             (3) Topology Enabled on WAN only: unit logs VNIP peers seen
                 out the WAN interface. Unit listens for topology reports
                 from the DTE but doesn't generate any towards the DTE. Will 
                 report learned DTE topology towards the WAN.
             (4) Topolgy Enabled on Both DTE and WAN: Unit logs VNIP peers
                 seen out both interfaces and generates DTE topolgy reports 
                 towards the WAN and vice versa."
         ::= { mfrapCfgVnipTable 1 }

   mfrapCfgVnipInitTimer OBJECT-TYPE
         SYNTAX      INTEGER (5..86400)
         ACCESS      read-write
         STATUS      mandatory
         DESCRIPTION
            "The frequency of hello messages sent
             during initialization in seconds from
             5 seconds to 86400 seconds (24 hours)."
         ::= { mfrapCfgVnipTable 2 }

   mfrapCfgVnipKeepAliveTimer OBJECT-TYPE
         SYNTAX      INTEGER (5..86400)
         ACCESS      read-write
         STATUS      mandatory
         DESCRIPTION
            "This is the frequency that topology reports are issued out 
             any interface that has VNIP enabled. Once a Hello exchange
             occurs, the unit will periodically issue a VNIP message which 
             reflects the topology it has learned on the opposite interface.
             This Keep Alive timer must be less than any peer unit's Inactivity
             timer.
             (5-86400) VNIP Topology Update frequency (in seconds)"
         ::= { mfrapCfgVnipTable 3 }

   mfrapCfgVnipInactivityTimer OBJECT-TYPE
         SYNTAX      INTEGER (5..86400)
         ACCESS      read-write
         STATUS      mandatory
         DESCRIPTION
            "The length of time to wait before dropping a VNIP
             peer from the database and attempting tp reestablish
             communications by issuing the VNIP Hello message. If
             this timer expires then the entire topology database
             is reset. The Inactivity timers of any unit participating
             in a VNIP topology must be greater than the highest Keep 
             Alive timer in the topology.
             (5- 86400) VNIP Hello frequency (in seconds)"
         ::= { mfrapCfgVnipTable 4 }

   mfrapCfgVnipTransitDelayFrequency OBJECT-TYPE
         SYNTAX      INTEGER (15..86400)
         ACCESS      read-write
         STATUS      mandatory
         DESCRIPTION
            "Transit Delay measurements may be enabled between any DLCI
             peers that have been logged through the topology protocol.
             Delay messages are issued at this frequency and results are
             recorded. Transit delay measures the round-trip network
             delay between two VNIP peers (internal unit latencies are
             not part of the measurement). Traps may be optionally generated 
             if a delay threshold is exceeded.
             (15-86400): Transit Delay message frequency (in seconds)"
         ::= { mfrapCfgVnipTable 5 }


   mfrapCfgTransitDelayTable   OBJECT-TYPE
         SYNTAX   SEQUENCE OF MfrapCfgTransitDelayEntry
         ACCESS   not-accessible
         STATUS   mandatory
         DESCRIPTION
            "The table defining the transit delay measurement profile for
             each of the learned VNIP peers. As peers are located and 
             logged into the topology database, a default transit delay
             profile is assumed. The default is to enable transit delay
             to all hops located out the interface. A DLCI's transit
             delay profile cannot be modified unless the DLCI has been
             discovered through the VNIP topology protocol."
         ::= { mfrapCfgVnipTable 20 }

      mfrapCfgTransitDelayEntry OBJECT-TYPE
          SYNTAX      MfrapCfgTransitDelayEntry
          ACCESS      not-accessible
          STATUS      mandatory
          DESCRIPTION
             "A VNIP Transit Delay configuration entry for a particular 
              DLCI on a particular interface. A DLCI's transit delay 
              profile cannot be modified unless the DLCI has been
              discovered through the VNIP topology protocol"
          INDEX { mfrapCfgTransitDelayInterface, mfrapCfgTransitDelayDlciValue }
          ::= { mfrapCfgTransitDelayTable 1 }

      MfrapCfgTransitDelayEntry ::=
          SEQUENCE
          {
               mfrapCfgTransitDelayInterface         INTEGER,
               mfrapCfgTransitDelayDlciValue         INTEGER,
               mfrapCfgTransitDelayNumHops           INTEGER,
               mfrapCfgTransitDelayRcvSummaryCancel  INTEGER,
               mfrapCfgTransitDelayThreshold         INTEGER
          }

      mfrapCfgTransitDelayInterface OBJECT-TYPE
         SYNTAX      INTEGER
         {
              dte-interface (1),
              t1-interface (2)
         }
         ACCESS      read-write
         STATUS      mandatory
         DESCRIPTION
            "This is the interface being configured for VNIP Transit 
             Delay. If topology is enabled, each interface will contain 
             a database of VNIP peers organized by DLCI value and 
             Number of Hops.
             (1) DTE Interface
             (2) DDS Interface"
         ::= { mfrapCfgTransitDelayEntry 1 }

      mfrapCfgTransitDelayDlciValue    OBJECT-TYPE
          SYNTAX      INTEGER 
          ACCESS      read-write
          STATUS      mandatory
          DESCRIPTION
             "This is the DLCI being configured for VNIP Transit 
              Delay. If topology is enabled, each interface will contain 
              a database of VNIP peers organized by DLCI value and 
              Number of Hops."
          ::= { mfrapCfgTransitDelayEntry 2 }

      mfrapCfgTransitDelayNumHops    OBJECT-TYPE
          SYNTAX      INTEGER (0..255)
          ACCESS      read-write
          STATUS      mandatory
          DESCRIPTION
             "VNIP topolgy may include multiple units on a given
              DLCI/interface. The topology logs the number of 
              intermediate VNIP peers between units (Hops). This 
              setting determines which peers on a DLCI are participating
              in delay measurements.
              (0) All hops
              (1-254) individually addressable delay measurement
                  between any two peers.
              (255) Furthest hop only"
          ::= { mfrapCfgTransitDelayEntry 4 }

      mfrapCfgTransitDelayRcvSummaryCancel    OBJECT-TYPE
          SYNTAX      INTEGER 
          {
               enable-rsc  (1),
               disable-rsc (2)
          }
          ACCESS      read-write
          STATUS      mandatory
          DESCRIPTION
             "Controls the Receive Summary Cancellation feature of VNIP 
              Transit Delay on this interface/DLCI. Every Transit Delay
              measurement exchange includes a follow-up message from the 
              initiator with the delay results. If RSC is enabled, a unit
              will log results based upon this summary message and will 
              not issue its next scheduled delay measurement. With RSC 
              disabled, the unit will not use the summary message and 
              will always issue its regularly scheduled message based on
              the delay frequency timer. The purpose of this feature is to
              reduce traffic introduced by VNIP. In a typical peer-to-peer
              transit delay measurement where both ends are concurrently
              conducting transit delay measurements it's recommended that 
              one end have RSC enabled and one end disabled."
          ::= { mfrapCfgTransitDelayEntry 5 }

      mfrapCfgTransitDelayThreshold    OBJECT-TYPE
          SYNTAX      INTEGER (0..86400000)
          ACCESS      read-write
          STATUS      mandatory
          DESCRIPTION
             "Specifies a transit delay threshold for this DLCI/interface.
              When the transit delay exceeds the threshold, a TRAP is sent. 
              The threshold may be set from one millisecond to 24 hours.
              A value of 0 will prevent a TRAP from being sent.
              (0): Transit delay threshold trap disabled for this DLCI/interface
              (1-86400000): delay threshhold. Any delay measurements exceeding
                  this result will generate a trap."
          ::= { mfrapCfgTransitDelayEntry 6 }


   mfrapCfgTDDeleteTable   OBJECT-TYPE
         SYNTAX   SEQUENCE OF MfrapCfgTDDeleteEntry
         ACCESS   not-accessible
         STATUS   mandatory
         DESCRIPTION
            "The table allows the user to disable transit delay 
             measurements for a specific DLCI on a particular 
             interface."
         ::= { mfrapCfgVnipTable 21 }

      mfrapCfgTDDeleteEntry OBJECT-TYPE
          SYNTAX      MfrapCfgTDDeleteEntry
          ACCESS      not-accessible
          STATUS      mandatory
          DESCRIPTION
             "Disables VNIP Transit Delay for a particular 
              interface and DLCI." 
          INDEX { mfrapCfgTDDeleteInterface }
          ::= { mfrapCfgTDDeleteTable 1 }

      MfrapCfgTDDeleteEntry ::=
          SEQUENCE
          {
               mfrapCfgTDDeleteInterface    INTEGER,
               mfrapCfgTDDeleteDlciValue    INTEGER
          }

      mfrapCfgTDDeleteInterface OBJECT-TYPE
         SYNTAX      INTEGER
         {
              dte-interface (1),
              t1-interface (2)
         }
         ACCESS      not-accessible
         STATUS      mandatory
         DESCRIPTION
            "Transit delay can be disabled for a given DLCI on
             either interface. This indexes the interface. 
             Setting this index and the associated DLCI index
             will disable transit delay on that combination."
         ::= { mfrapCfgTDDeleteEntry 1 }

      mfrapCfgTDDeleteDlciValue    OBJECT-TYPE
         SYNTAX      INTEGER 
         ACCESS      write-only
         STATUS      mandatory
         DESCRIPTION
            "Transit delay can be disabled for a given DLCI on
             either interface. This indexes the DLCI. Setting 
             this index and the associated interface index will
             disable transit delay on that combination."
          ::= { mfrapCfgTDDeleteEntry 2 }


   mfrapCfgTransitDelayTableClear  OBJECT-TYPE
         SYNTAX      INTEGER
         {
               clear-table   (1)
         }
         ACCESS      write-only
         STATUS      mandatory
         DESCRIPTION
              " The mfrapCfgTransitDelayTable is cleared.
                (1) clear the table "
         ::= { mfrapCfgVnipTable 22 }




--       The Frame Relay Performance Configuration
--              A group of configuration tables supporting frame relay
--              performance measurement on the MFRAP T1 CSU.

mfrapCfgFrPerf OBJECT IDENTIFIER ::= { mfrapConfiguration 7 }

  mfrapCfgFrPerfDlciNamesTable   OBJECT-TYPE
          SYNTAX      SEQUENCE OF MfrapCfgFrPerfDlciNamesEntry
          ACCESS      not-accessible
          STATUS      mandatory
          DESCRIPTION
             "This table allows the user to configure DLCI
              specific parameters such as Names, CIR, and EIR. 
              Additionally, any DLCIs configured with these
              parameters will be added into the Short Term 
              statistics database next time its cleared."
          ::= { mfrapCfgFrPerf 1 }

      mfrapCfgFrPerfDlciNamesEntry OBJECT-TYPE
          SYNTAX      MfrapCfgFrPerfDlciNamesEntry
          ACCESS      not-accessible
          STATUS      mandatory
          DESCRIPTION
             "A table entry indexed by DLCI, containing
              a DLCI, a DLCI name, a CIR, and how the
              CIR value was obtained." 
          INDEX { mfrapCfgFrPerfDlciNamesDlciValue }
          ::= { mfrapCfgFrPerfDlciNamesTable 1 }

      MfrapCfgFrPerfDlciNamesEntry ::=
          SEQUENCE
          {
             mfrapCfgFrPerfDlciNamesDlciValue   INTEGER,
             mfrapCfgFrPerfDlciNamesDlciName    DisplayString (SIZE (0..15)),
             mfrapCfgFrPerfDlciNamesCirValue    INTEGER,
             mfrapCfgFrPerfDlciNamesCirType     INTEGER,
             mfrapCfgFrPerfDlciNamesUtilThreshold INTEGER,
             mfrapCfgFrPerfDlciNamesEirValue    INTEGER
          } 

      mfrapCfgFrPerfDlciNamesDlciValue    OBJECT-TYPE
          SYNTAX      INTEGER 
          ACCESS      read-write
          STATUS      mandatory
          DESCRIPTION
             "A DLCI selected for customized configuration and to 
              be added to short term statistics collection (if it
              wasn't already there)."
          ::= { mfrapCfgFrPerfDlciNamesEntry 1 }

      mfrapCfgFrPerfDlciNamesDlciName   OBJECT-TYPE
          SYNTAX      DisplayString (SIZE (0..15))
          ACCESS      read-write
          STATUS      mandatory
          DESCRIPTION
             "A user-specifiable name for an individual DLCI."
          ::= { mfrapCfgFrPerfDlciNamesEntry 2 }

      mfrapCfgFrPerfDlciNamesCirValue    OBJECT-TYPE
          SYNTAX      INTEGER 
          ACCESS      read-write
          STATUS      mandatory
          DESCRIPTION
             "The CIR value for an individual DLCI. This
              value is used in the calculation utilization
              as a percentage of CIR. If the CIR is reported 
              in the LMI message then the reported value will
              override this configured entry. In the absence
              of LMI CIR and a configured CIR, the unit will
              assume that the CIR is the DTE Line Rate."
          ::= { mfrapCfgFrPerfDlciNamesEntry 3 }

      mfrapCfgFrPerfDlciNamesCirType    OBJECT-TYPE
          SYNTAX      INTEGER 
          {
               cir-acquired-from-lmi  (1),
               cir-configured-by-user (2),
               cir-is-datarate        (3)
          }
          ACCESS      read-only
          STATUS      mandatory
          DESCRIPTION
             "The source of the CIR value for this DLCI.
              If CIR for a DLCI is part of the LMI message
              then this LMI supplied CIR will override any 
              defined CIR. If CIR is not part of LMI and
              has not been explicitly defined by the user
              it will default to the DTE Line Rate.
              (1) CIR reported in LMI Full Status message
              (2) CIR configured by user
              (3) CIR defaulted to DTE Line Rate"
          ::= { mfrapCfgFrPerfDlciNamesEntry 4 }

   mfrapCfgFrPerfDlciNamesUtilThreshold  OBJECT-TYPE
          SYNTAX      INTEGER  (0..100) 
          ACCESS      read-write
          STATUS      mandatory
          DESCRIPTION
             "The threshold for generating a utilization 
              threshold trap as a percentage of the CIR.  
              If the utilization percentage is above this 
              threshold for more than 
              mfrapCfgFrPerfDlciUtilThreshold number of
              mfrapCfgFrPerfTimersSTInterval's a
              mfrapPvc(Rx/Tx)UtilizationExceeded trap
              will be issued.  If the If the utilization 
              percentage falls below this threshold for 
              more than mfrapCfgFrPerfDlciUtilThreshold 
              number of mfrapCfgFrPerfTimersSTInterval's a
              mfrapPvc(Rx/Tx)UtilizationExceeded trap
              will be issued."
          ::= { mfrapCfgFrPerfDlciNamesEntry 5}

      mfrapCfgFrPerfDlciNamesEirValue    OBJECT-TYPE
          SYNTAX      INTEGER 
          ACCESS      read-write
          STATUS      mandatory
          DESCRIPTION
             "The EIR value for an individual DLCI. In the 
              absence of a configured EIR, the unit will
              assume that the EIR is the DTE Line Rate."
          ::= { mfrapCfgFrPerfDlciNamesEntry 6 }

         
   mfrapCfgFrPerfDlciNamesDelete   OBJECT-TYPE
          SYNTAX      INTEGER 
          ACCESS      write-only
          STATUS      mandatory
          DESCRIPTION
             "Setting this object with a specific DLCI value
              will remove the DLCI from the DLCI-specific
              parameters database."
          ::= { mfrapCfgFrPerf 2 }

  mfrapCfgFrPerfTimers OBJECT IDENTIFIER ::= { mfrapCfgFrPerf 3 }

      mfrapCfgFrPerfTimersSTInterval   OBJECT-TYPE
          SYNTAX      INTEGER (3..60)
          ACCESS      read-write
          STATUS      mandatory
          DESCRIPTION
             "Short term statistics maintain cumulative counts, and
              counts for the current and previous short term windows.
              This value is the  window size for the short term statistics
              intervals.
              (3-60): short term statistics collection interval"
          ::= { mfrapCfgFrPerfTimers 1 }

      mfrapCfgFrPerfTimersLTInterval   OBJECT-TYPE
          SYNTAX      INTEGER (4..3600)
          ACCESS      read-write
          STATUS      mandatory
          DESCRIPTION
             "Long term statistics maintain 96 contiguous intervals
              of configurable protocol per DLCI statistics. This value
              is the window size of each interval. Adjusting this value
              will change the overall length of time that the 96 intervals
              will span.
             (4-3600): long term statsistics collection interval"
          ::= { mfrapCfgFrPerfTimers 2 }

   mfrapCfgFrPerfUserProtocolsTable   OBJECT-TYPE
          SYNTAX      SEQUENCE OF MfrapCfgFrPerfUserProtocolsEntry
          ACCESS      not-accessible
          STATUS      mandatory
          DESCRIPTION
             "This table allows the user to select TCP/UDP ports 
              for statistics collection.  Tx and Rx byte counts
              will collected on the specified ports.  These ports
              are selectable as protocols in the long term
              statistics filter and are displayed with the other
              protocols in the short term statistics."
          ::= { mfrapCfgFrPerf 4 }

      mfrapCfgFrPerfUserProtocolsEntry OBJECT-TYPE
          SYNTAX      MfrapCfgFrPerfUserProtocolsEntry
          ACCESS      not-accessible
          STATUS      mandatory
          DESCRIPTION
             "An index and TCP/UDP port number pair." 
          INDEX { mfrapCfgFrPerfUserProtocolsIndex }
          ::= { mfrapCfgFrPerfUserProtocolsTable 1 }

      MfrapCfgFrPerfUserProtocolsEntry ::=
          SEQUENCE
          {
               mfrapCfgFrPerfUserProtocolsIndex     INTEGER,
               mfrapCfgFrPerfUserProtocolsPortNum   INTEGER
          } 

      mfrapCfgFrPerfUserProtocolsIndex    OBJECT-TYPE
          SYNTAX      INTEGER 
          ACCESS      read-only
          STATUS      mandatory
          DESCRIPTION
             "An index. Beginning with index 1, the range is defined 
              in SysNumUserProtocols"
          ::= { mfrapCfgFrPerfUserProtocolsEntry 1 }

      mfrapCfgFrPerfUserProtocolsPortNum   OBJECT-TYPE
          SYNTAX      INTEGER
          ACCESS      read-write
          STATUS      mandatory
          DESCRIPTION
            "Tx and Rx byte counts will be collected on
             the user-specifiable TCP/UDP port number.
             (0) port not defined
             (1-65535): IP TCP/UDP protocol port number."
          ::= { mfrapCfgFrPerfUserProtocolsEntry 2 }

   mfrapCfgFrPerfLTDlciFilterTable       OBJECT-TYPE
          SYNTAX      SEQUENCE OF MfrapCfgFrPerfLTDlciFilterEntry
          ACCESS      not-accessible
          STATUS      mandatory
          DESCRIPTION
             "Long term statistics can only be collected
              on a limited number of DLCIs. The value of
              SysLTFNumDlcis defines the maximum number of
              DLCIs that can be included in the Long Term
              Statistics. Once one or more DLCIs are added
              to Long Term Stats, the user may assign a 
              set of protocols that will be monitored across
              all of the Long Term DLCIs."
          ::= { mfrapCfgFrPerf 5 }

      mfrapCfgFrPerfLTDlciFilterEntry OBJECT-TYPE
          SYNTAX      MfrapCfgFrPerfLTDlciFilterEntry
          ACCESS      not-accessible
          STATUS      mandatory
          DESCRIPTION
             "An index and DLCI number pair." 
          INDEX { mfrapCfgFrPerfLTDlciFilterIndex }
          ::= { mfrapCfgFrPerfLTDlciFilterTable 1 }

      MfrapCfgFrPerfLTDlciFilterEntry ::=
          SEQUENCE
          {
               mfrapCfgFrPerfLTDlciFilterIndex     INTEGER,
               mfrapCfgFrPerfLTDlciFilterDlciNum   INTEGER
          } 

      mfrapCfgFrPerfLTDlciFilterIndex    OBJECT-TYPE
          SYNTAX      INTEGER 
          ACCESS      read-only
          STATUS      mandatory
          DESCRIPTION
             "An index. Beginning with index 1, the maximum is 
              defined by the value of SysLTFNumDlcis."
          ::= { mfrapCfgFrPerfLTDlciFilterEntry 1 }

      mfrapCfgFrPerfLTDlciFilterDlciNum   OBJECT-TYPE
          SYNTAX      INTEGER
          ACCESS      read-write
          STATUS      mandatory
          DESCRIPTION
             "Setting a DLCI value here will add that DLCI into
              the Long term statistics database (associated with 
              its index) and it will be monitored for the protocol 
              activity defined in the Long Term Protocol filter."
          ::= { mfrapCfgFrPerfLTDlciFilterEntry 2 }


   mfrapCfgFrPerfLTProtocolFilterTable   OBJECT-TYPE
          SYNTAX      SEQUENCE OF MfrapCfgFrPerfLTProtocolFilterEntry
          ACCESS      not-accessible
          STATUS      mandatory
          DESCRIPTION
             "Long term statistics can only be collected
              on a limited number of protocols. The maximum
              number of Long Term Protoocls are defined by 
              SysLTFNumProtocols. This table allows the user to 
              configure those protocols."
          ::= { mfrapCfgFrPerf 6 }

      mfrapCfgFrPerfLTProtocolFilterEntry OBJECT-TYPE
          SYNTAX      MfrapCfgFrPerfLTProtocolFilterEntry
          ACCESS      not-accessible
          STATUS      mandatory
          DESCRIPTION
             "An index and protocol pair." 
          INDEX { mfrapCfgFrPerfLTProtocolFilterIndex }
          ::= { mfrapCfgFrPerfLTProtocolFilterTable 1 }

      MfrapCfgFrPerfLTProtocolFilterEntry ::=
          SEQUENCE
          {
               mfrapCfgFrPerfLTProtocolFilterIndex      INTEGER,
               mfrapCfgFrPerfLTProtocolFilterProtocol   INTEGER
          } 

      mfrapCfgFrPerfLTProtocolFilterIndex    OBJECT-TYPE
          SYNTAX      INTEGER 
          ACCESS      read-only
          STATUS      mandatory
          DESCRIPTION
             "An index. Beginning with index 1, the maximum is 
              defined by the value of SysLTFNumProtocols."
          ::= { mfrapCfgFrPerfLTProtocolFilterEntry 1 }

      mfrapCfgFrPerfLTProtocolFilterProtocol   OBJECT-TYPE
          SYNTAX      INTEGER
          {
            ip-tx-bc                    (1),
            ip-rx-bc                    (2),
            tcp-ip-tx-bc                (3),
            tcp-ip-rx-bc                (4),
            ftp-tcp-ip-tx-bc            (5),
            ftp-tcp-ip-rx-bc            (6),
            telnet-tcp-ip-tx-bc         (7),
            telnet-tcp-ip-rx-bc         (8),
            smtp-tcp-ip-tx-bc           (9),
            smtp-tcp-ip-rx-bc           (10),
--          tftp-tcp-ip-tx-bc           (11),
--          tftp-tcp-ip-rx-bc           (12),
            http-tcp-ip-tx-bc           (13),
            http-tcp-ip-rx-bc           (14),
            netbios-ssn-tcp-ip-tx-bc    (15),
            netbios-ssn-tcp-ip-rx-bc    (16),
--          snmp-tcp-ip-tx-bc           (17),
--          snmp-tcp-ip-rx-bc           (18),
--          snmptrap-tcp-ip-tx-bc       (19),
--          snmptrap-tcp-ip-rx-bc       (20),
            udp-ip-tx-bc                (21),
            udp-ip-rx-bc                (22),
--          ftp-udp-ip-tx-bc            (23),
--          ftp-udp-ip-rx-bc            (24),
--          telnet-udp-ip-tx-bc         (25),
--          telnet-udp-ip-rx-bc         (26),
--          smtp-udp-ip-tx-bc           (27),
--          smtp-udp-ip-rx-bc           (28),
            tftp-udp-ip-tx-bc           (29),
            tftp-udp-ip-rx-bc           (30),
--          http-udp-ip-tx-bc           (31),
--          http-udp-ip-rx-bc           (32),
            netbios-dgm-udp-ip-tx-bc    (33),
            netbios-dgm-udp-ip-rx-bc    (34),
            snmp-udp-ip-tx-bc           (35),
            snmp-udp-ip-rx-bc           (36),
            snmptrap-udp-ip-tx-bc       (37),
            snmptrap-udp-ip-rx-bc       (38),
            rip-udp-ip-tx-bc            (39),
            rip-udp-ip-rx-bc            (40),
            icmp-ip-tx-bc               (41),
            icmp-ip-rx-bc               (42),
            echorep-icmp-ip-tx-bc       (43),
            echorep-icmp-ip-rx-bc       (44),
            dest-unr-icmp-ip-tx-bc      (45),
            dest-unr-icmp-ip-rx-bc      (46),
            src-quench-icmp-ip-tx-bc    (47),
            src-quench-icmp-ip-rx-bc    (48),
            redirect-icmp-ip-tx-bc      (49),
            redirect-icmp-ip-rx-bc      (50),
            echoreq-icmp-ip-tx-bc       (51),
            echoreq-icmp-ip-rx-bc       (52),
            time-excd-icmp-ip-tx-bc     (53),
            time-excd-icmp-ip-rx-bc     (54),
            param-prob-icmp-ip-tx-bc    (55),
            param-prob-icmp-ip-rx-bc    (56),
            timestamp-req-icmp-ip-tx-bc (57),
            timestamp-req-icmp-ip-rx-bc (58),
            timestamp-rep-icmp-ip-tx-bc (59),
            timestamp-rep-icmp-ip-rx-bc (60),
            addr-mask-req-icmp-ip-tx-bc (61),
            addr-mask-req-icmp-ip-rx-bc (62),
            addr-mask-rep-icmp-ip-tx-bc (63),
            addr-mask-rep-icmp-ip-rx-bc (64),
            pkt-too-big-icmp-ip-tx-bc   (65),
            pkt-too-big-icmp-ip-rx-bc   (66),
            gp-mem-query-icmp-ip-tx-bc  (67),
            gp-mem-query-icmp-ip-rx-bc  (68),
            gp-mem-report-icmp-ip-tx-bc (69),
            gp-mem-report-icmp-ip-rx-bc (70),
            gp-mem-reduct-icmp-ip-tx-bc (71),
            gp-mem-reduct-icmp-ip-rx-bc (72),
            ospf-ip-tx-bc               (73),
            ospf-ip-rx-bc               (74),
            other-ip-tx-bc              (75),
            other-ip-rx-bc              (76),
            ipx-tx-bc                   (77),
            ipx-rx-bc                   (78),
            spx-ipx-tx-bc               (79),
            spx-ipx-rx-bc               (80),
            ncp-ipx-tx-bc               (81),
            ncp-ipx-rx-bc               (82),
            sap-ipx-tx-bc               (83),
            sap-ipx-rx-bc               (84),
            rip-ipx-tx-bc               (85),
            rip-ipx-rx-bc               (86),
            netbios-ipx-tx-bc           (87),
            netbios-ipx-rx-bc           (88),
            other-ipx-tx-bc             (89),
            other-ipx-rx-bc             (90),
            arp-tx-bc                   (91),
            arp-rx-bc                   (92),
            arp-req-tx-bc               (93),
            arp-req-rx-bc               (94),
            arp-rep-tx-bc               (95),
            arp-rep-rx-bc               (96),
            rarp-req-tx-bc              (97),
            rarp-req-rx-bc              (98),
            rarp-rep-tx-bc              (99),
            rarp-rep-rx-bc              (100),
            inarp-req-tx-bc             (101),
            inarp-req-rx-bc             (102),
            inarp-rep-tx-bc             (103),
            inarp-rep-rx-bc             (104),
            sna-tx-bc                   (105),
            sna-rx-bc                   (106),
            sna-subarea-tx-bc           (107),
            sna-subarea-rx-bc           (108),
            sna-periph-tx-bc            (109),
            sna-periph-rx-bc            (110),
            sna-appn-tx-bc              (111),
            sna-appn-rx-bc              (112),
            sna-netbios-tx-bc           (113),
            sna-netbios-rx-bc           (114),
            cisco-tx-bc                 (115),
            cisco-rx-bc                 (116),
            other-tx-bc                 (117),
            other-rx-bc                 (118),
            user-defined-1-tx-bc        (119),
            user-defined-1-rx-bc        (120),
            user-defined-2-tx-bc        (121),
            user-defined-2-rx-bc        (122),
            user-defined-3-tx-bc        (123),
            user-defined-3-rx-bc        (124),
            user-defined-4-tx-bc        (125),
            user-defined-4-rx-bc        (126),
            thru-byte-tx-bc             (127),
            thru-byte-rx-bc             (128),
            thru-frame-tx-bc            (129),
            thru-frame-rx-bc            (130),
            thru-fecn-tx-bc             (131),
            thru-fecn-rx-bc             (132),
            thru-becn-tx-bc             (133),
            thru-becn-rx-bc             (134),
            thru-de-tx-bc               (135),
            thru-de-rx-bc               (136),
            cir-percent-range1-tx-bc    (137),
            cir-percent-range1-rx-bc    (138),
            cir-percent-range2-tx-bc    (139),
            cir-percent-range2-rx-bc    (140),
            cir-percent-range3-tx-bc    (141),
            cir-percent-range3-rx-bc    (142),
            cir-percent-range4-tx-bc    (143),
            cir-percent-range4-rx-bc    (144),
            cir-percent-range5-tx-bc    (145),
            cir-percent-range5-rx-bc    (146),
            cir-percent-range6-tx-bc    (147),
            cir-percent-range6-rx-bc    (148),
            cir-percent-range7-tx-bc    (149),
            cir-percent-range7-rx-bc    (150),
            cir-percent-range8-tx-bc    (151),
            cir-percent-range8-rx-bc    (152),
            lmi-tx-bc                   (153),
            lmi-rx-bc                   (154),
            lmi-livo-enq-tx-bc          (155),
            lmi-livo-enq-rx-bc          (156),
            lmi-livo-stat-tx-bc         (157),
            lmi-livo-stat-rx-bc         (158),
            lmi-full-enq-tx-bc          (159),
            lmi-full-enq-rx-bc          (160),
            lmi-full-stat-tx-bc         (161),
            lmi-full-stat-rx-bc         (162),
            lmi-other-tx-bc             (163),
            lmi-other-rx-bc             (164),
            total-uptime                (165),
            total-downtime              (166),
            igrp-tx-bc                  (167),
            igrp-rx-bc                  (168),
            vnip-tx-bc                  (169),
            vnip-rx-bc                  (170),
            annex-g-tx-bc               (171),
            annex-g-rx-bc               (172),

            delete-entry                (-1)
          }
          ACCESS      read-write
          STATUS      mandatory
          DESCRIPTION
             "Long term statistics will be collected on
              the user-specifiable protocol. Setting a -1 
              remove the indexed protocol from the filter."
          ::= { mfrapCfgFrPerfLTProtocolFilterEntry 2 }

  mfrapCfgFrPerfDlciDefaultUtilThreshold  OBJECT-TYPE
          SYNTAX      INTEGER  (0..100) 
          ACCESS      read-write
          STATUS      mandatory
          DESCRIPTION
             "The default threshold for generating a 
              utilization threshold trap as a percentage 
              of the CIR. This value is used for 
              mfrapCfgFrPerfDlciNamesUtilThreshold when
              a DLCI is first discovered. "
          ::= { mfrapCfgFrPerf 7 }

   mfrapCfgFrPerfDlciUtilDuration  OBJECT-TYPE
          SYNTAX      INTEGER (0..65535) 
          ACCESS      read-write
          STATUS      mandatory
          DESCRIPTION
             "The number of Short Term Intervals that a
              DLCI's utilization as a percentage of CIR
              must be above or below the value of
           mfrapCfgFrPerfDlciUtilThreshold before a
              mfrapPvc(Rx/Tx)UtilizationExceededTrap or
              mfrapPvc(Rx/Tx)UtilizationClearedTrap is
              issued. "
          ::= { mfrapCfgFrPerf 8 }

  mfrapCfgFrPerfDlciNamesTableClear  OBJECT-TYPE
         SYNTAX       INTEGER
         {            
            clear-table                (1),
            clear-table-keep-stats     (2)
         }
          ACCESS      write-only
          STATUS      mandatory
          DESCRIPTION
             "Clears the smperCfgFrPerfDlciNamesTable
              (1) clear the table or (2) clear the table
              but don't remove the dlcis from the short
              term statistics."
          ::= { mfrapCfgFrPerf 9 }
         
  mfrapCfgFrPerfUserProtocolsTableClear  OBJECT-TYPE
         SYNTAX       INTEGER
         {            
            clear-table     (1)
         }
          ACCESS      write-only
          STATUS      mandatory
          DESCRIPTION
             " Clears the mfrapCfgFrPerfUserProtocolsTable
               (1) clear the table "
          ::= { mfrapCfgFrPerf 10 }
         
  mfrapCfgFrPerfLTDlciFilterTableClear  OBJECT-TYPE
         SYNTAX       INTEGER
         {            
            clear-table     (1)
         }
          ACCESS      write-only
          STATUS      mandatory
          DESCRIPTION
             " Clears the mfrapCfgFrPerfLTDlciFilterTable
               (1) clear the table "
          ::= { mfrapCfgFrPerf 11 }
         
  mfrapCfgFrPerfLTProtocolFilterTableClear  OBJECT-TYPE
         SYNTAX       INTEGER
         {            
            clear-table     (1)
         }
          ACCESS      write-only
          STATUS      mandatory
          DESCRIPTION
             " Clears the mfrapCfgFrPerfLTProtocolFilterTable
               (1) clear the table "
          ::= { mfrapCfgFrPerf 12 }
         
  mfrapCfgFrPerfUnprovDlcisDelete  OBJECT-TYPE
         SYNTAX       INTEGER
         {            
            delete-unprov     (1)
         }
          ACCESS      write-only
          STATUS      mandatory
          DESCRIPTION
             "Delete all unprovisioned and Not-In-LMI dlcis
              (1) delete all unprovisioned "
          ::= { mfrapCfgFrPerf 13 }
         

  
  mfrapCfgSecurityTable OBJECT IDENTIFIER ::= { mfrapConfiguration 8 }

      mfrapCfgTelnetCliLcdPassword   OBJECT-TYPE
          SYNTAX      DisplayString (SIZE (0..8))
          ACCESS      read-write
          STATUS      mandatory
          DESCRIPTION
             "The password needed to start a
              CLI (Command Line Interface),
              Telnet or LCD session."
          ::= { mfrapCfgSecurityTable 1 }

      mfrapCfgTftpPassword   OBJECT-TYPE
          SYNTAX      DisplayString (SIZE (0..8))
          ACCESS      read-write
          STATUS      mandatory
          DESCRIPTION
             "The password needed to initiate a TFTP download."
          ::= { mfrapCfgSecurityTable 2 }

      mfrapCfgCliPassword   OBJECT-TYPE
          SYNTAX      DisplayString (SIZE (0..8))
          ACCESS      read-write
          STATUS      mandatory
          DESCRIPTION
             "OBSOLETE: The Telnet, CLI and LCD passwords
              are one and the same.  Use the above
              mfrapCfgTelnetCliLcdPassword to log into
              the CLI (Command Line Interface)."
          ::= { mfrapCfgSecurityTable 3 }

      mfrapCfgLcdPassword   OBJECT-TYPE
          SYNTAX      DisplayString (SIZE (0..8))
          ACCESS      read-write
          STATUS      mandatory
          DESCRIPTION
             "OBSOLETE: The Telnet, CLI and LCD passwords
              are one and the same.  Use the above
              mfrapCfgTelnetCliLcdPassword to log into
              the LCD Interface."
          ::= { mfrapCfgSecurityTable 4 }

      mfrapCfgGetCommunityString   OBJECT-TYPE
          SYNTAX      DisplayString (SIZE (0..15))
          ACCESS      read-write
          STATUS      mandatory
          DESCRIPTION
             "The community string for doing SNMP GETs. The unit
              will respond to GETs that use either this string or
              the SET community string. All others will be rejected
              and a trap will be generated. String is case sensitive."
          ::= { mfrapCfgSecurityTable 5 }

      mfrapCfgSetCommunityString   OBJECT-TYPE
          SYNTAX      DisplayString (SIZE (0..15))
          ACCESS      read-write
          STATUS      mandatory
          DESCRIPTION
             "The community string for doing SNMP SETs. The unit 
              will reject SETs with any other coimmunity string
              and will generate a trap. String is case sensitive."
          ::= { mfrapCfgSecurityTable 6 }

      mfrapCfgLcdPswdEnable   OBJECT-TYPE
          SYNTAX      INTEGER 
          {
               enable-lcd-pswd  (1),
               disable-lcd-pswd (2)
          }
          ACCESS      read-write
          STATUS      mandatory
          DESCRIPTION
             "This selection controls whether a password is
              necessary to use the LCD interface."
          ::= { mfrapCfgSecurityTable 7 }

      mfrapCfgLcdPswdTimeout   OBJECT-TYPE
          SYNTAX      INTEGER 
          ACCESS      read-write
          STATUS      mandatory
          DESCRIPTION
             "OBSOLETE."
          ::= { mfrapCfgSecurityTable 8 }

--
--       The Connection Configuration Table
--         The Connection Configuration table contains methods for
--         assigning T1 network bandwidth to ports. In auto entry mode
--         the user provides a starting DS0 and the node assigns
--         sequential, contiguous, DS0s; all of the same type.
--         In manual entry the user configures each DS0 
--         separately. In manual mode the DS0s may be assigned 
--         discontinuously and could be a mix of voice, 
--         transparent or frame relay circuits. 
--
--         DTE connection configuration uses the auto entry mode.
--         The objects controlling this configuration can be found
--         in the DTE Configuration Table (mfrapCfgDteTable).  When 
--         a valid set of DTE connection parameters exist (the current 
--         values are used for parameters not set), the 
--         mfrapCfgEditConnTable must FIRST be updated using the 
--         mfrapCfgDteConnAutoUpdate object.  Thus to effect a change
--         in DTE connections, sets of BOTH mfrapCfgDteConnAutoUpdate
--         AND mfrapCfgConnUpdateCmd must be done. 
--
--         Drop & Insert connection configuration uses the manual
--         entry mode by directly writing to the mfrapCfgEditConnTable 
--         below.  If a legal set value leads to an invalid configuration,
--         the mfrapCfgConnStatus object will return an incorrect-bandwidth 
--         or bandwidth-conflict indication. 
--
--         In order to delete a connection, the mfrapCfgEditMode object
--         is set to not-connected.  The states of the other 
--         mfrapCfgEditTable objects will be updated automatically.
--
--         When the mfrapCfgConnUpdateCmd is set and the configuration is
--         valid, the connections will be updated and reads of the 
--         mfrapCfgCurrentConnTable will reflect the updated connections.

mfrapCfgConnectionTable OBJECT IDENTIFIER ::= { mfrapConfiguration 10 }

mfrapCfgCurrentConnTable OBJECT-TYPE
     SYNTAX       SEQUENCE OF MfrapCfgCurrentConnEntry
     ACCESS       not-accessible
     STATUS       mandatory
     DESCRIPTION
        "Retrieves node's active connections assignments for 
         display only. To edit connections, use the mfrapCfgDteTable
         and/or mfrapCfgEditConnTable."
     ::= { mfrapCfgConnectionTable 1 }

mfrapCfgCurrentConnEntry OBJECT-TYPE
     SYNTAX  MfrapCfgCurrentConnEntry
     ACCESS  not-accessible
     STATUS      mandatory
     DESCRIPTION
      "An entry in the Current Connections Table."
     INDEX { mfrapCfgCurrentConnDestPort, mfrapCfgCurrentConnDestDs0 }
     ::= { mfrapCfgCurrentConnTable 1 }

MfrapCfgCurrentConnEntry ::=
     SEQUENCE 
     {
        mfrapCfgCurrentConnDestPort       INTEGER,
        mfrapCfgCurrentConnDestDs0        INTEGER,
        mfrapCfgCurrentConnSrcPort        INTEGER,
        mfrapCfgCurrentConnSrcDs0         INTEGER,
        mfrapCfgCurrentConnType           INTEGER
     }

mfrapCfgCurrentConnDestPort  OBJECT-TYPE
     SYNTAX  INTEGER 
     {
         port1-t1      (1)
--       port2-dani    (2)
     }
     ACCESS      read-only
     STATUS      mandatory
     DESCRIPTION
      "Index to Destination port of interest. M-FRAP
       currently only supports the Network port (1) as the
       destination"
     ::= { mfrapCfgCurrentConnEntry 1 }

mfrapCfgCurrentConnDestDs0       OBJECT-TYPE
     SYNTAX        INTEGER (1..24)
     ACCESS        read-only
     STATUS        mandatory
     DESCRIPTION
        "DS0 number 1 through 24 corresponding to the destination
         port index "
     ::= { mfrapCfgCurrentConnEntry 2 }

mfrapCfgCurrentConnSrcPort   OBJECT-TYPE
     SYNTAX        INTEGER
     {
--       port1-t1      (1),
         port2-dandi   (2),
         port3-dte     (3),
         not-connected (33)
     }
     ACCESS        read-only
     STATUS        mandatory
     DESCRIPTION
      "DS0 assignment for Destination port. After 
      making any adjustments to the connections, the 
      mfrapCfgConnUpdateCmd must be sent. Node software 
      does not permit a port connection to itself."
     ::= { mfrapCfgCurrentConnEntry 3 }


mfrapCfgCurrentConnSrcDs0       OBJECT-TYPE
     SYNTAX        INTEGER
     {
         ds0-01        (1),
         ds0-02        (2),
         ds0-03        (3),
         ds0-04        (4),
         ds0-05        (5),
         ds0-06        (6),
         ds0-07        (7),
         ds0-08        (8),
         ds0-09        (9),
         ds0-10        (10),
         ds0-11        (11),
         ds0-12        (12),
         ds0-13        (13),
         ds0-14        (14),
         ds0-15        (15),
         ds0-16        (16),
         ds0-17        (17),
         ds0-18        (18),
         ds0-19        (19),
         ds0-20        (20),
         ds0-21        (21),
         ds0-22        (22),
         ds0-23        (23),
         ds0-24        (24),
         no-connection (40)
     }
     ACCESS        read-only
     STATUS        mandatory
     DESCRIPTION
        "DS0 number 1 through 24 corresponding to the sourced port"
     ::= { mfrapCfgCurrentConnEntry 4 }


mfrapCfgCurrentConnType   OBJECT-TYPE
     SYNTAX        INTEGER
     {
         voice (1),
         transparent(2),
         frame-relay (3),
         not-connected (33)
     }
     ACCESS        read-only
     STATUS        mandatory
     DESCRIPTION
        "Defines the type of traffic being transported."
     ::= { mfrapCfgCurrentConnEntry 5 }


mfrapCfgEditConnections OBJECT IDENTIFIER ::= { mfrapCfgConnectionTable 2 }             

mfrapCfgEditConnCopyCurrtoEdit   OBJECT-TYPE
     SYNTAX        INTEGER
     {
        copy-current  (1)
     }
     ACCESS        write-only
     STATUS        mandatory
     DESCRIPTION
       "Fill the edit buffer with the node's current active
        connections."
     ::= { mfrapCfgEditConnections 1 }             


mfrapCfgEditClearEdit  OBJECT-TYPE
     SYNTAX       INTEGER
     {
       clear-edit   (1)
     }
     ACCESS       write-only
     STATUS       mandatory
     DESCRIPTION
        "Clear all connections from the edit buffer. "
     ::= { mfrapCfgEditConnections 2 }

mfrapCfgEditConnTable OBJECT-TYPE 
     SYNTAX       SEQUENCE OF MfrapCfgEditConnEntry
     ACCESS       not-accessible
     STATUS       mandatory
     DESCRIPTION
        "Edits current DS0 assignment.   This table is also updated
         by the mfrapCfgDteTable.  After making any adjustments 
         to the connections, the mfrapCfgConnUpdateCmd must be sent."
     ::= { mfrapCfgEditConnections 3 }             

mfrapCfgEditConnEntry OBJECT-TYPE
     SYNTAX       MfrapCfgEditConnEntry
     ACCESS       not-accessible
     STATUS       mandatory
     DESCRIPTION
        "An entry in the Edit Connections table."
     INDEX { mfrapCfgEditConnDestPort, mfrapCfgEditConnDestDs0 }

     ::= { mfrapCfgEditConnTable 1 }             
   
MfrapCfgEditConnEntry ::=
     SEQUENCE 
     {
         mfrapCfgEditConnDestPort     INTEGER,
         mfrapCfgEditConnDestDs0      INTEGER,
         mfrapCfgEditConnSrcPort      INTEGER,
         mfrapCfgEditConnSrcDs0       INTEGER,
         mfrapCfgEditConnType         INTEGER,
         mfrapCfgEditDisconnect       INTEGER
     }

mfrapCfgEditConnDestPort OBJECT-TYPE
     SYNTAX  INTEGER 
     {
         port1-t1      (1)
--       port2-dandi   (2)
     }
     ACCESS      read-only
     STATUS      mandatory
     DESCRIPTION
        "Index to destination port of interest. M-FRAP currently
         only supports the Network port (1) as the destination. "
     ::= { mfrapCfgEditConnEntry 1 }

mfrapCfgEditConnDestDs0       OBJECT-TYPE
     SYNTAX        INTEGER (1..24)
     ACCESS        read-only
     STATUS        mandatory
     DESCRIPTION
        "DS0 number 1 through 24 corresponding to the Destination 
         port index"
     ::= { mfrapCfgEditConnEntry 2 }

mfrapCfgEditConnSrcPort   OBJECT-TYPE
     SYNTAX        INTEGER
     {
--       port1-t1      (1),
         port2-dandi   (2),
         port3-dte     (3),
         not-connected (33)
     }
     ACCESS        read-write
     STATUS        mandatory
     DESCRIPTION
        "DS0 assignment for indexed destination port.  The value
         not-connected may not be written; to clear a connection,
         use the mfrapCfgEditDisconnect table element.  Setting
         mfrapCfgEditDisconnect to disconnect will cause this
         element to return not-connected for a get.
      
         Currently, M-FRAP will not allow setting this value to 3.  
         Connections defined by the mfrapCfgDteTable will be reflected in
         reads of this object.  After making any adjustments to the 
         connections, the mfrapCfgConnUpdateCmd must be sent. Node 
         software does not permit connections between a port and itself."
     ::= { mfrapCfgEditConnEntry 3 }


mfrapCfgEditConnSrcDs0       OBJECT-TYPE
     SYNTAX        INTEGER
     {
         ds0-01        (1),
         ds0-02        (2),
         ds0-03        (3),
         ds0-04        (4),
         ds0-05        (5),
         ds0-06        (6),
         ds0-07        (7),
         ds0-08        (8),
         ds0-09        (9),
         ds0-10        (10),
         ds0-11        (11),
         ds0-12        (12),
         ds0-13        (13),
         ds0-14        (14),
         ds0-15        (15),
         ds0-16        (16),
         ds0-17        (17),
         ds0-18        (18),
         ds0-19        (19),
         ds0-20        (20),
         ds0-21        (21),
         ds0-22        (22),
         ds0-23        (23),
         ds0-24        (24),
         no-connection (40)
     }
     ACCESS        read-write
     STATUS        mandatory
     DESCRIPTION
        "DS0 number 1 through 24 corresponding to the sourced port index.
         The value no-connection may not be written.  To clear a 
         connection use the mfrapCfgEditDisconnect table element.
         Setting mfrapCfgEditDisconnect to disconnect will cause this
         element to return no-connection for a get."
     ::= { mfrapCfgEditConnEntry 4 }


mfrapCfgEditConnType       OBJECT-TYPE
     SYNTAX        INTEGER
     {
         voice (1),
         transparent (2),
         frame-relay (3),
         not-connected (33)
     }
     ACCESS        read-write
     STATUS        mandatory
     DESCRIPTION
      "Defines the type of traffic being transported.  The value
       not-connected may not be written.  To clear a connection
       use the mfrapCfgEditDisconnect table element.  Setting
       mfrapCfgEditDisconnect to disconnect will cause this
       element to return not-connected for a get. "
     ::= { mfrapCfgEditConnEntry 5 }

mfrapCfgEditDisconnect  OBJECT-TYPE
     SYNTAX        INTEGER
     {
         disconnect  (1)
     }
     ACCESS        write-only
     STATUS        mandatory
     DESCRIPTION
      "Setting this object to disconnect will cause the state of 
       the Src and Type objects for this destination port and ds0
       to be set to not-connected. When connections are updated,
       the connection between the source and destination will be
       terminated. "
    ::= { mfrapCfgEditConnEntry 6}

mfrapCfgEditLastSetStatus  OBJECT-TYPE
     SYNTAX          INTEGER
     {
        set-valid              (1),
        invalid-dte-bandwidth  (2),
        bandwidth-conflict     (3),
        ds0s-not-ascending     (4),
        illegal-value          (8)
     }
     ACCESS         read-only
     STATUS         mandatory
     DESCRIPTION
        "The status of the last set of an mfrapCfgEditConnTable
         object.  Invalid-dte-bandwidth is returned if the set
         reduces the number of ds0's assigned to a DTE port
         to less than the number required for the port's 
         bandwidth and density.  Bandwidth-conflict is returned
         if an attempt is made to change the source port without
         first disconnecting the existing connection.  
         Ds0s-not-ascending is returned if the source ds0 being
         set is not in ascending order with the other ds0's for
         that source port.  "
    ::= { mfrapCfgEditConnections 4 }

mfrapCfgEditConnStatus             OBJECT-TYPE
     SYNTAX          INTEGER
     {
         connections-valid      (1),
         invalid-dte-bandwidth  (2),
         ds0s-not-ascending     (4),
         incomplete-entry       (5),
         inconsistent-edit-buff (6),
         bad-connection-type    (7),
         no-current-connections (99)
     }
     ACCESS        read-only
     STATUS        mandatory
     DESCRIPTION
        "Displays the status of the connections in the edit buffer.
         This object should be read before setting the 
         mfrapCfgConnUpdateCmd. Incorrect-dte-bandwidth is returned if
         there are not enough DS0's starting with the 
         mfrapCfgDteConnStartDs0 to accommodate the 
         mfrapCfgDteConnDs0Required. Incomplete-entry is returned
         if the source port, source ds0 and/or connection type has
         not been set for a connection (and at least one of them
         has been set for that connection).  Inconsistent-edit-buffer
         is returned if there is an internal inconsistency in the
         edit buffer;  in this case, an mfrapCfgEditConnCopyCurrtoEdit
         or mfrapCfgEditClearEdit set should be performed before
         proceeding. Bad-connection-type is returned if the connection
         type is not consistent with the source and destination ports. " 
     ::= { mfrapCfgEditConnections 5 }             

mfrapCfgConnUpdateCmd        OBJECT-TYPE
     SYNTAX        INTEGER
     {
         config-and-connect (1)
     }
     ACCESS        write-only
     STATUS        mandatory
     DESCRIPTION
        "Updates the connections with the edit buffer if the connections
         are all valid. The edit buffer is comprised of any changes sent 
         (set) from the mfrapCfgEditConnTable or the mfrapCfgDteTable.
         Note that if changes are made to the mfrapCfgDteTable, the
         mfrapCfgConnAutoUpdate object must be set before the 
         mfrapCfgConnUpdateCmd in order for the changes to take effect."
     ::= { mfrapCfgEditConnections 6 }             

--
--       The Drop & Insert Configuration Table
--              This table contains the Drop & Insert port 
--              Configuration information for the MFRAP CSU/DSU.

mfrapCfgDandiTable   OBJECT IDENTIFIER ::= { mfrapConfiguration 11 }

   --     DESCRIPTION
   --        "The Drop & Insert Port Configuration table contains
   --         parameters for the Drop & Insert (T1) port on the
   --         MFRAP. "

mfrapCfgDandiFraming    OBJECT-TYPE
     SYNTAX      INTEGER 
     {
        d4              (1),
        esf             (2)
     }
     ACCESS        read-write
     STATUS        mandatory
     DESCRIPTION
        "Type of Framing on this D&I Line.  Check with your service 
         provider to determine value.  D4 is also known as 
         'SuperFrame', ESF is 'Extended SuperFrame'.  ESF provides 
         enhanced performance monitoring capabilities. "
    ::= { mfrapCfgDandiTable 1 }

mfrapCfgDandiLineEncoding    OBJECT-TYPE
     SYNTAX      INTEGER 
     {
        ami             (1),
        b8zs            (2)
     }
     ACCESS        read-write
     STATUS        mandatory
     DESCRIPTION
        "D&I interface bipolar encoding scheme.  Check with your 
        service provider to determine value. B8ZS, which inherently 
        provides ample 'ones-density', is recommended. AMI users 
        must pay special attention to the 'ones-density' requirements
        of the service provider."
    ::= { mfrapCfgDandiTable 2 }

mfrapCfgLock   OBJECT-TYPE
     SYNTAX      INTEGER (1..600)
     ACCESS      write-only
     STATUS      mandatory
     DESCRIPTION
        " Request to start configuration download and lock out any 
          other means of configuring the unit. The integer passed in
          represents the time out period  in seconds between sets. 
          A set to this object will fail if the unit is already in a 
          configuration locked state."
     ::= { mfrapConfiguration 12 }

mfrapCfgLockID   OBJECT-TYPE
     SYNTAX      IpAddress
     ACCESS      read-only
     STATUS      mandatory
     DESCRIPTION
        " Returns the IP Address of  the management station currently 
          in control of configuration. A unit that is not in a 
          configuration locked state will return  0.0.0.0" 
     ::= { mfrapConfiguration 13 }

mfrapCfgID   OBJECT-TYPE
     SYNTAX      DisplayString (SIZE (0..8))
     ACCESS      read-write
     STATUS      mandatory
     DESCRIPTION
        " A read of this object returns the Current Configuration ID 
          string. A write sets  the Configuration ID string. The 
          string contains a starting character to indicate the last 
          configuration source C = Envisage N = CLI/TELNET L = LCD 
          S= other SNMP management station  and a unique 7 integer 
          value to differentiate configurations between common sources. 
          A value of *STARTUP indicates the configuration has been 
          defaulted. A write will only be accepted from the management 
          station that has successfully obtained the configuration lock" 
     ::= { mfrapConfiguration 14 }

mfrapCfgStatus   OBJECT-TYPE
     SYNTAX      INTEGER
     {
         in-progress                (1),
         success                    (2),
         datarate-density-conflict  (3),
         bandwidth-allocation-error (4),
         general-error              (5),
         timeout                    (6),
         aborted-by-user            (7)
     }
     ACCESS      read-only
     STATUS      mandatory
     DESCRIPTION
        " The status of a configuration install is reported here.
          On startup, a status of success will be reported.
          (1) The configuration has been locked and an update or
              unlock command has not been received.
          (2) An update command has been received and the configuration
              has been validated as consistent; .
          (3) An update command has been received but the DTE port 
              datarate is not compatible with the density.
          (4) An update command has been received but the number of
              channels to be allocated will not fit in the available
              channels.
          (5) An update command has been received but there is an
              error in the configuration that is not a 
              datarate-density-conflict or bandwidth-allocation-error.
          (6) The time between consecutive set requests exceeded the
              timeout sent with the tfrapCfgLock command.
          (7) The user sent a tfrapCfgUnlock command before a 
              tfrapCfgUpdate command.  This usually means that one
              of the sets in the configuration failed. "
     ::= { mfrapConfiguration 15 }

mfrapCfgUnlock   OBJECT-TYPE
     SYNTAX      INTEGER 
     {
         un-lock (1)
     }
     ACCESS      write-only
     STATUS      mandatory
     DESCRIPTION
        " The management station sets this variable to complete 
          the configuration install process. Un-lock (1) notifies 
          the agent to remove the lock on configuring the unit
          without updating the configuration."
     ::= { mfrapConfiguration 16 }


mfrapCfgUpdate   OBJECT-TYPE
     SYNTAX      INTEGER 
     {
         update (1)
     }
     ACCESS      write-only
     STATUS      mandatory
     DESCRIPTION
        " The management station sets this variable to complete 
          the configuration install process. Update (1) notifies 
          the agent to start the update process within the unit."
     ::= { mfrapConfiguration 17 }



-- =========================
-- ==  DIAGNOSTICS group  ==
-- =========================

mfrapDiagnostics  OBJECT IDENTIFIER ::= { mfrap 3 }


--
--       The Diagnostics/Unit Table
--              This table contains the objects for unit level diagnostics
--              on the FRAP T1 DSU.

mfrapDiagUnitTable OBJECT IDENTIFIER ::= { mfrapDiagnostics 1 }

mfrapDiagUnitLocLoop OBJECT-TYPE
          SYNTAX      INTEGER 
          {
               enable-loopback-mode  (1),
               disable-loopback-mode (2)
          }
          ACCESS      read-write
          STATUS      mandatory
          DESCRIPTION
             "Controls a bi-directional unit loopback. Data 
              is received from either the DTE or Network interface, 
              processed, and transmitted back towards the same interface. 
              When configured for Frame Relay operation the unit 
              will preserve the LMI path and maintain managed access
              during this loopback. In Frame Relay mode, only valid 
              HDLC frames are looped back (pseudorandom test patterns
              will be dropped).  Data received on the Drop & Insert
              is not affected by this loopback mode.
                 (1) enable unit loopback
                 (2) disable unit loopback"
          ::= { mfrapDiagUnitTable 1 }

mfrapDiagUnitReset OBJECT-TYPE
          SYNTAX      INTEGER 
          {
               reset-unit (1)
          }
          ACCESS      write-only
          STATUS      mandatory
          DESCRIPTION
             "Enables the operator to remotely cause a software
              reset on the unit. Using this command will cause 
              the unit to terminate all its connections and drop data.
              (1) Reset Unit."
          ::= { mfrapDiagUnitTable 2 }

mfrapDiagUnitTimeRemaining OBJECT-TYPE
          SYNTAX      TimeTicks
          ACCESS      read-only
          STATUS      mandatory
          DESCRIPTION
             "The remaining time on the active loopback
              before the loopback times out and disables
              itself. The time is in hundredths of seconds
              (TimeTicks)."
          ::= { mfrapDiagUnitTable 3 }

--       The mfrapDiagT1Table
--              This table contains the T1 level diagnostics of the MFRAP CSU.
--

mfrapDiagT1Table   OBJECT IDENTIFIER ::= { mfrapDiagnostics 2 }
--        DESCRIPTION
--           "Network (T1) Diagnostics for the Sync MFRAP. "

mfrapDiagT1LocLineLpbk OBJECT-TYPE
     SYNTAX      INTEGER
     {
        line-lpbk-disable       (1),
        line-lpbk-enable        (2)
     }
     ACCESS      read-write
     STATUS      mandatory
     DESCRIPTION
        "Controls local network loopback. All data (including
         framing and line errors) received from the WAN, 
         regardless of format or content, is transmitted back 
         out to the WAN (line interface loopback) while still 
         being passed through to the DTE. In Frame Relay 
         applications the unit will not preserve the LMI path during
         this diagnostic and in-band management may not operate.
         (1) disable line loopback
         (2) enable line loopback "
     ::= { mfrapDiagT1Table 1 }

mfrapDiagT1LocPylLpbk OBJECT-TYPE
     SYNTAX      INTEGER
     {
        pyl-lpbk-disable        (1),
        pyl-lpbk-enable         (2)
     }
     ACCESS      read-write
     STATUS      mandatory
     DESCRIPTION
        "Controls network payload loopback. All data 
         received from the WAN is terminated, reframed
         and sent back towards the WAN. Framing errors
         and Line Code Violations are corrected. 
         Network contact via ESF Facility Data Link is 
         preserved during this loopback state. All user
         data regardless of format or content, is transmitted 
         back out while all Ones are sent to the DTE. In Frame
         Relay applications the unit will not preserve the LMI
         path during this diagnostic and in-band management may
         not operate.
         (1) disable payload loopback
         (2) enable payload loopback "
     ::= { mfrapDiagT1Table 2 }

mfrapDiagT1LocAggrLpbk OBJECT-TYPE
     SYNTAX      INTEGER
     {
        aggr-lpbk-disable       (1),
        aggr-lpbk-enable        (2)
     }
     ACCESS      read-write
     STATUS      mandatory
     DESCRIPTION
        "Controls Local Aggregate Loopback. All data 
         received from the DTE and Drop & Insert ports 
         is framed, formatted and transmitted towards 
         the WAN while being looped back towards the 
         respective port (DTE or Drop & Insert). The 
         loopback path covers the entire digital data 
         path within the device. In Frame Relay mode, 
         only error-free HDLC frames will pass through 
         the loopback path. Additionally, in Frame Relay 
         applications the unit will not preserve the LMI 
         path during this loopback and in-band management
         may not operate.
         (1) disable local aggregate (digital) loopback
         (2) enable local aggregate (digital) loopback "
     ::= { mfrapDiagT1Table 3 }

mfrapDiagT1RmtLpbkStatus OBJECT-TYPE
     SYNTAX      INTEGER
     {
        no-remote-lpbks         (1),
        csu-lpbk-from-remote    (2),
        dsu-lpbk-from-remote    (3),
        pyl-lpbk-from-remote    (4),
        csu-lpbk-sent-to-remote (5),
        dsu-lpbk-sent-to-remote (6)
     }
     ACCESS      read-only
     STATUS      mandatory
     DESCRIPTION
        "Status of Remote Loopback commands sent or received on the WAN.
         (1) no remote loopbacks are active.
         (2) csu loopback from remote - indicates the node is in a Network
             Line Loopback state due to the reception of the standard CSU 
             Loop-up pattern from the WAN.
         (3) dsu loopback from remote - indicates the node is in a Network
             Line Loopback state due to the reception of the Sync Research
             proprietary Loop-up pattern from a remote node.
         (4) payload loopback from remote - indicates the node is in a 
             Payload Loopback state due to the reception of the ESF Facility 
             Data Link's Loop-up pattern from the network.
         (5) csu loopback sent to remote - indicates the node has sent a csu
             loop up pattern towards the WAN. A device terminating the WAN's 
             physical link is expected to enter a Line Loopback. The initating 
             unit doesn't know if the loopback was accepted by the remote unit.
         (6) dsu loopback sent to remote - indicates the node has sent a dsu
             loop up pattern to a remote Sync unit out the WAN. A compatible 
             device detecting this pattern is expected to enter a Line Loopback. 
             The initating unit doesn't know if the loopback was accepted by 
             the remote unit."
     ::= { mfrapDiagT1Table 4 }

mfrapDiagT1RmtLpbkCmd OBJECT-TYPE
     SYNTAX      INTEGER
     {
        rmt-csu-lpbk-loopup     (1),
        rmt-csu-lpbk-loopdown   (2),
        rmt-dsu-lpbk-loopup     (3),
        rmt-dsu-lpbk-loopdown   (4)
     }
     ACCESS      write-only
     STATUS      mandatory
     DESCRIPTION
        "Remote loopback commands are intended to place compatible external
         equipment into a loopback state. The initiating unit will maintain
         normal data flows during these tests. 
         (1) csu loop up - commands the node to send a standard in-band 
             csu loop up pattern towards the WAN. This is a repetetive
             framed T1 signal consisting of four 'zeros' followed by one 'one'
             persisting for a few seconds in place of all T1 data. A 
             device terminating the WAN's physical link is expected to enter 
             a Line Loopback condition upon recognition of this pattern. 
             The initating unit doesn't know if the command was accepted by 
             the remote unit.
         (2) csu loop down - commands the node to send a standard in-band 
             csu loop down pattern towards the WAN. This is a repetetive
             framed T1 signal consisting of two 'zeros' followed by one 'one'
             persisting for a few seconds in place of all T1 data. A 
             device terminating the WAN's physical link is expected to clear 
             any Line Loopback condition upon recognition of this pattern. 
             The initating unit doesn't know if the commad was accepted by 
             the remote unit.
         (3) dsu loop up - commands the node to send a proprietary in-band 
             dsu loop up pattern towards the WAN. This is a repetetive
             framed T1 signal consisting of a pseudorandom pattern persisting 
             for a few seconds in place of all T1 data. A compatible 
             device terminating the WAN's physical link is expected to enter 
             a Line Loopback condition upon recognition of this pattern. 
             The initating unit doesn't know if the command was accepted by 
             the remote unit.
         (4) dsu loop down - commands the node to send a proprietary in-band
             dsu loop down pattern towards the WAN. This is a repetetive
             framed T1 signal consisting of a pseudorandom pattern persisting 
             for a few seconds in place of all T1 data. A compatible 
             device terminating the WAN's physical link is expected to clear 
             any Line Loopback condition upon recognition of this pattern. 
             The initating unit doesn't know if the command was accepted by 
             the remote unit."
     ::= { mfrapDiagT1Table 5 }

mfrapDiagT1TimeRemaining OBJECT-TYPE
     SYNTAX      TimeTicks
     ACCESS      read-only
     STATUS      mandatory
     DESCRIPTION
        "The remaining time on the active loopback before the loopback 
         times out and automatically clears itself to restore the unit
         to normal operation. The time is in hundredths of seconds
         (TimeTicks)."
     ::= { mfrapDiagT1Table 6 }

--
--       The mfrapDiagDteTable
--              This table contains the DTE level diagnostics of the MFRAP CSU.
--

mfrapDiagDteTable   OBJECT IDENTIFIER ::= { mfrapDiagnostics 3 }

mfrapDiagDteSigRTS OBJECT-TYPE
          SYNTAX      INTEGER 
          {
               rts-signal-on  (1),
               rts-signal-off (2)
          }
          ACCESS      read-only
          STATUS      mandatory
          DESCRIPTION
             "Status of the Request to Send (RTS) signal from the DTE port.
              (1) RTS Active
              (2) RTS Inactive"
          ::= { mfrapDiagDteTable 1 }

mfrapDiagDteSigDTR OBJECT-TYPE
          SYNTAX      INTEGER 
          {
               dtr-signal-on  (1),
               dtr-signal-off (2)
          }
          ACCESS      read-only
          STATUS      mandatory
          DESCRIPTION
             "Status of the Data Terminal Ready (DTR) signal from the DTE port.
              (1) DTR Active
              (2) DTR Inactive"
          ::= { mfrapDiagDteTable 2 }

mfrapDiagDteLclLpbk OBJECT-TYPE
          SYNTAX      INTEGER
          {
               enable-loopback-mode (1),
               disable-loopback-mode (2)
          }
          ACCESS      read-write
          STATUS      mandatory
          DESCRIPTION
             "Controls the DTE loopback state. This is a 
              bi-directional loopback state where both the
              DTE and WAN ports are placed in line loopback. 
              All data received on each interface is sent back
              out the respective interface regardless of format
              or content. In Frame Relay applications the unit 
              will not preserve the LMI path during this diagnostic 
              and in-band management will not operate.
              (1) enable payload loopback
              (2) disable payload loopback"
          ::= { mfrapDiagDteTable 3 }

mfrapDiagDteV54Lpbk   OBJECT-TYPE
          SYNTAX      INTEGER
          {
               loopback-enable (1),
               loopback-disable (2)
          }
          ACCESS      read-only
          STATUS      mandatory
          DESCRIPTION
             "This reports the status of any local V54 testing initiated by
              a remote unit. Remote V54 loopback commands are intended to place
              this unit into a loopback state. The initiating unit will maintain 
              normal data flows during these tests.
              (1) V54 loop up received - indicates the node has received a standard
                  in-band loop up pattern from the WAN per ITU V.54. This is a
                  framed T1 signal consisting of a pseudorandom signal in place of 
                  all user data (that is only in the DS0s assigned to the DTE). This
                  unit has entered a bi-directional DTE Loopback condition.
              (2) V54 loop down received - indicates the node has received a standard 
                  in-band loop down pattern from the WAN per ITU V.54. This is a
                  framed T1 signal consisting of a pseudorandom signal in place of 
                  all user data (that is only in the DS0s assigned to the DTE). This
                  unit has cleared the bi-directional DTE Loopback condition."
          ::= { mfrapDiagDteTable 4 }

mfrapDiagDteRmtV54Lpbk   OBJECT-TYPE
          SYNTAX      INTEGER
          {
               transmit-code-enable  (3),
               transmit-code-disable (4)
          }
          ACCESS      write-only
          STATUS      mandatory
          DESCRIPTION
             "Remote V54 loopback commands are intended to place compatible
              external equipment into a loopback state. The initiating unit
              will maintain normal data flows during these tests. 
              (3) Transmit V54 loop up - commands the node to send a standard 
                  in-band loop up pattern towards the WAN per ITU V.54. This is a
                  framed T1 signal consisting of a pseudorandom signal in place of 
                  all user data (that is only in the DS0s assigned to the DTE). A 
                  device terminating the fractional T1 data is expected to enter 
                  a bi-directional DTE Loopback condition upon recognition of this
                  pattern. The initating unit doesn't know if the command was accepted
                  by the remote unit. This pattern will not traverse a typical frame
                  relay network and is designed for circuit-switched diagnostics.
              (4) Transmit V54 loop down - commands the node to send a standard 
                  in-band loop down pattern towards the WAN per ITU V.54. This is a
                  framed T1 signal consisting of a pseudorandom signal in place of 
                  all user data (that is only in the DS0s assigned to the DTE). A 
                  device terminating the fractional T1 data is expected to clear 
                  a bi-directional DTE Loopback condition upon recognition of this
                  pattern. The initating unit doesn't know if the command was accepted
                  by the remote unit."
          ::= { mfrapDiagDteTable 5 }
                        
mfrapDiagDteTimeRemaining OBJECT-TYPE
          SYNTAX      TimeTicks
          ACCESS      read-only
          STATUS      mandatory
          DESCRIPTION
             "The remaining time on the active loopback
              before the loopback times out. The time is
              in hundredths of seconds (TimeTicks)."
          ::= { mfrapDiagDteTable 13 }

--
--       The mfrapDiagBertTable
--              This table contains the BERT diagnostics
--
mfrapDiagBertTable  OBJECT IDENTIFIER  ::= { mfrapDiagnostics 5 }
--
mfrapDiagBertState   OBJECT-TYPE
          SYNTAX      INTEGER
          {
               start-bert-test-t1            (1),
               start-bert-test-dte           (2),
               stop-bert-test                (3),
               inject-error-bert-test        (4),
               clear-error-bert-test         (5),
               start-bert-test-dandi         (6),
               start-bert-test-fractional-t1 (7)
          }
          ACCESS      write-only
          STATUS      mandatory
          DESCRIPTION
             "The unit is capable of sending a pseudorandom test pattern
              (511 or QRSS) out the WAN and monitoring the WAN received 
              data for the same pattern. The BERT pattern may be selected 
              to occupy the full T1 payload, only the bandwidth
              allocated to the DTE, only the bandwidth allocated to the
              Drop & Insert or only the bandwidth allocated to the DTE
              and the Drop & Insert (fractional T1). When a unit is sending
              this BERT, the receiver will monitor and characterize the 
              incoming signal for the same BERT pattern. In Frame Relay 
              applications the unit will not preserve the LMI path during
              this diagnostic and in-band management may not operate.
              This test may be ineffective in certain frame relay environments 
              as pseudorandom data lacks appropriate framing. Refer to 
              VLOOP and VBERT for PVC-based error-rate testing in a live frame 
              relay network.
              (1) Start a BERT test on full T1 - replaces entire T1 payload with
                  the configured BERT pattern while monitoring the full T1 bandwidth
                  (1.536M) for the presence of the BERT pattern.
              (2) Start a BERT test on the DTE bandwidth - replaces only the portion
                  of the T1 payload that has been allocated to the DTE with the
                  configured BERT pattern while monitoring the same T1 bandwidth
                  (DTE Data Rate) for the presence of the BERT pattern.
              (3) Stop a BERT test.
              (4) Inject a single bit error into the outgoing pattern.
              (5) Clear current BERT results.
              (6) Starts a BERT test on the Drop & Insert bandwidth - replaces 
                  only the portion of the T1 payload that has been allocated to 
                  the Drop & Insert with the configured BERT pattern while 
                  monitoring the same T1 bandwidth (D&I DS0's) for the presence 
                  of the BERT pattern.
              (7) Starts a BERT test on the DTE & D&I bandwidth (fractional T1) -
                  replaces only the portion of the T1 payload that has been 
                  allocated to the DTE or the Drop & Insert with the configured 
                  BERT pattern while monitoring the same T1 bandwidth for the 
                  presence of the BERT pattern."
          ::= { mfrapDiagBertTable 1 }

mfrapDiagBertStatus  OBJECT-TYPE
          SYNTAX      INTEGER 
          {
               bert-off         (1),
               bert-out-of-sync (2),
               bert-in-sync     (3)
          }
          ACCESS      read-only
          STATUS      mandatory
          DESCRIPTION
             "Displays the current BERT test sync status.
             (1) BERT is not running
             (2) BERT is running but is not in sync
             (3) BERT is running and has detected a received BERT"
          ::= { mfrapDiagBertTable 2 }

mfrapDiagBertErrors   OBJECT-TYPE
          SYNTAX      Counter
          ACCESS      read-only
          STATUS      mandatory
          DESCRIPTION
             "Displays the number of errors detected in Bert Test."
          ::= { mfrapDiagBertTable 3 }

mfrapDiagBertErrSec OBJECT-TYPE
          SYNTAX      Counter
          ACCESS      read-only
          STATUS      mandatory
          DESCRIPTION
             "Displays the number of seconds containing 1 or more errors
              in BERT Test."
          ::= { mfrapDiagBertTable 4 }

mfrapDiagBertTimeElaps OBJECT-TYPE
          SYNTAX      TimeTicks
          ACCESS      read-only
          STATUS      mandatory
          DESCRIPTION
             "Elapsed time since BERT test was started or cleared."
          ::= { mfrapDiagBertTable 5 }

mfrapDiagBertResyncs OBJECT-TYPE
          SYNTAX      Counter
          ACCESS      read-only
          STATUS      mandatory
          DESCRIPTION
             "Displays the number of times BERT test has synched up
              on the pattern. The BERT will attempt to resynchronize
              in response to excessive errors. A running count here
              indicates that a clean BERT is not being received."
          ::= { mfrapDiagBertTable 6 }

mfrapDiagBertPattern OBJECT-TYPE
          SYNTAX      INTEGER
          {
                five11-pattern  (1),
                qrss            (2)
          }
          ACCESS      read-write
          STATUS      mandatory
          DESCRIPTION
             "The type of pseudorandom BERT pattern used. 
              (1) 511: 9-bit pseudorandom pattern
              (2) QRSS: 20-bit pseudorandom pattern with 
                no more than 14 consecutive zeros" 
          ::= { mfrapDiagBertTable 7 }


--       The mfrapDiagVnipTable
--              This table contains the VNIP level diagnostics of the MFRAP CSU.
--
--
mfrapDiagVnipTable  OBJECT-TYPE
      SYNTAX   SEQUENCE OF MfrapDiagVnipEntry
      ACCESS   not-accessible
      STATUS   mandatory
      DESCRIPTION
         " Table of Diagnostics performed with the VNIP protocol"
      ::= { mfrapDiagnostics 6 }

    mfrapDiagVnipEntry OBJECT-TYPE
        SYNTAX   MfrapDiagVnipEntry
        ACCESS   not-accessible
        STATUS   mandatory
        DESCRIPTION
           "VNIP VLOOP and VBERT diagnostic profile. Initiating
            these tests require an established and stable VNIP topology
            on an interface. Once the topology is in place, the user
            can execute a PVC-based diagnostic between this unit and
            any indexed entry in the topology table. The index into the 
            topology table for a particular interface is required."
        INDEX {mfrapDiagVnipInterface, mfrapDiagVnipIndex}
         ::= { mfrapDiagVnipTable 1 }

    MfrapDiagVnipEntry ::=
          SEQUENCE {
                mfrapDiagVnipInterface          INTEGER,
                mfrapDiagVnipIndex              INTEGER,
                mfrapDiagVnipDlci               INTEGER,
                mfrapDiagVnipIpAddr             IpAddress,
                mfrapDiagVLOOP                  INTEGER,
                mfrapDiagVBERT                  INTEGER,
                mfrapDiagVBERTRate              INTEGER,
                mfrapDiagVBERTSize              INTEGER,
                mfrapDiagVBERTPktPercent        INTEGER,
                mfrapDiagVBERTTestPeriod        INTEGER
          }

mfrapDiagVnipInterface OBJECT-TYPE
   SYNTAX      INTEGER
   {
        dte-interface (1),
        t1-interface (2)
   }
   ACCESS      read-write
   STATUS      mandatory
   DESCRIPTION
      "The interface out which a PVC-based VNIP diagnostic
       will be run. This must be an interface with a valid 
       and stable VNIP topology for a VNIP Diagnostic."
   ::= { mfrapDiagVnipEntry 1 }

mfrapDiagVnipIndex OBJECT-TYPE
    SYNTAX      INTEGER
    ACCESS      read-write
    STATUS      mandatory
    DESCRIPTION
       "The index to the external VNIP peer as presented by the VNIP
        topology database for the given interface. Refer to 
        VnipTopologyTable to determine the index of the remote peer."
    ::= { mfrapDiagVnipEntry 2 }

mfrapDiagVnipDlci    OBJECT-TYPE
    SYNTAX      INTEGER
    ACCESS      read-only
    STATUS      mandatory
    DESCRIPTION
       "This is the DLCI value for the given interface/index
        combination. This comes from the VniptTopologyTable."
    ::= { mfrapDiagVnipEntry 3 }

mfrapDiagVnipIpAddr   OBJECT-TYPE
    SYNTAX      IpAddress
    ACCESS      read-only
    STATUS      mandatory
    DESCRIPTION
       "This is the ip address for the given interface/index
        combination. This comes from the VniptTopologyTable."
    ::= { mfrapDiagVnipEntry 4 }

mfrapDiagVLOOP OBJECT-TYPE
    SYNTAX      INTEGER
    {
         start-test         (1),
         stop-test          (2)
    }
    ACCESS      write-only
    STATUS      mandatory
    DESCRIPTION
       "Controls execution of the Vnip Logical Loopback (VLOOP) test. 
        VLOOP is designed as an intrusive test and customer data 
        on the DLCI-under-test will be discarded. The VLOOP test includes
        a timed VBERT test and is run using the profile configured within 
        this table.
        (1) start VLOOP test 
        (2) stop VLOOP test (override VBERT test duration)"
    ::= { mfrapDiagVnipEntry 5 }

 
mfrapDiagVBERT OBJECT-TYPE
    SYNTAX      INTEGER
    {
         start     (1),
         stop      (2)
    }
    ACCESS      write-only
    STATUS      mandatory
    DESCRIPTION
       "Controls execution of the Vnip Virtual Bit Eror Rate (VBERT) test. 
        VBERT is designed to be a non-intrusive test and will attempt to
        statistically multiplex VBERT test data and customer data on the
        DLCI-under-test. However, VBERT data is given priority over customer
        data when the selected VBERT volume causes internal congestion. 
        The test is run using the profile configured within this table.
        (1) start test 
        (2) stop test (override VBERT test duration)"
    ::= { mfrapDiagVnipEntry 6 }



mfrapDiagVBERTRate  OBJECT-TYPE
    SYNTAX      INTEGER (8000..2048000)
    ACCESS      read-write
    STATUS      mandatory
    DESCRIPTION
       "Specifies the throughput bit rate applied by VBERT or 
        VLOOP to the DLCI-under-test. For DTE Rates or configured
        CIR up to 64K the maximum VBERT rate is either the DTE data
        rate or 110% of CIR (which ever is less). For DTE Rates or
        configured CIR greater than 64K, the maximum VBERT rate is 
        75% of the DTE data rate or 110% of CIR (which ever is less). 
        Note that selecting rates that approach line rate will impact 
        neighboring PVCs.
        (8000-1152000): VBERT/VLOOP data rate (in bits per second)."
    ::= { mfrapDiagVnipEntry 7 }


mfrapDiagVBERTSize  OBJECT-TYPE
    SYNTAX      INTEGER (32..2048)
    ACCESS      read-write
    STATUS      mandatory
    DESCRIPTION
       "Specifies the size of framed data that will be used
        during the VBERT test, measured in Bytes.
         (64) 64-byte frames
         (128) 128-byte frames
         (256) 256-byte frames
         (512) 512-byte frames
         (1024) 1024-byte frames
         (2048) 2048-byte frames"
    ::= { mfrapDiagVnipEntry 8 }


mfrapDiagVBERTPktPercent  OBJECT-TYPE
    SYNTAX      INTEGER 
    {
       zero-percent        (0),
       twentyFive-percent  (1),
       fifty-percent       (2),
       seventyFive-percent (3),
       oneHundred-percent  (4)
    }
    ACCESS      read-write
    STATUS      mandatory
    DESCRIPTION
        "Specifies percentage of VBERT packets that will have the
         Frame Relay Discard Eligibility bit set. Frames with this
         bit set may be more likley to get dropped in a congested
         network.
         (0) 0%  of the test frames are marked discard eligible
         (25) 25% of the test frames are marked discard eligible
         (50) 50% of the test frames are marked discard eligible
         (75) 75% of the test frames are marked discard eligible
         (100) 100% of the test frames are marked discard eligible"
    ::= { mfrapDiagVnipEntry 9 }

mfrapDiagVBERTTestPeriod  OBJECT-TYPE
    SYNTAX      INTEGER (10..1440)
    ACCESS      read-write
    STATUS      mandatory
    DESCRIPTION
       "Specifies the duration of a VBERT test. Note that VBERT is 
        subjected to the unit's Loopback Timer and will be terminated 
        by whichever timer expires first.
        (10-1440): VBERT time duration in seconds"
    ::= { mfrapDiagVnipEntry 10 }

--
--       The mfrapDiagDandiTable
--              This table contains the Drop and Insert level diagnostics 
--              of the MFRAP CSU.
--
mfrapDiagDandiTable   OBJECT IDENTIFIER ::= { mfrapDiagnostics 8 }

mfrapDiagDandiLocLineLpbk OBJECT-TYPE
     SYNTAX      INTEGER
     {
        line-lpbk-disable       (1),
        line-lpbk-enable        (2)
     }
     ACCESS      read-write
     STATUS      mandatory
     DESCRIPTION
        "Local Line Loopback on the Drop & Insert port. Data and 
        framing received at the D & I port is transmitted back 
        out the D & I port
        (1) disable line loopback
        (2) enable line loopback"
     ::= { mfrapDiagDandiTable 1 }

mfrapDiagDandiLocPylLpbk OBJECT-TYPE
     SYNTAX      INTEGER
     {
        pyl-lpbk-disable        (1),
        pyl-lpbk-enable         (2)
     }
     ACCESS      read-write
     STATUS      mandatory
     DESCRIPTION
        "Local Payload Loopback on the Drop & Insert port. Data 
        (NOT framing) received at the T1 port is looped back
        at the D&I port and reframed and transmitted back out 
        the T1 port. 
        (1) disable line loopback
        (2) enable line loopback"
     ::= { mfrapDiagDandiTable 2 }

mfrapDiagDandiTimeRemaining OBJECT-TYPE
     SYNTAX      TimeTicks
     ACCESS      read-only
     STATUS      mandatory
     DESCRIPTION
        "The remaining time on the active loopback
         before the loopback times out. The time is
         in hundredths of seconds (TimeTicks)."
     ::= { mfrapDiagDandiTable 6 }


-- =========================
-- ==    STATUS group     ==
-- =========================

mfrapStatus  OBJECT IDENTIFIER ::= { mfrap 4 }


--
--      T1 Status 
--
--         The current status of the T1 port.
--

mfrapStatusT1Table   OBJECT IDENTIFIER ::= { mfrapStatus 1 }

mfrapStatusT1Mode   OBJECT-TYPE
     SYNTAX  INTEGER
     {
        no-connections (1),
        active         (2),
        test           (3)
     }
     ACCESS  read-only
     STATUS  mandatory
     DESCRIPTION
        "Status of allocation of T1 bandwidth to the DTE port data. 
         (1) no connections - indicates the DTE port has no connections 
           to the WAN. 
         (2) Active - indicates DTE data rate has been assigned T1 DS0s
           and is in a normal data mode.
         (3) Test -  indicates DTE data rate has been assigned T1 DS0s
           but is in a diagnostic condition."
     ::= { mfrapStatusT1Table 4 }

mfrapStatusT1Status   OBJECT-TYPE
     SYNTAX  INTEGER
     {
        t1-frame-sync-okay                (1),
        t1-frame-sync-with-errors         (2),
        signal-present-without-frame-sync (3),
        signal-not-present                (4), 
        not-applicable                    (5)
     }
     ACCESS  read-only
     STATUS  mandatory
     DESCRIPTION
      "Status of the signal received from the WAN
       (1) In Sync - unit has detected a properly framed T1 signal
           and is not experiencing any error conditions.
       (2) In Sync with Errors - unit has detected a properly framed 
           T1 signal but is experiencing some error conditions. Refer to
           T1 current performance results for details.
       (3) Signal Detected without Frame Sync - while a signal is present
           from the WAN it does not contain the framing pattern defined for
           this unit. This could be either incorrectly configured T1 Frame 
           type or the presence of an alarm condition on the WAN.
       (4) No Carrier - there is no signal detected from the WAN.
       (5) Not Applicable."
     ::= { mfrapStatusT1Table 5 }

mfrapStatusT1Alarms   OBJECT-TYPE
     SYNTAX  INTEGER
     {
        no-alarms                  (1),
        red-alarm-declared         (2), 
        yellow-alarm-detected      (3),
        unframed-all-ones-detected (4)
     }
     ACCESS  read-only
     STATUS  mandatory
     DESCRIPTION
        "Alarms present at the T1 port.
         (1) No alarm conditions present.
         (2) Red Alarm Declared - Unit has experienced loss of frame 
             synchronization with the signal received from the WAN 
             for an extended time and is reporting an alarm condition 
             that severely impairs normal operation. During this Red 
             Alarm condition the unit will transmit Yellow alarm back 
             to the WAN. If this condition persists consult your 
             service provider.
         (3) Yellow ALarm Detected - Unit is receiving a yellow alarm 
             indication from the wide area network. Detection of yellow 
             alarm implies that the attached device is in a red alarm 
             conditon. Red alarm is declared due to the extended absence 
             of a properly framed signal. If this condition persists 
             consult your service provider.
         (4) Unframe All Ones Detected - Unit is receiving unframed all 
             ones from the wide area network (AIS, blue alarm). Detection 
             of AIS implies that the attached device is reporting
             an alarm condition from an upstream device. If 
             this condition persists consult your service provider."
     ::= { mfrapStatusT1Table 6 }


--
--      DTE Status 
--
--         The current status of the DTE port.
--
mfrapStatusDteTable   OBJECT IDENTIFIER ::= { mfrapStatus 7 }

mfrapStatusDteMode   OBJECT-TYPE
     SYNTAX  INTEGER
     {
        no-connections (1),
        active         (2),
        test           (3)
     }
     ACCESS  read-only
     STATUS  mandatory
     DESCRIPTION
      "Status of allocation of T1 bandwidth to the DTE port data. 
      (1) no connections - indicates the DTE port has no connections 
        to the WAN. 
      (2) Active - indicates DTE data rate has been assigned T1 DS0s
          and is in a normal data mode.
      (3) Test -  indicates DTE data rate has been assigned T1 DS0s
          but is in a diagnostic condition."
     ::= { mfrapStatusDteTable 1 }

mfrapStatusDteRts   OBJECT-TYPE
     SYNTAX  INTEGER
     {
        on  (1),
        off (2)
     }
     ACCESS  read-only
     STATUS  mandatory
     DESCRIPTION
        "Status of the Request to Send (RTS) signal from the DTE port.
         (1) RTS Active
         (2) RTS Inactive"
     ::= { mfrapStatusDteTable 2 }

mfrapStatusDteDtr   OBJECT-TYPE
     SYNTAX  INTEGER
     {
        on  (1),
        off (2)
     }
     ACCESS  read-only
     STATUS  mandatory
     DESCRIPTION
        "Status of the Data Terminal Ready (DTR) signal from the DTE port.
         (1) DTR Active
         (2) DTR Inactive"
     ::= { mfrapStatusDteTable 3 }

mfrapStatusDteDcd OBJECT-TYPE
     SYNTAX      INTEGER
     {
          on   (1),
          off  (2),
          na   (3)
     }
     ACCESS      read-only
     STATUS      mandatory
     DESCRIPTION
        "Status of the Data Carrier Detect (DCD) signal driven by this
         unit towards the DTE port
         (1) DCD Active
         (2) DCD Inactive"
     ::= { mfrapStatusDteTable 4  }

mfrapStatusDteDsr OBJECT-TYPE
     SYNTAX      INTEGER
     {
          on   (1),
          off  (2),
          na   (3)
     }
     ACCESS      read-only
     STATUS      mandatory
     DESCRIPTION
        "Status of the Data Set Ready (DSR) signal driven by this
         unit towards the DTE port.
         (1) DSR Active
         (2) DSR Inactive" 
     ::= { mfrapStatusDteTable 5 }

mfrapStatusDteCts OBJECT-TYPE
     SYNTAX      INTEGER
     {
          on   (1),
          off  (2),
          na   (3)
     }
     ACCESS      read-only
     STATUS      mandatory
     DESCRIPTION
        "Status of the Clear to Send (CTS) signal driven by this
         unit towards the DTE port
         (1) CTS Active
         (2) CTS Inactive"
     ::= { mfrapStatusDteTable 6 }

--
--      Drop & Insert Status 
--
--         The current status of the D&I port.
--
mfrapStatusDandiTable   OBJECT IDENTIFIER ::= { mfrapStatus 15 }

mfrapStatusDandiMode   OBJECT-TYPE
     SYNTAX  INTEGER
     {
        no-connections (1),
        active         (2),
        test           (3)
     }
     ACCESS  read-only
     STATUS  mandatory
     DESCRIPTION
        "Status of allocation of T1 DS0s to the Drop & Insert port DS0s. 
         (1) no connections - indicates the Drop & Insert port has no 
           connections to the WAN. 
         (2) Active - indicates that at least one Drop & Insert DS0 
           has been assigned to a T1 DS0.
         (3) Test -  indicates that at least one Drop & Insert DS0 
           has been assigned to a T1 DS0 but is in a diagnostic condition."
     ::= { mfrapStatusDandiTable 4 }

mfrapStatusDandiStatus   OBJECT-TYPE
     SYNTAX  INTEGER
     {
        t1-frame-sync-okay                (1),
        t1-frame-sync-with-errors         (2),
        signal-present-without-frame-sync (3),
        signal-not-present                (4), 
        not-applicable                    (5)
     }
     ACCESS  read-only
     STATUS  mandatory
     DESCRIPTION
      "Status of the signal received from the Drop & Insert port.
       (1) In Sync - unit has detected a properly framed T1 signal
           and is not experiencing any error conditions.
       (2) In Sync with Errors - unit has detected a properly framed 
           T1 signal but is experiencing some error conditions. Refer to
           T1 current performance results for details.
       (3) Signal Detected without Frame Sync - while a signal is present
           from the Drop & Insert port, it does not contain the framing 
           pattern defined for this unit. This could be either incorrectly 
           configured T1 Frame type or the presence of an alarm condition 
           on the network.
       (4) No Carrier - there is no signal detected from the WAN.
       (5) Not Applicable."
     ::= { mfrapStatusDandiTable 5 }

mfrapStatusDandiAlarms   OBJECT-TYPE
     SYNTAX  INTEGER
     {
        no-alarms                  (1),
        red-alarm-declared         (2), 
        yellow-alarm-detected      (3),
        unframed-all-ones-detected (4)
     }
     ACCESS  read-only
     STATUS  mandatory
     DESCRIPTION
        "Alarms present at the T1 port.
         (1) No alarm conditions present.
         (2) Red Alarm Declared - Unit has experienced loss of frame 
             synchronization with the signal received from the Drop
             & Insert port for an extended time and is reporting an 
             alarm condition that severely impairs normal operation. 
             During this Red Alarm condition the unit will transmit 
             Yellow alarm back to the Drop & Insert port. If this 
             condition persists consult your service provider.
         (3) Yellow ALarm Detected - Unit is receiving a yellow alarm 
             indication from the Drop & Insert port. Detection of yellow 
             alarm implies that the attached device is in a red alarm 
             conditon. Red alarm is declared due to the extended absence 
             of a properly framed signal. If this condition persists 
             consult your service provider.
         (4) Unframe All Ones Detected - Unit is receiving unframed all 
             ones from the Drop & Insert port (AIS, blue alarm). Detection 
             of AIS implies that the attached device is reporting
             an alarm condition from an upstream device. If 
             this condition persists consult your service provider."
     ::= { mfrapStatusDandiTable 6 }

--
--      LED Status 
--
--         The current status of the front-panel LED indicators at 
--         the MFRAP node.
--

mfrapStatusLedTable   OBJECT IDENTIFIER ::= { mfrapStatus 4 }

mfrapStatusDteModeLED   OBJECT-TYPE
     SYNTAX  INTEGER
     {
        offLED-DTE-inactive               (1),
        greenLED-normal                   (2),
        yellowLED-test-mode               (3),
        redLED-no-active-WAN-connection   (4)
     }
     ACCESS  read-only
     STATUS  mandatory
     DESCRIPTION
        "Status of the DTE Mode LED.
         (1) DTE Mode LED off: Missing control signals
         (2) DTE Mode LED green: Normal
         (3) DTE Mode LED yellow: Test Mode"
     ::= { mfrapStatusLedTable 1 }

mfrapStatusDteStatusLED   OBJECT-TYPE
     SYNTAX  INTEGER
     {
        offLED-inactive                   (1),
        greenLED-active                   (2)
     }
     ACCESS  read-only
     STATUS  mandatory
     DESCRIPTION
        "Status of the DTE Status LED.
         (1) DTE Status LED off: no connections to WAN
         (2) DTE Status LED green: normal"
     ::= { mfrapStatusLedTable 2 }

mfrapStatusDteTxLED   OBJECT-TYPE
     SYNTAX  INTEGER
     {
        offLED-inactive                   (1),
        greenLED-tx-data-transmitting     (2),
        yellowLED-disabled                (3)
     }
     ACCESS  read-only
     STATUS  mandatory
     DESCRIPTION
        "Status of the DTE Tx Data LED. In Frame Relay mode, this LED is ON 
         (green) when the DTE is not sending HDLC Flags and is OFF when
         HDLC flags are being transmit. In CBO mode, the LED is ON (green) 
         for a SPACE and OFF for a MARK.
         (1) DTE Transmit LED OFF: inactive (HDLC flags or CBO marks)
         (2) DTE Transmit LED ON: active (HDLC frames or CBO spaces)"
     ::= { mfrapStatusLedTable 3 }

mfrapStatusDteRxLED   OBJECT-TYPE
     SYNTAX  INTEGER
     {
        offLED-inactive                   (1),
        greenLED-rx-data-receiving        (2),
        yellowLED-disabled                (3)
     }
     ACCESS  read-only
     STATUS  mandatory
     DESCRIPTION
        "Status of the DTE Rx Data LED. In Frame Relay mode, this LED is ON 
         (green) when the WAN is receiving HDLC Flags and is OFF when
         HDLC flags are being received. In CBO mode, the LED is ON (green) 
         for a SPACE and OFF for a MARK.
         (1) DTE Receive LED OFF: inactive (HDLC flags or CBO marks)
         (2) DTE Receive LED ON: active (HDLC frames or CBO spaces)"
     ::= { mfrapStatusLedTable 4 }

mfrapStatusT1ModeLED   OBJECT-TYPE
     SYNTAX  INTEGER
     {
        greenLED-normal                   (2),
        yellowLED-test-mode               (3)
     }
     ACCESS  read-only
     STATUS  mandatory
     DESCRIPTION
      "Status of the WAN Mode LED.
       (1) WAN Mode LED is green: normal data mode
       (2) WAN Mode LED is yellow: test mode"
     ::= { mfrapStatusLedTable 5 }

mfrapStatusT1StatusLED   OBJECT-TYPE
     SYNTAX  INTEGER
     {
        offLED-T1-no-signal                     (1),
        greenLED-normal                         (2),
        yellowLED-remote-alarm                  (3),
        redLED-red-alarm                        (4),
        blinking-redLED-no-carrier-red-alarm    (5),
        blinking-red-greenLED-transient-error   (6),
        blinking-red-yellowLED-AIS              (7)
     }
     ACCESS  read-only
     STATUS  mandatory
     DESCRIPTION
        "Status of the WAN Status LED.
         (1) Off - no signal detected from WAN.
         (2) Green - framed signal detected with no errors (normal operation)
         (3) Yellow - remote alarm condition detected (yellow or AIS alarms)
         (4) Red - unit has declared Red Alarm due to the presence of an 
             improperly framed signal from the WAN.
         (5) Blinking Red and Off - unit has declared Red Alarm due to the
             absence of a signal from the WAN.
         (6) Blinking Green and Red - unit is receiving a properly framed signal
             from the WAN but has detected a transient error condition. Possible
             Line Code Violations or ESF CRC errors indicating errored data bits.
         (7) Blinking Red and Yellow - unit is receiving an unframed all ones (AIS)
             from the WAN. This is indicative of an upstream alarm condition on the 
             WAN."
     ::= { mfrapStatusLedTable 6 }

mfrapStatusAllLEDs   OBJECT-TYPE
     SYNTAX      DisplayString (SIZE (0..7))
     ACCESS  read-only
     STATUS  mandatory
     DESCRIPTION
      "Status of all six MFRAP LEDs, encoded in a string.
           'F'    off
           '5'    green
           '0'    yellow
           'A'    red
           '7'    blinking green and off
           '3'    blinking yellow and off
           'B'    blinking red and off
           '4'    blinking green and yellow
           '6'    blinking green and red
           '8'    blinking yellow and red

       Positionally, the 8 letters are DTE Mode, DTE status,
       Dte Tx, Dte Rx, PBX Mode, PBX Status, T1 Mode, and T1 Status.
       For example, '55555556' would mean:  DTE in normal mode, active status,
       transmitting and receiving PBX in normal mode with normal status and 
       T1 normal with transient errors."
     ::= { mfrapStatusLedTable 7 }


mfrapStatusDandiModeLED   OBJECT-TYPE
     SYNTAX  INTEGER
     {
        greenLED-normal                   (2),
        yellowLED-test-mode               (3)
     }
     ACCESS  read-only
     STATUS  mandatory
     DESCRIPTION
      "Status of the Drop & Insert Mode LED.
       (1) Drop & Insert Mode LED is green: normal data mode
       (2) Drop & Insert Mode LED is yellow: test mode"
     ::= { mfrapStatusLedTable 8 }

mfrapStatusDandiStatusLED   OBJECT-TYPE
     SYNTAX  INTEGER
     {
        offLED-Dandi-no-signal                  (1),
        greenLED-normal                         (2),
        yellowLED-remote-alarm                  (3),
        redLED-red-alarm                        (4),
        blinking-redLED-no-carrier-red-alarm    (5),
        blinking-red-greenLED-transient-error   (6),
        blinking-red-yellowLED-AIS              (7)
     }
     ACCESS  read-only
     STATUS  mandatory
     DESCRIPTION
        "Status of the Drop & Insert Status LED.
         (1) Off - no signal detected from Drop & Insert port.
         (2) Green - framed signal detected with no errors 
             (normal operation)
         (3) Yellow - remote alarm condition detected (yellow or 
             AIS alarms)
         (4) Red - unit has declared Red Alarm due to the presence 
             of an improperly framed signal from the Drop & Insert 
             port.
         (5) Blinking Red and Off - unit has declared Red Alarm due 
             to the absence of a signal from the Drop & Insert port.
         (6) Blinking Green and Red - unit is receiving a properly 
             framed signal from the Drop & Insert port but has detected 
             a transient error condition. Possible Line Code Violations 
             or ESF CRC errors indicating errored data bits.
         (7) Blinking Red and Yellow - unit is receiving an unframed 
             all ones (AIS) from the Drop & Insert port. This is 
             indicative of an upstream alarm condition on the 
             Drop & Insert port."
     ::= { mfrapStatusLedTable 9 }


--
--     Table of peers discovered by VNIP
--

mfrapVnipTopologyTable   OBJECT-TYPE
      SYNTAX   SEQUENCE OF MfrapVnipTopologyEntry
      ACCESS   not-accessible
      STATUS   mandatory
      DESCRIPTION
        "VNIP topology is a feature that, for each interface, maps all 
         compatible VNIP peers, their DLCI value, ip address and relative 
         location. The topology is a fundamental prerequisite to applying 
         the VNIP feature set which includes PVC-based delay measurement, 
         diagnostics, and congestion monitoring. With VNIP enabled on an 
         interface the unit will attempt to locate VNIP peers out that port.
         As peers are discovered and logged the unit will report the topology
         it has learned on its opposite interface. If VNIP is inactive on 
         one interface it will not engage in any VNIP dialog; however it 
         will continue to listen for topology messages on the inactive 
         interface and will reflect these messages out the opposite interface
         if VNIP is enabled. With VNIP inactive on both interfaces the unit 
         will transparently pass all VNIP messages. The topology database 
         includes the interface, local DLCI value, remote peer DLCI value, 
         remote peer ip address, and the number of VNIP hops in between.
         This table also reports the status of other VNIP features as well."
      ::= { mfrapStatus 2 }

      mfrapVnipTopologyEntry OBJECT-TYPE
          SYNTAX   MfrapVnipTopologyEntry
          ACCESS   not-accessible
          STATUS   mandatory
          DESCRIPTION
             "The DLCI, IP address, and number of hops
              for a particular peer, discovered off of
              an interface (DTE or T1)."
         INDEX { mfrapVnipTopologyInterface, mfrapVnipTopologyIndex }
         ::= { mfrapVnipTopologyTable 1 }

      MfrapVnipTopologyEntry ::=
          SEQUENCE {
              mfrapVnipTopologyInterface          INTEGER,
              mfrapVnipTopologyIndex              INTEGER,
              mfrapVnipTopologyDlci               INTEGER,
              mfrapVnipTopologyIpAddr             IpAddress,
              mfrapVnipTopologyNumHops            INTEGER,
              mfrapVnipTopologyLocalDlci          INTEGER,
              mfrapVnipTopoTDNumSamples           Counter,
              mfrapVnipTopoTDAvgDelay             Counter,
              mfrapVnipTopoTDMaxDelay             Counter,
              mfrapVnipTopoTDMinDelay             Counter,
              mfrapVnipTopoTDLastDelay            Counter,
              mfrapVnipTopoVLOOPStatus            INTEGER,
              mfrapVnipTopoVBERTStatus            INTEGER,
              mfrapVnipTopoVBertTxDESetFrames     Counter,
              mfrapVnipTopoVBertRxDESetFrames     Counter,
              mfrapVnipTopoVBertTxDEClrFrames     Counter,
              mfrapVnipTopoVBertRxDEClrFrames     Counter,
              mfrapVnipTopoVBertTransitDelayMax   Counter,
              mfrapVnipTopoVBertTransitDelayAvg   Counter,
              mfrapVnipTopoVBertTimeElapse        TimeTicks,
              mfrapVnipTopoVBertPerUtilCIR        INTEGER,
              mfrapVnipTopoVBertPerUtilEIR        INTEGER
          }

      mfrapVnipTopologyInterface OBJECT-TYPE
          SYNTAX      INTEGER
          {
               dte-interface (1),
               t1-interface (2)
          }
          ACCESS      read-only
          STATUS      mandatory
          DESCRIPTION
             "The interface off of which the peer was
              discovered.  Topology is discovered by
              sending VNIP messages out each interface.
              Units discovered via a particular interface
              are kept in a list associated with that
              interface.
              (1) VNIP peers and status out DTE interface
              (2) VNIP peers and status out WAN interface"
          ::= { mfrapVnipTopologyEntry 1 }

      mfrapVnipTopologyIndex OBJECT-TYPE
          SYNTAX      INTEGER
          ACCESS      read-only
          STATUS      mandatory
          DESCRIPTION
             "The number of this discovered peer in the list
              of nodes for this interface. For each interface,
              the nodes are numbered 1 through n. This index
              is required when disabling or enabling VBERT/VLOOP
              to a particular peer."
          ::= { mfrapVnipTopologyEntry 2 }

      mfrapVnipTopologyDlci    OBJECT-TYPE
          SYNTAX      INTEGER 
          ACCESS      read-only
          STATUS      mandatory
          DESCRIPTION
            "The DLCI of the discovered neighboring peer.
             This may be different from the local DLCI."
         ::= { mfrapVnipTopologyEntry 3 }

      mfrapVnipTopologyIpAddr   OBJECT-TYPE
          SYNTAX      IpAddress
          ACCESS      read-only
          STATUS      mandatory
          DESCRIPTION
             "The IP address for the discovered peer."
          ::= { mfrapVnipTopologyEntry 4 }
 
      mfrapVnipTopologyNumHops OBJECT-TYPE
          SYNTAX      INTEGER
          ACCESS      read-only
          STATUS      mandatory
          DESCRIPTION
             "The discovered peer is this number of hops away. 
              Each hop is a VNIP peer."
          ::= { mfrapVnipTopologyEntry 5 }
 
      mfrapVnipTopologyLocalDlci OBJECT-TYPE
          SYNTAX      INTEGER
          ACCESS      read-only
          STATUS      mandatory
          DESCRIPTION
            "The DLCI of this node over which the neighboring peer
             was discovered."
          ::= { mfrapVnipTopologyEntry 6 }

      mfrapVnipTopoTDNumSamples  OBJECT-TYPE
          SYNTAX      Counter
          ACCESS      read-only
          STATUS      mandatory
          DESCRIPTION
            "The number of transit delay samples collected."
          ::= { mfrapVnipTopologyEntry 10 }

      mfrapVnipTopoTDAvgDelay  OBJECT-TYPE
          SYNTAX      Counter
          ACCESS      read-only
          STATUS      mandatory
          DESCRIPTION
             "The average transit delay between this
              unit and the remote peer (in milliseconds)."
          ::= { mfrapVnipTopologyEntry 11 }

      mfrapVnipTopoTDMaxDelay  OBJECT-TYPE
          SYNTAX      Counter
          ACCESS      read-only
          STATUS      mandatory
          DESCRIPTION
            "The maximum transit delay between this
             node and the remote peer (in milliseconds)."
          ::= { mfrapVnipTopologyEntry 12 }

      mfrapVnipTopoTDMinDelay  OBJECT-TYPE
          SYNTAX      Counter
          ACCESS      read-only
          STATUS      mandatory
          DESCRIPTION
            "The minimum transit delay between this
             node and the remote peer (in milliseconds)."
          ::= { mfrapVnipTopologyEntry 13 }

      mfrapVnipTopoTDLastDelay  OBJECT-TYPE
          SYNTAX      Counter
          ACCESS      read-only
          STATUS      mandatory
          DESCRIPTION
            "The most recent transit delay measured between
             this node and the remote peer (in milliseconds)."
          ::= { mfrapVnipTopologyEntry 14 }

      mfrapVnipTopoVLOOPStatus   OBJECT-TYPE
          SYNTAX      INTEGER
          {
               loopback-enable (1),
               loopback-disable (2)
          }
          ACCESS      read-only
          STATUS      mandatory
          DESCRIPTION
             "This selection displays the status of the VNIP PVC
              Loopback for this entry. This loopback is initiated 
              by the remote node through the VLOOP utility, causing 
              this node to loop data back to the remote node.
              (1) Virtual Loopback path present on this PVC due to
                  command received from remote unit. All data received
                  on this DLCI will be looped back out the same interface.
              (2) No active VLOOP test on this"
          ::= { mfrapVnipTopologyEntry  15 }
      
      mfrapVnipTopoVBERTStatus  OBJECT-TYPE
          SYNTAX      INTEGER
          {
               off            (1),
               testing        (2),
               test-failed    (3),
               test-completed (4),
               in-test        (5)
      
          }
          ACCESS      read-only
          STATUS      mandatory
          DESCRIPTION
             "Displays the current status of the VBERT/VLOOP test.
              (1) Off: no test has run or the entry has been cleared
              (2) Testing: the entry is generating VBERT test frames
              (3) Test Failed: the request for a test on this entry failed  
              (4) Test Completed: a test has run and is finished results 
                  are complete
              (5) In Test: the entry is on the receiving end of VBERT packets"
          ::= { mfrapVnipTopologyEntry 16 }

      mfrapVnipTopoVBertTxDESetFrames   OBJECT-TYPE
          SYNTAX      Counter
          ACCESS      read-only
          STATUS      mandatory
          DESCRIPTION
             "Displays the number of Frames transmitted during VBERT Test that
              had the Discard Eligibility indicator bit set."
          ::= { mfrapVnipTopologyEntry  17 }
      
      
      mfrapVnipTopoVBertRxDESetFrames OBJECT-TYPE
          SYNTAX      Counter
          ACCESS      read-only
          STATUS      mandatory
          DESCRIPTION
             "Displays the number of Frames received during VBERT Test that 
              had the Discard Eligibility indicator bit set."
          ::= { mfrapVnipTopologyEntry  18 }
      
      
      
      mfrapVnipTopoVBertTxDEClrFrames   OBJECT-TYPE
          SYNTAX      Counter
          ACCESS      read-only
          STATUS      mandatory
          DESCRIPTION
             "Displays the number of Frames transmitted during VBERT Test that
              had the Discard Eligibility indicator bit cleared."
          ::= { mfrapVnipTopologyEntry  19 }
      
      
      mfrapVnipTopoVBertRxDEClrFrames OBJECT-TYPE
          SYNTAX      Counter
          ACCESS      read-only
          STATUS      mandatory
          DESCRIPTION
             "Displays the number of Frames received during VBERT Test that 
              had the Discard Eligibility indicator bit cleared."
          ::= { mfrapVnipTopologyEntry  20 }
      
      mfrapVnipTopoVBertTransitDelayMax OBJECT-TYPE
          SYNTAX      Counter
          ACCESS      read-only
          STATUS      mandatory
          DESCRIPTION
             "The maximum transit delay between this node and the 
              remote peer during the VBERT test. This delay measurement
              will include internal device latencies. This result may
              differ from the VNIP transit delay measurement which accounts
              for internal latencies."
          ::= { mfrapVnipTopologyEntry  21 }
      
       
      mfrapVnipTopoVBertTransitDelayAvg OBJECT-TYPE
          SYNTAX      Counter
          ACCESS      read-only
          STATUS      mandatory
          DESCRIPTION
             "The average transit delay between this node and the remote 
              peer during the VBERT test. This delay measurement
              will include internal device latencies. This result may
              differ from the VNIP transit delay measurement which accounts
              for internal latencies"
          ::= { mfrapVnipTopologyEntry  22 }
      
      mfrapVnipTopoVBertTimeElapse OBJECT-TYPE
          SYNTAX      TimeTicks
          ACCESS      read-only
          STATUS      mandatory
          DESCRIPTION
             "Elapsed time since VBERT/VLOOP test was started or cleared
              (in seconds)."
          ::= { mfrapVnipTopologyEntry  23 }
      
      mfrapVnipTopoVBertPerUtilCIR OBJECT-TYPE
          SYNTAX      INTEGER
          ACCESS      read-only
          STATUS      mandatory
          DESCRIPTION
             " The calculated percent of CIR utilization during a VBERT test,
               this value is only valid after a test is complete not during."
          ::= { mfrapVnipTopologyEntry 24 }


      mfrapVnipTopoVBertPerUtilEIR OBJECT-TYPE
          SYNTAX      INTEGER
          ACCESS      read-only
          STATUS      mandatory
          DESCRIPTION
             " The calculated percent of EIR utilization during a VBERT test,
               this value is only valid after a test is complete not during."
          ::= { mfrapVnipTopologyEntry 25 }


mfrapVnipTransitDelayClear    OBJECT-TYPE
          SYNTAX      INTEGER
          {
              clear-transit-delay (1)
          }
          ACCESS      write-only
          STATUS      mandatory
          DESCRIPTION
             "Allows the user to clear all the VNIP Transit Delay
              data collected in the VNIP topology database.
              (1) Clear entire Transit Delay results database"
          ::= { mfrapStatus 5 }

mfrapLmiSourcing OBJECT-TYPE
         SYNTAX      INTEGER
         {
              initializing (1),
              passthrough  (2),
              user-dte     (3),
              user-t1      (4),
              network-dte  (5),
              network-t1   (6),
              disabled     (7),
              both-ports   (8)
         }
         ACCESS      read-only
         STATUS      mandatory
         DESCRIPTION
            "If configured for Frame Relay with a non-zero LMI inactivity timer
             the unit will monitor the status of LMI and, if proper messaging
             is not detected, will attempt to emulate either Frame Relay DTE or 
             DCE devices in attempt to restore LMI to any attached equipment and 
             provide managed access for diagnostic purposes. Typically frads/routers 
             are Frame Relay DTE while switches are Frame Relay DCE but this model
             may vary. In the absence of full-duplex LMI, the unit will cycle 
             through various states in attempt to adapt to an LMI partner.  The 
             unit will try each state for the duration of the LMI Inactivity timer 
             and then advance to the next one if satisfactory handshaking is not 
             established. While in any of these states if full-duplex LMI handshaking 
             does appear, the unit will immediately revert to the passthrough state.
             (1) initializing
             (2) Passthrough: not sourcing any LMI messages.
             (3) Status Enquiries out DTE interface: unit is emulating a Frame 
                 Relay DTE device out the its (physical) DTE interface. 
             (4) Status Enquiries out WAN interface: unit is emulating a Frame 
                 Relay DTE device out the its WAN interface.
             (5) Status Responses out the DTE interface: unit is emulating a 
                 Frame Relay DCE device out the its (physical) DTE interface
                 (provisioning the single default management DLCI).
             (6) Status Responses out the WAN interface: unit is emulating a 
                 Frame Relay DCE device out the its WAN interface (provisioning 
                 the single default management DLCI).
             (7) Disabled - LMI Inactivity timer is zero or unit not configured
                 for a Frame Relay application.
             (8) Status Responses out both DTE and WAN interfaces: unit is 
                 configured for Fixed DCE mode of management and emulates a Frame
                 Relay DCE independently on both ports (provisioning 
                 the single default management DLCI)."
         ::= { mfrapStatus 6 }


--
--      Management Status 
--
--         The current status of the InBand Mangement configuration. 
--         This section is intended to display information of how the MFRAP
--         is configured for InBand Management.
--
mfrapStatusMgmtTable   OBJECT IDENTIFIER ::= { mfrapStatus 3 }

mfrapStatusMgmtChannel   OBJECT-TYPE
     SYNTAX  INTEGER
     {
        none             (1),
        slip             (2), 
        private-dlci     (3),
        piggyback-dlci   (4)
     }
     ACCESS  read-only
     STATUS  mandatory
     DESCRIPTION
        "This is the method in which the unit is configured for
         SNMP management access.
         (1) None: SNMP management disabled
         (2) SLIP: out-of-band management via asynchronous Serial Line IP
         (3) Private DLCI: in-band management using a private DLCI that 
             is dedicated solely to this unit's management.
         (4) Piggyback DLCI: in-band management using any DLCI optionally
             multiplexing both management and user data."
    ::= {mfrapStatusMgmtTable 1}                

mfrapStatusMgmtInterface   OBJECT-TYPE
     SYNTAX  INTEGER
     {
        comm            (1),
        dte             (2), 
        t1              (3),
        dte-and-t1      (4)
     }
     ACCESS  read-only
     STATUS  mandatory
     DESCRIPTION
        "This is the port(s) on which the management traffic will appear.
         (1) Async Maintenance(Comm)/Console port - SLIP mode
         (2) Local DTE interface: unit is configured for Private Local 
             DLCI mode
         (3) Remote WAN Interface: unit is confiogured for Private Remote
             DLCI mode
         (4) DTE and WAN Interfaces: unit is configured for either Piggyback
             Bidirectional mode."
     ::= {mfrapStatusMgmtTable 2}                

mfrapStatusMgmtInterfaceStatus   OBJECT-TYPE
     SYNTAX  INTEGER
     {
        active     (1),
        inactive   (2), 
        alarm      (3)
     }
     ACCESS  read-only
     STATUS  mandatory
     DESCRIPTION
        "This is the status of the port(s) on which
         the management traffic will appear.
         (1) Active: port or DLCI is configured and status is okay
         (2) Inactive: port or DLCI is declared out of service 
         (3) Alarm: port or DLCI is experiencing an alarm condition that may
             interefere with management access  "
     ::= {mfrapStatusMgmtTable 3}                

mfrapStatusMgmtDefaultDLCINo   OBJECT-TYPE
     SYNTAX  INTEGER
     ACCESS  read-only
     STATUS  mandatory
     DESCRIPTION
        "This is the DLCI for the PVC that is defined for the
        Management port.  All traffic using this DLCI in the Frame
        Replay packet will be destined for the InBand Management task."
     ::= {mfrapStatusMgmtTable 4}                

mfrapStatusMgmtDefaultDLCIStatus   OBJECT-TYPE
     SYNTAX  INTEGER
     {
        na              (1),
        dlci-active     (2), 
        dlci-inactive   (3)
     }
     ACCESS  read-only
     STATUS  mandatory
     DESCRIPTION
        "This is the status of the default management DLCI.
         (1) not applicable: SLIP mode or management is disabled
         (2) DLCI Active: default DLCI is active in the LMI full 
             status response.
         (3) DLCI Inactive: default DLCI is not active in the LMI full 
             status response."
     ::= {mfrapStatusMgmtTable 5}                

mfrapStatusLmiAutosense   OBJECT-TYPE
     SYNTAX  INTEGER
     {
        disabled            (1),
        searching           (2),
        learned-annex-d     (3),
        learned-annex-a     (4),
        learned-type1       (5)
     }
     ACCESS  read-only
     STATUS  mandatory
     DESCRIPTION
        "This indicates the current status of LMI Auto Sensing if 
         it's enabled.
         (1) Disabled: LMI is configured as Type 1, Annex-D, or Annex-A
         (2) Searching: unit is attempting to determine the LMI type of
             the attached equipment by issuing LMI messages of each LMI 
             type and searching for responses.
         (3) Learned Annex-D: unit has successfully detected Annex-D LMI
             (ANSI T1.617 Annex D)
         (4) Learned Annex-A: unit has successfully detected Annex-A LMI
             (ITU/CCITT Q.933 Annex A)
         (5) Learned Type 1: unit has successfully detected Type 1 LMI
             (Cisco, Group of four, LMI)"
     ::= { mfrapStatus 12 }

--
--      Nest Status
--         The current status of the chasis containing the MFRAP
--
mfrapStatusNestTable   OBJECT IDENTIFIER ::= { mfrapStatus 14 }

mfrapStatusNestFanOne  OBJECT-TYPE
     SYNTAX  INTEGER
     {
        fan-ok    (1),
        fan-alarm (2),
        na        (3)
     }
     ACCESS  read-only
     STATUS  mandatory
     DESCRIPTION
       "The status of the chasis fan 1.
       (1) Fan is operating normally
       (2) Fan is in alarm state
       (3) Fan alarm is not applicable"
    ::= {mfrapStatusNestTable 1}

mfrapStatusNestFanTwo  OBJECT-TYPE
     SYNTAX  INTEGER
     {
        fan-ok    (1),
        fan-alarm (2),
        na        (3)
     }
     ACCESS  read-only
     STATUS  mandatory
     DESCRIPTION
       "The status of the chasis fan 2.
       (1) Fan is operating normally
       (2) Fan is in alarm state
       (3) Fan alarm is not applicable"
    ::= {mfrapStatusNestTable 2}

mfrapStatusNestPowerSupply  OBJECT-TYPE
     SYNTAX  INTEGER
     {
        power-supply-ok     (1),
        power-supply-alarm  (2),
        power-supply-na     (3)
     }
     ACCESS  read-only
     STATUS  mandatory
     DESCRIPTION
       "The status of the chasis power supply.
       (1) The nest power supply is operating
           normally
       (2) The nest power supply is in alarm 
           state
       (3) A standalone unit will return 'na' "
    ::= {mfrapStatusNestTable 3}

mfrapStatusNestSlotId  OBJECT-TYPE
     SYNTAX  INTEGER  (0..16)
     ACCESS  read-only
     STATUS  mandatory
     DESCRIPTION
       "The chassis slot number (1-16) occupied by the MFRAP 
        nest card. A standalone unit will return a '0'.
        "
    ::= {mfrapStatusNestTable 4}


-- =========================
-- ==  PERFORMANCE group  ==
-- =========================

mfrapPerformance  OBJECT IDENTIFIER ::= { mfrap 5 }

mfrapPerfPhysicalIntf OBJECT IDENTIFIER ::= { mfrapPerformance 1 }

--
--      T1 Current Performance Table
--       The T1 current performance table contains various statistics 
--       being collected for the current 15 minute interval.

mfrapPerfT1CurrentTable OBJECT-TYPE
     SYNTAX  SEQUENCE OF MfrapT1CurrentEntry
     ACCESS  not-accessible
     STATUS  mandatory
     DESCRIPTION
        "The T1 physical layer performance numbers for the current  
        15 minute interval. These are defined and accumulated per 
        ANSI specification T1.403 and AT&T publication 54016. Depending
        upon the configured T1 Framing mode, these results may be 
        retrieved via ESF facility data link by service personnel."
     ::= { mfrapPerfPhysicalIntf 1 }

mfrapT1CurrentEntry OBJECT-TYPE
     SYNTAX  MfrapT1CurrentEntry
     ACCESS  not-accessible
     STATUS  mandatory
     DESCRIPTION
        "An entry in the T1 Current Perf table."
     INDEX   { mfrapT1CurrentIndex }
     ::= { mfrapPerfT1CurrentTable 1 }

MfrapT1CurrentEntry ::=
     SEQUENCE {
        mfrapT1CurrentIndex       INTEGER,
        mfrapT1CurrentCrc6Events  Gauge,
        mfrapT1CurrentOofEvents   Gauge,
        mfrapT1CurrentESs         Gauge,
        mfrapT1CurrentSESs        Gauge,
        mfrapT1CurrentSEFSs       Gauge,
        mfrapT1CurrentUASs        Gauge,
        mfrapT1CurrentCSSs        Gauge,
        mfrapT1CurrentBESs        Gauge,
        mfrapT1CurrentLCVs        Gauge
     }

mfrapT1CurrentIndex OBJECT-TYPE
     SYNTAX  INTEGER (1..4)
     ACCESS  read-only
     STATUS  mandatory
     DESCRIPTION
        "The index value which uniquely identifies the
         T1 interface to which this entry is applicable.
         The Drop & Index port has its own Current
         Performance Table, so the index will always be 1."
     ::= { mfrapT1CurrentEntry 1 }

mfrapT1CurrentCrc6Events OBJECT-TYPE
     SYNTAX  Gauge
     ACCESS  read-only
     STATUS  mandatory
     DESCRIPTION
        "Count of CRC errors detected on an ESF framed circuit.
        In ESF framing a CRC is generated at the source, based upon 
        the composite data. A CRC error indicates the presence of
        at least one bit error in an ESF superframe. This field is 
        a free-running accumulation of CRC errors and IS NOT reset 
        when the current 15 minute interval expires. It can be reset 
        with the performance command mfrapT1PerfClearEvents. 
        Not applicable if D4/SF framing is selcted."
     ::= { mfrapT1CurrentEntry 2 }

mfrapT1CurrentOofEvents OBJECT-TYPE
     SYNTAX  Gauge
     ACCESS  read-only
     STATUS  mandatory
     DESCRIPTION
        "Count of Out-of-Frame events on a T1 circuit. An out-of-
        frame event occurs when the frame synchronization criteria
        is lost and a resynchronization must occur. Data is interrupted
        during frame resynchronization. This field is a free-running 
        accumulation of OOF transitions and IS NOT reset when the 
        current 15 minute interval expires. It can be reset with the 
        performance command mfrapT1PerfClearEvents." 
     ::= { mfrapT1CurrentEntry 3 }

mfrapT1CurrentESs OBJECT-TYPE
     SYNTAX  Gauge
     ACCESS  read-only
     STATUS  mandatory
     DESCRIPTION
        "The number of Errored Seconds, encountered  by
        a T1 interface in the current 15 minute inter-
        val. An errored second is a one-second interval with
        CRC errors or a loss of frame sync occurred."
     ::= { mfrapT1CurrentEntry 4 }

mfrapT1CurrentSESs OBJECT-TYPE
     SYNTAX  Gauge
     ACCESS  read-only
     STATUS  mandatory
     DESCRIPTION
        "The number of Severely Errored Seconds encountered by
         a t1 interface in the current 15 minute interval. A
         severely errored second is a one second interval with
         more than 320 CRC errors or one or more frame sync losses."
     ::= { mfrapT1CurrentEntry 5 }

mfrapT1CurrentSEFSs OBJECT-TYPE
     SYNTAX  Gauge
     ACCESS  read-only
     STATUS  mandatory
     DESCRIPTION
        "The number of Severely Errored Framing Seconds
        encountered by a t1 interface in the current
        15 minute interval. A SEFS is a one second interval
        with one or more frame sync losses."
     ::= { mfrapT1CurrentEntry 6 }

mfrapT1CurrentUASs OBJECT-TYPE
     SYNTAX  Gauge
     ACCESS  read-only
     STATUS  mandatory
     DESCRIPTION
        "The number of Unavailable Seconds  encountered
        by a t1 interface in the current 15 minute in-
        terval. A UAS is a one second interval during which 
        the received signal is classified as 'unavailable due
        to excessive errors'. A signal is unavailable after
        receiving ten consective severely errored seconds and
        stays unavailable until ten seconds without a severely
        errored second occur."
     ::= { mfrapT1CurrentEntry 7 }

mfrapT1CurrentCSSs OBJECT-TYPE
     SYNTAX  Gauge
     ACCESS  read-only
     STATUS  mandatory
     DESCRIPTION
        "The number of Controlled Slip Seconds encoun-
        tered by a t1 interface in the current 15
        minute interval. A controlled slip is the 
        replication or deletion of a T1 frame at the receiver.
        These events often indicate a T1 network timing 
        problem."
     ::= { mfrapT1CurrentEntry 8 }

mfrapT1CurrentBESs OBJECT-TYPE
     SYNTAX Gauge
     ACCESS read-only
     STATUS mandatory
     DESCRIPTION
        "The number of Bursty  Errored  Seconds  (BESs)
        encountered  by  a DS1 interface in the current
        15 minute interval. A BES is a one second interval
        with more than one and less than 320 CRC errors."
     ::= {mfrapT1CurrentEntry 9 }

mfrapT1CurrentLCVs OBJECT-TYPE
     SYNTAX Gauge
     ACCESS read-only
     STATUS mandatory
     DESCRIPTION
        "The number of Line Code Violations (LCVs)  en-
        countered  by a DS1 interface in the current 15
        minute interval. LCVs are non-B8ZS related
        violations of the alternate mark inversion protocol.
        An excessive count usually indicates a B8ZS/AMI
        configuration mismatch in the T1 network."
     ::= {mfrapT1CurrentEntry 10 }


--      T1 Performance Intervals
--      The T1 Interval Table contains various statistics
--      collected by each T1 Interface over the previous 24 hours of
--      operation.  The past 24 hours are broken into 96 completed
--      15 minute intervals.

mfrapPerfT1IntervalTable OBJECT-TYPE
     SYNTAX  SEQUENCE OF MfrapT1IntervalEntry
     ACCESS  not-accessible
     STATUS  mandatory
     DESCRIPTION
        "The DS1 Interval table. A history of physical layer performance 
         results are maintained and represented as 96 15-minute intervals.
         These are defined and accumulated per  ANSI specification T1.403 
         and AT&T publication 54016. Depending upon the configured T1 
         Framing mode, these results may be retrieved via ESF facility data 
         link by service personnel"
     ::= { mfrapPerfPhysicalIntf 2 }

mfrapT1IntervalEntry OBJECT-TYPE
     SYNTAX  MfrapT1IntervalEntry
     ACCESS  not-accessible
     STATUS  mandatory
     DESCRIPTION
        "An entry in the DS1 Interval table."
     INDEX   { mfrapT1IntervalIndex, mfrapT1IntervalNumber }
     ::= { mfrapPerfT1IntervalTable 1 }

MfrapT1IntervalEntry ::=
     SEQUENCE {
         mfrapT1IntervalIndex  INTEGER,
         mfrapT1IntervalNumber INTEGER,
         mfrapT1IntervalESs    Gauge,
         mfrapT1IntervalSESs   Gauge,
         mfrapT1IntervalSEFSs  Gauge,
         mfrapT1IntervalUASs   Gauge,
         mfrapT1IntervalCSSs   Gauge,
         mfrapT1IntervalBESs   Gauge,
         mfrapT1IntervalLCVs   Gauge
      }
      
mfrapT1IntervalIndex OBJECT-TYPE
     SYNTAX  INTEGER (1..4)
     ACCESS  read-only
     STATUS  mandatory
     DESCRIPTION
        "The index value which uniquely identifies the
         t1 interface to which this entry is applicable.
         Since there is a separate Drop & Insert Performance 
         Intervals Table, the value of this index will
         always be 1, referring to the WAN port." 
     ::= { mfrapT1IntervalEntry 1 }


mfrapT1IntervalNumber OBJECT-TYPE
     SYNTAX  INTEGER (1..96)
     ACCESS  read-only
     STATUS  mandatory
     DESCRIPTION
        "A number between 1 and 96, where 96 is the most
        recently completed 15 minute interval and 1 is
        the least recently completed 15 minutes  inter-
        val which occured 24 hours ago (assuming that all 
        96 intervals are valid)."
     ::= { mfrapT1IntervalEntry 2 }

mfrapT1IntervalESs OBJECT-TYPE
     SYNTAX  Gauge
     ACCESS  read-only
     STATUS  mandatory
     DESCRIPTION
        "The number of Errored Seconds encountered by a
        t1 interface in one of the previous 96, indi-
        vidual 15 minute, intervals. An errored second is 
        a one-second interval with CRC errors or a loss 
        of frame sync occurred."
     ::= { mfrapT1IntervalEntry 3 }


mfrapT1IntervalSESs OBJECT-TYPE
     SYNTAX  Gauge
     ACCESS  read-only
     STATUS  mandatory
     DESCRIPTION
        "The number of Severely Errored Seconds encoun-
        tered by a t1 interface in one of the previous
        96, individual 15 minute, intervals. A severely 
        errored second is a one second interval with more 
        than 320 CRC errors or one or more frame sync losses."
     ::= { mfrapT1IntervalEntry 4 }


mfrapT1IntervalSEFSs OBJECT-TYPE
     SYNTAX  Gauge
     ACCESS  read-only
     STATUS  mandatory
     DESCRIPTION
        "The number of Severely Errored Framing Seconds
        encountered  by  a  t1 interface in one of the
        previous 96, individual 15 minute, intervals.
        A SEFS is a one second interval with one or more 
        frame sync losses."
     ::= { mfrapT1IntervalEntry 5 }


mfrapT1IntervalUASs OBJECT-TYPE
     SYNTAX  Gauge
     ACCESS  read-only
     STATUS  mandatory
     DESCRIPTION
        "The number of Unavailable Seconds  encountered
        by  a  t1 interface in one of the previous 96,
        individual 15 minute, intervals. A UAS is a one second 
        interval during which the received signal is classified 
        as 'unavailable due to excessive errors'. A signal is 
        unavailable after receiving ten consective severely 
        errored seconds and stays unavailable until ten seconds 
        without a severely errored second occur."
     ::= { mfrapT1IntervalEntry 6 }

mfrapT1IntervalCSSs OBJECT-TYPE
     SYNTAX  Gauge
     ACCESS  read-only
     STATUS  mandatory
     DESCRIPTION
        "The number of Controlled Slip Seconds  encoun-
        tered by a t1 interface in one of the previous
        96, individual 15 minute, intervals. A controlled 
        slip is the replication or deletion of a T1 frame 
        at the receiver. These events often indicate a T1 
        network timing problem."
     ::= { mfrapT1IntervalEntry 7 }

mfrapT1IntervalBESs OBJECT-TYPE
     SYNTAX Gauge
     ACCESS read-only
     STATUS mandatory
     DESCRIPTION
        "The number of Bursty  Errored  Seconds  (BESs)
        encountered  by  a  t1 interface in one of the
        previous 96, individual 15 minute, intervals.
        A BES is a one second interval with more than one 
        and less than 320 CRC errors."
     ::= {mfrapT1IntervalEntry 8 }

mfrapT1IntervalLCVs OBJECT-TYPE
     SYNTAX Gauge
     ACCESS read-only
     STATUS mandatory
     DESCRIPTION
        "The number of Line Code Violations (LCVs)  en-
        countered  by a DS1 interface in the current 15
        minute interval. LCVs are non-B8ZS related
        violations of the alternate mark inversion protocol.
        An excessive count usually indicates a B8ZS/AMI
        configuration mismatch in the T1 network."
     ::= {mfrapT1IntervalEntry 9 }


--       T1 Performance 24 Hour
--       The T1 Totals Table contains the cumulative sum of the
--       various statistics for the 24 hour period preceding the
--       current interval.

mfrapPerfT1TotalTable OBJECT-TYPE
     SYNTAX  SEQUENCE OF MfrapT1TotalEntry
     ACCESS  not-accessible
     STATUS  mandatory
     DESCRIPTION
        "The T1 Total table cumulative physical layer performance 
         results from the past 24 hours. These are defined and 
         accumulated per ANSI specification T1.403 and AT&T publication
         54016. Depending upon the configured T1 Framing mode, these 
         results may be retrieved via ESF facility data link by service 
         personnel."
     ::= { mfrapPerfPhysicalIntf 3 }

mfrapT1TotalEntry OBJECT-TYPE
     SYNTAX  MfrapT1TotalEntry
     ACCESS  not-accessible
     STATUS  mandatory
     DESCRIPTION
        "An entry in the T1 Physical Layer Measurement Totals table."
     INDEX   { mfrapT1TotalIndex }
     ::= { mfrapPerfT1TotalTable 1 }

MfrapT1TotalEntry ::=
     SEQUENCE {
        mfrapT1TotalIndex INTEGER, 
        mfrapT1TotalESs   Gauge,
        mfrapT1TotalSESs  Gauge,
        mfrapT1TotalSEFSs Gauge,
        mfrapT1TotalUASs  Gauge,
        mfrapT1TotalCSSs  Gauge,
        mfrapT1TotalBESs  Gauge,
        mfrapT1TotalLCVs  Gauge
      }

mfrapT1TotalIndex OBJECT-TYPE
     SYNTAX  INTEGER (1..4)
     ACCESS  read-only
     STATUS  mandatory
     DESCRIPTION
        "The index value which uniquely identifies  the
        t1  interface  to which this entry is applica-
        ble. Since there is a separate Drop & Insert Performance 
        24 Hour Table, the value of this index will
        always be 1, referring to the WAN port. "
     ::= { mfrapT1TotalEntry 1 }

mfrapT1TotalESs OBJECT-TYPE
     SYNTAX  Gauge
     ACCESS  read-only
     STATUS  mandatory
     DESCRIPTION
        "The number of Errored Seconds encountered by a
        t1 interface in the previous 24 hour interval.
        An errored second is a one-second interval with 
        CRC errors or a loss of frame sync occurred."
     ::= { mfrapT1TotalEntry 2 }

mfrapT1TotalSESs OBJECT-TYPE
     SYNTAX  Gauge
     ACCESS  read-only
     STATUS  mandatory
     DESCRIPTION
        "The number of Severely Errored Seconds encoun-
        tered  by  a  t1  interface in the previous 24
        hour interval. A severely errored second is a one 
        second interval with more than 320 CRC errors or 
        one or more frame sync losses."
     ::= { mfrapT1TotalEntry 3 }

mfrapT1TotalSEFSs OBJECT-TYPE
     SYNTAX  Gauge
     ACCESS  read-only
     STATUS  mandatory
     DESCRIPTION
        "The number of Severely Errored Framing Seconds
        24 hour interval. A SEFS is a one second interval 
        with one or more frame sync losses."
     ::= { mfrapT1TotalEntry 4 }

mfrapT1TotalUASs OBJECT-TYPE
     SYNTAX  Gauge
     ACCESS  read-only
     STATUS  mandatory
     DESCRIPTION
        "The number of Unavailable Seconds  encountered
        by  a t1 interface in the previous 24 hour in-
        terval. A UAS is a one second interval during which 
        the received signal is classified as 'unavailable 
        due to excessive errors'. A signal is unavailable 
        after receiving ten consective severely errored 
        seconds and stays unavailable until ten seconds 
        without a severely errored second occur."
     ::= { mfrapT1TotalEntry 5 }

mfrapT1TotalCSSs OBJECT-TYPE
     SYNTAX  Gauge
     ACCESS  read-only
     STATUS  mandatory
     DESCRIPTION
        "The number of Controlled Slip Seconds  encoun-
        tered  by  a  t1  interface in the previous 24
        hour interval. A controlled slip is the replication 
        or deletion of a T1 frame at the receiver. These 
        events often indicate a T1 network timing problem."
     ::= { mfrapT1TotalEntry 6 }

mfrapT1TotalBESs OBJECT-TYPE
     SYNTAX Gauge
     ACCESS read-only
     STATUS mandatory
     DESCRIPTION
        "The number of Bursty  Errored  Seconds  (BESs)
        encountered  by a t1 interface in the previous
        24 hour interval. A BES is a one second interval 
        with more than one and less than 320 CRC errors."
     ::= { mfrapT1TotalEntry 7 }

mfrapT1TotalLCVs OBJECT-TYPE
     SYNTAX Gauge
     ACCESS read-only
     STATUS mandatory
     DESCRIPTION
        "The number of Line Code Violations (LCVs)  en-
        countered  by a t1 interface in the current 15
        minute interval. LCVs are non-B8ZS related
        violations of the alternate mark inversion protocol.
        An excessive count usually indicates a B8ZS/AMI
        configuration mismatch in the T1 network."
     ::= {mfrapT1TotalEntry 8 }


--      T1 Performance Commands
--      A set of commands that affect the (user) bank of T1 performance 
--      registers         


mfrapT1PerfCmdTypeTable OBJECT IDENTIFIER ::= { mfrapPerfPhysicalIntf 4 }
    
mfrapT1PerfFreezeState OBJECT-TYPE
     SYNTAX      INTEGER
      {
         freeze-reg (1),
         unfreeze-reg (2)
      }
     ACCESS  read-write
     STATUS  mandatory
     DESCRIPTION
        "This command halts the node's performance monitoring
        and freezes the current, interval, and total performance
        register values."
        ::= { mfrapT1PerfCmdTypeTable 1 }

mfrapT1PerfClearEvents OBJECT-TYPE
     SYNTAX      INTEGER
      {
         clear-events (1)
      }
     ACCESS  write-only
     STATUS  mandatory
     DESCRIPTION
        "This command resets all of the (user's) error event 
        registers. This includes the CRC6 and Out-of-Frame
        counts. It does not affect the interval or 24 hour
        performance totals."
     ::= { mfrapT1PerfCmdTypeTable 2 }

mfrapT1PerfClearAll OBJECT-TYPE
     SYNTAX      INTEGER
     {
        clear-all (1)
     }
     ACCESS  write-only
     STATUS  mandatory
     DESCRIPTION
        "This command resets all of the (user's) performance 
        registers."
     ::= { mfrapT1PerfCmdTypeTable 3 }

--
--      Drop & Insert Current Performance Table
--       The Drop & Insert current performance table contains 
--       various statistics being collected for the current 
--       15 minute interval.

mfrapPerfDandiCurrentTable OBJECT-TYPE
     SYNTAX  SEQUENCE OF MfrapDandiCurrentEntry
     ACCESS  not-accessible
     STATUS  mandatory
     DESCRIPTION
        "The T1 physical layer performance numbers for the current  
        15 minute interval. These are defined and accumulated per 
        ANSI specification T1.403 and AT&T publication 54016. Depending
        upon the configured T1 Framing mode, these results may be 
        retrieved via ESF facility data link by service personnel."
     ::= { mfrapPerfPhysicalIntf 5 }

mfrapDandiCurrentEntry OBJECT-TYPE
     SYNTAX  MfrapDandiCurrentEntry
     ACCESS  not-accessible
     STATUS  mandatory
     DESCRIPTION
        "An entry in the D&I Current Perf table."
     INDEX   { mfrapDandiCurrentIndex }
     ::= { mfrapPerfDandiCurrentTable 1 }

MfrapDandiCurrentEntry ::=
     SEQUENCE {
        mfrapDandiCurrentIndex       INTEGER,
        mfrapDandiCurrentCrc6Events  Gauge,
        mfrapDandiCurrentOofEvents   Gauge,
        mfrapDandiCurrentESs         Gauge,
        mfrapDandiCurrentSESs        Gauge,
        mfrapDandiCurrentSEFSs       Gauge,
        mfrapDandiCurrentUASs        Gauge,
        mfrapDandiCurrentCSSs        Gauge,
        mfrapDandiCurrentBESs        Gauge,
        mfrapDandiCurrentLCVs        Gauge
     }

mfrapDandiCurrentIndex OBJECT-TYPE
     SYNTAX  INTEGER
     {
        dandi-port1  (2)
     }
     ACCESS  read-only
     STATUS  mandatory
     DESCRIPTION
        "The index value which uniquely identifies  the
        D&I interface to which this entry is applica-
        ble. "
     ::= { mfrapDandiCurrentEntry 1 }

mfrapDandiCurrentCrc6Events OBJECT-TYPE
     SYNTAX  Gauge
     ACCESS  read-only
     STATUS  mandatory
     DESCRIPTION
        "Count of CRC errors detected on an ESF framed circuit.
        In ESF framing a CRC is generated at the source, based upon 
        the composite data. A CRC error indicates the presence of
        at least one bit error in an ESF superframe. This field is 
        a free-running accumulation of CRC errors and IS NOT reset 
        when the current 15 minute interval expires. It can be reset 
        with the performance command mfrapDandiPerfClearEvents. 
        Not applicable if D4/SF framing is selcted."
     ::= { mfrapDandiCurrentEntry 2 }

mfrapDandiCurrentOofEvents OBJECT-TYPE
     SYNTAX  Gauge
     ACCESS  read-only
     STATUS  mandatory
     DESCRIPTION
        "Count of Out-of-Frame events on a D&I circuit. An out-of-
        frame event occurs when the frame synchronization criteria
        is lost and a resynchronization must occur. Data is interrupted
        during frame resynchronization. This field is a free-running 
        accumulation of OOF transitions and IS NOT reset when the 
        current 15 minute interval expires. It can be reset with the 
        performance command mfrapDandiPerfClearEvents." 
     ::= { mfrapDandiCurrentEntry 3 }

mfrapDandiCurrentESs OBJECT-TYPE
     SYNTAX  Gauge
     ACCESS  read-only
     STATUS  mandatory
     DESCRIPTION
        "The number of Errored Seconds, encountered  by
        a D&I interface in the current 15 minute inter-
        val. An errored second is a one-second interval with
        CRC errors or a loss of frame sync occurred."
     ::= { mfrapDandiCurrentEntry 4 }

mfrapDandiCurrentSESs OBJECT-TYPE
     SYNTAX  Gauge
     ACCESS  read-only
     STATUS  mandatory
     DESCRIPTION
        "The number of Severely Errored Seconds encountered by
         a D&I interface in the current 15 minute interval. A
         severely errored second is a one second interval with
         more than 320 CRC errors or one or more frame sync losses."
     ::= { mfrapDandiCurrentEntry 5 }

mfrapDandiCurrentSEFSs OBJECT-TYPE
     SYNTAX  Gauge
     ACCESS  read-only
     STATUS  mandatory
     DESCRIPTION
        "The number of Severely Errored Framing Seconds
        encountered by a D&I interface in the current
        15 minute interval. A SEFS is a one second interval
        with one or more frame sync losses."
     ::= { mfrapDandiCurrentEntry 6 }

mfrapDandiCurrentUASs OBJECT-TYPE
     SYNTAX  Gauge
     ACCESS  read-only
     STATUS  mandatory
     DESCRIPTION
        "The number of Unavailable Seconds  encountered
        by a D&I interface in the current 15 minute in-
        terval. A UAS is a one second interval during which 
        the received signal is classified as 'unavailable due
        to excessive errors'. A signal is unavailable after
        receiving ten consective severely errored seconds and
        stays unavailable until ten seconds without a severely
        errored second occur."
     ::= { mfrapDandiCurrentEntry 7 }

mfrapDandiCurrentCSSs OBJECT-TYPE
     SYNTAX  Gauge
     ACCESS  read-only
     STATUS  mandatory
     DESCRIPTION
        "The number of Controlled Slip Seconds encoun-
        tered by a D&I interface in the current 15
        minute interval. A controlled slip is the 
        replication or deletion of a D&I frame at the receiver.
        These events often indicate a D&I network timing 
        problem."
     ::= { mfrapDandiCurrentEntry 8 }

mfrapDandiCurrentBESs OBJECT-TYPE
     SYNTAX Gauge
     ACCESS read-only
     STATUS mandatory
     DESCRIPTION
        "The number of Bursty  Errored  Seconds  (BESs)
        encountered  by  a DS1 interface in the current
        15 minute interval. A BES is a one second interval
        with more than one and less than 320 CRC errors."
     ::= {mfrapDandiCurrentEntry 9 }

mfrapDandiCurrentLCVs OBJECT-TYPE
     SYNTAX Gauge
     ACCESS read-only
     STATUS mandatory
     DESCRIPTION
        "The number of Line Code Violations (LCVs)  en-
        countered  by a DS1 interface in the current 15
        minute interval. LCVs are non-B8ZS related
        violations of the alternate mark inversion protocol.
        An excessive count usually indicates a B8ZS/AMI
        configuration mismatch in the D&I network."
     ::= {mfrapDandiCurrentEntry 10 }


--     Drop and Insert Performance Intervals
--      The D&I Interval Table contains various statistics
--      collected by the D&I Interface over the previous 24 hours of
--      operation.  The past 24 hours are broken into 96 completed
--      15 minute intervals.

mfrapPerfDandiIntervalTable OBJECT-TYPE
     SYNTAX  SEQUENCE OF MfrapDandiIntervalEntry
     ACCESS  not-accessible
     STATUS  mandatory
     DESCRIPTION
        "The DS1 Interval table. A history of physical layer performance 
         results are maintained and represented as 96 15-minute intervals.
         These are defined and accumulated per  ANSI specification T1.403 
         and AT&T publication 54016. Depending upon the configured T1 
         Framing mode, these results may be retrieved via ESF facility data 
         link by service personnel"
     ::= { mfrapPerfPhysicalIntf 6 }

mfrapDandiIntervalEntry OBJECT-TYPE
     SYNTAX  MfrapDandiIntervalEntry
     ACCESS  not-accessible
     STATUS  mandatory
     DESCRIPTION
        "An entry in the DS1 Interval table."
     INDEX   { mfrapDandiIntervalIndex, mfrapDandiIntervalNumber }
     ::= { mfrapPerfDandiIntervalTable 1 }

MfrapDandiIntervalEntry ::=
     SEQUENCE {
         mfrapDandiIntervalIndex  INTEGER,
         mfrapDandiIntervalNumber INTEGER,
         mfrapDandiIntervalESs    Gauge,
         mfrapDandiIntervalSESs   Gauge,
         mfrapDandiIntervalSEFSs  Gauge,
         mfrapDandiIntervalUASs   Gauge,
         mfrapDandiIntervalCSSs   Gauge,
         mfrapDandiIntervalBESs   Gauge,
         mfrapDandiIntervalLCVs   Gauge
     }
      
mfrapDandiIntervalIndex OBJECT-TYPE
     SYNTAX  INTEGER
     {
        dandi-port1  (2)
     }
     ACCESS  read-only
     STATUS  mandatory
     DESCRIPTION
        "The index value which uniquely identifies the
         D&I interface to which this entry is applicable.
         The interface identified by a particular value
         of this index is the same interface as identified
         by the same value as a NetwLineIndex object instance."
     ::= { mfrapDandiIntervalEntry 1 }


mfrapDandiIntervalNumber OBJECT-TYPE
     SYNTAX  INTEGER (1..96)
     ACCESS  read-only
     STATUS  mandatory
     DESCRIPTION
        "A number between 1 and 96, where 1 is the most
        recently completed 15 minute interval and 96 is
        the least recently completed 15 minutes  inter-
        val   (assuming   that  all  96  intervals  are
        valid)."
     ::= { mfrapDandiIntervalEntry 2 }

mfrapDandiIntervalESs OBJECT-TYPE
     SYNTAX  Gauge
     ACCESS  read-only
     STATUS  mandatory
     DESCRIPTION
        "The number of Errored Seconds encountered by a
        D&I interface in one of the previous 96, indi-
        vidual 15 minute, intervals. An errored second is 
        a one-second interval with CRC errors or a loss 
        of frame sync occurred."
     ::= { mfrapDandiIntervalEntry 3 }


mfrapDandiIntervalSESs OBJECT-TYPE
     SYNTAX  Gauge
     ACCESS  read-only
     STATUS  mandatory
     DESCRIPTION
        "The number of Severely Errored Seconds encoun-
        tered by a D&I interface in one of the previous
        96, individual 15 minute, intervals. A severely 
        errored second is a one second interval with more 
        than 320 CRC errors or one or more frame sync losses."
     ::= { mfrapDandiIntervalEntry 4 }


mfrapDandiIntervalSEFSs OBJECT-TYPE
     SYNTAX  Gauge
     ACCESS  read-only
     STATUS  mandatory
     DESCRIPTION
        "The number of Severely Errored Framing Seconds
        encountered  by  a  D&I interface in one of the
        previous 96, individual 15 minute, intervals.
        A SEFS is a one second interval with one or more 
        frame sync losses."
     ::= { mfrapDandiIntervalEntry 5 }


mfrapDandiIntervalUASs OBJECT-TYPE
     SYNTAX  Gauge
     ACCESS  read-only
     STATUS  mandatory
     DESCRIPTION
        "The number of Unavailable Seconds  encountered
        by  a  D&I interface in one of the previous 96,
        individual 15 minute, intervals. A UAS is a one second 
        interval during which the received signal is classified 
        as 'unavailable due to excessive errors'. A signal is 
        unavailable after receiving ten consective severely 
        errored seconds and stays unavailable until ten seconds 
        without a severely errored second occur."
     ::= { mfrapDandiIntervalEntry 6 }

mfrapDandiIntervalCSSs OBJECT-TYPE
     SYNTAX  Gauge
     ACCESS  read-only
     STATUS  mandatory
     DESCRIPTION
        "The number of Controlled Slip Seconds  encoun-
        tered by a D&I interface in one of the previous
        96, individual 15 minute, intervals. A controlled 
        slip is the replication or deletion of a D&I frame 
        at the receiver. These events often indicate a D&I 
        network timing problem."
     ::= { mfrapDandiIntervalEntry 7 }

mfrapDandiIntervalBESs OBJECT-TYPE
     SYNTAX Gauge
     ACCESS read-only
     STATUS mandatory
     DESCRIPTION
        "The number of Bursty  Errored  Seconds  (BESs)
        encountered  by  a  D&I interface in one of the
        previous 96, individual 15 minute, intervals.
        A BES is a one second interval with more than one 
        and less than 320 CRC errors."
     ::= {mfrapDandiIntervalEntry 8 }

mfrapDandiIntervalLCVs OBJECT-TYPE
     SYNTAX Gauge
     ACCESS read-only
     STATUS mandatory
     DESCRIPTION
        "The number of Line Code Violations (LCVs)  en-
        countered  by a DS1 interface in the current 15
        minute interval. LCVs are non-B8ZS related
        violations of the alternate mark inversion protocol.
        An excessive count usually indicates a B8ZS/AMI
        configuration mismatch in the D&I network."
     ::= {mfrapDandiIntervalEntry 9 }


--       Drip & Insert Performance 24 Hour
--       The D&I Totals Table contains the cumulative sum of the
--       various statistics for the 24 hour period preceding the
--       current interval.

mfrapPerfDandiTotalTable OBJECT-TYPE
     SYNTAX  SEQUENCE OF MfrapDandiTotalEntry
     ACCESS  not-accessible
     STATUS  mandatory
     DESCRIPTION
        "The T1 Total table cumulative physical layer performance 
         results from the past 24 hours. These are defined and 
         accumulated per ANSI specification T1.403 and AT&T publication
         54016. Depending upon the configured T1 Framing mode, these 
         results may be retrieved via ESF facility data link by service 
         personnel."
     ::= { mfrapPerfPhysicalIntf 7 }

mfrapDandiTotalEntry OBJECT-TYPE
     SYNTAX  MfrapDandiTotalEntry
     ACCESS  not-accessible
     STATUS  mandatory
     DESCRIPTION
        "An entry in the D&I Total table."
     INDEX   { mfrapDandiTotalIndex }
     ::= { mfrapPerfDandiTotalTable 1 }

MfrapDandiTotalEntry ::=
     SEQUENCE {
        mfrapDandiTotalIndex INTEGER, 
        mfrapDandiTotalESs   Gauge,
        mfrapDandiTotalSESs  Gauge,
        mfrapDandiTotalSEFSs Gauge,
        mfrapDandiTotalUASs  Gauge,
        mfrapDandiTotalCSSs  Gauge,
        mfrapDandiTotalBESs  Gauge,
        mfrapDandiTotalLCVs  Gauge
         }

mfrapDandiTotalIndex OBJECT-TYPE
     SYNTAX  INTEGER
     {
        dandi-port1  (2)
     }
     ACCESS  read-only
     STATUS  mandatory
     DESCRIPTION
        "The index value which uniquely identifies  the
        D&I  interface  to which this entry is applica-
        ble.  The interface identified by a  particular
        value  of  this  index is the same interface as
        identified by the same value as a NetwLineIndex
        object instance."
     ::= { mfrapDandiTotalEntry 1 }

mfrapDandiTotalESs OBJECT-TYPE
     SYNTAX  Gauge
     ACCESS  read-only
     STATUS  mandatory
     DESCRIPTION
        "The number of Errored Seconds encountered by a
        D&I interface in the previous 24 hour interval.
        An errored second is a one-second interval with 
        CRC errors or a loss of frame sync occurred."
     ::= { mfrapDandiTotalEntry 2 }

mfrapDandiTotalSESs OBJECT-TYPE
     SYNTAX  Gauge
     ACCESS  read-only
     STATUS  mandatory
     DESCRIPTION
        "The number of Severely Errored Seconds encoun-
        tered  by  a  D&I  interface in the previous 24
        hour interval. A severely errored second is a one 
        second interval with more than 320 CRC errors or 
        one or more frame sync losses."
     ::= { mfrapDandiTotalEntry 3 }

mfrapDandiTotalSEFSs OBJECT-TYPE
     SYNTAX  Gauge
     ACCESS  read-only
     STATUS  mandatory
     DESCRIPTION
        "The number of Severely Errored Framing Seconds
        24 hour interval. A SEFS is a one second interval 
        with one or more frame sync losses."
     ::= { mfrapDandiTotalEntry 4 }

mfrapDandiTotalUASs OBJECT-TYPE
     SYNTAX  Gauge
     ACCESS  read-only
     STATUS  mandatory
     DESCRIPTION
        "The number of Unavailable Seconds  encountered
        by  a D&I interface in the previous 24 hour in-
        terval. A UAS is a one second interval during which 
        the received signal is classified as 'unavailable 
        due to excessive errors'. A signal is unavailable 
        after receiving ten consective severely errored 
        seconds and stays unavailable until ten seconds 
        without a severely errored second occur."
     ::= { mfrapDandiTotalEntry 5 }

mfrapDandiTotalCSSs OBJECT-TYPE
     SYNTAX  Gauge
     ACCESS  read-only
     STATUS  mandatory
     DESCRIPTION
        "The number of Controlled Slip Seconds  encoun-
        tered  by  a  D&I  interface in the previous 24
        hour interval. A controlled slip is the replication 
        or deletion of a D&I frame at the receiver. These 
        events often indicate a D&I network timing problem."
     ::= { mfrapDandiTotalEntry 6 }

mfrapDandiTotalBESs OBJECT-TYPE
     SYNTAX Gauge
     ACCESS read-only
     STATUS mandatory
     DESCRIPTION
        "The number of Bursty  Errored  Seconds  (BESs)
        encountered  by a D&I interface in the previous
        24 hour interval. A BES is a one second interval 
        with more than one and less than 320 CRC errors."
     ::= { mfrapDandiTotalEntry 7 }

mfrapDandiTotalLCVs OBJECT-TYPE
     SYNTAX Gauge
     ACCESS read-only
     STATUS mandatory
     DESCRIPTION
        "The number of Line Code Violations (LCVs)  en-
        countered  by a D&I interface in the current 15
        minute interval. LCVs are non-B8ZS related
        violations of the alternate mark inversion protocol.
        An excessive count usually indicates a B8ZS/AMI
        configuration mismatch in the D&I network."
     ::= {mfrapDandiTotalEntry 8 }


--    Drop and Insert Performance Commands
--      A set of commands that affect the (user) bank of D&I performance 
--      registers         


mfrapDandiPerfCmdTypeTable OBJECT IDENTIFIER ::= { mfrapPerfPhysicalIntf 8 }
    
mfrapDandiPerfFreezeState OBJECT-TYPE
     SYNTAX      INTEGER
     {
         freeze-reg (1),
         unfreeze-reg (2)
     }
     ACCESS  read-write
     STATUS  mandatory
     DESCRIPTION
        "This command halts the node's performance monitoring
        and freezes the current, interval, and total performance
        register values."
        ::= { mfrapDandiPerfCmdTypeTable 1 }

mfrapDandiPerfClearEvents OBJECT-TYPE
     SYNTAX      INTEGER
     {
         clear-events (1)
     }
     ACCESS  write-only
     STATUS  mandatory
     DESCRIPTION
        "This command resets all of the (user's) error event 
        registers. This includes the CRC6 and Out-of-Frame
        counts. It does not affect the interval or 24 hour
        performance totals."
     ::= { mfrapDandiPerfCmdTypeTable 2 }

mfrapDandiPerfClearAll OBJECT-TYPE
     SYNTAX      INTEGER
     {
        clear-all (1)
     }
     ACCESS  write-only
     STATUS  mandatory
     DESCRIPTION
        "This command resets all of the (user's) performance 
        registers."
     ::= { mfrapDandiPerfCmdTypeTable 3 }


--
--    IP protocol stack statistics - a reflection of some MIB-2 variables
--

mfrapPerfMgmtIp   OBJECT IDENTIFIER ::= { mfrapPerformance 2 }

   mfrapPerfMgmtIpIFStatsTable OBJECT IDENTIFIER ::= { mfrapPerfMgmtIp 1 }

          mfrapPerfMgmtIpIFInOctets OBJECT-TYPE
              SYNTAX  Counter
              ACCESS  read-only
              STATUS  mandatory
              DESCRIPTION
                 "The count of all octets associated with received frames 
                  that are specifically addressed as management packets 
                  for this unit. Same as ifInOctets in mib-2."
              ::= { mfrapPerfMgmtIpIFStatsTable 1 }

          mfrapPerfMgmtIpIFInErrors OBJECT-TYPE
              SYNTAX  Counter
              ACCESS  read-only
              STATUS  mandatory
              DESCRIPTION
                 "The count of packets associated with received frames 
                  that are specifically addressed as management packets 
                  for this unit which could not be handled because of 
                  errors. Same as ifInErrors in mib-2."
              ::= { mfrapPerfMgmtIpIFStatsTable 2 }

          mfrapPerfMgmtIpIFOutOctets OBJECT-TYPE
              SYNTAX  Counter
              ACCESS  read-only
              STATUS  mandatory
              DESCRIPTION
                 "The count of all octets associated with generated frames 
                  that are specifically addressed as management packets 
                  from this unit. Same as ifOutOctets in mib-2.                     Same as ifOutOctets in mib-2."
              ::= { mfrapPerfMgmtIpIFStatsTable 3 }

          mfrapPerfMgmtIpIFOperStatus OBJECT-TYPE
              SYNTAX  INTEGER 
              {
                  up(1),
                  down(2),
                  testing(3)
              }
              ACCESS  read-only
              STATUS  mandatory
              DESCRIPTION
                 "The current operational state of the management interface.
                  Same as ifOperStatus in mib-2.
                  (1) Interface Up
                  (2) Interface Down
                  (3) Interface in Test"
              ::= { mfrapPerfMgmtIpIFStatsTable 4 }

   mfrapPerfMgmtIpIPStatsTable OBJECT IDENTIFIER ::= { mfrapPerfMgmtIp 2 }

          mfrapPerfMgmtIpIPInRcv OBJECT-TYPE
              SYNTAX  Counter
              ACCESS  read-only
              STATUS  mandatory
              DESCRIPTION
                 "The count of all ip datagrams received which
                  are specifically addressed as management frames 
                  for this unit. Same as ipInReceives in mib-2."
              ::= { mfrapPerfMgmtIpIPStatsTable 1 }

          mfrapPerfMgmtIpIPInHdrErr OBJECT-TYPE
              SYNTAX  Counter
              ACCESS  read-only
              STATUS  mandatory
              DESCRIPTION
                 "The count of ip datagrams received which
                  are specifically addressed as management frames 
                  for this unit that were discarded because of 
                  errors in their IP headers. Same as ipInHdrErrors 
                  in mib-2."
              ::= { mfrapPerfMgmtIpIPStatsTable 2 }

          mfrapPerfMgmtIpIPInAddrErr OBJECT-TYPE
              SYNTAX  Counter
              ACCESS  read-only
              STATUS  mandatory
              DESCRIPTION
                 "The count of ip datagrams received which
                  are specifically addressed as management frames 
                  for this unit that were discarded because unexpected 
                  or invalid IP addresses in their IP headers.
                  Same as ipInAddrErrors in mib-2."
              ::= { mfrapPerfMgmtIpIPStatsTable 3 }

          mfrapPerfMgmtIpIPInProtUnk OBJECT-TYPE
              SYNTAX  Counter
              ACCESS  read-only
              STATUS  mandatory
              DESCRIPTION
                 "The count of ip datagrams received which
                  are specifically addressed as management frames 
                  for this unit that were discarded because of 
                  unsupported protocols. Same as ipInUnknownProtos 
                  in mib-2."
              ::= { mfrapPerfMgmtIpIPStatsTable 4 }

          mfrapPerfMgmtIpIPInDscrd OBJECT-TYPE
              SYNTAX  Counter
              ACCESS  read-only
              STATUS  mandatory
              DESCRIPTION
                 "The count of datagrams received which
                  are specifically addressed as management frames 
                  for this unit that were discarded for reasons 
                  other than a problem with the datagram. Same as 
                  ipInDiscards in mib-2."
              ::= { mfrapPerfMgmtIpIPStatsTable 5 }

          mfrapPerfMgmtIpIPInDlvrs OBJECT-TYPE
              SYNTAX  Counter
              ACCESS  read-only
              STATUS  mandatory
              DESCRIPTION
                 "The count ofip datagrams received which
                  are specifically addressed as management frames 
                  for this unit that were delivered to IP client 
                  protocols. Same as ipInDelivers in mib-2."
              ::= { mfrapPerfMgmtIpIPStatsTable 6 }

          mfrapPerfMgmtIpIPOutRqst OBJECT-TYPE
              SYNTAX  Counter
              ACCESS  read-only
              STATUS  mandatory
              DESCRIPTION
                 "The count of all outgoing datagrams generated by this 
                  unit which are specifically addressed as management frames. 
                  Same as ipOutRequests in mib-2."
              ::= { mfrapPerfMgmtIpIPStatsTable 7 }

          mfrapPerfMgmtIpIPOutDscrd OBJECT-TYPE
              SYNTAX  Counter
              ACCESS  read-only
              STATUS  mandatory
              DESCRIPTION
                 "The count of outgoing datagrams generated by this 
                  unit which are specifically addressed as management 
                  frames that were discarded for reasons other than a 
                  problem with the datagram. Same as ipOutDiscards in mib-2."
              ::= { mfrapPerfMgmtIpIPStatsTable 8 }

          mfrapPerfMgmtIpIPOutNoRt OBJECT-TYPE
              SYNTAX  Counter
              ACCESS  read-only
              STATUS  mandatory
              DESCRIPTION
                "The count of outgoing datagrams generated by this 
                 unit which are specifically addressed as management 
                 frames that were discarded because no route could be 
                 found for transmission. Same as ipOutNoRoutes in mib-2."
              ::= { mfrapPerfMgmtIpIPStatsTable 9 }


   mfrapPerfMgmtIpICMPStatsTable OBJECT IDENTIFIER ::= { mfrapPerfMgmtIp 3 }

          mfrapPerfMgmtIpICMPInMsgs OBJECT-TYPE
              SYNTAX  Counter
              ACCESS  read-only
              STATUS  mandatory
              DESCRIPTION
                 "The count of all ICMP messages received which are
                  addressed to this unit. Same as icmpInMsgs in mib-2."
              ::= { mfrapPerfMgmtIpICMPStatsTable 1 }

          mfrapPerfMgmtIpICMPInErrors OBJECT-TYPE
              SYNTAX  Counter
              ACCESS  read-only
              STATUS  mandatory
              DESCRIPTION
                 "The count of ICMP messages received which are
                  addressed to this unit but contain errors. Same 
                  as icmpInErrors in mib-2."
              ::= { mfrapPerfMgmtIpICMPStatsTable 2 }

          mfrapPerfMgmtIpICMPInDestUnreachs OBJECT-TYPE
              SYNTAX  Counter
              ACCESS  read-only
              STATUS  mandatory
              DESCRIPTION
                 "The count of ICMP Destination Unreachable messages 
                  received which are addressed to this unit. Same as 
                  icmpInDestUnreachs in mib-2."
              ::= { mfrapPerfMgmtIpICMPStatsTable 3 }

          mfrapPerfMgmtIpICMPInTimeExcds OBJECT-TYPE
              SYNTAX  Counter
              ACCESS  read-only
              STATUS  mandatory
              DESCRIPTION
                 "The count of ICMP Time Exceeded messages received which 
                  are addressed to this unit. Same as icmpInTimeExcds in 
                  mib-2."
              ::= { mfrapPerfMgmtIpICMPStatsTable 4 }

          mfrapPerfMgmtIpICMPInParmProbs OBJECT-TYPE
              SYNTAX  Counter
              ACCESS  read-only
              STATUS  mandatory
              DESCRIPTION
                 "The count of ICMP Parameter Problem messages received 
                  which are addressed to this unit. Same as icmpInParmProbs 
                  in mib-2."
              ::= { mfrapPerfMgmtIpICMPStatsTable 5 }

          mfrapPerfMgmtIpICMPInRedirects OBJECT-TYPE
              SYNTAX  Counter
              ACCESS  read-only
              STATUS  mandatory
              DESCRIPTION
                 "The count of ICMP Redirect messages received which are
                  addressed to this unit. Same as icmpInRedirects in mib-2."
              ::= { mfrapPerfMgmtIpICMPStatsTable 6 }

          mfrapPerfMgmtIpICMPInEchos OBJECT-TYPE
              SYNTAX  Counter
              ACCESS  read-only
              STATUS  mandatory
              DESCRIPTION
                 "The count of ICMP Echo messages received which are
                  addressed to this unit. Same as icmpInEchos in mib-2."
              ::= { mfrapPerfMgmtIpICMPStatsTable 7 }

          mfrapPerfMgmtIpICMPInEchoReps OBJECT-TYPE
              SYNTAX  Counter
              ACCESS  read-only
              STATUS  mandatory
              DESCRIPTION
                 "The count of ICMP Echo Reply messages received which are
                  addressed to this unit. Same as icmpInEchoReps in mib-2."
              ::= { mfrapPerfMgmtIpICMPStatsTable 8 }

          mfrapPerfMgmtIpICMPOutMsgs OBJECT-TYPE
              SYNTAX  Counter
              ACCESS  read-only
              STATUS  mandatory
              DESCRIPTION
                 "The count of all outgoing ICMP messages originating 
                  from this node. Same as icmpOutMsgs in mib-2."
              ::= { mfrapPerfMgmtIpICMPStatsTable 9 }

          mfrapPerfMgmtIpICMPOutErrors OBJECT-TYPE
              SYNTAX  Counter
              ACCESS  read-only
              STATUS  mandatory
              DESCRIPTION
                 "The count of outgoing ICMP messages generated by this
                  unit which are not transmitted due problems found by 
                  the ICMP layer. Same as icmpOutErrors in mib-2."
              ::= { mfrapPerfMgmtIpICMPStatsTable 10 }

          mfrapPerfMgmtIpICMPOutDestUnreachs OBJECT-TYPE
              SYNTAX  Counter
              ACCESS  read-only
              STATUS  mandatory
              DESCRIPTION
                 "The count of outgoing ICMP Destination Unreachable
                  messages generated by this unit. Same as 
                  icmpOutDestUnreachs in mib-2."
              ::= { mfrapPerfMgmtIpICMPStatsTable 11 }

          mfrapPerfMgmtIpICMPOutParmProbs OBJECT-TYPE
              SYNTAX  Counter
              ACCESS  read-only
              STATUS  mandatory
              DESCRIPTION
                 "The count of outgoing ICMP Parameter Problem messages
                  generated by this unit. Same as icmpOutParmProbs in mib-2."
              ::= { mfrapPerfMgmtIpICMPStatsTable 12 }

          mfrapPerfMgmtIpICMPOutRedirects OBJECT-TYPE
              SYNTAX  Counter
              ACCESS  read-only
              STATUS  mandatory
              DESCRIPTION
                 "The count of outgoing ICMP Redirect messages generated
                  by this unit. Same as icmpOutRedirects in mib-2."
              ::= { mfrapPerfMgmtIpICMPStatsTable 13 }

          mfrapPerfMgmtIpICMPOutEchos OBJECT-TYPE
              SYNTAX  Counter
              ACCESS  read-only
              STATUS  mandatory
              DESCRIPTION
                 "The count of outgoing ICMP Echo messages generated by this
                  unit. Same as icmpOutEchos in mib-2."
              ::= { mfrapPerfMgmtIpICMPStatsTable 14 }

          mfrapPerfMgmtIpICMPOutEchoReps OBJECT-TYPE
              SYNTAX  Counter
              ACCESS  read-only
              STATUS  mandatory
              DESCRIPTION
                 "The count of outgoing ICMP Echo Reply messages generated 
                  by this unit. Same as icmpOutEchoReps in mib-2."
              ::= { mfrapPerfMgmtIpICMPStatsTable 15 }

   mfrapPerfMgmtIpUDPStatsTable OBJECT IDENTIFIER ::= { mfrapPerfMgmtIp 4 }

          mfrapPerfMgmtIpUDPInDatagrams OBJECT-TYPE
              SYNTAX  Counter
              ACCESS  read-only
              STATUS  mandatory
              DESCRIPTION
                 "The count of all UDP datagrams received that are 
                  addressed as management frames for this unit. Same 
                  as udpInDatagrams in mib-2."
              ::= { mfrapPerfMgmtIpUDPStatsTable 1 }

          mfrapPerfMgmtIpUDPOutDatagrams OBJECT-TYPE
              SYNTAX  Counter
              ACCESS  read-only
              STATUS  mandatory
              DESCRIPTION
                      "The count of all UDP datagrams generated by
                       this unit. Same as udpOutDatagrams in mib-2."
              ::= { mfrapPerfMgmtIpUDPStatsTable 2 }

          mfrapPerfMgmtIpUDPNoPorts OBJECT-TYPE
              SYNTAX  Counter
              ACCESS  read-only
              STATUS  mandatory
              DESCRIPTION
                 "The count of all UDP datagrams received that are 
                  addressed as management frames for this unit with 
                  no application at the destination port. Same as 
                  udpNoPorts in mib-2."
              ::= { mfrapPerfMgmtIpUDPStatsTable 3 }


   mfrapPerfMgmtIpTCPStatsTable OBJECT IDENTIFIER ::= { mfrapPerfMgmtIp 5 }

          mfrapPerfMgmtIpTCPActiveOpens OBJECT-TYPE
              SYNTAX  Counter
              ACCESS  read-only
              STATUS  mandatory
              DESCRIPTION
                 "The count of the times TCP connections specific to this 
                  unit have made a direct state transition from CLOSED to 
                  SYN-SENT. Same as tcpActiveOpens in mib-2."
              ::= { mfrapPerfMgmtIpTCPStatsTable 1 }

          mfrapPerfMgmtIpTCPPassiveOpens OBJECT-TYPE
              SYNTAX  Counter
              ACCESS  read-only
              STATUS  mandatory
              DESCRIPTION
                 "The count of the times TCP connections specific to 
                  this unit have made a direct state transition from 
                  CLOSED to SYN-RCVD. Same as tcpPassiveOpens in mib-2."
              ::= { mfrapPerfMgmtIpTCPStatsTable 2 }

          mfrapPerfMgmtIpTCPAttemptFails OBJECT-TYPE
              SYNTAX  Counter
              ACCESS  read-only
              STATUS  mandatory
              DESCRIPTION
                 "The count of the times TCP connections specific to this unit
                  have made a direct state transition from SYN-SENT or SYN-RCVD
                  to CLOSED state, plus the count of the times TCP connections 
                  have made a direct state transition from SYN-RCVD to LISTEN.
                  Same as tcpAttemptFails in mib-2."
              ::= { mfrapPerfMgmtIpTCPStatsTable 3 }

          mfrapPerfMgmtIpTCPCurrEstab OBJECT-TYPE
              SYNTAX  Gauge
              ACCESS  read-only
              STATUS  mandatory
              DESCRIPTION
                 "The count of the TCP connections specific to this unit
                  in state ESTABLISHED or CLOSE-WAIT. Same as tcpCurrEstab 
                  in mib-2."
              ::= { mfrapPerfMgmtIpTCPStatsTable 4 }

          mfrapPerfMgmtIpTCPInSegs OBJECT-TYPE
              SYNTAX  Counter
              ACCESS  read-only
              STATUS  mandatory
              DESCRIPTION
                 "The count of all the segments received that are 
                  addressed as management frames for this unit.
                  Same as tcpInSegs in mib-2."
              ::= { mfrapPerfMgmtIpTCPStatsTable 5 }

          mfrapPerfMgmtIpTCPOutSegs OBJECT-TYPE
              SYNTAX  Counter
              ACCESS  read-only
              STATUS  mandatory
              DESCRIPTION
                 "The count of all the segments generated from this unit.
                  Same as tcpOutSegs in mib-2."
              ::= { mfrapPerfMgmtIpTCPStatsTable 6 }


--
--       The MFRAP Performance Thruput Table
--              This table contains Thruput statistics for the DTE port
--              and the T1 port.  This table does NOT contain any PVC 
--              DLCI thruput statistics.
--

mfrapPerfThruput   OBJECT IDENTIFIER ::= { mfrapPerformance 3 }

mfrapPerfThruputPerIntfTable  OBJECT-TYPE
     SYNTAX  SEQUENCE OF MfrapPerfThruputPerIntfEntry
     ACCESS  not-accessible
     STATUS  mandatory
     DESCRIPTION
        "The throughput per interface table. These values are accumulated
         across all DLCIs."
     ::= { mfrapPerfThruput 1 }

mfrapPerfThruputPerIntfEntry  OBJECT-TYPE
     SYNTAX  MfrapPerfThruputPerIntfEntry
     ACCESS  not-accessible
     STATUS  mandatory
     DESCRIPTION
        "An entry in the throughput per interface table."
     INDEX   { mfrapPerfThruputPerIntfIndex }
     ::= { mfrapPerfThruputPerIntfTable 1 }

MfrapPerfThruputPerIntfEntry ::=
     SEQUENCE {
        mfrapPerfThruputPerIntfIndex       INTEGER, 
        mfrapPerfThruputPerIntfRxByteCnt   Counter,
        mfrapPerfThruputPerIntfTxByteCnt   Counter,
        mfrapPerfThruputPerIntfRxFrameCnt  Counter,
        mfrapPerfThruputPerIntfTxFrameCnt  Counter,
        mfrapPerfThruputPerIntfRxCrcErrCnt Counter,
        mfrapPerfThruputPerIntfRxAbortCnt  Counter
     }

   mfrapPerfThruputPerIntfIndex    OBJECT-TYPE
          SYNTAX      INTEGER
          {
             dte (1),
             t1  (2)
          }
          ACCESS      read-only
          STATUS      mandatory
          DESCRIPTION
             "Interface for which the statistics apply.
              (1) DTE interface
              (2) T1 interface"
          ::= { mfrapPerfThruputPerIntfEntry 1 }

   mfrapPerfThruputPerIntfRxByteCnt    OBJECT-TYPE
          SYNTAX      Counter 
          ACCESS      read-only
          STATUS      mandatory
          DESCRIPTION
             "The number of bytes that have been counted
              on this interface."
          ::= { mfrapPerfThruputPerIntfEntry 2 }

   mfrapPerfThruputPerIntfTxByteCnt    OBJECT-TYPE
             SYNTAX      Counter
             ACCESS      read-only
             STATUS      mandatory
             DESCRIPTION
                "The number of bytes that have been counted
                 on this interface."
             ::= { mfrapPerfThruputPerIntfEntry 3 }

   mfrapPerfThruputPerIntfRxFrameCnt    OBJECT-TYPE
             SYNTAX      Counter 
             ACCESS      read-only
             STATUS      mandatory
             DESCRIPTION
                "The number of frames that have been counted
                 on this interface."
             ::= { mfrapPerfThruputPerIntfEntry 4 }

   mfrapPerfThruputPerIntfTxFrameCnt    OBJECT-TYPE
             SYNTAX      Counter 
             ACCESS      read-only
             STATUS      mandatory
             DESCRIPTION
                "The number of frames that have been counted
                 on this interface."
             ::= { mfrapPerfThruputPerIntfEntry 5 }

   mfrapPerfThruputPerIntfRxCrcErrCnt  OBJECT-TYPE
             SYNTAX      Counter 
             ACCESS      read-only
             STATUS      mandatory
             DESCRIPTION
                "The number of frames with CRC errors received
                 on this interface."
            ::= { mfrapPerfThruputPerIntfEntry 6 }

   mfrapPerfThruputPerIntfRxAbortCnt   OBJECT-TYPE
             SYNTAX      Counter 
             ACCESS      read-only
             STATUS      mandatory
             DESCRIPTION
                "The number of aborted frames received
                 on this interface."
            ::= { mfrapPerfThruputPerIntfEntry 7 }


--
--       The DLCI Statistics Table
--              This table contains the DLCI Statistics (layer 2).

   Index ::= INTEGER

   mfrapPerfThruputPerDlciTable OBJECT-TYPE
         SYNTAX   SEQUENCE OF MfrapPerfThruputPerDlciEntry
         ACCESS   not-accessible
         STATUS   mandatory
         DESCRIPTION
            "Layer 2 statistics on a per-DLCI basis. Transmit direction
             is from DTE to WAN and receive direction is from the WAN
             towards the DTE."
         ::= { mfrapPerfThruput 2 }

         mfrapPerfThruputPerDlciEntry OBJECT-TYPE
             SYNTAX   MfrapPerfThruputPerDlciEntry
             ACCESS   not-accessible
             STATUS   mandatory
             DESCRIPTION
                "The Statistics for a particular Data Link
                 Connection Management Interface (DLCI)."
            INDEX { mfrapPerfThruputPerDlciIndex,
                    mfrapPerfThruputPerDlciValue }
            ::= { mfrapPerfThruputPerDlciTable 1 }

         MfrapPerfThruputPerDlciEntry ::=
             SEQUENCE {
                 mfrapPerfThruputPerDlciIndex               Index,
                 mfrapPerfThruputPerDlciValue               INTEGER,
                 mfrapPerfThruputPerDlciCreateTime          INTEGER,
                 mfrapPerfThruputPerDlciChangeTime          INTEGER,
                 mfrapPerfThruputPerDlciRxByte              Counter,
                 mfrapPerfThruputPerDlciTxByte              Counter,
                 mfrapPerfThruputPerDlciRxFrame             Counter,
                 mfrapPerfThruputPerDlciTxFrame             Counter,
                 mfrapPerfThruputPerDlciRxFecn              Counter,
                 mfrapPerfThruputPerDlciRxBecn              Counter,
                 mfrapPerfThruputPerDlciRxDe                Counter,
                 mfrapPerfThruputPerDlciTxDe                Counter,
                 mfrapPerfThruputPerDlciRxThruput           INTEGER,
                 mfrapPerfThruputPerDlciTxThruput           INTEGER,
                 mfrapPerfThruputPerDlciCIR                 INTEGER,
                 mfrapPerfThruputPerDlciUptime              INTEGER,
                 mfrapPerfThruputPerDlciDowntime            INTEGER,
                 mfrapPerfThruputPerDlciCirType             INTEGER,
                 mfrapPerfThruputPerDlciPvcState            INTEGER,
                 mfrapPerfThruputPerDlciOutageCount         Counter,
                 mfrapPerfThruputPerDlciAvailability        INTEGER,
                 mfrapPerfThruputPerDlciMTBSO               INTEGER,
                 mfrapPerfThruputPerDlciMTTSR               INTEGER,
                 mfrapPerfThruputPerDlciEncapType           INTEGER,
                 mfrapPerfThruputPerDlciRxUtilizationStatus INTEGER,
                 mfrapPerfThruputPerDlciTxUtilizationStatus INTEGER,
                 mfrapPerfThruputPerDlciEIR                 INTEGER
             }

   mfrapPerfThruputPerDlciIndex OBJECT-TYPE
             SYNTAX   Index
             ACCESS   read-only
             STATUS   mandatory
             DESCRIPTION
                "This value must be in the range 1-3.
                 Other than that, this value is ignored as
                 all three will return the same result."
            ::= { mfrapPerfThruputPerDlciEntry 1 }

   mfrapPerfThruputPerDlciValue    OBJECT-TYPE
             SYNTAX      INTEGER 
             ACCESS      read-only
             STATUS      mandatory
             DESCRIPTION
                "The DLCI value in which the Statistics are associated."
            ::= { mfrapPerfThruputPerDlciEntry 2 }

   mfrapPerfThruputPerDlciCreateTime    OBJECT-TYPE
             SYNTAX      INTEGER 
             ACCESS      read-only
             STATUS      mandatory
             DESCRIPTION
                "The amount of time elapsed since this DLCI was first
                 detected through traffic sensing or in an LMI message 
                 (in seconds)."
            ::= { mfrapPerfThruputPerDlciEntry 3 }

   mfrapPerfThruputPerDlciChangeTime    OBJECT-TYPE
           SYNTAX      INTEGER 
             ACCESS      read-only
             STATUS      mandatory
             DESCRIPTION
                "The amount of elapsed time since this DLCI last
                 changed state from active to inactive or vice versa
                 (in seconds)."
            ::= { mfrapPerfThruputPerDlciEntry 4 }

   mfrapPerfThruputPerDlciRxByte    OBJECT-TYPE
             SYNTAX      Counter 
             ACCESS      read-only
             STATUS      mandatory
             DESCRIPTION
                "The number of bytes that have been received from
                 the WAN towards the DTE on this DLCI. This count
                 will include any frames that are terminated by the 
                 unit and do not pass through to the opposite interface 
                 (management and networking data)."
            ::= { mfrapPerfThruputPerDlciEntry 5 }

   mfrapPerfThruputPerDlciTxByte    OBJECT-TYPE
             SYNTAX      Counter
             ACCESS      read-only
             STATUS      mandatory
             DESCRIPTION
                "The number of bytes that have been transmit from the
                 DTE towards the WAN on this DLCI. This count
                 will include any frames that are terminated by the 
                 unit and do not pass through to the opposite interface 
                 (management and networking data)."
       ::= { mfrapPerfThruputPerDlciEntry 6 }

   mfrapPerfThruputPerDlciRxFrame    OBJECT-TYPE
             SYNTAX      Counter
             ACCESS      read-only
             STATUS      mandatory
             DESCRIPTION
                "The number of frames that have been received from
                 the WAN towards to the DTE on this DLCI. This count
                 will include any frames that are terminated by the 
                 unit and do not pass through to the opposite interface 
                 (management and networking data)."
            ::= { mfrapPerfThruputPerDlciEntry 7 }

   mfrapPerfThruputPerDlciTxFrame    OBJECT-TYPE
             SYNTAX      Counter
             ACCESS      read-only
             STATUS      mandatory
             DESCRIPTION
                "The number of frames that have been transmit from the
                 DTE towards the WAN on this DLCI. This count
                 will include any frames that are terminated by the 
                 unit and do not pass through to the opposite interface 
                 (management and networking data)."
            ::= { mfrapPerfThruputPerDlciEntry 8 }

   mfrapPerfThruputPerDlciRxFecn    OBJECT-TYPE
             SYNTAX      Counter
             ACCESS      read-only
             STATUS      mandatory
             DESCRIPTION
                "The number frames received from the WAN towards the DTE 
                 that have had the Forward Explict Congestion Notification 
                 (FECN) bit set on this DLCI. This count will include any 
                 frames that are terminated by the unit and do not pass 
                 through to the opposite interface (management and networking 
                 data)."
            ::= { mfrapPerfThruputPerDlciEntry 9 }

   mfrapPerfThruputPerDlciRxBecn    OBJECT-TYPE
             SYNTAX      Counter
             ACCESS      read-only
             STATUS      mandatory
             DESCRIPTION
                "The number frames received from the WAN towards the DTE 
                 that have had the Backward Explict Congestion Notification 
                 (BECN) bit set on this DLCI. This count will include any 
                 frames that are terminated by the unit and do not pass 
                 through to the opposite interface (management and networking 
                 data)."
            ::= { mfrapPerfThruputPerDlciEntry 10 }

   mfrapPerfThruputPerDlciRxDe    OBJECT-TYPE
             SYNTAX      Counter
             ACCESS      read-only
             STATUS      mandatory
             DESCRIPTION
                "The number frames received from the WAN towards the DTE 
                 that have had the Discard Eligibility (DE) bit set on 
                 this DLCI. This count will include any frames that are 
                 terminated by the unit and do not pass through to the 
                 opposite interface (management and networking data)."
            ::= { mfrapPerfThruputPerDlciEntry 11 }

   mfrapPerfThruputPerDlciTxDe    OBJECT-TYPE
             SYNTAX      Counter
             ACCESS      read-only
             STATUS      mandatory
             DESCRIPTION
                "The number frames transmit towards the WAN from the DTE 
                 that have had the Discard Eligibility (DE) bit set on 
                 this DLCI. This count will include any frames that are 
                 terminated by the unit and do not pass through to the 
                 opposite interface (management and networking data)."
            ::= { mfrapPerfThruputPerDlciEntry 12 }

   mfrapPerfThruputPerDlciRxThruput    OBJECT-TYPE
             SYNTAX      INTEGER
             ACCESS      read-only
             STATUS      mandatory
             DESCRIPTION
                "The number of bits/sec received from the WAN on this 
                 DLCI. This count will include any frames that are 
                 terminated by the unit and do not pass through to the 
                 opposite interface (management and networking data)."
            ::= { mfrapPerfThruputPerDlciEntry 13 }

   mfrapPerfThruputPerDlciTxThruput    OBJECT-TYPE
             SYNTAX      INTEGER
             ACCESS      read-only
             STATUS      mandatory
             DESCRIPTION
                "The number of bits/sec transmit to the WAN on this 
                 DLCI. This count will include any frames that are 
                 terminated by the unit and do not pass through to 
                 the opposite interface (management and networking data)."
            ::= { mfrapPerfThruputPerDlciEntry 14 }

   mfrapPerfThruputPerDlciCIR    OBJECT-TYPE
             SYNTAX      INTEGER
             ACCESS      read-only
             STATUS      mandatory
             DESCRIPTION
                "The Committed Information Rate (CIR) for this DLCI.
                 This can come form one of three sources: From the LMI
                 Full Status Response, configured by the user, or 
                 the DTE line rate (default)."
            ::= { mfrapPerfThruputPerDlciEntry 15 }

      mfrapPerfThruputPerDlciCirType    OBJECT-TYPE
             SYNTAX      INTEGER 
             {
               cir-acquired-from-lmi  (1),
               cir-configured-by-user (2),
               cir-is-dte-datarate    (3)
             }
             ACCESS      read-only
             STATUS      mandatory
             DESCRIPTION
               "The source of the CIR value for this DLCI. 
                (1) CIR acquired from LMI message. Will override user
                    configured CIR. This feature is not supported by all
                    Frame Relay DCE (switches).
                (2) CIR configured by user.
                (3) CIR is DTE Line Rate. Default if CIR is not set
                    by one of the other methods."
            ::= { mfrapPerfThruputPerDlciEntry 18 }

      mfrapPerfThruputPerDlciUptime    OBJECT-TYPE
             SYNTAX      INTEGER 
             ACCESS      read-only
             STATUS      mandatory
             DESCRIPTION
                "The total amount of time that the DLCI has been up as
                 reproted by the LMI Full Status Response (in seconds)."
            ::= { mfrapPerfThruputPerDlciEntry 16 }

      mfrapPerfThruputPerDlciDowntime    OBJECT-TYPE
             SYNTAX      INTEGER 
             ACCESS      read-only
             STATUS      mandatory
             DESCRIPTION
                "The total amount of time that the DLCI has been declared
                 down (in seconds). A DLCI is Down if it's explicitly 
                 declared Inactive through LMI or if it's missing from the 
                 LMI Full Status message or if there is no Full Status 
                 message at all."
            ::= { mfrapPerfThruputPerDlciEntry 17 }

   mfrapPerfThruputPerDlciPvcState   OBJECT-TYPE
          SYNTAX       INTEGER
          {
             pvc-active        (1),
             pvc-inactive      (2),
             pvc-unprovisioned (3),
             pvc-not-in-lmi    (4),
             pvc-lmi-timeout   (5),
             pvc-undetermined  (6)
          }
          ACCESS      read-only
          STATUS      mandatory
          DESCRIPTION
             "The current state of the DLCI:
            (1) DLCI marked active in last full status LMI
            (2) DLCI in last full status LMI but not marked active
            (3) DLCI has never been seen in a full status LMI
            (4) DLCI was seen at least once in a full status LMI
                but was not in the last full status LMI
            (5) the full status LMI has timed out; all previously
                active or inactive DLCIs are changed to this state
            (6) DLCI was detected in the traffic stream and a full
                status LMI has not been received so the state cannot
                be determined yet. "
         ::= { mfrapPerfThruputPerDlciEntry 19 }
         
   mfrapPerfThruputPerDlciOutageCount   OBJECT-TYPE
          SYNTAX      Counter
          ACCESS      read-only
          STATUS      mandatory
          DESCRIPTION
             "The number of times the smperPerfThruputPerDlciPvcState
             transitions from pvc-active or pvc-undetermined to one
             of the other (inactive) states. "
            ::= { mfrapPerfThruputPerDlciEntry 20 }

   mfrapPerfThruputPerDlciAvailability    OBJECT-TYPE
          SYNTAX      INTEGER
          ACCESS      read-only
          STATUS      mandatory
          DESCRIPTION
                "The measure of the percentage time the DLCI is
             available: UpTime/CreateTime or zero if CreateTime
             = 0. (in 1/1000 per cent; i.e. availability = 1000 
             converts to 1%). "
            ::= { mfrapPerfThruputPerDlciEntry 21 }

   mfrapPerfThruputPerDlciMTBSO    OBJECT-TYPE
          SYNTAX      INTEGER
          ACCESS      read-only
          STATUS      mandatory
          DESCRIPTION
             "Mean Time Between Service Outages: UpTime/OutageCount
             or zero if OutageCount = 0 (in seconds). "
            ::= { mfrapPerfThruputPerDlciEntry 22 }

   mfrapPerfThruputPerDlciMTTSR    OBJECT-TYPE
          SYNTAX      INTEGER
          ACCESS      read-only
          STATUS      mandatory
          DESCRIPTION
             "Mean Time to ServiceRestoral: DownTime/OutageCount
             or zero if OutageCount = 0 (in seconds). "
            ::= { mfrapPerfThruputPerDlciEntry 23 }

   mfrapPerfThruputPerDlciEncapType   OBJECT-TYPE
          SYNTAX      INTEGER
          {
            encap-na      (1),
            encap-1490    (2),
            encap-cisco   (3),
            encap-annex-g (4),
            encap-other   (5)
          }
          ACCESS      read-only
          STATUS      mandatory
          DESCRIPTION
             "The encapsulation protocol seen in the last frame
              analyzed on this DLCI:
              (1) DLCI is the LMI DLCI or no frames have been
                  analyzed
              (2) The encapsulation is per rfc1490
              (3) The encapsulation is per Cisco proprietary
              (4) The encapsulation is per Annex-G (X.25 over
                  frame relay)
              (5) The encapsulation is not one of the above. "
            ::= { mfrapPerfThruputPerDlciEntry 24 }

   mfrapPerfThruputPerDlciRxUtilizationStatus OBJECT-TYPE
             SYNTAX      INTEGER
             {
               clear                  (1),
               over-threshold         (2),
               alarm                  (3),
               alarm-under-threshold  (4)
             }
             ACCESS      read-only
             STATUS      mandatory
             DESCRIPTION
                " The status of the per-DLCI utilization
                  alarm in the receive direction.
                  (1) there is no alarm condition; utilization
                      is under the configured CIR percentage
                      threshold; if traps are enabled and the 
                      alarm had been previously triggered, a
                      utilization alarm clear trap will be sent.
                  (2) the utilization has been over the configured 
                      CIR percentage threshold for less than the
                      configured duration.
                  (3) the utilization has been over the configured 
                      CIR percentage threshold for more than the
                      configured duration; if traps are enabled
                      a utilization exceeded trap will be sent.
                  (4) the utilization has been under the configured 
                      CIR percentage threshold for less than the
                      configured duration. "
             ::= { mfrapPerfThruputPerDlciEntry 25 }
             
   mfrapPerfThruputPerDlciTxUtilizationStatus OBJECT-TYPE
             SYNTAX      INTEGER
             {
               clear                  (1),
               over-threshold         (2),
               alarm                  (3),
               alarm-under-threshold  (4)
             }
             ACCESS      read-only
             STATUS      mandatory
             DESCRIPTION
                " The status of the per-DLCI utilization
                  alarm in the transmit direction.
                  (1) there is no alarm condition; utilization
                      is under the configured CIR percentage
                      threshold; if traps are enabled and the 
                      alarm had been previously triggered, a
                      utilization alarm clear trap will be sent.
                  (2) the utilization has been over the configured 
                      CIR percentage threshold for less than the
                      configured duration.
                  (3) the utilization has been over the configured 
                      CIR percentage threshold for more than the
                      configured duration; if traps are enabled
                      a utilization exceeded trap will be sent.
                  (4) the utilization has been under the configured 
                      CIR percentage threshold for less than the
                      configured duration. "
             ::= { mfrapPerfThruputPerDlciEntry 26 }
             
   mfrapPerfThruputPerDlciEIR    OBJECT-TYPE
             SYNTAX      INTEGER
             ACCESS      read-only
             STATUS      mandatory
             DESCRIPTION
                "The Excess Information Rate.  This is defined to
                 be the maximum rate traffic is (supposed to be)
                 allowed to burst to."
            ::= { mfrapPerfThruputPerDlciEntry 27 }
             

mfrapPerfThruputCommands OBJECT IDENTIFIER ::= { mfrapPerfThruput 3 }

   mfrapPerfThruputCmdClearDteStats    OBJECT-TYPE
          SYNTAX      INTEGER
          {
              clear-statistics (1)
          }
          ACCESS      write-only
          STATUS      mandatory
          DESCRIPTION
             "Allows the user to zero out all the interface statistics in
              the DTE portion of the ThruputPerIntf statistics table.
              (1) Clear DTE interface statistics command."
          ::= { mfrapPerfThruputCommands 1 }

   mfrapPerfThruputCmdClearT1Stats    OBJECT-TYPE
          SYNTAX      INTEGER
          {
              clear-statistics (1)
          }
          ACCESS      write-only
          STATUS      mandatory
          DESCRIPTION
             "Allows the user to zero out all the interface statistics in
              the WAN portion of the ThruputPerIntf statistics table.
              (1) Clear WAN interface statistics command."
          ::= { mfrapPerfThruputCommands 2 }

   mfrapPerfThruputCmdClearAllIntfStats    OBJECT-TYPE
          SYNTAX      INTEGER
          {
              clear-statistics (1)
          }
          ACCESS      write-only
          STATUS      mandatory
          DESCRIPTION
             "Allows the user to zero out all the statistics in
              the ThruputPerIntf statistics table.
              (1) Clear all interface statistics command."
          ::= { mfrapPerfThruputCommands 3 }

   mfrapPerfThruputCmdClearDlciStats    OBJECT-TYPE
          SYNTAX      INTEGER
          {
              clear-statistics (1)
          }
          ACCESS      write-only
          STATUS      mandatory
          DESCRIPTION
             "Allows the user to zero out all the per-DLCI statistics
              in the ThruputPerDlci statistics table and the the short 
              term statistics tables.
              (1) Clear layer 2 per-DLCI statistics command."
          ::= { mfrapPerfThruputCommands 4 }

   mfrapPerfThruputCmdClearAllStats    OBJECT-TYPE
          SYNTAX      INTEGER
          {
              clear-statistics (1)
          }
          ACCESS      write-only
          STATUS      mandatory
          DESCRIPTION
             "Allows the user to zero out all the statistics
              in the ThruputPerIntf and ThruputPerDlci statistics
              tables and in the short term statistics tables.
              (1) Clear all interface and layer 2 per-DLCI statistics."
          ::= { mfrapPerfThruputCommands 5 }

   mfrapPerfThruputCmdRemoveStsDlci    OBJECT-TYPE
          SYNTAX      INTEGER
          ACCESS      write-only
          STATUS      mandatory
          DESCRIPTION
             "Allows the user to remove a Dlci from the short term 
              statistics tables."
          ::= { mfrapPerfThruputCommands 6 }

   mfrapPerfThruputCmdReplaceDlciTable    OBJECT-TYPE
          SYNTAX      SEQUENCE OF MfrapPerfThruputCmdReplaceDlciEntry
          ACCESS      not-accessible
          STATUS      mandatory
          DESCRIPTION
             "Allows the user to replace one DLCI in the short-term
              statistics table with another one."
          ::= { mfrapPerfThruputCommands 7 }

          mfrapPerfThruputCmdReplaceDlciEntry   OBJECT-TYPE
          SYNTAX  MfrapPerfThruputCmdReplaceDlciEntry
          ACCESS  not-accessible
          STATUS  mandatory
          DESCRIPTION
                "Allows the user to replace one DLCI in the short-term
                 statistics table with another one."
          INDEX { mfrapPerfThruputCmdReplaceDlciValue }
          ::= { mfrapPerfThruputCmdReplaceDlciTable 1 }

      MfrapPerfThruputCmdReplaceDlciEntry ::=
           SEQUENCE {
               mfrapPerfThruputCmdReplaceDlciValue     INTEGER,
               mfrapPerfThruputCmdReplaceDlciNewValue  INTEGER
           }
            
          mfrapPerfThruputCmdReplaceDlciValue  OBJECT-TYPE
             SYNTAX  INTEGER
             ACCESS  read-only
             STATUS  mandatory
             DESCRIPTION
                "A Dlci that is in the short-term stats table.  Index by
                 this Dlci value to identify the statistics entry to be
                 replaced."
             ::= { mfrapPerfThruputCmdReplaceDlciEntry 1 }

          mfrapPerfThruputCmdReplaceDlciNewValue  OBJECT-TYPE
             SYNTAX  INTEGER
             ACCESS  write-only
             STATUS  mandatory
             DESCRIPTION
                "A Dlci that is to replace another in the short-term stats 
                 table.  Index by this Dlci value to identify the statistics 
                 entry to do the replacing."
             ::= { mfrapPerfThruputCmdReplaceDlciEntry 2 }

   mfrapPerfThruputCmdAvailabilityStsDlciReset    OBJECT-TYPE
          SYNTAX      INTEGER
          ACCESS      write-only
          STATUS      mandatory
          DESCRIPTION
             "Allows the user to reset the availability
              statistics of an individual Dlci within
              the short-term stats table."
          ::= { mfrapPerfThruputCommands 8 }

   mfrapPerfThruputCmdAvailabilityStsDlciResetAll    OBJECT-TYPE
          SYNTAX      INTEGER
          ACCESS      write-only
          STATUS      mandatory
          DESCRIPTION
             "Allows the user to reset the availability
              statistics of all Dlci's within the short-term
              stats table."
          ::= { mfrapPerfThruputCommands 9 }

   mfrapPerfThruputCmdCountsStsDlciReset    OBJECT-TYPE
          SYNTAX      INTEGER
          ACCESS      write-only
          STATUS      mandatory
          DESCRIPTION
             "Allows the user to reset the count 
              statistics of an individual Dlci within
              the short-term stats table."
          ::= { mfrapPerfThruputCommands 10 }

   mfrapPerfThruputCmdCountsStsDlciResetAll    OBJECT-TYPE
          SYNTAX      INTEGER
          ACCESS      write-only
          STATUS      mandatory
          DESCRIPTION
             "Allows the user to reset the count
              statistics of all Dlci's within the short-term
              stats table."
          ::= { mfrapPerfThruputCommands 11 }

   mfrapPerfThruputCmdAllStsDlciReset    OBJECT-TYPE
          SYNTAX      INTEGER
          ACCESS      write-only
          STATUS      mandatory
          DESCRIPTION
             "Allows the user to reset both the count 
              and availability statistics of an individual Dlci within
              the short-term stats table."
          ::= { mfrapPerfThruputCommands 12 }

   mfrapPerfThruputCmdAllStsDlciResetAll    OBJECT-TYPE
          SYNTAX      INTEGER
          ACCESS      write-only
          STATUS      mandatory
          DESCRIPTION
             "Allows the user to reset both the count and the
              availability statistics of all Dlci's within the short-term
              stats table."
          ::= { mfrapPerfThruputCommands 13 }



mfrapPerfNetworkShortTerm OBJECT IDENTIFIER ::= { mfrapPerformance 4 }

   --  Network Layer Short Term Statistics for each DLCI.

   mfrapPerfNetwProtoPerDlciTable OBJECT-TYPE
         SYNTAX   SEQUENCE OF MfrapPerfNetwProtoPerDlciEntry
         ACCESS   not-accessible
         STATUS   mandatory
         DESCRIPTION
            "The Short Term Statistics on the Network Layer
             protocol for each DLCI. These are protocol-based
             per-DLCI statistics. The Short Term model maintains
             three intervals: current, previous, and cumulative
             totals. Interval duration is defined by the Short Term
             Timer (CfgFrPerfTimersSTInterval)."
         ::= { mfrapPerfNetworkShortTerm 1 }

         mfrapPerfNetwProtoPerDlciEntry OBJECT-TYPE
             SYNTAX   MfrapPerfNetwProtoPerDlciEntry
             ACCESS   not-accessible
             STATUS   mandatory
             DESCRIPTION
                "The Network Layer Short Term Statistics
                 for a particular DLCI. This table organizes
                 statistics by high-layer network protocol."
            INDEX { mfrapPerfNetwProtoPerDlciInterval,
                    mfrapPerfNetwProtoPerDlciValue }
            ::= { mfrapPerfNetwProtoPerDlciTable 1 }

         MfrapPerfNetwProtoPerDlciEntry ::=
             SEQUENCE {
                 mfrapPerfNetwProtoPerDlciInterval  INTEGER,
                 mfrapPerfNetwProtoPerDlciValue     INTEGER,
                 mfrapPerfNetwProtoPerDlciRxTotal   Counter,
                 mfrapPerfNetwProtoPerDlciTxTotal   Counter,
                 mfrapPerfNetwProtoPerDlciRxIp      Counter,
                 mfrapPerfNetwProtoPerDlciTxIp      Counter,
                 mfrapPerfNetwProtoPerDlciRxIpx     Counter,
                 mfrapPerfNetwProtoPerDlciTxIpx     Counter,
                 mfrapPerfNetwProtoPerDlciRxSna     Counter,
                 mfrapPerfNetwProtoPerDlciTxSna     Counter,
                 mfrapPerfNetwProtoPerDlciRxArp     Counter,
                 mfrapPerfNetwProtoPerDlciTxArp     Counter,
                 mfrapPerfNetwProtoPerDlciRxCisco   Counter,
                 mfrapPerfNetwProtoPerDlciTxCisco   Counter,
                 mfrapPerfNetwProtoPerDlciRxOther   Counter,
                 mfrapPerfNetwProtoPerDlciTxOther   Counter,
                 mfrapPerfNetwProtoPerDlciRxVnip    Counter,
                 mfrapPerfNetwProtoPerDlciTxVnip    Counter,
                 mfrapPerfNetwProtoPerDlciRxAnnexG  Counter,
                 mfrapPerfNetwProtoPerDlciTxAnnexG  Counter
             }

      mfrapPerfNetwProtoPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfNetwProtoPerDlciEntry 1 }

      mfrapPerfNetwProtoPerDlciValue    OBJECT-TYPE
             SYNTAX      INTEGER 
             ACCESS      read-only
             STATUS      mandatory
             DESCRIPTION
                "The DLCI value with which the Statistics are associated."
            ::= { mfrapPerfNetwProtoPerDlciEntry 2 }

      mfrapPerfNetwProtoPerDlciRxTotal    OBJECT-TYPE
             SYNTAX      Counter 
             ACCESS      read-only
             STATUS      mandatory
             DESCRIPTION
                "The total number of received Network Layer bytes
                 that have been counted on this DLCI."
            ::= { mfrapPerfNetwProtoPerDlciEntry 3 }

      mfrapPerfNetwProtoPerDlciTxTotal    OBJECT-TYPE
             SYNTAX      Counter
             ACCESS      read-only
             STATUS      mandatory
             DESCRIPTION
                "The total number of transmitted Network Layer bytes
                 that have been counted on this DLCI."
            ::= { mfrapPerfNetwProtoPerDlciEntry 4 }

      mfrapPerfNetwProtoPerDlciRxIp    OBJECT-TYPE
             SYNTAX      Counter
             ACCESS      read-only
             STATUS      mandatory
             DESCRIPTION
                "The number of received IP bytes
                 that have been counted on this DLCI."
            ::= { mfrapPerfNetwProtoPerDlciEntry 5 }

      mfrapPerfNetwProtoPerDlciTxIp    OBJECT-TYPE
             SYNTAX      Counter
             ACCESS      read-only
             STATUS      mandatory
             DESCRIPTION
                "The number of transmitted IP bytes
                 that have been counted on this DLCI."
            ::= { mfrapPerfNetwProtoPerDlciEntry 6 }

      mfrapPerfNetwProtoPerDlciRxIpx    OBJECT-TYPE
             SYNTAX      Counter
             ACCESS      read-only
             STATUS      mandatory
             DESCRIPTION
                "The number of received IPX bytes
                 that have been counted on this DLCI."
            ::= { mfrapPerfNetwProtoPerDlciEntry 7 }

      mfrapPerfNetwProtoPerDlciTxIpx    OBJECT-TYPE
             SYNTAX      Counter
             ACCESS      read-only
             STATUS      mandatory
             DESCRIPTION
                "The number of transmitted IPX bytes
                 that have been counted on this DLCI."
            ::= { mfrapPerfNetwProtoPerDlciEntry 8 }

      mfrapPerfNetwProtoPerDlciRxSna    OBJECT-TYPE
             SYNTAX      Counter
             ACCESS      read-only
             STATUS      mandatory
             DESCRIPTION
                "The number of received SNA bytes
                 that have been counted on this DLCI."
            ::= { mfrapPerfNetwProtoPerDlciEntry 9 }

      mfrapPerfNetwProtoPerDlciTxSna    OBJECT-TYPE
             SYNTAX      Counter
             ACCESS      read-only
             STATUS      mandatory
             DESCRIPTION
                "The number of transmitted SNA bytes
                 that have been counted on this DLCI."
            ::= { mfrapPerfNetwProtoPerDlciEntry 10 }

      mfrapPerfNetwProtoPerDlciRxArp    OBJECT-TYPE
             SYNTAX      Counter
             ACCESS      read-only
             STATUS      mandatory
             DESCRIPTION
                "The number of received ARP bytes
                 that have been counted on this DLCI."
            ::= { mfrapPerfNetwProtoPerDlciEntry 11 }

      mfrapPerfNetwProtoPerDlciTxArp    OBJECT-TYPE
             SYNTAX      Counter
             ACCESS      read-only
             STATUS      mandatory
             DESCRIPTION
                "The number of transmitted ARP bytes
                 that have been counted on this DLCI."
            ::= { mfrapPerfNetwProtoPerDlciEntry 12 }

      mfrapPerfNetwProtoPerDlciRxCisco    OBJECT-TYPE
             SYNTAX      Counter
             ACCESS      read-only
             STATUS      mandatory
             DESCRIPTION
                "The number of received Cisco protocol bytes
                 that have been counted on this DLCI."
            ::= { mfrapPerfNetwProtoPerDlciEntry 13 }

      mfrapPerfNetwProtoPerDlciTxCisco    OBJECT-TYPE
             SYNTAX      Counter
             ACCESS      read-only
             STATUS      mandatory
             DESCRIPTION
                "The number of transmitted Cisco protocol bytes
                 that have been counted on this DLCI."
            ::= { mfrapPerfNetwProtoPerDlciEntry 14 }

      mfrapPerfNetwProtoPerDlciRxOther    OBJECT-TYPE
             SYNTAX      Counter
             ACCESS      read-only
             STATUS      mandatory
             DESCRIPTION
                "The number of received bytes on this DLCI
                 from protocols that are not counted elsewhere
                 in this table."
            ::= { mfrapPerfNetwProtoPerDlciEntry 15 }

      mfrapPerfNetwProtoPerDlciTxOther    OBJECT-TYPE
             SYNTAX      Counter
             ACCESS      read-only
             STATUS      mandatory
             DESCRIPTION
                "The number of transmitted bytes on this DLCI
                 from protocols that are not counted elsewhere
                 in this table."
            ::= { mfrapPerfNetwProtoPerDlciEntry 16 }

      mfrapPerfNetwProtoPerDlciRxVnip    OBJECT-TYPE
             SYNTAX      Counter 
             ACCESS      read-only
             STATUS      mandatory
             DESCRIPTION
                "The number of received VNIP protocol bytes
                 that have been counted on this DLCI."
            ::= { mfrapPerfNetwProtoPerDlciEntry 17 }

      mfrapPerfNetwProtoPerDlciTxVnip    OBJECT-TYPE
             SYNTAX      Counter 
             ACCESS      read-only
             STATUS      mandatory
             DESCRIPTION
                "The number of transmitted VNIP protocol bytes
                 that have been counted on this DLCI."
            ::= { mfrapPerfNetwProtoPerDlciEntry 18 }

      mfrapPerfNetwProtoPerDlciRxAnnexG  OBJECT-TYPE
             SYNTAX      Counter 
             ACCESS      read-only
             STATUS      mandatory
             DESCRIPTION
                "The number of received Annex G protocol 
                 bytes that have been counted on this DLCI."
            ::= { mfrapPerfNetwProtoPerDlciEntry 19 }

      mfrapPerfNetwProtoPerDlciTxAnnexG  OBJECT-TYPE
             SYNTAX      Counter 
             ACCESS      read-only
             STATUS      mandatory
             DESCRIPTION
                "The number of transmitted Annex G protocol 
                 bytes that have been counted on this DLCI."
            ::= { mfrapPerfNetwProtoPerDlciEntry 20 }





   --  Network Layer Short Term Statistics totals.

   mfrapPerfNetwProtoTotalTable OBJECT-TYPE
         SYNTAX   SEQUENCE OF MfrapPerfNetwProtoTotalEntry
         ACCESS   not-accessible
         STATUS   mandatory
         DESCRIPTION
            "The Short Term Statistics on Network Layer
            protocols summed across all DLCIs."
         ::= { mfrapPerfNetworkShortTerm 2 }

         mfrapPerfNetwProtoTotalEntry OBJECT-TYPE
             SYNTAX   MfrapPerfNetwProtoTotalEntry
             ACCESS   not-accessible
             STATUS   mandatory
             DESCRIPTION
                "The Network Layer Short Term Statistics
                 for a particular DLCI."
             INDEX { mfrapPerfNetwProtoTotalInterval }
            ::= { mfrapPerfNetwProtoTotalTable 1 }

         MfrapPerfNetwProtoTotalEntry ::=
             SEQUENCE {
                 mfrapPerfNetwProtoTotalInterval  INTEGER,
                 mfrapPerfNetwProtoTotalRxTotal   Counter,
                 mfrapPerfNetwProtoTotalTxTotal   Counter,
                 mfrapPerfNetwProtoTotalRxIp      Counter,
                 mfrapPerfNetwProtoTotalTxIp      Counter,
                 mfrapPerfNetwProtoTotalRxIpx     Counter,
                 mfrapPerfNetwProtoTotalTxIpx     Counter,
                 mfrapPerfNetwProtoTotalRxSna     Counter,
                 mfrapPerfNetwProtoTotalTxSna     Counter,
                 mfrapPerfNetwProtoTotalRxArp     Counter,
                 mfrapPerfNetwProtoTotalTxArp     Counter,
                 mfrapPerfNetwProtoTotalRxCisco   Counter,
                 mfrapPerfNetwProtoTotalTxCisco   Counter,
                 mfrapPerfNetwProtoTotalRxOther   Counter,
                 mfrapPerfNetwProtoTotalTxOther   Counter,
                 mfrapPerfNetwProtoTotalRxVnip    Counter,
                 mfrapPerfNetwProtoTotalTxVnip    Counter,
                 mfrapPerfNetwProtoTotalRxAnnexG  Counter,
                 mfrapPerfNetwProtoTotalTxAnnexG  Counter
             }

      mfrapPerfNetwProtoTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfNetwProtoTotalEntry 1 }

      mfrapPerfNetwProtoTotalRxTotal    OBJECT-TYPE
             SYNTAX      Counter 
             ACCESS      read-only
             STATUS      mandatory
             DESCRIPTION
                "The total number of received Network Layer bytes
                 that have been counted on this DLCI."
            ::= { mfrapPerfNetwProtoTotalEntry 3 }

      mfrapPerfNetwProtoTotalTxTotal    OBJECT-TYPE
             SYNTAX      Counter 
             ACCESS      read-only
             STATUS      mandatory
             DESCRIPTION
                "The total number of transmitted Network Layer bytes
                 that have been counted on this DLCI."
            ::= { mfrapPerfNetwProtoTotalEntry 4 }

      mfrapPerfNetwProtoTotalRxIp    OBJECT-TYPE
             SYNTAX      Counter 
             ACCESS      read-only
             STATUS      mandatory
             DESCRIPTION
                "The number of received IP bytes
                 that have been counted on this DLCI."
            ::= { mfrapPerfNetwProtoTotalEntry 5 }

      mfrapPerfNetwProtoTotalTxIp    OBJECT-TYPE
             SYNTAX      Counter
             ACCESS      read-only
             STATUS      mandatory
             DESCRIPTION
                "The number of transmitted IP bytes
                 that have been counted on this DLCI."
            ::= { mfrapPerfNetwProtoTotalEntry 6 }

      mfrapPerfNetwProtoTotalRxIpx    OBJECT-TYPE
             SYNTAX      Counter
             ACCESS      read-only
             STATUS      mandatory
             DESCRIPTION
                "The number of received IPX bytes
                 that have been counted on this DLCI."
            ::= { mfrapPerfNetwProtoTotalEntry 7 }

      mfrapPerfNetwProtoTotalTxIpx    OBJECT-TYPE
             SYNTAX      Counter
             ACCESS      read-only
             STATUS      mandatory
             DESCRIPTION
                "The number of transmitted IPX bytes
                 that have been counted on this DLCI."
            ::= { mfrapPerfNetwProtoTotalEntry 8 }

      mfrapPerfNetwProtoTotalRxSna    OBJECT-TYPE
             SYNTAX      Counter
             ACCESS      read-only
             STATUS      mandatory
             DESCRIPTION
                "The number of received SNA bytes
                 that have been counted on this DLCI."
            ::= { mfrapPerfNetwProtoTotalEntry 9 }

      mfrapPerfNetwProtoTotalTxSna    OBJECT-TYPE
             SYNTAX      Counter
             ACCESS      read-only
             STATUS      mandatory
             DESCRIPTION
                "The number of transmitted SNA bytes
                 that have been counted on this DLCI."
            ::= { mfrapPerfNetwProtoTotalEntry 10 }

      mfrapPerfNetwProtoTotalRxArp    OBJECT-TYPE
             SYNTAX      Counter
             ACCESS      read-only
             STATUS      mandatory
             DESCRIPTION
                "The number of received ARP bytes
                 that have been counted on this DLCI."
            ::= { mfrapPerfNetwProtoTotalEntry 11 }

      mfrapPerfNetwProtoTotalTxArp    OBJECT-TYPE
             SYNTAX      Counter
             ACCESS      read-only
             STATUS      mandatory
             DESCRIPTION
                "The number of transmitted ARP bytes
                 that have been counted on this DLCI."
            ::= { mfrapPerfNetwProtoTotalEntry 12 }

      mfrapPerfNetwProtoTotalRxCisco    OBJECT-TYPE
             SYNTAX      Counter
             ACCESS      read-only
             STATUS      mandatory
             DESCRIPTION
                "The number of received Cisco protocol bytes
                 that have been counted on this DLCI."
            ::= { mfrapPerfNetwProtoTotalEntry 13 }

      mfrapPerfNetwProtoTotalTxCisco    OBJECT-TYPE
             SYNTAX      Counter
             ACCESS      read-only
             STATUS      mandatory
             DESCRIPTION
                "The number of transmitted Cisco protocol bytes
                 that have been counted on this DLCI."
            ::= { mfrapPerfNetwProtoTotalEntry 14 }

      mfrapPerfNetwProtoTotalRxOther    OBJECT-TYPE
             SYNTAX      Counter
             ACCESS      read-only
             STATUS      mandatory
             DESCRIPTION
                "The number of received bytes on this DLCI
                 from protocols that are not counted elsewhere
                 in this table."
            ::= { mfrapPerfNetwProtoTotalEntry 15 }

      mfrapPerfNetwProtoTotalTxOther    OBJECT-TYPE
             SYNTAX      Counter
             ACCESS      read-only
             STATUS      mandatory
             DESCRIPTION
                "The number of transmitted bytes on this DLCI
                 from protocols that are not counted elsewhere
                 in this table."
            ::= { mfrapPerfNetwProtoTotalEntry 16 }

      mfrapPerfNetwProtoTotalRxVnip    OBJECT-TYPE
             SYNTAX      Counter 
             ACCESS      read-only
             STATUS      mandatory
             DESCRIPTION
                "The number of received VNIP protocol bytes
                 that have been counted on this DLCI."
            ::= { mfrapPerfNetwProtoTotalEntry 17 }

      mfrapPerfNetwProtoTotalTxVnip    OBJECT-TYPE
             SYNTAX      Counter 
             ACCESS      read-only
             STATUS      mandatory
             DESCRIPTION
                "The number of transmitted VNIP protocol bytes
                 that have been counted on this DLCI."
            ::= { mfrapPerfNetwProtoTotalEntry 18 }

      mfrapPerfNetwProtoTotalRxAnnexG  OBJECT-TYPE
             SYNTAX      Counter 
             ACCESS      read-only
             STATUS      mandatory
             DESCRIPTION
                "The number of received Annex G protocol bytes
                 that have been counted on this DLCI."
            ::= { mfrapPerfNetwProtoTotalEntry 19 }

      mfrapPerfNetwProtoTotalTxAnnexG  OBJECT-TYPE
             SYNTAX      Counter 
             ACCESS      read-only
             STATUS      mandatory
             DESCRIPTION
                "The number of transmitted Annex G protocol bytes
                 that have been counted on this DLCI."
            ::= { mfrapPerfNetwProtoTotalEntry 20 }


   --  IP Short Term Statistics for each DLCI.

   mfrapPerfIpPerDlciTable OBJECT-TYPE
         SYNTAX   SEQUENCE OF MfrapPerfIpPerDlciEntry
         ACCESS   not-accessible
         STATUS   mandatory
         DESCRIPTION
            "The Short Term Statistics on the IP
             protocol for each DLCI."
         ::= { mfrapPerfNetworkShortTerm 3 }

         mfrapPerfIpPerDlciEntry OBJECT-TYPE
             SYNTAX   MfrapPerfIpPerDlciEntry
             ACCESS   not-accessible
             STATUS   mandatory
             DESCRIPTION
                "The IP Short Term Statistics for a particular DLCI."
             INDEX { mfrapPerfIpPerDlciInterval, mfrapPerfIpPerDlciValue }
            ::= { mfrapPerfIpPerDlciTable 1 }

         MfrapPerfIpPerDlciEntry ::=
             SEQUENCE {
                 mfrapPerfIpPerDlciInterval  INTEGER,
                 mfrapPerfIpPerDlciValue     INTEGER,
                 mfrapPerfIpPerDlciRxTotal   Counter,
                 mfrapPerfIpPerDlciTxTotal   Counter,
                 mfrapPerfIpPerDlciRxTcp     Counter,
                 mfrapPerfIpPerDlciTxTcp     Counter,
                 mfrapPerfIpPerDlciRxUdp     Counter,
                 mfrapPerfIpPerDlciTxUdp     Counter,
                 mfrapPerfIpPerDlciRxIcmp    Counter,
                 mfrapPerfIpPerDlciTxIcmp    Counter,
                 mfrapPerfIpPerDlciRxOther   Counter,
                 mfrapPerfIpPerDlciTxOther   Counter,
                 mfrapPerfIpPerDlciRxIgrp    Counter,
                 mfrapPerfIpPerDlciTxIgrp    Counter
             }

      mfrapPerfIpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfIpPerDlciEntry 1 }

      mfrapPerfIpPerDlciValue    OBJECT-TYPE
             SYNTAX      INTEGER 
             ACCESS      read-only
             STATUS      mandatory
             DESCRIPTION
                "The DLCI value with which the Statistics are associated."
            ::= { mfrapPerfIpPerDlciEntry 2 }

      mfrapPerfIpPerDlciRxTotal    OBJECT-TYPE
             SYNTAX      Counter 
             ACCESS      read-only
             STATUS      mandatory
             DESCRIPTION
                "The total number of received IP bytes
                 that have been counted on this DLCI."
            ::= { mfrapPerfIpPerDlciEntry 3 }

      mfrapPerfIpPerDlciTxTotal    OBJECT-TYPE
             SYNTAX      Counter
             ACCESS      read-only
             STATUS      mandatory
             DESCRIPTION
                "The total number of transmitted IP bytes
                 that have been counted on this DLCI."
            ::= { mfrapPerfIpPerDlciEntry 4 }

      mfrapPerfIpPerDlciRxTcp    OBJECT-TYPE
             SYNTAX      Counter
             ACCESS      read-only
             STATUS      mandatory
             DESCRIPTION
                "The number of received TCP over IP bytes
                 that have been counted on this DLCI."
            ::= { mfrapPerfIpPerDlciEntry 5 }

      mfrapPerfIpPerDlciTxTcp    OBJECT-TYPE
             SYNTAX      Counter
             ACCESS      read-only
             STATUS      mandatory
             DESCRIPTION
                "The number of transmitted TCP over IP bytes
                 that have been counted on this DLCI."
            ::= { mfrapPerfIpPerDlciEntry 6 }

      mfrapPerfIpPerDlciRxUdp    OBJECT-TYPE
             SYNTAX      Counter
             ACCESS      read-only
             STATUS      mandatory
             DESCRIPTION
                "The number of received UDP over IP bytes
                 that have been counted on this DLCI."
            ::= { mfrapPerfIpPerDlciEntry 7 }

      mfrapPerfIpPerDlciTxUdp    OBJECT-TYPE
             SYNTAX      Counter
             ACCESS      read-only
             STATUS      mandatory
             DESCRIPTION
                "The number of transmitted UDP over IP bytes
                 that have been counted on this DLCI."
            ::= { mfrapPerfIpPerDlciEntry 8 }

      mfrapPerfIpPerDlciRxIcmp    OBJECT-TYPE
             SYNTAX      Counter
             ACCESS      read-only
             STATUS      mandatory
             DESCRIPTION
                "The number of received ICMP over IP bytes
                 that have been counted on this DLCI."
            ::= { mfrapPerfIpPerDlciEntry 9 }

      mfrapPerfIpPerDlciTxIcmp    OBJECT-TYPE
             SYNTAX      Counter
             ACCESS      read-only
             STATUS      mandatory
             DESCRIPTION
                "The number of transmitted ICMP over IP bytes
                 that have been counted on this DLCI."
            ::= { mfrapPerfIpPerDlciEntry 10 }

      mfrapPerfIpPerDlciRxOther    OBJECT-TYPE
             SYNTAX      Counter
             ACCESS      read-only
             STATUS      mandatory
             DESCRIPTION
                "The number of received bytes on this DLCI
                 from protocols over IP that are not counted
                 elsewhere in this table."
            ::= { mfrapPerfIpPerDlciEntry 11 }

      mfrapPerfIpPerDlciTxOther    OBJECT-TYPE
             SYNTAX      Counter
             ACCESS      read-only
             STATUS      mandatory
             DESCRIPTION
                "The number of transmitted bytes on this DLCI
                 from protocols over IP that are not counted
                 elsewhere in this table."
            ::= { mfrapPerfIpPerDlciEntry 12 }

      mfrapPerfIpPerDlciRxIgrp    OBJECT-TYPE
             SYNTAX      Counter 
             ACCESS      read-only
             STATUS      mandatory
             DESCRIPTION
                "The number of received IGRP over IP bytes
                 that have been counted on this DLCI."
            ::= { mfrapPerfIpPerDlciEntry 13 }

      mfrapPerfIpPerDlciTxIgrp    OBJECT-TYPE
             SYNTAX      Counter 
             ACCESS      read-only
             STATUS      mandatory
             DESCRIPTION
                "The number of transmitted IGRP over IP bytes
                 that have been counted on this DLCI."
            ::= { mfrapPerfIpPerDlciEntry 14 }


   --  IP Short Term Statistics totals.

   mfrapPerfIpTotalTable OBJECT-TYPE
         SYNTAX   SEQUENCE OF MfrapPerfIpTotalEntry
         ACCESS   not-accessible
         STATUS   mandatory
         DESCRIPTION
            "The Short Term Statistics on the IP
            protocol for each DLCI."
         ::= { mfrapPerfNetworkShortTerm 4 }

         mfrapPerfIpTotalEntry OBJECT-TYPE
             SYNTAX   MfrapPerfIpTotalEntry
             ACCESS   not-accessible
             STATUS   mandatory
             DESCRIPTION
                "The IP Short Term Statistics for a particular DLCI."
             INDEX { mfrapPerfIpTotalInterval }
            ::= { mfrapPerfIpTotalTable 1 }

         MfrapPerfIpTotalEntry ::=
             SEQUENCE {
                 mfrapPerfIpTotalInterval INTEGER,
                 mfrapPerfIpTotalRxTotal  Counter,
                 mfrapPerfIpTotalTxTotal  Counter,
                 mfrapPerfIpTotalRxTcp    Counter,
                 mfrapPerfIpTotalTxTcp    Counter,
                 mfrapPerfIpTotalRxUdp    Counter,
                 mfrapPerfIpTotalTxUdp    Counter,
                 mfrapPerfIpTotalRxIcmp   Counter,
                 mfrapPerfIpTotalTxIcmp   Counter,
                 mfrapPerfIpTotalRxOther  Counter,
                 mfrapPerfIpTotalTxOther  Counter,
                 mfrapPerfIpTotalRxIgrp   Counter,
                 mfrapPerfIpTotalTxIgrp   Counter
             }

      mfrapPerfIpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfIpTotalEntry 1 }

      mfrapPerfIpTotalRxTotal    OBJECT-TYPE
             SYNTAX      Counter
             ACCESS      read-only
             STATUS      mandatory
             DESCRIPTION
                "The total number of received IP bytes
                 that have been counted on this DLCI."
            ::= { mfrapPerfIpTotalEntry 3 }

      mfrapPerfIpTotalTxTotal    OBJECT-TYPE
             SYNTAX      Counter
             ACCESS      read-only
             STATUS      mandatory
             DESCRIPTION
                "The total number of transmitted IP bytes
                 that have been counted on this DLCI."
            ::= { mfrapPerfIpTotalEntry 4 }

      mfrapPerfIpTotalRxTcp    OBJECT-TYPE
             SYNTAX      Counter
             ACCESS      read-only
             STATUS      mandatory
             DESCRIPTION
                "The number of received TCP over IP bytes
                 that have been counted on this DLCI."
            ::= { mfrapPerfIpTotalEntry 5 }

      mfrapPerfIpTotalTxTcp    OBJECT-TYPE
             SYNTAX      Counter
             ACCESS      read-only
             STATUS      mandatory
             DESCRIPTION
                "The number of transmitted TCP over IP bytes
                 that have been counted on this DLCI."
            ::= { mfrapPerfIpTotalEntry 6 }

      mfrapPerfIpTotalRxUdp    OBJECT-TYPE
             SYNTAX      Counter
             ACCESS      read-only
             STATUS      mandatory
             DESCRIPTION
                "The number of received UDP over IP bytes
                 that have been counted on this DLCI."
            ::= { mfrapPerfIpTotalEntry 7 }

      mfrapPerfIpTotalTxUdp    OBJECT-TYPE
             SYNTAX      Counter
             ACCESS      read-only
             STATUS      mandatory
             DESCRIPTION
                "The number of transmitted UDP over IP bytes
                 that have been counted on this DLCI."
            ::= { mfrapPerfIpTotalEntry 8 }

      mfrapPerfIpTotalRxIcmp    OBJECT-TYPE
             SYNTAX      Counter
             ACCESS      read-only
             STATUS      mandatory
             DESCRIPTION
                "The number of received ICMP over IP bytes
                 that have been counted on this DLCI."
            ::= { mfrapPerfIpTotalEntry 9 }

      mfrapPerfIpTotalTxIcmp    OBJECT-TYPE
             SYNTAX      Counter
             ACCESS      read-only
             STATUS      mandatory
             DESCRIPTION
                "The number of transmitted ICMP over IP bytes
                 that have been counted on this DLCI."
            ::= { mfrapPerfIpTotalEntry 10 }

      mfrapPerfIpTotalRxOther    OBJECT-TYPE
             SYNTAX      Counter
             ACCESS      read-only
             STATUS      mandatory
             DESCRIPTION
                "The number of received bytes on this DLCI
                 from protocols over IP that are not counted
                 elsewhere in this table."
            ::= { mfrapPerfIpTotalEntry 11 }

      mfrapPerfIpTotalTxOther    OBJECT-TYPE
             SYNTAX      Counter
             ACCESS      read-only
             STATUS      mandatory
             DESCRIPTION
                "The number of transmitted bytes on this DLCI
                 from protocols over IP that are not counted
                 elsewhere in this table."
            ::= { mfrapPerfIpTotalEntry 12 }

      mfrapPerfIpTotalRxIgrp    OBJECT-TYPE
             SYNTAX      Counter 
             ACCESS      read-only
             STATUS      mandatory
             DESCRIPTION
                "The number of received IGRP over IP bytes
                 that have been counted on this DLCI."
            ::= { mfrapPerfIpTotalEntry 13 }

      mfrapPerfIpTotalTxIgrp    OBJECT-TYPE
             SYNTAX      Counter 
             ACCESS      read-only
             STATUS      mandatory
             DESCRIPTION
                "The number of transmitted IGRP over IP bytes
                 that have been counted on this DLCI."
            ::= { mfrapPerfIpTotalEntry 14 }


   --  ICMP Short Term Statistics for each DLCI.

   mfrapPerfIcmpPerDlciTable OBJECT-TYPE
         SYNTAX   SEQUENCE OF MfrapPerfIcmpPerDlciEntry
         ACCESS   not-accessible
         STATUS   mandatory
         DESCRIPTION
            "Short Term Statistics on the ICMP
             protocol for each DLCI."
         ::= { mfrapPerfNetworkShortTerm 5 }

         mfrapPerfIcmpPerDlciEntry OBJECT-TYPE
             SYNTAX   MfrapPerfIcmpPerDlciEntry
             ACCESS   not-accessible
             STATUS   mandatory
             DESCRIPTION
                "The ICMP Short Term Statistics for a particular DLCI."
            INDEX { mfrapPerfIcmpPerDlciInterval, mfrapPerfIcmpPerDlciValue }
            ::= { mfrapPerfIcmpPerDlciTable 1 }

         MfrapPerfIcmpPerDlciEntry ::=
             SEQUENCE {
                 mfrapPerfIcmpPerDlciInterval        INTEGER,
                 mfrapPerfIcmpPerDlciValue           INTEGER,
                 mfrapPerfIcmpPerDlciRxTotal         Counter,
                 mfrapPerfIcmpPerDlciTxTotal         Counter,
                 mfrapPerfIcmpPerDlciRxEchoRep       Counter,
                 mfrapPerfIcmpPerDlciTxEchoRep       Counter,
                 mfrapPerfIcmpPerDlciRxDestUnr       Counter,
                 mfrapPerfIcmpPerDlciTxDestUnr       Counter,
                 mfrapPerfIcmpPerDlciRxSrcQuench     Counter,
                 mfrapPerfIcmpPerDlciTxSrcQuench     Counter,
                 mfrapPerfIcmpPerDlciRxRedirect      Counter,
                 mfrapPerfIcmpPerDlciTxRedirect      Counter,
                 mfrapPerfIcmpPerDlciRxEchoReq       Counter,
                 mfrapPerfIcmpPerDlciTxEchoReq       Counter,
                 mfrapPerfIcmpPerDlciRxTimeExcd      Counter,
                 mfrapPerfIcmpPerDlciTxTimeExcd      Counter,
                 mfrapPerfIcmpPerDlciRxParamProb     Counter,
                 mfrapPerfIcmpPerDlciTxParamProb     Counter,
                 mfrapPerfIcmpPerDlciRxTimestpReq    Counter,
                 mfrapPerfIcmpPerDlciTxTimestpReq    Counter,
                 mfrapPerfIcmpPerDlciRxTimestpRep    Counter,
                 mfrapPerfIcmpPerDlciTxTimestpRep    Counter,
                 mfrapPerfIcmpPerDlciRxAddrMaskReq   Counter,
                 mfrapPerfIcmpPerDlciTxAddrMaskReq   Counter,
                 mfrapPerfIcmpPerDlciRxAddrMaskRep   Counter,
                 mfrapPerfIcmpPerDlciTxAddrMaskRep   Counter,
                 mfrapPerfIcmpPerDlciRxPktTooBig     Counter,
                 mfrapPerfIcmpPerDlciTxPktTooBig     Counter,
                 mfrapPerfIcmpPerDlciRxGmQuery       Counter,
                 mfrapPerfIcmpPerDlciTxGmQuery       Counter,
                 mfrapPerfIcmpPerDlciRxGmReport      Counter,
                 mfrapPerfIcmpPerDlciTxGmReport      Counter,
                 mfrapPerfIcmpPerDlciRxGmReduct      Counter,
                 mfrapPerfIcmpPerDlciTxGmReduct      Counter
             }

      mfrapPerfIcmpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfIcmpPerDlciEntry 1 }

      mfrapPerfIcmpPerDlciValue    OBJECT-TYPE
             SYNTAX      INTEGER 
            ACCESS      read-only
             STATUS      mandatory
             DESCRIPTION
                "The DLCI value in which the Statistics are associated."
            ::= { mfrapPerfIcmpPerDlciEntry 2 }

      mfrapPerfIcmpPerDlciRxTotal    OBJECT-TYPE
             SYNTAX      Counter
             ACCESS      read-only
             STATUS      mandatory
             DESCRIPTION
                "The total number of ICMP bytes that have been
                 counted on this DLCI."
            ::= { mfrapPerfIcmpPerDlciEntry 3 }

      mfrapPerfIcmpPerDlciTxTotal    OBJECT-TYPE
             SYNTAX      Counter
             ACCESS      read-only
               STATUS      mandatory
             DESCRIPTION
                "The total number of ICMP bytes that have been
                 counted on this DLCI."
            ::= { mfrapPerfIcmpPerDlciEntry 4 }

      mfrapPerfIcmpPerDlciRxEchoRep    OBJECT-TYPE
             SYNTAX      Counter
             ACCESS      read-only
             STATUS      mandatory
             DESCRIPTION
                "The number of bytes in ICMP ECHO repies
                 that have been counted on this DLCI."
            ::= { mfrapPerfIcmpPerDlciEntry 5 }

      mfrapPerfIcmpPerDlciTxEchoRep    OBJECT-TYPE
             SYNTAX      Counter
             ACCESS      read-only
             STATUS      mandatory
             DESCRIPTION
                "The number of bytes in ICMP ECHO repies
                 that have been counted on this DLCI."
            ::= { mfrapPerfIcmpPerDlciEntry 6 }

      mfrapPerfIcmpPerDlciRxDestUnr    OBJECT-TYPE
             SYNTAX      Counter
             ACCESS      read-only
             STATUS      mandatory
             DESCRIPTION
                "The number of bytes in ICMP destination unreachables
                 that have been counted on this DLCI."
            ::= { mfrapPerfIcmpPerDlciEntry 7 }

      mfrapPerfIcmpPerDlciTxDestUnr    OBJECT-TYPE
             SYNTAX      Counter
             ACCESS      read-only
             STATUS      mandatory
             DESCRIPTION
                "The number of bytes in ICMP destination unreachables
                 that have been counted on this DLCI."
            ::= { mfrapPerfIcmpPerDlciEntry 8 }

      mfrapPerfIcmpPerDlciRxSrcQuench    OBJECT-TYPE
             SYNTAX      Counter
             ACCESS      read-only
             STATUS      mandatory
             DESCRIPTION
                "The number of bytes in ICMP source quenches
                 that have been counted on this DLCI."
            ::= { mfrapPerfIcmpPerDlciEntry 9 }

      mfrapPerfIcmpPerDlciTxSrcQuench    OBJECT-TYPE
             SYNTAX      Counter
             ACCESS      read-only
             STATUS      mandatory
             DESCRIPTION
                "The number of bytes in ICMP source quenches
                 that have been counted on this DLCI."
            ::= { mfrapPerfIcmpPerDlciEntry 10 }

      mfrapPerfIcmpPerDlciRxRedirect    OBJECT-TYPE
             SYNTAX      Counter
             ACCESS      read-only
             STATUS      mandatory
             DESCRIPTION
                "The number of bytes in ICMP redirects
                 that have been counted on this DLCI."
            ::= { mfrapPerfIcmpPerDlciEntry 11 }

      mfrapPerfIcmpPerDlciTxRedirect    OBJECT-TYPE
             SYNTAX      Counter
             ACCESS      read-only
             STATUS      mandatory
             DESCRIPTION
                "The number of bytes in ICMP redirects
                 that have been counted on this DLCI."
            ::= { mfrapPerfIcmpPerDlciEntry 12 }

      mfrapPerfIcmpPerDlciRxEchoReq    OBJECT-TYPE
             SYNTAX      Counter
             ACCESS      read-only
             STATUS      mandatory
             DESCRIPTION
                "The number of bytes in ICMP ECHO requests
                 that have been counted on this DLCI."
            ::= { mfrapPerfIcmpPerDlciEntry 13 }

      mfrapPerfIcmpPerDlciTxEchoReq    OBJECT-TYPE
             SYNTAX      Counter
             ACCESS      read-only
             STATUS      mandatory
             DESCRIPTION
                "The number of bytes in ICMP ECHO requests
                 that have been counted on this DLCI."
            ::= { mfrapPerfIcmpPerDlciEntry 14 }

      mfrapPerfIcmpPerDlciRxTimeExcd    OBJECT-TYPE
             SYNTAX      Counter
             ACCESS      read-only
             STATUS      mandatory
             DESCRIPTION
                "The number of bytes in ICMP time exceededs
                 that have been counted on this DLCI."
            ::= { mfrapPerfIcmpPerDlciEntry 15 }

      mfrapPerfIcmpPerDlciTxTimeExcd    OBJECT-TYPE
             SYNTAX      Counter
             ACCESS      read-only
             STATUS      mandatory
             DESCRIPTION
                "The number of bytes in ICMP time exceededs
                 that have been counted on this DLCI."
            ::= { mfrapPerfIcmpPerDlciEntry 16 }

      mfrapPerfIcmpPerDlciRxParamProb    OBJECT-TYPE
             SYNTAX      Counter
             ACCESS      read-only
             STATUS      mandatory
             DESCRIPTION
                "The number of bytes in ICMP parameter problems
                 that have been counted on this DLCI."
            ::= { mfrapPerfIcmpPerDlciEntry 17 }

      mfrapPerfIcmpPerDlciTxParamProb    OBJECT-TYPE
             SYNTAX      Counter
             ACCESS      read-only
             STATUS      mandatory
             DESCRIPTION
                "The number of bytes in ICMP parameter problems
                 that have been counted on this DLCI."
            ::= { mfrapPerfIcmpPerDlciEntry 18 }

      mfrapPerfIcmpPerDlciRxTimestpReq    OBJECT-TYPE
             SYNTAX      Counter
             ACCESS      read-only
             STATUS      mandatory
             DESCRIPTION
                "The number of bytes in ICMP timestamp requests
                 that have been counted on this DLCI."
            ::= { mfrapPerfIcmpPerDlciEntry 19 }

      mfrapPerfIcmpPerDlciTxTimestpReq    OBJECT-TYPE
             SYNTAX      Counter
             ACCESS      read-only
             STATUS      mandatory
             DESCRIPTION
                "The number of bytes in ICMP timestamp requests
                 that have been counted on this DLCI."
            ::= { mfrapPerfIcmpPerDlciEntry 20 }

      mfrapPerfIcmpPerDlciRxTimestpRep    OBJECT-TYPE
             SYNTAX      Counter
             ACCESS      read-only
             STATUS      mandatory
             DESCRIPTION
                "The number of bytes in ICMP timestamp replies
                 that have been counted on this DLCI."
            ::= { mfrapPerfIcmpPerDlciEntry 21 }

      mfrapPerfIcmpPerDlciTxTimestpRep    OBJECT-TYPE
             SYNTAX      Counter
             ACCESS      read-only
             STATUS      mandatory
             DESCRIPTION
                "The number of bytes in ICMP timestamp replies
                 that have been counted on this DLCI."
            ::= { mfrapPerfIcmpPerDlciEntry 22 }

      mfrapPerfIcmpPerDlciRxAddrMaskReq    OBJECT-TYPE
             SYNTAX      Counter
             ACCESS      read-only
             STATUS      mandatory
             DESCRIPTION
                "The number of bytes in ICMP address mask requests
                 that have been counted on this DLCI."
            ::= { mfrapPerfIcmpPerDlciEntry 23 }

      mfrapPerfIcmpPerDlciTxAddrMaskReq    OBJECT-TYPE
             SYNTAX      Counter
             ACCESS      read-only
             STATUS      mandatory
             DESCRIPTION
                "The number of bytes in ICMP address mask requests
                 that have been counted on this DLCI."
            ::= { mfrapPerfIcmpPerDlciEntry 24 }

      mfrapPerfIcmpPerDlciRxAddrMaskRep    OBJECT-TYPE
             SYNTAX      Counter
             ACCESS      read-only
             STATUS      mandatory
             DESCRIPTION
                "The number of bytes in ICMP address mask replies
                 that have been counted on this DLCI."
            ::= { mfrapPerfIcmpPerDlciEntry 25 }

      mfrapPerfIcmpPerDlciTxAddrMaskRep    OBJECT-TYPE
             SYNTAX      Counter
             ACCESS      read-only
             STATUS      mandatory
             DESCRIPTION
                "The number of bytes in ICMP address mask replies
                 that have been counted on this DLCI."
            ::= { mfrapPerfIcmpPerDlciEntry 26 }

      mfrapPerfIcmpPerDlciRxPktTooBig    OBJECT-TYPE
             SYNTAX      Counter
             ACCESS      read-only
             STATUS      mandatory
             DESCRIPTION
                "The number of bytes in ICMP packet too bigs
                 that have been counted on this DLCI."
            ::= { mfrapPerfIcmpPerDlciEntry 27 }

      mfrapPerfIcmpPerDlciTxPktTooBig    OBJECT-TYPE
             SYNTAX      Counter
             ACCESS      read-only
             STATUS      mandatory
             DESCRIPTION
                "The number of bytes in ICMP packet too bigs
                 that have been counted on this DLCI."
            ::= { mfrapPerfIcmpPerDlciEntry 28 }

      mfrapPerfIcmpPerDlciRxGmQuery    OBJECT-TYPE
             SYNTAX      Counter
             ACCESS      read-only
             STATUS      mandatory
             DESCRIPTION
                "The number of bytes in ICMP group membership
                 queries that have been counted on this DLCI."
            ::= { mfrapPerfIcmpPerDlciEntry 29 }

      mfrapPerfIcmpPerDlciTxGmQuery    OBJECT-TYPE
             SYNTAX      Counter
             ACCESS      read-only
             STATUS      mandatory
             DESCRIPTION
                "The number of bytes in ICMP group membership
                 queries that have been counted on this DLCI."
            ::= { mfrapPerfIcmpPerDlciEntry 30 }

      mfrapPerfIcmpPerDlciRxGmReport    OBJECT-TYPE
             SYNTAX      Counter
             ACCESS      read-only
             STATUS      mandatory
             DESCRIPTION
                "The number of bytes in ICMP group membership
                 reports that have been counted on this DLCI."
            ::= { mfrapPerfIcmpPerDlciEntry 31 }

      mfrapPerfIcmpPerDlciTxGmReport    OBJECT-TYPE
             SYNTAX      Counter
             ACCESS      read-only
             STATUS      mandatory
             DESCRIPTION
                "The number of bytes in ICMP group membership
                 reports that have been counted on this DLCI."
            ::= { mfrapPerfIcmpPerDlciEntry 32 }

      mfrapPerfIcmpPerDlciRxGmReduct    OBJECT-TYPE
             SYNTAX      Counter
             ACCESS      read-only
             STATUS      mandatory
             DESCRIPTION
                "The number of bytes in ICMP group membership
                 reductions that have been counted on this DLCI."
            ::= { mfrapPerfIcmpPerDlciEntry 33 }

      mfrapPerfIcmpPerDlciTxGmReduct    OBJECT-TYPE
             SYNTAX      Counter
             ACCESS      read-only
             STATUS      mandatory
             DESCRIPTION
                "The number of bytes in ICMP group membership
                 reductions that have been counted on this DLCI."
            ::= { mfrapPerfIcmpPerDlciEntry 34 }


   --  ICMP Short Term Statistics totals.

   mfrapPerfIcmpTotalTable OBJECT-TYPE
         SYNTAX   SEQUENCE OF MfrapPerfIcmpTotalEntry
         ACCESS   not-accessible
         STATUS   mandatory
         DESCRIPTION
            "Short Term Statistics on the ICMP
             protocol for each DLCI."
         ::= { mfrapPerfNetworkShortTerm 6 }

         mfrapPerfIcmpTotalEntry OBJECT-TYPE
             SYNTAX   MfrapPerfIcmpTotalEntry
             ACCESS   not-accessible
             STATUS   mandatory
             DESCRIPTION
                "The ICMP Short Term Statistics for a particular DLCI."
             INDEX { mfrapPerfIcmpTotalInterval }
            ::= { mfrapPerfIcmpTotalTable 1 }

         MfrapPerfIcmpTotalEntry ::=
             SEQUENCE {
                 mfrapPerfIcmpTotalInterval        INTEGER,
                 mfrapPerfIcmpTotalRxTotal         Counter,
                 mfrapPerfIcmpTotalTxTotal         Counter,
                 mfrapPerfIcmpTotalRxEchoRep       Counter,
                 mfrapPerfIcmpTotalTxEchoRep       Counter,
                 mfrapPerfIcmpTotalRxDestUnr       Counter,
                 mfrapPerfIcmpTotalTxDestUnr       Counter,
                 mfrapPerfIcmpTotalRxSrcQuench     Counter,
                 mfrapPerfIcmpTotalTxSrcQuench     Counter,
                 mfrapPerfIcmpTotalRxRedirect      Counter,
                 mfrapPerfIcmpTotalTxRedirect      Counter,
                 mfrapPerfIcmpTotalRxEchoReq       Counter,
                 mfrapPerfIcmpTotalTxEchoReq       Counter,
                 mfrapPerfIcmpTotalRxTimeExcd      Counter,
                 mfrapPerfIcmpTotalTxTimeExcd      Counter,
                 mfrapPerfIcmpTotalRxParamProb     Counter,
                 mfrapPerfIcmpTotalTxParamProb     Counter,
                 mfrapPerfIcmpTotalRxTimestpReq    Counter,
                 mfrapPerfIcmpTotalTxTimestpReq    Counter,
                 mfrapPerfIcmpTotalRxTimestpRep    Counter,
                 mfrapPerfIcmpTotalTxTimestpRep    Counter,
                 mfrapPerfIcmpTotalRxAddrMaskReq   Counter,
                 mfrapPerfIcmpTotalTxAddrMaskReq   Counter,
                 mfrapPerfIcmpTotalRxAddrMaskRep   Counter,
                 mfrapPerfIcmpTotalTxAddrMaskRep   Counter,
                 mfrapPerfIcmpTotalRxPktTooBig     Counter,
                 mfrapPerfIcmpTotalTxPktTooBig     Counter,
                 mfrapPerfIcmpTotalRxGmQuery       Counter,
                 mfrapPerfIcmpTotalTxGmQuery       Counter,
                 mfrapPerfIcmpTotalRxGmReport      Counter,
                 mfrapPerfIcmpTotalTxGmReport      Counter,
                 mfrapPerfIcmpTotalRxGmReduct      Counter,
                 mfrapPerfIcmpTotalTxGmReduct      Counter
             }

      mfrapPerfIcmpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfIcmpTotalEntry 1 }

      mfrapPerfIcmpTotalRxTotal    OBJECT-TYPE
             SYNTAX      Counter
             ACCESS      read-only
             STATUS      mandatory
             DESCRIPTION
                "The total number of ICMP bytes that have been
                 counted on this DLCI."
            ::= { mfrapPerfIcmpTotalEntry 3 }

      mfrapPerfIcmpTotalTxTotal    OBJECT-TYPE
             SYNTAX      Counter
             ACCESS      read-only
             STATUS      mandatory
             DESCRIPTION
                "The total number of ICMP bytes that have been
                 counted on this DLCI."
            ::= { mfrapPerfIcmpTotalEntry 4 }

      mfrapPerfIcmpTotalRxEchoRep    OBJECT-TYPE
             SYNTAX      Counter
             ACCESS      read-only
             STATUS      mandatory
             DESCRIPTION
                "The number of bytes in ICMP ECHO repies
                 that have been counted on this DLCI."
            ::= { mfrapPerfIcmpTotalEntry 5 }

      mfrapPerfIcmpTotalTxEchoRep    OBJECT-TYPE
             SYNTAX      Counter
             ACCESS      read-only
             STATUS      mandatory
             DESCRIPTION
                "The number of bytes in ICMP ECHO repies
                 that have been counted on this DLCI."
            ::= { mfrapPerfIcmpTotalEntry 6 }

      mfrapPerfIcmpTotalRxDestUnr    OBJECT-TYPE
             SYNTAX      Counter
             ACCESS      read-only
             STATUS      mandatory
             DESCRIPTION
                "The number of bytes in ICMP destination unreachables
                 that have been counted on this DLCI."
            ::= { mfrapPerfIcmpTotalEntry 7 }

      mfrapPerfIcmpTotalTxDestUnr    OBJECT-TYPE
             SYNTAX      Counter
             ACCESS      read-only
             STATUS      mandatory
             DESCRIPTION
                "The number of bytes in ICMP destination unreachables
                 that have been counted on this DLCI."
            ::= { mfrapPerfIcmpTotalEntry 8 }

      mfrapPerfIcmpTotalRxSrcQuench    OBJECT-TYPE
             SYNTAX      Counter
             ACCESS      read-only
             STATUS      mandatory
             DESCRIPTION
                "The number of bytes in ICMP source quenches
                 that have been counted on this DLCI."
            ::= { mfrapPerfIcmpTotalEntry 9 }

      mfrapPerfIcmpTotalTxSrcQuench    OBJECT-TYPE
             SYNTAX      Counter
             ACCESS      read-only
             STATUS      mandatory
             DESCRIPTION
                "The number of bytes in ICMP source quenches
                 that have been counted on this DLCI."
            ::= { mfrapPerfIcmpTotalEntry 10 }

      mfrapPerfIcmpTotalRxRedirect    OBJECT-TYPE
             SYNTAX      Counter
             ACCESS      read-only
             STATUS      mandatory
             DESCRIPTION
                "The number of bytes in ICMP redirects
                 that have been counted on this DLCI."
            ::= { mfrapPerfIcmpTotalEntry 11 }

      mfrapPerfIcmpTotalTxRedirect    OBJECT-TYPE
             SYNTAX      Counter
             ACCESS      read-only
             STATUS      mandatory
             DESCRIPTION
                "The number of bytes in ICMP redirects
                 that have been counted on this DLCI."
            ::= { mfrapPerfIcmpTotalEntry 12 }

      mfrapPerfIcmpTotalRxEchoReq    OBJECT-TYPE
             SYNTAX      Counter
             ACCESS      read-only
             STATUS      mandatory
             DESCRIPTION
                "The number of bytes in ICMP ECHO requests
                 that have been counted on this DLCI."
            ::= { mfrapPerfIcmpTotalEntry 13 }

      mfrapPerfIcmpTotalTxEchoReq    OBJECT-TYPE
             SYNTAX      Counter
             ACCESS      read-only
             STATUS      mandatory
             DESCRIPTION
                "The number of bytes in ICMP ECHO requests
                 that have been counted on this DLCI."
            ::= { mfrapPerfIcmpTotalEntry 14 }

      mfrapPerfIcmpTotalRxTimeExcd    OBJECT-TYPE
             SYNTAX      Counter
             ACCESS      read-only
             STATUS      mandatory
             DESCRIPTION
                "The number of bytes in ICMP time exceededs
                 that have been counted on this DLCI."
            ::= { mfrapPerfIcmpTotalEntry 15 }

      mfrapPerfIcmpTotalTxTimeExcd    OBJECT-TYPE
             SYNTAX      Counter
             ACCESS      read-only
             STATUS      mandatory
             DESCRIPTION
                "The number of bytes in ICMP time exceededs
                 that have been counted on this DLCI."
            ::= { mfrapPerfIcmpTotalEntry 16 }

      mfrapPerfIcmpTotalRxParamProb    OBJECT-TYPE
             SYNTAX      Counter
             ACCESS      read-only
             STATUS      mandatory
             DESCRIPTION
                "The number of bytes in ICMP parameter problems
                 that have been counted on this DLCI."
            ::= { mfrapPerfIcmpTotalEntry 17 }

      mfrapPerfIcmpTotalTxParamProb    OBJECT-TYPE
             SYNTAX      Counter
             ACCESS      read-only
             STATUS      mandatory
             DESCRIPTION
                "The number of bytes in ICMP parameter problems
                 that have been counted on this DLCI."
            ::= { mfrapPerfIcmpTotalEntry 18 }

      mfrapPerfIcmpTotalRxTimestpReq    OBJECT-TYPE
             SYNTAX      Counter
             ACCESS      read-only
             STATUS      mandatory
             DESCRIPTION
                "The number of bytes in ICMP timestamp requests
                 that have been counted on this DLCI."
            ::= { mfrapPerfIcmpTotalEntry 19 }

      mfrapPerfIcmpTotalTxTimestpReq    OBJECT-TYPE
             SYNTAX      Counter
             ACCESS      read-only
             STATUS      mandatory
             DESCRIPTION
                "The number of bytes in ICMP timestamp requests
                 that have been counted on this DLCI."
            ::= { mfrapPerfIcmpTotalEntry 20 }

      mfrapPerfIcmpTotalRxTimestpRep    OBJECT-TYPE
             SYNTAX      Counter
             ACCESS      read-only
             STATUS      mandatory
             DESCRIPTION
                "The number of bytes in ICMP timestamp replies
                 that have been counted on this DLCI."
            ::= { mfrapPerfIcmpTotalEntry 21 }

      mfrapPerfIcmpTotalTxTimestpRep    OBJECT-TYPE
             SYNTAX      Counter
             ACCESS      read-only
             STATUS      mandatory
             DESCRIPTION
                "The number of bytes in ICMP timestamp replies
                 that have been counted on this DLCI."
            ::= { mfrapPerfIcmpTotalEntry 22 }

      mfrapPerfIcmpTotalRxAddrMaskReq    OBJECT-TYPE
             SYNTAX      Counter
             ACCESS      read-only
             STATUS      mandatory
             DESCRIPTION
                "The number of bytes in ICMP address mask requests
                 that have been counted on this DLCI."
            ::= { mfrapPerfIcmpTotalEntry 23 }

      mfrapPerfIcmpTotalTxAddrMaskReq    OBJECT-TYPE
             SYNTAX      Counter
             ACCESS      read-only
             STATUS      mandatory
             DESCRIPTION
                "The number of bytes in ICMP address mask requests
                 that have been counted on this DLCI."
            ::= { mfrapPerfIcmpTotalEntry 24 }

      mfrapPerfIcmpTotalRxAddrMaskRep    OBJECT-TYPE
             SYNTAX      Counter
             ACCESS      read-only
             STATUS      mandatory
             DESCRIPTION
                "The number of bytes in ICMP address mask replies
                 that have been counted on this DLCI."
            ::= { mfrapPerfIcmpTotalEntry 25 }

      mfrapPerfIcmpTotalTxAddrMaskRep    OBJECT-TYPE
             SYNTAX      Counter
             ACCESS      read-only
             STATUS      mandatory
             DESCRIPTION
                "The number of bytes in ICMP address mask replies
                 that have been counted on this DLCI."
            ::= { mfrapPerfIcmpTotalEntry 26 }

      mfrapPerfIcmpTotalRxPktTooBig    OBJECT-TYPE
             SYNTAX      Counter
             ACCESS      read-only
             STATUS      mandatory
             DESCRIPTION
                "The number of bytes in ICMP packet too bigs
                 that have been counted on this DLCI."
            ::= { mfrapPerfIcmpTotalEntry 27 }

      mfrapPerfIcmpTotalTxPktTooBig    OBJECT-TYPE
             SYNTAX      Counter
             ACCESS      read-only
             STATUS      mandatory
             DESCRIPTION
                "The number of bytes in ICMP packet too bigs
                 that have been counted on this DLCI."
            ::= { mfrapPerfIcmpTotalEntry 28 }

      mfrapPerfIcmpTotalRxGmQuery    OBJECT-TYPE
             SYNTAX      Counter
             ACCESS      read-only
             STATUS      mandatory
             DESCRIPTION
                "The number of bytes in ICMP group membership
                 queries that have been counted on this DLCI."
            ::= { mfrapPerfIcmpTotalEntry 29 }

      mfrapPerfIcmpTotalTxGmQuery    OBJECT-TYPE
             SYNTAX      Counter
             ACCESS      read-only
             STATUS      mandatory
             DESCRIPTION
                "The number of bytes in ICMP group membership
                 queries that have been counted on this DLCI."
            ::= { mfrapPerfIcmpTotalEntry 30 }

      mfrapPerfIcmpTotalRxGmReport    OBJECT-TYPE
             SYNTAX      Counter
             ACCESS      read-only
             STATUS      mandatory
             DESCRIPTION
                "The number of bytes in ICMP group membership
                 reports that have been counted on this DLCI."
            ::= { mfrapPerfIcmpTotalEntry 31 }

      mfrapPerfIcmpTotalTxGmReport    OBJECT-TYPE
             SYNTAX      Counter
             ACCESS      read-only
             STATUS      mandatory
             DESCRIPTION
                "The number of bytes in ICMP group membership
                 reports that have been counted on this DLCI."
            ::= { mfrapPerfIcmpTotalEntry 32 }

      mfrapPerfIcmpTotalRxGmReduct    OBJECT-TYPE
             SYNTAX      Counter
             ACCESS      read-only
             STATUS      mandatory
             DESCRIPTION
                "The number of bytes in ICMP group membership
                 reductions that have been counted on this DLCI."
            ::= { mfrapPerfIcmpTotalEntry 33 }

      mfrapPerfIcmpTotalTxGmReduct    OBJECT-TYPE
             SYNTAX      Counter
             ACCESS      read-only
             STATUS      mandatory
             DESCRIPTION
                "The number of bytes in ICMP group membership
                 reductions that have been counted on this DLCI."
            ::= { mfrapPerfIcmpTotalEntry 34 }

   --  Application-level Short Term Statistics for each DLCI.

   mfrapPerfApplicationPerDlciTable OBJECT-TYPE
         SYNTAX   SEQUENCE OF MfrapPerfApplicationPerDlciEntry
         ACCESS   not-accessible
         STATUS   mandatory
         DESCRIPTION
            "The Short Term Statistics on the Application
            protocol for each DLCI."
         ::= { mfrapPerfNetworkShortTerm 7 }

         mfrapPerfApplicationPerDlciEntry OBJECT-TYPE
             SYNTAX   MfrapPerfApplicationPerDlciEntry
             ACCESS   not-accessible
             STATUS   mandatory
             DESCRIPTION
                "The Application Short Term Statistics for a particular DLCI."
            INDEX { mfrapPerfApplicationPerDlciInterval, 
                    mfrapPerfApplicationPerDlciValue }
            ::= { mfrapPerfApplicationPerDlciTable 1 }

         MfrapPerfApplicationPerDlciEntry ::=
             SEQUENCE {
                 mfrapPerfApplicationPerDlciInterval   INTEGER,
                 mfrapPerfApplicationPerDlciValue      INTEGER,
                 mfrapPerfApplicationPerDlciRxSnmp     Counter,
                 mfrapPerfApplicationPerDlciTxSnmp     Counter,
                 mfrapPerfApplicationPerDlciRxSnmpTrap Counter,
                 mfrapPerfApplicationPerDlciTxSnmpTrap Counter,
                 mfrapPerfApplicationPerDlciRxHttp     Counter,
                 mfrapPerfApplicationPerDlciTxHttp     Counter,
                 mfrapPerfApplicationPerDlciRxTelnet   Counter,
                 mfrapPerfApplicationPerDlciTxTelnet   Counter,
                 mfrapPerfApplicationPerDlciRxSmtp     Counter,
                 mfrapPerfApplicationPerDlciTxSmtp     Counter,
                 mfrapPerfApplicationPerDlciRxFtp      Counter,
                 mfrapPerfApplicationPerDlciTxFtp      Counter,
                 mfrapPerfApplicationPerDlciRxTftp     Counter,
                 mfrapPerfApplicationPerDlciTxTftp     Counter,
                 mfrapPerfApplicationPerDlciRxCustom1  Counter,
                 mfrapPerfApplicationPerDlciTxCustom1  Counter,
                 mfrapPerfApplicationPerDlciRxCustom2  Counter,
                 mfrapPerfApplicationPerDlciTxCustom2  Counter,
                 mfrapPerfApplicationPerDlciRxCustom3  Counter,
                 mfrapPerfApplicationPerDlciTxCustom3  Counter,
                 mfrapPerfApplicationPerDlciRxCustom4  Counter,
                 mfrapPerfApplicationPerDlciTxCustom4  Counter
             }

      mfrapPerfApplicationPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfApplicationPerDlciEntry 1 }

      mfrapPerfApplicationPerDlciValue    OBJECT-TYPE
             SYNTAX      INTEGER 
             ACCESS      read-only
             STATUS      mandatory
             DESCRIPTION
                "The DLCI value with which the Statistics are associated."
            ::= { mfrapPerfApplicationPerDlciEntry 2 }

      mfrapPerfApplicationPerDlciRxSnmp    OBJECT-TYPE
             SYNTAX      Counter
             ACCESS      read-only
             STATUS      mandatory
             DESCRIPTION
                "The number of received SNMP bytes
                 that have been counted on this DLCI."
            ::= { mfrapPerfApplicationPerDlciEntry 3 }

      mfrapPerfApplicationPerDlciTxSnmp    OBJECT-TYPE
             SYNTAX      Counter
             ACCESS      read-only
             STATUS      mandatory
             DESCRIPTION
                "The number of transmitted SNMP bytes
                 that have been counted on this DLCI."
            ::= { mfrapPerfApplicationPerDlciEntry 4 }

      mfrapPerfApplicationPerDlciRxSnmpTrap    OBJECT-TYPE
             SYNTAX      Counter
             ACCESS      read-only
             STATUS      mandatory
             DESCRIPTION
                "The number of received SNMP TRAP bytes
                 that have been counted on this DLCI."
            ::= { mfrapPerfApplicationPerDlciEntry 5 }

      mfrapPerfApplicationPerDlciTxSnmpTrap    OBJECT-TYPE
             SYNTAX      Counter
             ACCESS      read-only
             STATUS      mandatory
             DESCRIPTION
                "The number of transmitted SNMP TRAP bytes
                 that have been counted on this DLCI."
            ::= { mfrapPerfApplicationPerDlciEntry 6 }

      mfrapPerfApplicationPerDlciRxHttp    OBJECT-TYPE
             SYNTAX      Counter
             ACCESS      read-only
             STATUS      mandatory
             DESCRIPTION
                "The number of received HTTP bytes
                 that have been counted on this DLCI."
            ::= { mfrapPerfApplicationPerDlciEntry 7 }

      mfrapPerfApplicationPerDlciTxHttp    OBJECT-TYPE
             SYNTAX      Counter
             ACCESS      read-only
             STATUS      mandatory
             DESCRIPTION
                "The number of transmitted HTTP bytes
                 that have been counted on this DLCI."
            ::= { mfrapPerfApplicationPerDlciEntry 8 }

      mfrapPerfApplicationPerDlciRxTelnet    OBJECT-TYPE
             SYNTAX      Counter
             ACCESS      read-only
             STATUS      mandatory
             DESCRIPTION
                "The number of received Telnet bytes
                 that have been counted on this DLCI."
            ::= { mfrapPerfApplicationPerDlciEntry 9 }

      mfrapPerfApplicationPerDlciTxTelnet    OBJECT-TYPE
             SYNTAX      Counter
             ACCESS      read-only
             STATUS      mandatory
             DESCRIPTION
                "The number of transmitted Telnet bytes
                 that have been counted on this DLCI."
            ::= { mfrapPerfApplicationPerDlciEntry 10 }

      mfrapPerfApplicationPerDlciRxSmtp    OBJECT-TYPE
             SYNTAX      Counter
             ACCESS      read-only
             STATUS      mandatory
             DESCRIPTION
                "The number of received SMTP bytes
                 that have been counted on this DLCI."
            ::= { mfrapPerfApplicationPerDlciEntry 11 }

      mfrapPerfApplicationPerDlciTxSmtp    OBJECT-TYPE
             SYNTAX      Counter
             ACCESS      read-only
             STATUS      mandatory
             DESCRIPTION
                "The number of transmitted SMTP bytes
                 that have been counted on this DLCI."
            ::= { mfrapPerfApplicationPerDlciEntry 12 }

      mfrapPerfApplicationPerDlciRxFtp    OBJECT-TYPE
             SYNTAX      Counter
             ACCESS      read-only
             STATUS      mandatory
             DESCRIPTION
                "The number of received FTP bytes
                 that have been counted on this DLCI."
            ::= { mfrapPerfApplicationPerDlciEntry 13 }

      mfrapPerfApplicationPerDlciTxFtp    OBJECT-TYPE
             SYNTAX      Counter
             ACCESS      read-only
             STATUS      mandatory
             DESCRIPTION
                "The number of transmitted FTP bytes
                 that have been counted on this DLCI."
            ::= { mfrapPerfApplicationPerDlciEntry 14 }

      mfrapPerfApplicationPerDlciRxTftp    OBJECT-TYPE
             SYNTAX      Counter
             ACCESS      read-only
             STATUS      mandatory
             DESCRIPTION
                "The number of received TFTP bytes
                 that have been counted on this DLCI."
            ::= { mfrapPerfApplicationPerDlciEntry 15 }

      mfrapPerfApplicationPerDlciTxTftp    OBJECT-TYPE
             SYNTAX      Counter
             ACCESS      read-only
             STATUS      mandatory
             DESCRIPTION
                "The number of transmitted TFTP bytes
                 that have been counted on this DLCI."
            ::= { mfrapPerfApplicationPerDlciEntry 16 }

      mfrapPerfApplicationPerDlciRxCustom1    OBJECT-TYPE
             SYNTAX      Counter
             ACCESS      read-only
             STATUS      mandatory
             DESCRIPTION
                "The number of received bytes of
                 User Defined Protocol #1 that have
                 been counted on this DLCI."
            ::= { mfrapPerfApplicationPerDlciEntry 17 }

      mfrapPerfApplicationPerDlciTxCustom1    OBJECT-TYPE
             SYNTAX      Counter
             ACCESS      read-only
             STATUS      mandatory
             DESCRIPTION
                "The number of transmitted bytes of
                 User Defined Protocol #1 that have
                 been counted on this DLCI."
            ::= { mfrapPerfApplicationPerDlciEntry 18 }

      mfrapPerfApplicationPerDlciRxCustom2    OBJECT-TYPE
             SYNTAX      Counter
             ACCESS      read-only
             STATUS      mandatory
             DESCRIPTION
                "The number of received bytes of
                 User Defined Protocol #2 that have
                 been counted on this DLCI."
            ::= { mfrapPerfApplicationPerDlciEntry 19 }

      mfrapPerfApplicationPerDlciTxCustom2    OBJECT-TYPE
             SYNTAX      Counter
             ACCESS      read-only
             STATUS      mandatory
             DESCRIPTION
                "The number of transmitted bytes of
                 User Defined Protocol #2 that have
                 been counted on this DLCI."
            ::= { mfrapPerfApplicationPerDlciEntry 20 }

      mfrapPerfApplicationPerDlciRxCustom3    OBJECT-TYPE
             SYNTAX      Counter
             ACCESS      read-only
             STATUS      mandatory
             DESCRIPTION
                "The number of received bytes of
                 User Defined Protocol #3 that have
                 been counted on this DLCI."
            ::= { mfrapPerfApplicationPerDlciEntry 21 }

      mfrapPerfApplicationPerDlciTxCustom3    OBJECT-TYPE
             SYNTAX      Counter
             ACCESS      read-only
             STATUS      mandatory
             DESCRIPTION
                "The number of transmitted bytes of
                 User Defined Protocol #3 that have
                 been counted on this DLCI."
            ::= { mfrapPerfApplicationPerDlciEntry 22 }

      mfrapPerfApplicationPerDlciRxCustom4    OBJECT-TYPE
             SYNTAX      Counter
             ACCESS      read-only
             STATUS      mandatory
             DESCRIPTION
                "The number of received bytes of
                 User Defined Protocol #4 that have
                 been counted on this DLCI."
            ::= { mfrapPerfApplicationPerDlciEntry 23 }

      mfrapPerfApplicationPerDlciTxCustom4    OBJECT-TYPE
             SYNTAX      Counter
             ACCESS      read-only
             STATUS      mandatory
             DESCRIPTION
                "The number of transmitted bytes of
                 User Defined Protocol #4 that have
                 been counted on this DLCI."
            ::= { mfrapPerfApplicationPerDlciEntry 24 }



   --  Application-level Short Term Statistics totals.

   mfrapPerfApplicationTotalTable OBJECT-TYPE
         SYNTAX   SEQUENCE OF MfrapPerfApplicationTotalEntry
         ACCESS   not-accessible
         STATUS   mandatory
         DESCRIPTION
            "The Short Term Statistics on the Application
            protocol for each DLCI."
         ::= { mfrapPerfNetworkShortTerm 8 }

         mfrapPerfApplicationTotalEntry OBJECT-TYPE
             SYNTAX   MfrapPerfApplicationTotalEntry
             ACCESS   not-accessible
             STATUS   mandatory
             DESCRIPTION
                "The Application Short Term Statistics for a particular DLCI."
            INDEX { mfrapPerfApplicationTotalInterval }
            ::= { mfrapPerfApplicationTotalTable 1 }

         MfrapPerfApplicationTotalEntry ::=
             SEQUENCE {
                 mfrapPerfApplicationTotalInterval   INTEGER,
                 mfrapPerfApplicationTotalRxSnmp     Counter,
                 mfrapPerfApplicationTotalTxSnmp     Counter,
                 mfrapPerfApplicationTotalRxSnmpTrap Counter,
                 mfrapPerfApplicationTotalTxSnmpTrap Counter,
                 mfrapPerfApplicationTotalRxHttp     Counter,
                 mfrapPerfApplicationTotalTxHttp     Counter,
                 mfrapPerfApplicationTotalRxTelnet   Counter,
                 mfrapPerfApplicationTotalTxTelnet   Counter,
                 mfrapPerfApplicationTotalRxSmtp     Counter,
                 mfrapPerfApplicationTotalTxSmtp     Counter,
                 mfrapPerfApplicationTotalRxFtp      Counter,
                 mfrapPerfApplicationTotalTxFtp      Counter,
                 mfrapPerfApplicationTotalRxTftp     Counter,
                 mfrapPerfApplicationTotalTxTftp     Counter,
                 mfrapPerfApplicationTotalRxCustom1  Counter,
                 mfrapPerfApplicationTotalTxCustom1  Counter,
                 mfrapPerfApplicationTotalRxCustom2  Counter,
                 mfrapPerfApplicationTotalTxCustom2  Counter,
                 mfrapPerfApplicationTotalRxCustom3  Counter,
                 mfrapPerfApplicationTotalTxCustom3  Counter,
                 mfrapPerfApplicationTotalRxCustom4  Counter,
                 mfrapPerfApplicationTotalTxCustom4  Counter
             }

      mfrapPerfApplicationTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfApplicationTotalEntry 1 }

      mfrapPerfApplicationTotalRxSnmp    OBJECT-TYPE
             SYNTAX      Counter
             ACCESS      read-only
             STATUS      mandatory
             DESCRIPTION
                "The number of received SNMP bytes
                 that have been counted on this DLCI."
            ::= { mfrapPerfApplicationTotalEntry 3 }

      mfrapPerfApplicationTotalTxSnmp    OBJECT-TYPE
             SYNTAX      Counter
             ACCESS      read-only
             STATUS      mandatory
             DESCRIPTION
                "The number of transmitted SNMP bytes
                 that have been counted on this DLCI."
            ::= { mfrapPerfApplicationTotalEntry 4 }

      mfrapPerfApplicationTotalRxSnmpTrap    OBJECT-TYPE
             SYNTAX      Counter
             ACCESS      read-only
             STATUS      mandatory
             DESCRIPTION
                "The number of received SNMP TRAP bytes
                 that have been counted on this DLCI."
            ::= { mfrapPerfApplicationTotalEntry 5 }

      mfrapPerfApplicationTotalTxSnmpTrap    OBJECT-TYPE
             SYNTAX      Counter
             ACCESS      read-only
             STATUS      mandatory
             DESCRIPTION
                "The number of transmitted SNMP TRAP bytes
                 that have been counted on this DLCI."
            ::= { mfrapPerfApplicationTotalEntry 6 }

      mfrapPerfApplicationTotalRxHttp    OBJECT-TYPE
             SYNTAX      Counter
             ACCESS      read-only
             STATUS      mandatory
             DESCRIPTION
                "The number of received HTTP bytes
                 that have been counted on this DLCI."
            ::= { mfrapPerfApplicationTotalEntry 7 }

      mfrapPerfApplicationTotalTxHttp    OBJECT-TYPE
             SYNTAX      Counter
             ACCESS      read-only
             STATUS      mandatory
             DESCRIPTION
                "The number of transmitted HTTP bytes
                 that have been counted on this DLCI."
            ::= { mfrapPerfApplicationTotalEntry 8 }

      mfrapPerfApplicationTotalRxTelnet    OBJECT-TYPE
             SYNTAX      Counter
             ACCESS      read-only
             STATUS      mandatory
             DESCRIPTION
                "The number of received Telnet bytes
                 that have been counted on this DLCI."
            ::= { mfrapPerfApplicationTotalEntry 9 }

      mfrapPerfApplicationTotalTxTelnet    OBJECT-TYPE
             SYNTAX      Counter
             ACCESS      read-only
             STATUS      mandatory
             DESCRIPTION
                "The number of transmitted Telnet bytes
                 that have been counted on this DLCI."
            ::= { mfrapPerfApplicationTotalEntry 10 }

      mfrapPerfApplicationTotalRxSmtp    OBJECT-TYPE
             SYNTAX      Counter
             ACCESS      read-only
             STATUS      mandatory
             DESCRIPTION
                "The number of received SMTP bytes
                 that have been counted on this DLCI."
            ::= { mfrapPerfApplicationTotalEntry 11 }

      mfrapPerfApplicationTotalTxSmtp    OBJECT-TYPE
             SYNTAX      Counter
             ACCESS      read-only
             STATUS      mandatory
             DESCRIPTION
                "The number of transmitted SMTP bytes
                 that have been counted on this DLCI."
            ::= { mfrapPerfApplicationTotalEntry 12 }

      mfrapPerfApplicationTotalRxFtp    OBJECT-TYPE
             SYNTAX      Counter
             ACCESS      read-only
             STATUS      mandatory
             DESCRIPTION
                "The number of received FTP bytes
                 that have been counted on this DLCI."
            ::= { mfrapPerfApplicationTotalEntry 13 }

      mfrapPerfApplicationTotalTxFtp    OBJECT-TYPE
             SYNTAX      Counter
             ACCESS      read-only
             STATUS      mandatory
             DESCRIPTION
                "The number of transmitted FTP bytes
                 that have been counted on this DLCI."
            ::= { mfrapPerfApplicationTotalEntry 14 }

      mfrapPerfApplicationTotalRxTftp    OBJECT-TYPE
             SYNTAX      Counter
             ACCESS      read-only
             STATUS      mandatory
             DESCRIPTION
                "The number of received TFTP bytes
                 that have been counted on this DLCI."
            ::= { mfrapPerfApplicationTotalEntry 15 }

      mfrapPerfApplicationTotalTxTftp    OBJECT-TYPE
             SYNTAX      Counter
             ACCESS      read-only
             STATUS      mandatory
             DESCRIPTION
                "The number of transmitted TFTP bytes
                 that have been counted on this DLCI."
            ::= { mfrapPerfApplicationTotalEntry 16 }

      mfrapPerfApplicationTotalRxCustom1    OBJECT-TYPE
             SYNTAX      Counter
             ACCESS      read-only
             STATUS      mandatory
             DESCRIPTION
                "The number of received bytes of
                 User Defined Protocol #1 that have
                 been counted on this DLCI."
            ::= { mfrapPerfApplicationTotalEntry 17 }

      mfrapPerfApplicationTotalTxCustom1    OBJECT-TYPE
             SYNTAX      Counter
             ACCESS      read-only
             STATUS      mandatory
             DESCRIPTION
                "The number of transmitted bytes of
                 User Defined Protocol #1 that have
                 been counted on this DLCI."
            ::= { mfrapPerfApplicationTotalEntry 18 }

      mfrapPerfApplicationTotalRxCustom2    OBJECT-TYPE
             SYNTAX      Counter
             ACCESS      read-only
             STATUS      mandatory
             DESCRIPTION
                "The number of received bytes of
                 User Defined Protocol #2 that have
                 been counted on this DLCI."
            ::= { mfrapPerfApplicationTotalEntry 19 }

      mfrapPerfApplicationTotalTxCustom2    OBJECT-TYPE
             SYNTAX      Counter
             ACCESS      read-only
             STATUS      mandatory
             DESCRIPTION
                "The number of transmitted bytes of
                 User Defined Protocol #2 that have
                 been counted on this DLCI."
            ::= { mfrapPerfApplicationTotalEntry 20 }

      mfrapPerfApplicationTotalRxCustom3    OBJECT-TYPE
             SYNTAX      Counter
             ACCESS      read-only
             STATUS      mandatory
             DESCRIPTION
                "The number of received bytes of
                 User Defined Protocol #3 that have
                 been counted on this DLCI."
            ::= { mfrapPerfApplicationTotalEntry 21 }

      mfrapPerfApplicationTotalTxCustom3    OBJECT-TYPE
             SYNTAX      Counter
             ACCESS      read-only
             STATUS      mandatory
             DESCRIPTION
                "The number of transmitted bytes of
                 User Defined Protocol #3 that have
                 been counted on this DLCI."
            ::= { mfrapPerfApplicationTotalEntry 22 }

      mfrapPerfApplicationTotalRxCustom4    OBJECT-TYPE
             SYNTAX      Counter
             ACCESS      read-only
             STATUS      mandatory
             DESCRIPTION
                "The number of received bytes of
                 User Defined Protocol #4 that have
                 been counted on this DLCI."
            ::= { mfrapPerfApplicationTotalEntry 23 }

      mfrapPerfApplicationTotalTxCustom4    OBJECT-TYPE
             SYNTAX      Counter
             ACCESS      read-only
             STATUS      mandatory
             DESCRIPTION
                "The number of transmitted bytes of
                 User Defined Protocol #4 that have
                 been counted on this DLCI."
            ::= { mfrapPerfApplicationTotalEntry 24 }


   --  Routing Short Term Statistics for each DLCI.

   mfrapPerfRoutingPerDlciTable OBJECT-TYPE
         SYNTAX   SEQUENCE OF MfrapPerfRoutingPerDlciEntry
         ACCESS   not-accessible
         STATUS   mandatory
         DESCRIPTION
            "The Short Term Statistics on the Routing
            protocol for each DLCI."
         ::= { mfrapPerfNetworkShortTerm 9 }

         mfrapPerfRoutingPerDlciEntry OBJECT-TYPE
             SYNTAX   MfrapPerfRoutingPerDlciEntry
             ACCESS   not-accessible
             STATUS   mandatory
             DESCRIPTION
                "The Routing Short Term Statistics for a particular DLCI."
            INDEX { mfrapPerfRoutingPerDlciInterval,
                    mfrapPerfRoutingPerDlciValue }
            ::= { mfrapPerfRoutingPerDlciTable 1 }

         MfrapPerfRoutingPerDlciEntry ::=
             SEQUENCE {
                 mfrapPerfRoutingPerDlciInterval  INTEGER,
                 mfrapPerfRoutingPerDlciValue     INTEGER,
                 mfrapPerfRoutingPerDlciRxOspf    Counter,
                 mfrapPerfRoutingPerDlciTxOspf    Counter,
                 mfrapPerfRoutingPerDlciRxRip     Counter,
                 mfrapPerfRoutingPerDlciTxRip     Counter,
                 mfrapPerfRoutingPerDlciRxNetbios Counter,
                 mfrapPerfRoutingPerDlciTxNetbios Counter
             }

      mfrapPerfRoutingPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfRoutingPerDlciEntry 1 }

      mfrapPerfRoutingPerDlciValue    OBJECT-TYPE
             SYNTAX      INTEGER 
             ACCESS      read-only
             STATUS      mandatory
             DESCRIPTION
                "The DLCI value with which the Statistics are associated."
            ::= { mfrapPerfRoutingPerDlciEntry 2 }


      mfrapPerfRoutingPerDlciRxOspf    OBJECT-TYPE
             SYNTAX      Counter
             ACCESS      read-only
             STATUS      mandatory
             DESCRIPTION
                "The number of received OSPF bytes
                 that have been counted on this DLCI."
            ::= { mfrapPerfRoutingPerDlciEntry 3 }

      mfrapPerfRoutingPerDlciTxOspf    OBJECT-TYPE
             SYNTAX      Counter
             ACCESS      read-only
             STATUS      mandatory
             DESCRIPTION
                "The number of transmitted OSPF bytes
                 that have been counted on this DLCI."
            ::= { mfrapPerfRoutingPerDlciEntry 4 }

      mfrapPerfRoutingPerDlciRxRip    OBJECT-TYPE
             SYNTAX      Counter
             ACCESS      read-only
             STATUS      mandatory
             DESCRIPTION
                "The number of received RIP bytes
                 that have been counted on this DLCI."
            ::= { mfrapPerfRoutingPerDlciEntry 5 }

      mfrapPerfRoutingPerDlciTxRip    OBJECT-TYPE
             SYNTAX      Counter
             ACCESS      read-only
             STATUS      mandatory
             DESCRIPTION
                "The number of transmitted RIP bytes
                 that have been counted on this DLCI."
            ::= { mfrapPerfRoutingPerDlciEntry 6 }

      mfrapPerfRoutingPerDlciRxNetbios    OBJECT-TYPE
             SYNTAX      Counter
             ACCESS      read-only
             STATUS      mandatory
             DESCRIPTION
                "The number of received Netbios bytes
                 that have been counted on this DLCI."
            ::= { mfrapPerfRoutingPerDlciEntry 7 }

      mfrapPerfRoutingPerDlciTxNetbios    OBJECT-TYPE
             SYNTAX      Counter
             ACCESS      read-only
             STATUS      mandatory
             DESCRIPTION
                "The number of transmitted Netbios bytes
                 that have been counted on this DLCI."
            ::= { mfrapPerfRoutingPerDlciEntry 8 }


   --  Routing Short Term Statistics totals.

   mfrapPerfRoutingTotalTable OBJECT-TYPE
         SYNTAX   SEQUENCE OF MfrapPerfRoutingTotalEntry
         ACCESS   not-accessible
         STATUS   mandatory
         DESCRIPTION
            "The Short Term Statistics on the Routing
            protocol for each DLCI."
         ::= { mfrapPerfNetworkShortTerm 10 }

         mfrapPerfRoutingTotalEntry OBJECT-TYPE
             SYNTAX   MfrapPerfRoutingTotalEntry
             ACCESS   not-accessible
             STATUS   mandatory
             DESCRIPTION
                "The Routing Short Term Statistics for a particular DLCI."
            INDEX { mfrapPerfRoutingTotalInterval }
            ::= { mfrapPerfRoutingTotalTable 1 }

         MfrapPerfRoutingTotalEntry ::=
             SEQUENCE {
                 mfrapPerfRoutingTotalInterval  INTEGER,
                 mfrapPerfRoutingTotalRxOspf    Counter,
                 mfrapPerfRoutingTotalTxOspf    Counter,
                 mfrapPerfRoutingTotalRxRip     Counter,
                 mfrapPerfRoutingTotalTxRip     Counter,
                 mfrapPerfRoutingTotalRxNetbios Counter,
                 mfrapPerfRoutingTotalTxNetbios Counter
               }

      mfrapPerfRoutingTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfRoutingTotalEntry 1 }

      mfrapPerfRoutingTotalRxOspf    OBJECT-TYPE
             SYNTAX      Counter 
             ACCESS      read-only
             STATUS      mandatory
             DESCRIPTION
                "The number of received OSPF bytes
                 that have been counted on this DLCI."
            ::= { mfrapPerfRoutingTotalEntry 3 }

      mfrapPerfRoutingTotalTxOspf    OBJECT-TYPE
             SYNTAX      Counter
             ACCESS      read-only
             STATUS      mandatory
             DESCRIPTION
                "The number of transmitted OSPF bytes
                 that have been counted on this DLCI."
            ::= { mfrapPerfRoutingTotalEntry 4 }

      mfrapPerfRoutingTotalRxRip    OBJECT-TYPE
             SYNTAX      Counter
             ACCESS      read-only
             STATUS      mandatory
             DESCRIPTION
                "The number of received RIP bytes
                 that have been counted on this DLCI."
            ::= { mfrapPerfRoutingTotalEntry 5 }

      mfrapPerfRoutingTotalTxRip    OBJECT-TYPE
             SYNTAX      Counter
             ACCESS      read-only
             STATUS      mandatory
             DESCRIPTION
                "The number of transmitted RIP bytes
                 that have been counted on this DLCI."
            ::= { mfrapPerfRoutingTotalEntry 6 }

      mfrapPerfRoutingTotalRxNetbios    OBJECT-TYPE
             SYNTAX      Counter
             ACCESS      read-only
             STATUS      mandatory
             DESCRIPTION
                "The number of received Netbios bytes
                 that have been counted on this DLCI."
            ::= { mfrapPerfRoutingTotalEntry 7 }

      mfrapPerfRoutingTotalTxNetbios    OBJECT-TYPE
             SYNTAX      Counter
             ACCESS      read-only
             STATUS      mandatory
             DESCRIPTION
                "The number of transmitted Netbios bytes
                 that have been counted on this DLCI."
            ::= { mfrapPerfRoutingTotalEntry 8 }



   --  IPX Short Term Statistics for each DLCI.

   mfrapPerfIpxPerDlciTable OBJECT-TYPE
         SYNTAX   SEQUENCE OF MfrapPerfIpxPerDlciEntry
         ACCESS   not-accessible
         STATUS   mandatory
         DESCRIPTION
            "Short Term Statistics on the IPX
             protocol for each DLCI."
         ::= { mfrapPerfNetworkShortTerm 11 }

         mfrapPerfIpxPerDlciEntry OBJECT-TYPE
             SYNTAX   MfrapPerfIpxPerDlciEntry
             ACCESS   not-accessible
             STATUS   mandatory
             DESCRIPTION
                "The IPX Short Term Statistics for a particular DLCI."
            INDEX { mfrapPerfIpxPerDlciInterval, mfrapPerfIpxPerDlciValue }
            ::= { mfrapPerfIpxPerDlciTable 1 }

         MfrapPerfIpxPerDlciEntry ::=
             SEQUENCE {
                 mfrapPerfIpxPerDlciInterval   INTEGER,
                 mfrapPerfIpxPerDlciValue      INTEGER,
                 mfrapPerfIpxPerDlciRxTotal    Counter,
                 mfrapPerfIpxPerDlciTxTotal    Counter,
                 mfrapPerfIpxPerDlciRxSpx      Counter,
                 mfrapPerfIpxPerDlciTxSpx      Counter,
                 mfrapPerfIpxPerDlciRxNcp      Counter,
                 mfrapPerfIpxPerDlciTxNcp      Counter,
                 mfrapPerfIpxPerDlciRxSap      Counter,
                 mfrapPerfIpxPerDlciTxSap      Counter,
                 mfrapPerfIpxPerDlciRxRip      Counter,
                 mfrapPerfIpxPerDlciTxRip      Counter,
                 mfrapPerfIpxPerDlciRxNetbios  Counter,
                 mfrapPerfIpxPerDlciTxNetbios  Counter,
                 mfrapPerfIpxPerDlciRxOther    Counter,
                 mfrapPerfIpxPerDlciTxOther    Counter
             }

      mfrapPerfIpxPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfIpxPerDlciEntry 1 }

      mfrapPerfIpxPerDlciValue    OBJECT-TYPE
             SYNTAX      INTEGER 
            ACCESS      read-only
             STATUS      mandatory
             DESCRIPTION
                "The DLCI value in which the Statistics are associated."
            ::= { mfrapPerfIpxPerDlciEntry 2 }

      mfrapPerfIpxPerDlciRxTotal    OBJECT-TYPE
             SYNTAX      Counter
             ACCESS      read-only
             STATUS      mandatory
             DESCRIPTION
                "The total number of IPX bytes
                 that have been counted on this DLCI."
            ::= { mfrapPerfIpxPerDlciEntry 3 }

      mfrapPerfIpxPerDlciTxTotal    OBJECT-TYPE
             SYNTAX      Counter
             ACCESS      read-only
             STATUS      mandatory
             DESCRIPTION
                "The total number of IPX bytes
                 that have been counted on this DLCI."
            ::= { mfrapPerfIpxPerDlciEntry 4 }

      mfrapPerfIpxPerDlciRxSpx    OBJECT-TYPE
             SYNTAX      Counter
             ACCESS      read-only
             STATUS      mandatory
             DESCRIPTION
                "The number of SPX over IPX bytes
                 that have been counted on this DLCI."
            ::= { mfrapPerfIpxPerDlciEntry 5 }

      mfrapPerfIpxPerDlciTxSpx    OBJECT-TYPE
             SYNTAX      Counter
             ACCESS      read-only
             STATUS      mandatory
             DESCRIPTION
                "The number of SPX over IPX bytes
                 that have been counted on this DLCI."
            ::= { mfrapPerfIpxPerDlciEntry 6 }

      mfrapPerfIpxPerDlciRxNcp    OBJECT-TYPE
             SYNTAX      Counter
             ACCESS      read-only
             STATUS      mandatory
             DESCRIPTION
                "The number of NCP over IPX bytes
                 that have been counted on this DLCI."
            ::= { mfrapPerfIpxPerDlciEntry 7 }

      mfrapPerfIpxPerDlciTxNcp    OBJECT-TYPE
             SYNTAX      Counter
             ACCESS      read-only
             STATUS      mandatory
             DESCRIPTION
                "The number of NCP over IPX bytes
                 that have been counted on this DLCI."
            ::= { mfrapPerfIpxPerDlciEntry 8 }

      mfrapPerfIpxPerDlciRxSap    OBJECT-TYPE
             SYNTAX      Counter
             ACCESS      read-only
             STATUS      mandatory
             DESCRIPTION
                "The number of SAP over IPX bytes
                 that have been counted on this DLCI."
            ::= { mfrapPerfIpxPerDlciEntry 9 }

      mfrapPerfIpxPerDlciTxSap    OBJECT-TYPE
             SYNTAX      Counter
             ACCESS      read-only
             STATUS      mandatory
             DESCRIPTION
                "The number of SAP over IPX bytes
                 that have been counted on this DLCI."
            ::= { mfrapPerfIpxPerDlciEntry 10 }

      mfrapPerfIpxPerDlciRxRip    OBJECT-TYPE
             SYNTAX      Counter
             ACCESS      read-only
             STATUS      mandatory
             DESCRIPTION
                "The number of RIP over IPX bytes
                 that have been counted on this DLCI."
            ::= { mfrapPerfIpxPerDlciEntry 11 }

      mfrapPerfIpxPerDlciTxRip    OBJECT-TYPE
             SYNTAX      Counter
             ACCESS      read-only
             STATUS      mandatory
             DESCRIPTION
                "The number of RIP over IPX bytes
                 that have been counted on this DLCI."
            ::= { mfrapPerfIpxPerDlciEntry 12 }

      mfrapPerfIpxPerDlciRxNetbios    OBJECT-TYPE
             SYNTAX      Counter
             ACCESS      read-only
             STATUS      mandatory
             DESCRIPTION
                "The number of NETBIOS over IPX bytes
                 that have been counted on this DLCI."
            ::= { mfrapPerfIpxPerDlciEntry 13 }

      mfrapPerfIpxPerDlciTxNetbios    OBJECT-TYPE
             SYNTAX      Counter
             ACCESS      read-only
             STATUS      mandatory
             DESCRIPTION
                "The number of NETBIOS over IPX bytes
                 that have been counted on this DLCI."
            ::= { mfrapPerfIpxPerDlciEntry 14 }

      mfrapPerfIpxPerDlciRxOther    OBJECT-TYPE
             SYNTAX      Counter
             ACCESS      read-only
             STATUS      mandatory
             DESCRIPTION
                "The number of received bytes on this DLCI
                 from protocols over IPX that are not counted
                 elsewhere in this table."
            ::= { mfrapPerfIpxPerDlciEntry 15 }

      mfrapPerfIpxPerDlciTxOther    OBJECT-TYPE
             SYNTAX      Counter
             ACCESS      read-only
             STATUS      mandatory
             DESCRIPTION
                "The number of transmitted bytes on this DLCI
                 from protocols over IPX that are not counted
                 elsewhere in this table."
            ::= { mfrapPerfIpxPerDlciEntry 16 }


   --  IPX Short Term Statistics totals.

   mfrapPerfIpxTotalTable OBJECT-TYPE
         SYNTAX   SEQUENCE OF MfrapPerfIpxTotalEntry
         ACCESS   not-accessible
         STATUS   mandatory
         DESCRIPTION
            "Short Term Statistics on the IPX
             protocol for each DLCI."
         ::= { mfrapPerfNetworkShortTerm 12 }

         mfrapPerfIpxTotalEntry OBJECT-TYPE
             SYNTAX   MfrapPerfIpxTotalEntry
             ACCESS   not-accessible
             STATUS   mandatory
             DESCRIPTION
                "The IPX Short Term Statistics for a particular DLCI."
            INDEX { mfrapPerfIpxTotalInterval }
            ::= { mfrapPerfIpxTotalTable 1 }

         MfrapPerfIpxTotalEntry ::=
             SEQUENCE {
                 mfrapPerfIpxTotalInterval   INTEGER,
                 mfrapPerfIpxTotalRxTotal    Counter,
                 mfrapPerfIpxTotalTxTotal    Counter,
                 mfrapPerfIpxTotalRxSpx      Counter,
                 mfrapPerfIpxTotalTxSpx      Counter,
                 mfrapPerfIpxTotalRxNcp      Counter,
                 mfrapPerfIpxTotalTxNcp      Counter,
                 mfrapPerfIpxTotalRxSap      Counter,
                 mfrapPerfIpxTotalTxSap      Counter,
                 mfrapPerfIpxTotalRxRip      Counter,
                 mfrapPerfIpxTotalTxRip      Counter,
                 mfrapPerfIpxTotalRxNetbios  Counter,
                 mfrapPerfIpxTotalTxNetbios  Counter,
                 mfrapPerfIpxTotalRxOther    Counter,
                 mfrapPerfIpxTotalTxOther    Counter
             }

      mfrapPerfIpxTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfIpxTotalEntry 1 }

      mfrapPerfIpxTotalRxTotal    OBJECT-TYPE
             SYNTAX      Counter
             ACCESS      read-only
             STATUS      mandatory
             DESCRIPTION
                "The total number of IPX bytes
                 that have been counted on this DLCI."
            ::= { mfrapPerfIpxTotalEntry 3 }

      mfrapPerfIpxTotalTxTotal    OBJECT-TYPE
             SYNTAX      Counter
             ACCESS      read-only
             STATUS      mandatory
             DESCRIPTION
                "The total number of IPX bytes
                 that have been counted on this DLCI."
            ::= { mfrapPerfIpxTotalEntry 4 }

      mfrapPerfIpxTotalRxSpx    OBJECT-TYPE
             SYNTAX      Counter
             ACCESS      read-only
             STATUS      mandatory
             DESCRIPTION
                "The number of SPX over IPX bytes
                 that have been counted on this DLCI."
            ::= { mfrapPerfIpxTotalEntry 5 }

      mfrapPerfIpxTotalTxSpx    OBJECT-TYPE
             SYNTAX      Counter
             ACCESS      read-only
             STATUS      mandatory
             DESCRIPTION
                "The number of SPX over IPX bytes
                 that have been counted on this DLCI."
            ::= { mfrapPerfIpxTotalEntry 6 }

      mfrapPerfIpxTotalRxNcp    OBJECT-TYPE
             SYNTAX      Counter
             ACCESS      read-only
             STATUS      mandatory
             DESCRIPTION
                "The number of NCP over IPX bytes
                 that have been counted on this DLCI."
            ::= { mfrapPerfIpxTotalEntry 7 }

      mfrapPerfIpxTotalTxNcp    OBJECT-TYPE
             SYNTAX      Counter
             ACCESS      read-only
             STATUS      mandatory
             DESCRIPTION
                "The number of NCP over IPX bytes
                 that have been counted on this DLCI."
            ::= { mfrapPerfIpxTotalEntry 8 }

      mfrapPerfIpxTotalRxSap    OBJECT-TYPE
             SYNTAX      Counter
             ACCESS      read-only
             STATUS      mandatory
             DESCRIPTION
                "The number of SAP over IPX bytes
                 that have been counted on this DLCI."
            ::= { mfrapPerfIpxTotalEntry 9 }

      mfrapPerfIpxTotalTxSap    OBJECT-TYPE
             SYNTAX      Counter
             ACCESS      read-only
             STATUS      mandatory
             DESCRIPTION
                "The number of SAP over IPX bytes
                 that have been counted on this DLCI."
            ::= { mfrapPerfIpxTotalEntry 10 }

      mfrapPerfIpxTotalRxRip    OBJECT-TYPE
             SYNTAX      Counter
             ACCESS      read-only
             STATUS      mandatory
             DESCRIPTION
                "The number of RIP over IPX bytes
                 that have been counted on this DLCI."
            ::= { mfrapPerfIpxTotalEntry 11 }

      mfrapPerfIpxTotalTxRip    OBJECT-TYPE
             SYNTAX      Counter
             ACCESS      read-only
             STATUS      mandatory
             DESCRIPTION
                "The number of RIP over IPX bytes
                 that have been counted on this DLCI."
            ::= { mfrapPerfIpxTotalEntry 12 }

      mfrapPerfIpxTotalRxNetbios    OBJECT-TYPE
             SYNTAX      Counter
             ACCESS      read-only
             STATUS      mandatory
             DESCRIPTION
                "The number of NETBIOS over IPX bytes
                 that have been counted on this DLCI."
            ::= { mfrapPerfIpxTotalEntry 13 }

      mfrapPerfIpxTotalTxNetbios    OBJECT-TYPE
             SYNTAX      Counter
             ACCESS      read-only
             STATUS      mandatory
             DESCRIPTION
                "The number of NETBIOS over IPX bytes
                 that have been counted on this DLCI."
            ::= { mfrapPerfIpxTotalEntry 14 }

      mfrapPerfIpxTotalRxOther    OBJECT-TYPE
             SYNTAX      Counter
             ACCESS      read-only
             STATUS      mandatory
             DESCRIPTION
                "The number of received bytes on this DLCI
                 from protocols over IPX that are not counted
                 elsewhere in this table."
            ::= { mfrapPerfIpxTotalEntry 15 }

      mfrapPerfIpxTotalTxOther    OBJECT-TYPE
             SYNTAX      Counter
             ACCESS      read-only
             STATUS      mandatory
             DESCRIPTION
                "The number of transmitted bytes on this DLCI
                 from protocols over IPX that are not counted
                 elsewhere in this table."
            ::= { mfrapPerfIpxTotalEntry 16 }


   --  SNA Short Term Statistics for each DLCI.

   mfrapPerfSnaPerDlciTable OBJECT-TYPE
         SYNTAX   SEQUENCE OF MfrapPerfSnaPerDlciEntry
         ACCESS   not-accessible
         STATUS   mandatory
         DESCRIPTION
            "Short Term Statistics on the SNA
             protocol for each DLCI."
         ::= { mfrapPerfNetworkShortTerm 13 }

         mfrapPerfSnaPerDlciEntry OBJECT-TYPE
             SYNTAX   MfrapPerfSnaPerDlciEntry
             ACCESS   not-accessible
             STATUS   mandatory
             DESCRIPTION
                "The SNA Short Term Statistics for a particular DLCI."
            INDEX { mfrapPerfSnaPerDlciInterval, mfrapPerfSnaPerDlciValue }
            ::= { mfrapPerfSnaPerDlciTable 1 }

         MfrapPerfSnaPerDlciEntry ::=
             SEQUENCE {
                 mfrapPerfSnaPerDlciInterval        INTEGER,
                 mfrapPerfSnaPerDlciValue           INTEGER,
                 mfrapPerfSnaPerDlciRxTotal         Counter,
                 mfrapPerfSnaPerDlciTxTotal         Counter,
                 mfrapPerfSnaPerDlciRxSubarea       Counter,
                 mfrapPerfSnaPerDlciTxSubarea       Counter,
                 mfrapPerfSnaPerDlciRxPeriph        Counter,
                 mfrapPerfSnaPerDlciTxPeriph        Counter,
                 mfrapPerfSnaPerDlciRxAppn          Counter,
                 mfrapPerfSnaPerDlciTxAppn          Counter,
                 mfrapPerfSnaPerDlciRxNetbios       Counter,
                 mfrapPerfSnaPerDlciTxNetbios       Counter,
                 mfrapPerfSnaPerDlciRxOther         Counter,
                 mfrapPerfSnaPerDlciTxOther         Counter
             }

      mfrapPerfSnaPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfSnaPerDlciEntry 1 }

      mfrapPerfSnaPerDlciValue    OBJECT-TYPE
             SYNTAX      INTEGER 
             ACCESS      read-only
             STATUS      mandatory
             DESCRIPTION
                "The DLCI value in which the Statistics are associated."
            ::= { mfrapPerfSnaPerDlciEntry 2 }

      mfrapPerfSnaPerDlciRxTotal    OBJECT-TYPE
             SYNTAX      Counter
             ACCESS      read-only
             STATUS      mandatory
             DESCRIPTION
                "The total number of SNA bytes
                 that have been counted on this DLCI."
            ::= { mfrapPerfSnaPerDlciEntry 3 }

      mfrapPerfSnaPerDlciTxTotal    OBJECT-TYPE
             SYNTAX      Counter
             ACCESS      read-only
             STATUS      mandatory
             DESCRIPTION
                "The total number of SNA bytes
                 that have been counted on this DLCI."
            ::= { mfrapPerfSnaPerDlciEntry 4 }

      mfrapPerfSnaPerDlciRxSubarea    OBJECT-TYPE
             SYNTAX      Counter
             ACCESS      read-only
             STATUS      mandatory
             DESCRIPTION
                "The number of SNA Subarea bytes
                 that have been counted on this DLCI."
            ::= { mfrapPerfSnaPerDlciEntry 5 }

      mfrapPerfSnaPerDlciTxSubarea    OBJECT-TYPE
             SYNTAX      Counter
             ACCESS      read-only
             STATUS      mandatory
             DESCRIPTION
                "The number of SNA Subarea bytes
                 that have been counted on this DLCI."
            ::= { mfrapPerfSnaPerDlciEntry 6 }

      mfrapPerfSnaPerDlciRxPeriph    OBJECT-TYPE
             SYNTAX      Counter
             ACCESS      read-only
             STATUS      mandatory
             DESCRIPTION
                "The number of SNA Periph bytes
                 that have been counted on this DLCI."
            ::= { mfrapPerfSnaPerDlciEntry 7 }

      mfrapPerfSnaPerDlciTxPeriph    OBJECT-TYPE
             SYNTAX      Counter
             ACCESS      read-only
             STATUS      mandatory
             DESCRIPTION
                "The number of SNA Periph bytes
                 that have been counted on this DLCI."
            ::= { mfrapPerfSnaPerDlciEntry 8 }

      mfrapPerfSnaPerDlciRxAppn    OBJECT-TYPE
             SYNTAX      Counter
             ACCESS      read-only
             STATUS      mandatory
             DESCRIPTION
                "The number of SNA Appn bytes
                 that have been counted on this DLCI."
            ::= { mfrapPerfSnaPerDlciEntry 9 }

      mfrapPerfSnaPerDlciTxAppn    OBJECT-TYPE
             SYNTAX      Counter
             ACCESS      read-only
             STATUS      mandatory
             DESCRIPTION
                "The number of SNA Appn bytes
                 that have been counted on this DLCI."
            ::= { mfrapPerfSnaPerDlciEntry 10 }

      mfrapPerfSnaPerDlciRxNetbios    OBJECT-TYPE
             SYNTAX      Counter
             ACCESS      read-only
             STATUS      mandatory
             DESCRIPTION
                "The number of SNA Netbios bytes
                 that have been counted on this DLCI."
            ::= { mfrapPerfSnaPerDlciEntry 11 }

      mfrapPerfSnaPerDlciTxNetbios    OBJECT-TYPE
             SYNTAX      Counter
             ACCESS      read-only
             STATUS      mandatory
             DESCRIPTION
                "The number of SNA Netbios bytes
                 that have been counted on this DLCI."
            ::= { mfrapPerfSnaPerDlciEntry 12 }

      mfrapPerfSnaPerDlciRxOther    OBJECT-TYPE
             SYNTAX      Counter
             ACCESS      read-only
             STATUS      mandatory
             DESCRIPTION
                "The number of received bytes on this DLCI
                 from protocols over SNA that are not counted
                 elsewhere in this table."
            ::= { mfrapPerfSnaPerDlciEntry 13 }

      mfrapPerfSnaPerDlciTxOther    OBJECT-TYPE
             SYNTAX      Counter
             ACCESS      read-only
             STATUS      mandatory
             DESCRIPTION
                "The number of transmitted bytes on this DLCI
                 from protocols over SNA that are not counted
                 elsewhere in this table."
            ::= { mfrapPerfSnaPerDlciEntry 14 }


   --  SNA Short Term Statistics totals.

   mfrapPerfSnaTotalTable OBJECT-TYPE
         SYNTAX   SEQUENCE OF MfrapPerfSnaTotalEntry
         ACCESS   not-accessible
         STATUS   mandatory
         DESCRIPTION
            "Short Term Statistics on the SNA
             protocol for each DLCI."
         ::= { mfrapPerfNetworkShortTerm 14 }

         mfrapPerfSnaTotalEntry OBJECT-TYPE
             SYNTAX   MfrapPerfSnaTotalEntry
             ACCESS   not-accessible
             STATUS   mandatory
             DESCRIPTION
                "The SNA Short Term Statistics for a particular DLCI."
            INDEX { mfrapPerfSnaTotalInterval }
            ::= { mfrapPerfSnaTotalTable 1 }

         MfrapPerfSnaTotalEntry ::=
             SEQUENCE {
                 mfrapPerfSnaTotalInterval        INTEGER,
                 mfrapPerfSnaTotalRxTotal         Counter,
                 mfrapPerfSnaTotalTxTotal         Counter,
                 mfrapPerfSnaTotalRxSubarea       Counter,
                 mfrapPerfSnaTotalTxSubarea       Counter,
                 mfrapPerfSnaTotalRxPeriph        Counter,
                 mfrapPerfSnaTotalTxPeriph        Counter,
                 mfrapPerfSnaTotalRxAppn          Counter,
                 mfrapPerfSnaTotalTxAppn          Counter,
                 mfrapPerfSnaTotalRxNetbios       Counter,
                 mfrapPerfSnaTotalTxNetbios       Counter,
                 mfrapPerfSnaTotalRxOther         Counter,
                 mfrapPerfSnaTotalTxOther         Counter
             }

      mfrapPerfSnaTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfSnaTotalEntry 1 }

      mfrapPerfSnaTotalRxTotal    OBJECT-TYPE
             SYNTAX      Counter
             ACCESS      read-only
             STATUS      mandatory
             DESCRIPTION
                "The total number of SNA bytes
                 that have been counted on this DLCI."
            ::= { mfrapPerfSnaTotalEntry 3 }

      mfrapPerfSnaTotalTxTotal    OBJECT-TYPE
             SYNTAX      Counter
             ACCESS      read-only
             STATUS      mandatory
             DESCRIPTION
                "The total number of SNA bytes
                 that have been counted on this DLCI."
            ::= { mfrapPerfSnaTotalEntry 4 }

      mfrapPerfSnaTotalRxSubarea    OBJECT-TYPE
             SYNTAX      Counter
             ACCESS      read-only
             STATUS      mandatory
             DESCRIPTION
                "The number of SNA Subarea bytes
                 that have been counted on this DLCI."
            ::= { mfrapPerfSnaTotalEntry 5 }

      mfrapPerfSnaTotalTxSubarea    OBJECT-TYPE
             SYNTAX      Counter
             ACCESS      read-only
             STATUS      mandatory
             DESCRIPTION
                "The number of SNA Subarea bytes
                 that have been counted on this DLCI."
            ::= { mfrapPerfSnaTotalEntry 6 }

      mfrapPerfSnaTotalRxPeriph    OBJECT-TYPE
             SYNTAX      Counter
             ACCESS      read-only
             STATUS      mandatory
             DESCRIPTION
                "The number of SNA Periph bytes
                 that have been counted on this DLCI."
            ::= { mfrapPerfSnaTotalEntry 7 }

      mfrapPerfSnaTotalTxPeriph    OBJECT-TYPE
             SYNTAX      Counter
             ACCESS      read-only
             STATUS      mandatory
             DESCRIPTION
                "The number of SNA Periph bytes
                 that have been counted on this DLCI."
            ::= { mfrapPerfSnaTotalEntry 8 }

      mfrapPerfSnaTotalRxAppn    OBJECT-TYPE
             SYNTAX      Counter
             ACCESS      read-only
             STATUS      mandatory
             DESCRIPTION
                "The number of SNA Appn bytes
                 that have been counted on this DLCI."
            ::= { mfrapPerfSnaTotalEntry 9 }

      mfrapPerfSnaTotalTxAppn    OBJECT-TYPE
             SYNTAX      Counter
             ACCESS      read-only
             STATUS      mandatory
             DESCRIPTION
                "The number of SNA Appn bytes
                 that have been counted on this DLCI."
            ::= { mfrapPerfSnaTotalEntry 10 }

      mfrapPerfSnaTotalRxNetbios    OBJECT-TYPE
             SYNTAX      Counter
             ACCESS      read-only
             STATUS      mandatory
             DESCRIPTION
                "The number of SNA Netbios bytes
                 that have been counted on this DLCI."
            ::= { mfrapPerfSnaTotalEntry 11 }

      mfrapPerfSnaTotalTxNetbios    OBJECT-TYPE
             SYNTAX      Counter
             ACCESS      read-only
             STATUS      mandatory
             DESCRIPTION
                "The number of SNA Netbios bytes
                 that have been counted on this DLCI."
            ::= { mfrapPerfSnaTotalEntry 12 }

      mfrapPerfSnaTotalRxOther    OBJECT-TYPE
             SYNTAX      Counter
             ACCESS      read-only
             STATUS      mandatory
             DESCRIPTION
                "The number of received bytes on this DLCI
                 from protocols over SNA that are not counted
                 elsewhere in this table."
            ::= { mfrapPerfSnaTotalEntry 13 }

      mfrapPerfSnaTotalTxOther    OBJECT-TYPE
             SYNTAX      Counter
             ACCESS      read-only
             STATUS      mandatory
             DESCRIPTION
                "The number of transmitted bytes on this DLCI
                 from protocols over SNA that are not counted
                 elsewhere in this table."
            ::= { mfrapPerfSnaTotalEntry 14 }


   --  ARP Short Term Statistics for each DLCI.

   mfrapPerfArpPerDlciTable OBJECT-TYPE
         SYNTAX   SEQUENCE OF MfrapPerfArpPerDlciEntry
         ACCESS   not-accessible
         STATUS   mandatory
         DESCRIPTION
            "Short Term Statistics on the ARP
             protocol for each DLCI."
         ::= { mfrapPerfNetworkShortTerm 15 }

         mfrapPerfArpPerDlciEntry OBJECT-TYPE
             SYNTAX   MfrapPerfArpPerDlciEntry
             ACCESS   not-accessible
             STATUS   mandatory
             DESCRIPTION
                "The ARP Short Term Statistics for a particular DLCI."
            INDEX { mfrapPerfArpPerDlciInterval, mfrapPerfArpPerDlciValue }
            ::= { mfrapPerfArpPerDlciTable 1 }

         MfrapPerfArpPerDlciEntry ::=
             SEQUENCE {
                 mfrapPerfArpPerDlciInterval        INTEGER,
                 mfrapPerfArpPerDlciValue           INTEGER,
                 mfrapPerfArpPerDlciRxTotal         Counter,
                 mfrapPerfArpPerDlciTxTotal         Counter,
                 mfrapPerfArpPerDlciRxArpReq        Counter,
                 mfrapPerfArpPerDlciTxArpReq        Counter,
                 mfrapPerfArpPerDlciRxArpRep        Counter,
                 mfrapPerfArpPerDlciTxArpRep        Counter,
                 mfrapPerfArpPerDlciRxRarpReq       Counter,
                 mfrapPerfArpPerDlciTxRarpReq       Counter,
                 mfrapPerfArpPerDlciRxRarpRep       Counter,
                 mfrapPerfArpPerDlciTxRarpRep       Counter,
                 mfrapPerfArpPerDlciRxInarpReq      Counter,
                 mfrapPerfArpPerDlciTxInarpReq      Counter,
                 mfrapPerfArpPerDlciRxInarpRep      Counter,
                 mfrapPerfArpPerDlciTxInarpRep      Counter,
                 mfrapPerfArpPerDlciRxOther         Counter,
                 mfrapPerfArpPerDlciTxOther         Counter
             }

      mfrapPerfArpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfArpPerDlciEntry 1 }

      mfrapPerfArpPerDlciValue    OBJECT-TYPE
             SYNTAX      INTEGER 
            ACCESS      read-only
             STATUS      mandatory
             DESCRIPTION
                "The DLCI value in which the Statistics are associated."
            ::= { mfrapPerfArpPerDlciEntry 2 }

      mfrapPerfArpPerDlciRxTotal    OBJECT-TYPE
             SYNTAX      Counter
             ACCESS      read-only
             STATUS      mandatory
             DESCRIPTION
                "The total number of ARP bytes
                 that have been counted on this DLCI."
            ::= { mfrapPerfArpPerDlciEntry 3 }

      mfrapPerfArpPerDlciTxTotal    OBJECT-TYPE
             SYNTAX      Counter
             ACCESS      read-only
             STATUS      mandatory
             DESCRIPTION
                "The total number of ARP bytes
                 that have been counted on this DLCI."
            ::= { mfrapPerfArpPerDlciEntry 4 }

      mfrapPerfArpPerDlciRxArpReq    OBJECT-TYPE
             SYNTAX      Counter
             ACCESS      read-only
             STATUS      mandatory
             DESCRIPTION
                "The number of ARP request bytes
                 that have been counted on this DLCI."
            ::= { mfrapPerfArpPerDlciEntry 5 }

      mfrapPerfArpPerDlciTxArpReq    OBJECT-TYPE
             SYNTAX      Counter
             ACCESS      read-only
             STATUS      mandatory
             DESCRIPTION
                "The number of ARP request bytes
                 that have been counted on this DLCI."
            ::= { mfrapPerfArpPerDlciEntry 6 }

      mfrapPerfArpPerDlciRxArpRep    OBJECT-TYPE
             SYNTAX      Counter
             ACCESS      read-only
             STATUS      mandatory
             DESCRIPTION
                "The number of ARP reply bytes
                 that have been counted on this DLCI."
            ::= { mfrapPerfArpPerDlciEntry 7 }

      mfrapPerfArpPerDlciTxArpRep    OBJECT-TYPE
             SYNTAX      Counter
             ACCESS      read-only
             STATUS      mandatory
             DESCRIPTION
                "The number of ARP reply bytes
                 that have been counted on this DLCI."
            ::= { mfrapPerfArpPerDlciEntry 8 }

      mfrapPerfArpPerDlciRxRarpReq    OBJECT-TYPE
             SYNTAX      Counter
             ACCESS      read-only
             STATUS      mandatory
             DESCRIPTION
                "The number of RARP request bytes
                 that have been counted on this DLCI."
            ::= { mfrapPerfArpPerDlciEntry 9 }

      mfrapPerfArpPerDlciTxRarpReq    OBJECT-TYPE
             SYNTAX      Counter
             ACCESS      read-only
             STATUS      mandatory
             DESCRIPTION
                "The number of RARP request bytes
                 that have been counted on this DLCI."
            ::= { mfrapPerfArpPerDlciEntry 10 }

      mfrapPerfArpPerDlciRxRarpRep    OBJECT-TYPE
             SYNTAX      Counter
             ACCESS      read-only
             STATUS      mandatory
             DESCRIPTION
                "The number of RARP reply bytes
                 that have been counted on this DLCI."
            ::= { mfrapPerfArpPerDlciEntry 11 }

      mfrapPerfArpPerDlciTxRarpRep    OBJECT-TYPE
             SYNTAX      Counter
             ACCESS      read-only
             STATUS      mandatory
             DESCRIPTION
                "The number of RARP reply bytes
                 that have been counted on this DLCI."
            ::= { mfrapPerfArpPerDlciEntry 12 }

      mfrapPerfArpPerDlciRxInarpReq    OBJECT-TYPE
             SYNTAX      Counter
             ACCESS      read-only
             STATUS      mandatory
             DESCRIPTION
                "The number of INARP request bytes
                 that have been counted on this DLCI."
            ::= { mfrapPerfArpPerDlciEntry 13 }

      mfrapPerfArpPerDlciTxInarpReq    OBJECT-TYPE
             SYNTAX      Counter
             ACCESS      read-only
             STATUS      mandatory
             DESCRIPTION
                "The number of INARP request bytes
                 that have been counted on this DLCI."
            ::= { mfrapPerfArpPerDlciEntry 14 }

      mfrapPerfArpPerDlciRxInarpRep    OBJECT-TYPE
             SYNTAX      Counter
             ACCESS      read-only
             STATUS      mandatory
             DESCRIPTION
                "The number of INARP reply bytes
                 that have been counted on this DLCI."
            ::= { mfrapPerfArpPerDlciEntry 15 }

      mfrapPerfArpPerDlciTxInarpRep    OBJECT-TYPE
             SYNTAX      Counter
             ACCESS      read-only
             STATUS      mandatory
             DESCRIPTION
                "The number of INARP reply bytes
                 that have been counted on this DLCI."
            ::= { mfrapPerfArpPerDlciEntry 16 }

      mfrapPerfArpPerDlciRxOther    OBJECT-TYPE
             SYNTAX      Counter
             ACCESS      read-only
             STATUS      mandatory
             DESCRIPTION
                "The number of received bytes on this DLCI
                 from ARP message types that are not counted
                 elsewhere in this table."
            ::= { mfrapPerfArpPerDlciEntry 17 }

      mfrapPerfArpPerDlciTxOther    OBJECT-TYPE
             SYNTAX      Counter
             ACCESS      read-only
             STATUS      mandatory
             DESCRIPTION
                "The number of transmitted bytes on this DLCI
                 from ARP message types that are not counted
                 elsewhere in this table."
            ::= { mfrapPerfArpPerDlciEntry 18 }


   --  ARP Short Term Statistics totals.

   mfrapPerfArpTotalTable OBJECT-TYPE
         SYNTAX   SEQUENCE OF MfrapPerfArpTotalEntry
         ACCESS   not-accessible
         STATUS   mandatory
         DESCRIPTION
            "Short Term Statistics on the ARP
             protocol across all DLCIs."
         ::= { mfrapPerfNetworkShortTerm 16 }

         mfrapPerfArpTotalEntry OBJECT-TYPE
             SYNTAX   MfrapPerfArpTotalEntry
             ACCESS   not-accessible
             STATUS   mandatory
             DESCRIPTION
                "The ARP Short Term Statistics for a particular DLCI."
            INDEX { mfrapPerfArpTotalInterval }
            ::= { mfrapPerfArpTotalTable 1 }

         MfrapPerfArpTotalEntry ::=
             SEQUENCE {
                 mfrapPerfArpTotalInterval        INTEGER,
                 mfrapPerfArpTotalRxTotal         Counter,
                 mfrapPerfArpTotalTxTotal         Counter,
                 mfrapPerfArpTotalRxArpReq        Counter,
                 mfrapPerfArpTotalTxArpReq        Counter,
                 mfrapPerfArpTotalRxArpRep        Counter,
                 mfrapPerfArpTotalTxArpRep        Counter,
                 mfrapPerfArpTotalRxRarpReq       Counter,
                 mfrapPerfArpTotalTxRarpReq       Counter,
                 mfrapPerfArpTotalRxRarpRep       Counter,
                 mfrapPerfArpTotalTxRarpRep       Counter,
                 mfrapPerfArpTotalRxInarpReq      Counter,
                 mfrapPerfArpTotalTxInarpReq      Counter,
                 mfrapPerfArpTotalRxInarpRep      Counter,
                 mfrapPerfArpTotalTxInarpRep      Counter,
                 mfrapPerfArpTotalRxOther         Counter,
                 mfrapPerfArpTotalTxOther         Counter
             }

      mfrapPerfArpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfArpTotalEntry 1 }

      mfrapPerfArpTotalRxTotal    OBJECT-TYPE
             SYNTAX      Counter
             ACCESS      read-only
             STATUS      mandatory
             DESCRIPTION
                "The total number of ARP bytes
                 that have been counted on this DLCI."
            ::= { mfrapPerfArpTotalEntry 3 }

      mfrapPerfArpTotalTxTotal    OBJECT-TYPE
             SYNTAX      Counter
             ACCESS      read-only
             STATUS      mandatory
             DESCRIPTION
                "The total number of ARP bytes
                 that have been counted on this DLCI."
            ::= { mfrapPerfArpTotalEntry 4 }

      mfrapPerfArpTotalRxArpReq    OBJECT-TYPE
             SYNTAX      Counter
             ACCESS      read-only
             STATUS      mandatory
             DESCRIPTION
                "The number of ARP request bytes
                 that have been counted on this DLCI."
            ::= { mfrapPerfArpTotalEntry 5 }

      mfrapPerfArpTotalTxArpReq    OBJECT-TYPE
             SYNTAX      Counter
             ACCESS      read-only
             STATUS      mandatory
             DESCRIPTION
                "The number of ARP request bytes
                 that have been counted on this DLCI."
            ::= { mfrapPerfArpTotalEntry 6 }

      mfrapPerfArpTotalRxArpRep    OBJECT-TYPE
             SYNTAX      Counter
             ACCESS      read-only
             STATUS      mandatory
             DESCRIPTION
                "The number of ARP reply bytes
                 that have been counted on this DLCI."
            ::= { mfrapPerfArpTotalEntry 7 }

      mfrapPerfArpTotalTxArpRep    OBJECT-TYPE
             SYNTAX      Counter
             ACCESS      read-only
             STATUS      mandatory
             DESCRIPTION
                "The number of ARP reply bytes
                 that have been counted on this DLCI."
            ::= { mfrapPerfArpTotalEntry 8 }

      mfrapPerfArpTotalRxRarpReq    OBJECT-TYPE
             SYNTAX      Counter
             ACCESS      read-only
             STATUS      mandatory
             DESCRIPTION
                "The number of RARP request bytes
                 that have been counted on this DLCI."
            ::= { mfrapPerfArpTotalEntry 9 }

      mfrapPerfArpTotalTxRarpReq    OBJECT-TYPE
             SYNTAX      Counter
             ACCESS      read-only
             STATUS      mandatory
             DESCRIPTION
                "The number of RARP request bytes
                 that have been counted on this DLCI."
            ::= { mfrapPerfArpTotalEntry 10 }

      mfrapPerfArpTotalRxRarpRep    OBJECT-TYPE
             SYNTAX      Counter
             ACCESS      read-only
             STATUS      mandatory
             DESCRIPTION
                "The number of RARP reply bytes
                 that have been counted on this DLCI."
            ::= { mfrapPerfArpTotalEntry 11 }

      mfrapPerfArpTotalTxRarpRep    OBJECT-TYPE
             SYNTAX      Counter
             ACCESS      read-only
             STATUS      mandatory
             DESCRIPTION
                "The number of RARP reply bytes
                 that have been counted on this DLCI."
            ::= { mfrapPerfArpTotalEntry 12 }

      mfrapPerfArpTotalRxInarpReq    OBJECT-TYPE
             SYNTAX      Counter
             ACCESS      read-only
             STATUS      mandatory
             DESCRIPTION
                "The number of INARP request bytes
                 that have been counted on this DLCI."
            ::= { mfrapPerfArpTotalEntry 13 }

      mfrapPerfArpTotalTxInarpReq    OBJECT-TYPE
             SYNTAX      Counter
             ACCESS      read-only
             STATUS      mandatory
             DESCRIPTION
                "The number of INARP request bytes
                 that have been counted on this DLCI."
            ::= { mfrapPerfArpTotalEntry 14 }

      mfrapPerfArpTotalRxInarpRep    OBJECT-TYPE
             SYNTAX      Counter
             ACCESS      read-only
             STATUS      mandatory
             DESCRIPTION
                "The number of INARP reply bytes
                 that have been counted on this DLCI."
            ::= { mfrapPerfArpTotalEntry 15 }

      mfrapPerfArpTotalTxInarpRep    OBJECT-TYPE
             SYNTAX      Counter
             ACCESS      read-only
             STATUS      mandatory
             DESCRIPTION
                "The number of INARP reply bytes
                 that have been counted on this DLCI."
            ::= { mfrapPerfArpTotalEntry 16 }

      mfrapPerfArpTotalRxOther    OBJECT-TYPE
             SYNTAX      Counter
             ACCESS      read-only
             STATUS      mandatory
             DESCRIPTION
                "The number of received bytes on this DLCI
                 from ARP message types that are not counted
                 elsewhere in this table."
            ::= { mfrapPerfArpTotalEntry 17 }

      mfrapPerfArpTotalTxOther    OBJECT-TYPE
             SYNTAX      Counter
             ACCESS      read-only
             STATUS      mandatory
             DESCRIPTION
                "The number of transmitted bytes on this DLCI
                 from ARP message types that are not counted
                 elsewhere in this table."
            ::= { mfrapPerfArpTotalEntry 18 }



   --  LMI Statistics for each DLCI.

   mfrapPerfLmiPerDlciTable OBJECT-TYPE
         SYNTAX   SEQUENCE OF  MfrapPerfLmiPerDlciEntry
         ACCESS   not-accessible
         STATUS   mandatory
         DESCRIPTION
            "Short Term Statistics on LMI protocol for each DLCI."
         ::= { mfrapPerfNetworkShortTerm  17 }

         mfrapPerfLmiPerDlciEntry OBJECT-TYPE
             SYNTAX   MfrapPerfLmiPerDlciEntry
             ACCESS   not-accessible
             STATUS   mandatory
             DESCRIPTION
                "The LMI Short Term Statistics for a particular DLCI."
             INDEX { mfrapPerfLmiPerDlciInterval, mfrapPerfLmiPerDlciValue }
             ::= { mfrapPerfLmiPerDlciTable 1 }

         MfrapPerfLmiPerDlciEntry ::=
             SEQUENCE {
                 mfrapPerfLmiPerDlciInterval            INTEGER,
                 mfrapPerfLmiPerDlciValue               INTEGER,
                 mfrapPerfLmiPerDlciRxTotalByteCnt      Counter,
                 mfrapPerfLmiPerDlciTxTotalByteCnt      Counter,
                 mfrapPerfLmiPerDlciRxLivoEnqByteCnt    Counter,
                 mfrapPerfLmiPerDlciTxLivoEnqByteCnt    Counter,
                 mfrapPerfLmiPerDlciRxLivoStatByteCnt   Counter,
                 mfrapPerfLmiPerDlciTxLivoStatByteCnt   Counter,
                 mfrapPerfLmiPerDlciRxFullEnqByteCnt    Counter,
                 mfrapPerfLmiPerDlciTxFullEnqByteCnt    Counter,
                 mfrapPerfLmiPerDlciRxFullStatByteCnt   Counter,
                 mfrapPerfLmiPerDlciTxFullStatByteCnt   Counter,
                 mfrapPerfLmiPerDlciRxOtherByteCnt      Counter,
                 mfrapPerfLmiPerDlciTxOtherByteCnt      Counter
             }

      mfrapPerfLmiPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfLmiPerDlciEntry 1 }

      mfrapPerfLmiPerDlciValue    OBJECT-TYPE
             SYNTAX      INTEGER 
             ACCESS      read-only
             STATUS      mandatory
             DESCRIPTION
                "The DLCI value with which the Statistics are associated."
            ::= { mfrapPerfLmiPerDlciEntry 2 }

      mfrapPerfLmiPerDlciRxTotalByteCnt    OBJECT-TYPE
             SYNTAX      Counter 
             ACCESS      read-only
             STATUS      mandatory
             DESCRIPTION
                "The total number of received LMI bytes
                 counted on this DLCI."
            ::= { mfrapPerfLmiPerDlciEntry 3 }

      mfrapPerfLmiPerDlciTxTotalByteCnt    OBJECT-TYPE
             SYNTAX      Counter 
             ACCESS      read-only
             STATUS      mandatory
             DESCRIPTION
                "The total number of transmitted LMI bytes
                 counted on this DLCI."
            ::= { mfrapPerfLmiPerDlciEntry 4 }

      mfrapPerfLmiPerDlciRxLivoEnqByteCnt    OBJECT-TYPE
             SYNTAX      Counter  
             ACCESS      read-only
             STATUS      mandatory
             DESCRIPTION
                "The number of bytes received in Link Integrity
                 Verification Only (LIVO) enquiries on this DLCI."
            ::= { mfrapPerfLmiPerDlciEntry 5 }

      mfrapPerfLmiPerDlciTxLivoEnqByteCnt    OBJECT-TYPE
             SYNTAX      Counter  
             ACCESS      read-only
             STATUS      mandatory
             DESCRIPTION
                "The number of bytes transmitted in Link Integrity
                 Verification Only (LIVO) enquiries on this DLCI."
            ::= { mfrapPerfLmiPerDlciEntry 6 }

      mfrapPerfLmiPerDlciRxLivoStatByteCnt    OBJECT-TYPE
             SYNTAX      Counter  
             ACCESS      read-only
             STATUS      mandatory
             DESCRIPTION
                "The number of bytes received in Link Integrity
                 Verification Only (LIVO) statuses on this DLCI."
            ::= { mfrapPerfLmiPerDlciEntry 7 }

      mfrapPerfLmiPerDlciTxLivoStatByteCnt    OBJECT-TYPE
             SYNTAX      Counter  
             ACCESS      read-only
             STATUS      mandatory
             DESCRIPTION
                "The number of bytes transmitted in Link Integrity
                 Verification Only (LIVO) statuses on this DLCI."
            ::= { mfrapPerfLmiPerDlciEntry 8 }

      mfrapPerfLmiPerDlciRxFullEnqByteCnt    OBJECT-TYPE
             SYNTAX      Counter  
             ACCESS      read-only
             STATUS      mandatory
             DESCRIPTION
                "The number of bytes received in 
                 Full Status enquiries on this DLCI."
            ::= { mfrapPerfLmiPerDlciEntry 9 }

      mfrapPerfLmiPerDlciTxFullEnqByteCnt    OBJECT-TYPE
             SYNTAX      Counter  
             ACCESS      read-only
             STATUS      mandatory
             DESCRIPTION
                "The number of bytes transmitted in 
                 Full Status enquiries on this DLCI."
            ::= { mfrapPerfLmiPerDlciEntry 10 }

      mfrapPerfLmiPerDlciRxFullStatByteCnt    OBJECT-TYPE
             SYNTAX      Counter  
             ACCESS      read-only
             STATUS      mandatory
             DESCRIPTION
                "The number of bytes received in 
                 Full Status messages on this DLCI."
            ::= { mfrapPerfLmiPerDlciEntry 11 }

      mfrapPerfLmiPerDlciTxFullStatByteCnt    OBJECT-TYPE
             SYNTAX      Counter  
             ACCESS      read-only
             STATUS      mandatory
             DESCRIPTION
                "The number of bytes transmitted in 
                 Full Status messages on this DLCI."
            ::= { mfrapPerfLmiPerDlciEntry 12 }

      mfrapPerfLmiPerDlciRxOtherByteCnt    OBJECT-TYPE
             SYNTAX      Counter  
             ACCESS      read-only
             STATUS      mandatory
             DESCRIPTION
                "The number of received bytes on this DLCI
                 from LMI protocols that are not counted
                 elsewhere (other than Total) in this table."
            ::= { mfrapPerfLmiPerDlciEntry 13 }

      mfrapPerfLmiPerDlciTxOtherByteCnt    OBJECT-TYPE
             SYNTAX      Counter  
             ACCESS      read-only
             STATUS      mandatory
             DESCRIPTION
                "The number of transmitted bytes on this DLCI
                 from LMI protocols that are not counted
                 elsewhere (other than Total) in this table."
            ::= { mfrapPerfLmiPerDlciEntry 14 }


   --  LMI Statistics for totals.

   mfrapPerfLmiTotalTable OBJECT-TYPE
         SYNTAX   SEQUENCE OF MfrapPerfLmiTotalEntry
         ACCESS   not-accessible
         STATUS   mandatory
         DESCRIPTION
            "Short Term Statistics on LMI protocol across all DLCIs."
         ::= { mfrapPerfNetworkShortTerm 18 }

         mfrapPerfLmiTotalEntry OBJECT-TYPE
             SYNTAX   MfrapPerfLmiTotalEntry
             ACCESS   not-accessible
             STATUS   mandatory
             DESCRIPTION
                "The LMI Short Term Statistics across all DLCIs."
             INDEX { mfrapPerfLmiTotalInterval }
             ::= { mfrapPerfLmiTotalTable 1 }

         MfrapPerfLmiTotalEntry ::=
             SEQUENCE {
                 mfrapPerfLmiTotalInterval            INTEGER,
                 mfrapPerfLmiTotalDlciValue           INTEGER,
                 mfrapPerfLmiTotalRxTotalByteCnt      Counter,
                 mfrapPerfLmiTotalTxTotalByteCnt      Counter,
                 mfrapPerfLmiTotalRxLivoEnqByteCnt    Counter,
                 mfrapPerfLmiTotalTxLivoEnqByteCnt    Counter,
                 mfrapPerfLmiTotalRxLivoStatByteCnt   Counter,
                 mfrapPerfLmiTotalTxLivoStatByteCnt   Counter,
                 mfrapPerfLmiTotalRxFullEnqByteCnt    Counter,
                 mfrapPerfLmiTotalTxFullEnqByteCnt    Counter,
                 mfrapPerfLmiTotalRxFullStatByteCnt   Counter,
                 mfrapPerfLmiTotalTxFullStatByteCnt   Counter,
                 mfrapPerfLmiTotalRxOtherByteCnt      Counter,
                 mfrapPerfLmiTotalTxOtherByteCnt      Counter
             }

      mfrapPerfLmiTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfLmiTotalEntry 1 }

      mfrapPerfLmiTotalDlciValue    OBJECT-TYPE
             SYNTAX      INTEGER 
             ACCESS      read-only
             STATUS      mandatory
             DESCRIPTION
                "OBSOLETE."
            ::= { mfrapPerfLmiTotalEntry 2 }

      mfrapPerfLmiTotalRxTotalByteCnt    OBJECT-TYPE
             SYNTAX      Counter  
             ACCESS      read-only
             STATUS      mandatory
             DESCRIPTION
                "The total number of received LMI bytes
                 counted on this DLCI."
            ::= { mfrapPerfLmiTotalEntry 3 }

      mfrapPerfLmiTotalTxTotalByteCnt    OBJECT-TYPE
             SYNTAX      Counter  
             ACCESS      read-only
             STATUS      mandatory
             DESCRIPTION
                "The total number of transmitted LMI bytes
                 counted on this DLCI."
            ::= { mfrapPerfLmiTotalEntry 4 }

      mfrapPerfLmiTotalRxLivoEnqByteCnt    OBJECT-TYPE
             SYNTAX      Counter  
             ACCESS      read-only
             STATUS      mandatory
             DESCRIPTION
                "The number of bytes received in Link Integrity
                 Verification Only (LIVO) enquiries on this DLCI."
            ::= { mfrapPerfLmiTotalEntry 5 }

      mfrapPerfLmiTotalTxLivoEnqByteCnt    OBJECT-TYPE
             SYNTAX      Counter  
             ACCESS      read-only
             STATUS      mandatory
             DESCRIPTION
                "The number of bytes transmitted in Link Integrity
                 Verification Only (LIVO) enquiries on this DLCI."
            ::= { mfrapPerfLmiTotalEntry 6 }

      mfrapPerfLmiTotalRxLivoStatByteCnt    OBJECT-TYPE
             SYNTAX      Counter  
             ACCESS      read-only
             STATUS      mandatory
             DESCRIPTION
                "The number of bytes received in Link Integrity
                 Verification Only (LIVO) statuses on this DLCI."
            ::= { mfrapPerfLmiTotalEntry 7 }

      mfrapPerfLmiTotalTxLivoStatByteCnt    OBJECT-TYPE
             SYNTAX      Counter  
             ACCESS      read-only
             STATUS      mandatory
             DESCRIPTION
                "The number of bytes transmitted in Link Integrity
                 Verification Only (LIVO) statuses on this DLCI."
            ::= { mfrapPerfLmiTotalEntry 8 }

      mfrapPerfLmiTotalRxFullEnqByteCnt    OBJECT-TYPE
             SYNTAX      Counter  
             ACCESS      read-only
             STATUS      mandatory
             DESCRIPTION
                "The number of bytes received in 
                 Full Status enquiries on this DLCI."
            ::= { mfrapPerfLmiTotalEntry 9 }

      mfrapPerfLmiTotalTxFullEnqByteCnt    OBJECT-TYPE
             SYNTAX      Counter  
             ACCESS      read-only
             STATUS      mandatory
             DESCRIPTION
                "The number of bytes transmitted in 
                 Full Status enquiries on this DLCI."
            ::= { mfrapPerfLmiTotalEntry 10 }

      mfrapPerfLmiTotalRxFullStatByteCnt    OBJECT-TYPE
             SYNTAX      Counter  
             ACCESS      read-only
             STATUS      mandatory
             DESCRIPTION
                "The number of bytes received in 
                 Full Status messages on this DLCI."
            ::= { mfrapPerfLmiTotalEntry 11 }

      mfrapPerfLmiTotalTxFullStatByteCnt    OBJECT-TYPE
             SYNTAX      Counter  
             ACCESS      read-only
             STATUS      mandatory
             DESCRIPTION
                "The number of bytes transmitted in 
                 Full Status messages on this DLCI."
            ::= { mfrapPerfLmiTotalEntry 12 }

      mfrapPerfLmiTotalRxOtherByteCnt    OBJECT-TYPE
             SYNTAX      Counter  
             ACCESS      read-only
             STATUS      mandatory
             DESCRIPTION
                "The number of received bytes on this DLCI
                 from LMI protocols that are not counted
                 elsewhere (other than Total) in this table."
            ::= { mfrapPerfLmiTotalEntry 13 }

      mfrapPerfLmiTotalTxOtherByteCnt   OBJECT-TYPE
             SYNTAX      Counter  
             ACCESS      read-only
             STATUS      mandatory
             DESCRIPTION
                "The number of transmitted bytes on this DLCI
                 from LMI protocols that are not counted
                 elsewhere (other than Total) in this table."
            ::= { mfrapPerfLmiTotalEntry 14 }




mfrapPerfNetworkLongTerm OBJECT IDENTIFIER ::= { mfrapPerformance 5 }

--
--       Long Term Statistics by DLCI, protocol, and interval.
--

   mfrapPerfNetwLongTermTable OBJECT-TYPE
         SYNTAX   SEQUENCE OF MfrapPerfNetwLongTermEntry
         ACCESS   not-accessible
         STATUS   mandatory
         DESCRIPTION
            "Long Term Statistics by DLCI, protocol, and interval.
             LT statistics are collected on a configurable set
             of DLCIs and protocols. There are 96 intervals maintained
             each with a duration defined by the Long Term Timer. 
             Interval 96 is the current window and Interval 1 is 
             furthest back in time (96xLT Timer seconds ago)."
         ::= { mfrapPerfNetworkLongTerm 1 }

         mfrapPerfNetwLongTermEntry OBJECT-TYPE
             SYNTAX   MfrapPerfNetwLongTermEntry
             ACCESS   not-accessible
             STATUS   mandatory
             DESCRIPTION
                "The Long Term Statistic for a particular DLCI,
                 protocol and interval."
            INDEX { mfrapPerfNetwLongTermDlci,
                    mfrapPerfNetwLongTermProtocol,
                    mfrapPerfNetwLongTermInterval }
            ::= { mfrapPerfNetwLongTermTable 1 }

         MfrapPerfNetwLongTermEntry ::=
             SEQUENCE {
                 mfrapPerfNetwLongTermDlci      INTEGER,
                 mfrapPerfNetwLongTermProtocol  INTEGER,
                 mfrapPerfNetwLongTermInterval  INTEGER,
                 mfrapPerfNetwLongTermValue     Counter
             }

         mfrapPerfNetwLongTermDlci    OBJECT-TYPE
             SYNTAX      INTEGER 
             ACCESS      read-only
             STATUS      mandatory
             DESCRIPTION
               "The DLCI monitored for the statistics. The Long
                Term DLCI filter must first be configured." 
            ::= { mfrapPerfNetwLongTermEntry 1 }

         mfrapPerfNetwLongTermProtocol    OBJECT-TYPE
            SYNTAX      INTEGER
            {
               ip-tx-bc                    (1),
               ip-rx-bc                    (2),
               tcp-ip-tx-bc                (3),
               tcp-ip-rx-bc                (4),
               ftp-tcp-ip-tx-bc            (5),
               ftp-tcp-ip-rx-bc            (6),
               telnet-tcp-ip-tx-bc         (7),
               telnet-tcp-ip-rx-bc         (8),
               smtp-tcp-ip-tx-bc           (9),
               smtp-tcp-ip-rx-bc           (10),
--             tftp-tcp-ip-tx-bc           (11),
--             tftp-tcp-ip-rx-bc           (12),
               http-tcp-ip-tx-bc           (13),
               http-tcp-ip-rx-bc           (14),
               netbios-ssn-tcp-ip-tx-bc    (15),
               netbios-ssn-tcp-ip-rx-bc    (16),
--             snmp-tcp-ip-tx-bc           (17),
--             snmp-tcp-ip-rx-bc           (18),
--             snmptrap-tcp-ip-tx-bc       (19),
--             snmptrap-tcp-ip-rx-bc       (20),
               udp-ip-tx-bc                (21),
               udp-ip-rx-bc                (22),
--             ftp-udp-ip-tx-bc            (23),
--             ftp-udp-ip-rx-bc            (24),
--             telnet-udp-ip-tx-bc         (25),
--             telnet-udp-ip-rx-bc         (26),
--             smtp-udp-ip-tx-bc           (27),
--             smtp-udp-ip-rx-bc           (28),
               tftp-udp-ip-tx-bc           (29),
               tftp-udp-ip-rx-bc           (30),
--             http-udp-ip-tx-bc           (31),
--             http-udp-ip-rx-bc           (32),
               netbios-dgm-udp-ip-tx-bc    (33),
               netbios-dgm-udp-ip-rx-bc    (34),
               snmp-udp-ip-tx-bc           (35),
               snmp-udp-ip-rx-bc           (36),
               snmptrap-udp-ip-tx-bc       (37),
               snmptrap-udp-ip-rx-bc       (38),
               rip-udp-ip-tx-bc            (39),
               rip-udp-ip-rx-bc            (40),
               icmp-ip-tx-bc               (41),
               icmp-ip-rx-bc               (42),
               echorep-icmp-ip-tx-bc       (43),
               echorep-icmp-ip-rx-bc       (44),
               dest-unr-icmp-ip-tx-bc      (45),
               dest-unr-icmp-ip-rx-bc      (46),
               src-quench-icmp-ip-tx-bc    (47),
               src-quench-icmp-ip-rx-bc    (48),
               redirect-icmp-ip-tx-bc      (49),
               redirect-icmp-ip-rx-bc      (50),
               echoreq-icmp-ip-tx-bc       (51),
               echoreq-icmp-ip-rx-bc       (52),
               time-excd-icmp-ip-tx-bc     (53),
               time-excd-icmp-ip-rx-bc     (54),
               param-prob-icmp-ip-tx-bc    (55),
               param-prob-icmp-ip-rx-bc    (56),
               timestamp-req-icmp-ip-tx-bc (57),
               timestamp-req-icmp-ip-rx-bc (58),
               timestamp-rep-icmp-ip-tx-bc (59),
               timestamp-rep-icmp-ip-rx-bc (60),
               addr-mask-req-icmp-ip-tx-bc (61),
               addr-mask-req-icmp-ip-rx-bc (62),
               addr-mask-rep-icmp-ip-tx-bc (63),
               addr-mask-rep-icmp-ip-rx-bc (64),
               pkt-too-big-icmp-ip-tx-bc   (65),
               pkt-too-big-icmp-ip-rx-bc   (66),
               gp-mem-query-icmp-ip-tx-bc  (67),
               gp-mem-query-icmp-ip-rx-bc  (68),
               gp-mem-report-icmp-ip-tx-bc (69),
               gp-mem-report-icmp-ip-rx-bc (70),
               gp-mem-reduct-icmp-ip-tx-bc (71),
               gp-mem-reduct-icmp-ip-rx-bc (72),
               ospf-ip-tx-bc               (73),
               ospf-ip-rx-bc               (74),
               other-ip-tx-bc              (75),
               other-ip-rx-bc              (76),
               ipx-tx-bc                   (77),
               ipx-rx-bc                   (78),
               spx-ipx-tx-bc               (79),
               spx-ipx-rx-bc               (80),
               ncp-ipx-tx-bc               (81),
               ncp-ipx-rx-bc               (82),
               sap-ipx-tx-bc               (83),
               sap-ipx-rx-bc               (84),
               rip-ipx-tx-bc               (85),
               rip-ipx-rx-bc               (86),
               netbios-ipx-tx-bc           (87),
               netbios-ipx-rx-bc           (88),
               other-ipx-tx-bc             (89),
               other-ipx-rx-bc             (90),
               arp-tx-bc                   (91),
               arp-rx-bc                   (92),
               arp-req-tx-bc               (93),
               arp-req-rx-bc               (94),
               arp-rep-tx-bc               (95),
               arp-rep-rx-bc               (96),
               rarp-req-tx-bc              (97),
               rarp-req-rx-bc              (98),
               rarp-rep-tx-bc              (99),
               rarp-rep-rx-bc              (100),
               inarp-req-tx-bc             (101),
               inarp-req-rx-bc             (102),
               inarp-rep-tx-bc             (103),
               inarp-rep-rx-bc             (104),
               sna-tx-bc                   (105),
               sna-rx-bc                   (106),
               sna-subarea-tx-bc           (107),
               sna-subarea-rx-bc           (108),
               sna-periph-tx-bc            (109),
               sna-periph-rx-bc            (110),
               sna-appn-tx-bc              (111),
               sna-appn-rx-bc              (112),
               sna-netbios-tx-bc           (113),
               sna-netbios-rx-bc           (114),
               cisco-tx-bc                 (115),
               cisco-rx-bc                 (116),
               other-tx-bc                 (117),
               other-rx-bc                 (118),
               user-defined-1-tx-bc        (119),
               user-defined-1-rx-bc        (120),
               user-defined-2-tx-bc        (121),
               user-defined-2-rx-bc        (122),
               user-defined-3-tx-bc        (123),
               user-defined-3-rx-bc        (124),
               user-defined-4-tx-bc        (125),
               user-defined-4-rx-bc        (126),
               thru-byte-tx-bc             (127),
               thru-byte-rx-bc             (128),
               thru-frame-tx-bc            (129),
               thru-frame-rx-bc            (130),
               thru-fecn-tx-bc             (131),
               thru-fecn-rx-bc             (132),
               thru-becn-tx-bc             (133),
               thru-becn-rx-bc             (134),
               thru-de-tx-bc               (135),
               thru-de-rx-bc               (136),
               cir-percent-range1-tx-bc    (137),
               cir-percent-range1-rx-bc    (138),
               cir-percent-range2-tx-bc    (139),
               cir-percent-range2-rx-bc    (140),
               cir-percent-range3-tx-bc    (141),
               cir-percent-range3-rx-bc    (142),
               cir-percent-range4-tx-bc    (143),
               cir-percent-range4-rx-bc    (144),
               cir-percent-range5-tx-bc    (145),
               cir-percent-range5-rx-bc    (146),
               cir-percent-range6-tx-bc    (147),
               cir-percent-range6-rx-bc    (148),
               cir-percent-range7-tx-bc    (149),
               cir-percent-range7-rx-bc    (150),
               cir-percent-range8-tx-bc    (151),
               cir-percent-range8-rx-bc    (152),
               lmi-tx-bc                   (153),
               lmi-rx-bc                   (154),
               lmi-livo-enq-tx-bc          (155),
               lmi-livo-enq-rx-bc          (156),
               lmi-livo-stat-tx-bc         (157),
               lmi-livo-stat-rx-bc         (158),
               lmi-full-enq-tx-bc          (159),
               lmi-full-enq-rx-bc          (160),
               lmi-full-stat-tx-bc         (161),
               lmi-full-stat-rx-bc         (162),
               lmi-other-tx-bc             (163),
               lmi-other-rx-bc             (164),
               total-uptime                (165),
               total-downtime              (166),
               igrp-tx-bc                  (167),
               igrp-rx-bc                  (168),
               vnip-tx-bc                  (169),
               vnip-rx-bc                  (170),
               annex-g-tx-bc               (171),
               annex-g-rx-bc               (172)
            }
            ACCESS      read-only
            STATUS      mandatory
            DESCRIPTION
             "The type of protocol monitored for the statistics."
            ::= { mfrapPerfNetwLongTermEntry 2 }

         mfrapPerfNetwLongTermInterval    OBJECT-TYPE
             SYNTAX      INTEGER 
             ACCESS      read-only
             STATUS      mandatory
             DESCRIPTION
                "The time interval in which the value was collected.
                 Long Term statistis are maintained for 96 intervals 
                 with the interval duration defined by 
                 (CfgFrPerfTimersLTInterval)."
            ::= { mfrapPerfNetwLongTermEntry 3 }

         mfrapPerfNetwLongTermValue    OBJECT-TYPE
             SYNTAX      Counter
             ACCESS      read-only
             STATUS      mandatory
             DESCRIPTION
                "The statistic collected for the given DLCI and protocol
                 and within the given time interval."
            ::= { mfrapPerfNetwLongTermEntry 4 }


--
--       Long Term Statistics by DLCI: alternative method.
--

   mfrapPerfNetwLongTermAltTable OBJECT-TYPE
         SYNTAX   SEQUENCE OF MfrapPerfNetwLongTermAltEntry
         ACCESS   not-accessible
         STATUS   mandatory
         DESCRIPTION
            "This is an alternative method to access the database of
             long term statistics.  The statistics are indexed by DLCI
             and protocol and are returned in an OCTETSTRING."
         ::= { mfrapPerfNetworkLongTerm 2 }

         mfrapPerfNetwLongTermAltEntry   OBJECT-TYPE
             SYNTAX   MfrapPerfNetwLongTermAltEntry
             ACCESS   not-accessible
             STATUS   mandatory
             DESCRIPTION
                "The Long Term Statistic for a particular
                 DLCI and protocol."
            INDEX { mfrapPerfNetwLongTermAltDlci,
                    mfrapPerfNetwLongTermAltProtocol }
            ::= { mfrapPerfNetwLongTermAltTable 1 }

         MfrapPerfNetwLongTermAltEntry ::=
             SEQUENCE {
                 mfrapPerfNetwLongTermAltDlci      INTEGER,
                 mfrapPerfNetwLongTermAltProtocol  INTEGER,
                 mfrapPerfNetwLongTermAltArray     OCTET STRING
             }

         mfrapPerfNetwLongTermAltDlci    OBJECT-TYPE
             SYNTAX      INTEGER 
             ACCESS      read-only
             STATUS      mandatory
             DESCRIPTION
               "The DLCI monitored for the statistics."
            ::= { mfrapPerfNetwLongTermAltEntry 1 }

         mfrapPerfNetwLongTermAltProtocol   OBJECT-TYPE
             SYNTAX      INTEGER 
             {
               ip-tx-bc                    (1),
               ip-rx-bc                    (2),
               tcp-ip-tx-bc                (3),
               tcp-ip-rx-bc                (4),
               ftp-tcp-ip-tx-bc            (5),
               ftp-tcp-ip-rx-bc            (6),
               telnet-tcp-ip-tx-bc         (7),
               telnet-tcp-ip-rx-bc         (8),
               smtp-tcp-ip-tx-bc           (9),
               smtp-tcp-ip-rx-bc           (10),
--             tftp-tcp-ip-tx-bc           (11),
--             tftp-tcp-ip-rx-bc           (12),
               http-tcp-ip-tx-bc           (13),
               http-tcp-ip-rx-bc           (14),
               netbios-ssn-tcp-ip-tx-bc    (15),
               netbios-ssn-tcp-ip-rx-bc    (16),
--             snmp-tcp-ip-tx-bc           (17),
--             snmp-tcp-ip-rx-bc           (18),
--             snmptrap-tcp-ip-tx-bc       (19),
--             snmptrap-tcp-ip-rx-bc       (20),
               udp-ip-tx-bc                (21),
               udp-ip-rx-bc                (22),
--             ftp-udp-ip-tx-bc            (23),
--             ftp-udp-ip-rx-bc            (24),
--             telnet-udp-ip-tx-bc         (25),
--             telnet-udp-ip-rx-bc         (26),
--             smtp-udp-ip-tx-bc           (27),
--             smtp-udp-ip-rx-bc           (28),
               tftp-udp-ip-tx-bc           (29),
               tftp-udp-ip-rx-bc           (30),
--             http-udp-ip-tx-bc           (31),
--             http-udp-ip-rx-bc           (32),
               netbios-dgm-udp-ip-tx-bc    (33),
               netbios-dgm-udp-ip-rx-bc    (34),
               snmp-udp-ip-tx-bc           (35),
               snmp-udp-ip-rx-bc           (36),
               snmptrap-udp-ip-tx-bc       (37),
               snmptrap-udp-ip-rx-bc       (38),
               rip-udp-ip-tx-bc            (39),
               rip-udp-ip-rx-bc            (40),
               icmp-ip-tx-bc               (41),
               icmp-ip-rx-bc               (42),
               echorep-icmp-ip-tx-bc       (43),
               echorep-icmp-ip-rx-bc       (44),
               dest-unr-icmp-ip-tx-bc      (45),
               dest-unr-icmp-ip-rx-bc      (46),
               src-quench-icmp-ip-tx-bc    (47),
               src-quench-icmp-ip-rx-bc    (48),
               redirect-icmp-ip-tx-bc      (49),
               redirect-icmp-ip-rx-bc      (50),
               echoreq-icmp-ip-tx-bc       (51),
               echoreq-icmp-ip-rx-bc       (52),
               time-excd-icmp-ip-tx-bc     (53),
               time-excd-icmp-ip-rx-bc     (54),
               param-prob-icmp-ip-tx-bc    (55),
               param-prob-icmp-ip-rx-bc    (56),
               timestamp-req-icmp-ip-tx-bc (57),
               timestamp-req-icmp-ip-rx-bc (58),
               timestamp-rep-icmp-ip-tx-bc (59),
               timestamp-rep-icmp-ip-rx-bc (60),
               addr-mask-req-icmp-ip-tx-bc (61),
               addr-mask-req-icmp-ip-rx-bc (62),
               addr-mask-rep-icmp-ip-tx-bc (63),
               addr-mask-rep-icmp-ip-rx-bc (64),
               pkt-too-big-icmp-ip-tx-bc   (65),
               pkt-too-big-icmp-ip-rx-bc   (66),
               gp-mem-query-icmp-ip-tx-bc  (67),
               gp-mem-query-icmp-ip-rx-bc  (68),
               gp-mem-report-icmp-ip-tx-bc (69),
               gp-mem-report-icmp-ip-rx-bc (70),
               gp-mem-reduct-icmp-ip-tx-bc (71),
               gp-mem-reduct-icmp-ip-rx-bc (72),
               ospf-ip-tx-bc               (73),
               ospf-ip-rx-bc               (74),
               other-ip-tx-bc              (75),
               other-ip-rx-bc              (76),
               ipx-tx-bc                   (77),
               ipx-rx-bc                   (78),
               spx-ipx-tx-bc               (79),
               spx-ipx-rx-bc               (80),
               ncp-ipx-tx-bc               (81),
               ncp-ipx-rx-bc               (82),
               sap-ipx-tx-bc               (83),
               sap-ipx-rx-bc               (84),
               rip-ipx-tx-bc               (85),
               rip-ipx-rx-bc               (86),
               netbios-ipx-tx-bc           (87),
               netbios-ipx-rx-bc           (88),
               other-ipx-tx-bc             (89),
               other-ipx-rx-bc             (90),
               arp-tx-bc                   (91),
               arp-rx-bc                   (92),
               arp-req-tx-bc               (93),
               arp-req-rx-bc               (94),
               arp-rep-tx-bc               (95),
               arp-rep-rx-bc               (96),
               rarp-req-tx-bc              (97),
               rarp-req-rx-bc              (98),
               rarp-rep-tx-bc              (99),
               rarp-rep-rx-bc              (100),
               inarp-req-tx-bc             (101),
               inarp-req-rx-bc             (102),
               inarp-rep-tx-bc             (103),
               inarp-rep-rx-bc             (104),
               sna-tx-bc                   (105),
               sna-rx-bc                   (106),
               sna-subarea-tx-bc           (107),
               sna-subarea-rx-bc           (108),
               sna-periph-tx-bc            (109),
               sna-periph-rx-bc            (110),
               sna-appn-tx-bc              (111),
               sna-appn-rx-bc              (112),
               sna-netbios-tx-bc           (113),
               sna-netbios-rx-bc           (114),
               cisco-tx-bc                 (115),
               cisco-rx-bc                 (116),
               other-tx-bc                 (117),
               other-rx-bc                 (118),
               user-defined-1-tx-bc        (119),
               user-defined-1-rx-bc        (120),
               user-defined-2-tx-bc        (121),
               user-defined-2-rx-bc        (122),
               user-defined-3-tx-bc        (123),
               user-defined-3-rx-bc        (124),
               user-defined-4-tx-bc        (125),
               user-defined-4-rx-bc        (126),
               thru-byte-tx-bc             (127),
               thru-byte-rx-bc             (128),
               thru-frame-tx-bc            (129),
               thru-frame-rx-bc            (130),
               thru-fecn-tx-bc             (131),
               thru-fecn-rx-bc             (132),
               thru-becn-tx-bc             (133),
               thru-becn-rx-bc             (134),
               thru-de-tx-bc               (135),
               thru-de-rx-bc               (136),
               cir-percent-range1-tx-bc    (137),
               cir-percent-range1-rx-bc    (138),
               cir-percent-range2-tx-bc    (139),
               cir-percent-range2-rx-bc    (140),
               cir-percent-range3-tx-bc    (141),
               cir-percent-range3-rx-bc    (142),
               cir-percent-range4-tx-bc    (143),
               cir-percent-range4-rx-bc    (144),
               cir-percent-range5-tx-bc    (145),
               cir-percent-range5-rx-bc    (146),
               cir-percent-range6-tx-bc    (147),
               cir-percent-range6-rx-bc    (148),
               cir-percent-range7-tx-bc    (149),
               cir-percent-range7-rx-bc    (150),
               cir-percent-range8-tx-bc    (151),
               cir-percent-range8-rx-bc    (152),
               lmi-tx-bc                   (153),
               lmi-rx-bc                   (154),
               lmi-livo-enq-tx-bc          (155),
               lmi-livo-enq-rx-bc          (156),
               lmi-livo-stat-tx-bc         (157),
               lmi-livo-stat-rx-bc         (158),
               lmi-full-enq-tx-bc          (159),
               lmi-full-enq-rx-bc          (160),
               lmi-full-stat-tx-bc         (161),
               lmi-full-stat-rx-bc         (162),
               lmi-other-tx-bc             (163),
               lmi-other-rx-bc             (164),
               total-uptime                (165),
               total-downtime              (166),
               igrp-tx-bc                  (167),
               igrp-rx-bc                  (168),
               vnip-tx-bc                  (169),
               vnip-rx-bc                  (170),
               annex-g-tx-bc               (171),
               annex-g-rx-bc               (172)
             }
             ACCESS      read-only
             STATUS      mandatory
             DESCRIPTION
               "The protocol monitored for the statistics."
            ::= { mfrapPerfNetwLongTermAltEntry 2 }
          
         mfrapPerfNetwLongTermAltArray    OBJECT-TYPE
          SYNTAX      OCTET STRING
             ACCESS      read-only
             STATUS      mandatory
             DESCRIPTION
                "The statistic collected for the given DLCI and protocol."
            ::= { mfrapPerfNetwLongTermAltEntry 3 }


   mfrapPerfNetworkLongTermCommands OBJECT IDENTIFIER
            ::= { mfrapPerfNetworkLongTerm 3 }

   mfrapPerfNetworkLongTermCmdClear    OBJECT-TYPE
          SYNTAX      INTEGER
          {
              clear-statistics (1)
          }
          ACCESS      write-only
          STATUS      mandatory
          DESCRIPTION
             "Allows the user to zero out all the statistics in
              the long term statistics tables.
              (1) Clear all Long Term statistics"
          ::= { mfrapPerfNetworkLongTermCommands 1 }


mfrapPerfCirPercentUtilization OBJECT IDENTIFIER ::= { mfrapPerformance 6 }

--
--  CIR Percentage Statistics for each DLCI.
--

 mfrapPerfCirPercentUtilizationTable OBJECT-TYPE
         SYNTAX   SEQUENCE OF MfrapPerfCirPercentUtilizationEntry
         ACCESS   not-accessible
         STATUS   mandatory
         DESCRIPTION
            "Short Term Statistics on the percentage of CIR used
             on each DLCI.  Each short term statistics interval,
             the count of bytes transmitted and received is used
             to calculate the percentage of CIR used.  The byte
             count is then added to the appropriate bucket for
             the CIR percentage range."
         ::= { mfrapPerfCirPercentUtilization 1 }

 mfrapPerfCirPercentUtilizationEntry OBJECT-TYPE
             SYNTAX MfrapPerfCirPercentUtilizationEntry
             ACCESS   not-accessible
             STATUS   mandatory
             DESCRIPTION
                "The CIR Percentage Statistics for a particular DLCI."
             INDEX { mfrapPerfCirPercentUtilizationInterval,
                     mfrapPerfCirPercentUtilizationDlciValue }
             ::= { mfrapPerfCirPercentUtilizationTable 1 }

         MfrapPerfCirPercentUtilizationEntry ::=
             SEQUENCE {
                 mfrapPerfCirPercentUtilizationInterval    INTEGER,
                 mfrapPerfCirPercentUtilizationDlciValue   INTEGER,
                 mfrapPerfCirRxPercentUtilizationRange1    INTEGER,
                 mfrapPerfCirRxPercentUtilizationRange2    INTEGER,
                 mfrapPerfCirRxPercentUtilizationRange3    INTEGER,
                 mfrapPerfCirRxPercentUtilizationRange4    INTEGER,
                 mfrapPerfCirRxPercentUtilizationRange5    INTEGER,
                 mfrapPerfCirRxPercentUtilizationRange6    INTEGER,
                 mfrapPerfCirRxPercentUtilizationRange7    INTEGER,
                 mfrapPerfCirRxPercentUtilizationRange8    INTEGER,
                 mfrapPerfCirTxPercentUtilizationRange1    INTEGER,
                 mfrapPerfCirTxPercentUtilizationRange2    INTEGER,
                 mfrapPerfCirTxPercentUtilizationRange3    INTEGER,
                 mfrapPerfCirTxPercentUtilizationRange4    INTEGER,
                 mfrapPerfCirTxPercentUtilizationRange5    INTEGER,
                 mfrapPerfCirTxPercentUtilizationRange6    INTEGER,
                 mfrapPerfCirTxPercentUtilizationRange7    INTEGER,
                 mfrapPerfCirTxPercentUtilizationRange8    INTEGER
             }

 mfrapPerfCirPercentUtilizationInterval OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { mfrapPerfCirPercentUtilizationEntry 1 }

 mfrapPerfCirPercentUtilizationDlciValue OBJECT-TYPE
             SYNTAX      INTEGER 
             ACCESS      read-only
             STATUS      mandatory
             DESCRIPTION
                "The DLCI value with which the Statistics are associated."
            ::= { mfrapPerfCirPercentUtilizationEntry 2 }

 mfrapPerfCirRxPercentUtilizationRange1 OBJECT-TYPE
             SYNTAX      INTEGER 
             ACCESS      read-only
             STATUS      mandatory
             DESCRIPTION
                "The number of short-term intervals during
                 which rx data throughput on this DLCI compared
                 to CIR was in range 1 (0% of CIR)."
            ::= { mfrapPerfCirPercentUtilizationEntry 21 }

 mfrapPerfCirRxPercentUtilizationRange2 OBJECT-TYPE
             SYNTAX      INTEGER 
             ACCESS      read-only
             STATUS      mandatory
             DESCRIPTION
                "The number of short-term intervals during
                 which rx data throughput on this DLCI compared
                 to CIR was in range 2 (1-10% of CIR)."
            ::= { mfrapPerfCirPercentUtilizationEntry 22 }

 mfrapPerfCirRxPercentUtilizationRange3 OBJECT-TYPE
             SYNTAX      INTEGER 
             ACCESS      read-only
             STATUS      mandatory
             DESCRIPTION
                "The number of short-term intervals during
                 which rx data throughput on this DLCI compared
                 to CIR was in range 3 (11-20% of CIR)."
            ::= { mfrapPerfCirPercentUtilizationEntry 23 }

 mfrapPerfCirRxPercentUtilizationRange4 OBJECT-TYPE
             SYNTAX      INTEGER 
             ACCESS      read-only
             STATUS      mandatory
             DESCRIPTION
                "The number of short-term intervals during
                 which rx data throughput on this DLCI compared
                 to CIR was in range 4 (21-50% of CIR)."
            ::= { mfrapPerfCirPercentUtilizationEntry 24 }

 mfrapPerfCirRxPercentUtilizationRange5 OBJECT-TYPE
             SYNTAX      INTEGER 
             ACCESS      read-only
             STATUS      mandatory
             DESCRIPTION
                "The number of short-term intervals during
                 which rx data throughput on this DLCI compared
                 to CIR was in range 5 (51-80% of CIR)."
            ::= { mfrapPerfCirPercentUtilizationEntry 25 }

 mfrapPerfCirRxPercentUtilizationRange6 OBJECT-TYPE
             SYNTAX      INTEGER 
             ACCESS      read-only
             STATUS      mandatory
             DESCRIPTION
                "The number of short-term intervals during
                 which rx data throughput on this DLCI compared
                 to CIR was in range 6 (81-100% of CIR)."
            ::= { mfrapPerfCirPercentUtilizationEntry 26 }

 mfrapPerfCirRxPercentUtilizationRange7 OBJECT-TYPE
             SYNTAX      INTEGER 
             ACCESS      read-only
             STATUS      mandatory
             DESCRIPTION
                "The number of short-term intervals during
                 which rx data throughput on this DLCI compared
                 to CIR was in range 7 (101-150% of CIR)."
            ::= { mfrapPerfCirPercentUtilizationEntry 27 }

 mfrapPerfCirRxPercentUtilizationRange8 OBJECT-TYPE
             SYNTAX      INTEGER 
             ACCESS      read-only
             STATUS      mandatory
             DESCRIPTION
                "The number of short-term intervals during
                 which rx data throughput on this DLCI compared
                 to CIR was in range 8 (> 150% of CIR)."
            ::= { mfrapPerfCirPercentUtilizationEntry 28 }

 mfrapPerfCirTxPercentUtilizationRange1 OBJECT-TYPE
             SYNTAX      INTEGER 
             ACCESS      read-only
             STATUS      mandatory
             DESCRIPTION
                "The number of short-term intervals during
                 which tx data throughput on this DLCI compared
                 to CIR was in range 1 (0% of CIR)."
            ::= { mfrapPerfCirPercentUtilizationEntry 41 }

 mfrapPerfCirTxPercentUtilizationRange2 OBJECT-TYPE
             SYNTAX      INTEGER 
             ACCESS      read-only
             STATUS      mandatory
             DESCRIPTION
                "The number of short-term intervals during
                 which tx data throughput on this DLCI compared
                 to CIR was in range 2 (1-10% of CIR)."
            ::= { mfrapPerfCirPercentUtilizationEntry 42 }

 mfrapPerfCirTxPercentUtilizationRange3 OBJECT-TYPE
             SYNTAX      INTEGER 
             ACCESS      read-only
             STATUS      mandatory
             DESCRIPTION
                "The number of short-term intervals during
                 which tx data throughput on this DLCI compared
                 to CIR was in range 3 (11-20% of CIR)."
            ::= { mfrapPerfCirPercentUtilizationEntry 43 }

 mfrapPerfCirTxPercentUtilizationRange4 OBJECT-TYPE
             SYNTAX      INTEGER 
             ACCESS      read-only
             STATUS      mandatory
             DESCRIPTION
                "The number of short-term intervals during
                 which tx data throughput on this DLCI compared
                 to CIR was in range 4 (21-50% of CIR)."
            ::= { mfrapPerfCirPercentUtilizationEntry 44 }

 mfrapPerfCirTxPercentUtilizationRange5 OBJECT-TYPE
             SYNTAX      INTEGER 
             ACCESS      read-only
             STATUS      mandatory
             DESCRIPTION
                "The number of short-term intervals during
                 which tx data throughput on this DLCI compared
                 to CIR was in range 5 (51-80% of CIR)."
            ::= { mfrapPerfCirPercentUtilizationEntry 45 }

 mfrapPerfCirTxPercentUtilizationRange6 OBJECT-TYPE
             SYNTAX      INTEGER 
             ACCESS      read-only
             STATUS      mandatory
             DESCRIPTION
                "The number of short-term intervals during
                 which tx data throughput on this DLCI compared
                 to CIR was in range 6 (81-100% o0f CIR)."
            ::= { mfrapPerfCirPercentUtilizationEntry 46 }

 mfrapPerfCirTxPercentUtilizationRange7 OBJECT-TYPE
             SYNTAX      INTEGER 
             ACCESS      read-only
             STATUS      mandatory
             DESCRIPTION
                "The number of short-term intervals during
                 which tx data throughput on this DLCI compared
                 to CIR was in range 7 (101-150% of CIR)."
            ::= { mfrapPerfCirPercentUtilizationEntry 47 }

 mfrapPerfCirTxPercentUtilizationRange8 OBJECT-TYPE
             SYNTAX      INTEGER 
             ACCESS      read-only
             STATUS      mandatory
             DESCRIPTION
                "The number of short-term intervals during
                 which tx data throughput on this DLCI compared
                 to CIR was in range 8 (> 150% of CIR)."
            ::= { mfrapPerfCirPercentUtilizationEntry 48 }


--
--  Current Utilization for each DLCI.
--

 mfrapPerfCurrentPerDlciUtilizationTable OBJECT-TYPE
         SYNTAX   SEQUENCE OF MfrapPerfCurrentPerDlciUtilizationEntry
         ACCESS   not-accessible
         STATUS   mandatory
         DESCRIPTION
            "The current measurement of utilization as a percentage
             of CIR on each DLCI.  Each short term statistics
             interval, the count of bytes transmitted and received
             is used to calculate the percentage of CIR used."
         ::= { mfrapPerfCirPercentUtilization 2 }

 mfrapPerfCurrentPerDlciUtilizationEntry OBJECT-TYPE
             SYNTAX MfrapPerfCurrentPerDlciUtilizationEntry
             ACCESS   not-accessible
             STATUS   mandatory
             DESCRIPTION
                "The utilization statistics for a particular DLCI."
             INDEX { mfrapPerfCurrentPerDlciUtilizationDlciValue }
             ::= { mfrapPerfCurrentPerDlciUtilizationTable 1 }

         MfrapPerfCurrentPerDlciUtilizationEntry ::=
             SEQUENCE {
                 mfrapPerfCurrentPerDlciUtilizationDlciValue  INTEGER,
                 mfrapPerfCurrentPerDlciRxUtilization         INTEGER,
                 mfrapPerfCurrentPerDlciTxUtilization         INTEGER,
                 mfrapPerfCurrentPerDlciAggregateUtilization  INTEGER
             }

 mfrapPerfCurrentPerDlciUtilizationDlciValue OBJECT-TYPE
             SYNTAX      INTEGER 
             ACCESS      read-only
             STATUS      mandatory
             DESCRIPTION
                "The DLCI value with which the Statistics are associated."
            ::= { mfrapPerfCurrentPerDlciUtilizationEntry 1 }

 mfrapPerfCurrentPerDlciRxUtilization OBJECT-TYPE
             SYNTAX      INTEGER 
             ACCESS      read-only
             STATUS      mandatory
             DESCRIPTION
                "The receive direction utilization as a
                 percentage of CIR."
            ::= { mfrapPerfCurrentPerDlciUtilizationEntry 2 }

 mfrapPerfCurrentPerDlciTxUtilization OBJECT-TYPE
             SYNTAX      INTEGER 
             ACCESS      read-only
             STATUS      mandatory
             DESCRIPTION
                "The transmit direction utilization as a
                 percentage of CIR."
            ::= { mfrapPerfCurrentPerDlciUtilizationEntry 3 }

 mfrapPerfCurrentPerDlciAggregateUtilization OBJECT-TYPE
             SYNTAX      INTEGER 
             ACCESS      read-only
             STATUS      mandatory
             DESCRIPTION
                "The aggregate utilization, the average
                 of the receive and transmit utilization
                 as a percentage of CIR."
            ::= { mfrapPerfCurrentPerDlciUtilizationEntry 4 }


--
--  Current Utilization for each interface and the unit as a whole.
--

mfrapPerfCurrentUnitUtilization OBJECT IDENTIFIER
            ::= { mfrapPerfCirPercentUtilization 3 }

 mfrapPerfCurrentDteUtilization OBJECT-TYPE
             SYNTAX      INTEGER 
             ACCESS      read-only
             STATUS      mandatory
             DESCRIPTION
                "The DTE interface utilization as a
                 percentage of line rate."
            ::= { mfrapPerfCurrentUnitUtilization 2 }

 mfrapPerfCurrentWanUtilization OBJECT-TYPE
             SYNTAX      INTEGER 
             ACCESS      read-only
             STATUS      mandatory
             DESCRIPTION
                "The WAN interface utilization as a
                 percentage of line rate."
            ::= { mfrapPerfCurrentUnitUtilization 3 }

 mfrapPerfCurrentAggregateUtilization OBJECT-TYPE
             SYNTAX      INTEGER 
             ACCESS      read-only
             STATUS      mandatory
             DESCRIPTION
                "The aggregate utilization of the unit,
                 the average of the DTE and WAN interface
                 utilizations as a percentage of line rate."
            ::= { mfrapPerfCurrentUnitUtilization 4 }


-- =============================
-- ==  MFRAP EVENT LOG group  ==
-- =============================
mfrapEventTrapLog      OBJECT IDENTIFIER ::= { mfrap 10 }

mfrapEventTrapLogTable              OBJECT-TYPE
        SYNTAX  SEQUENCE OF     MFRAPEventTrapLogEntry
        ACCESS  not-accessible
        STATUS  mandatory
        DESCRIPTION
            "This table contains the Event/Trap log.  The entries are
            indexed by sequence number."
        ::= { mfrapEventTrapLog 1}

    mfrapEventTrapLogEntry              OBJECT-TYPE
        SYNTAX  MFRAPEventTrapLogEntry
        ACCESS  not-accessible
        STATUS  mandatory
        DESCRIPTION
            "The event record for a particular event."
        INDEX {mfrapEventTrapLogSeqNum}
        ::= { mfrapEventTrapLogTable 1}

    MFRAPEventTrapLogEntry ::=
        SEQUENCE
        {
           mfrapEventTrapLogSeqNum        INTEGER,
           mfrapEventTrapLogGenericEvent  INTEGER,
           mfrapEventTrapLogSpecificEvent INTEGER,
           mfrapEventTrapLogTimeStamp     TimeTicks,
           mfrapEventTrapLogVarBind1      INTEGER,
           mfrapEventTrapLogVarBind2      INTEGER,
           mfrapEventTrapLogVarBind3      INTEGER
        }

    mfrapEventTrapLogSeqNum         OBJECT-TYPE
        SYNTAX  INTEGER
        ACCESS  read-only
        STATUS  mandatory
        DESCRIPTION
            "The sequence number associated with an event record."
        ::= {mfrapEventTrapLogEntry 1}

    mfrapEventTrapLogGenericEvent       OBJECT-TYPE
        SYNTAX  INTEGER
        ACCESS  read-only
        STATUS  mandatory
        DESCRIPTION
            "The SNMP generic trap or event number."
        ::= {mfrapEventTrapLogEntry 2}

    mfrapEventTrapLogSpecificEvent      OBJECT-TYPE
        SYNTAX  INTEGER
        ACCESS  read-only
        STATUS  mandatory
        DESCRIPTION
            "The SNMP specific trap or event sub-identifier number."
        ::= {mfrapEventTrapLogEntry 3}

    mfrapEventTrapLogTimeStamp      OBJECT-TYPE
        SYNTAX  TimeTicks
        ACCESS  read-only
        STATUS  mandatory
        DESCRIPTION
            "The SNMP trap timestamp."
        ::= {mfrapEventTrapLogEntry 4}

    mfrapEventTrapLogVarBind1           OBJECT-TYPE
        SYNTAX  INTEGER
        ACCESS  read-only
        STATUS  mandatory
        DESCRIPTION
            "Variable Binding 1 for this SNMP Trap event."
        ::= {mfrapEventTrapLogEntry 5}

    mfrapEventTrapLogVarBind2           OBJECT-TYPE
        SYNTAX  INTEGER
        ACCESS  read-only
        STATUS  mandatory
        DESCRIPTION
            "Variable Binding 2 for this SNMP Trap event."
        ::= {mfrapEventTrapLogEntry 6}

    mfrapEventTrapLogVarBind3           OBJECT-TYPE
        SYNTAX  INTEGER
        ACCESS  read-only
        STATUS  mandatory
        DESCRIPTION
            "Variable Binding 3 for this SNMP Trap event."
        ::= {mfrapEventTrapLogEntry 7}


    mfrapEventLogAltTable OBJECT-TYPE
         SYNTAX   SEQUENCE OF MFRAPEventLogAltEntry
         ACCESS   not-accessible
         STATUS   mandatory
         DESCRIPTION
            "This is an alternative method to access the database of the
             Event/Trap Log.  The database is indexed by Sequence Number
             and Event/Trap log's are returned  in an OCTETSTRING."
         ::= { mfrapEventTrapLog  2 }

        mfrapEventLogAltEntry   OBJECT-TYPE
            SYNTAX   MFRAPEventLogAltEntry
            ACCESS   not-accessible
            STATUS   mandatory
            DESCRIPTION
               "The Event/Trap Log for a particular sequence number."
           INDEX { mfrapEventLogAltSeqNum }
           ::= { mfrapEventLogAltTable 1 }

        MFRAPEventLogAltEntry ::=
            SEQUENCE {
                mfrapEventLogAltSeqNum               INTEGER,
                mfrapEventLogAltArray                OCTET STRING
                }

        mfrapEventLogAltSeqNum    OBJECT-TYPE
            SYNTAX      INTEGER
            ACCESS      read-only
            STATUS      mandatory
            DESCRIPTION
              "The Sequence Number monitored for the Event Log"
           ::= { mfrapEventLogAltEntry 1 }

        mfrapEventLogAltArray    OBJECT-TYPE
            SYNTAX      OCTET STRING
            ACCESS      read-only
            STATUS      mandatory
            DESCRIPTION
               "The Event / Trap log for the given sequence number."
           ::= { mfrapEventLogAltEntry 2 }

   mfrapEventLogCurrentSeqNum                 OBJECT-TYPE
        SYNTAX  INTEGER
        ACCESS  read-only
        STATUS  mandatory
        DESCRIPTION
            "The current index into the Event Log Table."
        ::= {mfrapEventTrapLog 3}


    mfrapEventLogFreeze                 OBJECT-TYPE
        SYNTAX  INTEGER
        {
            freeze      (1),
            un-freeze   (2)
        }
        ACCESS  write-only
        STATUS  mandatory
        DESCRIPTION
            "This freezes the Event/Trap Log. freeze(1) will 
             prevent Events / Traps from being entered into the database,
             un-freeze(2) will allow Events / Traps to be logged into the
             database. An event will be logged indicating a set of this
             entry"
        ::= { mfrapEventTrapLog 4}


    mfrapEventLogClear                  OBJECT-TYPE
        SYNTAX  INTEGER
        {
            clear   (1)
        }
        ACCESS  write-only
        STATUS  mandatory
        DESCRIPTION
            "This clears the Event/Trap Log."
        ::= { mfrapEventTrapLog 5}


-- =========================
-- ==        TRAPS        ==
-- =========================
--
--       The Alarm (Trap) table for the MFRAP.
--              This table contains definitions for enterprise specific traps
--              associated with the MFRAP T1 DSU.
mfrapAlarmType     OBJECT-TYPE
          SYNTAX      INTEGER
          {
               bad-config-in-set                       (1),
               config-local-update                     (2),
               t1-netw-carrier-loss                    (3),
               t1-netw-carrier-detect                  (4),
               t1-netw-sync-loss-declare               (5),
               t1-netw-sync-acquire                    (6),
               t1-netw-red-alarm-declare               (7),
               t1-netw-red-alarm-clear                 (8),
               t1-netw-yellow-alarm-detect             (9),
               t1-netw-yellow-alarm-clear              (10),
               t1-netw-ais-detect                      (11),
               t1-netw-ais-clear                       (12),
               t1-controlled-slip                      (13),
               local-unit-loopback-enabled             (14),
               local-unit-loopback-disabled            (15),
               local-unit-loopback-failure             (16),
               local-dte-loopback-enabled              (17),
               local-dte-loopback-disabled             (18),
               local-dte-loopback-failure              (19),
               local-aggregate-loopback-enabled        (20),
               local-aggregate-loopback-disabled       (21),
               local-aggregate-loopback-failure        (22),
               local-payload-loopback-enabled          (23),
               local-payload-loopback-disabled         (24),
               local-payload-loopback-failure          (25),
               local-network-loopback-enabled          (26),
               local-network-loopback-disabled         (27),
               local-network-loopback-failure          (28),
               v54-loop-up-initiated                   (29),
               v54-loop-down-completed                 (30),
               v54-loopback-enabled-by-remote          (31),
               v54-loopback-disabled-by-remote         (32),
               v54-loopback-failure                    (33),
               csu-loop-up-initiated                   (34),
               csu-loop-down-completed                 (35),
               csu-loopback-enabled-by-remote          (36),
               csu-loopback-disabled-by-remote         (37),
               csu-loopback-failure                    (38),
               dsu-loop-up-initiated                   (39),
               dsu-loop-down-completed                 (40),
               dsu-loopback-enabled-by-remote          (41),
               dsu-loopback-disabled-by-remote         (42),
               dsu-loopback-failure                    (43),
               bert-test-pattern-initiated             (44),
               bert-test-pattern-completed             (45),
               bert-test-pattern-failure               (46),
               dlci-active                             (47),
               dlci-inactive                           (48),
               dlci-td-threshold                       (49),
               lmi-sourcing-change-passthru            (50),
               lmi-sourcing-change-user-dte            (51),
               lmi-sourcing-change-net-dte             (52),
               lmi-sourcing-change-user-net            (53),
               lmi-sourcing-change-net-net             (54),
               dte-signal-rts-on                       (55),
               dte-signal-rts-off                      (56),
               dte-signal-dtr-on                       (57),
               dte-signal-dtr-off                      (58),
               lmi-non-incr-seq-num-dte                (59),
               lmi-non-incr-seq-num-net                (60),
               lmi-seq-num-mismatch-dte                (61),
               lmi-seq-num-mismatch-net                (62),
               trap-muting-active                      (75),
               trap-muting-inactive                    (76),
               vloop-loop-up                           (90),
               vloop-loop-down                         (91),   
               vloop-up-via-remote                     (92),
               vloop-down-via-remote                   (93),
               vloop-failed                            (94),
               vbert-started                           (95),
               vbert-stopped                           (96),
               vbert-request-failed                    (97),
               dandi-carrier-loss                      (110),
               dandi-carrier-detect                    (111),
               dandi-sync-loss-declare                 (112),
               dandi-sync-acquire                      (113),
               dandi-red-alarm-declare                 (114),
               dandi-red-alarm-clear                   (115),
               dandi-yellow-alarm-detect               (116),
               dandi-yellow-alarm-clear                (117),
               dandi-ais-detect                        (118),
               dandi-ais-clear                         (119),
               dandi-controlled-slip                   (120),
               local-dandi-payload-loopback-enabled    (121),
               local-dandi-payload-loopback-disabled   (122),
               local-dandi-payload-loopback-failure    (123),
               local-dandi-line-loopback-enabled       (124),
               local-dandi-line-loopback-disabled      (125),
               local-dandi-line-loopback-failure       (126),
               nest-fan-one-alarm                      (130),
               nest-fan-one-alarm-clear                (131),
               nest-fan-two-alarm                      (132),
               nest-fan-two-alarm-clear                (133),
               nest-power-supply-alarm                 (134),
               nest-power-supply-alarm-clear           (135),
               local-payload-loopback-via-rmt-enabled  (136),
               local-payload-loopback-via-rmt-disabled (137),
               pvc-rx-utilization-exceeded             (138),
               pvc-tx-utilization-exceeded             (139),
               pvc-rx-utilization-cleared              (140),
               pvc-tx-utilization-cleared              (141),
               config-install-success                  (142),
               tftp-requested                          (257),
               tftp-transferring                       (258),
               tftp-programming                        (259),
               tftp-aborted                            (260),
               tftp-success                            (261),
               tftp-host-unreachable                   (262),
               tftp-no-file                            (263),
               tftp-invalid-file                       (264),
               tftp-corrupt-file                       (265)
          }
          ACCESS      read-only
          STATUS      mandatory
          DESCRIPTION
             "The type of alarms that are generated on the node"
          ::= { mfrap 6 }

mfrapDLCINum     OBJECT-TYPE
          SYNTAX      INTEGER
          ACCESS      read-only
          STATUS      mandatory
          DESCRIPTION
             "The DLCI number for the DLCI active or inactive trap"
          ::= { mfrap 7 }


mfrapInterface     OBJECT-TYPE
          SYNTAX      INTEGER
          {
              dte (1),
              t1  (2)
          }
          ACCESS      read-only
          STATUS      mandatory
          DESCRIPTION
             "The interface most recently reported in a TRAP."
          ::= { mfrap 8 }

mfrapIpAddress     OBJECT-TYPE
          SYNTAX      IpAddress
          ACCESS      read-only
          STATUS      mandatory
          DESCRIPTION
             "The IP address most recently reported in a TRAP."
          ::= { mfrap 9 }

mfrapPercentUtilization   OBJECT-TYPE
          SYNTAX      INTEGER
          ACCESS      read-only
          STATUS      mandatory
          DESCRIPTION
            "The percent utilization for a DLCI most recently
           reported in a TRAP."
         ::= { mfrap 11 }

mfrapUtilizationThreshold   OBJECT-TYPE
          SYNTAX      INTEGER
          ACCESS      read-only
          STATUS      mandatory
          DESCRIPTION
            "The percent utilization threshold for a DLCI most 
             recently reported in a TRAP."
         ::= { mfrap 12 }

mfrapCfgLockIpAddress   OBJECT-TYPE
          SYNTAX      IpAddress
          ACCESS      read-only
          STATUS      mandatory
          DESCRIPTION
            "The IP address of the management station locking 
              the configuration most recently reported in a TRAP."
         ::= { mfrap 13 }
          

mfrapTrap          TRAP-TYPE
          ENTERPRISE  mfrap
          VARIABLES   
          { 
               mfrapAlarmType
          }
          DESCRIPTION
             "An mfrapTrap trap signifies that the
             sending node had its `mfrapAlarmType`
             variable modified."
          ::= 0

mfrapBadConfigTrap          TRAP-TYPE
          ENTERPRISE  mfrap
          VARIABLES   
          { 
               mfrapAlarmType
          }
          DESCRIPTION
             "Unit has received a configuration
              update request through SNMP but the
              request was rejected to due an incorrect
              or inappropriate parameter."
          ::= 1

mfrapLocalConfigTrap          TRAP-TYPE
          ENTERPRISE  mfrap
          VARIABLES   
          { 
               mfrapAlarmType
          }
          DESCRIPTION
             "Unit configuration has been updated locally
              (console port or front panel keypad) or
              remotely (telnet)."
          ::= 2

mfrapt1netwcarrierloss          TRAP-TYPE
          ENTERPRISE  mfrap
          VARIABLES   
          { 
             mfrapAlarmType
          }
          DESCRIPTION
             "Unit is not detecting a signal from the
              wide area network."
          ::= 3

mfrapt1netwcarrierdetect          TRAP-TYPE
          ENTERPRISE  mfrap
          VARIABLES   
          { 
             mfrapAlarmType
          }
          DESCRIPTION
             "Unit is detecting a signal from the wide
              area network."
          ::= 4

mfrapt1netwsynclossdeclare          TRAP-TYPE
          ENTERPRISE  mfrap
          VARIABLES   
          { 
             mfrapAlarmType
          }
          DESCRIPTION
             "Unit is not properly synchronized to the
              signal received from the wide area network. 
              Frame synchronization is required for normal 
              operation."
          ::= 5

mfrapt1netwsyncacquire          TRAP-TYPE
          ENTERPRISE  mfrap
          VARIABLES   
          { 
             mfrapAlarmType
          }
          DESCRIPTION
             "Unit is now synchronized with the signal
              received from the wide area network."
          ::= 6

mfrapt1netwredalarmdeclare          TRAP-TYPE
          ENTERPRISE  mfrap
          VARIABLES   
          { 
             mfrapAlarmType
          }
          DESCRIPTION
             "Unit has experienced loss of frame 
             synchronization for an extended time 
             and is reporting an alarm condition that 
             severely impairs normal operation. During 
             this Red Alarm condition the unit will 
             transmit Yellow alarm back to the network. 
             If this condition persists consult your 
             service provider."
          ::= 7

mfrapt1netwredalarmclear          TRAP-TYPE
          ENTERPRISE  mfrap
          VARIABLES   
          { 
             mfrapAlarmType
          }
          DESCRIPTION
             "Unit has achieved frame synchronization for 
              a length of time necessary to declare the 
              interface stable and operational."
          ::= 8

mfrapt1netwyellowalarmdetect          TRAP-TYPE
          ENTERPRISE  mfrap
          VARIABLES   
          { 
             mfrapAlarmType
          }
          DESCRIPTION
             "Unit is receiving a yellow alarm indication 
              from the wide area network. Detection of 
              yellow alarm implies that the attached device 
              is in a red alarm conditon. Red alarm is declared 
              due to the extended absence of a properly framed 
              signal. If this condition persists consult your 
              service provider."
          ::= 9

mfrapt1netwyellowalarmclear          TRAP-TYPE
          ENTERPRISE  mfrap
          VARIABLES   
          { 
             mfrapAlarmType
          }
          DESCRIPTION
             "Unit is no longer receiving a yellow alarm 
              indication from the wide area network. Yellow 
              alarm implies that the attached device is in a 
              red alarm conditon. Red alarm is declared due 
              to the extended absence of a properly framed signal."
          ::= 10

mfrapt1netwaisdetect          TRAP-TYPE
          ENTERPRISE  mfrap
          VARIABLES   
          { 
             mfrapAlarmType
          }
          DESCRIPTION
             "Unit is receiving unframed all ones from the 
              wide area network (AIS, blue alarm). Detection 
              of AIS implies that the attached device is reporting
              an alarm condition from an upstream device. If 
              this condition persists consult your service provider."
          ::= 11

mfrapt1netwaisclear          TRAP-TYPE
          ENTERPRISE  mfrap
          VARIABLES   
          { 
             mfrapAlarmType
          }
          DESCRIPTION
             "Unit is no longer receiving unframed all ones
              from the wide area network (AIS, blue alarm).
              Detection of AIS implies that the attached device 
              is reporting an alarm condition from an upstream 
              device."
          ::= 12

mfrapt1controlledslip          TRAP-TYPE
          ENTERPRISE  mfrap
          VARIABLES   
          { 
             mfrapAlarmType
          }
          DESCRIPTION
             "Unit is reporting an occurrence of a timing slip
              causing either the deletion or repetition of a 
              block of data. This is indicative of a timing 
              problem within the application. Check for multiple 
              clock sources or the absence of a stable clock source."
          ::= 13


mfrapLocalUnitLoopbackEnabledTrap          TRAP-TYPE
          ENTERPRISE  mfrap
          VARIABLES   
          { 
               mfrapAlarmType
          }
          DESCRIPTION
             "Unit is in a bidirectional unit loopback. Data
              is received from either interface, processed, 
              and transmitted back towards the same interface. 
              When configured for Frame Relay operation the unit 
              will preserve the LMI path during this loopback. 
              In Frame Relay mode, only valid frames are looped 
              back (pseudorandom test patterns will be dropped)."
          ::= 14

mfrapLocalUnitLoopbackDisabledTrap          TRAP-TYPE
          ENTERPRISE  mfrap
          VARIABLES   
          { 
               mfrapAlarmType
          }
          DESCRIPTION
             "Bidirectional unit loopback path is removed."
          ::= 15

mfrapLocalUnitLoopbackFailedTrap          TRAP-TYPE
          ENTERPRISE  mfrap
          VARIABLES   
          { 
               mfrapAlarmType
          }
          DESCRIPTION
             "Bidirectional unit loopback request has been
              rejected by the unit. Typically, this is due 
              to the presence of another loopback condition."
          ::= 16

mfrapLocalDteLoopbackEnabledTrap          TRAP-TYPE
          ENTERPRISE  mfrap
          VARIABLES   
          { 
               mfrapAlarmType
          }
          DESCRIPTION
             "Unit is in a bidirectional DTE loopback. All
              data received at the DTE interface is looped 
              back regardless of format or content (line 
              loopback). When configured for Frame Relay 
              operation the unit will not preserve the LMI 
              path during this loopback. Data received from 
              the WAN is processed and transmitted back out 
              the WAN. In Frame Relay mode, on the WAN 
              interface, only valid frames are looped back 
              (pseudorandom test patterns will be dropped)."
          ::= 17

mfrapLocalDteLoopbackDisabledTrap          TRAP-TYPE
          ENTERPRISE  mfrap
          VARIABLES   
          { 
               mfrapAlarmType
          }
          DESCRIPTION
             "Bidirectional DTE loopback path is removed."
          ::= 18

mfrapLocalDteLoopbackFailedTrap          TRAP-TYPE
          ENTERPRISE  mfrap
          VARIABLES   
          { 
               mfrapAlarmType
          }
          DESCRIPTION
             "Bidirectional DTE loopback request has been
              rejected by the unit. Typically, this is due 
              to the presence of another loopback condition."
          ::= 19

mfrapLocalAggregateLoopbackEnabledTrap          TRAP-TYPE
          ENTERPRISE  mfrap
          VARIABLES   
          { 
               mfrapAlarmType
          }
          DESCRIPTION
             "Unit is in local aggregate loopback. All data
              received from the DTE is transmit to the WAN and 
              also looped back towards the DTE at a point just 
              prior to WAN transmission (digital loopback). When 
              configured for Frame Relay operation the unit will 
              not preserve the LMI path during this loopback. In 
              Frame Relay mode only valid frames are looped back 
              (pseudorandom test patterns will be dropped)."
          ::= 20

mfrapLocalAggregateLoopbackDisabledTrap          TRAP-TYPE
          ENTERPRISE  mfrap
          VARIABLES   
          { 
               mfrapAlarmType
          }
          DESCRIPTION
            "Local aggregate loopback path is removed."
          ::= 21

mfrapLocalAggregateLoopbackFailedTrap          TRAP-TYPE
          ENTERPRISE  mfrap
          VARIABLES   
          { 
               mfrapAlarmType
          }
          DESCRIPTION
             "Local aggregate loopback request has been rejected
              by the unit. Typically, this is due to the presence 
              of another loopback condition."
          ::= 22

mfrapLocalPayloadLoopbackEnabledTrap          TRAP-TYPE
          ENTERPRISE  mfrap
          VARIABLES   
          { 
               mfrapAlarmType
          }
          DESCRIPTION
             "Unit is in payload loopback. All data received from
              the WAN, regardless of format or content, is processed 
              at the physical layer before being reframed and 
              transmit back out the WAN. All ones are sent to the 
              DTE during this diagnostic state. When configured for 
              Frame Relay operation the unit will not preserve the 
              LMI path during this loopback."
          ::= 23

mfrapLocalPayloadLoopbackDisabledTrap          TRAP-TYPE
          ENTERPRISE  mfrap
          VARIABLES   
          { 
               mfrapAlarmType
          }
          DESCRIPTION
             "Local payload loopback path is removed."
          ::= 24

mfrapLocalPayloadLoopbackFailedTrap          TRAP-TYPE
          ENTERPRISE  mfrap
          VARIABLES   
          { 
               mfrapAlarmType
          }
          DESCRIPTION
             "Local payload loopback request has been rejected.
              Typically, this is due to the presence of another 
              loopback condition."
          ::= 25

mfrapLocalNetLoopbackEnabledTrap          TRAP-TYPE
          ENTERPRISE  mfrap
          VARIABLES   
          { 
               mfrapAlarmType
          }
          DESCRIPTION
             "Unit is in local network loopback. All data
              received from the WAN, regardless of format or 
              content, is transmitted back out (line interface 
              loopback) while still being sent to the DTE. When 
              configured for Frame Relay operation the unit 
              will not preserve the LMI path during this loopback."
          ::= 26

mfrapLocalNetLoopbackDisabledTrap          TRAP-TYPE
          ENTERPRISE  mfrap
          VARIABLES   
          { 
               mfrapAlarmType
          }
          DESCRIPTION
             "Local network loopback path is removed."
          ::= 27

mfrapLocalNetLoopbackFailedTrap          TRAP-TYPE
          ENTERPRISE  mfrap
          VARIABLES   
          { 
               mfrapAlarmType
          }
          DESCRIPTION
             "Local network loopback request is rejected.
              Typically, this is due to the presence of another 
              loopback condition."
          ::= 28

mfrapV54LoopUpInitiatedTrap          TRAP-TYPE
          ENTERPRISE  mfrap
          VARIABLES   
          { 
               mfrapAlarmType
          }
          DESCRIPTION
             "Unit has sent the standard V54 loop up pattern
              out the WAN at the DTE rate. A compatible piece 
              of equipment can sense this pattern and enter a 
              loopback state - typically putting up a bidirectional 
              DTE loopback path. After sending the V54 loop up 
              pattern, the (local) unit returns to normal operation, 
              expecting a loopback condition at the remote device."
          ::= 29

mfrapV54LoopDownCompletedTrap          TRAP-TYPE
          ENTERPRISE  mfrap
          VARIABLES   
          { 
               mfrapAlarmType
          }
          DESCRIPTION
             "Unit has sent the standard V54 loop down pattern
              out the WAN at the DTE rate. A compatible piece of 
              equipment can sense this pattern remove the loopback 
              state that is entered after receiving a loop up pattern - 
              typically a bidirectional DTE loopback path. After 
              sending the V54 loop down pattern, the unit returns 
              to normal operation."
          ::= 30

mfrapV54LoopbackEnabledTrap          TRAP-TYPE
          ENTERPRISE  mfrap
          VARIABLES   
          { 
               mfrapAlarmType
          }
          DESCRIPTION
             "Unit has received a V54 loop up pattern from a
              compatible piece of equipment. A bidirectional DTE 
              loopback is activated. All data received at the 
              DTE interface is looped back regardless of format 
              or content. When configured for Frame Relay 
              operation the unit will not preserve the LMI path 
              during this loopback. Data received from the WAN is 
              processed and transmitted back out the WAN. In 
              Frame Relay mode, on the WAN interface, only valid 
              frames are looped back (pseudorandom test patterns 
              will be dropped)."
          ::= 31

mfrapV54LoopbackDisabledTrap          TRAP-TYPE
          ENTERPRISE  mfrap
          VARIABLES   
          { 
               mfrapAlarmType
          }
          DESCRIPTION
             "Unit has received a V54 loop down pattern from
              a compatible piece of equipment. The bidirectional 
              local DTE loopback is removed."
          ::= 32

mfrapV54LoopbackFailedTrap          TRAP-TYPE
          ENTERPRISE  mfrap
          VARIABLES   
          { 
              mfrapAlarmType
          }
          DESCRIPTION
             "Unit has rejected the request to send a V54 loop
              up. Typically, this is due to the presence of 
              another loopback condition."
          ::= 33

mfrapCsuLoopUpInitiatedTrap          TRAP-TYPE
          ENTERPRISE  mfrap
          VARIABLES   
          { 
               mfrapAlarmType
          }
          DESCRIPTION
             "Unit has sent a standard CSU loop up pattern at
              the full WAN rate. A compatible piece of equipment 
              can sense this pattern and enter a loopback state - 
              typically putting up a network line loopback. 
              After sending the CSU loop up pattern, the (local) 
              unit returns to normal operation, expecting a 
              loopback condition at the attached device."
          ::= 34

mfrapCsuLoopDownCompletedTrap          TRAP-TYPE
          ENTERPRISE  mfrap
          VARIABLES   
          { 
               mfrapAlarmType
          }
          DESCRIPTION
             "Unit has sent the standard CSU loop down pattern
              out the WAN at the full WAN rate. A compatible piece 
              of equipment can sense this pattern and remove the 
              loopback state that is entered after receiving a 
              loop up pattern - typically a network line loopback. 
              After sending the CSU loop down pattern, the unit 
              returns to normal operation."
          ::= 35

mfrapCsuLoopbackEnabledTrap          TRAP-TYPE
          ENTERPRISE  mfrap
          VARIABLES   
          { 
               mfrapAlarmType
          }
          DESCRIPTION
             "Unit has received a standard CSU loop up pattern
              and will enter a local network loopback state. All 
              data received from the WAN, regardless of format 
              or content, is transmitted back out (line interface 
              loopback) while still being sent to the DTE. When 
              configured for Frame Relay operation the unit will 
              not preserve the LMI path during this loopback."
          ::= 36

mfrapCsuLoopbackDisabledTrap          TRAP-TYPE
          ENTERPRISE  mfrap
          VARIABLES   
          { 
               mfrapAlarmType
          }
          DESCRIPTION
             "Unit has received a standard CSU loop down pattern
              and will remove the local network loopback path."
          ::= 37

mfrapCsuLoopbackFailedTrap          TRAP-TYPE
          ENTERPRISE  mfrap
          VARIABLES   
          { 
              mfrapAlarmType
          }
          DESCRIPTION
             "Unit has rejected the request to send a CSU loop up.
              Typically, this is due to the presence of another 
              loopback condition."
          ::= 38

mfrapDsuLoopUpInitiatedTrap          TRAP-TYPE
          ENTERPRISE  mfrap
          VARIABLES   
          { 
               mfrapAlarmType
          }
          DESCRIPTION
             "Unit has sent a proprietary DSU loop up pattern at
              the full WAN rate. A compatible piece of equipment 
              can sense this pattern and enter a network line 
              loopback state. After sending the DSU loop up 
              pattern, the (local) unit returns to normal 
              operation, expecting a loopback condition at the 
              remote device."
          ::= 39

mfrapDsuLoopDownCompletedTrap          TRAP-TYPE
          ENTERPRISE  mfrap
          VARIABLES   
          { 
               mfrapAlarmType
          }
          DESCRIPTION
             "Unit has sent the proprietary DSU loop down pattern
              out the WAN at the full WAN rate. A compatible 
              piece of equipment can sense this pattern and remove 
              a network line loopback condition. After sending the 
              DSU loop down pattern, the unit returns to normal 
              operation."
          ::= 40

mfrapDsuLoopbackEnabledTrap          TRAP-TYPE
          ENTERPRISE  mfrap
          VARIABLES   
          { 
               mfrapAlarmType
          }
          DESCRIPTION
             "Unit has received a proprietary DSU loop up pattern
              and will enter a local network loopback state. All 
              data received from the WAN, regardless of format or 
              content, is transmitted back out (line interface 
              loopback) while still being sent to the DTE. When 
              configured for Frame Relay operation the unit will 
              not preserve the LMI path during this loopback."
          ::= 41

mfrapDsuLoopbackDisabledTrap          TRAP-TYPE
          ENTERPRISE  mfrap
          VARIABLES   
          { 
               mfrapAlarmType
          }
          DESCRIPTION
             "Unit has received a proprietary DSU loop down
              pattern and will remove the local network 
              loopback path."
          ::= 42

mfrapDsuLoopbackFailedTrap          TRAP-TYPE
          ENTERPRISE  mfrap
          VARIABLES   
          { 
              mfrapAlarmType
          }
          DESCRIPTION
             "Unit has rejected the request to send a DSU loop up.
              Typically, this is due to the presence of another 
              loopback condition."
          ::= 43

mfrapBertInitiatedTrap          TRAP-TYPE
          ENTERPRISE  mfrap
          VARIABLES   
          { 
               mfrapAlarmType
          }
          DESCRIPTION
             "Unit is sending a pseudorandom test pattern
              (511 or QRSS) out the WAN and monitoring the 
              WAN received data for the same pattern. This 
              test may be ineffective in certain frame relay 
              applications as pseudorandom data lacks appropriate 
              framing."
          ::= 44

mfrapBertCompletedTrap          TRAP-TYPE
          ENTERPRISE  mfrap
          VARIABLES   
          { 
               mfrapAlarmType
          }
          DESCRIPTION
             "Unit has stopped sending a pseudorandom test
              pattern out the WAN."
          ::= 45


mfrapBertFailedTrap          TRAP-TYPE
          ENTERPRISE  mfrap
          VARIABLES   
          { 
               mfrapAlarmType
          }
          DESCRIPTION
             "Unit has rejected the request to enter a BERT
              test state. Typically, this is due to the presence 
              of another diagnostic condition."
          ::= 46

mfrapDLCIActiveTrap          TRAP-TYPE
          ENTERPRISE  mfrap
          VARIABLES   
          { 
               mfrapAlarmType,
               mfrapDLCINum
          }
          DESCRIPTION
             "Unit is reporting this DLCI as active and
              provisioned. An active DLCI is one that is 
              explictly declared ACTIVE in an LMI Full 
              Status Response (typically coming from a 
              frame relay switch)."
          ::= 47

mfrapDLCIInactiveTrap          TRAP-TYPE
          ENTERPRISE  mfrap
          VARIABLES   
          { 
               mfrapAlarmType,
               mfrapDLCINum
          }
          DESCRIPTION
             "Unit is reporting this DLCI as inactive. An
              inactive DLCI is determined inactive one of two 
              ways: it is either explictly declared inactive
              in an LMI Full Status Response (typically coming 
              from a frame relay switch) or a Full Status 
              Response is not seen causing a Full Status Timer 
              expiry. Having the unit's full status timer too 
              low could result in the unit falsely declaring DLCIs 
              inactive (then active again). This does not interfere 
              with any data activity on the DLCI but could result
              in excessive traps."
          ::= 48

mfrapDLCITDThresholdTrap          TRAP-TYPE
          ENTERPRISE  mfrap
          VARIABLES   
          { 
               mfrapAlarmType,
               mfrapDLCINum,
               mfrapIpAddress
          }
          DESCRIPTION
             "VNIP has measured a round-trip transit delay on this
              PVC to this peer which exceeds the user-defined threshold."
          ::= 49

mfrapLmiSourcingChangePassthruTrap          TRAP-TYPE
          ENTERPRISE  mfrap
          VARIABLES   
          { 
               mfrapAlarmType
          }
          DESCRIPTION
             "Unit is not sourcing any LMI messages. If this
              state persists then LMI is up and the proper 
              handshaking is occurring independent of the unit. 
              This may also be a transient state if the unit 
              is in an LMI hunt mode. If this trap occurs 
              repeatedly, separated by other LMI sourcing states, 
              the unit is not seeing any of the expected LMI 
              messages from either interface. Check LMI type, 
              connectivity, and configuration of associated equipment."
          ::= 50

mfrapLmiSourcingChangeUserDteTrap           TRAP-TYPE
          ENTERPRISE  mfrap
          VARIABLES   
          { 
               mfrapAlarmType
          }
          DESCRIPTION
             "Unit is acting as a source of LMI Status Requests
              (Link Integrity Verification, Keep Alive). If this 
              state persists then the equipment attached to the 
              DTE interface is configured as a Frame Relay DCE 
              but a companion Frame Relay DTE device is not seen 
              out the WAN. This could also be a transient state 
              if the unit is in an LMI hunt mode. If this trap 
              occurs repeatedly, separated by other LMI sourcing 
              states, the unit is not seeing any of the expected 
              LMI messages from either interface. Check LMI type, 
              connectivity, and configuration of associated equipment."
          ::= 51

mfrapLmiSourcingChangeNetDteTrap            TRAP-TYPE
          ENTERPRISE  mfrap
          VARIABLES   
          { 
               mfrapAlarmType
          }
          DESCRIPTION
             "Unit is acting as a source of LMI Status Responses
              (Link Intergrity Verification, Keep Alive). If this 
              state persists then the equpiment attached to the 
              DTE interface is configured as a Frame Relay DTE 
              but a companion Frame Relay DCE device is not seen 
              out the WAN. This could also be a transient state 
              if the unit is in an LMI hunt mode. If this trap 
              occurs repeatedly, separated by other LMI sourcing 
              states, the unit is not seeing any of the expected 
              LMI messages from either interface. Check LMI type, 
              connectivity, and configuration of external equipment."
          ::= 52

mfrapLmiSourcingChangeUserT1Trap           TRAP-TYPE
          ENTERPRISE  mfrap
          VARIABLES   
          { 
               mfrapAlarmType
          }
          DESCRIPTION
             "Unit is acting as a source of LMI Status Requests
              (Link Integrity Verification, Keep Alive). If this 
              state persists then the equipment attached to the 
              WAN interface is configured as a Frame Relay DCE 
              but a companion Frame Relay DTE device is not seen 
              out the DTE interface. This could also be a transient 
              state if the unit is in an LMI hunt mode. If this 
              trap occurs repeatedly, separated by other LMI 
              sourcing states, the unit is not seeing any of the 
              expected LMI messages from either interface. Check 
              LMI type, connectivity, and configuration of 
              associated equipment."
          ::= 53

mfrapLmiSourcingChangeNetT1Trap            TRAP-TYPE
          ENTERPRISE  mfrap
          VARIABLES   
          { 
               mfrapAlarmType
          }
          DESCRIPTION
             "Unit is acting as a source of LMI Status Responses
              (Link Integrity Verification, Keep Alive). If this 
              state persists then the equipment attached to the 
              WAN interface is configured as a Frame Relay DTE 
              but a companion Frame Relay DCE device is not seen 
              out the DTE interface. This could also be a transient 
              state if the unit is in an LMI hunt mode. If this 
              trap occurs repeatedly, separated by other LMI sourcing 
              states, the unit is not seeing any of the expected 
              LMI messages from either interface. Check LMI type, 
              connectivity, and configuration of associated equipment."
          ::= 54

mfrapDteSignalRtsOnTrap                     TRAP-TYPE
          ENTERPRISE  mfrap
          VARIABLES   
          { 
               mfrapAlarmType
          }
          DESCRIPTION
             "Unit's DTE Request to Send (RTS) interface control
              signal is now active (on). This signal is presented 
              by the external DTE device. Unit may be configured 
              to ignore the state of this signal or to require 
              it for data transmission."
          ::= 55

mfrapDteSignalRtsOffTrap                    TRAP-TYPE
          ENTERPRISE  mfrap
          VARIABLES   
          { 
               mfrapAlarmType
          }
          DESCRIPTION
             "Unit's DTE Request to Send (RTS) interface control 
              signal is now inactive (off). This signal is presented 
              by the external DTE device. Unit may be configured 
              to ignore the state of this signal or to require it 
              for data transmission."
          ::= 56

mfrapDteSignalDtrOnTrap                     TRAP-TYPE
          ENTERPRISE  mfrap
          VARIABLES   
          { 
               mfrapAlarmType
          }
          DESCRIPTION
             "Unit's DTE Data Terminal Ready (DTR) interface control
              signal is now active (on). This signal is presented by the 
              external DTE device. The unit may be configured to ignore 
              the state of this signal or to require it for data transmission."
          ::= 57

mfrapDteSignalDtrOffTrap                    TRAP-TYPE
          ENTERPRISE  mfrap
          VARIABLES   
          { 
               mfrapAlarmType
          }
          DESCRIPTION
             "Unit's DTE Data Terminal Ready (DTR) interface control
              signal is now inactive (off). This signal is presented by 
              the external DTE device. Unit may be configured to ignore 
              the state of this signal or to require it for data 
              transmission."
          ::= 58

mfrapNonIncrLmiSeqNumDteTrap           TRAP-TYPE
          ENTERPRISE  mfrap
          VARIABLES   
          { 
               mfrapAlarmType
          }
          DESCRIPTION
             "Unit has detected a non-incrementing LMI sequence number
              from the DTE. A Status Enquiry or Status Response message 
              has been seen at the DTE interface. The Link Integrity 
              information element's Send Sequence Number was not 
              incremented or was incremented more than once since the 
              last Send Sequence Number seen from the DTE interface."
          ::= 59

mfrapNonIncrLmiSeqNumT1Trap           TRAP-TYPE
          ENTERPRISE  mfrap
          VARIABLES   
          { 
               mfrapAlarmType
          }
          DESCRIPTION
             "Unit has detected a non-incrementing LMI sequence number
              from the WAN. A Status Enquiry or Status Response message 
              has been seen at the WAN interface. The Link Integrity 
              information element's Send Sequence Number was not 
              incremented or was incremented more than once since the 
              last Send Sequence Number seen from the WAN interface."
          ::= 60

mfrapLmiSeqNumMismatchDteTrap           TRAP-TYPE
          ENTERPRISE  mfrap
          VARIABLES   
          { 
               mfrapAlarmType
          }
          DESCRIPTION
             "Unit has detetcted an LMI sequence number mismatch from
              the DTE. A Status Enquiry or Status Response message has 
              been seen at the DTE interface. The Link Inetgrity information 
              element's Receive Sequence Number was not the most recent 
              Send Sequence number sent from the WAN interface. "
          ::= 61

mfrapLmiSeqNumMismatchT1Trap           TRAP-TYPE
          ENTERPRISE  mfrap
          VARIABLES   
          { 
               mfrapAlarmType
          }
          DESCRIPTION
             "Unit has detetcted an LMI sequence number mismatch from
              the WAN. A Status Enquiry or Status Response message has 
              been seen at the WAN interface. The Link Inetgrity information 
              element's Receive Sequence Number was not the most recent 
              Send Sequence number sent from the DTE interface."
          ::= 62

mfrapTrapMutingActive           TRAP-TYPE
          ENTERPRISE  mfrap
          VARIABLES   
          { 
               mfrapAlarmType
          }
          DESCRIPTION
             "Trap generation is muted."
          ::= 75

mfrapTrapMutingInactive           TRAP-TYPE
          ENTERPRISE  mfrap
          VARIABLES   
          { 
               mfrapAlarmType
          }
          DESCRIPTION
             "Trap generation is re-enabled (muting disabled)."
          ::= 76

mfrapVloopUp         TRAP-TYPE
          ENTERPRISE  mfrap
          VARIABLES
          { 
               mfrapAlarmType,
               mfrapDLCINum,
               mfrapInterface
          }
          DESCRIPTION
             "A Vnip PVC loopback (VLOOP) request has been sent to
              a remote device on this DLCI out this interface. The
              remote unit should respond by looping all data received
              on this PVC back towards the unit that initiated this
              request. A PVC running VLOOP will not be running any
              user data."
          ::= 90

mfrapVloopDown         TRAP-TYPE
          ENTERPRISE  mfrap
          VARIABLES   
          { 
               mfrapAlarmType,
               mfrapDLCINum,
               mfrapInterface
          }
          DESCRIPTION
             "A Vnip PVC loopback (VLOOP) disable request has been
              sent to a remote device on this DLCI out this interface.
              The remote unit should respond by tearing down the
              logical loop on this DLCI."
          ::= 91 

mfrapVloopUpViaRemote     TRAP-TYPE
          ENTERPRISE  mfrap
          VARIABLES   
          { 
               mfrapAlarmType,
               mfrapDLCINum,
               mfrapInterface
          }
          DESCRIPTION
             "A Vnip PVC loopback (VLOOP) request has been received
              from a remote device on this DLCI on this interface.
              The unit will respond by looping all data received on
              this PVC back out the interface towards the unit that
              initiated the request." 
          ::= 92   

mfrapVloopDownViaRemote     TRAP-TYPE
          ENTERPRISE  mfrap
          VARIABLES   
          { 
               mfrapAlarmType,
               mfrapDLCINum,
               mfrapInterface
          }
          DESCRIPTION
           "A request to disable a Vnip PVC loopback (VLOOP) on
           this unit with the indicated DLCI and Interface has
           been received.  Usually this disable request is from
           the remote device that requested the VLOOP, however
           the request may also be due to a local event such as
           expiration of a locally configured loopback timeout.
           The unit will respond by tearing down the logical loop
           on this DLCI."
          ::= 93  

mfrapVloopRequestFailed       TRAP-TYPE
          ENTERPRISE  mfrap
          VARIABLES   
          { 
               mfrapAlarmType,
               mfrapDLCINum,
               mfrapInterface
          }
          DESCRIPTION
             "The request for a PVC loopback (VLOOP) has been rejected
              or did not complete."
          ::= 94

mfrapVbertStarted              TRAP-TYPE
          ENTERPRISE  mfrap
          VARIABLES   
          { 
               mfrapAlarmType,
               mfrapDLCINum,
               mfrapInterface
          }
          DESCRIPTION
             "A Vnip PVC error rate test (VBERT) has been started on
              this DLCI out this interface to a remote device. The
              VBERT test data will be statistically multiplexed in
              with user data, management data, and networking data.
              The destination peer will echo this test data back to
              the source producing a full-duplex volume-based timed
              test."
          ::= 95


mfrapVbertStopped              TRAP-TYPE
          ENTERPRISE  mfrap
          VARIABLES   
          { 
               mfrapAlarmType,
               mfrapDLCINum,
               mfrapInterface
          }   
          DESCRIPTION
             "A Vnip PVC BERT (VBERT) has been stopped on this DLCI 
              on this interface to a remote device."
          ::= 96

mfrapVbertRequestFailed       TRAP-TYPE
          ENTERPRISE  mfrap
          VARIABLES   
          { 
               mfrapAlarmType,
               mfrapDLCINum,
               mfrapInterface
          }   
          DESCRIPTION
             "The request for a PVC BERT (VBERT) on this DLCI 
              on this interface has been rejected."
          ::= 97

mfrapDandiCarrierLoss          TRAP-TYPE
          ENTERPRISE  mfrap
          VARIABLES   
          { 
             mfrapAlarmType
          }
          DESCRIPTION
             "Unit is not detecting a signal from the
              Drop & Insert port."
          ::= 110

mfrapDandiCarrierDetect          TRAP-TYPE
          ENTERPRISE  mfrap
          VARIABLES   
          { 
             mfrapAlarmType
          }
          DESCRIPTION
             "Unit is not detecting a signal from the
              Drop & Insert port."
          ::= 111

mfrapDandiSyncLossDeclare          TRAP-TYPE
          ENTERPRISE  mfrap
          VARIABLES   
          { 
             mfrapAlarmType
          }
          DESCRIPTION
             "Unit is not properly synchronized to the
              signal received from the Drop & Insert port. 
              Frame synchronization is required for normal 
              operation."
          ::= 112

mfrapDandiSyncAcquire          TRAP-TYPE
          ENTERPRISE  mfrap
          VARIABLES   
          { 
             mfrapAlarmType
          }
          DESCRIPTION
             "Unit is now synchronized with the signal
              received from the Drop & Insert port."
          ::= 113

mfrapDandiRedAlarmDeclare          TRAP-TYPE
          ENTERPRISE  mfrap
          VARIABLES   
          { 
             mfrapAlarmType
          }
          DESCRIPTION
             "Unit has experienced loss of frame 
             synchronization for an extended time 
             and is reporting an alarm condition that 
             severely impairs normal operation. During 
             this Red Alarm condition the unit will 
             transmit Yellow alarm back to the network. 
             If this condition persists consult your 
             service provider."
          ::= 114

mfrapDandiRedalArmclear          TRAP-TYPE
          ENTERPRISE  mfrap
          VARIABLES   
          { 
             mfrapAlarmType
          }
          DESCRIPTION
             "Unit has achieved frame synchronization for 
              a length of time necessary to declare the 
              interface stable and operational."
          ::= 115

mfrapDandiYellowAlarmDetect          TRAP-TYPE
          ENTERPRISE  mfrap
          VARIABLES   
          { 
             mfrapAlarmType
          }
          DESCRIPTION
             "Unit is receiving a yellow alarm indication 
              from the Drop & Insert port. Detection of 
              yellow alarm implies that the attached device 
              is in a red alarm conditon. Red alarm is declared 
              due to the extended absence of a properly framed 
              signal. If this condition persists consult your 
              service provider."
          ::= 116

mfrapDandiYellowAlarmClear          TRAP-TYPE
          ENTERPRISE  mfrap
          VARIABLES   
          { 
             mfrapAlarmType
          }
          DESCRIPTION
             "Unit is no longer receiving a yellow alarm 
              indication from the Drop & Insert port. Yellow 
              alarm implies that the attached device is in a 
              red alarm conditon. Red alarm is declared due 
              to the extended absence of a properly framed signal."
          ::= 117

mfrapDandIaisDetect          TRAP-TYPE
          ENTERPRISE  mfrap
          VARIABLES   
          { 
             mfrapAlarmType
          }
          DESCRIPTION
             "Unit is receiving unframed all ones from the 
              Drop & Insert port (AIS, blue alarm). Detection 
              of AIS implies that the attached device is reporting
              an alarm condition from an upstream device. If 
              this condition persists consult your service provider."
          ::= 118

mfrapDandiAisClear          TRAP-TYPE
          ENTERPRISE  mfrap
          VARIABLES   
          { 
             mfrapAlarmType
          }
          DESCRIPTION
             "Unit is no longer receiving unframed all ones
              from the Drop & Insert port (AIS, blue alarm).
              Detection of AIS implies that the attached device 
              is reporting an alarm condition from an upstream 
              device."
          ::= 119

mfrapDandiControlledSlip          TRAP-TYPE
          ENTERPRISE  mfrap
          VARIABLES   
          { 
             mfrapAlarmType
          }
          DESCRIPTION
             "Unit is reporting an occurrence of a timing slip
              causing either the deletion or repetition of a 
              block of data. This is indicative of a timing 
              problem within the application. Check for multiple 
              clock sources or the absence of a stable clock source."
          ::= 120

mfrapLocalDandiPayloadLoopbackEnabledTrap   TRAP-TYPE
          ENTERPRISE  mfrap
          VARIABLES   
          { 
             mfrapAlarmType
          }
          DESCRIPTION
             "Unit is in local Drop & Insert payload loopback. All 
              Drop & Insert data received from the WAN, regardless 
              of format or content, is processed at the Drop & Insert 
              line interface before being reframed and transmited 
              back out the WAN. DTE data are unaffected."
          ::= 121

mfrapLocalDandiPayloadLoopbackDisabledTrap   TRAP-TYPE
          ENTERPRISE  mfrap
          VARIABLES   
          { 
             mfrapAlarmType
          }
          DESCRIPTION
             "Local Drop & Insert payload loopback path is removed."
          ::= 122

mfrapLocalDandiPayloadLoopbackFailureTrap   TRAP-TYPE
          ENTERPRISE  mfrap
          VARIABLES   
          { 
             mfrapAlarmType
          }
          DESCRIPTION
             "Local Drop & Insert payload loopback request has 
              been rejected. Typically, this is due to the 
              presence of another loopback condition."
          ::= 123

mfrapLocalDandiLineLoopbackEnabledTrap   TRAP-TYPE
          ENTERPRISE  mfrap
          VARIABLES   
          { 
             mfrapAlarmType
          }
          DESCRIPTION
             "Unit is in local Drop & Insert line loopback. All 
              data received from the Drop & Insert port, regardless 
              of format or content, is transmitted back out (line 
              interface loopback) while still being sent to the WAN. 
              DTE data are unaffected."
          ::= 124

mfrapLocalDandiLineLoopbackDisabledTrap   TRAP-TYPE
          ENTERPRISE  mfrap
          VARIABLES   
          { 
             mfrapAlarmType
          }
          DESCRIPTION
             "Local Drop & Insert line loopback path is removed."
          ::= 125

mfrapLocalDandiLineLoopbackFailureTrap   TRAP-TYPE
          ENTERPRISE  mfrap
          VARIABLES   
          { 
             mfrapAlarmType
          }
          DESCRIPTION
             "Local Drop & Insert line loopback request is rejected.
              Typically, this is due to the presence of another 
              loopback condition."
          ::= 126

mfrapNestFanOneAlarm       TRAP-TYPE
          ENTERPRISE  mfrap
          VARIABLES   
          { 
             mfrapAlarmType
          }
          DESCRIPTION
             "Unit has received an alarm signal from
              the nest that Fan 1 has malfunctioned."
          ::= 130

mfrapNestFanOneAlarmClear  TRAP-TYPE
          ENTERPRISE  mfrap
          VARIABLES   
          { 
             mfrapAlarmType
          }
          DESCRIPTION
             "The Fan 1 alarm signal from the nest
              has been cleared."
          ::= 131

mfrapNestFanTwoAlarm       TRAP-TYPE
          ENTERPRISE  mfrap
          VARIABLES   
          { 
             mfrapAlarmType
          }
          DESCRIPTION
             "Unit has received an alarm signal from
              the nest that Fan 2 has malfunctioned."
          ::= 132

mfrapNestFanTwoAlarmClear  TRAP-TYPE
          ENTERPRISE  mfrap
          VARIABLES   
          { 
             mfrapAlarmType
          }
          DESCRIPTION
             "The Fan 2 alarm signal from the nest
              has been cleared."
          ::= 133

mfrapNestPowerSupplyAlarm       TRAP-TYPE
          ENTERPRISE  mfrap
          VARIABLES   
          { 
             mfrapAlarmType
          }
          DESCRIPTION
             "Unit has received an alarm signal from
              the nest that the power supply has 
              malfunctioned."
          ::= 134

mfrapNestPowerSupplyAlarmClear  TRAP-TYPE
          ENTERPRISE  mfrap
          VARIABLES   
          { 
             mfrapAlarmType
          }
          DESCRIPTION
             "The power supply alarm signal from the nest
              has been cleared."
          ::= 135

mfrapLocalPayloadLoopbackEnabledViaRemoteTrap     TRAP-TYPE
          ENTERPRISE  mfrap
          VARIABLES   
          { 
               mfrapAlarmType
          }
          DESCRIPTION
             "Local Payload loopback enabled Via Remote unit."
          ::= 136

mfrapLocalPayloadLoopbackDisabledViaRemoteTrap          TRAP-TYPE
          ENTERPRISE  mfrap
          VARIABLES   
          { 
               mfrapAlarmType
          }
          DESCRIPTION
             "Local Payload loopback disabled Via Remote unit."
          ::= 137

mfrapPvcRxUtilizationExceededTrap   TRAP-TYPE
          ENTERPRISE  mfrap
          VARIABLES   
          { 
               mfrapAlarmType,
               mfrapDLCINum,
               mfrapPercentUtilization,
               mfrapUtilizationThreshold
        }
        DESCRIPTION
           "Percent utilization threshold was exceeded for the
           defined number of Short Term Intervals in the
           reception direction on this DLCI. "
        ::= 138

mfrapPvcTxUtilizationExceededTrap   TRAP-TYPE
          ENTERPRISE  mfrap
          VARIABLES   
          { 
               mfrapAlarmType,
               mfrapDLCINum,
               mfrapPercentUtilization,
               mfrapUtilizationThreshold
        }
        DESCRIPTION
           "Percent utilization threshold was exceeded for the
           defined number of Short Term Intervals in the
           transmission direction on this DLCI. "
        ::= 139

mfrapPvcRxUtilizationClearedTrap   TRAP-TYPE
          ENTERPRISE  mfrap
          VARIABLES   
          { 
               mfrapAlarmType,
               mfrapDLCINum,
               mfrapPercentUtilization,
               mfrapUtilizationThreshold
        }
        DESCRIPTION
           "Percent utilization was below the threshold for the
           defined number of Short Term Intervals in the
           reception direction on this DLCI. "
        ::= 140

mfrapPvcTxUtilizationClearedTrap   TRAP-TYPE
          ENTERPRISE  mfrap
          VARIABLES   
          { 
               mfrapAlarmType,
               mfrapDLCINum,
               mfrapPercentUtilization,
               mfrapUtilizationThreshold
        }
        DESCRIPTION
           "Percent utilization was below the threshold for the
           defined number of Short Term Intervals in the
           transmission direction on this DLCI. "
        ::= 141

          
mfrapConfigInstallSuccess     TRAP-TYPE
          ENTERPRISE  mfrap
          VARIABLES   
          { 
               mfrapAlarmType,
               mfrapCfgLockIpAddress
        }
        DESCRIPTION
             " The configuration install process has successfully 
               completed. "
          ::= 142
          
mfrapTftpRequestedTrap            TRAP-TYPE
          ENTERPRISE  mfrap
          VARIABLES   
          { 
               mfrapAlarmType
          }
          DESCRIPTION
             "Unit has received a TFTP download request. TFTP is
              the preferred method for upgrading a unit's software 
              image."
          ::= 257

mfrapTftpTransferringTrap            TRAP-TYPE
          ENTERPRISE  mfrap
          VARIABLES   
          { 
               mfrapAlarmType
          }
          DESCRIPTION
             "Unit has established a TFTP session, found the file,
              and begun the transfer. The file must still be qualified 
              as appropriate for this unit."
          ::= 258

mfrapTftpProgrammingTrap            TRAP-TYPE
          ENTERPRISE  mfrap
          VARIABLES   
          { 
               mfrapAlarmType
          }
          DESCRIPTION
             "Unit has completed the TFTP transfer of a new software
              image which will next be programmed into non-volatile 
              flash memory."
          ::= 259

mfrapTftpAbortedTrap            TRAP-TYPE
          ENTERPRISE  mfrap
          VARIABLES   
          { 
               mfrapAlarmType
          }
          DESCRIPTION
             "Unit's TFTP session was established but the transfer was
              aborted by user intervention or an unrecoverable TFTP 
              protocol error."
          ::= 260

mfrapTftpSuccessTrap            TRAP-TYPE
          ENTERPRISE  mfrap
          VARIABLES   
          { 
               mfrapAlarmType
          }
          DESCRIPTION
             "Unit's TFTP download completed successfully. Flash
              devices will be programmed with a new image. Unit will stop
              passing data during the programming phase (less than a minute)
              and, upon completion, will reset and return to full operation
              using the new image."
          ::= 261

mfrapTftpHostUnreachableTrap    TRAP-TYPE
          ENTERPRISE  mfrap
          VARIABLES   
          { 
               mfrapAlarmType
          }
          DESCRIPTION
             "Unit could not establish a TFTP session with the
              designated server. Verify that the correct TFTP 
              ip address, TFTP DLCI and TFTP interface are 
              configured on the unit and also verify the TFTP 
              server confguration."
          ::= 262

mfrapTftpNoFileTrap             TRAP-TYPE
          ENTERPRISE  mfrap
          VARIABLES   
          { 
               mfrapAlarmType
          }
          DESCRIPTION
             "Unit could not locate the designated file on the TFTP
              server. Verify the correct TFTP filename is configured 
              on the unit and verify the location of this file on 
              the server (file name may be case sensitive)."
          ::= 263

mfrapTftpInvalidFileTrap        TRAP-TYPE
          ENTERPRISE  mfrap
          VARIABLES   
          { 
               mfrapAlarmType
          }
          DESCRIPTION
             "Unit had established a TFTP session and began transfer
              of the designated file. The unit aborted the transfer 
              after determining that the specified file is not 
              appropriate for this product (failed header verification)."
          ::= 264

mfrapTftpCorruptFileTrap        TRAP-TYPE
          ENTERPRISE  mfrap
          VARIABLES   
          { 
               mfrapAlarmType
          }
          DESCRIPTION
             "Unit transferred the designated file but aborted the
              operation due to a checksum error within the downloaded
              s-record file."
          ::= 265

END
