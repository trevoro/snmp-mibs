P8511-MIB DEFINITIONS ::= BEGIN


IMPORTS
	enterprises
		FROM RFC1155-SMI
	OBJECT-TYPE
		FROM RFC-1212;
  
  DisplayString ::= OCTET STRING


comet         OBJECT IDENTIFIER ::= { enterprises 22626 }
products      OBJECT IDENTIFIER ::= { comet 1 }
p8511         OBJECT IDENTIFIER ::= { products 5 }
settings      OBJECT IDENTIFIER ::= { p8511 1 }
channels      OBJECT IDENTIFIER ::= { p8511 2 }
channel1      OBJECT IDENTIFIER ::= { channels 1 }
traps         OBJECT IDENTIFIER ::= { p8511 3 }
tables	      OBJECT IDENTIFIER ::= { p8511 4 }

-- Power Source MIB
-- Parameters (Prefix ps)

-----------------------------------------------------------------------
-- settings
-----------------------------------------------------------------------
sensorName OBJECT-TYPE
	SYNTAX		DisplayString (SIZE (0..16))
	ACCESS		read-only
	STATUS		mandatory
	DESCRIPTION	"Sensor name."
::= { settings 1 }

-----------------------------------------------------------------------
-- channels
-----------------------------------------------------------------------

-----------------------------------------------------------------------
-- channel1
-----------------------------------------------------------------------
ch1Name OBJECT-TYPE
	SYNTAX		DisplayString (SIZE (0..16))
	ACCESS		read-only
	STATUS		mandatory
	DESCRIPTION	"Channel 1 name."
::= { channel1 1 }

ch1Val OBJECT-TYPE
	SYNTAX		DisplayString (SIZE (0..8))
	ACCESS		read-only
	STATUS		mandatory
	DESCRIPTION	"Channel 1 temperature."
::= { channel1 2 }

ch1IntVal OBJECT-TYPE
	SYNTAX		INTEGER (-550..1250)
	ACCESS		read-only
	STATUS		mandatory
	DESCRIPTION	"Channel 1 temperature * 10 (12,5 dgr C = 125)."
::= { channel1 3 }

ch1Alarm OBJECT-TYPE
	SYNTAX		INTEGER (0..1)
	ACCESS		read-only
	STATUS		mandatory
	DESCRIPTION	"Alarm on channel 1; 0 - No alarm, 1 - Alarm Hi, 2- Alarm Lo."
::= { channel1 4 }

ch1LimHi OBJECT-TYPE
	SYNTAX		DisplayString (SIZE (0..8))
	ACCESS		read-only
	STATUS		mandatory
	DESCRIPTION	"Channel 1 temperature upper alarm limit."
::= { channel1 5 }

ch1LimLo OBJECT-TYPE
	SYNTAX		DisplayString (SIZE (0..8))
	ACCESS		read-only
	STATUS		mandatory
	DESCRIPTION	"Channel 1 temperature low alarm limit."
::= { channel1 6 }

ch1LimHyst OBJECT-TYPE
	SYNTAX		DisplayString (SIZE (0..8))
	ACCESS		read-only
	STATUS		mandatory
	DESCRIPTION	"Channel 1 temperature hysteressis."
::= { channel1 7 }

ch1Delay OBJECT-TYPE
	SYNTAX		INTEGER (0..65534)
	ACCESS		read-only
	STATUS		mandatory
	DESCRIPTION	"Channel 1 temperature alarm delay [s]."
::= { channel1 8 }

-----------------------------------------------------------------------
-- traps
-----------------------------------------------------------------------

messageString OBJECT-TYPE
	SYNTAX		DisplayString (SIZE (0..30))
	ACCESS		read-only
	STATUS		mandatory
	DESCRIPTION	"Message giving more detailed information on alarms."
::= { traps 1 }

-----------------------------------------------------------------------
-- tables
-----------------------------------------------------------------------
historyTable OBJECT-TYPE
	SYNTAX  SEQUENCE OF HistoryEntry
	ACCESS  not-accessible
	STATUS  mandatory
	DESCRIPTION	"Table of the history values."
::= { tables 1 }

historyEntry OBJECT-TYPE
	SYNTAX  HistoryEntry
	ACCESS  not-accessible
	STATUS  optional
	DESCRIPTION	"History values entries."
	INDEX   { ch1temperature }
::= { historyTable 1 }

HistoryEntry ::=
	SEQUENCE {
		ch1temperature
			INTEGER
		}

ch1temperature OBJECT-TYPE
	SYNTAX  INTEGER (1..65535)
	ACCESS  read-only
	STATUS  mandatory
	DESCRIPTION	"Temperature reading."
::= { historyEntry 1 }

END
