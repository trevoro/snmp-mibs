CNTSVCEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, RowStatus
			FROM SNMPv2-TC
		cntsvcExt
			FROM APENT-MIB;

--CNTSVCEXT MIB

    apCntsvcExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  content rule table"
      ::= { cntsvcExt 1}


apCntsvcTable OBJECT-TYPE
	SYNTAX          SEQUENCE OF APCntsvcEntry
	MAX-ACCESS      not-accessible
	STATUS          current
	DESCRIPTION
		"A list of content rule entries."
	::= { cntsvcExt 2 }

apCntsvcEntry OBJECT-TYPE
	SYNTAX          APCntsvcEntry
	MAX-ACCESS      not-accessible
	STATUS          current
	DESCRIPTION
		"A group of information to uniquely identify a content providing 
		service."
	INDEX   { apCntsvcOwnName, apCntsvcCntName, apCntsvcSvcName }
	--DEFAULT apjam-group apCntSvcInst, apCntsvcSvcName
	--DEFAULT apjam-popup-def apCntSvcInst, Properties, local
	--DEFAULT apjam-popup-def apCntSvcInst, Statistics, local
	--DEFAULT apjam-popup-def apCntSvcInst, Delete, special, apCntsvcStatus
	--DEFAULT apjam-wizard apCntSvcInst, 1, images/arrowlogo.gif, "This wizard will let you add a service to a given content rule."
	::= { apCntsvcTable 1 }

APCntsvcEntry ::= SEQUENCE {
		apCntsvcOwnName              DisplayString,
		apCntsvcCntName              DisplayString,
		apCntsvcSvcName              DisplayString,
		apCntsvcHits                 Integer32,
		apCntsvcBytes                Integer32,
		apCntsvcFrames               Integer32,
		apCntsvcBucket				 Integer32,
		apCntsvcStatus               RowStatus,
		apCntsvcWeight				 Integer32,
		apCntsvcDnsHits              Integer32,
		apCntsvcDnsProximityHits     Integer32,
		apCntsvcState                INTEGER
}

apCntsvcOwnName OBJECT-TYPE
	SYNTAX          DisplayString (SIZE(1..31))
	MAX-ACCESS      read-create
	STATUS          current
	DESCRIPTION     
			"The name of the Owner."
	--DEFAULT ap-display-name Owner
	--DEFAULT apjam-popup-ref apCntSvcInst, Properties
	--DEFAULT ap-create-requires Yes
	--DEFAULT apjam-noedit-dlg	True
	--DEFAULT apjam-wizard-field 1, choice, apOwnName( ), nodepend
	::= {apCntsvcEntry 1}

apCntsvcCntName OBJECT-TYPE
	SYNTAX          DisplayString (SIZE(1..31))
	MAX-ACCESS      read-create
	STATUS          current
	DESCRIPTION     
			"The name of the content rule."
	--DEFAULT ap-display-name Content Rule
	--DEFAULT apjam-popup-ref apCntSvcInst, Properties
	--DEFAULT ap-create-requires Yes
	--DEFAULT apjam-noedit-dlg	True
	--DEFAULT apjam-wizard-field 1, choice, apCntName( apCntsvcOwnName ), depend, apCntsvcOwnName
	::= {apCntsvcEntry 2}

apCntsvcSvcName OBJECT-TYPE
	SYNTAX          DisplayString (SIZE(1..31))
	MAX-ACCESS      read-create
	STATUS          current
	DESCRIPTION     
			"The name of the service."
	--DEFAULT ap-display-name Service
	--DEFAULT apjam-popup-ref apCntSvcInst, Properties
	--DEFAULT ap-create-requires Yes
	--DEFAULT apjam-noedit-dlg	True
	--DEFAULT apjam-wizard-field 1, choice, apSvcName( ), nodepend
	::= {apCntsvcEntry 3}

apCntsvcHits OBJECT-TYPE
	SYNTAX          Integer32
	MAX-ACCESS      read-only
	STATUS  		current
	DESCRIPTION     
		"Total number of flows placed onto this service for this content rule."
	DEFVAL { 0 }
	--DEFAULT ap-display-name Hits
	--DEFAULT apjam-popup-ref apCntSvcInst, Statistics
	--DEFAULT apjam-chart-def cntSvcHitsChart, pie, apCntInst, "Hit Information Per Service"
	--DEFAULT apjam-chart-item cntSvcHitsChart, getnext, apCntsvcSvcName
	::= {apCntsvcEntry 4}

apCntsvcBytes OBJECT-TYPE
	SYNTAX          Integer32
	MAX-ACCESS      read-only
	STATUS  		current
	DESCRIPTION     
		"Total number of flows moved by this service for this content rule."
	DEFVAL { 0 }
	--DEFAULT ap-display-name Bytes
	--DEFAULT apjam-popup-ref apCntSvcInst, Statistics
	::= {apCntsvcEntry 5}

apCntsvcFrames OBJECT-TYPE
	SYNTAX          Integer32
	MAX-ACCESS      read-only
	STATUS  		current
	DESCRIPTION     
		"Total number of frames moved by this service for this content rule."
	DEFVAL { 0 }
	--DEFAULT ap-display-name Frames
	--DEFAULT apjam-popup-ref apCntSvcInst, Statistics
	::= {apCntsvcEntry 6}

apCntsvcBucket OBJECT-TYPE
	SYNTAX          Integer32 (1..12)
	MAX-ACCESS      read-create
	STATUS  		current
	DESCRIPTION     
		"The service bucket used for cache divisions."
	DEFVAL { 1 }
	--DEFAULT ap-display-name Frames
	--DEFAULT apjam-popup-ref apCntSvcInst, Statistics
	::= {apCntsvcEntry 7}

apCntsvcStatus OBJECT-TYPE
	SYNTAX          RowStatus
	MAX-ACCESS      read-create
	STATUS          current
	DESCRIPTION      
		"Status entry for this row "
	::= {apCntsvcEntry 8}

apCntsvcWeight OBJECT-TYPE
	SYNTAX          Integer32 (1..10)
	MAX-ACCESS      read-create
	STATUS  		current
	DESCRIPTION     
		"The service weighting used for weighted round robin."
	DEFVAL { 1 }
	--DEFAULT ap-display-name Weight
	--DEFAULT apjam-popup-ref apCntSvcInst, Statistics
	::= {apCntsvcEntry 9}

apCntsvcDnsHits OBJECT-TYPE
	SYNTAX          Integer32
	MAX-ACCESS      read-only
	STATUS  		current
	DESCRIPTION     
		"Total number DNS resolutions to this service on this content rule."
	DEFVAL { 0 }
	--DEFAULT ap-display-name Resolves
	--DEFAULT apjam-popup-ref apCntSvcInst, Statistics
	::= {apCntsvcEntry 10}

apCntsvcDnsProximityHits OBJECT-TYPE
	SYNTAX          Integer32
	MAX-ACCESS      read-only
	STATUS  		current
	DESCRIPTION     
		"Total number DNS proximity resolutions to this service on this content rule."
	DEFVAL { 0 }
	--DEFAULT ap-display-name ProximityResolves
	--DEFAULT apjam-popup-ref apCntSvcInst, Statistics
	::= {apCntsvcEntry 11}

apCntsvcState OBJECT-TYPE
	SYNTAX  INTEGER {
					suspended(1),
					down(2),
					alive(4)
 					}
	MAX-ACCESS      read-only
	STATUS  		current
	DESCRIPTION     
		"The current service state."
	DEFVAL { suspended }
	::= {apCntsvcEntry 12}

END
