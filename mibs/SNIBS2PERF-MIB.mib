--
--  Copyright (C) Siemens AG 1998
--                  All rights reserved
--

-- *******************************************************************
-- Modification Record:
--
--   Date   | Name       | Description
-- ---------+------------+--------------------------------------------
-- 01.04.94 | Braess     | Creation
-- 14.11.94 | Braess     | new name: PERFMIB
-- 10.04.96 | Naydek     | SNI-SM2 objects added
-- 05.07.96 | Naydek     | sm2MpUTM objects added
-- 22.07.96 | Naydek     | a few textual corrections
-- 04.10.96 | Naydek     | a new object: sm2BasicTimeString
--
-- *******************************************************************

-- This MIB describes objects, to monitor BS2000 systems via SNMP.
-- These objects are realized by a subagent within the BS2000 system.
-- The subagent assumes that the subsystem SM2 is running always.
-- This MIB has two parts:
--    - sniSM2Parms:   static informations
--    - sniSM2Mpoints: samples structured by SM2 buffers


SNIBS2PERF-MIB DEFINITIONS ::= BEGIN

-- DateAndTime ::= OCTET STRING (SIZE (8 | 11))
--        Definition copied from RFC 1514
--        A date-time specification for the local time of day.
--        This data type is intended to provide a consistent
--        method of reporting date information.
--
--            field  octets  contents                  range
--            =====  ======  ========                  =====
--              1      1-2   year                      0..65536
--                           (in network byte order)
--              2       3    month                     1..12
--              3       4    day                       1..31
--              4       5    hour                      0..23
--              5       6    minutes                   0..59
--              6       7    seconds                   0..60
--                           (use 60 for leap-second)
--              7       8    deci-seconds              0..9
--              8       9    direction from UTC        "+" / "-"
--                           (in ascii notation)
--              9      10    hours from UTC            0..11
--             10      11    minutes from UTC          0..59
--
--            Note that if only local time is known, then
--            timezone information (fields 8-10) is not present.
--
--
--
IMPORTS
		DateAndTime, DisplayString FROM SNMPv2-TC
	OBJECT-TYPE, enterprises FROM RFC1155-SMI;

sni                  OBJECT IDENTIFIER ::= { enterprises 231 }
sniProductMibs       OBJECT IDENTIFIER ::= { sni 2 }
sniSar               OBJECT IDENTIFIER ::= { sniProductMibs  13 }
sniSarParms          OBJECT IDENTIFIER ::= { sniSar 1 }
sniSarMpoints        OBJECT IDENTIFIER ::= { sniSar 2 }
sniSarHist           OBJECT IDENTIFIER ::= { sniSar 3 }

-- reserved set of OID's { sniSar.x | x = 10,11, ..,19 } for performance
-- MIB of BS2000

sniSM2Parms          OBJECT IDENTIFIER ::= { sniSar 10 }
sniSM2Mpoints        OBJECT IDENTIFIER ::= { sniSar 11 }
-- sniSM2Hist           OBJECT IDENTIFIER ::= { sniSar 12 }

--
--
-- BS2000 specific definitions
--
--

sm2Status OBJECT-TYPE
	SYNTAX  INTEGER
		{
		    running     (1),  -- subsystem SM2 running
		    not-running (2),  -- subsystem SM2 not running
		    unkown      (3)   -- program interface error
		     -- not-running (1), subsystem SM2 not running
		     -- created (2),     subsystem SM2 created
		     -- in-hold (3),     subsystem SM2 in hold/held
		     -- in-delete (4),   subsystem SM2 in delete/deleted
		     -- down (5),        SM2G task down
		     -- unkown (6)       program interface error
		}
	ACCESS  read-only
	STATUS  mandatory
	DESCRIPTION
	     "Status of the measurement subsystem SM2.
	      The subsystem SM2 is assumed running always."
	::= { sniSM2Parms 1 }

sm2Version OBJECT-TYPE
	SYNTAX  DisplayString (SIZE (8))
	ACCESS  read-only
	STATUS  mandatory
	DESCRIPTION
	     "Version of the measurement subsystem SM2: format Vnn.0Ann"
	::= { sniSM2Parms 2 }

sm2Interval OBJECT-TYPE
	SYNTAX  INTEGER (10..3600)
		-- a negative value (-1) stands for:
		--   at the moment no data available
		--   or error conditions have occured
	ACCESS  read-write
	STATUS  mandatory
	DESCRIPTION
	     "online cycle of the measurement subsystem SM2 in units of a
	      second, also called measurement interval (default value: 120).
	      Valid integer range for setting: 10..3600 "
	::= { sniSM2Parms 3 }

sm2SamplingCycle OBJECT-TYPE
	SYNTAX  INTEGER (200..10000)
		-- a negative value (-1) stands for:
		--   at the moment no data available
		--   or error conditions have occured
	ACCESS  read-write
	STATUS  mandatory
	DESCRIPTION
	     "sampling cycle of the measurement subsystem SM2
	      in units of a millisecond (default value: 800).
	      Valid integer range for setting: 200..10000 "
	::= { sniSM2Parms 4 }

--
--
--
sm2MpBasic OBJECT IDENTIFIER ::= { sniSM2Mpoints  1 }
--

sm2BasicStatus OBJECT-TYPE
	SYNTAX  INTEGER
		{
		  data-supported (1), -- data are supported and valid
		  data-invalid (2),   -- data are supported but invalid
		  prg-inactive (3),   -- measurement program inactive
		  no-subsystem (4),   -- subsystem is not running
		  sm2-not-running(5), -- subsystem SM2 not running
		  unkown (6)          -- program interface error
		}
	ACCESS  read-only
	STATUS  mandatory
	DESCRIPTION
	     "Status associated with BASIC buffer"
	::= { sm2MpBasic 1 }

-- sm2BasicElapsedTime OBJECT-TYPE
--         SYNTAX  INTEGER
--         ACCESS  read-only
--         STATUS  mandatory
--         DESCRIPTION
--              "Time period of the last measurement interval"
--      ::= { sm2MpBasic 2 }

sm2BasicTime OBJECT-TYPE
	SYNTAX  DateAndTime
	ACCESS  read-only
	STATUS  mandatory
	DESCRIPTION
	     "Time at the end of the last measurement interval.
	      DateAndTime in accordance with RFC1514"
	::= { sm2MpBasic 2 }

sm2BasicTimeString OBJECT-TYPE
	SYNTAX  DisplayString (SIZE (21|28) )
	ACCESS  read-only
	STATUS  mandatory
	DESCRIPTION
	  "Time at the end of the last measurement interval.
	   Date and Time in a direct displayable format:
	       YYYY-MM-DD,hh:mm:ss.d[,shh:mm]
	   where
	   YYYY-MM-DD is local date with year-month-day,
	   hh:mm:ss.d is local time with hour-minutes-seconds.deciseconds,
	   shh:mm     is (-|+)hours:minutes from UTC"
	::= { sm2MpBasic 3 }

sm2BasicSamples OBJECT-TYPE
	SYNTAX  INTEGER
		{ -- a non negative valid value OR
		     no-data (-1) -- at the moment no data available
		}                 -- or error conditions have occured
	ACCESS  read-only
	STATUS  mandatory
	DESCRIPTION
	     "Number of samples taken place within last measurement interval"
	::= { sm2MpBasic 4 }

sm2BasicMaxLogMach OBJECT-TYPE
	SYNTAX  INTEGER
		{ -- a non negative valid value OR
		     no-data (-1) -- at the moment no data available
		}                 -- or error conditions have occured
	ACCESS  read-only
	STATUS  mandatory
	DESCRIPTION
	     "Number of logical machines"
	::= { sm2MpBasic 5 }

sm2BasicVM2000 OBJECT-TYPE
	SYNTAX  INTEGER
		{
		  no-data (-1), -- at the moment no data available
				-- or error conditions have occured
		  inactive (1), -- VM2000 is not active
		  active (2)    -- VM2000 is active
		}
	ACCESS  read-only
	STATUS  mandatory
	DESCRIPTION
	     "Boolean info about VM2000 activity"
	::= { sm2MpBasic 6 }

--
--
--
sm2MpTimeIO OBJECT IDENTIFIER ::= { sniSM2Mpoints  2 }
--

sm2TimeIOStatus OBJECT-TYPE
	SYNTAX  INTEGER
		{
		  data-supported (1), -- data are supported and valid
		  data-invalid (2),   -- data are supported but invalid
		  prg-inactive (3),    -- measurement program inactive
		  no-subsystem (4),   -- subsystem is not running
		  sm2-not-running(5), -- subsystem SM2 not running
		  unkown (6)          -- program interface error
		}
	ACCESS  read-only
	STATUS  mandatory
	DESCRIPTION
	     "Status associated with TIME IO buffer"
	::= { sm2MpTimeIO 1 }

sm2TimeIOActMach OBJECT-TYPE
	SYNTAX  INTEGER
		{ -- a non negative valid value OR
		     no-data (-1) -- at the moment no data available
		}                 -- or error conditions have occured
	ACCESS  read-only
	STATUS  mandatory
	DESCRIPTION
	     "Number of active logical machines"
	::= { sm2MpTimeIO 2 }

sm2TimeIOMachTabNumber OBJECT-TYPE
	SYNTAX  INTEGER
		{ -- a non negative valid value OR
		     no-data (-1) -- at the moment no data available
		}                 -- or error conditions have occured
	ACCESS  read-only
	STATUS  mandatory
	DESCRIPTION
	     "Number of entries in following machine table"
	::= { sm2MpTimeIO 3 }

sm2TimeIOMachTab OBJECT-TYPE
	SYNTAX  SEQUENCE OF Sm2TimeIOMachTabEntry
	ACCESS  not-accessible
	STATUS  mandatory
	DESCRIPTION
	     "List about all logical machines and their data"
	::= { sm2MpTimeIO 4 }

sm2TimeIOMachTabEntry OBJECT-TYPE
	SYNTAX  Sm2TimeIOMachTabEntry
	ACCESS  not-accessible
	STATUS  mandatory
	DESCRIPTION
	     "Contains data of a logical machine"
	INDEX { sm2TimeIOMachTabIndex }
	::= { sm2TimeIOMachTab 1 }

Sm2TimeIOMachTabEntry ::= SEQUENCE
	{
	  sm2TimeIOMachTabIndex       INTEGER,
	  sm2TimeIOMachTabIdleTime    INTEGER,
	  sm2TimeIOMachTabTUTime      INTEGER,
	  sm2TimeIOMachTabTPRTime     INTEGER,
	  sm2TimeIOMachTabSIHTime     INTEGER,
	  sm2TimeIOMachTabStopTime    INTEGER,
	  sm2TimeIOMachTabPagingIO    INTEGER,
	  sm2TimeIOMachTabDiskIO      INTEGER,
	  sm2TimeIOMachTabTapeIO      INTEGER,
	  sm2TimeIOMachTabPrinterIO   INTEGER,
	  sm2TimeIOMachTabOtherIO     INTEGER
	}

sm2TimeIOMachTabIndex OBJECT-TYPE
	SYNTAX  INTEGER
		{
		    mach1   (1),  -- logical machine number 1
		    mach2   (2),  -- logical machine number 2
		    mach3   (3),  -- logical machine number 3
		    mach4   (4),  -- logical machine number 4
		    mach5   (5),  -- logical machine number 5
		    mach6   (6),  -- logical machine number 6
		    mach7   (7),  -- logical machine number 7
		    mach8   (8),  -- logical machine number 8
		    mach9   (9),  -- logical machine number 9
		    mach10 (10),  -- logical machine number 10
		    mach11 (11),  -- logical machine number 11
		    mach12 (12),  -- logical machine number 12
		    mach13 (13),  -- logical machine number 13
		    mach14 (14),  -- logical machine number 14
		    mach15 (15),  -- logical machine number 15
		    mach16 (16),  -- logical machine number 16
		    average (100)  -- average values over all logical machines
		}
	ACCESS  read-only
	STATUS  mandatory
	DESCRIPTION
	     "The index starts with 1 and uniquely identifies each entry.
	      Entry 'average' (index 100) will contain average values
	      for all provided measurement times and sums for the
	      remaining io counters over all logical machines.
	      Since the table provides average/sum values
	      'sm2TimeIOMachTabNumber' is regularly by one higher
	      than 'sm2TimeIOActMach'."
	::= { sm2TimeIOMachTabEntry 1 }

sm2TimeIOMachTabIdleTime OBJECT-TYPE
	SYNTAX  INTEGER
		{ -- a non negative valid value OR
		     no-data (-1) -- at the moment no data available
		}                 -- or error conditions have occured
	ACCESS  read-only
	STATUS  mandatory
	DESCRIPTION
	     "Time in which the logical machine was inactive (not stopped)
	      in o/oo (share of time in parts per thousand)."
	::= { sm2TimeIOMachTabEntry 2 }

sm2TimeIOMachTabTUTime OBJECT-TYPE
	SYNTAX  INTEGER
		{ -- a non negative valid value OR
		     no-data (-1) -- at the moment no data available
		}                 -- or error conditions have occured
	ACCESS  read-only
	STATUS  mandatory
	DESCRIPTION
	     "TU time of the logical machine
	      in o/oo (share of time in parts per thousand)."
	::= { sm2TimeIOMachTabEntry 3 }

sm2TimeIOMachTabTPRTime OBJECT-TYPE
	SYNTAX  INTEGER
		{ -- a non negative valid value OR
		     no-data (-1) -- at the moment no data available
		}                 -- or error conditions have occured
	ACCESS  read-only
	STATUS  mandatory
	DESCRIPTION
	     "TPR time of the logical machine
	      in o/oo (share of time in parts per thousand)."
	::= { sm2TimeIOMachTabEntry 4 }

sm2TimeIOMachTabSIHTime OBJECT-TYPE
	SYNTAX  INTEGER
		{ -- a non negative valid value OR
		     no-data (-1) -- at the moment no data available
		}                 -- or error conditions have occured
	ACCESS  read-only
	STATUS  mandatory
	DESCRIPTION
	     "SIH time of the logical machine
	      in o/oo (share of time in parts per thousand)."
	::= { sm2TimeIOMachTabEntry 5 }

sm2TimeIOMachTabStopTime OBJECT-TYPE
	SYNTAX  INTEGER
		{ -- a non negative valid value OR
		     no-data (-1) -- at the moment no data available
		}                 -- or error conditions have occured
	ACCESS  read-only
	STATUS  mandatory
	DESCRIPTION
	     "Stop time of the logical machine
	      in o/oo (share of time in parts per thousand)."
	::= { sm2TimeIOMachTabEntry 6 }

sm2TimeIOMachTabPagingIO OBJECT-TYPE
	SYNTAX  INTEGER
		{ -- a non negative valid value OR
		     no-data (-1) -- at the moment no data available
		}                 -- or error conditions have occured
	ACCESS  read-only
	STATUS  mandatory
	DESCRIPTION
	     "Rate of paging IO concerning the logical machine
	      in (number of paging IOs per second) * 10"
	::= { sm2TimeIOMachTabEntry 7 }

sm2TimeIOMachTabDiskIO OBJECT-TYPE
	SYNTAX  INTEGER
		{ -- a non negative valid value OR
		     no-data (-1) -- at the moment no data available
		}                 -- or error conditions have occured
	ACCESS  read-only
	STATUS  mandatory
	DESCRIPTION
	     "Rate of disk IO concerning the logical machine
	      in (number of disk IOs per second) * 10"
	::= { sm2TimeIOMachTabEntry 8 }

sm2TimeIOMachTabTapeIO OBJECT-TYPE
	SYNTAX  INTEGER
		{ -- a non negative valid value OR
		     no-data (-1) -- at the moment no data available
		}                 -- or error conditions have occured
	ACCESS  read-only
	STATUS  mandatory
	DESCRIPTION
	     "Rate of tape IO concerning the logical machine
	      in (number of tape IOs per second) * 10"
	::= { sm2TimeIOMachTabEntry 9 }

sm2TimeIOMachTabPrinterIO OBJECT-TYPE
	SYNTAX  INTEGER
		{ -- a non negative valid value OR
		     no-data (-1) -- at the moment no data available
		}                 -- or error conditions have occured
	ACCESS  read-only
	STATUS  mandatory
	DESCRIPTION
	     "Rate of printer IO concerning the logical machine
	      in (number of printer IOs per second) * 10"
	::= { sm2TimeIOMachTabEntry 10 }

sm2TimeIOMachTabOtherIO OBJECT-TYPE
	SYNTAX  INTEGER
		{ -- a non negative valid value OR
		     no-data (-1) -- at the moment no data available
		}                 -- or error conditions have occured
	ACCESS  read-only
	STATUS  mandatory
	DESCRIPTION
	     "Rate of other IO concerning the logical machine
	      in (number of other IOs per second) * 10"
	::= { sm2TimeIOMachTabEntry 11 }

--
--
--
sm2MpMemory OBJECT IDENTIFIER ::= { sniSM2Mpoints  3 }
--

sm2MemoryStatus OBJECT-TYPE
	SYNTAX  INTEGER
		{
		  data-supported (1), -- data are supported and valid
		  data-invalid (2),   -- data are supported but invalid
		  prg-inactive (3),    -- measurement program inactive
		  no-subsystem (4),   -- subsystem is not running
		  sm2-not-running(5), -- subsystem SM2 not running
		  unkown (6)          -- program interface error
		}
	ACCESS  read-only
	STATUS  mandatory
	DESCRIPTION
	     "Status associated with Memory buffer"
	::= { sm2MpMemory 1 }

sm2MemorySize OBJECT-TYPE
	SYNTAX  INTEGER
		{ -- a non negative valid value OR
		     no-data (-1) -- at the moment no data available
		}                 -- or error conditions have occured
	ACCESS  read-only
	STATUS  mandatory
	DESCRIPTION
	     "Total size of main memory in kilo bytes (kB)"
	::= { sm2MpMemory 2 }

sm2MemoryPageableSize OBJECT-TYPE
	SYNTAX  INTEGER
		{ -- a non negative valid value OR
		     no-data (-1) -- at the moment no data available
		}                 -- or error conditions have occured
	ACCESS  read-only
	STATUS  mandatory
	DESCRIPTION
	     "Size of pageable memory in kilo bytes (kB)"
	::= { sm2MpMemory 3 }

sm2MemoryFreeReadSize OBJECT-TYPE
	SYNTAX  INTEGER
		{ -- a non negative valid value OR
		     no-data (-1) -- at the moment no data available
		}                 -- or error conditions have occured
	ACCESS  read-only
	STATUS  mandatory
	DESCRIPTION
	     "Size of free read-only memory (pageable) in kilo bytes (kB)"
	::= { sm2MpMemory 4 }

sm2MemoryFreeReadWriteSize OBJECT-TYPE
	SYNTAX  INTEGER
		{ -- a non negative valid value OR
		     no-data (-1) -- at the moment no data available
		}                 -- or error conditions have occured
	ACCESS  read-only
	STATUS  mandatory
	DESCRIPTION
	     "Size of free read/write memory (pageable) in kilo bytes (kB)"
	::= { sm2MpMemory 5 }

sm2MemoryPagingAreaTotal OBJECT-TYPE
	SYNTAX  INTEGER
		{ -- a non negative valid value OR
		     no-data (-1) -- at the moment no data available
		}                 -- or error conditions have occured
	ACCESS  read-only
	STATUS  mandatory
	DESCRIPTION
	     "Total size of paging area (incl. ES/GS) in kilo bytes (kB)"
	::= { sm2MpMemory 6 }

sm2MemoryPagingAreaESGS OBJECT-TYPE
	SYNTAX  INTEGER
		{ -- a non negative valid value OR
		     no-data (-1) -- at the moment no data available
		}                 -- or error conditions have occured
	ACCESS  read-only
	STATUS  mandatory
	DESCRIPTION
	     "Size of ES/GS paging area in kilo bytes (kB)"
	::= { sm2MpMemory 7 }

sm2MemoryPagingAreaFree OBJECT-TYPE
	SYNTAX  INTEGER
		{ -- a non negative valid value OR
		     no-data (-1) -- at the moment no data available
		}                 -- or error conditions have occured
	ACCESS  read-only
	STATUS  mandatory
	DESCRIPTION
	     "Size of free paging area in kilo bytes (kB)"
	::= { sm2MpMemory 8 }

sm2MemoryPageFaults OBJECT-TYPE
	SYNTAX  INTEGER
		{ -- a non negative valid value OR
		     no-data (-1) -- at the moment no data available
		}                 -- or error conditions have occured
	ACCESS  read-only
	STATUS  mandatory
	DESCRIPTION
	     "Total number of page faults interrupts per second * 10"
	::= { sm2MpMemory 9 }

sm2MemoryPage1stFaults OBJECT-TYPE
	SYNTAX  INTEGER
		{ -- a non negative valid value OR
		     no-data (-1) -- at the moment no data available
		}                 -- or error conditions have occured
	ACCESS  read-only
	STATUS  mandatory
	DESCRIPTION
	     "Number of page faults interrupts for the
	      first access to a page per second * 10"
	::= { sm2MpMemory 10 }

sm2MemoryPageReclaims OBJECT-TYPE
	SYNTAX  INTEGER
		{ -- a non negative valid value OR
		     no-data (-1) -- at the moment no data available
		}                 -- or error conditions have occured
	ACCESS  read-only
	STATUS  mandatory
	DESCRIPTION
	     "Number of page faults interrupts for which the
	      addressed page is still in memory per second * 10"
	::= { sm2MpMemory 11 }

sm2MemoryPageReads OBJECT-TYPE
	SYNTAX  INTEGER
		{ -- a non negative valid value OR
		     no-data (-1) -- at the moment no data available
		}                 -- or error conditions have occured
	ACCESS  read-only
	STATUS  mandatory
	DESCRIPTION
	     "Number of pages read from background storage
	      per second * 10 (PAGE READS)"
	::= { sm2MpMemory 12 }

sm2MemoryPageWrites OBJECT-TYPE
	SYNTAX  INTEGER
		{ -- a non negative valid value OR
		     no-data (-1) -- at the moment no data available
		}                 -- or error conditions have occured
	ACCESS  read-only
	STATUS  mandatory
	DESCRIPTION
	     "Number of pages written to background storage
	      per second * 10 (PAGE WRITES)"
	::= { sm2MpMemory 13 }

sm2MemoryPageReadESGS OBJECT-TYPE
	SYNTAX  INTEGER
		{ -- a non negative valid value OR
		     no-data (-1) -- at the moment no data available
		}                 -- or error conditions have occured
	ACCESS  read-only
	STATUS  mandatory
	DESCRIPTION
	     "Number of pages read from expanded (ES) or global
	      storage (GS) per second * 10"
	::= { sm2MpMemory 14 }

sm2MemoryPageWriteESGS OBJECT-TYPE
	SYNTAX  INTEGER
		{ -- a non negative valid value OR
		     no-data (-1) -- at the moment no data available
		}                 -- or error conditions have occured
	ACCESS  read-only
	STATUS  mandatory
	DESCRIPTION
	     "Number of pages written to expanded (ES) or global
	      storage (GS) per second * 10"
	::= { sm2MpMemory 15 }

--
--
--
sm2MpCategory OBJECT IDENTIFIER ::= { sniSM2Mpoints  5 }
--

sm2CategoryStatus OBJECT-TYPE
	SYNTAX  INTEGER
		{
		  data-supported (1), -- data are supported and valid
		  data-invalid (2),   -- data are supported but invalid
		  prg-inactive (3),    -- measurement program inactive
		  no-subsystem (4),   -- subsystem is not running
		  sm2-not-running(5), -- subsystem SM2 not running
		  unkown (6)          -- program interface error
		}
	ACCESS  read-only
	STATUS  mandatory
	DESCRIPTION
	     "Status associated with Category buffer"
	::= { sm2MpCategory 1 }

sm2CategorySystemTasks OBJECT-TYPE
	SYNTAX  INTEGER
		{ -- a non negative valid value OR
		     no-data (-1) -- at the moment no data available
		}                 -- or error conditions have occured
	ACCESS  read-only
	STATUS  mandatory
	DESCRIPTION
	     "Average number of system tasks *10"
	::= { sm2MpCategory 2 }

sm2CategoryDialogTasks OBJECT-TYPE
	SYNTAX  INTEGER
		{ -- a non negative valid value OR
		     no-data (-1) -- at the moment no data available
		}                 -- or error conditions have occured
	ACCESS  read-only
	STATUS  mandatory
	DESCRIPTION
	     "Average number of dialog tasks *10"
	::= { sm2MpCategory 3 }

sm2CategoryBatchTasks OBJECT-TYPE
	SYNTAX  INTEGER
		{ -- a non negative valid value OR
		     no-data (-1) -- at the moment no data available
		}                 -- or error conditions have occured
	ACCESS  read-only
	STATUS  mandatory
	DESCRIPTION
	     "Average number of batch tasks *10"
	::= { sm2MpCategory 4 }

sm2CategoryTPTasks OBJECT-TYPE
	SYNTAX  INTEGER
		{ -- a non negative valid value OR
		     no-data (-1) -- at the moment no data available
		}                 -- or error conditions have occured
	ACCESS  read-only
	STATUS  mandatory
	DESCRIPTION
	     "Average number of tp tasks *10"
	::= { sm2MpCategory 5 }

-- sm2CategoryPCSFlag OBJECT-TYPE
--      SYNTAX  INTEGER
--              {    no-data     (-1), - at the moment no data available
--                                     - or error conditions have occured
--                   pcs-active   (1), - PCS is active
--                   pcs-inactive (2)  - PCS is not active
--              }
--      ACCESS  read-only
--      STATUS  mandatory
--      DESCRIPTION
--           "Flag indicating whether PCS is active or not"
--      ::= { sm2MpCategory 6 }

--
--
--
sm2MpSDevice OBJECT IDENTIFIER ::= { sniSM2Mpoints 7 }
--

sm2SDeviceStatus OBJECT-TYPE
	SYNTAX  INTEGER
		{
		  data-supported (1), -- data are supported and valid
		  data-invalid (2),   -- data are supported but invalid
		  prg-inactive (3),    -- measurement program inactive
		  no-subsystem (4),   -- subsystem is not running
		  sm2-not-running(5), -- subsystem SM2 not running
		  unkown (6)          -- program interface error
		}
	ACCESS  read-only
	STATUS  mandatory
	DESCRIPTION
	     "Status associated with Sampling-Device buffer"
	::= { sm2MpSDevice 1 }

sm2SDeviceRealNumber OBJECT-TYPE
	SYNTAX  INTEGER
		{ -- a non negative valid value OR
		     no-data (-1) -- at the moment no data available
		}                 -- or error conditions have occured
	ACCESS  read-only
	STATUS  mandatory
	DESCRIPTION
	     "Real number of available devices"
	::= { sm2MpSDevice 2 }

sm2SDeviceTabNumber OBJECT-TYPE
	SYNTAX  INTEGER
		{ -- a non negative valid value OR
		     no-data (-1) -- at the moment no data available
		}                 -- or error conditions have occured
	ACCESS  read-only
	STATUS  mandatory
	DESCRIPTION
	     "Number of entries in following table; default: 10 entries"
	::= { sm2MpSDevice 3 }

sm2SDeviceTab OBJECT-TYPE
	SYNTAX  SEQUENCE OF Sm2SDeviceTabEntry
	ACCESS  not-accessible
	STATUS  mandatory
	DESCRIPTION
	     "List of devices (terminals, fixed disks, IO-devices, ... );
	      sorted by 'sm2SDeviceTabIO' in descending order."
	::= { sm2MpSDevice 4 }

sm2SDeviceTabEntry OBJECT-TYPE
	SYNTAX  Sm2SDeviceTabEntry
	ACCESS  not-accessible
	STATUS  mandatory
	DESCRIPTION
	     "Brief description of a certain device"
	INDEX { sm2SDeviceTabIndex }
	::= { sm2SDeviceTab 1 }

Sm2SDeviceTabEntry ::= SEQUENCE
	{
	  sm2SDeviceTabIndex INTEGER,
	  sm2SDeviceTabVSN DisplayString (SIZE (6)),
	  sm2SDeviceTabMnemonic DisplayString (SIZE (4)),
	  sm2SDeviceTabType DisplayString,
	  sm2SDeviceTabIO INTEGER,
	  sm2SDeviceTabBusyDms INTEGER,
	  sm2SDeviceTabBusyPaging INTEGER
	}

sm2SDeviceTabIndex OBJECT-TYPE
	SYNTAX  INTEGER
	ACCESS  read-only
	STATUS  mandatory
	DESCRIPTION
	     "Uniquely identifies each entry of this table"
	::= { sm2SDeviceTabEntry 1 }

sm2SDeviceTabVSN OBJECT-TYPE
	SYNTAX  DisplayString (SIZE (6))
	ACCESS  read-only
	STATUS  mandatory
	DESCRIPTION
	     "Volume sequence number (volume name)"
	::= { sm2SDeviceTabEntry 2 }

sm2SDeviceTabMnemonic OBJECT-TYPE
	SYNTAX  DisplayString (SIZE (4))
	ACCESS  read-only
	STATUS  mandatory
	DESCRIPTION
	     "Mnemonic device name"
	::= { sm2SDeviceTabEntry 3 }

sm2SDeviceTabType OBJECT-TYPE
	SYNTAX  DisplayString
	ACCESS  read-only
	STATUS  mandatory
	DESCRIPTION
	     "Device type gained using macro NKGTYPE"
	::= { sm2SDeviceTabEntry 4 }

sm2SDeviceTabIO OBJECT-TYPE
	SYNTAX  INTEGER
		{ -- a non negative valid value OR
		     no-data (-1) -- at the moment no data available
		}                 -- or error conditions have occured
	ACCESS  read-only
	STATUS  mandatory
	DESCRIPTION
	     "Number of IO operations performed physically per second * 10"
	::= { sm2SDeviceTabEntry 5 }

sm2SDeviceTabBusyDms OBJECT-TYPE
	SYNTAX  INTEGER
		{ -- a non negative valid value OR
		     no-data (-1) -- at the moment no data available
		}                 -- or error conditions have occured
	ACCESS  read-only
	STATUS  mandatory
	DESCRIPTION
	     "Device activity (excluding paging)
	      in o/oo (share of time in parts per thousand)."
	::= { sm2SDeviceTabEntry 6 }

sm2SDeviceTabBusyPaging OBJECT-TYPE
	SYNTAX  INTEGER
		{ -- a non negative valid value OR
		     no-data (-1) -- at the moment no data available
		}                 -- or error conditions have occured
	ACCESS  read-only
	STATUS  mandatory
	DESCRIPTION
	     "Device activity due to paging
	      in o/oo (share of time in parts per thousand)."
	::= { sm2SDeviceTabEntry 7 }


--
--
--
sm2MpUTM OBJECT IDENTIFIER ::= { sniSM2Mpoints 15 }
--

sm2UTMStatus OBJECT-TYPE
	SYNTAX  INTEGER
		{
		  data-supported (1), -- data are supported and valid
		  data-invalid (2),   -- data are supported but invalid
		  prg-inactive (3),    -- measurement program inactive
		  no-subsystem (4),   -- subsystem is not running
		  sm2-not-running(5), -- subsystem SM2 not running
		  unkown (6)          -- program interface error
		}
	ACCESS  read-only
	STATUS  mandatory
	DESCRIPTION
	     "Status associated with UTM buffer"
	::= { sm2MpUTM 1 }

sm2UTMTabNumber OBJECT-TYPE
	SYNTAX  INTEGER
		{ -- a non negative valid value OR
		     no-data (-1) -- at the moment no data available
		}                 -- or error conditions have occured
	ACCESS  read-only
	STATUS  mandatory
	DESCRIPTION
	     "Number of entries in following table"
	::= { sm2MpUTM 2 }

sm2UTMTab OBJECT-TYPE
	SYNTAX  SEQUENCE OF Sm2UTMTabEntry
	ACCESS  not-accessible
	STATUS  mandatory
	DESCRIPTION
	     "List of UTM applications sorted by 'sm2UTMTabDialTotalTime'
	      in descending order."
	::= { sm2MpUTM 3 }

sm2UTMTabEntry OBJECT-TYPE
	SYNTAX  Sm2UTMTabEntry
	ACCESS  not-accessible
	STATUS  mandatory
	DESCRIPTION
	     "Few characteristical values of an UTM application"
	INDEX { sm2UTMTabIndex }
	::= { sm2UTMTab 1 }

Sm2UTMTabEntry ::= SEQUENCE
	{
	  sm2UTMTabIndex            INTEGER,
	  sm2UTMTabApplName         DisplayString (SIZE (8)),
	  sm2UTMTabUTMVersion       DisplayString (SIZE (8)),
	  sm2UTMTabApplMode         INTEGER,
	  sm2UTMTabTasksRunning     INTEGER,
	  sm2UTMTabMaxAsyncTasks    INTEGER,
	  sm2UTMTabConnectedUsers   INTEGER,
	  sm2UTMTabCurrConvDial     INTEGER,
	  sm2UTMTabCurrConvAsync    INTEGER,
	  sm2UTMTabWaitingATACS     INTEGER,
	  sm2UTMTabCacheHitRate     INTEGER,
	  sm2UTMTabFreePagePool     INTEGER,
	  sm2UTMTabDialTACS         INTEGER,
	  sm2UTMTabAsyncTACS        INTEGER,
	  sm2UTMTabDialTotalTime    INTEGER,
	  sm2UTMTabDialTotalTimeDB  INTEGER,
	  sm2UTMTabDialDBTime       INTEGER,
	  sm2UTMTabDialDBCall       INTEGER,
	  sm2UTMTabDialDBCpuTime    INTEGER,
	  sm2UTMTabDialDBIO         INTEGER,
	  sm2UTMTabDialUTMCpuTime   INTEGER,
	  sm2UTMTabDialUTMIO        INTEGER,
	  sm2UTMTabAsyncTotalTime   INTEGER,
	  sm2UTMTabAsyncTotalTimeDB INTEGER,
	  sm2UTMTabAsyncDBTime      INTEGER,
	  sm2UTMTabAsyncDBCall      INTEGER,
	  sm2UTMTabAsyncDBCpuTime   INTEGER,
	  sm2UTMTabAsyncDBIO        INTEGER,
	  sm2UTMTabAsyncUTMCpuTime  INTEGER,
	  sm2UTMTabAsyncUTMIO       INTEGER
	}

sm2UTMTabIndex OBJECT-TYPE
	SYNTAX  INTEGER
	ACCESS  read-only
	STATUS  mandatory
	DESCRIPTION
	     "Uniquely identifies each entry of this table"
	::= { sm2UTMTabEntry 1 }

sm2UTMTabApplName OBJECT-TYPE
	SYNTAX  DisplayString (SIZE (8))
	ACCESS  read-only
	STATUS  mandatory
	DESCRIPTION
	     "Name of UTM application"
	::= { sm2UTMTabEntry 2 }

sm2UTMTabUTMVersion OBJECT-TYPE
	SYNTAX  DisplayString (SIZE (8))
	ACCESS  read-only
	STATUS  mandatory
	DESCRIPTION
	     "Version of subsystem. Format: Vnn.nann"
	::= { sm2UTMTabEntry 3 }

sm2UTMTabApplMode OBJECT-TYPE
	SYNTAX  INTEGER
		{
		  no-data (-1),          -- at the moment no data available
		  utm-s-application (1), -- UTM-S application
		  utm-f-application (2)  -- UTM-F application
		}
	ACCESS  read-only
	STATUS  mandatory
	DESCRIPTION
	     "UTM application mode"
	::= { sm2UTMTabEntry 4 }

sm2UTMTabTasksRunning OBJECT-TYPE
	SYNTAX  INTEGER
		{ -- a non negative valid value OR
		     no-data (-1) -- at the moment no data available
		}                 -- or error conditions have occured
	ACCESS  read-only
	STATUS  mandatory
	DESCRIPTION
	     "Number of tasks running for this UTM application"
	::= { sm2UTMTabEntry 5 }

sm2UTMTabMaxAsyncTasks OBJECT-TYPE
	SYNTAX  INTEGER
		{ -- a non negative valid value OR
		     no-data (-1) -- at the moment no data available
		}                 -- or error conditions have occured
	ACCESS  read-only
	STATUS  mandatory
	DESCRIPTION
	     "Maximal number of tasks for asynchronous processing"
	::= { sm2UTMTabEntry 6 }

sm2UTMTabConnectedUsers OBJECT-TYPE
	SYNTAX  INTEGER
		{ -- a non negative valid value OR
		     no-data (-1) -- at the moment no data available
		}                 -- or error conditions have occured
	ACCESS  read-only
	STATUS  mandatory
	DESCRIPTION
	     "Number of currently connected users"
	::= { sm2UTMTabEntry 7 }

sm2UTMTabCurrConvDial OBJECT-TYPE
	SYNTAX  INTEGER
		{ -- a non negative valid value OR
		     no-data (-1) -- at the moment no data available
		}                 -- or error conditions have occured
	ACCESS  read-only
	STATUS  mandatory
	DESCRIPTION
	     "Number of active dialog conversations"
	::= { sm2UTMTabEntry 8 }

sm2UTMTabCurrConvAsync OBJECT-TYPE
	SYNTAX  INTEGER
		{ -- a non negative valid value OR
		     no-data (-1) -- at the moment no data available
		}                 -- or error conditions have occured
	ACCESS  read-only
	STATUS  mandatory
	DESCRIPTION
	     "Number of active asynchronous conversations"
	::= { sm2UTMTabEntry 9 }

sm2UTMTabWaitingATACS OBJECT-TYPE
	SYNTAX  INTEGER
		{ -- a non negative valid value OR
		     no-data (-1) -- at the moment no data available
		}                 -- or error conditions have occured
	ACCESS  read-only
	STATUS  mandatory
	DESCRIPTION
	     "Number of waiting asynchronous transactions,
	      buffered but not yet processed"
	::= { sm2UTMTabEntry 10 }

sm2UTMTabCacheHitRate OBJECT-TYPE
	SYNTAX  INTEGER
		{ -- a non negative valid value OR
		     no-data (-1) -- at the moment no data available
		}                 -- or error conditions have occured
	ACCESS  read-only
	STATUS  mandatory
	DESCRIPTION
	     "UTM cache hit rate in o/oo (parts per thousand)."
	::= { sm2UTMTabEntry 11 }

sm2UTMTabFreePagePool OBJECT-TYPE
	SYNTAX  INTEGER
		{ -- a non negative valid value OR
		     no-data (-1) -- at the moment no data available
		}                 -- or error conditions have occured
	ACCESS  read-only
	STATUS  mandatory
	DESCRIPTION
	     "Percentage of free pages in UTM pagepool *10;
	      parts per thousand (o/oo)."
	::= { sm2UTMTabEntry 12 }

sm2UTMTabDialTACS OBJECT-TYPE
	SYNTAX  INTEGER
		{ -- a non negative valid value OR
		     no-data (-1) -- at the moment no data available
		}                 -- or error conditions have occured
	ACCESS  read-only
	STATUS  mandatory
	DESCRIPTION
	     "Number of (finished) dialog transactions per second *10"
	::= { sm2UTMTabEntry 13 }

sm2UTMTabAsyncTACS OBJECT-TYPE
	SYNTAX  INTEGER
		{ -- a non negative valid value OR
		     no-data (-1) -- at the moment no data available
		}                 -- or error conditions have occured
	ACCESS  read-only
	STATUS  mandatory
	DESCRIPTION
	     "Number of (finished) asynchronous transactions (ATACS)
	      per second *10"
	::= { sm2UTMTabEntry 14 }

sm2UTMTabDialTotalTime OBJECT-TYPE
	SYNTAX  INTEGER
		{ -- a non negative valid value OR
		     no-data (-1) -- at the moment no data available
		}                 -- or error conditions have occured
	ACCESS  read-only
	STATUS  mandatory
	DESCRIPTION
	     "Average time period of a dialog step (UTM response time)
	      in seconds *10"
	::= { sm2UTMTabEntry 15 }

sm2UTMTabDialTotalTimeDB OBJECT-TYPE
	SYNTAX  INTEGER
		{ -- a non negative valid value OR
		     no-data (-1) -- at the moment no data available
		}                 -- or error conditions have occured
	ACCESS  read-only
	STATUS  mandatory
	DESCRIPTION
	     "Average time period of a dialog step (UTM response time)
	      in seconds *10.
	      Only dialog steps with data base accesses are considered."
	::= { sm2UTMTabEntry 16 }

sm2UTMTabDialDBTime OBJECT-TYPE
	SYNTAX  INTEGER
		{ -- a non negative valid value OR
		     no-data (-1) -- at the moment no data available
		}                 -- or error conditions have occured
	ACCESS  read-only
	STATUS  mandatory
	DESCRIPTION
	     "Average time per dialog step UTM is waiting for data base
	      responses in seconds *10.
	      Only dialog steps with data base accesses are considered."
	::= { sm2UTMTabEntry 17 }

sm2UTMTabDialDBCall OBJECT-TYPE
	SYNTAX  INTEGER
		{ -- a non negative valid value OR
		     no-data (-1) -- at the moment no data available
		}                 -- or error conditions have occured
	ACCESS  read-only
	STATUS  mandatory
	DESCRIPTION
	     "Average number of data base calls per dialog step.
	      Only dialog steps with data base accesses are considered."
	::= { sm2UTMTabEntry 18 }

sm2UTMTabDialDBCpuTime OBJECT-TYPE
	SYNTAX  INTEGER
		{ -- a non negative valid value OR
		     no-data (-1) -- at the moment no data available
		}                 -- or error conditions have occured
	ACCESS  read-only
	STATUS  mandatory
	DESCRIPTION
	     "Average CPU time per dialog step data base/s is/are processing
	      in seconds *10.
	      Only dialog steps with data base accesses are considered."
	::= { sm2UTMTabEntry 19 }

sm2UTMTabDialDBIO OBJECT-TYPE
	SYNTAX  INTEGER
		{ -- a non negative valid value OR
		     no-data (-1) -- at the moment no data available
		}                 -- or error conditions have occured
	ACCESS  read-only
	STATUS  mandatory
	DESCRIPTION
	     "Average number of data base IOs per dialog step.
	      Only dialog steps with data base accesses are considered."
	::= { sm2UTMTabEntry 20 }

sm2UTMTabDialUTMCpuTime OBJECT-TYPE
	SYNTAX  INTEGER
		{ -- a non negative valid value OR
		     no-data (-1) -- at the moment no data available
		}                 -- or error conditions have occured
	ACCESS  read-only
	STATUS  mandatory
	DESCRIPTION
	 "Average CPU time per dialog step UTM tasks are consuming
	  in seconds *10"
	::= { sm2UTMTabEntry 21 }

sm2UTMTabDialUTMIO OBJECT-TYPE
	SYNTAX  INTEGER
		{ -- a non negative valid value OR
		     no-data (-1) -- at the moment no data available
		}                 -- or error conditions have occured
	ACCESS  read-only
	STATUS  mandatory
	DESCRIPTION
	     "Average number of IOs done by UTM tasks per dialog step"
	::= { sm2UTMTabEntry 22 }

sm2UTMTabAsyncTotalTime OBJECT-TYPE
	SYNTAX  INTEGER
		{ -- a non negative valid value OR
		     no-data (-1) -- at the moment no data available
		}                 -- or error conditions have occured
	ACCESS  read-only
	STATUS  mandatory
	DESCRIPTION
	     "Average Time period of a asynchronous conversation
	      (UTM response time) in seconds *10"
	::= { sm2UTMTabEntry 23 }

sm2UTMTabAsyncTotalTimeDB OBJECT-TYPE
	SYNTAX  INTEGER
		{ -- a non negative valid value OR
		     no-data (-1) -- at the moment no data available
		}                 -- or error conditions have occured
	ACCESS  read-only
	STATUS  mandatory
	DESCRIPTION
	     "Average time period of a asynchronous conversation
	      in seconds *10. Only asynchronous conversations
	      with data base accesses are considered."
	::= { sm2UTMTabEntry 24 }

sm2UTMTabAsyncDBTime OBJECT-TYPE
	SYNTAX  INTEGER
		{ -- a non negative valid value OR
		     no-data (-1) -- at the moment no data available
		}                 -- or error conditions have occured
	ACCESS  read-only
	STATUS  mandatory
	DESCRIPTION
	     "Average time per asynchonous conversation UTM is waiting
	      for data base responses in seconds *10. Only asynchronous
	      conversations with data base accesses are considered."
	::= { sm2UTMTabEntry 25 }

sm2UTMTabAsyncDBCall OBJECT-TYPE
	SYNTAX  INTEGER
		{ -- a non negative valid value OR
		     no-data (-1) -- at the moment no data available
		}                 -- or error conditions have occured
	ACCESS  read-only
	STATUS  mandatory
	DESCRIPTION
	     "Average number of data base calls per asynchronous
	      conversation. Only asynchronous conversations
	      with data base accesses are considered."
	::= { sm2UTMTabEntry 26 }

sm2UTMTabAsyncDBCpuTime OBJECT-TYPE
	SYNTAX  INTEGER
		{ -- a non negative valid value OR
		     no-data (-1) -- at the moment no data available
		}                 -- or error conditions have occured
	ACCESS  read-only
	STATUS  mandatory
	DESCRIPTION
	     "Average CPU time per asynchronous conversation data base/s
	      is/are processing in seconds *10. Only asynchronous
	      conversations with data base accesses are considered."
	::= { sm2UTMTabEntry 27 }

sm2UTMTabAsyncDBIO OBJECT-TYPE
	SYNTAX  INTEGER
		{ -- a non negative valid value OR
		     no-data (-1) -- at the moment no data available
		}                 -- or error conditions have occured
	ACCESS  read-only
	STATUS  mandatory
	DESCRIPTION
	     "Average number of data base IOs per asynchronous conversation.
	      Only asynchronous conversations
	      with data base accesses are considered."
	::= { sm2UTMTabEntry 28 }

sm2UTMTabAsyncUTMCpuTime OBJECT-TYPE
	SYNTAX  INTEGER
		{ -- a non negative valid value OR
		     no-data (-1) -- at the moment no data available
		}                 -- or error conditions have occured
	ACCESS  read-only
	STATUS  mandatory
	DESCRIPTION
	     "Average CPU time per asynchronous conversation UTM tasks
	      are consuming in seconds *10"
	::= { sm2UTMTabEntry 29 }

sm2UTMTabAsyncUTMIO OBJECT-TYPE
	SYNTAX  INTEGER
		{ -- a non negative valid value OR
		     no-data (-1) -- at the moment no data available
		}                 -- or error conditions have occured
	ACCESS  read-only
	STATUS  mandatory
	DESCRIPTION
	     "Average number of IOs done by UTM tasks per asynchronous
	      conversation "
	::= { sm2UTMTabEntry 30 }


--
--
--
sm2MpPerTask OBJECT IDENTIFIER ::= { sniSM2Mpoints 16 }
--

sm2PerTaskStatus OBJECT-TYPE
	SYNTAX  INTEGER
		{
		  data-supported (1), -- data are supported and valid
		  data-invalid (2),   -- data are supported but invalid
		  prg-inactive (3),    -- measurement program inactive
		  no-subsystem (4),   -- subsystem is not running
		  sm2-not-running(5), -- subsystem SM2 not running
		  unkown (6)          -- program interface error
		}
	ACCESS  read-only
	STATUS  mandatory
	DESCRIPTION
	     "Status associated with Periodic Task buffer"
	::= { sm2MpPerTask 1 }

sm2PerTaskRealNumber OBJECT-TYPE
	SYNTAX  INTEGER
		{ -- a non negative valid value OR
		     no-data (-1) -- at the moment no data available
		}                 -- or error conditions have occured
	ACCESS  read-only
	STATUS  mandatory
	DESCRIPTION
	     "Real number of available tasks"
	::= { sm2MpPerTask 2 }

sm2PerTaskTabNumber OBJECT-TYPE
	SYNTAX  INTEGER
		{ -- a non negative valid value OR
		     no-data (-1) -- at the moment no data available
		}                 -- or error conditions have occured
	ACCESS  read-only
	STATUS  mandatory
	DESCRIPTION
	     "Number of entries in following table; default: 10 entries"
	::= { sm2MpPerTask 3 }

sm2PerTaskTab OBJECT-TYPE
	SYNTAX  SEQUENCE OF Sm2SDeviceTabEntry
	ACCESS  not-accessible
	STATUS  mandatory
	DESCRIPTION
	     "List of tasks sorted by 'sm2PerTaskTabCPU' in descending order"
	::= { sm2MpPerTask 4 }

sm2PerTaskTabEntry OBJECT-TYPE
	SYNTAX  Sm2PerTaskTabEntry
	ACCESS  not-accessible
	STATUS  mandatory
	DESCRIPTION
	     "Brief description of a certain task"
	INDEX { sm2PerTaskTabIndex }
	::= { sm2PerTaskTab 1 }

Sm2PerTaskTabEntry ::= SEQUENCE
	{
	  sm2PerTaskTabIndex INTEGER,
	  sm2PerTaskTabTSN DisplayString (SIZE (4)),
	  sm2PerTaskTabUserID DisplayString (SIZE (8)),
	  sm2PerTaskTabJobName DisplayString (SIZE (8)),
	  sm2PerTaskTabType INTEGER,
	  sm2PerTaskTabCPU INTEGER,
	  sm2PerTaskTabIO INTEGER,
	  sm2PerTaskTabUPG INTEGER,
	  sm2PerTaskTabServiceUnits INTEGER,
	  sm2PerTaskTabPageRead INTEGER
	}

sm2PerTaskTabIndex OBJECT-TYPE
	SYNTAX  INTEGER
	ACCESS  read-only
	STATUS  mandatory
	DESCRIPTION
	     "Uniquely identifies each entry of this table"
	::= { sm2PerTaskTabEntry 1 }

sm2PerTaskTabTSN OBJECT-TYPE
	SYNTAX  DisplayString (SIZE (4))
	ACCESS  read-only
	STATUS  mandatory
	DESCRIPTION
	     "Task sequence number"
	::= { sm2PerTaskTabEntry 2 }

sm2PerTaskTabUserID OBJECT-TYPE
	SYNTAX  DisplayString (SIZE (8))
	ACCESS  read-only
	STATUS  mandatory
	DESCRIPTION
	     "User ID under which the task is running"
	::= { sm2PerTaskTabEntry 3 }

sm2PerTaskTabJobName OBJECT-TYPE
	SYNTAX  DisplayString (SIZE (8))
	ACCESS  read-only
	STATUS  mandatory
	DESCRIPTION
	     "Job name"
	::= { sm2PerTaskTabEntry 4 }

sm2PerTaskTabType OBJECT-TYPE
	SYNTAX  INTEGER
		{
		  no-data (-1), -- at the moment no data available
				-- or error conditions have occured
		  system  (1),  -- task type: system
		  dialog  (2),  -- task type: dialog
		  batch   (3),  -- task type: batch
		  tp      (4)   -- task type: tp
		}
	ACCESS  read-only
	STATUS  mandatory
	DESCRIPTION
	     "Task type"
	::= { sm2PerTaskTabEntry 5 }

sm2PerTaskTabCPU OBJECT-TYPE
	SYNTAX  INTEGER
		{ -- a non negative valid value OR
		     no-data (-1) -- at the moment no data available
		}                 -- or error conditions have occured
	ACCESS  read-only
	STATUS  mandatory
	DESCRIPTION
	     "CPU utilization in o/oo
	      (share of time in parts per thousand)."
	::= { sm2PerTaskTabEntry 6 }

sm2PerTaskTabIO OBJECT-TYPE
	SYNTAX  INTEGER
		{ -- a non negative valid value OR
		     no-data (-1) -- at the moment no data available
		}                 -- or error conditions have occured
	ACCESS  read-only
	STATUS  mandatory
	DESCRIPTION
	     "Number of IO operations per second * 10"
	::= { sm2PerTaskTabEntry 7 }

sm2PerTaskTabUPG OBJECT-TYPE
	SYNTAX  INTEGER
		{ -- a non negative valid value OR
		     no-data (-1) -- at the moment no data available
		}                 -- or error conditions have occured
	ACCESS  read-only
	STATUS  mandatory
	DESCRIPTION
	     "Average number of Used Pages"
	::= { sm2PerTaskTabEntry 8 }

sm2PerTaskTabServiceUnits OBJECT-TYPE
	SYNTAX  INTEGER
		{ -- a non negative valid value OR
		     no-data (-1) -- at the moment no data available
		}                 -- or error conditions have occured
	ACCESS  read-only
	STATUS  mandatory
	DESCRIPTION
	     "Number of service units utilized per second * 10"
	::= { sm2PerTaskTabEntry 9 }

sm2PerTaskTabPageRead OBJECT-TYPE
	SYNTAX  INTEGER
		{ -- a non negative valid value OR
		     no-data (-1) -- at the moment no data available
		}                 -- or error conditions have occured
	ACCESS  read-only
	STATUS  mandatory
	DESCRIPTION
	     "Number of pages read per second * 10"
	::= { sm2PerTaskTabEntry 10 }

  END
