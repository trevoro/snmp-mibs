-------------------------------------------------------
-- Copyright 1999 - Sun Microsystems, Inc. All Rights Reserved.
--
--
-------------------------------------------------------
-- Sun Management Center
-------------------------------------------------------


NFSSTAT-SUNMANAGEMENTCENTER-MIB2 DEFINITIONS ::= BEGIN


  IMPORTS
        enterprises, MODULE-IDENTITY, OBJECT-TYPE,  Integer32
                FROM SNMPv2-SMI
         OBJECT-GROUP
                FROM SNMPv2-CONF
         DisplayString
               FROM SNMPv2-TC;


nfsstat MODULE-IDENTITY
    LAST-UPDATED "9907201505Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        "The NFS statistics mib allows to monitor information regarding client
         and server call related to both NFS and RPC."

    REVISION  "9907201505Z"
    DESCRIPTION
        "Rev 1.0  20th July 1999 15:05, Initial version Of MIB."
    ::= { modules 28 }

sun       OBJECT IDENTIFIER ::= { enterprises 42 }
prod      OBJECT IDENTIFIER ::= { sun 2 }
sunsymon  OBJECT IDENTIFIER ::= { prod 12 }
agent     OBJECT IDENTIFIER ::= { sunsymon 2 }
modules   OBJECT IDENTIFIER ::= { agent 2 }
nfsStats   OBJECT IDENTIFIER ::= { nfsstat 1 }


nfssServerRPCStatGroup OBJECT-GROUP
        OBJECTS {  nfssTotServRPCCalls, nfssServBadRPCCalls, 
		nfssServPcntBadRPCCalls, nfssServRPCCallRate }
        STATUS current
        DESCRIPTION
        "RPC server calls related statistics."
        ::= { nfsStats 1 }


nfssServerNFSStatGroup OBJECT-GROUP
        OBJECTS { nfssServTotNFSCalls, nfssServBadNFSCalls, 
		nfssServPcntBadNFSCalls, nfssServNFSCallRate }
        STATUS current
        DESCRIPTION
        "NFS server calls related statistics."
        ::= { nfsStats 2 }


nfssClientRPCStatGroup OBJECT-GROUP
        OBJECTS {  nfssCliTotRPCCalls, nfssCliBadRPCCalls, 
		nfssCliPcntBadRPCCalls, nfssCliRPCCallRate }
        STATUS current
        DESCRIPTION
        "RPC client calls related statistics."
        ::= { nfsStats 3 }


nfssClientNFSStatGroup OBJECT-GROUP
        OBJECTS {  nfssCliTotNFSCalls, nfssCliBadNFSCalls, 
		nfssCliPcntBadNFSCalls, nfssCliNFSCallRate }
        STATUS current
        DESCRIPTION
        "NFS client calls related statistics."
        ::= { nfsStats 4 }


nfssTotServRPCCalls OBJECT-TYPE
    SYNTAX      Integer32
    MAX-ACCESS  read-only
    STATUS      current
    DESCRIPTION
                "Total number of RPC server calls received by the host 
		since last init. This is the total bad or good RPC 
                server calls."
    ::= { nfssServerRPCStatGroup 1 }

nfssServBadRPCCalls OBJECT-TYPE
    SYNTAX      Integer32
    MAX-ACCESS  read-only
    STATUS      current
    DESCRIPTION
                "Number of bad RPC server calls received since last init.
		This is the total number of RPC calls rejected by 
		the RPC layer."
    ::= { nfssServerRPCStatGroup 2 }

nfssServPcntBadRPCCalls OBJECT-TYPE
    SYNTAX      DisplayString
    UNITS       "%"
    MAX-ACCESS  read-only
    STATUS      current
    DESCRIPTION
                "Bad RPC server calls as a percentage of the total RPC 
                 server calls received."
    ::= { nfssServerRPCStatGroup 3 }

nfssServRPCCallRate OBJECT-TYPE
    SYNTAX      DisplayString
    UNITS       "/sec"
    MAX-ACCESS  read-only
    STATUS      current
    DESCRIPTION
                "Rate at which server RPC calls are being received per 
                 second."
    ::= { nfssServerRPCStatGroup 4 }

nfssServTotNFSCalls OBJECT-TYPE
    SYNTAX      Integer32
    MAX-ACCESS  read-only
    STATUS      current
    DESCRIPTION
                "Total number of NFS server calls since last init.
		This is the total of bad and good NFS calls received 
		by the server host. "
    ::= { nfssServerNFSStatGroup 1 }

nfssServBadNFSCalls OBJECT-TYPE
    SYNTAX      Integer32
    MAX-ACCESS  read-only
    STATUS      current
    DESCRIPTION
                "Number of bad NFS server calls since last init.
		This is the total number of NFS calls rejected by 
		the RPC layer."

    ::= { nfssServerNFSStatGroup 2 }

nfssServPcntBadNFSCalls OBJECT-TYPE
    SYNTAX      DisplayString
    UNITS       "%"
    MAX-ACCESS  read-only
    STATUS      current
    DESCRIPTION
                "Bad NFS server calls as a percentage of the total 
                 server NFS calls received."
    ::= { nfssServerNFSStatGroup 3 }

nfssServNFSCallRate OBJECT-TYPE
    SYNTAX      DisplayString
    UNITS       "/sec"
    MAX-ACCESS  read-only
    STATUS      current
    DESCRIPTION
                "Rate at which NFS server calls are being received per 
                 second."
    ::= { nfssServerNFSStatGroup 4 }

nfssCliTotRPCCalls OBJECT-TYPE
    SYNTAX      Integer32
    MAX-ACCESS  read-only
    STATUS      current
    DESCRIPTION
                "Total number of RPC client calls made by the host since 
		last init. This is the total bad or good RPC client calls."
    ::= { nfssClientRPCStatGroup 1 }

nfssCliBadRPCCalls OBJECT-TYPE
    SYNTAX      Integer32
    MAX-ACCESS  read-only
    STATUS      current
    DESCRIPTION
                "Number of bad RPC client calls since last init. This is the
		total number of RPC calls rejected by the RPC layer."

    ::= { nfssClientRPCStatGroup 2 }

nfssCliPcntBadRPCCalls OBJECT-TYPE
    SYNTAX      DisplayString
    UNITS       "%"
    MAX-ACCESS  read-only
    STATUS      current
    DESCRIPTION
                "Bad RPC client calls as a percentage of the total RPC 
		client calls made."
    ::= { nfssClientRPCStatGroup 3 }

nfssCliRPCCallRate OBJECT-TYPE
    SYNTAX      DisplayString
    UNITS       "/sec"
    MAX-ACCESS  read-only
    STATUS      current
    DESCRIPTION
                "Rate at which RPC client calls are being made per second."
    ::= { nfssClientRPCStatGroup 4 }

nfssCliTotNFSCalls OBJECT-TYPE
    SYNTAX      Integer32
    MAX-ACCESS  read-only
    STATUS      current
    DESCRIPTION
                "Total number of NFS client calls made by the host since last init. 
		This is the total bad or good NFS calls made by host."
    ::= { nfssClientNFSStatGroup 1 }

nfssCliBadNFSCalls OBJECT-TYPE
    SYNTAX      Integer32
    MAX-ACCESS  read-only
    STATUS      current
    DESCRIPTION
                "Number of bad NFS client calls since last init. This is 
		the total number of NFS calls rejected."
    ::= { nfssClientNFSStatGroup 2 }

nfssCliPcntBadNFSCalls OBJECT-TYPE
    SYNTAX      DisplayString
    UNITS       "%"
    MAX-ACCESS  read-only
    STATUS      current
    DESCRIPTION
                "Bad NFS client calls as a percentage of the total NFS 
		client calls made."
    ::= { nfssClientNFSStatGroup 3 }

nfssCliNFSCallRate OBJECT-TYPE
    SYNTAX      DisplayString
    UNITS       "/sec"
    MAX-ACCESS  read-only
    STATUS      current
    DESCRIPTION
                "Rate at which NFS client calls are being made per second."
    ::= { nfssClientNFSStatGroup 4 }
END
