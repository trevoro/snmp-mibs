INCOGNITO-MIB DEFINITIONS ::= BEGIN

IMPORTS
	enterprises,
	MODULE-IDENTITY,
	OBJECT-IDENTITY
		FROM SNMPv2-SMI;

incognito MODULE-IDENTITY
	LAST-UPDATED "200304151442Z"
	ORGANIZATION "Incognito Software Inc."
	CONTACT-INFO
		"Incognito Software Inc.
		Customer Service

		Postal:
		    1128 Hornby St.
		    Vancouver, BC, Canada
		    V6Z 2L4

		Tel: +1 604-688-4332
		Fax: +1 604-688-4339

		E-Mail: support@incognito.com"
	DESCRIPTION
		"The root of the OID sub-tree assigned to
		Incognito Software Inc. by the Internet
		Assigned Numbers Authority (IANA)."
	::= { enterprises 3606 }


incognitoSNMPObjects OBJECT-IDENTITY
	STATUS obsolete
	DESCRIPTION
		"This sub-tree was used in earlier revisions of software and is no longer used."
	::= { incognito 1 }

incognitoReg OBJECT-IDENTITY
	STATUS current
	DESCRIPTION
		"Sub-tree for registrations"
	::= { incognito 2 }

incognitoGeneric OBJECT-IDENTITY
	STATUS current
	DESCRIPTION
		"Sub-tree for common object and event definitions"
	::= { incognito 3 }

incognitoProducts OBJECT-IDENTITY
	STATUS current
	DESCRIPTION
		"Sub-tree for specific object and event definitions"
	::= { incognito 4 }

incognitoCaps OBJECT-IDENTITY
	STATUS current
	DESCRIPTION
		"Sub-tree for agent profiles"
	::= { incognito 5 }

incognitoReqs OBJECT-IDENTITY
	STATUS current
	DESCRIPTION
		"Sub-tree for management application requirements"
	::= { incognito 6 }

incognitoExpr OBJECT-IDENTITY
	STATUS current
	DESCRIPTION
		"Sub-tree for experimental definitions"
	::= { incognito 7 }

END
