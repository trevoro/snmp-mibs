Nortel-Magellan-Passport-FrameRelayIsdnMIB
DEFINITIONS ::= BEGIN



IMPORTS

      OBJECT-TYPE
   FROM RFC-1212

      passportMIBs
   FROM Nortel-Magellan-Passport-UsefulDefinitionsMIB

      Counter32,
      DisplayString,
      StorageType,
      RowStatus,
      Unsigned32
   FROM Nortel-Magellan-Passport-StandardTextualConventionsMIB

      NonReplicated,
      DigitString
   FROM Nortel-Magellan-Passport-TextualConventionsMIB

      frUniIndex,
      frUni
   FROM Nortel-Magellan-Passport-FrameRelayUniMIB;




-- LAST-UPDATED   "9711240000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayIsdn Enterprise MIB."

frameRelayIsdnMIB OBJECT IDENTIFIER ::= { passportMIBs 122 }










-- FrUni/n Isdn
-- This component defines the parameters associated with the ISDN B-
-- Channel interface. Adding this component makes the FrUni 
-- behaves as an ISDN access to the Frame Relay Network.

frUniIsdn OBJECT IDENTIFIER ::= { frUni 100 }



frUniIsdnRowStatusTable OBJECT-TYPE
   SYNTAX     SEQUENCE OF FrUniIsdnRowStatusEntry
   ACCESS     not-accessible
   STATUS     mandatory
   DESCRIPTION
     "This entry controls the addition and deletion of 
      frUniIsdn components."
::= { frUniIsdn 1 }

frUniIsdnRowStatusEntry OBJECT-TYPE
   SYNTAX     FrUniIsdnRowStatusEntry
   ACCESS     not-accessible
   STATUS     mandatory
   DESCRIPTION
     "A single entry in the table represents a single 
      frUniIsdn component."
   INDEX {
      frUniIndex,
      frUniIsdnIndex }
::= { frUniIsdnRowStatusTable 1 }

FrUniIsdnRowStatusEntry ::= SEQUENCE {
   frUniIsdnRowStatus
      RowStatus,
   frUniIsdnComponentName
      DisplayString,
   frUniIsdnStorageType
      StorageType,
   frUniIsdnIndex
      NonReplicated }

frUniIsdnRowStatus OBJECT-TYPE
   SYNTAX     RowStatus 
   ACCESS     read-write
   STATUS     mandatory
   DESCRIPTION
     "This variable is used as the basis for SNMP naming of
      frUniIsdn components.
      These components can be added and deleted."
::= { frUniIsdnRowStatusEntry 1 }

frUniIsdnComponentName OBJECT-TYPE
   SYNTAX     DisplayString 
   ACCESS     read-only
   STATUS     mandatory
   DESCRIPTION
     "This variable provides the component's string name for
      use with the ASCII Console Interface"
::= { frUniIsdnRowStatusEntry 2 }

frUniIsdnStorageType OBJECT-TYPE
   SYNTAX     StorageType 
   ACCESS     read-only
   STATUS     mandatory
   DESCRIPTION
     "This variable represents the storage type value for the
      frUniIsdn tables."
::= { frUniIsdnRowStatusEntry 4 }

frUniIsdnIndex OBJECT-TYPE
   SYNTAX     NonReplicated 
   ACCESS     not-accessible
   STATUS     mandatory
   DESCRIPTION
     "This variable represents the index for the frUniIsdn tables."
::= { frUniIsdnRowStatusEntry 10 }

frUniIsdnProvTable OBJECT-TYPE
   SYNTAX     SEQUENCE OF FrUniIsdnProvEntry
   ACCESS     not-accessible
   STATUS     mandatory
   DESCRIPTION
     "This group contains the provisionable attributes of the Isdn 
      component."
::= { frUniIsdn 11 }

frUniIsdnProvEntry OBJECT-TYPE
   SYNTAX     FrUniIsdnProvEntry
   ACCESS     not-accessible
   STATUS     mandatory
   DESCRIPTION
     "An entry in the frUniIsdnProvTable."
   INDEX {
      frUniIndex,
      frUniIsdnIndex }
::= { frUniIsdnProvTable 1 }

FrUniIsdnProvEntry ::= SEQUENCE {
   frUniIsdnT320
      Unsigned32,
   frUniIsdnAddressSignalling
      INTEGER }

frUniIsdnT320 OBJECT-TYPE
   SYNTAX     Unsigned32 (0..255)
   ACCESS     read-write
   STATUS     mandatory
   DESCRIPTION
     "This attribute specifies the waiting time for a silent 
      B-Channel (no active VCs associated with the FrUni) to be 
      disconnected and made available. Default is 60 seconds. 0 means 
      t320 will never timeout."
   DEFVAL     { 60 }
::= { frUniIsdnProvEntry 1 }

frUniIsdnAddressSignalling OBJECT-TYPE
   SYNTAX     INTEGER  {
                 isdnDna(0),
                 normalBehavior(1) }
   ACCESS     read-write
   STATUS     mandatory
   DESCRIPTION
     "This attribute defines whether the ISDN Calling Party Number is to 
      be signalled to the remote DTE during an SVC call establishment. 
      Otherwise, no changes to the current behavior of SVC call 
      establishement (i.e., Passport Dna is used in the calling party 
      number information element)."
   DEFVAL     { normalBehavior }
::= { frUniIsdnProvEntry 2 }

frUniIsdnOperTable OBJECT-TYPE
   SYNTAX     SEQUENCE OF FrUniIsdnOperEntry
   ACCESS     not-accessible
   STATUS     mandatory
   DESCRIPTION
     "This group contains the operational attributes of the Isdn 
      component."
::= { frUniIsdn 12 }

frUniIsdnOperEntry OBJECT-TYPE
   SYNTAX     FrUniIsdnOperEntry
   ACCESS     not-accessible
   STATUS     mandatory
   DESCRIPTION
     "An entry in the frUniIsdnOperTable."
   INDEX {
      frUniIndex,
      frUniIsdnIndex }
::= { frUniIsdnOperTable 1 }

FrUniIsdnOperEntry ::= SEQUENCE {
   frUniIsdnDataSigChan
      INTEGER,
   frUniIsdnBChannelState
      INTEGER,
   frUniIsdnLastUsedCgpn
      DigitString,
   frUniIsdnBChanIntState
      INTEGER,
   frUniIsdnActiveVirtualCircuitsCount
      Counter32 }

frUniIsdnDataSigChan OBJECT-TYPE
   SYNTAX     INTEGER (1..255)
   ACCESS     read-only
   STATUS     mandatory
   DESCRIPTION
     "This attribute indicates the instance number of the dataSigChan 
      component controlling the allocation of this FrUni Isdn component."
::= { frUniIsdnOperEntry 1 }

frUniIsdnBChannelState OBJECT-TYPE
   SYNTAX     INTEGER  {
                 idle(0),
                 busy(1),
                 disabled(2) }
   ACCESS     read-only
   STATUS     mandatory
   DESCRIPTION
     "This attribute indicates the state of the B-Channel. If the value is 
      idle it means that no VCs are connected and this B-Channel is 
      available. If the value is busy it means this B-Channel has been 
      allocated and is not available. If the value is disabled it means the 
      application interface or the port is locked or disabled."
::= { frUniIsdnOperEntry 2 }

frUniIsdnLastUsedCgpn OBJECT-TYPE
   SYNTAX     DigitString (SIZE (0..15))
   ACCESS     read-only
   STATUS     mandatory
   DESCRIPTION
     "This attribute indicates the calling party number currently using
      the B-Channel. When the B-Channel is free, the null string is 
      displayed."
::= { frUniIsdnOperEntry 3 }

frUniIsdnBChanIntState OBJECT-TYPE
   SYNTAX     INTEGER  {
                 isdnInit(0),
                 waitAccEnable(1),
                 waitLnsResponse(2),
                 waitFramerData(3),
                 enabling(4),
                 waitAccRegAck(5),
                 up(6),
                 down(7),
                 releasing(8) }
   ACCESS     read-only
   STATUS     mandatory
   DESCRIPTION
     "Debug information"
::= { frUniIsdnOperEntry 4 }

frUniIsdnActiveVirtualCircuitsCount OBJECT-TYPE
   SYNTAX     Counter32 
   ACCESS     read-only
   STATUS     mandatory
   DESCRIPTION
     "Current number of virtual circuits (switched and permanent) in data 
      transfer."
::= { frUniIsdnOperEntry 5 }




-- 
-- Version and Compliance statements
-- 



-- Object-Group Statement:
-- A list of all current accessible leaf objects.

-- OBJECTS { frUniIsdnAddressSignalling,
--           frUniIsdnDataSigChan,
--           frUniIsdnBChannelState,
--           frUniIsdnComponentName,
--           frUniIsdnBChanIntState,
--           frUniIsdnLastUsedCgpn,
--           frUniIsdnActiveVirtualCircuitsCount,
--           frUniIsdnStorageType,
--           frUniIsdnRowStatus,
--           frUniIsdnT320 }
-- STATUS  mandatory
-- DESCRIPTION
--   "A list of all current accessible leaf objects."

frameRelayIsdnGroup OBJECT IDENTIFIER ::= { frameRelayIsdnMIB 1 }
frameRelayIsdnGroupBD OBJECT IDENTIFIER ::= { frameRelayIsdnGroup 4 }
frameRelayIsdnGroupBD02 OBJECT IDENTIFIER ::= { frameRelayIsdnGroupBD 3 }
frameRelayIsdnGroupBD02A OBJECT IDENTIFIER ::= { frameRelayIsdnGroupBD02 2 }



-- Agent-Capabilities Statement:

-- PRODUCT-RELEASE "Passport Release 7.0 FrameRelayIsdn."
-- STATUS          mandatory
-- DESCRIPTION     "FrameRelayIsdn MIB: MIB Version BD02A,
--                  Software Version BG00S4C."
-- SUPPORTS        Nortel-Magellan-Passport-FrameRelayIsdnMIB
--    INCLUDES     { frameRelayIsdnGroupBD02A }

frameRelayIsdnCapabilities OBJECT IDENTIFIER ::= { frameRelayIsdnMIB 3 }
frameRelayIsdnCapabilitiesBD OBJECT IDENTIFIER ::= { frameRelayIsdnCapabilities 4 }
frameRelayIsdnCapabilitiesBD02 OBJECT IDENTIFIER ::= { frameRelayIsdnCapabilitiesBD 3 }
frameRelayIsdnCapabilitiesBD02A OBJECT IDENTIFIER ::= { frameRelayIsdnCapabilitiesBD02 2 }





END
