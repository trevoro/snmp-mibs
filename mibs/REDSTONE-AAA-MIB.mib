-- *****************************************************************
-- REDSTONE-AAA-MIB
--
-- Redstone Communications Inc. Enterprise MIB
-- Authentication/Authorization/Accounting MIB
--
-- Copyright 1999 Redstone Communications, Incorporated.
-- All Rights Reserved.
-- *****************************************************************

REDSTONE-AAA-MIB DEFINITIONS ::= BEGIN

IMPORTS
	TEXTUAL-CONVENTION FROM SNMPv2-TC
    MODULE-IDENTITY, 
    OBJECT-TYPE,
    Integer32,
    IpAddress
        FROM SNMPv2-SMI

    DisplayString,
    RowStatus
        FROM SNMPv2-TC

    MODULE-COMPLIANCE, 
    OBJECT-GROUP  
        FROM SNMPv2-CONF

    rsMgmt
		FROM REDSTONE-SMI

    RsName
        FROM REDSTONE-TC;


rsAaaMIB MODULE-IDENTITY
    LAST-UPDATED "9906010000Z"
    ORGANIZATION "Redstone Communications Inc."
	CONTACT-INFO
        "
        Redstone Communications, Inc.
		5 Carlisle Road
        Westford MA 01886
        USA
        Tel:    +1-978-692-1999
		Email:  mib@redstonecom.com
        "
	DESCRIPTION
		"The AAA MIB for the
		Redstone Communications Inc. enterprise."
	REVISION      "9906010000Z"
	DESCRIPTION
		"Initial version of this MIB module."
    ::= { rsMgmt 20 }


-- ++++++++++++++++++++++++++++++++++++++++++++++++++++++++++++++++++++++
-- Textual conventions
-- ++++++++++++++++++++++++++++++++++++++++++++++++++++++++++++++++++++++

RsAaaDomainName ::= TEXTUAL-CONVENTION
    STATUS      current
    DESCRIPTION
        "The name of an internet domain."
    SYNTAX      DisplayString(SIZE(1..63))


-- ++++++++++++++++++++++++++++++++++++++++++++++++++++++++++++++++++++++
-- Managed object groups
-- ++++++++++++++++++++++++++++++++++++++++++++++++++++++++++++++++++++++

rsAaaObjects                OBJECT IDENTIFIER ::= {rsAaaMIB 1}

-- Functional groups

rsAaaAssignment             OBJECT IDENTIFIER ::= {rsAaaObjects 1}
rsAaaAuthentication         OBJECT IDENTIFIER ::= {rsAaaObjects 2}
rsAaaAccounting             OBJECT IDENTIFIER ::= {rsAaaObjects 3}
rsAaaAddress                OBJECT IDENTIFIER ::= {rsAaaObjects 4}



-- ++++++++++++++++++++++++++++++++++++++++++++++++++++++++++++++++++++++
-- Managed objects for Assignment functions
-- ++++++++++++++++++++++++++++++++++++++++++++++++++++++++++++++++++++++

rsAaaAssignGeneral          OBJECT IDENTIFIER ::= {rsAaaAssignment 1}

rsAaaAssignBrasLicense OBJECT-TYPE
    SYNTAX      DisplayString(SIZE(0..16))
    MAX-ACCESS  read-write
    STATUS      current
    DESCRIPTION
        "The license string that determines the system-wide maximum number 
        of remote user connections allowed. A zero-length string (no license)
        prohibits remote user connections."
    ::= { rsAaaAssignGeneral 1 }

rsAaaAssignBrasLicensedUsers OBJECT-TYPE
    SYNTAX      Integer32
    MAX-ACCESS  read-only
    STATUS      current
    DESCRIPTION
        "The system-wide maximum number of remote user connections allowed by the 
        currently configured license string."
    ::= { rsAaaAssignGeneral 2 }

rsAaaAssignDomain           OBJECT IDENTIFIER ::= {rsAaaAssignment 2}

rsAaaAssignDomainTable OBJECT-TYPE
    SYNTAX      SEQUENCE OF RsAaaAssignDomainEntry
    MAX-ACCESS  not-accessible
    STATUS      current
    DESCRIPTION
        "The entries in this table specify the assignment of a remote access user
        to a virtual router, based on the user's domain."
    ::= { rsAaaAssignDomain 1 }

rsAaaAssignDomainEntry OBJECT-TYPE
    SYNTAX      RsAaaAssignDomainEntry
    MAX-ACCESS  not-accessible
    STATUS      current
    DESCRIPTION
        "A specification of the virtual router to which users on a specified 
        domain should be assigned."
    INDEX { IMPLIED rsAaaAssignDomainName }
    ::= { rsAaaAssignDomainTable 1 }

RsAaaAssignDomainEntry ::= SEQUENCE {
    rsAaaAssignDomainName               RsAaaDomainName,
    rsAaaAssignDomainRowStatus          RowStatus,
    rsAaaAssignDomainRouterName         RsName,
    rsAaaAssignDomainLoopback           Integer32
}

rsAaaAssignDomainName OBJECT-TYPE
    SYNTAX      RsAaaDomainName
    MAX-ACCESS  read-only
    STATUS      current
    DESCRIPTION
        "The domain name uniquely identifying this entry."
    ::= { rsAaaAssignDomainEntry 1 }

rsAaaAssignDomainRowStatus OBJECT-TYPE
    SYNTAX      RowStatus
    MAX-ACCESS  read-create
    STATUS      current
    DESCRIPTION
        "Controls creation/deletion of entries in this table.
        Only the values 'createAndGo' and 'destroy' may be SET."
    ::= { rsAaaAssignDomainEntry 2 }

rsAaaAssignDomainRouterName OBJECT-TYPE
    SYNTAX      RsName
    MAX-ACCESS  read-create
    STATUS      current
    DESCRIPTION
        "The name of the virtual router to which remote access users within this
        domain are assigned."
    ::= { rsAaaAssignDomainEntry 3 }

rsAaaAssignDomainLoopback OBJECT-TYPE
    SYNTAX      Integer32(-1..32000)
    MAX-ACCESS  read-create
    STATUS      current
    DESCRIPTION
        "The number of the loopback interface, associated with the specified
        virtual router, whose IP address is used as the source address when 
        transmitting IP packets on unnumbered remote access user links.

        For example, if the associated loopback interface for this domain/router
        was configured via the console as 'loopback 2', this object 
        would contain the integer value 2.

        A value of -1 indicates the loopback interface is unspecified."
    ::= { rsAaaAssignDomainEntry 4 }



-- ++++++++++++++++++++++++++++++++++++++++++++++++++++++++++++++++++++++
-- Managed objects for Authentication functions
-- ++++++++++++++++++++++++++++++++++++++++++++++++++++++++++++++++++++++

rsAaaAuthGeneral            OBJECT IDENTIFIER ::= {rsAaaAuthentication 1}

-- ++++++++++++++++++++++++++++++++++++++++++++++++++++++++++++++++++++++
-- Managed objects for Accounting functions
-- ++++++++++++++++++++++++++++++++++++++++++++++++++++++++++++++++++++++

rsAaaAcctGeneral            OBJECT IDENTIFIER ::= {rsAaaAccounting 1}

rsAaaAcctInterval OBJECT-TYPE
    SYNTAX      Integer32(0 | 600..64800)
    UNITS       "seconds"
    MAX-ACCESS  read-write
    STATUS      current
    DESCRIPTION
        "The interval that must elapse between generation of 
        accounting reports, ranging from 10 minutes to 18 hours,
        or disabled if set to zero."
    ::= { rsAaaAcctGeneral 1 }

rsAaaAcctDupServerRouterName OBJECT-TYPE
    SYNTAX      RsName
    MAX-ACCESS  read-write
    STATUS      current
    DESCRIPTION
        "The name of another router on this system to which
        accounting reports should be sent, in addition to or
        instead of sending accounting reports to the accounting 
        service (if any) configured on the current router (i.e.
        the router context within which this object instance
        exists).

        A zero-length name disables this mechanism."
    ::= { rsAaaAcctGeneral 2 }

-- ++++++++++++++++++++++++++++++++++++++++++++++++++++++++++++++++++++++
-- Managed objects for Address functions
-- ++++++++++++++++++++++++++++++++++++++++++++++++++++++++++++++++++++++

rsAaaAddrGeneral            OBJECT IDENTIFIER ::= {rsAaaAddress 1}

rsAaaAddrPoolDefault OBJECT-TYPE
    SYNTAX      INTEGER {
                    none(0),
                    local(1)
                }
    MAX-ACCESS  read-write
    STATUS      current
    DESCRIPTION
        "Identifies the default source of IP address allocation
        for remote access links:

        none        No address source is specified.   
        local       Use the local address pool named 'default'."
    ::= { rsAaaAddrGeneral 1 }


rsAaaAddrNameServer         OBJECT IDENTIFIER ::= {rsAaaAddress 2}

rsAaaAddrDns                OBJECT IDENTIFIER ::= {rsAaaAddrNameServer 1}
rsAaaAddrWins               OBJECT IDENTIFIER ::= {rsAaaAddrNameServer 2}

rsAaaAddrDnsPrimary OBJECT-TYPE
    SYNTAX      IpAddress
    MAX-ACCESS  read-write
    STATUS      current
    DESCRIPTION
        "The IP address of the primary DNS server to be used by remote
        access clients. A value of 0.0.0.0 indicates no server is configured."
    ::= { rsAaaAddrDns 1 }

rsAaaAddrDnsSecondary OBJECT-TYPE
    SYNTAX      IpAddress
    MAX-ACCESS  read-write
    STATUS      current
    DESCRIPTION
        "The IP address of the secondary DNS server to be used by remote
        access clients. A value of 0.0.0.0 indicates no server is configured."
    ::= { rsAaaAddrDns 2 }

rsAaaAddrWinsPrimary OBJECT-TYPE
    SYNTAX      IpAddress
    MAX-ACCESS  read-write
    STATUS      current
    DESCRIPTION
        "The IP address of the primary WINS server to be used by remote
        access clients. A value of 0.0.0.0 indicates no server is configured."
    ::= { rsAaaAddrWins 1 }

rsAaaAddrWinsSecondary OBJECT-TYPE
    SYNTAX      IpAddress
    MAX-ACCESS  read-write
    STATUS      current
    DESCRIPTION
        "The IP address of the secondary WINS server to be used by remote
        access clients. A value of 0.0.0.0 indicates no server is configured."
    ::= { rsAaaAddrWins 2 }


-- ++++++++++++++++++++++++++++++++++++++++++++++++++++++++++++++++++++++
-- Notification control objects
-- ++++++++++++++++++++++++++++++++++++++++++++++++++++++++++++++++++++++

-- No notifications are defined in this MIB. Placeholder follows.

-- rsAaaTrapControl      OBJECT IDENTIFIER ::= { rsAaaMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsAaaTraps            OBJECT IDENTIFIER ::= { rsAaaMIB 3 }
-- rsAaaTrapPrefix       OBJECT IDENTIFIER ::= { rsAaaTraps 0 }



-- ++++++++++++++++++++++++++++++++++++++++++++++++++++++++++++++++++++++
-- Conformance information
-- ++++++++++++++++++++++++++++++++++++++++++++++++++++++++++++++++++++++

rsAaaMIBConformance
             OBJECT IDENTIFIER ::= { rsAaaMIB 4 }
rsAaaMIBCompliances
             OBJECT IDENTIFIER ::= { rsAaaMIBConformance 1 }
rsAaaMIBGroups
             OBJECT IDENTIFIER ::= { rsAaaMIBConformance 2 }


-- compliance statements

rsAaaCompliance MODULE-COMPLIANCE
    STATUS      current
    DESCRIPTION
        "The compliance statement for systems supporting DNS."
    MODULE  -- this module
    MANDATORY-GROUPS { rsAaaGroup }
    ::= { rsAaaMIBCompliances 1 }


-- units of conformance

rsAaaGroup OBJECT-GROUP
    OBJECTS {
        rsAaaAssignBrasLicense,
        rsAaaAssignBrasLicensedUsers,
        rsAaaAssignDomainName,
        rsAaaAssignDomainRowStatus,
        rsAaaAssignDomainRouterName,
        rsAaaAssignDomainLoopback,

        rsAaaAcctInterval,
        rsAaaAcctDupServerRouterName,

        rsAaaAddrPoolDefault,
        rsAaaAddrDnsPrimary,
        rsAaaAddrDnsSecondary,
        rsAaaAddrWinsPrimary,
        rsAaaAddrWinsSecondary
    }
    STATUS      current
    DESCRIPTION
        "The basic collection of objects providing management
        of AAA functionality in a Redstone product."
    ::= { rsAaaMIBGroups 1 }

END
