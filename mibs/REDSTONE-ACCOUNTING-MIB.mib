-- *****************************************************************
-- REDSTONE-ACCOUNTING-MIB
--
-- Redstone Communications Inc. Enterprise MIB
-- Accounting MIB
--
-- Copyright 1999 Redstone Communications, Incorporated.
-- All Rights Reserved.
--
-- This MIB augments the MIB specified in RFC2513 - Connection 
-- Oriented Accounting MIB.
-- *****************************************************************

REDSTONE-ACCOUNTING-MIB DEFINITIONS ::= BEGIN

IMPORTS
    MODULE-IDENTITY, OBJECT-TYPE, Integer32
                                                  FROM SNMPv2-SMI
    
    MODULE-COMPLIANCE, OBJECT-GROUP
                                                  FROM SNMPv2-CONF
    RowStatus                                     FROM SNMPv2-TC
    acctngSelectionEntry, acctngFileEntry	  FROM ACCOUNTING-CONTROL-MIB
    rsMgmt                                        FROM REDSTONE-SMI
    rsIfType                                      FROM REDSTONE-IF-MIB
    RsAcctngOperType, RsAcctngAdminType           FROM REDSTONE-TC;

rsAcctngMIB  MODULE-IDENTITY
        LAST-UPDATED "9903120000Z"
        ORGANIZATION "Redstone Communications, Inc."
        CONTACT-INFO
        "
        Redstone Communications, Inc.
                5 Carlisle Road
        Westford MA 01886
        USA
        Tel:    +1-978-692-1999
                Email:  mib@redstonecom.com
        "
        DESCRIPTION
                "The accounting MIB for the
                Redstone Communications Inc. enterprise."
        REVISION      "9901010000Z"
        DESCRIPTION
                "Initial version of this MIB module."
    ::= { rsMgmt 24 }

-- ++++++++++++++++++++++++++++++++++++++++++++++++++++++++++++++++++++++
-- Textual conventions
-- ++++++++++++++++++++++++++++++++++++++++++++++++++++++++++++++++++++++

-- +++++++++++++++++++++++++++++++++++++++++++++++++++++++++++++++++++++
-- MIB Structure 
--
-- +++++++++++++++++++++++++++++++++++++++++++++++++++++++++++++++++++++

rsAcctngMIBObjects       OBJECT IDENTIFIER ::= { rsAcctngMIB 1 }

rsAcctngSelectionControl OBJECT IDENTIFIER ::= { rsAcctngMIBObjects 1 }
rsAcctngFileControl      OBJECT IDENTIFIER ::= { rsAcctngMIBObjects 2 }
rsAcctngInterfaceControl OBJECT IDENTIFIER ::= { rsAcctngMIBObjects 3 }

-- ++++++++++++++++++++++++++++++++++++++++++++++++++++++++++++++++++++
-- MIB Objects
-- +++++++++++++++++++++++++++++++++++++++++++++++++++++++++++++++++++

-- The Accounting Information Selection table

rsAcctngSelectionTable OBJECT-TYPE
    SYNTAX      SEQUENCE OF RsAcctngSelectionEntry
    MAX-ACCESS  not-accessible
    STATUS      current
    DESCRIPTION
            "A list of accounting information selection entries.

            Note that additions, modifications and deletions of entries
            in this table can occur at any time, but such changes only
            take effect on the next occasion when collection begins into
            a new file.  Thus, between modification and the next 'swap',
            the content of this table does not reflect the current
            selection."
    ::= { rsAcctngSelectionControl 1 }

rsAcctngSelectionEntry OBJECT-TYPE
    SYNTAX      RsAcctngSelectionEntry
    MAX-ACCESS  not-accessible
    STATUS      current
    DESCRIPTION
            "An entry used to extend the the selection entry in  
            acctngSelectionEntry.  This conceptual row extension is
            used for Redstone accounting extensions for connectionless
            data collection."  
    AUGMENTS   { acctngSelectionEntry }
    ::= { rsAcctngSelectionTable 1 }

RsAcctngSelectionEntry ::=
    SEQUENCE {
        rsAcctngSelectionType	BITS,
	rsAcctngSelectionMode	INTEGER	
    }

rsAcctngSelectionType OBJECT-TYPE
    SYNTAX      BITS { ietfAccountControl(0),
                       connectionLessLayer2(1) }
    MAX-ACCESS  read-create
    STATUS      current
    DESCRIPTION
            "Indicates the types of connections for which the
            information selected by this entry are to be collected.
            The ietfAccountControl(0) bit position indicates that the
            acctngSelectionType in the base conceptual row determines
            the selection type.  All other bit positions for this object
            over-ride the acctngSelectionType in the base conceptual
            row." 
    ::= { rsAcctngSelectionEntry 1 }

rsAcctngSelectionMode OBJECT-TYPE
    SYNTAX      INTEGER { absoluteCounterValues(1),
                          deltaCounterValues(2) }
    MAX-ACCESS  read-create
    STATUS      current
    DESCRIPTION
            "Indicates the data collection mode."
    DEFVAL { deltaCounterValues }
    ::= { rsAcctngSelectionEntry 2 }


-- The Accounting File Table

rsAcctngFileTable OBJECT-TYPE
    SYNTAX      SEQUENCE OF RsAcctngFileEntry
    MAX-ACCESS  not-accessible
    STATUS      current
    DESCRIPTION
            "A unique value identifying the file transfer behavior 
             and the the file to where accounting data is to be stored."
    ::= { rsAcctngFileControl 1 }

rsAcctngFileEntry OBJECT-TYPE
    SYNTAX      RsAcctngFileEntry
    MAX-ACCESS  not-accessible
    STATUS      current
    DESCRIPTION
            "An entry used to extend the file management of   
            acctngFileEntry.  This conceptual row extension is
            used for Redstone accounting extensions to automate
            the transfer of accounting data to remote hosts."
    AUGMENTS   { acctngFileEntry }
    ::= { rsAcctngFileTable 1 }

RsAcctngFileEntry ::=
    SEQUENCE {
        rsAcctngFileXferMode	        INTEGER,
	rsAcctngFileXferIndex		INTEGER,
	rsAcctngFileXferSecondaryIndex  INTEGER
    }

rsAcctngFileXferMode OBJECT-TYPE
    SYNTAX    INTEGER   { rsAcctngManualTransfer(1),
                          rsAcctngAutomatedTransfer(2),
			  rsAcctngTransferOnFileFull(3),
                          rsAcctngRedundantTransfer(4) }
    MAX-ACCESS  read-create
    STATUS      current
    DESCRIPTION
            "Indicates the mode to use for transfering accounting
	     data to remote client.

		rsAcctngManualTransfer
		Administrator is responsible for manually transfering
		collected accounting data off of the system.

		rsAcctngAutomatedTransfer
		The agent will automatically transfer the collected
		accounting data based at a rsAcctngFileXferIntervals
		using an entry in the rsFileXferTable pointed to by
		rsAcctngFileXferIndex. If a manager sets this object
                to this value, a corresponding row in the rsFileXferTable
                must exist, otherwise the set command will fail.

		rsActngTransferOnFileFull
		The agent will automatically transfer the collected
		accounting data when the file reaches the maximum
		size defined by acctngFileMaximumSize.  If a manager sets
                this object to this value, a corresponding row in the
                rsFileXferTable must exist, otherwise the set command
                will fail.

                rsAcctngRedundantTransfer
                The agent will automatically transfer two copies of the 
                accounting data based on the rsAcctngFileXferInterval.
                One copy will go to the rsFileXferTable entry identified
                by rsAcctngFileXferIndex and one copy will go the the
                rsFileXferTable entry identified by rsAcctngFileXferSecondaryIndex" 
    DEFVAL {rsAcctngManualTransfer }     
    ::= { rsAcctngFileEntry 1 }

rsAcctngFileXferIndex OBJECT-TYPE
    SYNTAX      INTEGER 
    MAX-ACCESS  read-create
    STATUS      current
    DESCRIPTION
            "Identifies an entry in the rsFileXferTable, which defines
 	     the file transfer parameters to use when the agent is
	     configured to automatically transfer collected accounting
	     data files. A set to this object will fail if a corresponding
             entry in the rsFileXferTable does not exist or it is not
	     set to rsFileXferAcctngStatistics. " 
    ::= { rsAcctngFileEntry 2 }

rsAcctngFileXferSecondaryIndex OBJECT-TYPE
    SYNTAX      INTEGER 
    MAX-ACCESS  read-create
    STATUS      current
    DESCRIPTION
            "Identifies a backup or secondary entry in the rsFileXferTable,
             which defines the file transfer parameters to use when the agent is
	     configured to automatically transfer collected accounting
	     data files. A set to this object will fail if a corresponding
             entry in the rsFileXferTable does not exist or it is not
	     set to rsFileXferAcctngStatistics. " 
    ::= { rsAcctngFileEntry 3 }
--  Per-interface Type Control Table

rsAcctngInterfaceTable OBJECT-TYPE
    SYNTAX      SEQUENCE OF RsAcctngInterfaceEntry
    MAX-ACCESS  not-accessible
    STATUS      current
    DESCRIPTION
            "A table controlling the collection of accounting data on
            specific interfaces types.  This table provides an efficient
            mechanism to enable and/or disable data collection on
            all interfaces of a specified type."
    ::= { rsAcctngInterfaceControl 1 }

rsAcctngInterfaceEntry OBJECT-TYPE
    SYNTAX      RsAcctngInterfaceEntry
    MAX-ACCESS  not-accessible
    STATUS      current
    DESCRIPTION
            "An entry which controls whether accounting data is to be
            collected on interfaces of a specific type." 
    INDEX   { rsIfType }
    ::= { rsAcctngInterfaceTable 1 }

RsAcctngInterfaceEntry ::=
    SEQUENCE {
        rsAcctngInterfaceAdminStatus    RsAcctngAdminType, 
        rsAcctngInterfaceOperStatus     RsAcctngOperType,
        rsAcctngInterfaceRowStatus      RowStatus 
    }

rsAcctngInterfaceAdminStatus OBJECT-TYPE
    SYNTAX      RsAcctngAdminType 
    MAX-ACCESS  read-write
    STATUS      current
    DESCRIPTION
            "The desired administrative state for accounting data
            collection for interfaces defined by the type of this entry.
            The administrative scope is for all interfaces of the type
            defined by the corresponding rsIfType for this entry."
    ::= { rsAcctngInterfaceEntry 1 }

rsAcctngInterfaceOperStatus OBJECT-TYPE
    SYNTAX      RsAcctngOperType 
    MAX-ACCESS  read-only
    STATUS      current
    DESCRIPTION
             "The operational state for accounting data collection
             on for all interfaces corresponding to this entries type."
    ::= { rsAcctngInterfaceEntry 2 }

rsAcctngInterfaceRowStatus OBJECT-TYPE
    SYNTAX      RowStatus 
    MAX-ACCESS  read-write
    STATUS      current
    DESCRIPTION
             "Controls creation/deletion of entries in this table."
    ::= { rsAcctngInterfaceEntry 3 }


-- conformance information

rsAcctngConformance OBJECT IDENTIFIER ::= { rsAcctngMIB 3 }
rsAcctngGroups      OBJECT IDENTIFIER ::= { rsAcctngConformance 1 }
rsAcctngCompliances OBJECT IDENTIFIER ::= { rsAcctngConformance 2 }

rsAcctngCompliance MODULE-COMPLIANCE
    STATUS  current
    DESCRIPTION
            "The compliance statement for switches which implement the
            RedStone Accounting Control MIB."
    MODULE  -- this module
        MANDATORY-GROUPS { rsAcctngBasicGroup }

        OBJECT      rsAcctngSelectionType
        MIN-ACCESS  read-only
        DESCRIPTION "Write access is required.  When the value of this
                     object over-rides the the acctngSelectionType in
                     the IETF accountingControlMIB, the following objects
                     in that MIB has no meaning: 
                      
                             acctngFileCollectFailedAttempts
			     acctngFileMinAge

                    because they control or are related to connection
                    oriented accounting." 
    ::= { rsAcctngCompliances 1 }


-- units of conformance

rsAcctngBasicGroup    OBJECT-GROUP
    OBJECTS { rsAcctngSelectionType,
              rsAcctngSelectionMode,
              rsAcctngFileXferMode,
	      rsAcctngFileXferIndex,
              rsAcctngInterfaceAdminStatus,
              rsAcctngInterfaceOperStatus }
    STATUS  current
    DESCRIPTION
            "A collection of objects providing control of the basic
            collection of accounting data for connection-less
            networks."
    ::= { rsAcctngGroups 1 }

END
