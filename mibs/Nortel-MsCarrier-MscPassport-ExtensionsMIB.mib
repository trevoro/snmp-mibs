Nortel-MsCarrier-MscPassport-ExtensionsMIB
DEFINITIONS ::= BEGIN

IMPORTS


      OBJECT-TYPE
   FROM RFC-1212

      RowPointer
   FROM Nortel-MsCarrier-MscPassport-StandardTextualConventionsMIB

      mscComponents, mscPassportMIBs
   FROM Nortel-MsCarrier-MscPassport-UsefulDefinitionsMIB

      ifIndex
   FROM RFC1213-MIB;

-- LAST-UPDATED "9907300000Z"
-- ORGANIZATION "Nortel Networks"
-- CONTACT-INFO "
--         Nortel Carrier Data Network Management
--
--         Postal:       P.O. Box 3511, Station C
--                       Ottawa, Ontario
--                       Canada  K1Y 4H7
--
--         via the WEB:  http://www.nortelnetworks.com
--                       select 'Contact Us' from the menu
--
--         via phone:    1-800-4NORTEL"

-- DESCRIPTION
--    "The MIB module describing the Nortel MsCarrier MscPassport enterprise 
--    extensions to standard Mibs."

extensionsMIB OBJECT IDENTIFIER  ::= { mscPassportMIBs 5 }

mscExtensions OBJECT IDENTIFIER ::= { mscComponents 4 }

mscExtensionIfTable    OBJECT-TYPE
   SYNTAX     SEQUENCE OF ExtensionIfEntry
   ACCESS     not-accessible
   STATUS     mandatory
   DESCRIPTION
      "A table which provides enterprise extensions to the standard 
       ifTable."
   ::= { mscExtensions 1 }

mscExtensionIfEntry     OBJECT-TYPE
   SYNTAX      ExtensionIfEntry 
   ACCESS      not-accessible
   STATUS     mandatory
   DESCRIPTION
      " An entry containing enterprise extensions to the standard
	ifEntry."
   INDEX  { ifIndex }
   ::= { mscExtensionIfTable 1}

 ExtensionIfEntry ::=
    SEQUENCE {
       mscIfRowPointer    RowPointer
       }

 mscIfRowPointer    OBJECT-TYPE
    SYNTAX       RowPointer
    ACCESS       read-only 
    STATUS       mandatory
    DESCRIPTION
       "A pointer to the RowStatus variable for the component 
        represented by the ifTable entry."
    ::= { mscExtensionIfEntry 1 }


--
-- Version and Compliance statements
--
 
 
-- Object-Group Statement:
 
-- OBJECTS   { mscIfRowPointer }
-- STATUS     current
-- DESCRIPTION
--       "A list of all current accessible leaf objects."

extensionsGroup OBJECT IDENTIFIER ::= { extensionsMIB 1 }
extensionsGroupCA OBJECT IDENTIFIER ::= { extensionsGroup 1 }
extensionsGroupCA01 OBJECT IDENTIFIER ::= { extensionsGroupCA 2 }
extensionsGroupCA01A OBJECT IDENTIFIER ::= { extensionsGroupCA01 2 }

 
-- Agent-Capabilities Statement:
 
-- PRODUCT-RELEASE "Passport Carrier Release 1.1 Standard MIB Extensions."
-- STATUS          current
-- DESCRIPTION
--    "Carrier Passport Extensions MIB: MIB Version CA01A."
-- SUPPORTS        Nortel-MsCarrier-MscPassport-ExtensionsMIB
-- INCLUDES        { extensionsGroupCA01A }

extensionsCapabilities OBJECT IDENTIFIER ::= { extensionsMIB 3 }
extensionsCapabilitiesCA OBJECT IDENTIFIER ::= { extensionsCapabilities 1 }
extensionsCapabilitiesCA01 OBJECT IDENTIFIER ::= { extensionsCapabilitiesCA 2 }
extensionsCapabilitiesCA01A OBJECT IDENTIFIER ::= { extensionsCapabilitiesCA01 2 }


END
