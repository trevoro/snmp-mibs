ACC-BOOTP DEFINITIONS ::= BEGIN

    IMPORTS
  	 OBJECT-TYPE, IpAddress, Counter FROM RFC1155-SMI
	 accTrapLogSeqNum FROM ACC-SYSTEM
	accBRG, DisplayString, RowStatus, IfIndex, SmdsAddress
             FROM ACC-MIB;

-- Bootp Group
accBootp        OBJECT IDENTIFIER ::= { accBRG 29 }
-- These objects are being deprecated because they were improperly defined
-- when first implemented.
accBootServerOld OBJECT IDENTIFIER ::= { accBootp 1 }
            accBootpServerOld   OBJECT-TYPE   
                        SYNTAX  IpAddress
                        ACCESS  read-only
                        STATUS  mandatory
                        DESCRIPTION
                 " IP address of the Bootp Server."
                        ::= { accBootServerOld 1 }
-- end of deprecated objects
	accBootMode		OBJECT-TYPE
			SYNTAX	 INTEGER {
				automatic(1),
				forced(2),
				off(3),
				default(4)
				}
			 ACCESS  read-only
			 STATUS  mandatory
			 DESCRIPTION
		" Mode of operation on unit boot-up.
		  Automatic - stored configuration information is ignored and
		  configuration is sought from the last known server or via
		  BOOTP if no previous server information is known.
		  Forced - stored configuration information is ignored and
		  configuration information is sought via BOOTP.
		  Off - stored configuration information is used."
			::= { accBootp 2 }
	accBootState		OBJECT-TYPE
			SYNTAX INTEGER {
				initial(1),
				disabled(2),
				requesting(3),
				waiting(4),
				configuring(5),
				complete(6),
				failed(7)
				}
			ACCESS  read-only
			STATUS  mandatory
			DESCRIPTION
		"The state of Bootp client operation:
		 initial - client initializing after start-up.
		 disabled - client operation is disabled (Boot Mode Off).
		 requesting - BootP requests are being generated.
		 waiting - waiting between request generation phases.
		 configuring - Bootp response has been received and a
	 	 configuration is being downloaded and executed.
		 complete - configuration is complete.
		 failed - configuration download or execution has failed."
			 ::= { accBootp 3 }
	accBootyiaddr		OBJECT-TYPE
			SYNTAX IpAddress
			ACCESS	read-only
			STATUS	mandatory
			DESCRIPTION
		"The value of yiaddr returned in the last Bootp reply
		 processed.  This is the address used by the unit
		 as its address in the TFTP download of a configuration
		 script file."
			 ::= { accBootp 4 }
	accBootsiaddr		OBJECT-TYPE
			SYNTAX IpAddress
			ACCESS	read-only
			STATUS	mandatory
			DESCRIPTION
		"The value of siaddr returned in the last Bootp reply
		 processed.  This is the address used by the unit
		 as the server address from which the TFTP download of 
		 a configuration script file is attempted."
			 ::= { accBootp 5 }
	accBootsname		OBJECT-TYPE
			SYNTAX	DisplayString
			ACCESS	read-only
			STATUS	mandatory
			DESCRIPTION
		"The value of siaddr returned in the last Bootp reply
		 processed.  This is the name of the Bootp server."
			 ::= { accBootp 6 }
-- This object is being replaced by the three gateway addresses below
	accBootgiaddr		OBJECT-TYPE
			SYNTAX IpAddress
			ACCESS	read-only
			STATUS	deprecated
			DESCRIPTION
		"The value of giaddr returned in the last Bootp reply
		 processed.  This is the address used by the unit
		 as the address of any intermediate gateway between
		 the unit and the Bootp server during the download
		 of the configuration script file."
			 ::= { accBootp 7 }
	accBootfile		OBJECT-TYPE
			SYNTAX	DisplayString
			ACCESS	read-only
			STATUS	mandatory
			DESCRIPTION
		"The value of file returned in the last Bootp reply
		 processed.  This is the name of the file to download
		 as a configuration script."
			 ::= { accBootp 8 }
	accBootInterface	OBJECT-TYPE
			SYNTAX  INTEGER
			ACCESS  read-only
			STATUS  mandatory
			DESCRIPTION
		"The interface index for the interface the last valid
		Bootp reply frame processed was received on."
			 ::= { accBootp 9 }
	accBootSentRequests	OBJECT-TYPE
			SYNTAX	Counter
			ACCESS	read-only
			STATUS	mandatory
			DESCRIPTION
		"The number of Bootp requests sent."
			 ::= { accBootp 10 }
	accBootReceivedReplies	OBJECT-TYPE
			SYNTAX	Counter
			ACCESS	read-only
			STATUS	mandatory
			DESCRIPTION
		"The number of valid Bootp replies received."
			 ::= { accBootp 11 }
	accBootDiscardedReplies	OBJECT-TYPE
			SYNTAX	Counter
			ACCESS	read-only
			STATUS	mandatory
			DESCRIPTION
		"The number of Bootp replies discarded due to
		 insufficient data in reply."
			 ::= { accBootp 12 }
        accBootServerTable      OBJECT-TYPE
                        SYNTAX  SEQUENCE OF AccBootServerEntry
                        ACCESS  not-accessible
                        STATUS  mandatory
                        DESCRIPTION
                " A table of Bootpstrap protocol servers that this unit
                 will forward Bootp requests to."
                        ::= { accBootp 13 }
        accBootServerEntry      OBJECT-TYPE
                        SYNTAX AccBootServerEntry
                        ACCESS not-accessible
                        STATUS mandatory
                        DESCRIPTION
                " A Boot server table entry. "
                        INDEX
								{
								IpAddress
								}
                        ::= { accBootServerTable 1 }
        AccBootServerEntry ::= SEQUENCE {
                                accBootServerIPAddr     IpAddress
                                }
        accBootServerIPAddr     OBJECT-TYPE
                        SYNTAX  IpAddress
                        ACCESS  read-write
                        STATUS  mandatory
                        DESCRIPTION
                " An IP address of a Bootstrap protocol server to be
                 supported by Boot Helper."
                        ::= { accBootServerEntry 1 }
        accBootg1iaddr           OBJECT-TYPE
                        SYNTAX IpAddress
                        ACCESS  read-only
                        STATUS  mandatory
                        DESCRIPTION
                "The value of first giaddr returned in the last Bootp reply
                 processed.  This is the first address used by the unit
                 as the address of any intermediate gateway between
                 the unit and the Bootp server during the download
                 of the configuration script file."
                         ::= { accBootp 14 }
        accBootg2iaddr           OBJECT-TYPE
                        SYNTAX IpAddress
                        ACCESS  read-only
                        STATUS  mandatory
                        DESCRIPTION
                "The value of second giaddr returned in the last Bootp reply
                 processed.  This is the second address used by the unit
                 as the address of any intermediate gateway between
                 the unit and the Bootp server during the download
                 of the configuration script file."
                         ::= { accBootp 15 }
        accBootg3iaddr           OBJECT-TYPE
                        SYNTAX IpAddress
                        ACCESS  read-only
                        STATUS  mandatory
                        DESCRIPTION
                "The value of third giaddr returned in the last Bootp reply
                 processed.  This is the third address used by the unit
                 as the address of any intermediate gateway between
                 the unit and the Bootp server during the download
                 of the configuration script file."
                         ::= { accBootp 16 }
        accBootpServerMode             OBJECT-TYPE
                        SYNTAX   INTEGER {
                                on(1),
                                off(2)
                                }
                         ACCESS  read-write
                         STATUS  mandatory
                         DESCRIPTION
                " Mode for the Bootp Server."
                        ::= { accBootp 17 }

END
