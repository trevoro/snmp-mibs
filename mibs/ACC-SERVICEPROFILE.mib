ACC-SERVICEPROFILE DEFINITIONS ::= BEGIN

    IMPORTS
		OBJECT-TYPE, IpAddress, TimeTicks, Gauge, Counter FROM RFC1155-SMI
		TRAP-TYPE FROM RFC-1215
     accTrapLogSeqNum FROM ACC-SYSTEM
accBRG, DisplayString, RowStatus, IfIndex, SmdsAddress
             FROM ACC-MIB;

-- Service Profile Group
    accServiceProfile OBJECT IDENTIFIER ::= { accBRG 65 }
	-- The Service Profile Table Group
	-- Configuration parameters, operational parameters and statistics
	-- maintained for each Service Profile.
	accServiceProfileTable OBJECT-TYPE
	    SYNTAX SEQUENCE OF AccServiceProfileEntry
	    ACCESS not-accessible
	    STATUS mandatory
	    DESCRIPTION
	       "The Service Profile Table"
	    ::= { accServiceProfile 1 }
	accServiceProfileEntry OBJECT-TYPE
	    SYNTAX AccServiceProfileEntry
	    ACCESS not-accessible
	    STATUS mandatory
	    DESCRIPTION
	       "An entry in the Service Profile Table"
	    INDEX  { accServiceProfileName }
	    ::= { accServiceProfileTable 1 }
	AccServiceProfileEntry ::= SEQUENCE {
	    accServiceProfileName        DisplayString,
	    accServiceProfileType        INTEGER,
	    accServiceProfileAdminState  INTEGER,
	    accServiceProfileMsgLevel    INTEGER,
	    accServiceProfilePppDefault  INTEGER,
	    accServiceProfileAuthMethod  INTEGER,
	    accServiceProfilePortLimit   INTEGER,
	    accServiceProfileAccessPart  DisplayString,
	    accServiceProfileModemPool   DisplayString,
	    accServiceProfileEntryStatus INTEGER,
	    accServiceProfileBusyCount   Gauge,
	    accServiceProfileNumAccepts   Counter,
	    accServiceProfileNumRejects   Counter,
	    accServiceProfileNumActive   Gauge,
	    accServiceProfileNumberGroup INTEGER,
	    accServiceProfilePppMru      INTEGER,
	    accServiceProfileMlpppMrru   INTEGER,
	    accServiceProfileMlxState    INTEGER,
	    accServiceProfileWelcomeMessage DisplayString, 
	    accServiceProfileLoginPrompt DisplayString,
            accServiceProfilePasswordPrompt DisplayString,
            accServiceProfileServicePrompt DisplayString,
            accServiceProfileLoginTimeout  TimeTicks,
            accServiceProfileAuthPreference  INTEGER,
            accServiceProfileAccountingOptn  INTEGER,
            accServiceProfileBandwidthMgmt  INTEGER,
	    accServiceProfilePppIpComp      INTEGER
	}
	accServiceProfileName OBJECT-TYPE
	    SYNTAX DisplayString -- (SIZE (1..16))
	    ACCESS read-only
	    STATUS mandatory
	    DESCRIPTION
	       "The name of the service profile.  This name serves as the 
	        index for accessing information in the Sevice Profile Table.  
	        The service profile name is usually acquired from an entry 
	        in the Called Number Table."
	    ::= { accServiceProfileEntry 1 }
	accServiceProfileType OBJECT-TYPE
	    SYNTAX INTEGER {
		mpbr(1),
		cdnr(2)
	    }
	    ACCESS read-write
	    STATUS mandatory
	    DESCRIPTION
	       "The type of service profile entry.  MPBR is normal, multi-
	        protocol bridge/router service.  CDNR is partitioned access 
	        service via called number routing."
	    ::= { accServiceProfileEntry 2 }
	accServiceProfileAdminState OBJECT-TYPE
	    SYNTAX INTEGER {
		enabled(1),
		disabled(2),
		drained(3)
	    }
	    ACCESS read-write
	    STATUS mandatory
	    DESCRIPTION
	       "The administrative state of this service profile.  If the 
	        administrative state is set to disabled, no new connections 
	        will be allowed using this profile, and all existing 
	        connections using the profile will be terminated.  If the 
	        administrative state is set to drained, no new connections 
	        will be accepted, but existing connections will be 
	        maintained."
	    ::= { accServiceProfileEntry 3 }
	accServiceProfileMsgLevel OBJECT-TYPE
	    SYNTAX INTEGER (1..7)
	    ACCESS read-write
	    STATUS mandatory
	    DESCRIPTION
	       "The current severity level of trap messages that may be 
	        generated regarding events associated with this service 
	        profile.  Only trap messages whose serverity level is less 
	        than or equal to the current setting of this object will be 
	        displayed."
	    ::= { accServiceProfileEntry 4 }
	accServiceProfilePppDefault OBJECT-TYPE
	    SYNTAX INTEGER {
		factory(1),
		override(2)
	    }
	    ACCESS read-write
	    STATUS obsolete
	    DESCRIPTION
	       "The method used to set default PPP parameters.  
	        FACTORY indicates  that factory defaults will be used or 
	        default parameters will be obtained from the usual sources 
	        (e.g., preconfigured dial ports).  OVERRIDE indicates that 
	        default parameters should be overriden using values 
	        configured in this service profile.
                This object has been obsoleted with release 11.1."
	    ::= { accServiceProfileEntry 5 }
	accServiceProfileAuthMethod OBJECT-TYPE
	    SYNTAX INTEGER {
		            none         (1),
		            pap          (2),
		            chap         (3),
		            chap-or-pap  (4),
		            login        (5),
                            token-chap   (6)
	                   }
	    ACCESS read-write
	    STATUS mandatory
	    DESCRIPTION
	       "The default PPP authentication method for this service 
	        profile."
	    ::= { accServiceProfileEntry 6 }
	accServiceProfilePortLimit OBJECT-TYPE
	    SYNTAX INTEGER (1..32)
	    ACCESS read-write
	    STATUS mandatory
	    DESCRIPTION
	       "The maximum port limit for this service profile.  A value 
	        of 1 disables PPP multilink.  A value greater than 1 enables 
	        multilink negotiation."
	    ::= { accServiceProfileEntry 7 }
	accServiceProfileAccessPart OBJECT-TYPE
	    SYNTAX DisplayString -- (SIZE (0..16))
	    ACCESS read-write
	    STATUS mandatory
	    DESCRIPTION
	       "The name of the access partition to use for this service.  If 
	        the service type is CDNR, an access partition name must be 
	        configured and the corresponding access partition should be 
	        defined in the Access Partition Table.  Otherwise, this object 
	        need not be configured."
	    ::= { accServiceProfileEntry 8 }
	accServiceProfileModemPool OBJECT-TYPE
	    SYNTAX DisplayString -- (SIZE (0..16))
	    ACCESS read-write
	    STATUS mandatory
	    DESCRIPTION
	       "The name of the modem pool to use for providing service 
	        to switched users connecting via modems.  If no modem 
	        pool is configured, a default modem pool will be used to 
	        provide service."
	    ::= { accServiceProfileEntry 9 }
	accServiceProfileEntryStatus OBJECT-TYPE
	    SYNTAX INTEGER {
		add(1),
		delete(2)
	    }
	    ACCESS read-write
	    STATUS mandatory
	    DESCRIPTION
	       "The modification status of this service profile entry.  
	        Setting the status to add causes a new entry to be added.  
	        Setting the status to deleete causes an existing entry to be 
	        deleted."
	    ::= { accServiceProfileEntry 10 }
	accServiceProfileBusyCount OBJECT-TYPE
	    SYNTAX Gauge
	    ACCESS read-only
	    STATUS mandatory
	    DESCRIPTION
	       "The number of internal resources currently bound to this 
	        service profile.  If the busy count is non-zero, the service 
	        profile entry cannot be removed."
	    ::= { accServiceProfileEntry 11 }
	accServiceProfileNumAccepts OBJECT-TYPE
	    SYNTAX Counter
	    ACCESS read-only
	    STATUS mandatory
	    DESCRIPTION
	       "The number of incoming or outgoing connection requests 
	        accepted for this service profile."
	    ::= { accServiceProfileEntry 12 }
	accServiceProfileNumRejects OBJECT-TYPE
	    SYNTAX Counter
	    ACCESS read-only
	    STATUS mandatory
	    DESCRIPTION
	       "The number of incoming or outgoing connection requests 
	        rejected for this service profile."
	    ::= { accServiceProfileEntry 13 }
	accServiceProfileNumActive OBJECT-TYPE
	    SYNTAX Gauge
	    ACCESS read-only
	    STATUS mandatory
	    DESCRIPTION
	       "The current number of connected physical ports using this 
	        service profile.  Each physical link in a multilink bundle 
	        counts as one connection."
	    ::= { accServiceProfileEntry 14 }
	accServiceProfileNumberGroup OBJECT-TYPE
	    SYNTAX INTEGER (1..127)
	    ACCESS read-write
	    STATUS mandatory
	    DESCRIPTION
	       "The calling number group to use for incoming call 
	        screening.  The calling number group is defined in the 
	        Calling Number Table.  If the calling number group is 0, no 
	        incoming call screening is performed for this service 
	        profile."
	    ::= { accServiceProfileEntry 15 }
	accServiceProfilePppMru OBJECT-TYPE
	    SYNTAX INTEGER (64..4500)
	    ACCESS read-write
	    STATUS mandatory
	    DESCRIPTION
	       "The default maximum receive unit to negotiate for the PPP 
	        connection using this service profile."
	    ::= { accServiceProfileEntry 16 }
	accServiceProfileMlpppMrru OBJECT-TYPE
	    SYNTAX INTEGER (64..4500)
	    ACCESS read-write
	    STATUS mandatory
	    DESCRIPTION
	       "The default maximum reassembly receive unit to negotiate 
	        for the Multilink PPP connection using this service profile.  "
	    ::= { accServiceProfileEntry 17 }
	accServiceProfileMlxState OBJECT-TYPE
	    SYNTAX INTEGER {
		enabled(1),
		disabled(2)
	    }
	    ACCESS read-write
	    STATUS obsolete
	    DESCRIPTION
	       "The default MLX administrative state for the Multilink 
	        PPP connection using this service profile.
                This object has been obsoleted with release 11.1."
	    ::= { accServiceProfileEntry 18 }
	accServiceProfileWelcomeMessage OBJECT-TYPE
	    SYNTAX DisplayString -- (SIZE (0..79))
	    ACCESS read-write
	    STATUS mandatory
	    DESCRIPTION
	       "This is the string that will be displayed when PPP scripting
		is enabled (sp LOGIN authentication mode) to welcome the user.
		It will appear before the username/login prompt."
	    ::= { accServiceProfileEntry 19 }
	accServiceProfileLoginPrompt OBJECT-TYPE
	    SYNTAX DisplayString -- (SIZE (0..19))
	    ACCESS read-write
	    STATUS mandatory
	    DESCRIPTION
	       "This is the string that will be displayed when PPP scripting
		is enabled (sp LOGIN authentication mode) to prompt the user
		for entry of a username.  It will appear after the 
		Welcome Message."
	    ::= { accServiceProfileEntry 20 }
	accServiceProfilePasswordPrompt OBJECT-TYPE
	    SYNTAX DisplayString -- (SIZE (0..19))
	    ACCESS read-write
	    STATUS mandatory
	    DESCRIPTION
	       "This is the string that will be displayed when PPP scripting
		is enabled (sp LOGIN authentication mode) to prompt the user
		for entry of a password.  It will appear after the 
		Login Prompt."
	    ::= { accServiceProfileEntry 21 }
	accServiceProfileServicePrompt OBJECT-TYPE
	    SYNTAX DisplayString -- (SIZE (0..79))
	    ACCESS read-write
	    STATUS mandatory
	    DESCRIPTION
	       "This is the string that will be displayed when PPP scripting
		is enabled (sp LOGIN authentication mode) after successful
		authentication has occurred.  It will appear after the password
		prompt."
	    ::= { accServiceProfileEntry 22 }
        accServiceProfileLoginTimeout OBJECT-TYPE
--          SYNTAX INTEGER (0..300)
            SYNTAX TimeTicks
            ACCESS read-write
            STATUS mandatory
            DESCRIPTION
               "The duration in seconds that the system will wait
                for an answer to a login/password prompt. After this
                timeout, the system will start normal PPP negotiation.
                Zero disables timer (no timeout)."
            ::= { accServiceProfileEntry 23 }
        accServiceProfileAuthPreference OBJECT-TYPE
            SYNTAX INTEGER {
                pap(1),
                chap(2)
            }
            ACCESS read-write
            STATUS mandatory
            DESCRIPTION
               "The authentication preference for this service profile. This
                This object is useful for altering the behavior of PPP 
                negotiation when providing service to clietns that cannot be
                configured to deny negotiation of the stronger CHAP authentication
                method and PAP authentication is required. PAP is the default setting."
            ::= { accServiceProfileEntry 24 }
        accServiceProfileAccountingOptn OBJECT-TYPE
            SYNTAX INTEGER {
                on(1),
                off(2)
            }
            ACCESS read-write
            STATUS mandatory
            DESCRIPTION
               "The Accounting option for this service profile.  This is
                used to enable or disable RADIUS accounting for PPP sessions
                associated with this service profile. RADIUS accounting is
                enabled by default."
            ::= { accServiceProfileEntry 25 }
        accServiceProfileBandwidthMgmt OBJECT-TYPE
            SYNTAX INTEGER {
                bacp(1),
                mlx(2),
                default(3),
                any(4)
            }
            ACCESS read-write
            STATUS mandatory
            DESCRIPTION
               "The bandwidth management protocols that can be negotiated for PPP 
                connections associated with this service profile.
                   BACP enables the negotiation of the Bandwidth Allocation Control 
                        Protocol (BACP) and Bandwidth Allocation Protocol (BAP). This
                        is the default setting.
                   MLX enables the Multilink Extended (MLX) protocol. MLX is compatible
                        with MP+.
                   DEFAULT disables negotiation of BACP or MLX and uses local mechanisms
                        for adding bandwidth to PPP multilink connections.
                   ANY enables the negotiation of any supported management protocol.
                This objects supercedes the accServiceProfileMlxState object that
                was previously used to enable MLX negotiation."                
            ::= { accServiceProfileEntry 26 }
        accServiceProfilePppIpComp OBJECT-TYPE
            SYNTAX INTEGER {
                none(1),
                vjhc(2)
            }
            ACCESS read-write
            STATUS mandatory
            DESCRIPTION
               "The VJ header compression option for this
                service profile."
            ::= { accServiceProfileEntry 27 }
	-- The Service Profile Port Group
	-- Service Profile information maintained on a per-port basis.
	accServiceProfilePortTable OBJECT-TYPE
	    SYNTAX SEQUENCE OF AccServiceProfilePortEntry
	    ACCESS not-accessible
	    STATUS mandatory
	    DESCRIPTION
	       "The Service Profile Port Table"
	    ::= { accServiceProfile 2 }
	accServiceProfilePortEntry OBJECT-TYPE
	    SYNTAX AccServiceProfilePortEntry
	    ACCESS not-accessible
	    STATUS mandatory
	    DESCRIPTION
	       "An entry in the Service Profile Port Table"
	    INDEX  { accServiceProfileIfIndex }
	    ::= { accServiceProfilePortTable 1 }
	AccServiceProfilePortEntry ::= SEQUENCE {
	    accServiceProfileIfIndex        INTEGER,
	    accServiceProfileConfiguredName DisplayString,
	    accServiceProfileActiveName     DisplayString,
	    accServiceProfileActiveType     INTEGER
	}
	accServiceProfileIfIndex OBJECT-TYPE
	    SYNTAX INTEGER (1..'7fffffff'h)
	    ACCESS read-only
	    STATUS mandatory
	    DESCRIPTION
	       "The interface index of the physical port associated with this 
	        entry."
	    ::= { accServiceProfilePortEntry 1 }
	accServiceProfileConfiguredName OBJECT-TYPE
	    SYNTAX DisplayString -- (SIZE (0..16))
	    ACCESS read-only
	    STATUS mandatory
	    DESCRIPTION
	       "The name of the service profile configured for this physical 
	        port."
	    ::= { accServiceProfilePortEntry 2 }
	accServiceProfileActiveName OBJECT-TYPE
	    SYNTAX DisplayString -- (SIZE (0..16))
	    ACCESS read-only
	    STATUS mandatory
	    DESCRIPTION
	       "The name of the service profile currently active for this 
	        physical port.  If a service profile has been manually 
	        configured for this port, the active profile will always be the 
	        same as the configured profile.  Otherwise, the active 
	        service profile is assigned dynamically when the physical 
	        circuit is connected."
	    ::= { accServiceProfilePortEntry 3 }
	accServiceProfileActiveType OBJECT-TYPE
	    SYNTAX INTEGER {
		inactive(1),
		mpbr(2),
		cdnr(3)
	    }
	    ACCESS read-only
	    STATUS mandatory
	    DESCRIPTION
	       "The type of service associated with the active service 
	        profile."
	    ::= { accServiceProfilePortEntry 4 }

END
