AIPORTVLAN-MIB DEFINITIONS ::=  BEGIN

-- Applied Innovation Port VLAN MIB definitions
-- @(#) ai $Revision:   1.00  $ $Date:   1 Nov 2000 12:23:37  $

IMPORTS
    DisplayString
        FROM RFC1213-MIB
		  
	PositiveInteger FROM AISYSTEM-MIB

    MODULE-IDENTITY, OBJECT-TYPE, Counter32, Gauge32,
    enterprises
        FROM SNMPv2-SMI;


-- group object IDs

aii             OBJECT IDENTIFIER ::= { enterprises 539 }
aiSystemOID     OBJECT IDENTIFIER ::= { aii 2 }

aiPortVlan  MODULE-IDENTITY
    LAST-UPDATED "980803164411Z"
    ORGANIZATION "Applied Innovation Incorporated"
    CONTACT-INFO
        "        Engineering MIB Administrator

        Postal:  Applied Innovation Inc.
                 5800 Innovation Drive
                 Dublin, OH 43016-3271

           Tel:  614/798-2000
           Fax:  614/798-1770
        E-mail:  snmp@aiinet.com"
    DESCRIPTION  " The MIB Module for port based VLAN."
    ::= { aii 29 }

-- System group for port based VLAN

aiPortVlanCnf    OBJECT IDENTIFIER ::= { aiPortVlan 1 }

-- System Group

portVlanCnfTable OBJECT-TYPE
        SYNTAX          SEQUENCE OF PORTVlanCnfEntry
        MAX-ACCESS      not-accessible
        STATUS          current
        DESCRIPTION
                "Table of configuration information about port based VLANs."
        ::= { aiPortVlanCnf 1 }

portVlanCnfEntry  OBJECT-TYPE
        SYNTAX          PORTVlanCnfEntry
        MAX-ACCESS      not-accessible
        STATUS          current
        DESCRIPTION
                "Entries of aiPortVlanTable."
        INDEX { portVlanIndex }
     ::= { portVlanCnfTable 1 }

PORTVlanCnfEntry ::= SEQUENCE {
         portVlanIndex            PositiveInteger,
         portVlanName             DisplayString,
         portVlanOverlap          PositiveInteger
        }

portVlanIndex OBJECT-TYPE
        SYNTAX          INTEGER (1..1024)
        MAX-ACCESS      read-only
        STATUS          current
        DESCRIPTION
                "This object identifies the VLAN within the group
                for which this entry contains information."
        ::= {portVlanCnfEntry 1}

portVlanName OBJECT-TYPE
        SYNTAX          DisplayString (SIZE (0..30))
        MAX-ACCESS      read-write
        STATUS          current
        DESCRIPTION
                "This is the name given to this VLAN."
        ::= {portVlanCnfEntry 2}

portVlanOverlap OBJECT-TYPE
        SYNTAX          INTEGER {
                                 enabled(1),
                                 disabled(2)
                                }
        MAX-ACCESS      read-write
        STATUS          current
        DESCRIPTION
                "This allows VLANs to overlap.  WARNING: Enabling this feature 
                 will turn STP off on the overlapped switch ports.  Therefore, it  
                 is possible to generate undetected loops."
        ::= {portVlanCnfEntry 3}

portVlanMembershipTable  OBJECT-TYPE
        SYNTAX          SEQUENCE OF PORTVlanMembershipEntry
        MAX-ACCESS      not-accessible
        STATUS          current
        DESCRIPTION
                "A two dimensional table listing the vlan and port membership
                 of each vlan."
        ::= { aiPortVlanCnf 2 }

portVlanMembershipEntry OBJECT-TYPE
        SYNTAX          PORTVlanMembershipEntry
        MAX-ACCESS      not-accessible
        STATUS          current
        DESCRIPTION
                "Table of VLAN membership per port."
        INDEX { portVlanMembershipVlanIndex, portVlanMembershipPortIndex }
        ::= {portVlanMembershipTable 1}

PORTVlanMembershipEntry ::=
        SEQUENCE {
                    portVlanMembershipVlanIndex       PositiveInteger,
                    portVlanMembershipPortIndex       PositiveInteger,
                    portVlanMembershipStatus          PositiveInteger
                 }

portVlanMembershipVlanIndex OBJECT-TYPE
        SYNTAX          INTEGER (1..1024)
        MAX-ACCESS      read-only
        STATUS          current
        DESCRIPTION
                "This object identifies the VLAN within the group
                for which this entry contains information."
        ::= { portVlanMembershipEntry 1 }

portVlanMembershipPortIndex OBJECT-TYPE
        SYNTAX          INTEGER (1..1024)
        MAX-ACCESS      read-only
        STATUS          current
        DESCRIPTION
                "This object identifies the port within the group
                for which this entry contains information."
        ::= { portVlanMembershipEntry 2 }

portVlanMembershipStatus OBJECT-TYPE
        SYNTAX          INTEGER {
	                         member(1),
				 nonmember(2)
				}
        MAX-ACCESS      read-write
        STATUS          current
        DESCRIPTION
                "The status of the vlan membership of the specified port."
        ::= { portVlanMembershipEntry 3 }

END
