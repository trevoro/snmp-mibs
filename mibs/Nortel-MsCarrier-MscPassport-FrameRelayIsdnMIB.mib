Nortel-MsCarrier-MscPassport-FrameRelayIsdnMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Unsigned32
   FROM Nortel-MsCarrier-MscPassport-StandardTextualConventionsMIB

      NonReplicated,
      DigitString
   FROM Nortel-MsCarrier-MscPassport-TextualConventionsMIB

      mscFrUniIndex,
      mscFrUni
   FROM Nortel-MsCarrier-MscPassport-FrameRelayUniMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayIsdn Enterprise MIB."

frameRelayIsdnMIB OBJECT IDENTIFIER ::= { mscPassportMIBs 122 }










-- FrUni/n Isdn
-- This component defines the parameters associated with the ISDN B-
-- Channel interface. Adding this component makes the FrUni 
-- behaves as an ISDN access to the Frame Relay Network.

mscFrUniIsdn OBJECT IDENTIFIER ::= { mscFrUni 100 }



mscFrUniIsdnRowStatusTable OBJECT-TYPE
   SYNTAX     SEQUENCE OF MscFrUniIsdnRowStatusEntry
   ACCESS     not-accessible
   STATUS     mandatory
   DESCRIPTION
     "This entry controls the addition and deletion of 
      mscFrUniIsdn components."
::= { mscFrUniIsdn 1 }

mscFrUniIsdnRowStatusEntry OBJECT-TYPE
   SYNTAX     MscFrUniIsdnRowStatusEntry
   ACCESS     not-accessible
   STATUS     mandatory
   DESCRIPTION
     "A single entry in the table represents a single 
      mscFrUniIsdn component."
   INDEX {
      mscFrUniIndex,
      mscFrUniIsdnIndex }
::= { mscFrUniIsdnRowStatusTable 1 }

MscFrUniIsdnRowStatusEntry ::= SEQUENCE {
   mscFrUniIsdnRowStatus
      RowStatus,
   mscFrUniIsdnComponentName
      DisplayString,
   mscFrUniIsdnStorageType
      StorageType,
   mscFrUniIsdnIndex
      NonReplicated }

mscFrUniIsdnRowStatus OBJECT-TYPE
   SYNTAX     RowStatus 
   ACCESS     read-write
   STATUS     mandatory
   DESCRIPTION
     "This variable is used as the basis for SNMP naming of
      mscFrUniIsdn components.
      These components can be added and deleted."
::= { mscFrUniIsdnRowStatusEntry 1 }

mscFrUniIsdnComponentName OBJECT-TYPE
   SYNTAX     DisplayString 
   ACCESS     read-only
   STATUS     mandatory
   DESCRIPTION
     "This variable provides the component's string name for
      use with the ASCII Console Interface"
::= { mscFrUniIsdnRowStatusEntry 2 }

mscFrUniIsdnStorageType OBJECT-TYPE
   SYNTAX     StorageType 
   ACCESS     read-only
   STATUS     mandatory
   DESCRIPTION
     "This variable represents the storage type value for the
      mscFrUniIsdn tables."
::= { mscFrUniIsdnRowStatusEntry 4 }

mscFrUniIsdnIndex OBJECT-TYPE
   SYNTAX     NonReplicated 
   ACCESS     not-accessible
   STATUS     mandatory
   DESCRIPTION
     "This variable represents the index for the mscFrUniIsdn tables."
::= { mscFrUniIsdnRowStatusEntry 10 }

mscFrUniIsdnProvTable OBJECT-TYPE
   SYNTAX     SEQUENCE OF MscFrUniIsdnProvEntry
   ACCESS     not-accessible
   STATUS     mandatory
   DESCRIPTION
     "This group contains the provisionable attributes of the Isdn 
      component."
::= { mscFrUniIsdn 11 }

mscFrUniIsdnProvEntry OBJECT-TYPE
   SYNTAX     MscFrUniIsdnProvEntry
   ACCESS     not-accessible
   STATUS     mandatory
   DESCRIPTION
     "An entry in the mscFrUniIsdnProvTable."
   INDEX {
      mscFrUniIndex,
      mscFrUniIsdnIndex }
::= { mscFrUniIsdnProvTable 1 }

MscFrUniIsdnProvEntry ::= SEQUENCE {
   mscFrUniIsdnT320
      Unsigned32,
   mscFrUniIsdnAddressSignalling
      INTEGER }

mscFrUniIsdnT320 OBJECT-TYPE
   SYNTAX     Unsigned32 (0..255)
   ACCESS     read-write
   STATUS     mandatory
   DESCRIPTION
     "This attribute specifies the waiting time for a silent 
      B-Channel (no active VCs associated with the FrUni) to be 
      disconnected and made available. Default is 60 seconds. 0 means 
      t320 will never timeout."
   DEFVAL     { 60 }
::= { mscFrUniIsdnProvEntry 1 }

mscFrUniIsdnAddressSignalling OBJECT-TYPE
   SYNTAX     INTEGER  {
                 isdnDna(0),
                 normalBehavior(1) }
   ACCESS     read-write
   STATUS     mandatory
   DESCRIPTION
     "This attribute defines whether the ISDN Calling Party Number is to 
      be signalled to the remote DTE during an SVC call establishment. 
      Otherwise, no changes to the current behavior of SVC call 
      establishement (i.e., Passport Dna is used in the calling party 
      number information element)."
   DEFVAL     { normalBehavior }
::= { mscFrUniIsdnProvEntry 2 }

mscFrUniIsdnOperTable OBJECT-TYPE
   SYNTAX     SEQUENCE OF MscFrUniIsdnOperEntry
   ACCESS     not-accessible
   STATUS     mandatory
   DESCRIPTION
     "This group contains the operational attributes of the Isdn 
      component."
::= { mscFrUniIsdn 12 }

mscFrUniIsdnOperEntry OBJECT-TYPE
   SYNTAX     MscFrUniIsdnOperEntry
   ACCESS     not-accessible
   STATUS     mandatory
   DESCRIPTION
     "An entry in the mscFrUniIsdnOperTable."
   INDEX {
      mscFrUniIndex,
      mscFrUniIsdnIndex }
::= { mscFrUniIsdnOperTable 1 }

MscFrUniIsdnOperEntry ::= SEQUENCE {
   mscFrUniIsdnDataSigChan
      INTEGER,
   mscFrUniIsdnBChannelState
      INTEGER,
   mscFrUniIsdnLastUsedCgpn
      DigitString,
   mscFrUniIsdnBChanIntState
      INTEGER,
   mscFrUniIsdnActiveVirtualCircuitsCount
      Counter32 }

mscFrUniIsdnDataSigChan OBJECT-TYPE
   SYNTAX     INTEGER (1..255)
   ACCESS     read-only
   STATUS     mandatory
   DESCRIPTION
     "This attribute indicates the instance number of the dataSigChan 
      component controlling the allocation of this FrUni Isdn component."
::= { mscFrUniIsdnOperEntry 1 }

mscFrUniIsdnBChannelState OBJECT-TYPE
   SYNTAX     INTEGER  {
                 idle(0),
                 busy(1),
                 disabled(2) }
   ACCESS     read-only
   STATUS     mandatory
   DESCRIPTION
     "This attribute indicates the state of the B-Channel. If the value is 
      idle it means that no VCs are connected and this B-Channel is 
      available. If the value is busy it means this B-Channel has been 
      allocated and is not available. If the value is disabled it means the 
      application interface or the port is locked or disabled."
::= { mscFrUniIsdnOperEntry 2 }

mscFrUniIsdnLastUsedCgpn OBJECT-TYPE
   SYNTAX     DigitString (SIZE (0..15))
   ACCESS     read-only
   STATUS     mandatory
   DESCRIPTION
     "This attribute indicates the calling party number currently using
      the B-Channel. When the B-Channel is free, the null string is 
      displayed."
::= { mscFrUniIsdnOperEntry 3 }

mscFrUniIsdnBChanIntState OBJECT-TYPE
   SYNTAX     INTEGER  {
                 isdnInit(0),
                 waitAccEnable(1),
                 waitLnsResponse(2),
                 waitFramerData(3),
                 enabling(4),
                 waitAccRegAck(5),
                 up(6),
                 down(7),
                 releasing(8) }
   ACCESS     read-only
   STATUS     mandatory
   DESCRIPTION
     "Debug information"
::= { mscFrUniIsdnOperEntry 4 }

mscFrUniIsdnActiveVirtualCircuitsCount OBJECT-TYPE
   SYNTAX     Counter32 
   ACCESS     read-only
   STATUS     mandatory
   DESCRIPTION
     "Current number of virtual circuits (switched and permanent) in data 
      transfer."
::= { mscFrUniIsdnOperEntry 5 }




-- 
-- Version and Compliance statements
-- 



-- Object-Group Statement:
-- A list of all current accessible leaf objects.

-- OBJECTS { mscFrUniIsdnT320,
--           mscFrUniIsdnAddressSignalling,
--           mscFrUniIsdnDataSigChan,
--           mscFrUniIsdnComponentName,
--           mscFrUniIsdnBChannelState,
--           mscFrUniIsdnBChanIntState,
--           mscFrUniIsdnLastUsedCgpn,
--           mscFrUniIsdnActiveVirtualCircuitsCount,
--           mscFrUniIsdnStorageType,
--           mscFrUniIsdnRowStatus }
-- STATUS  mandatory
-- DESCRIPTION
--   "A list of all current accessible leaf objects."

frameRelayIsdnGroup OBJECT IDENTIFIER ::= { frameRelayIsdnMIB 1 }
frameRelayIsdnGroupCA OBJECT IDENTIFIER ::= { frameRelayIsdnGroup 1 }
frameRelayIsdnGroupCA02 OBJECT IDENTIFIER ::= { frameRelayIsdnGroupCA 3 }
frameRelayIsdnGroupCA02A OBJECT IDENTIFIER ::= { frameRelayIsdnGroupCA02 2 }



-- Agent-Capabilities Statement:

-- PRODUCT-RELEASE "MscPassport Release 1.2 FrameRelayIsdn."
-- STATUS          mandatory
-- DESCRIPTION     "Carrier Passport FrameRelayIsdn MIB: MIB Version CA02A,
--                  Software Version CA02S9C."
-- SUPPORTS        Nortel-MsCarrier-MscPassport-FrameRelayIsdnMIB
--    INCLUDES     { frameRelayIsdnGroupCA02A }

frameRelayIsdnCapabilities OBJECT IDENTIFIER ::= { frameRelayIsdnMIB 3 }
frameRelayIsdnCapabilitiesCA OBJECT IDENTIFIER ::= { frameRelayIsdnCapabilities 1 }
frameRelayIsdnCapabilitiesCA02 OBJECT IDENTIFIER ::= { frameRelayIsdnCapabilitiesCA 3 }
frameRelayIsdnCapabilitiesCA02A OBJECT IDENTIFIER ::= { frameRelayIsdnCapabilitiesCA02 2 }





END
