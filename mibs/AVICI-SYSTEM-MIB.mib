AVICI-SYSTEM-MIB DEFINITIONS ::= BEGIN

IMPORTS
   MODULE-IDENTITY, OBJECT-TYPE, Integer32, TimeTicks, IpAddress
      FROM SNMPv2-SMI
   DisplayString
      FROM SNMPv2-TC
   MODULE-COMPLIANCE, OBJECT-GROUP
      FROM SNMPv2-CONF
   ifIndex
      FROM IF-MIB
   IANAifType
      FROM IANAifType-MIB
   aviciMibs
      FROM AVICI-SMI
   AviciSystemType, AviciInventoryType, AviciBayType, AviciSlotType,
   AviciTrapDescrType, AviciPlatformIndexType
      FROM AVICI-TC;

aviciSystemMIB MODULE-IDENTITY
        LAST-UPDATED "990330095500Z"
        ORGANIZATION "Avici Systems Inc."
        CONTACT-INFO "
                  Avici Systems, Inc.
                  101 Billerica Avenue
                  North Billerica, MA 01862-1256
 
                  (978) 964-2000
                  (978) 964-2100 (fax)
 
                  snmp@avici.com"
        DESCRIPTION  "The MIB module for the Avici Proprietary system MIB."
        ::= { aviciMibs 2 }

aviciSystemObjects     OBJECT IDENTIFIER ::= { aviciSystemMIB 1 }
aviciSystemGroup       OBJECT IDENTIFIER ::= { aviciSystemMIB 2 }

--
-- aviciSystemGroup
-- 

aviciSysRouterId OBJECT-TYPE
    SYNTAX      IpAddress
    MAX-ACCESS  read-only
    STATUS      current
    DESCRIPTION
        "The router id of the entire system."
    ::= { aviciSystemGroup 1 }

aviciSysType OBJECT-TYPE
   SYNTAX AviciSystemType
   MAX-ACCESS   read-only
   STATUS       current
   DESCRIPTION
       "The type of the Avici System."
   ::= { aviciSystemGroup 2 }

aviciSysInventoryTableChange OBJECT-TYPE
   SYNTAX TimeTicks
   MAX-ACCESS   read-only
   STATUS       current
   DESCRIPTION
       "The time of the last addition or deletion of a row in hundreths of a second since the last
       time the system was rebooted."
   ::= { aviciSystemGroup 3 }

aviciSysTrapDescr OBJECT-TYPE
     SYNTAX      AviciTrapDescrType
     MAX-ACCESS  accessible-for-notify
     STATUS      current
     DESCRIPTION
         "A description of the event that has occurred."
     ::= { aviciSystemGroup 4 }

--
-- aviciSysInventoryTable
--
-- removed the line aviciSysInventoryCleiCode to be added in later 
-- release when snmp support for clei codes is added.

aviciSysInventoryTable OBJECT-TYPE
   SYNTAX	SEQUENCE OF AviciSysInventoryEntry
   MAX-ACCESS	not-accessible
   STATUS	current
   DESCRIPTION
      "A list of components in the system.  This includes modules, bays and control servers."
   ::= { aviciSystemObjects 1 }

aviciSysInventoryEntry OBJECT-TYPE
   SYNTAX	AviciSysInventoryEntry
   MAX-ACCESS   not-accessible
   STATUS	current
   DESCRIPTION
       "An entry in the Avici table."
   INDEX   { aviciSysInventoryId }
   ::= { aviciSysInventoryTable 1 }

AviciSysInventoryEntry ::=
    SEQUENCE {
       aviciSysInventoryId          AviciPlatformIndexType,
       aviciSysInventoryType	    AviciInventoryType,
       aviciSysInventoryOperStatus  INTEGER,
       aviciSysInventoryBay         AviciBayType,
       aviciSysInventorySlot	    AviciSlotType,
       aviciSysInventoryDescr       DisplayString(SIZE(0..255))
    }

aviciSysInventoryId OBJECT-TYPE
   SYNTAX       AviciPlatformIndexType
   MAX-ACCESS	read-only
   STATUS	current
   DESCRIPTION
       "The component identification number used to uniquely identify any
        entity in the system."
   ::= { aviciSysInventoryEntry 1 }

aviciSysInventoryType OBJECT-TYPE
   SYNTAX       AviciInventoryType
   MAX-ACCESS	read-only
   STATUS	current
   DESCRIPTION
       "The type of the component."
   ::= { aviciSysInventoryEntry 2 }

aviciSysInventoryOperStatus OBJECT-TYPE
   SYNTAX INTEGER {
               up(1),        
               down(2)           
   }
   MAX-ACCESS   read-only
   STATUS       current
   DESCRIPTION
       "The operating state of the component."
   ::= {aviciSysInventoryEntry 3 }

aviciSysInventoryBay OBJECT-TYPE
  SYNTAX        AviciBayType
  MAX-ACCESS    read-only
  STATUS        current
  DESCRIPTION
        "The bay that this component can be found in.  If the component is
         not in a bay, then the value of this object is 0."
  ::= { aviciSysInventoryEntry 4 }

aviciSysInventorySlot OBJECT-TYPE
  SYNTAX        AviciSlotType
  MAX-ACCESS    read-only
  STATUS        current
  DESCRIPTION
        "The slot that this component can be found in.  If the component is not
         in a slot, then the value of this object is 0."
  ::= { aviciSysInventoryEntry 5}

  aviciSysInventoryDescr OBJECT-TYPE
    SYNTAX      DisplayString (SIZE(0..255))
    MAX-ACCESS  read-only
    STATUS      current
    DESCRIPTION
        "A description of this component in the system."
    ::= { aviciSysInventoryEntry 6 }

--
-- aviciSysIfTransTable
--   The Avici Interface Translation Table maps line card interfaces into
--   their corresponding bay and slot numbers. Only line card interfaces
--   are mapped by this table not server interfaces.

aviciSysIfTransTable OBJECT-TYPE
   SYNTAX	SEQUENCE OF AviciSysIfTransEntry
   MAX-ACCESS	not-accessible
   STATUS	current
   DESCRIPTION
      "A list of interface translation entries."
   ::= { aviciSystemObjects 2 }

aviciSysIfTransEntry OBJECT-TYPE
   SYNTAX	AviciSysIfTransEntry
   MAX-ACCESS   not-accessible
   STATUS       current
   DESCRIPTION
      "An entry in the Avici Interface Translation table.  The ifIndex 
       translation table will map an ifIndex into its corresponding
       bay/slot/port/interface."
   INDEX   { ifIndex }
   ::= { aviciSysIfTransTable 1 }

AviciSysIfTransEntry ::=
   SEQUENCE {
      aviciSysIfTransBay  AviciBayType,
      aviciSysIfTransSlot AviciSlotType,
      aviciSysIfTransPort Integer32,
      aviciSysIfTransIfc  Integer32,
      aviciSysIfTransType IANAifType,
      aviciSysIfTransName DisplayString
   }

aviciSysIfTransBay OBJECT-TYPE
   SYNTAX	AviciBayType
   MAX-ACCESS	read-only
   STATUS	current
   DESCRIPTION
      "The bay number that the interface resides in."
   ::= { aviciSysIfTransEntry 1 }

aviciSysIfTransSlot OBJECT-TYPE
   SYNTAX	AviciSlotType
   MAX-ACCESS	read-only
   STATUS	current
   DESCRIPTION
      "The slot number in the bay."
   ::= { aviciSysIfTransEntry 2 }

aviciSysIfTransPort OBJECT-TYPE
   SYNTAX	Integer32
   MAX-ACCESS	read-only
   STATUS	current
   DESCRIPTION
      "The physical port on the linecard."
   ::= { aviciSysIfTransEntry 3 }

aviciSysIfTransIfc OBJECT-TYPE
   SYNTAX	Integer32
   MAX-ACCESS	read-only
   STATUS	current
   DESCRIPTION
      "The logical interface on the linecard. The value of this object
       is 0, if it does not apply."
   ::= { aviciSysIfTransEntry 4 }

aviciSysIfTransType OBJECT-TYPE
   SYNTAX      IANAifType
   MAX-ACCESS  read-only
   STATUS      current
   DESCRIPTION
           "The type of interface. This object corresponds to
            ifType in the ifTable."
   ::= { aviciSysIfTransEntry 5 }

aviciSysIfTransName OBJECT-TYPE
    SYNTAX      DisplayString (SIZE(0..255))
    MAX-ACCESS  read-only
    STATUS      current
    DESCRIPTION
        "The name of this interface."
    ::= { aviciSysIfTransEntry 6 }


--
-- Conformance Information
--    

aviciSystemMIBConformance OBJECT IDENTIFIER ::= { aviciSystemMIB 3 }
aviciSystemMIBCompliances OBJECT IDENTIFIER ::= { aviciSystemMIBConformance 1 }
aviciSystemMIBGroups OBJECT IDENTIFIER ::= { aviciSystemMIBConformance 2 }

--
-- Compliance Statements
--

aviciSystemMIBCompliance MODULE-COMPLIANCE
    STATUS current
    DESCRIPTION
        "The compliance statement for the aviciSystem."
    MODULE
    MANDATORY-GROUPS {
        aviciSysGroup
    }
    ::= { aviciSystemMIBCompliances 1 }

aviciSysGroup OBJECT-GROUP
        OBJECTS {
            aviciSysRouterId,
            aviciSysType,
            aviciSysInventoryTableChange,
            aviciSysInventoryId,
            aviciSysInventoryType,
            aviciSysInventoryOperStatus,
            aviciSysInventoryBay,
            aviciSysInventorySlot,
            aviciSysInventoryDescr,
            aviciSysIfTransBay,
            aviciSysIfTransSlot,
            aviciSysIfTransPort,
            aviciSysIfTransIfc,
            aviciSysIfTransType,
            aviciSysIfTransName
        }
        STATUS     current
        DESCRIPTION
            "Objects for the system."
        ::= { aviciSystemMIBGroups 1 }

END
