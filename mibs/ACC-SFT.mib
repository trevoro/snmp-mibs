ACC-SFT DEFINITIONS ::= BEGIN

    IMPORTS
		OBJECT-TYPE, IpAddress, TimeTicks, Gauge, Counter FROM RFC1155-SMI
		TRAP-TYPE FROM RFC-1215
      accTrapLogSeqNum FROM ACC-SYSTEM
	accBRG, DisplayString, RowStatus, IfIndex, SmdsAddress
             FROM ACC-MIB;

--  This file was introduced with the realease of Ceylon 9.7
-- SFT Group
-- SFT Group
   accSFT 		OBJECT IDENTIFIER ::= { accBRG 47 }
    --
    --		The SFT Tunnel Table
    --
    accSFTunTable OBJECT-TYPE
        SYNTAX  SEQUENCE OF AccSFTunEntry
        ACCESS  	not-accessible
        STATUS  	mandatory
	DESCRIPTION
	     "Status of tunnel operation"
    ::= { accSFT 1 }
    accSFTunEntry OBJECT-TYPE
        SYNTAX 	AccSFTunEntry
        ACCESS 	not-accessible
        STATUS  mandatory
	DESCRIPTION
		" "
        INDEX   { accSFTunIndex }
        ::= { accSFTunTable  1 }
    AccSFTunEntry ::=
        SEQUENCE {
		accSFTunIndex		INTEGER,
		accSFTunEntStatus	INTEGER,
    		accSFTunIfIndex 	INTEGER,
    		accSFTunRemIPAddr	IpAddress,
    		accSFTunUDPAddr		INTEGER,
    		accSFTunAdStat		INTEGER
        }
    	accSFTunIndex OBJECT-TYPE
   	 	SYNTAX 	INTEGER
    		ACCESS 	read-only
    		STATUS 	mandatory
		DESCRIPTION
		     "Index amongst tunnels"
    		::= { accSFTunEntry  1 }
    	accSFTunEntStatus OBJECT-TYPE
    		SYNTAX 	INTEGER {
			    valid(1),
			    invalid(2)
		}
    		ACCESS 	read-write
    		STATUS  mandatory
		DESCRIPTION
		     "Status of this table entry. INVALID signifies deletion."
       		DEFVAL { valid }
    		::= { accSFTunEntry  2 }
    	accSFTunIfIndex OBJECT-TYPE
    		SYNTAX 	INTEGER
    		ACCESS 	read-write
    		STATUS  mandatory
		DESCRIPTION
		     "The ifindex of the serial port on which this tunnel 				terminates"
    		::= { accSFTunEntry  3 }
    	accSFTunRemIPAddr OBJECT-TYPE
    		SYNTAX 	IpAddress
    		ACCESS 	read-write
    		STATUS  mandatory
		DESCRIPTION
		     "IP address of peer router at the remote end of this tunnel"
    		::= { accSFTunEntry  4 }
    	accSFTunUDPAddr OBJECT-TYPE
    		SYNTAX 	INTEGER (2000..4000)
    		ACCESS 	read-write
    		STATUS  mandatory
		DESCRIPTION
		     "UDP port number of both ends of this tunnel."
       		DEFVAL { 2764 }               --(DEFVAL in Hex '0xACC')
    		::= { accSFTunEntry  5 }
    	accSFTunAdStat OBJECT-TYPE
    		SYNTAX 	INTEGER {
    			    enabled(1),
    			    disabled(2)
    		}
    		ACCESS 	read-write
    		STATUS  mandatory
		DESCRIPTION
		     "Determines whether or not traffic will be carried on this tunnel."
       	 	DEFVAL { enabled }
    		::= { accSFTunEntry  6 }
    --
    --		The SFT Tunnel Statistics Table
    --
    accSFTStatTable OBJECT-TYPE
        	SYNTAX  SEQUENCE OF AccSFTStatEntry
        	ACCESS  	not-accessible
       	 	STATUS  	mandatory
		DESCRIPTION
		     "Serial Frame Tunnels, which carry HDLC frames
       		       from one serial port to another via an IP network"
    		::= { accSFT 2 }
    accSFTStatEntry OBJECT-TYPE
        	SYNTAX 	AccSFTStatEntry
        	ACCESS 	not-accessible
        	STATUS  mandatory
		DESCRIPTION
			" "
        	INDEX   { accSFTunIndex }
        	::= { accSFTStatTable  1 }
    AccSFTStatEntry ::=
        	SEQUENCE {
    			accSFTunInPkts		Counter,
    			accSFTunOutPkts		Counter
       		 }
    	accSFTunInPkts OBJECT-TYPE
    		SYNTAX 	Counter
    		ACCESS 	read-only
    		STATUS 	mandatory
		DESCRIPTION
		     "Number of HDLC frames received from the serial port and
       		       transmitted along this tunnel"
    		::= { accSFTStatEntry  1 }
    	accSFTunOutPkts OBJECT-TYPE
    		SYNTAX 	Counter
    		ACCESS 	read-only
    		STATUS 	mandatory
		DESCRIPTION
		     "Number of frames read from this tunnel and written
       		       to the associated HDLC port"
    		::= { accSFTStatEntry  2 }

END
