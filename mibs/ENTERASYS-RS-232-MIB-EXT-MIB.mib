ENTERASYS-RS-232-MIB-EXT-MIB DEFINITIONS ::= BEGIN

--  enterasys-rs-232-mib-ext-mib.txt
--
--  Part Number:
--
--

--  This module provides authoritative definitions for Enterasys 
--  Networks' RS232 MIB Extensions functionality.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in 
--  connection with the management of Enterasys Networks products.

--  Copyright June 2011 Enterasys Networks, Inc.

IMPORTS
    MODULE-IDENTITY, OBJECT-TYPE, Integer32
        FROM SNMPv2-SMI
    TEXTUAL-CONVENTION
        FROM SNMPv2-TC
    MODULE-COMPLIANCE, OBJECT-GROUP
        FROM SNMPv2-CONF
    rs232PortEntry
        FROM RS-232-MIB
    EnabledStatus
        FROM P-BRIDGE-MIB
    etsysModules
        FROM ENTERASYS-MIB-NAMES;

etsysRs232MibExtMIB MODULE-IDENTITY
    LAST-UPDATED "201106221450Z"  -- Wed Jun 22 14:50 UTC 2011
    ORGANIZATION "Enterasys Networks, Inc."
    CONTACT-INFO
        "Postal:  Enterasys Networks
                  50 Minuteman Rd.
                  Andover, MA 01810-1008
                  USA
         Phone:   +1 978 684 1000
         E-mail:  support@enterasys.com
         WWW:     http://www.enterasys.com"
   
    DESCRIPTION
        "This MIB module defines a portion of the SNMP MIB under
         the Enterasys Networks enterprise OID that provide 
         extensions to the industry standard RS232-MIB."

    REVISION    "201106221450Z"  -- Wed Jun 22 14:50 UTC 2011
    DESCRIPTION 
        "Added the etsysRs232CtsLinkExtTable."
    
    REVISION    "201011092007Z"  -- Tue Nov  9 20:07 UTC 2010
    DESCRIPTION 
        "The initial version of this MIB module."
    ::= { etsysModules 77 } 


-- -------------------------------------------------------------
-- MIB Objects
-- -------------------------------------------------------------

etsysRs232MibExtObjects   OBJECT IDENTIFIER 
                           ::= { etsysRs232MibExtMIB 1 }

etsysRs232MibExtVt100     OBJECT IDENTIFIER 
                           ::= { etsysRs232MibExtObjects 1 }

etsysRs232MibExtCtsLink   OBJECT IDENTIFIER
                           ::= { etsysRs232MibExtObjects 2 }


-- -------------------------------------------------------------
-- The RS-232 MIB Extension Interface Group
-- -------------------------------------------------------------

etsysRs232Vt100ExtTable OBJECT-TYPE
    SYNTAX       SEQUENCE OF EtsysRs232Vt100ExtEntry
    MAX-ACCESS   not-accessible
    STATUS       current
    DESCRIPTION
        "A table of per interface information that extends the general 
         rs232 port table defined in RFC1659."
    ::= {  etsysRs232MibExtVt100 1 }

etsysRs232Vt100ExtEntry OBJECT-TYPE
    SYNTAX       EtsysRs232Vt100ExtEntry
    MAX-ACCESS   not-accessible
    STATUS       current
    DESCRIPTION
        "An entry containing per interface information."
    AUGMENTS  { rs232PortEntry }
    ::= { etsysRs232Vt100ExtTable 1 }

EtsysRs232Vt100ExtEntry ::=
    SEQUENCE { 
        etsysRs232Vt100DsrEnableState
            EnabledStatus,
        etsysRs232Vt100DsrTimeout
            Integer32
    }

etsysRs232Vt100DsrEnableState OBJECT-TYPE
    SYNTAX       EnabledStatus 
    MAX-ACCESS   read-write
    STATUS       current
    DESCRIPTION
        "This object indicates the current enabled status for 
        transmitting a VT100 Device Status Request (DSR) to an
        attached terminal."
    DEFVAL      { disabled }
    ::= { etsysRs232Vt100ExtEntry 1 }

etsysRs232Vt100DsrTimeout OBJECT-TYPE
    SYNTAX       Integer32
    UNITS        "seconds"
    MAX-ACCESS   read-write
    STATUS       current
    DESCRIPTION
        "This object indicates the current timeout value in
        seconds to wait for a reply to a Device Status Request
        VT100 ANSI escape sequence."
    DEFVAL      { 3 }
    ::= { etsysRs232Vt100ExtEntry 2 }


-- -------------------------------------------------------------
-- The RS-232 MIB Extension CTS Link Group
-- -------------------------------------------------------------

etsysRs232CtsLinkExtTable OBJECT-TYPE
    SYNTAX       SEQUENCE OF EtsysRs232CtsLinkExtEntry
    MAX-ACCESS   not-accessible
    STATUS       current
    DESCRIPTION
        "A table of per interface information that extends the general
         rs232 port table defined in RFC1659."
    ::= {  etsysRs232MibExtCtsLink 1 }

etsysRs232CtsLinkExtEntry OBJECT-TYPE
    SYNTAX       EtsysRs232CtsLinkExtEntry
    MAX-ACCESS   not-accessible
    STATUS       current
    DESCRIPTION
        "An entry containing per interface information."
    AUGMENTS  { rs232PortEntry }
    ::= { etsysRs232CtsLinkExtTable 1 }

EtsysRs232CtsLinkExtEntry ::=
    SEQUENCE {
        etsysRs232CtsLinkEnableState
            EnabledStatus
    }

etsysRs232CtsLinkEnableState OBJECT-TYPE
    SYNTAX       EnabledStatus
    MAX-ACCESS   read-write
    STATUS       current
    DESCRIPTION
        "This object indicates the current enabled status for
        utilizing the Clear To Send input signal as a physical link
        indication."
    DEFVAL      { disabled }
    ::= { etsysRs232CtsLinkExtEntry 1 }


-- -------------------------------------------------------------
-- Conformance Information
-- -------------------------------------------------------------

etsysRs232MibExtConformance OBJECT IDENTIFIER
    ::= { etsysRs232MibExtMIB 2 }

etsysRs232MibExtGroups      OBJECT IDENTIFIER
    ::= { etsysRs232MibExtConformance 1 }

etsysRs232MibExtCompliances OBJECT IDENTIFIER
    ::= { etsysRs232MibExtConformance 2 }


-- -------------------------------------------------------------
-- Units of conformance
-- -------------------------------------------------------------

etsysRs232MibExtVt100DsrGroup OBJECT-GROUP
    OBJECTS {
        etsysRs232Vt100DsrEnableState, 
        etsysRs232Vt100DsrTimeout
    }
    STATUS     current
    DESCRIPTION
        "The group that controls the operational properties of the
        a VT100 Device Status ANSI escape sequence exchange between a
        RS-232-like host and terminal."
    ::= { etsysRs232MibExtGroups 1 }

etsysRs232MibExtCtsLinkGroup OBJECT-GROUP
    OBJECTS {
        etsysRs232CtsLinkEnableState
    }
    STATUS     current
    DESCRIPTION
        "The group that controls the operational properties of the
        physical link detection method utilizing the Clear To Send
        input signal."
    ::= { etsysRs232MibExtGroups 2 }


-- -------------------------------------------------------------
-- Compliance statements
-- -------------------------------------------------------------

etsysRs232MibExtCompliance MODULE-COMPLIANCE
    STATUS     current
    DESCRIPTION
        "The compliance statement for devices that support RS232-MIB
         extensions."

    MODULE
        GROUP       etsysRs232MibExtVt100DsrGroup
        DESCRIPTION
            "This group is mandatory for all devices that support
            the VT100 Device Status ANSI escape sequence exchange between
            a RS-232-like host and terminal."
    ::= { etsysRs232MibExtCompliances 1 }

etsysRs232MibCtsExtCompliance MODULE-COMPLIANCE
    STATUS     current
    DESCRIPTION
        "The compliance statement for devices that support RS232-MIB
         CTS physical link detection extensions."

    MODULE
        GROUP       etsysRs232MibExtCtsLinkGroup
        DESCRIPTION
            "This group is mandatory for all devices that support
            the Clear To Send (CTS) physical link detection method."
    ::= { etsysRs232MibExtCompliances 2 }

END
