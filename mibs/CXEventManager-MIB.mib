CXEventManager-MIB DEFINITIONS ::= BEGIN

IMPORTS
	OBJECT-TYPE		FROM RFC-1212

--  Proprietary Imports
	cxEventManager FROM CXProduct-SMI;


--********************************************************************
--            Event Manager Module objects
--********************************************************************

cxEvmLoggingCPU OBJECT-TYPE
	SYNTAX  INTEGER (0..16)
	ACCESS  read-write
	STATUS  mandatory
	DESCRIPTION
"Determines whether the events generated by the software will be logged
locally or on a centralised CPU card within the chassis.  

A value of 0 or a value equal to the local slot number will enable local 
Event Manager processing (events filtering, logging and trap generation). 
Other values determines the central Event Manager CPU slot number (1 to 16).
When central Event Manager is enabled, all the events manager messages are
filtered locally and then sent to the CPU card specified by this object for 
recording.

Centralised event manager is avaliable only in CX1000 and CX2000 products.  
In single CPU units, like the CX900 or the CX950, the value will be fixed 
to 0 allowing local Event Manager processing only.

A log file can be read by the console through UI module.  The syntax of  
the reading command is defined as follows:

Command:	readlog    <logfile>   <option>

Where:	<logfile>   - the name of the logfile which contains the events information.
		<option>    - optionnal parameter: 0 to read (default), 1 to read and delete
		              items as they are read, and 2 to delete the enntire file.

Range of Values: 0 to 16

Default Value: 0
Configuration Changed: operative"
	::= { cxEventManager 1 }

cxEvmTriggerFunction OBJECT-TYPE
	SYNTAX  INTEGER (0..255)
	ACCESS  read-write
	STATUS  mandatory
	DESCRIPTION
"Activates the Event Manager triggering mechanism.  This triggering mechanism 
will send a MSG_EVM_TRIG type message that will contain cxEvmTriggerFunction 
and cxEvmTrigDestSapId to the module specified by cxEvmTrigDestTaskId.  

Events manager functions are defined by module programmer for each module and are used
to generate event to be sent to the Event Manager when specific conditions occurs 
such as errors, status, etc... .                                        

Since writing this object will send a function trigger, it should be used carefully by
advised users only.

Range of Values: 0 to 255

Default Value: 0
Configuration Changed: operative"
	::= { cxEventManager 2 }

cxEvmTrigDestSelector OBJECT-TYPE
	SYNTAX  INTEGER (0..255)
	ACCESS  read-write
	STATUS  mandatory
	DESCRIPTION
"Specifies the module to which the Event Manager triggering function
will send the triggering message.          

Modules are the different types of software that reside in the unit, 
for example the Frame Relay module or the Voice module. Modules ID are 
defined in the \sm\taskid.h file.

Range of Values: 0 to 255

Default Value: 0
Configuration Changed: operative"
	::= { cxEventManager 3 }

cxEvmTrigDestSapId OBJECT-TYPE
	SYNTAX  INTEGER (0..255)
	ACCESS  read-write
	STATUS  mandatory
	DESCRIPTION
"Specifies the Sap ID to which the Event Manager triggering function
should be applied. 

Range of Values: 0 to 255

Default Value: 0
Configuration Changed: operative"
	::= { cxEventManager 4 }

cxEvmTrigArgument1 OBJECT-TYPE
	SYNTAX  INTEGER (0..255)
	ACCESS  read-write
	STATUS  mandatory
	DESCRIPTION
"Specifies the value of the first optional parameter that can be used
with the triggering function.

Range of Values: 0 to 255

Default Value: 0
Configuration Changed: operative"
	::= { cxEventManager 5 }

cxEvmTrigArgument2 OBJECT-TYPE
	SYNTAX  INTEGER (0..255)
	ACCESS  read-write
	STATUS  mandatory
	DESCRIPTION
"Specifies the value of the second optional parameter that can be used
with the triggering function.

Range of Values: 0 to 255

Default Value: 0
Configuration Changed: operative"
	::= { cxEventManager 6 }

cxEvmTrigDestCPU OBJECT-TYPE
	SYNTAX  INTEGER (0..16)
	ACCESS  read-write
	STATUS  mandatory
	DESCRIPTION
"Specifies the destination CPU of the trigger function.  For centralised 
CPU only.  A value of 0 means the local CPU.  For single CPU products, 
this value will be fixed to 0.

Range of Values: 0 to 16

Default Value: 0
Configuration Changed: operative"
	::= { cxEventManager 7 }

--********************************************************************
--            Event Manager Log File Table
--********************************************************************

cxEvmLogFileTable OBJECT-TYPE
	SYNTAX  SEQUENCE OF CxEvmLogFileEntry
	ACCESS  not-accessible
	STATUS  mandatory
	DESCRIPTION
		"A table that defines a log file id, size, and filters applied to 
		this file. When saving configuration, the table is saved and when 
		system restarts, the table is initialised according to the saved 
		configuration."
	REFERENCE
		" "
	::= { cxEventManager 8 }

cxEvmLogFileEntry OBJECT-TYPE
	SYNTAX  CxEvmLogFileEntry 
	ACCESS  not-accessible
	STATUS  mandatory
	DESCRIPTION
		" Entry of cxEvmLogFileTable."
	INDEX { cxEvmLogFileId } 
	::= { cxEvmLogFileTable 1 }

CxEvmLogFileEntry ::=
	SEQUENCE {
		cxEvmLogFileId  			INTEGER,
		cxEvmLogFileRowStatus   	INTEGER,
		cxEvmLogFileMaxSize			INTEGER,
		cxEvmLogFileCurSize			INTEGER,
		cxEvmLogFileCPUFilter 		OCTET STRING,
		cxEvmLogFileEvLogFilter		OCTET STRING,
		cxEvmLogFileEvTrapFilter	OCTET STRING
	}

cxEvmLogFileId  OBJECT-TYPE
	SYNTAX  INTEGER (0..20)
	ACCESS  read-only
	STATUS  mandatory
	DESCRIPTION
"Displays the index index of the log file. The software assigns this 
index automatically to uniquely identify the log file. The index acts as 
a pointer to this table.

You cannot modify this object. It is a display that the software provides.

The first entry of the table is reserved by the event manager as a 
special log file for screen display of the events.  You can define 
up to 19 logfiles.  

After a coldstart, a default logfile (LOG1.EVM) is defined in the second entry 
of the table and will record all events. When an entry of the filetable is activated, 
a file is created with the filename LOGx.EVM where 'x' is the index of the table.

Range of Values: 0 to 20

Default Value: none"

	::= { cxEvmLogFileEntry 1 }

cxEvmLogFileRowStatus OBJECT-TYPE
	SYNTAX  INTEGER {
				invalid (1),
				valid	(2)
			  } 
	ACCESS  read-write
	STATUS  mandatory
	DESCRIPTION
"Determines the status of the objects in a table row.

Options:
invalid (1): row is flagged; after the next reset the values will be 
disabled and the row will be deleted from the table.

valid (2): values are enabled.

Default Value: valid (2)

Configuration Changed: operative

	DEFVAL { valid }	         "
	::= { cxEvmLogFileEntry 2 }

cxEvmLogFileMaxSize  OBJECT-TYPE
	SYNTAX  INTEGER  
	ACCESS  read-write
	STATUS  mandatory
	DESCRIPTION
"Determines the maximum size, in KBytes, of the logfile specified by 
cxEvmLogFileId.

When determining the size you must take into consideration the size of all 
existing logfiles. The maximum size of a single file can not exceed 
1000 Kbytes, and the sum of all the logfiles size cannot exceed 10 % of the
memory available after system initialisation.  This number can vary according 
to the product, the hardware configuration, and to the software used.  

It is the responsability of the user to verify that the memory size 
specified is allowed by the system.  If the system can not allow the
specified memory size, the memory size value will be downsized automatically
by the software.

Note: After a reset, the system must re-evaluate the RAM distribution and 
therefore it can reduce the maximum size value according to the memory
available. 

Range of Values: 1 to 1000

Default Value: none

Configuration Changed: operative "

	::= { cxEvmLogFileEntry 3 }

cxEvmLogFileCurSize  OBJECT-TYPE
	SYNTAX  INTEGER  
	ACCESS  read-write
	STATUS  mandatory
	DESCRIPTION
"Determines the current size, in KBytes, of the logfile specified by 
cxEvmLogFileId.

You cannot modify this object. It is a display that the software provides.

Range of Values: 1024 to 1048576

Default Value: none"

	::= { cxEvmLogFileEntry 4 }
                                 
cxEvmLogFileCPUFilter  OBJECT-TYPE
    SYNTAX  OCTET STRING (SIZE (2))
	ACCESS  read-write
	STATUS  mandatory
	DESCRIPTION
"This field consists of 2 hexadecimal octets.  The value represents a bit field
used to determines which CPU cards are to be filtered out.  Each bit in this 
object is mapped to a specific CPU card within a chassis. Turning the 
bit off (0) causes the events coming from the associated CPU card to 
filtered out. Setting a bit to 1 will enable event manager processing
for the associated CPU card.

- bit 0:   CPU card in slot #1  (0: filter out, 1:continue filtering process)
- bit 1:   CPU card in slot #2  (0: filter out, 1:continue filtering process)
- bit 2:   CPU card in slot #3  (0: filter out, 1:continue filtering process)
- bit 3:   CPU card in slot #4  (0: filter out, 1:continue filtering process)
- bit 4:   CPU card in slot #5  (0: filter out, 1:continue filtering process)
- bit 5:   CPU card in slot #6  (0: filter out, 1:continue filtering process)
- bit 6:   CPU card in slot #7  (0: filter out, 1:continue filtering process)
- bit 7:   CPU card in slot #8  (0: filter out, 1:continue filtering process)
- bit 8:   CPU card in slot #9  (0: filter out, 1:continue filtering process)
- bit 9:   CPU card in slot #10 (0: filter out, 1:continue filtering process)
- bit 10:  CPU card in slot #11 (0: filter out, 1:continue filtering process)
- bit 11:  CPU card in slot #12 (0: filter out, 1:continue filtering process)
- bit 12:  CPU card in slot #13 (0: filter out, 1:continue filtering process)
- bit 13:  CPU card in slot #14 (0: filter out, 1:continue filtering process)
- bit 14:  CPU card in slot #15 (0: filter out, 1:continue filtering process)
- bit 15:  CPU card in slot #16 (0: filter out, 1:continue filtering process)

Range of Values: 0000 to ffff (hexadecimal)

Default Value: 0000"

	::= { cxEvmLogFileEntry 5 }
                                 
cxEvmLogFileEvLogFilter   OBJECT-TYPE
    SYNTAX  OCTET STRING (SIZE (2))
	ACCESS  read-write
	STATUS  mandatory
	DESCRIPTION
"This field consists of 2 hexadecimal octets.  The value represents a bit field
used to determines which events are to be filtered out according to their event 
type.  Each bit in this object is mapped to a specific event type. 
Turning a bit off (0) causes the associated events to be filtered out.  
Setting a bit to 1 will allow the event manager process to log the event 
message received.

- bit 0:    error type		(0: filter out, 1:log event)
- bit 1:    warning type	(0: filter out, 1:log event)
- bit 2:    status type		(0: filter out, 1:log event)
- bit 3:    trace type		(0: filter out, 1:log event)
- bit 4:    user1 type		(0: filter out, 1:log event)
- bit 5:    user2 type		(0: filter out, 1:log event)
- bit 6:    user3 type		(0: filter out, 1:log event)
- bit 7:    user4 type		(0: filter out, 1:log event)
- bit 8:    user5 type		(0: filter out, 1:log event)
- bit 9:    user6 type		(0: filter out, 1:log event)
- bit 10:   user7 type		(0: filter out, 1:log event)
- bit 11:   user8 type		(0: filter out, 1:log event)
- bit 12:   user9 type		(0: filter out, 1:log event)
- bit 13:	user10 type		(0: filter out, 1:log event)
- bit 14:	user11 type		(0: filter out, 1:log event)
- bit 15:	user12 type		(0: filter out, 1:log event)

Range of Values: 0000 to ffff (hexadecimal)

Default Value: 0000"

	::= { cxEvmLogFileEntry 6 }
                                 
cxEvmLogFileEvTrapFilter   OBJECT-TYPE
    SYNTAX  OCTET STRING (SIZE (2))
	ACCESS  read-write
	STATUS  mandatory
	DESCRIPTION
"The field consists of 2 hexadecimal octets.  The value represents a bit field
used to determines which events are to generate SNMP traps according to their event 
type.  Each bit in this object is mapped to a specific event type. 
Setting a bit to 1 will cause SNMP trap generation for the associated event type.
Turning a bit off (0) disables SNMP trap generation for the associated event.  

- bit 0:    error type		(0: filter out, 1:send SNMP trap)
- bit 1:    warning type	(0: filter out, 1:send SNMP trap)
- bit 2:    status type		(0: filter out, 1:send SNMP trap)
- bit 3:    trace type		(0: filter out, 1:send SNMP trap)
- bit 4:    user1 type		(0: filter out, 1:send SNMP trap)
- bit 5:    user2 type		(0: filter out, 1:send SNMP trap)
- bit 6:    user3 type		(0: filter out, 1:send SNMP trap)
- bit 7:    user4 type		(0: filter out, 1:send SNMP trap)
- bit 8:    user5 type		(0: filter out, 1:send SNMP trap)
- bit 9:    user6 type		(0: filter out, 1:send SNMP trap)
- bit 10:   user7 type		(0: filter out, 1:send SNMP trap)
- bit 11:   user8 type		(0: filter out, 1:send SNMP trap)
- bit 12:   user9 type		(0: filter out, 1:send SNMP trap)
- bit 13:	user10 type		(0: filter out, 1:send SNMP trap)
- bit 14:	user11 type		(0: filter out, 1:send SNMP trap)
- bit 15:	user12 type		(0: filter out, 1:send SNMP trap)

Range of Values: 0000 to ffff (hexadecimal)

Default Value: 0000"

	::= { cxEvmLogFileEntry 7 }

END
