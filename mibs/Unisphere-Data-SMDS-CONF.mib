-- *****************************************************************************
-- Unisphere-Data-SMDS-CONF
--
-- SNMP Agent Capabilities definitions for the Smds MIB.
--
-- Copyright (c) 2001 Unisphere Networks, Inc.  All rights reserved.
-- *****************************************************************************

Unisphere-Data-SMDS-CONF DEFINITIONS ::= BEGIN

IMPORTS
    MODULE-IDENTITY
        FROM SNMPv2-SMI
    AGENT-CAPABILITIES
        FROM SNMPv2-CONF
    usDataAgents
        FROM Unisphere-Data-Agents
    usdSmdsGroup,
    usdSmdsGroup2
        FROM Unisphere-Data-SMDS-MIB;

usdSmdsAgent MODULE-IDENTITY
    LAST-UPDATED "200109201457Z"  -- 20-Sep-01 10:57 AM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Switched Multimegabit Data
        Service (SMDS) management component of the SNMP agent in the Unisphere
        Routing Switch family of products."
    -- Revision History
    REVISION    "200109201457Z"  -- 20-Sep-01 10:57 AM EDT  - RX 4.0
    DESCRIPTION
        "Added support for major and sub interfaces."
    REVISION    "200103301430Z"  -- 30-Mar-01 09:30 AM EST  - RX 3.2
    DESCRIPTION
        "The initial release of this management information module."
    ::= { usDataAgents 46 }

usdSmdsAgentV1 AGENT-CAPABILITIES
    PRODUCT-RELEASE
        "Version 1 of the Switched Multimegabit Data Service (SMDS) management
        component of the Unisphere Routing Switch SNMP agent.  This version of
        the SMDS component was supported in the Unisphere RX 3.1 thru 3.x system
        releases."
    STATUS      obsolete
    DESCRIPTION
        "The MIB supported by the SNMP agent for the SMDS application in the
        Unisphere Routing Switch.  These capabilities became obsolete when
        support was added for major and sub interfaces"
    SUPPORTS    Unisphere-Data-SMDS-MIB
        INCLUDES  {
            usdSmdsGroup }
    ::= { usdSmdsAgent 1 }

usdSmdsAgentV2 AGENT-CAPABILITIES
    PRODUCT-RELEASE
        "Version 2 of the Switched Multimegabit Data Service (SMDS) management
        component of the Unisphere Routing Switch SNMP agent.  This version of
        the SMDS component is supported in the Unisphere RX 4.0 and subsequent
        system releases."
    STATUS      current
    DESCRIPTION
        "The MIB supported by the SNMP agent for the SMDS application in the
        Unisphere Routing Switch."
    SUPPORTS    Unisphere-Data-SMDS-MIB
        INCLUDES  {
            usdSmdsGroup2 }
    ::= { usdSmdsAgent 2 }

END
