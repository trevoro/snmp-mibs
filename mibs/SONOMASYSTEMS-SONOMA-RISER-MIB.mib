-- |**********************************************************************|
 -- | Copyright 1999 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : risermib.def
 --
 -- DESCRIPTION : This file contains MIB information specific to the
 --               Sonoma Systems proprietary designed Riser-M card.
 --
 -- ARCHIVE : $Archive:   M:\pvcs\pvcsproj\sonoma3\src\mib\slipmib.dev  $
 -- REVISION: $Revision:   1.5  $
 -- AUTHOR  : $Author:   FREEVE  $
 -- DATE    : $Date:   Nov 13 1998 10:33:40  $


SONOMASYSTEMS-SONOMA-RISER-MIB DEFINITIONS ::= BEGIN

      IMPORTS
        OBJECT-TYPE
        FROM RFC-1212
		sonomaSeries 
        FROM SONOMASYSTEMS-SONOMA-MIB;


  --  This MIB module uses the extended OBJECT-TYPE macro as
  --  defined in [14];

    -- Define all the groups supported on the Sonoma Series
    -- of products.

    sonomaRiser   OBJECT IDENTIFIER ::= { sonomaSeries 12 }
     
    --
    -- FAN status table
    --

    riserFanTable  OBJECT-TYPE
        SYNTAX  SEQUENCE OF RiserFanEntry
        ACCESS  not-accessible
        STATUS  mandatory
        DESCRIPTION
            "A table that records the status of all fans in the chassis. 
             This is a read only table.  SNMP management application cannot 
             add or remove any rows.  The number of rows in this table is 
             determined by the number of fans installed in the chassis."
        ::= { sonomaRiser 1 }
 
    riserFanEntry OBJECT-TYPE
        SYNTAX  RiserFanEntry
        ACCESS  not-accessible
        STATUS  mandatory
        DESCRIPTION
            "A list of information for each fan."
        INDEX  { riserFanIndex }
        ::= { riserFanTable 1 }

    RiserFanEntry ::= SEQUENCE {
        riserFanIndex        INTEGER,          
        riserFanStatus       INTEGER
        }

    riserFanIndex OBJECT-TYPE
        SYNTAX  INTEGER
        ACCESS  read-only
        STATUS  mandatory
        DESCRIPTION
          "The value of this object uniquely identifies the fan in a 
           device chassis."
        ::= { riserFanEntry 1 }

    riserFanStatus  OBJECT-TYPE
        SYNTAX  INTEGER {
                    ok (1),
                    fail (2)
                }
        ACCESS  read-only
        STATUS  mandatory
        DESCRIPTION
            "Status of the fan:             
               ok(1) if no problems,             
               fail(2) if something is wrong with the fan."
        ::= { riserFanEntry 2 }


    -- The Thermal Group contains objects related to monitoring the
    -- temperature inside the chassis.

    thermalGroup OBJECT IDENTIFIER ::= { sonomaRiser 2 }

    --
    -- Thermal Monitoring objects
    --

    riserTemperatureC OBJECT-TYPE
        SYNTAX  INTEGER
        ACCESS  read-only
        STATUS  mandatory
        DESCRIPTION
            "This object is the system temperature measured in Celsius."
        ::= { thermalGroup 1 }

END
