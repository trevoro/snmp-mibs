BayNetworks-DHCP-MIB DEFINITIONS ::= BEGIN

    IMPORTS

      IpAddress, Counter, Gauge
        FROM RFC1155-SMI
      OBJECT-TYPE
        FROM RFC-1212
      DisplayString
        FROM RFC1213-MIB
      wfDhcpServerGroup
        FROM Wellfleet-COMMON-MIB;

    wfDhcpSvrGroup OBJECT IDENTIFIER ::= { wfDhcpServerGroup 1 }

    wfDhcpSvrGeneral OBJECT IDENTIFIER ::= { wfDhcpSvrGroup 1}

    wfDhcpSvrDelete OBJECT-TYPE
        SYNTAX	INTEGER {
    		    created(1),
    		    deleted(2)
    		}
        ACCESS	read-write
        STATUS	mandatory
        DESCRIPTION
                "Created/Deleted: if set to Deleted, the DHCP server is
                removed from this platform."
        DEFVAL	{ created }
        ::= { wfDhcpSvrGeneral 1 }

    wfDhcpSvrDisable OBJECT-TYPE
        SYNTAX	INTEGER {
    		    enabled(1),
    		    disabled(2)
    		}
        ACCESS	read-write
        STATUS	mandatory
        DESCRIPTION
                "Enable/Disable: controls whether the DHCP server is
                enabled or disabled on this platform."
        DEFVAL	{ disabled }
        ::= { wfDhcpSvrGeneral 2 }

    wfDhcpSvrMgrIpAddr OBJECT-TYPE
        SYNTAX IpAddress
        ACCESS read-write
        STATUS mandatory
        DESCRIPTION
               "IP Address of the NetID DHCP Server Manager serving
               this platform instance."
        ::= { wfDhcpSvrGeneral 3 }

    wfDhcpSvrMgrTcpPort OBJECT-TYPE
        SYNTAX INTEGER
        ACCESS read-write
        STATUS mandatory
        DESCRIPTION
               "The remote TCP port number over which the DHCP Server
               communicates with the NetID DHCP Server Manager."
        ::= { wfDhcpSvrGeneral 4 }

    wfDhcpSvrConfDetPings OBJECT-TYPE
        SYNTAX INTEGER
        ACCESS read-write
        STATUS mandatory
        DESCRIPTION
               "Number of ping attempts that should be made to a
               prospective client IP address to detect a possible
               conflict before declaring it unused and therefore
               available."
        DEFVAL { 1 }
        ::= { wfDhcpSvrGeneral 5 }

    wfDhcpSvrIcmpTmo OBJECT-TYPE
        SYNTAX INTEGER
        ACCESS read-write
        STATUS mandatory
        DESCRIPTION
               "Amount of time, in milliseconds, to wait for
               a conflict detection ping to time out."
        DEFVAL { 750 }
        ::= { wfDhcpSvrGeneral 6 }

    wfDhcpSvrSafeModeDisable OBJECT-TYPE
        SYNTAX INTEGER {
	            enabled(1),
	            disabled(2)
               }
        ACCESS read-write
        STATUS mandatory
        DESCRIPTION
               "Specifies whether the DHCP Server should wait until it
               gets acknowledgment of successful commitment of a lease
               from the NetID DHCP Server Manager before sending a
               lease-granted acknowledgment back to the DHCP Client.
               If set to Enabled, the DHCP Server will wait for the
               NetID DHCP Server Manager to confirm successful commit.
               If set to Disabled, the DHCP Server will immediately
               send back a lease-granted acknowledgement to the DHCP
               Client, without awaiting a commit-succeeded
               acknowledgment from the NetID DHCP Server Manager."
        DEFVAL { enabled }
        ::= { wfDhcpSvrGeneral 7 }

    wfDhcpSvrMaxPendingLeases OBJECT-TYPE
        SYNTAX INTEGER
        ACCESS read-write
        STATUS mandatory
        DESCRIPTION
               "Maximum number of lease requests to the DHCP Server
               which are pending commitment by the NetID DHCP Server
               Manager. Once there are wfDhcpSvrMaxPendingLeases lease
               requests pending, all new lease requests will be
               dropped until the number of requests pending decreases
               to wfDhcpSvrMaxPendingLeases/2."
        DEFVAL { 2 }
        ::= { wfDhcpSvrGeneral 8 }

    wfDhcpSvrDebugLevel OBJECT-TYPE
        SYNTAX INTEGER
        ACCESS read-write
        STATUS mandatory
        DESCRIPTION
               "Maximum debug level for optional debug messages from
               the DHCP Server.  Normally, only messages with a debug
               level of 0 will be logged.  The higher this attribute
               is made (up to a maximum of 10), the more messages will
               be logged.  Since the logging of additional information
               can fill the log very rapidly and cause loss of other
               information, this attribute should only be changed to
               resolve critical problems."
        DEFVAL { 0 }
        ::= { wfDhcpSvrGeneral 9 }

    wfDhcpSvrMgrLocIpAddr OBJECT-TYPE
        SYNTAX IpAddress
        ACCESS read-write
        STATUS mandatory
        DESCRIPTION
               "IP Address the DHCP Server uses to identify itself
               to NetID DHCP Server Manager serving this platform
               instance.  Should correspond to an actual local
               interface address on the router."
        ::= { wfDhcpSvrGeneral 10 }



        
-- End of non-tabular base server records.

wfDhcpSvrIntfTable OBJECT-TYPE
        SYNTAX SEQUENCE OF WfDhcpSvrIntfEntry
        ACCESS not-accessible
        STATUS mandatory
        DESCRIPTION
               "This table contains per-interface status information
               for DHCP Server operation."
        ::= { wfDhcpSvrGroup 2 }

    wfDhcpSvrIntfEntry OBJECT-TYPE
        SYNTAX WfDhcpSvrIntfEntry
        ACCESS not-accessible
        STATUS mandatory
        DESCRIPTION
               "A DHCP Server network interface status description."
        INDEX { wfDhcpSvrIntfAddress }
        ::= { wfDhcpSvrIntfTable 1 }

    WfDhcpSvrIntfEntry ::= SEQUENCE {
        wfDhcpSvrIntfAddress
        IpAddress,
        wfDhcpSvrIntfState
        INTEGER,
        wfDhcpSvrIntfPendLsCnt
        Gauge,
        wfDhcpSvrIntfActLsCnt
        Gauge,
        wfDhcpSvrIntfCommits
        Counter,
        wfDhcpSvrIntfCommitFails
        Counter,
        wfDhcpSvrIntfCommitTmos
        Counter,
        wfDhcpSvrIntfIllegPkts
        Counter,
        wfDhcpSvrIntfDiscovers
        Counter,
        wfDhcpSvrIntfBadDiscovers
        Counter,
        wfDhcpSvrIntfReassgnLeases
        Counter,
        wfDhcpSvrIntfNoFreeLeases
        Counter,
        wfDhcpSvrIntfDropdLeaseRqs
        Counter,
        wfDhcpSvrIntfOffers
        Counter,
        wfDhcpSvrIntfRequests
        Counter,
        wfDhcpSvrIntfBadRequests
        Counter,
        wfDhcpSvrIntfReleases
        Counter,
        wfDhcpSvrIntfBadReleases
        Counter,
        wfDhcpSvrIntfDeclines
        Counter,
        wfDhcpSvrIntfBadDeclines
        Counter,
        wfDhcpSvrIntfInforms
        Counter,
        wfDhcpSvrIntfBadInforms
        Counter,
        wfDhcpSvrIntfAddrConflict
        Counter
        }

    wfDhcpSvrIntfAddress OBJECT-TYPE
        SYNTAX IpAddress
        ACCESS read-only
        STATUS mandatory
        DESCRIPTION
               "Address of this network interface."
        ::= { wfDhcpSvrIntfEntry 1 }

    wfDhcpSvrIntfState OBJECT-TYPE
        SYNTAX INTEGER {
		   up(1),
		   down(2)
               }
        ACCESS read-only
        STATUS mandatory
        DESCRIPTION
               "The state of the DHCP Server on this network
               interface."
        ::= { wfDhcpSvrIntfEntry 2 }

    wfDhcpSvrIntfPendLsCnt OBJECT-TYPE
        SYNTAX Gauge
        ACCESS read-only
        STATUS mandatory
        DESCRIPTION
               "Number of DHCP leases pending commitment by the NetID
               Server Manager on this network interface."
        ::= { wfDhcpSvrIntfEntry 3 }

    wfDhcpSvrIntfActLsCnt OBJECT-TYPE
        SYNTAX Gauge
        ACCESS read-only
        STATUS mandatory
        DESCRIPTION
               "Number of DHCP leases currently active and committed
               by the NetID Server Manager on this network interface."
        ::= { wfDhcpSvrIntfEntry 4 }

    wfDhcpSvrIntfCommits OBJECT-TYPE
        SYNTAX Counter
        ACCESS read-only
        STATUS mandatory
        DESCRIPTION
               "Number of Commit requests made by the DHCP Server for
               clients on this network interface."
        ::= { wfDhcpSvrIntfEntry 5 }

    wfDhcpSvrIntfCommitFails OBJECT-TYPE
        SYNTAX Counter
        ACCESS read-only
        STATUS mandatory
        DESCRIPTION
               "Number of Commit-failed responses to the DHCP Server
               for clients on this network interface."
        ::= { wfDhcpSvrIntfEntry 6 }

    wfDhcpSvrIntfCommitTmos OBJECT-TYPE
        SYNTAX Counter
        ACCESS read-only
        STATUS mandatory
        DESCRIPTION
               "Number of times the NetID DHCP Server Manager did not
               respond to a commit request from the DHCP Server 
               for clients on this network interface."
        ::= { wfDhcpSvrIntfEntry 7 }

    wfDhcpSvrIntfIllegPkts OBJECT-TYPE
        SYNTAX Counter
        ACCESS read-only
        STATUS mandatory
        DESCRIPTION
               "Number of DHCP packets with no legal type sent to the
               DHCP Server for clients on this network interface."
        ::= { wfDhcpSvrIntfEntry 8 }

    wfDhcpSvrIntfDiscovers OBJECT-TYPE
        SYNTAX Counter
        ACCESS read-only
        STATUS mandatory
        DESCRIPTION
               "Number of DISCOVER packets sent to DHCP Server by
               clients on this network interface."
        ::= { wfDhcpSvrIntfEntry 9 }

    wfDhcpSvrIntfBadDiscovers OBJECT-TYPE
        SYNTAX Counter
        ACCESS read-only
        STATUS mandatory
        DESCRIPTION
               "Number of badly-formed DISCOVER packets sent to DHCP
               Server for clients on this network interface."
        ::= { wfDhcpSvrIntfEntry 10 }

    wfDhcpSvrIntfReassgnLeases OBJECT-TYPE
        SYNTAX Counter
        ACCESS read-only
        STATUS mandatory
        DESCRIPTION
               "Number of client requests for leases already
               reassigned to another client of DHCP Server on this
               network interface."
        ::= { wfDhcpSvrIntfEntry 11 }

    wfDhcpSvrIntfNoFreeLeases OBJECT-TYPE
        SYNTAX Counter
        ACCESS read-only
        STATUS mandatory
        DESCRIPTION
               "Number of times DHCP Server had no leases available to
               offer a client in response to a DHCPDISCOVER request on
               this network interface."
        ::= { wfDhcpSvrIntfEntry 12 }

    wfDhcpSvrIntfDropdLeaseRqs OBJECT-TYPE
        SYNTAX Counter
        ACCESS read-only
        STATUS mandatory
        DESCRIPTION
               "Number of DHCP client requests for a lease on this
               interface which were dropped by the DHCP Server because
               the total number of leases pending commitment exceeded
               the threshhold for accepting new leases at the time the
               client made the request."
        ::= { wfDhcpSvrIntfEntry 13 }

    wfDhcpSvrIntfOffers OBJECT-TYPE
        SYNTAX Counter
        ACCESS read-only
        STATUS mandatory
        DESCRIPTION
               "Number of offers (DHCPOFFER messages) sent out by DHCP
               Server for clients on this network interface."
        ::= { wfDhcpSvrIntfEntry 14 }

    wfDhcpSvrIntfRequests OBJECT-TYPE
        SYNTAX Counter
        ACCESS read-only
        STATUS mandatory
        DESCRIPTION
               "Number of DHCPREQUEST packets sent to DHCP Server by
               clients on this network interface."
        ::= { wfDhcpSvrIntfEntry 15 }

    wfDhcpSvrIntfBadRequests OBJECT-TYPE
        SYNTAX Counter
        ACCESS read-only
        STATUS mandatory
        DESCRIPTION
               "Number of badly-formed DHCPREQUEST packets sent to
               DHCP Server by clients on this network interface."
        ::= { wfDhcpSvrIntfEntry 16 }

    wfDhcpSvrIntfReleases OBJECT-TYPE
        SYNTAX Counter
        ACCESS read-only
        STATUS mandatory
        DESCRIPTION
               "Number of DHCPRELEASE packets sent to DHCP Server by
               clients on this network interface."
        ::= { wfDhcpSvrIntfEntry 17 }

    wfDhcpSvrIntfBadReleases OBJECT-TYPE
        SYNTAX Counter
        ACCESS read-only
        STATUS mandatory
        DESCRIPTION
               "Number of badly-formed DHCPRELEASE packets sent to
               DHCP Server by clients on this network interface."
        ::= { wfDhcpSvrIntfEntry 18 }

    wfDhcpSvrIntfDeclines OBJECT-TYPE
        SYNTAX Counter
        ACCESS read-only
        STATUS mandatory
        DESCRIPTION
               "Number of DHCPDECLINE packets sent to DHCP Server by
               clients on this network interface."
        ::= { wfDhcpSvrIntfEntry 19 }

    wfDhcpSvrIntfBadDeclines OBJECT-TYPE
        SYNTAX Counter
        ACCESS read-only
        STATUS mandatory
        DESCRIPTION
               "Number of badly-formed DHCPDECLINE packets sent to
               DHCP Server by clients on this network interface."
        ::= { wfDhcpSvrIntfEntry 20 }

    wfDhcpSvrIntfInforms OBJECT-TYPE
        SYNTAX Counter
        ACCESS read-only
        STATUS mandatory
        DESCRIPTION
                "Number of DHCPINFORM packets sent to DHCP Server by
               non-lease clients on this network interface."
        ::= { wfDhcpSvrIntfEntry 21 }

    wfDhcpSvrIntfBadInforms OBJECT-TYPE
        SYNTAX Counter
        ACCESS read-only
        STATUS mandatory
        DESCRIPTION
               "Number of badly-formed DHCPINFORM packets sent to DHCP
               Server by non-lease clients on this network interface."
        ::= { wfDhcpSvrIntfEntry 22 }

    wfDhcpSvrIntfAddrConflict OBJECT-TYPE
        SYNTAX Counter
        ACCESS read-only
        STATUS mandatory
        DESCRIPTION
               "Number of times the conflict detection phase of DHCP
               lease assignment detected a host using the IP address
               the DHCP Server was working to assign.  This normally
               indicates that the detected host is using an IP address
               which it doesn't own."
        ::= { wfDhcpSvrIntfEntry 23 }


    wfDhcpSvrLeaseTable OBJECT-TYPE
        SYNTAX SEQUENCE OF WfDhcpSvrLeaseEntry
        ACCESS not-accessible
        STATUS mandatory
        DESCRIPTION
               "This table contains per-interface, per-lease status
               information for DHCP Server operation."
        ::= { wfDhcpSvrGroup 3 }

    wfDhcpSvrLeaseEntry OBJECT-TYPE
        SYNTAX WfDhcpSvrLeaseEntry
        ACCESS not-accessible
        STATUS mandatory
        DESCRIPTION
               "A DHCP Server lease description."
        INDEX { wfDhcpSvrLeaseAddress }
        ::= { wfDhcpSvrLeaseTable 1 }

    WfDhcpSvrLeaseEntry ::= SEQUENCE {
        wfDhcpSvrLeaseState
        INTEGER,
        wfDhcpSvrLeaseRetries
        INTEGER,
        wfDhcpSvrLeaseAddress
        IpAddress,
        wfDhcpSvrLeaseExpir
        INTEGER,
        wfDhcpSvrLeaseDuration
        INTEGER,
        wfDhcpSvrLeaseHwId
        OCTET STRING,
        wfDhcpSvrLeaseClId
        OCTET STRING,
        wfDhcpSvrLeaseFqdn
        DisplayString
	}

    wfDhcpSvrLeaseState OBJECT-TYPE
        SYNTAX INTEGER {
                  committed(1),
                  pending(2),
                  pendingfail(3),
                  pendingtmo(4)
               }
        ACCESS read-only
        STATUS mandatory
        DESCRIPTION
               "The current state of a lease.  It may be committed in
               the NetID Server Manager, pending commitment, or
               pending with an already failed or timed-out commitment
               attempt."
        ::= { wfDhcpSvrLeaseEntry 1 }

    wfDhcpSvrLeaseRetries OBJECT-TYPE
        SYNTAX INTEGER
        ACCESS read-only
        STATUS mandatory
        DESCRIPTION
               "Number of lease commit retries for this lease either
               because of reported commit fail from NetID Server
               Manager or because of timeout on commit request.  Zero
               if lease pending or committed."
        ::= { wfDhcpSvrLeaseEntry 2 }

    wfDhcpSvrLeaseAddress OBJECT-TYPE
        SYNTAX IpAddress
        ACCESS read-only
        STATUS mandatory
        DESCRIPTION
               "Leased IP Address of client."
        ::= { wfDhcpSvrLeaseEntry 3 }

    wfDhcpSvrLeaseExpir OBJECT-TYPE
        SYNTAX INTEGER
        ACCESS read-only
        STATUS mandatory
        DESCRIPTION
               "Time when lease will expire.  Expressed as number
               of seconds since beginning of January 1, 1970."
        ::= { wfDhcpSvrLeaseEntry 4 }

    wfDhcpSvrLeaseDuration OBJECT-TYPE
        SYNTAX INTEGER
        ACCESS read-only
        STATUS mandatory
        DESCRIPTION
               "Agreed-upon duration of lease, in seconds."
        ::= { wfDhcpSvrLeaseEntry 5 }

    wfDhcpSvrLeaseHwId OBJECT-TYPE
        SYNTAX OCTET STRING
        ACCESS read-only
        STATUS mandatory
        DESCRIPTION
               "Hardware identifier of client holding the lease."
        ::= { wfDhcpSvrLeaseEntry 6 }

    wfDhcpSvrLeaseClId OBJECT-TYPE
        SYNTAX OCTET STRING
        ACCESS read-only
        STATUS mandatory
        DESCRIPTION
               "Client identifier of client holding the lease."
        ::= { wfDhcpSvrLeaseEntry 7 }

    wfDhcpSvrLeaseFqdn OBJECT-TYPE
        SYNTAX DisplayString
        ACCESS read-only
        STATUS mandatory
        DESCRIPTION
               "Fully qualified domain name of client holding the
               lease, for DNS update management."
        ::= { wfDhcpSvrLeaseEntry 8 }

-- end of per-lease information.
    END  -- BayNetworks-DHCP-MIB
