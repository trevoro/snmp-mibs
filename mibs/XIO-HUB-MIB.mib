--  ************************************************************************
--
--      XioAgent.mib  -  Xiotech Storage HUB Management Information Base (MIB)
--
--
--              Xiotech Enterprise Number  -  2366
--
--      Dependencies:
--                    o XIOtech Storage HUB.
--                    o Remote Hub Manager.
--
--      Copyright:
--                    (c) Xiotech Systems, Inc.  1997
--                    All rights reserved.
--
--      The information in this document is subject to change without notice.
--
--      XIOTECH CORPORATION SHALL NOT BE LIABLE FOR TECHNICAL OR EDITORIAL
--      ERRORS OR OMISSIONS CONTAINED HEREIN;  NOR FOR INCIDENTAL OR 
--      CONSEQUENTIAL DAMAGES RESULTING FROM THE FURNISHING, PERFORMANCE, OR
--      USE OF THIS MATERIAL.
--
--  ************************************************************************


XIO-HUB-MIB DEFINITIONS  ::= BEGIN

IMPORTS
        enterprises, Counter
                FROM RFC1155-SMI
        OBJECT-TYPE
                FROM RFC-1212
        DisplayString
                FROM RFC1213-MIB
        TRAP-TYPE
                FROM RFC-1215;

            -- textual conventions
            --
            --    DisplayString ::=
            --              OCTET STRING
            -- This data type is used to model textual information taken
            -- from the NVT ASCII character set.  By convention, objects
            -- with this syntax are declared as having
            --
            --              SIZE (0..255)


--  **********************************************************************
--
--  Xiotech MIB Objects
--
--      Xiotech enterprise                   1.3.6.1.4.1.2366
--          xiotech HUB MIB                  1.3.6.1.4.1.2366.1
--              Hub Identification Group     1.3.6.1.4.1.2366.1.1  
--              Environmental Data Group     1.3.6.1.4.1.2366.1.2  
--              Status Data Group            1.3.6.1.4.1.2366.1.3  
--              Physical Devices Group       1.3.6.1.4.1.2366.1.4
--              RAID Devices Group           1.3.6.1.4.1.2366.1.5
--              Virtual Devices Group        1.3.6.1.4.1.2366.1.6
--              Cache Information Group      1.3.6.1.4.1.2366.1.7
--              HAB Information Group        1.3.6.1.4.1.2366.1.8
--              Bus Information Group        1.3.6.1.4.1.2366.1.9
--              Trap Variables Group         1.3.6.1.4.1.2366.1.10
--              Traps Group                  1.3.6.1.4.1.2366.1.20 
--              CPU Loads Information Group  1.3.6.1.4.1.2366.1.30
--              Storage Device List Group    1.3.6.1.4.1.2366.1.40
--              VDisk Perf. Stats Group      1.3.6.1.4.1.2366.1.50 
--              PDisk Perf. Stats Group      1.3.6.1.4.1.2366.1.60 
--              Server Info Group            1.3.6.1.4.1.2366.1.70 
--
--  Object Naming Conventions
--
--      Group Naming Conventions
--
--           cccmmmnnnnnnnnnnnn
--
--          where : ccc      -  3 character company symbol (i.e. 'xio')
--                  mmm      -  3 character MIB identifier ( i.e. 'Hub')
--                  nn...nn  -  1 - 15 character group name
--  
--      Variable Naming Conventions
--
--           cccmmmggg[tt]nnnnnnnnnnnn
--
--          where : ccc      -  3 character company symbol (i.e. 'xio')
--                  mmm      -  3 character MIB identifier ( i.e. 'Hub')
--                  gg       -  2character group designation ( i.e. 'Ev')
--                  nn...nn  -  1 - 13 character variable name
--  
--      Trap Naming Conventions
--
--           cccmmmTRPnnnnnnnnnnnn
--
--          where : ccc      -  3 character company symbol (i.e. 'xio')
--                  mmm      -  3 character MIB identifier ( i.e. 'Hub')
--                  TRP      -  3 characters identifying a TRAP (required)
--                  nn...nn  -  1 - 15 character trap name
--  
--  **********************************************************************

xiotech				OBJECT IDENTIFIER ::= { enterprises 2366 }

--
--      Xiotech HUB  'xioHub' MIB
--
xioHub               OBJECT IDENTIFIER ::= { xiotech 1 }

--
--      HUB MIB Groups        1.3.6.1.4.1.2366.1.x  (x = 1 - 20)
--
xioHubIdentification OBJECT IDENTIFIER ::= { xioHub  1 }
xioHubEnvironment    OBJECT IDENTIFIER ::= { xioHub  2 }
xioHubStatusData     OBJECT IDENTIFIER ::= { xioHub  3 }
xioHubPhysicalDevice OBJECT IDENTIFIER ::= { xioHub  4 }
xioHubRaidDevice     OBJECT IDENTIFIER ::= { xioHub  5 }
xioHubVirtualDevice  OBJECT IDENTIFIER ::= { xioHub  6 }
xioHubCacheInfo      OBJECT IDENTIFIER ::= { xioHub  7 }
xioHubHabInfo        OBJECT IDENTIFIER ::= { xioHub  8 }
xioHubBusInfo        OBJECT IDENTIFIER ::= { xioHub  9 }
xioHubTrapVariables  OBJECT IDENTIFIER ::= { xioHub  10 }
xioHubTraps          OBJECT IDENTIFIER ::= { xioHub  20 }
xioHubLoadInfo       OBJECT IDENTIFIER ::= { xioHub  30 }
xioHubStorageDevList OBJECT IDENTIFIER ::= { xioHub  40 }
xioHubVpInfo         OBJECT IDENTIFIER ::= { xioHub  50 }
xioHubPpInfo         OBJECT IDENTIFIER ::= { xioHub  60 }
xioHubSvInfo         OBJECT IDENTIFIER ::= { xioHub  70 }


--  **********************************************************************
--  **********************************************************************
--
--  Hub Identification Group (1)
--
--      Contains Storage Hub name.
--
--      Object Name  (ID) :  'xioHubIdentification'  (1)
--
--      Group designation : 'Hu'
--
--  **********************************************************************
--  **********************************************************************

    xioHubHuName   OBJECT-TYPE
                   SYNTAX  DisplayString  (SIZE (0..64))
                   ACCESS  read-write
                   STATUS  mandatory
                   DESCRIPTION
                           "Storage Hub Name." 
                   ::= { xioHubIdentification 1 }      

    xioHubHuSerialNum OBJECT-TYPE
                   SYNTAX  INTEGER
                   ACCESS  read-only
                   STATUS  mandatory
                   DESCRIPTION
                           "Storage Hub Serial Number." 
                   ::= { xioHubIdentification 2 }      

    xioHubHuCompat OBJECT-TYPE
                   SYNTAX  INTEGER
                   ACCESS  read-only
                   STATUS  mandatory
                   DESCRIPTION
                           "Compatibility level of Storage Hub." 
                   ::= { xioHubIdentification 3 }      

    xioHubHuTCPIPAddr   OBJECT-TYPE
                   SYNTAX  DisplayString  (SIZE (0..64))
                   ACCESS  read-write
                   STATUS  mandatory
                   DESCRIPTION
                           "Storage Hub TCPIP address." 
                   ::= { xioHubIdentification 4 }      

    xioHubHuHeartbeat  OBJECT-TYPE
                       SYNTAX  INTEGER
                       ACCESS  read-only
                       STATUS  mandatory
                       DESCRIPTION
                           "Storage Hub Heartbeat." 
                      ::= { xioHubIdentification 5 }      

--  **********************************************************************
--  **********************************************************************
--
--  Environmental Data Group (2)
--
--      Contains status and temperature for HUB components.
--
--      Object Name  (ID) :  'xioHubEnvironment'  (2)
--
--      Group designation : 'Ev'
--
--  **********************************************************************
--  **********************************************************************

    xioHubEvUpsAc   OBJECT-TYPE
                   SYNTAX  INTEGER
                   ACCESS  read-only
                   STATUS  mandatory
                   DESCRIPTION
                           "Indicates that the UPS AC input is good." 
                   ::= { xioHubEnvironment 1 }      

    xioHubEvUpsBattLow   OBJECT-TYPE
                   SYNTAX  INTEGER 
                   ACCESS  read-only
                   STATUS  mandatory
                   DESCRIPTION
                           "UPS Battery is good." 
                   ::= { xioHubEnvironment 2 }      

    xioHubEvMainPower   OBJECT-TYPE
                   SYNTAX  INTEGER
                   ACCESS  read-only
                   STATUS  mandatory
                   DESCRIPTION
                           "Main DC Power supply is good." 
                   ::= { xioHubEnvironment 3 }      

    xioHubEvNumSupplies  OBJECT-TYPE
                   SYNTAX  INTEGER
                   ACCESS  read-only
                   STATUS  mandatory
                   DESCRIPTION
                           "Number of DC Power Supplies." 
                   ::= { xioHubEnvironment 4 }      

    xioHubEvNumFrontFans  OBJECT-TYPE
                   SYNTAX  INTEGER
                   ACCESS  read-only
                   STATUS  mandatory
                   DESCRIPTION
                           "Number of Front Fans." 
                   ::= { xioHubEnvironment 5 }      

    xioHubEvNumRearFans  OBJECT-TYPE
                   SYNTAX  INTEGER
                   ACCESS  read-only
                   STATUS  mandatory
                   DESCRIPTION
                           "Number of Rear Fans." 
                   ::= { xioHubEnvironment 6 }      

    xioHubEvMainDcPowerTable OBJECT-TYPE
                   SYNTAX  SEQUENCE OF XioHubEvMainDcPowerEntry
                   ACCESS  not-accessible
                   STATUS  mandatory
                   DESCRIPTION
                              "The status of Main DC Power Supplies."
                   ::= { xioHubEnvironment 7 }

            --  *************************************************************
            --  xioHubEvMainDcPowerTable objects 
            --  *************************************************************

           xioHubEvMainDcPowerEntry OBJECT-TYPE
                           SYNTAX  XioHubEvMainDcPowerEntry
                           ACCESS  not-accessible
                           STATUS  mandatory
                           DESCRIPTION
                                      "Main DC Power Supply status."
                           INDEX   { xioHubEvDcId }
                           ::= { xioHubEvMainDcPowerTable 1 }
        
                           XioHubEvMainDcPowerEntry ::=
                               SEQUENCE {
                                    xioHubEvDcId
                                           INTEGER,
                                    xioHubEvDcExists
                                           INTEGER,
                                    xioHubEvDcGood
                                           INTEGER
                                  }

            xioHubEvDcId   OBJECT-TYPE
                           SYNTAX  INTEGER  (0..12)
                           ACCESS  read-only
                           STATUS  mandatory
                           DESCRIPTION
                                   "Value indicating a specific DC Power Supply."
                           ::= { xioHubEvMainDcPowerEntry 1 }      

            xioHubEvDcExists   OBJECT-TYPE
                           SYNTAX  INTEGER  (0..12)
                           ACCESS  read-only
                           STATUS  mandatory
                           DESCRIPTION
                                   "Flag indicating that DC Power Supply exists."
                           ::= { xioHubEvMainDcPowerEntry 2 }      

            xioHubEvDcGood    OBJECT-TYPE
                           SYNTAX  INTEGER (0..12)
                           ACCESS  read-only
                           STATUS  mandatory
                           DESCRIPTION
                                   "Flag indicating status of DC Power Supply"
                           ::= { xioHubEvMainDcPowerEntry 3 }      


    xioHubEvFrontFansTable OBJECT-TYPE
                   SYNTAX  SEQUENCE OF XioHubEvFrontFansEntry
                   ACCESS  not-accessible
                   STATUS  mandatory
                   DESCRIPTION
                              "The status of Front fans."
                   ::= { xioHubEnvironment 8 }

            --  *************************************************************
            --  xioHubEvFrontFansTable objects 
            --  *************************************************************

           xioHubEvFrontFansEntry OBJECT-TYPE
                           SYNTAX  XioHubEvFrontFansEntry
                           ACCESS  not-accessible
                           STATUS  mandatory
                           DESCRIPTION
                                      "Front Fans status."
                           INDEX   { xioHubEvFrontFansId }
                           ::= { xioHubEvFrontFansTable 1 }
        
                           XioHubEvFrontFansEntry ::=
                               SEQUENCE {
                                    xioHubEvFrontFansId
                                           INTEGER,
                                    xioHubEvFrontFansGood
                                           INTEGER
                                  }

            xioHubEvFrontFansId  OBJECT-TYPE
                           SYNTAX  INTEGER  (0..12)
                           ACCESS  read-only
                           STATUS  mandatory
                           DESCRIPTION
                                   "Value indicating specfic Front Fans."
                           ::= { xioHubEvFrontFansEntry 1 }      

            xioHubEvFrontFansGood  OBJECT-TYPE
                           SYNTAX  INTEGER  (0..12)
                           ACCESS  read-only
                           STATUS  mandatory
                           DESCRIPTION
                                   "Flag indicating that Front Fans are good."
                           ::= { xioHubEvFrontFansEntry 2 }      

    xioHubEvRearFansTable OBJECT-TYPE
                   SYNTAX  SEQUENCE OF XioHubEvRearFansEntry
                   ACCESS  not-accessible
                   STATUS  mandatory
                   DESCRIPTION
                              "The status of Rear fans."
                   ::= { xioHubEnvironment 9 }

            --  *************************************************************
            --  xioHubEvRearFansTable objects 
            --  *************************************************************

           xioHubEvRearFansEntry OBJECT-TYPE
                           SYNTAX  XioHubEvRearFansEntry
                           ACCESS  not-accessible
                           STATUS  mandatory
                           DESCRIPTION
                                      "Rear Fans status."
                           INDEX   { xioHubEvRearFansId }
                           ::= { xioHubEvRearFansTable 1 }
        
                           XioHubEvRearFansEntry ::=
                               SEQUENCE {
                                    xioHubEvRearFansId
                                           INTEGER,
                                    xioHubEvRearFansGood
                                           INTEGER
                                  }

            xioHubEvRearFansId  OBJECT-TYPE
                           SYNTAX  INTEGER  (0..12)
                           ACCESS  read-only
                           STATUS  mandatory
                           DESCRIPTION
                                   "Value indicating specific Rear Fans."
                           ::= { xioHubEvRearFansEntry 1 }      
            
			xioHubEvRearFansGood  OBJECT-TYPE
                           SYNTAX  INTEGER  (0..12)
                           ACCESS  read-only
                           STATUS  mandatory
                           DESCRIPTION
                                   "Flag indicating that Rear Fans are good."
                           ::= { xioHubEvRearFansEntry 2 }     


    xioHubEvExtUpsAc   OBJECT-TYPE
                   SYNTAX  INTEGER
                   ACCESS  read-only
                   STATUS  mandatory
                   DESCRIPTION
                           "Indicates status of external cabinet UPS AC input." 
                   ::= { xioHubEnvironment 10 }      

    xioHubEvExtUpsBatt   OBJECT-TYPE
                   SYNTAX  INTEGER
                   ACCESS  read-only
                   STATUS  mandatory
                   DESCRIPTION
                           "Indicates status of external cabinet UPS battery." 
                   ::= { xioHubEnvironment 11 }      

    xioHubEvExtDcMain   OBJECT-TYPE
                   SYNTAX  INTEGER
                   ACCESS  read-only
                   STATUS  mandatory
                   DESCRIPTION
                           "Indicates status of external cabinet Main DC Power Supply." 
                   ::= { xioHubEnvironment 12 }      

    xioHubEvExtNumSupplies OBJECT-TYPE
                   SYNTAX  INTEGER
                   ACCESS  read-only
                   STATUS  mandatory
                   DESCRIPTION
                           "Number of Power Supplies in external cabinet." 
                   ::= { xioHubEnvironment 13 }      

    xioHubEvExtNumRearFans OBJECT-TYPE
                   SYNTAX  INTEGER
                   ACCESS  read-only
                   STATUS  mandatory
                   DESCRIPTION
                           "Number of rear fans in external cabinet." 
                   ::= { xioHubEnvironment 14 }      

    xioHubEvExtMainDcPowerTable OBJECT-TYPE
                   SYNTAX  SEQUENCE OF XioHubEvExtMainDcPowerEntry
                   ACCESS  not-accessible
                   STATUS  mandatory
                   DESCRIPTION
                              "The status of Main DC Power Supplies."
                   ::= { xioHubEnvironment 15 }

            --  *************************************************************
            --  xioHubEvExtMainDcPowerTable objects 
            --  *************************************************************

           xioHubEvExtMainDcPowerEntry OBJECT-TYPE
                           SYNTAX  XioHubEvExtMainDcPowerEntry
                           ACCESS  not-accessible
                           STATUS  mandatory
                           DESCRIPTION
                                      "Main DC Power Supply status."
                           INDEX   { xioHubEvExtDcId }
                           ::= { xioHubEvExtMainDcPowerTable 1 }
        
                           XioHubEvExtMainDcPowerEntry ::=
                               SEQUENCE {
                                    xioHubEvExtDcId
                                           INTEGER,
                                    xioHubEvExtDcExists
                                           INTEGER,
                                    xioHubEvExtDcGood
                                           INTEGER
                                  }

            xioHubEvExtDcId   OBJECT-TYPE
                           SYNTAX  INTEGER  (0..12)
                           ACCESS  read-only
                           STATUS  mandatory
                           DESCRIPTION
                                   "Value indicating specific external cabinet 
									DC Power Supply."
                           ::= { xioHubEvExtMainDcPowerEntry 1 }      

            xioHubEvExtDcExists   OBJECT-TYPE
                           SYNTAX  INTEGER  (0..12)
                           ACCESS  read-only
                           STATUS  mandatory
                           DESCRIPTION
                                   "Flag indicating that external cabinet 
									DC Power Supply exists."
                           ::= { xioHubEvExtMainDcPowerEntry 2 } 

            xioHubEvExtDcGood    OBJECT-TYPE
                           SYNTAX  INTEGER (0..12)
                           ACCESS  read-only
                           STATUS  mandatory
                           DESCRIPTION
                                   "Flag indicating status of external cabinet 
									DC Power Supply"
                           ::= { xioHubEvExtMainDcPowerEntry 3 }      


    xioHubEvExtRearFansTable OBJECT-TYPE
                   SYNTAX  SEQUENCE OF XioHubEvExtRearFansEntry
                   ACCESS  not-accessible
                   STATUS  mandatory
                   DESCRIPTION
                              "The status of External Cabinet Rear fans."
                   ::= { xioHubEnvironment 16 }

            --  *************************************************************
            --  xioHubEvExtRearFansTable objects 
            --  *************************************************************

           xioHubEvExtRearFansEntry OBJECT-TYPE
                           SYNTAX  XioHubEvExtRearFansEntry
                           ACCESS  not-accessible
                           STATUS  mandatory
                           DESCRIPTION
                                      "External cabinet Rear Fans status."
                           INDEX   { xioHubEvExtRearFansId }
                           ::= { xioHubEvExtRearFansTable 1 }
        
                           XioHubEvExtRearFansEntry ::=
                               SEQUENCE {
                                    xioHubEvExtRearFansId
                                           INTEGER,
                                    xioHubEvExtRearFansGood
                                           INTEGER
                                  }

            xioHubEvExtRearFansId  OBJECT-TYPE
                           SYNTAX  INTEGER  (0..12)
                           ACCESS  read-only
                           STATUS  mandatory
                           DESCRIPTION
                                   "Value indicating spcecific external cabinet 
								    Rear Fan."
                           ::= { xioHubEvExtRearFansEntry 1 }      

            xioHubEvExtRearFansGood  OBJECT-TYPE
                           SYNTAX  INTEGER  (0..12)
                           ACCESS  read-only
                           STATUS  mandatory
                           DESCRIPTION
                                   "Flag indicating that external cabinet 
								    Rear Fans are good."
                           ::= { xioHubEvExtRearFansEntry 2 }  

    xioHubEvHabTempsTable OBJECT-TYPE
                   SYNTAX  SEQUENCE OF XioHubEvHabTempsEntry
                   ACCESS  not-accessible
                   STATUS  mandatory
                   DESCRIPTION
                              "The Hab temperatures."
                   ::= { xioHubEnvironment 17 }

            --  *************************************************************
            --  xioHubEvExtRearFansTable objects 
            --  *************************************************************

           xioHubEvHabTempsEntry OBJECT-TYPE
                           SYNTAX  XioHubEvHabTempsEntry
                           ACCESS  not-accessible
                           STATUS  mandatory
                           DESCRIPTION
                                      "Hab temperatures."
                           INDEX   { xioHubEvHabId }
                           ::= { xioHubEvHabTempsTable 1 }
        
                           XioHubEvHabTempsEntry ::=
                               SEQUENCE {
                                    xioHubEvHabId
                                           INTEGER,
                                    xioHubEvHabInstalled
                                           INTEGER,
                                    xioHubEvHubHabTemp
                                           INTEGER,
                                    xioHubEvServerHabTemp
                                           INTEGER
                                  }

            xioHubEvHabId  OBJECT-TYPE
                           SYNTAX  INTEGER  
                           ACCESS  read-only
                           STATUS  mandatory
                           DESCRIPTION
                                   "Value indicating specific Hab."
                           ::= { xioHubEvHabTempsEntry 1 }      

            xioHubEvHabInstalled  OBJECT-TYPE
                           SYNTAX  INTEGER  
                           ACCESS  read-only
                           STATUS  mandatory
                           DESCRIPTION
                                   "Flag indicating that Hab is installed."
                           ::= { xioHubEvHabTempsEntry 2 } 

            xioHubEvHubHabTemp  OBJECT-TYPE
                           SYNTAX  INTEGER  
                           ACCESS  read-only
                           STATUS  mandatory
                           DESCRIPTION
                                   "Temperature of Hab within the Hub."
                           ::= { xioHubEvHabTempsEntry 3 }      

            xioHubEvServerHabTemp  OBJECT-TYPE
                           SYNTAX  INTEGER  
                           ACCESS  read-only
                           STATUS  mandatory
                           DESCRIPTION
                                   "Temperature of Hab within the Server."
                           ::= { xioHubEvHabTempsEntry 4 }      

    xioHubEvProcessorTemp   OBJECT-TYPE
                   SYNTAX  INTEGER
                   ACCESS  read-only
                   STATUS  mandatory
                   DESCRIPTION
                           "Controller processor temperature." 
                   ::= { xioHubEnvironment 18 }      

    xioHubEvCacheTemp   OBJECT-TYPE
                   SYNTAX  INTEGER
                   ACCESS  read-only
                   STATUS  mandatory
                   DESCRIPTION
                           "Cache temperature." 
                   ::= { xioHubEnvironment 19 }      

    xioHubEvIsaTemp   OBJECT-TYPE
                   SYNTAX  INTEGER
                   ACCESS  read-only
                   STATUS  mandatory
                   DESCRIPTION
                           "ISA board temperature." 
                   ::= { xioHubEnvironment 20 }      

    xioHubEvRearTemp   OBJECT-TYPE
                   SYNTAX  INTEGER
                   ACCESS  read-only
                   STATUS  mandatory
                   DESCRIPTION
                           "Rear temperature." 
                   ::= { xioHubEnvironment 21 }      

    xioHubEvExtCabinetTemp   OBJECT-TYPE
                   SYNTAX  INTEGER
                   ACCESS  read-only
                   STATUS  mandatory
                   DESCRIPTION
                           "External cabinet temperature." 
                   ::= { xioHubEnvironment 22 }      

    xioHubEvKBsPerSec   OBJECT-TYPE
                   SYNTAX  INTEGER
                   ACCESS  read-only
                   STATUS  mandatory
                   DESCRIPTION
                           "Total Magnitude transfer rate, in KB/s." 
                   ::= { xioHubEnvironment 23 }      

    xioHubEvIOsPerSec   OBJECT-TYPE
                   SYNTAX  INTEGER
                   ACCESS  read-only
                   STATUS  mandatory
                   DESCRIPTION
                           "Total Magnitude transfer rate, in IO/s." 
                   ::= { xioHubEnvironment 24 }      


--  **********************************************************************
--  **********************************************************************
--
--  Status Data Group (3)
--
--      Contains Information and Status of HUB components.
--
--      Object Name  (ID) :  'xioHubStatusData'  (3)
--
--      Group designation : 'Sd'
--
--  **********************************************************************
--  **********************************************************************

    xioHubSdEmbedPcState   OBJECT-TYPE
                   SYNTAX  INTEGER {   offline(0),
                                       standby(1),
                                       post0(2),
                                       post1(3),
                                       runningdiagnostics(4),
                                       operational(5),
                                       failed(6),
                                       waitingforfibreconnect(7),
                                       synchronizing(8),
                                       notconnected(9),
                                       unknown(15),
                                       goneoffline(65535)
                                       }
                  ACCESS  read-only
                   STATUS  mandatory
                   DESCRIPTION
                           "Embedded PC State." 
                   ::= { xioHubStatusData 1 }      

    xioHubSdControllerState   OBJECT-TYPE
                   SYNTAX  INTEGER {   offline(0),
                                       standby(1),
                                       post0(2),
                                       post1(3),
                                       runningdiagnostics(4),
                                       operational(5),
                                       failed(6),
                                       waitingforfibreconnect(7),
                                       synchronizing(8),
                                       notconnected(9),
                                       unknown(15),
                                       goneoffline(65535)
                                       }
                   ACCESS  read-only
                   STATUS  mandatory
                   DESCRIPTION
                           "Controller State." 
                   ::= { xioHubStatusData 2 }

    xioHubSdCacheState   OBJECT-TYPE
                   SYNTAX  INTEGER
                   ACCESS  read-only
                   STATUS  mandatory
                   DESCRIPTION
                           "Write Cache State." 
                   ::= { xioHubStatusData 3 }

    xioHubSdHabStatusTable OBJECT-TYPE
                   SYNTAX  SEQUENCE OF XioHubSdHabStatusEntry
                   ACCESS  not-accessible
                   STATUS  mandatory
                   DESCRIPTION
                              "The Hab board status."
                   ::= { xioHubStatusData 4 }

            --  *************************************************************
            --  xioHubSdHabStatusTable objects 
            --  *************************************************************

           xioHubSdHabStatusEntry OBJECT-TYPE
                           SYNTAX  XioHubSdHabStatusEntry
                           ACCESS  not-accessible
                           STATUS  mandatory
                           DESCRIPTION
                                      "Hab status."
                           INDEX   { xioHubSdHabId }
                           ::= { xioHubSdHabStatusTable 1 }
        
                           XioHubSdHabStatusEntry ::=
                               SEQUENCE {
                                    xioHubSdHabId
                                           INTEGER,
                                    xioHubSdHabInstalled
                                           INTEGER,
                                    xioHubSdHubHabState
                                           INTEGER,
                                    xioHubSdServerHabState
                                           INTEGER
                                  }

            xioHubSdHabId  OBJECT-TYPE
                           SYNTAX  INTEGER  
                           ACCESS  read-only
                           STATUS  mandatory
                           DESCRIPTION
                                   "Value indicating specific Hab."
                           ::= { xioHubSdHabStatusEntry 1 } 

            xioHubSdHabInstalled  OBJECT-TYPE
                           SYNTAX  INTEGER  
                           ACCESS  read-only
                           STATUS  mandatory
                           DESCRIPTION
                                   "Flag indicating that Hab is installed."
                           ::= { xioHubSdHabStatusEntry 2 }      

            xioHubSdHubHabState  OBJECT-TYPE
                   SYNTAX  INTEGER {   offline(0),
                                       standby(1),
                                       post0(2),
                                       post1(3),
                                       runningdiagnostics(4),
                                       operational(5),
                                       failed(6),
                                       waitingforfibreconnect(7),
                                       synchronizing(8),
                                       notconnected(9),
                                       unknown(15),
                                       goneoffline(65535)
                                       }
                           ACCESS  read-only
                           STATUS  mandatory
                           DESCRIPTION
                                   "State of Hab within the Hub."
                           ::= { xioHubSdHabStatusEntry 3 }      

            xioHubSdServerHabState  OBJECT-TYPE
                   SYNTAX  INTEGER {   offline(0),
                                       standby(1),
                                       post0(2),
                                       post1(3),
                                       runningdiagnostics(4),
                                       operational(5),
                                       failed(6),
                                       waitingforfibreconnect(7),
                                       synchronizing(8),
                                       notconnected(9),
                                       unknown(15),
                                       goneoffline(65535)
                                       }
                           ACCESS  read-only
                           STATUS  mandatory
                           DESCRIPTION
                                   "State of Hab within the Server."
                           ::= { xioHubSdHabStatusEntry 4 }      

    xioHubSdServerInfoTable OBJECT-TYPE
                   SYNTAX  SEQUENCE OF XioHubSdServerInfoEntry
                   ACCESS  not-accessible
                   STATUS  mandatory
                   DESCRIPTION
                              "The Server status info."
                   ::= { xioHubStatusData 5 }

            --  *************************************************************
            --  xioHubSdServerInfoTable objects 
            --  *************************************************************

           xioHubSdServerInfoEntry OBJECT-TYPE
                           SYNTAX  XioHubSdServerInfoEntry
                           ACCESS  not-accessible
                           STATUS  mandatory
                           DESCRIPTION
                                      "Server status."
                           INDEX   { xioHubSdServerId }
                           ::= { xioHubSdServerInfoTable 1 }
        
                           XioHubSdServerInfoEntry ::=
                               SEQUENCE {
                                    xioHubSdServerId
                                           INTEGER,
                                    xioHubSdServerStates
                                           INTEGER
                                  }

            xioHubSdServerId  OBJECT-TYPE
                           SYNTAX  INTEGER  
                           ACCESS  read-only
                           STATUS  mandatory
                           DESCRIPTION
                                   "Value indicating specific Server."
                           ::= { xioHubSdServerInfoEntry 1 } 

            xioHubSdServerStates  OBJECT-TYPE
                   SYNTAX  INTEGER {   offline(0),
                                       standby(1),
                                       post0(2),
                                       post1(3),
                                       runningdiagnostics(4),
                                       operational(5),
                                       failed(6),
                                       waitingforfibreconnect(7),
                                       synchronizing(8),
                                       notconnected(9),
                                       unknown(15),
                                       goneoffline(65535)
                                       }
                           ACCESS  read-only
                           STATUS  mandatory
                           DESCRIPTION
                                   "State of the Server containing a Hab."
                           ::= { xioHubSdServerInfoEntry 2 }  



--  **********************************************************************
--  **********************************************************************
--
--  Physical Device Group (4)
--
--      Contains information and statisitics for Physical Devices.
--
--      Object Name  (ID) :  'xioHubPhysicalDevice'  (4)
--
--      Group designation : 'Pd'
--
--  **********************************************************************
--  **********************************************************************

    xioHubPdPhysDevTable OBJECT-TYPE
                   SYNTAX  SEQUENCE OF XioHubPdPhysDevEntry
                   ACCESS  not-accessible
                   STATUS  mandatory
                   DESCRIPTION
                              "Physical Devices info and statistics."
                   ::= { xioHubPhysicalDevice 1 }

            --  *************************************************************
            --  xioHubPdPhysDevTable objects 
            --  *************************************************************

           xioHubPdPhysDevEntry OBJECT-TYPE
                           SYNTAX  XioHubPdPhysDevEntry
                           ACCESS  not-accessible
                           STATUS  mandatory
                           DESCRIPTION
                                      "Physical device info and statistics."
                           INDEX   { xioHubPdIndex }
                           ::= { xioHubPdPhysDevTable 1 }
        
                           XioHubPdPhysDevEntry ::=
                               SEQUENCE {
                                    xioHubPdIndex
                                           INTEGER,
                                    xioHubPdChannel
                                           INTEGER,
                                    xioHubPdScsiId
                                           INTEGER,
                                    xioHubPdClass
                                           INTEGER,
                                    xioHubPdDevName
                                           DisplayString,
                                    xioHubPdSerialNum
                                           INTEGER,
                                    xioHubPdPostStatus
                                           INTEGER,
                                    xioHubPdDevStatus
                                           INTEGER,
                                    xioHubPdDevCapacity
                                           INTEGER,
                                    xioHubPdProductId
                                           DisplayString,
                                    xioHubPdVendorId
                                           DisplayString,
                                    xioHubPdProductRev
                                           DisplayString,
                                    xioHubPdSerialNo
                                           DisplayString,
                                    xioHubPdTotAvail
                                           INTEGER,
                                    xioHubPdLargestAvail
                                           INTEGER,
                                    xioHubPdTotRdReq
                                           Counter,
                                    xioHubPdTotWrReq
                                           Counter,
                                    xioHubPdTotCorrectErr
                                           Counter,
                                    xioHubPdAvgSec
                                           INTEGER,
                                    xioHubPdNumReq
                                           INTEGER,
                                    xioHubPdQueDepth
                                           INTEGER,
                                    xioHubPdKBytesPS
                                           INTEGER
                                  }

            xioHubPdIndex  OBJECT-TYPE
                           SYNTAX  INTEGER  
                           ACCESS  read-only
                           STATUS  mandatory
                           DESCRIPTION
                                   "Physical Devices table index."
                           ::= { xioHubPdPhysDevEntry 1 } 

            xioHubPdChannel  OBJECT-TYPE
                           SYNTAX  INTEGER  
                           ACCESS  read-only
                           STATUS  mandatory
                           DESCRIPTION
                                   "SCSI Channel to which the device is attached."
                           ::= { xioHubPdPhysDevEntry 2 } 

            xioHubPdScsiId  OBJECT-TYPE
                           SYNTAX  INTEGER  
                           ACCESS  read-only
                           STATUS  mandatory
                           DESCRIPTION
                                   "SCSI ID for device."
                           ::= { xioHubPdPhysDevEntry 3 } 


            xioHubPdClass  OBJECT-TYPE
                           SYNTAX  INTEGER {
                                       unlabled (1),
                                       data (2),
                                       hotspare (3),
                                       notsafe (4)
                                       } 
                           ACCESS  read-only
                           STATUS  mandatory
                           DESCRIPTION
                                   "Physical device class."
                           ::= { xioHubPdPhysDevEntry 4 } 


            xioHubPdDevName  OBJECT-TYPE
                           SYNTAX  DisplayString  (SIZE (0..5))
                           ACCESS  read-only
                           STATUS  mandatory
                           DESCRIPTION
                                   "Physical device name."
                           ::= { xioHubPdPhysDevEntry 5 } 


            xioHubPdSerialNum  OBJECT-TYPE
                           SYNTAX  INTEGER
                           ACCESS  read-only
                           STATUS  mandatory
                           DESCRIPTION
                                   "System serial number."
                           ::= { xioHubPdPhysDevEntry 6 }


            xioHubPdPostStatus  OBJECT-TYPE
                           SYNTAX  INTEGER {
                                       nonexistent (1),
                                       deviceok (2),
                                       failinquirecmd (3),
                                       failtestunitready (4),
                                       failstartunit (5),
                                       failinquireserialno (6),
                                       failsenddiag (7),
                                       failwritebuf (8),
                                       failreadbuf (9),
                                       failwrrdbufpat (10),
                                       failverify (11),
                                       failrdcapacity (12)
                                       } 
                           ACCESS  read-only
                           STATUS  mandatory
                           DESCRIPTION
                                   "Results from the Power On Self Test."
                           ::= { xioHubPdPhysDevEntry 7 } 


            xioHubPdDevStatus  OBJECT-TYPE
                           SYNTAX  INTEGER  {
                                       nonExistent (1),
                                       deviceOK (2),
                                       inoperable (3)
                                       }
                           ACCESS  read-only
                           STATUS  mandatory
                           DESCRIPTION
                                   "Physical device status."
                           ::= { xioHubPdPhysDevEntry 8 } 


            xioHubPdDevCapacity  OBJECT-TYPE
                           SYNTAX  INTEGER
                           ACCESS  read-only
                           STATUS  mandatory
                           DESCRIPTION
                                   "Physical device storage capacity, in MB."
                           ::= { xioHubPdPhysDevEntry 9 } 


            xioHubPdProductId  OBJECT-TYPE
                           SYNTAX  DisplayString  (SIZE (0..17))
                           ACCESS  read-only
                           STATUS  mandatory
                           DESCRIPTION
                                   "Physical device product ID."
                           ::= { xioHubPdPhysDevEntry 10 } 


            xioHubPdVendorId  OBJECT-TYPE
                           SYNTAX  DisplayString  (SIZE (0..9))
                           ACCESS  read-only
                           STATUS  mandatory
                           DESCRIPTION
                                   "Physical device vendor ID."
                           ::= { xioHubPdPhysDevEntry 11 } 


            xioHubPdProductRev  OBJECT-TYPE
                           SYNTAX  DisplayString  (SIZE (0..5))
                           ACCESS  read-only
                           STATUS  mandatory
                           DESCRIPTION
                                   "Physical device revision."
                           ::= { xioHubPdPhysDevEntry 12 } 


            xioHubPdSerialNo  OBJECT-TYPE
                           SYNTAX  DisplayString  (SIZE (0..13))
                           ACCESS  read-only
                           STATUS  mandatory
                           DESCRIPTION
                                   "Physical device serial number."
                           ::= { xioHubPdPhysDevEntry 13 } 


            xioHubPdTotAvail  OBJECT-TYPE
                           SYNTAX  INTEGER
                           ACCESS  read-only
                           STATUS  mandatory
                           DESCRIPTION
                                   "Physical device storage available, in MB."
                           ::= { xioHubPdPhysDevEntry 14 } 


            xioHubPdLargestAvail  OBJECT-TYPE
                           SYNTAX  INTEGER
                           ACCESS  read-only
                           STATUS  mandatory
                           DESCRIPTION
                                   "Largest block available on the physical device, in MB."
                           ::= { xioHubPdPhysDevEntry 15 } 


            xioHubPdTotRdReq  OBJECT-TYPE
                           SYNTAX  Counter  
                           ACCESS  read-only
                           STATUS  mandatory
                           DESCRIPTION
                                   "Total read requests made on the physical device."
                           ::= { xioHubPdPhysDevEntry 16 } 


            xioHubPdTotWrReq  OBJECT-TYPE
                           SYNTAX  Counter  
                           ACCESS  read-only
                           STATUS  mandatory
                           DESCRIPTION
                                   "Total write requests made on the physical device."
                           ::= { xioHubPdPhysDevEntry 17 } 


            xioHubPdTotCorrectErr  OBJECT-TYPE
                           SYNTAX  Counter  
                           ACCESS  read-only
                           STATUS  mandatory
                           DESCRIPTION
                                   "Total error corrections made on the physical device."
                           ::= { xioHubPdPhysDevEntry 18 } 


            xioHubPdAvgSec  OBJECT-TYPE
                           SYNTAX  INTEGER  
                           ACCESS  read-only
                           STATUS  mandatory
                           DESCRIPTION
                                   "Avg number of sectors per data transfer
                                    occurring over the last second."
                           ::= { xioHubPdPhysDevEntry 19 } 


            xioHubPdNumReq  OBJECT-TYPE
                           SYNTAX  INTEGER  
                           ACCESS  read-only
                           STATUS  mandatory
                           DESCRIPTION
                                   "Number of requests occuring over last second."
                           ::= { xioHubPdPhysDevEntry 20 } 

            xioHubPdQueDepth  OBJECT-TYPE
                           SYNTAX  INTEGER  
                           ACCESS  read-only
                           STATUS  mandatory
                           DESCRIPTION
                                   "I/O request queue depth."
                           ::= { xioHubPdPhysDevEntry 21 } 

            xioHubPdKBytesPS OBJECT-TYPE
                           SYNTAX  INTEGER
                           ACCESS  read-only
                           STATUS  mandatory
                           DESCRIPTION
                                   "Physical device transfer rate, in KB/s."
                           ::= { xioHubPdPhysDevEntry 22 } 



--  **********************************************************************
--  **********************************************************************
--
--  RAID Device Group (5)
--
--      Contains information and statisitics for RAID Devices.
--
--      Object Name  (ID) :  'xioHubRaidDevice'  (5)
--
--      Group designation : 'Rd'
--
--  **********************************************************************
--  **********************************************************************

    xioHubRdRaidDevTable OBJECT-TYPE
                   SYNTAX  SEQUENCE OF XioHubRdRaidDevEntry
                   ACCESS  not-accessible
                   STATUS  mandatory
                   DESCRIPTION
                              "RAID Devices info and statistics."
                   ::= { xioHubRaidDevice 1 }

            --  *************************************************************
            --  xioHubRdRaidDevTable objects 
            --  *************************************************************

           xioHubRdRaidDevEntry OBJECT-TYPE
                           SYNTAX  XioHubRdRaidDevEntry
                           ACCESS  not-accessible
                           STATUS  mandatory
                           DESCRIPTION
                                      "RAID device info and statistics."
                           INDEX   { xioHubRdRaidId }
                           ::= { xioHubRdRaidDevTable 1 }
        
                           XioHubRdRaidDevEntry ::=
                               SEQUENCE {
                                    xioHubRdRaidId
                                           INTEGER,
                                    xioHubRdClass
                                           INTEGER,
                                    xioHubRdDevStatus
                                           INTEGER,
                                    xioHubRdDepthMirror
                                           INTEGER,
                                    xioHubRdDevStripe
                                           INTEGER,
                                    xioHubRdDevCapacity
                                           INTEGER,
                                    xioHubRdNumSectors
                                           INTEGER,
                                    xioHubRdTotRdReq
                                           Counter,
                                    xioHubRdTotWrReq
                                           Counter,
                                    xioHubRdTotCorrectErr
                                           Counter,
                                    xioHubRdAvgSec
                                           INTEGER,
                                    xioHubRdNumReq
                                           INTEGER,
                                    xioHubRdQueDepth
                                           INTEGER,
                                    xioHubRdKBytesPS
                                           INTEGER
                                  }

            xioHubRdRaidId  OBJECT-TYPE
                           SYNTAX  INTEGER  
                           ACCESS  read-only
                           STATUS  mandatory
                           DESCRIPTION
                                   "RAID device identifier."
                           ::= { xioHubRdRaidDevEntry 1 } 

            xioHubRdClass  OBJECT-TYPE
                           SYNTAX  INTEGER {
                                       classNonRaid (1),
                                       classRaid0 (2),
                                       classRaid1 (3),
                                       classRaid5 (4),
                                       classRaid10 (5)
                                       }
                           ACCESS  read-only
                           STATUS  mandatory
                           DESCRIPTION
                                   "RAID device class."
                           ::= { xioHubRdRaidDevEntry 2 } 


            xioHubRdDevStatus  OBJECT-TYPE
                           SYNTAX  INTEGER {
                                       nonExistent (1),
                                       deviceOK (2),
                                       uninitialized (3),
                                       inoperable (4)
                                       }  
                           ACCESS  read-only
                           STATUS  mandatory
                           DESCRIPTION
                                   "RAID device status."
                           ::= { xioHubRdRaidDevEntry 3 } 


            xioHubRdDepthMirror  OBJECT-TYPE
                           SYNTAX  INTEGER  
                           ACCESS  read-only
                           STATUS  mandatory
                           DESCRIPTION
                                   "Number of drives data is mirrored on."
                           ::= { xioHubRdRaidDevEntry 4 } 


            xioHubRdDevStripe  OBJECT-TYPE
                           SYNTAX  INTEGER  
                           ACCESS  read-only
                           STATUS  mandatory
                           DESCRIPTION
                                   "Number of drives in a stripe."
                           ::= { xioHubRdRaidDevEntry 5 } 


            xioHubRdDevCapacity  OBJECT-TYPE
                           SYNTAX  INTEGER
                           ACCESS  read-only
                           STATUS  mandatory
                           DESCRIPTION
                                   "RAID device capacity, in MB."
                           ::= { xioHubRdRaidDevEntry 6 } 


            xioHubRdNumSectors  OBJECT-TYPE
                           SYNTAX  INTEGER  
                           ACCESS  read-only
                           STATUS  mandatory
                           DESCRIPTION
                                   "Stripe size, in sectors."
                           ::= { xioHubRdRaidDevEntry 7 } 


            xioHubRdTotRdReq  OBJECT-TYPE
                           SYNTAX  Counter  
                           ACCESS  read-only
                           STATUS  mandatory
                           DESCRIPTION
                                   "Total read requests made on the RAID device."
                           ::= { xioHubRdRaidDevEntry 8 } 


            xioHubRdTotWrReq  OBJECT-TYPE
                           SYNTAX  Counter  
                           ACCESS  read-only
                           STATUS  mandatory
                           DESCRIPTION
                                   "Total write requests made on the RAID device."
                           ::= { xioHubRdRaidDevEntry 9 } 


            xioHubRdTotCorrectErr  OBJECT-TYPE
                           SYNTAX  Counter  
                           ACCESS  read-only
                           STATUS  mandatory
                           DESCRIPTION
                                   "Total error corrections made on the RAID device."
                           ::= { xioHubRdRaidDevEntry 10 } 


            xioHubRdAvgSec  OBJECT-TYPE
                           SYNTAX  INTEGER  
                           ACCESS  read-only
                           STATUS  mandatory
                           DESCRIPTION
                                   "Avg number of sectors per data transfer
                                    occurring over the last second."
                           ::= { xioHubRdRaidDevEntry 11 } 


            xioHubRdNumReq  OBJECT-TYPE
                           SYNTAX  INTEGER  
                           ACCESS  read-only
                           STATUS  mandatory
                           DESCRIPTION
                                   "Number of requests occuring over last second."
                           ::= { xioHubRdRaidDevEntry 12 } 

            xioHubRdQueDepth  OBJECT-TYPE
                           SYNTAX  INTEGER  
                           ACCESS  read-only
                           STATUS  mandatory
                           DESCRIPTION
                                   "I/O request queue depth."
                           ::= { xioHubRdRaidDevEntry 13 } 

            xioHubRdKBytesPS OBJECT-TYPE
                           SYNTAX  INTEGER
                           ACCESS  read-only
                           STATUS  mandatory
                           DESCRIPTION
                                   "RAID device transfer rate, in KB/s."
                           ::= { xioHubRdRaidDevEntry 14 } 


    xioHubRdPhysDevTable OBJECT-TYPE
                   SYNTAX  SEQUENCE OF XioHubRdPhysDevEntry
                   ACCESS  not-accessible
                   STATUS  mandatory
                   DESCRIPTION
                              "Physical devices within a RAID Device."
                   ::= { xioHubRaidDevice 2 }

            --  *************************************************************
            --  xioHubRdPhysDevTable objects 
            --  *************************************************************

           xioHubRdPhysDevEntry OBJECT-TYPE
                           SYNTAX  XioHubRdPhysDevEntry
                           ACCESS  not-accessible
                           STATUS  mandatory
                           DESCRIPTION
                                      "Physical devices within a RAID device."
                           INDEX   { xioHubRdRaidDevId }
                           ::= { xioHubRdPhysDevTable 1 }
        
                           XioHubRdPhysDevEntry ::=
                               SEQUENCE {
                                    xioHubRdRaidDevId
                                           INTEGER,
                                    xioHubRdChannel
                                           INTEGER,
                                    xioHubRdScsiId
                                           INTEGER,
                                    xioHubRdDevInRaid
                                           INTEGER,
                                    xioHubRdDevRebuild
                                           INTEGER,
                                    xioHubRdDevFailed
                                           INTEGER
                                  }

            xioHubRdRaidDevId  OBJECT-TYPE
                           SYNTAX  INTEGER  
                           ACCESS  read-only
                           STATUS  mandatory
                           DESCRIPTION
                                   "RAID device identifier for physical 
                                    devices in RAID."
                           ::= { xioHubRdPhysDevEntry 1 } 

            xioHubRdChannel  OBJECT-TYPE
                           SYNTAX  INTEGER  
                           ACCESS  read-only
                           STATUS  mandatory
                           DESCRIPTION
                                   "Scsi Channel for physical devices in RAID."
                           ::= { xioHubRdPhysDevEntry 2 } 

            xioHubRdScsiId  OBJECT-TYPE
                           SYNTAX  INTEGER  
                           ACCESS  read-only
                           STATUS  mandatory
                           DESCRIPTION
                                   "SCSI ID for physical devices in RAID."
                           ::= { xioHubRdPhysDevEntry 3 } 

            xioHubRdDevInRaid  OBJECT-TYPE
                           SYNTAX  INTEGER  
                           ACCESS  read-only
                           STATUS  mandatory
                           DESCRIPTION
                                   "Flag indicating physical devices in RAID."
                           ::= { xioHubRdPhysDevEntry 4 } 

            xioHubRdDevRebuild  OBJECT-TYPE
                           SYNTAX  INTEGER  
                           ACCESS  read-only
                           STATUS  mandatory
                           DESCRIPTION
                                   "physical devices in RAID being rebuilt."
                           ::= { xioHubRdPhysDevEntry 5 } 

            xioHubRdDevFailed  OBJECT-TYPE
                           SYNTAX  INTEGER  
                           ACCESS  read-only
                           STATUS  mandatory
                           DESCRIPTION
                                   "physical devices in RAID which have failed."
                           ::= { xioHubRdPhysDevEntry 6 } 



--  **********************************************************************
--  **********************************************************************
--
--  Virtual Device Group (6)
--
--      Contains information and statisitics for Virtual Devices.
--
--      Object Name  (ID) :  'xioHubVirtualDevice'  (6)
--
--      Group designation : 'Vd'
--
--  **********************************************************************
--  **********************************************************************

    xioHubVdVirtualDevTable OBJECT-TYPE
                   SYNTAX  SEQUENCE OF XioHubVdVirtualDevEntry
                   ACCESS  not-accessible
                   STATUS  mandatory
                   DESCRIPTION
                              "Virtual Devices info and statistics."
                   ::= { xioHubVirtualDevice 1 }

            --  *************************************************************
            --  xioHubVdVirtualDevTable objects 
            --  *************************************************************

           xioHubVdVirtualDevEntry OBJECT-TYPE
                           SYNTAX  XioHubVdVirtualDevEntry
                           ACCESS  not-accessible
                           STATUS  mandatory
                           DESCRIPTION
                                      "Virtual device info and statistics."
                           INDEX   { xioHubVdVirtualId }
                           ::= { xioHubVdVirtualDevTable 1 }
        
                           XioHubVdVirtualDevEntry ::=
                               SEQUENCE {
                                    xioHubVdVirtualId
                                           INTEGER,
                                    xioHubVdHabGroup
                                           INTEGER,
                                    xioHubVdDevStatus
                                           INTEGER,
                                    xioHubVdDevCapacity
                                           INTEGER,
                                    xioHubVdTotRdReq
                                           Counter,
                                    xioHubVdTotWrReq
                                           Counter,
                                    xioHubVdAvgSec
                                           INTEGER,
                                    xioHubVdNumReq
                                           INTEGER,
                                    xioHubVdQueDepth
                                           INTEGER,
                                    xioHubVdKBytesPS
                                           INTEGER,
                                    xioHubVdAttribute
                                           INTEGER
                                  }

            xioHubVdVirtualId  OBJECT-TYPE
                           SYNTAX  INTEGER  
                           ACCESS  read-only
                           STATUS  mandatory
                           DESCRIPTION
                                   "Virtual device identifier."
                           ::= { xioHubVdVirtualDevEntry 1 } 

            xioHubVdHabGroup  OBJECT-TYPE
                           SYNTAX  INTEGER
                           ACCESS  read-only
                           STATUS  mandatory
                           DESCRIPTION
                                   "Cluster to which this Virtual Device belongs."
                           ::= { xioHubVdVirtualDevEntry 2 }

            xioHubVdDevStatus  OBJECT-TYPE
                           SYNTAX  INTEGER {
                                       nonExistent (1),
                                       deviceOK (2),
                                       uninitialized (3),
                                       inoperable (4),
                                       copyingTo (5),
                                       mirroring (6),
                                       pausedInCopy (7)
                                       } 
                           ACCESS  read-only
                           STATUS  mandatory
                           DESCRIPTION
                                   "Virtual device status."
                           ::= { xioHubVdVirtualDevEntry 3 } 

            xioHubVdDevCapacity  OBJECT-TYPE
                           SYNTAX  INTEGER
                           ACCESS  read-only
                           STATUS  mandatory
                           DESCRIPTION
                                   "Virtual device storage capacity, in MB."
                           ::= { xioHubVdVirtualDevEntry 4 } 

            xioHubVdTotRdReq  OBJECT-TYPE
                           SYNTAX  Counter  
                           ACCESS  read-only
                           STATUS  mandatory
                           DESCRIPTION
                                   "Total read requests made on the virtual device."
                           ::= { xioHubVdVirtualDevEntry 5 } 

            xioHubVdTotWrReq  OBJECT-TYPE
                           SYNTAX  Counter  
                           ACCESS  read-only
                           STATUS  mandatory
                           DESCRIPTION
                                   "Total write requests made on the virtual device."
                           ::= { xioHubVdVirtualDevEntry 6 } 


            xioHubVdAvgSec  OBJECT-TYPE
                           SYNTAX  INTEGER
                           ACCESS  read-only
                           STATUS  mandatory
                           DESCRIPTION
                                   "Avg number of sectors per data transfer
                                    occurring over the last second."
                           ::= { xioHubVdVirtualDevEntry 7 } 

            xioHubVdNumReq  OBJECT-TYPE
                           SYNTAX  INTEGER
                           ACCESS  read-only
                           STATUS  mandatory
                           DESCRIPTION
                                   "Number of requests occuring over last second."
                           ::= { xioHubVdVirtualDevEntry 8 } 

            xioHubVdQueDepth  OBJECT-TYPE
                           SYNTAX  INTEGER
                           ACCESS  read-only
                           STATUS  mandatory
                           DESCRIPTION
                                   "I/O request queue depth."
                           ::= { xioHubVdVirtualDevEntry 9 } 

            xioHubVdKBytesPS OBJECT-TYPE
                           SYNTAX  INTEGER
                           ACCESS  read-only
                           STATUS  mandatory
                           DESCRIPTION
                                   "Virtual device transfer rate, in KB/s."
                           ::= { xioHubVdVirtualDevEntry 10 } 

            xioHubVdAttribute OBJECT-TYPE
                           SYNTAX  INTEGER
                           ACCESS  read-only
                           STATUS  mandatory
                           DESCRIPTION
                                   "Virtual device attributes."
                           ::= { xioHubVdVirtualDevEntry 11 } 

    xioHubVdRaidDevTable OBJECT-TYPE
                   SYNTAX  SEQUENCE OF XioHubVdRaidDevEntry
                   ACCESS  not-accessible
                   STATUS  mandatory
                   DESCRIPTION
                              "Raid devices within a Virtual Device."
                   ::= { xioHubVirtualDevice 2 }

            --  *************************************************************
            --  xioHubVdRaidDevTable objects 
            --  *************************************************************

           xioHubVdRaidDevEntry OBJECT-TYPE
                           SYNTAX  XioHubVdRaidDevEntry
                           ACCESS  not-accessible
                           STATUS  mandatory
                           DESCRIPTION
                                      "Raid devices within a Virtual device."
                           INDEX   { xioHubVdRaidVirtId }
                           ::= { xioHubVdRaidDevTable 1 }
        
                           XioHubVdRaidDevEntry ::=
                               SEQUENCE {
                                    xioHubVdRaidVirtId
                                           INTEGER,
                                    xioHubVdRaidId
                                           INTEGER,
                                    xioHubVdRaidExists
                                           INTEGER
                                  }

            xioHubVdRaidVirtId  OBJECT-TYPE
                           SYNTAX  INTEGER  
                           ACCESS  read-only
                           STATUS  mandatory
                           DESCRIPTION
                                   "Virtual device identifier for Raid dev list."
                           ::= { xioHubVdRaidDevEntry 1 } 

            xioHubVdRaidId  OBJECT-TYPE
                           SYNTAX  INTEGER  
                           ACCESS  read-only
                           STATUS  mandatory
                           DESCRIPTION
                                   "RAID device identifier for Raid dev list."
                           ::= { xioHubVdRaidDevEntry 2 } 

            xioHubVdRaidExists  OBJECT-TYPE
                           SYNTAX  INTEGER  
                           ACCESS  read-only
                           STATUS  mandatory
                           DESCRIPTION
                                   "Flag indicating that RAID device is 
                                    part of virtual device."
                           ::= { xioHubVdRaidDevEntry 3 } 

    xioHubVdCacheInfoTable OBJECT-TYPE
                   SYNTAX  SEQUENCE OF XioHubVdCacheInfoEntry
                   ACCESS  not-accessible
                   STATUS  mandatory
                   DESCRIPTION
                              "Cache Infor for a Virtual Device."
                   ::= { xioHubVirtualDevice 3 }
  

            --  *************************************************************
            --  xioHubVdCacheInfoTable objects 
            --  *************************************************************

           xioHubVdCacheInfoEntry OBJECT-TYPE
                           SYNTAX  XioHubVdCacheInfoEntry
                           ACCESS  not-accessible
                           STATUS  mandatory
                           DESCRIPTION
                                      "Virtual device info and statistics."
                           INDEX   { xioHubVdCacheVirtId }
                           ::= { xioHubVdCacheInfoTable 1 }
        
                           XioHubVdCacheInfoEntry ::=
                               SEQUENCE {
                                    xioHubVdCacheVirtId
                                           INTEGER,
                                    xioHubVdCacheEnabled
                                           INTEGER,
                                    xioHubVdReadHits
                                           Counter,
                                    xioHubVdReadMiss
                                           Counter,
                                    xioHubVdWriteHits
                                           Counter,
                                    xioHubVdWriteMiss
                                           Counter
                                  }

            xioHubVdCacheVirtId  OBJECT-TYPE
                           SYNTAX  INTEGER  
                           ACCESS  read-only
                           STATUS  mandatory
                           DESCRIPTION
                                   "Virtual device identifier for cache info."
                           ::= { xioHubVdCacheInfoEntry 1 }

            xioHubVdCacheEnabled  OBJECT-TYPE
                           SYNTAX  INTEGER  
                           ACCESS  read-only
                           STATUS  mandatory
                           DESCRIPTION
                                   "Flag indicating that cache is enabled for 
                                    Virtual device."
                           ::= { xioHubVdCacheInfoEntry 2 } 

            xioHubVdReadHits  OBJECT-TYPE
                           SYNTAX  Counter  
                           ACCESS  read-only
                           STATUS  mandatory
                           DESCRIPTION
                                   "Number of read hits in cache."
                           ::= { xioHubVdCacheInfoEntry 3 } 

            xioHubVdReadMiss  OBJECT-TYPE
                           SYNTAX  Counter  
                           ACCESS  read-only
                           STATUS  mandatory
                           DESCRIPTION
                                   "Number of read misses."
                           ::= { xioHubVdCacheInfoEntry 4 } 

            xioHubVdWriteHits  OBJECT-TYPE
                           SYNTAX  Counter  
                           ACCESS  read-only
                           STATUS  mandatory
                           DESCRIPTION
                                   "Number of write hits."
                           ::= { xioHubVdCacheInfoEntry 5 } 

            xioHubVdWriteMiss  OBJECT-TYPE
                           SYNTAX  Counter  
                           ACCESS  read-only
                           STATUS  mandatory
                           DESCRIPTION
                                   "Number of write misses."
                           ::= { xioHubVdCacheInfoEntry 6 } 


--  **********************************************************************
--  **********************************************************************
--
--  Cache Info Group (7)
--
--      Contains Write Cache Information.
--
--      Object Name  (ID) :  'xioHubCacheInfo'  (7)
--
--      Group designation : 'Ci'
--
--  **********************************************************************
--  **********************************************************************


    xioHubCiStatus OBJECT-TYPE
                   SYNTAX  INTEGER {
                                       notInstalled(1),
                                       deviceOK (2),
                                       noPower (3),
                                       hwFailure (4)
                                       }
                   ACCESS  read-only
                   STATUS  mandatory
                   DESCRIPTION
                           "Write Cache status." 
                   ::= { xioHubCacheInfo 1 }      

    xioHubCiCacheSize OBJECT-TYPE
                   SYNTAX  INTEGER
                   ACCESS  read-only
                   STATUS  mandatory
                   DESCRIPTION
                           "Total size of cache memory in bytes." 
                   ::= { xioHubCacheInfo 2 }      

    xioHubCiMaxCacheable OBJECT-TYPE
                   SYNTAX  INTEGER
                   ACCESS  read-only
                   STATUS  mandatory
                   DESCRIPTION
                           "Max # of sectors cacehable for any write operation." 
                   ::= { xioHubCacheInfo 3 }  

    xioHubCiNumWrBacks OBJECT-TYPE
                   SYNTAX  INTEGER
                   ACCESS  read-only
                   STATUS  mandatory
                   DESCRIPTION
                           "Current # of writebacks that are in process." 
                   ::= { xioHubCacheInfo 4 }      

    xioHubCiFreeBuffers OBJECT-TYPE
                   SYNTAX  INTEGER
                   ACCESS  read-only
                   STATUS  mandatory
                   DESCRIPTION
                           "Total # of free (unassigned) cache buffers." 
                   ::= { xioHubCacheInfo 5 }      

    xioHubCiCleanBuffers OBJECT-TYPE
                   SYNTAX  INTEGER
                   ACCESS  read-only
                   STATUS  mandatory
                   DESCRIPTION
                           "Total # of clean (assigned) chace buffers." 
                   ::= { xioHubCacheInfo 6 }      

    xioHubCiDirtyBuffers OBJECT-TYPE
                   SYNTAX  INTEGER
                   ACCESS  read-only
                   STATUS  mandatory
                   DESCRIPTION
                           "Total # of dirty (assigned) cache buffers." 
                   ::= { xioHubCacheInfo 7 }      


--  **********************************************************************
--  **********************************************************************
--
--  Hab Information Group (8)
--
--      Contains HAB information.
--
--      Object Name  (ID) :  'xioHubHabInfo'  (8)
--
--      Group designation : 'Hi'
--
--  **********************************************************************
--  **********************************************************************

    xioHubHiHabInfoTable OBJECT-TYPE
                   SYNTAX  SEQUENCE OF XioHubHiHabInfoEntry
                   ACCESS  not-accessible
                   STATUS  mandatory
                   DESCRIPTION
                              "Hab info."
                   ::= { xioHubHabInfo 1 }

            --  *************************************************************
            --  xioHubHiHabInfoTable objects 
            --  *************************************************************

           xioHubHiHabInfoEntry OBJECT-TYPE
                           SYNTAX  XioHubHiHabInfoEntry
                           ACCESS  not-accessible
                           STATUS  mandatory
                           DESCRIPTION
                                      "Hab info."
                           INDEX   { xioHubHiHabId }
                           ::= { xioHubHiHabInfoTable 1 }
        
                           XioHubHiHabInfoEntry ::=
                               SEQUENCE {
                                    xioHubHiStatus
                                           INTEGER,
                                    xioHubHiHabId
                                           INTEGER,
                                    xioHubHiHabGroup
                                           INTEGER,
                                    xioHubHiServerName
                                           DisplayString
                                  }

            xioHubHiStatus  OBJECT-TYPE
                           SYNTAX  INTEGER {
                                       deviceNotInstalled (1),
                                       deviceOK (2),
                                       failed (3)
                                       } 
                           ACCESS  read-only
                           STATUS  mandatory
                           DESCRIPTION
                                   "HAB Status."
                           ::= { xioHubHiHabInfoEntry 1 } 

            xioHubHiHabId  OBJECT-TYPE
                           SYNTAX  INTEGER  
                           ACCESS  read-only
                           STATUS  mandatory
                           DESCRIPTION
                                   "Physical HAB id."
                           ::= { xioHubHiHabInfoEntry 2 } 

            xioHubHiHabGroup  OBJECT-TYPE
                           SYNTAX  INTEGER {
                                             unassigned (255)
                                           } 
                           ACCESS  read-only
                           STATUS  mandatory
                           DESCRIPTION
                                   "HAB Group associated with physical HAB."
                           ::= { xioHubHiHabInfoEntry 3 } 

            xioHubHiServerName  OBJECT-TYPE
                           SYNTAX  DisplayString (SIZE (0..17))  
                           ACCESS  read-only
                           STATUS  mandatory
                           DESCRIPTION
                                   "Name of server associated with physical HAB."
                           ::= { xioHubHiHabInfoEntry 4 } 



--  **********************************************************************
--  **********************************************************************
--
--  Bus Info Group (9)
--
--      Contains information and statisitics for SCSI Buses.
--
--      Object Name  (ID) :  'xioHubBusInfo'  (9)
--
--      Group designation : 'Bi'
--
--  **********************************************************************
--  **********************************************************************

    xioHubBiBusInfoTable OBJECT-TYPE
                   SYNTAX  SEQUENCE OF XioHubBiBusInfoEntry
                   ACCESS  not-accessible
                   STATUS  mandatory
                   DESCRIPTION
                              "SCSI Bus info and statistics."
                   ::= { xioHubBusInfo 1 }

            --  *************************************************************
            --  xioHubBiBusInfoTable objects 
            --  *************************************************************

           xioHubBiBusInfoEntry OBJECT-TYPE
                           SYNTAX  XioHubBiBusInfoEntry
                           ACCESS  not-accessible
                           STATUS  mandatory
                           DESCRIPTION
                                      "Physical device info and statistics."
                           INDEX   { xioHubBiChannel }
                           ::= { xioHubBiBusInfoTable 1 }
        
                           XioHubBiBusInfoEntry ::=
                               SEQUENCE {
                                    xioHubBiChannel
                                           INTEGER,
                                    xioHubBiTotRdReq
                                           Counter,
                                    xioHubBiTotWrReq
                                           Counter,
                                    xioHubBiTotCorrectErr
                                           Counter,
                                    xioHubBiAvgSec
                                           INTEGER,
                                    xioHubBiNumReq
                                           INTEGER,
                                    xioHubBiQueDepth
                                           INTEGER,
                                    xioHubBiKBytesPS
                                           INTEGER
                                  }

            xioHubBiChannel  OBJECT-TYPE
                           SYNTAX  INTEGER  
                           ACCESS  read-only
                           STATUS  mandatory
                           DESCRIPTION
                                   "SCSI Channel device is attached to."
                           ::= { xioHubBiBusInfoEntry 1 } 

            xioHubBiTotRdReq  OBJECT-TYPE
                           SYNTAX  Counter  
                           ACCESS  read-only
                           STATUS  mandatory
                           DESCRIPTION
                                   "Total read requests made on the bus."
                           ::= { xioHubBiBusInfoEntry 2 } 


            xioHubBiTotWrReq  OBJECT-TYPE
                           SYNTAX  Counter  
                           ACCESS  read-only
                           STATUS  mandatory
                           DESCRIPTION
                                   "Total write requests made on the bus."
                           ::= { xioHubBiBusInfoEntry 3 } 


            xioHubBiTotCorrectErr  OBJECT-TYPE
                           SYNTAX  Counter  
                           ACCESS  read-only
                           STATUS  mandatory
                           DESCRIPTION
                                   "Total error corrections made on the bus."
                           ::= { xioHubBiBusInfoEntry 4 } 


            xioHubBiAvgSec  OBJECT-TYPE
                           SYNTAX  INTEGER  
                           ACCESS  read-only
                           STATUS  mandatory
                           DESCRIPTION
                                   "Avg number of sectors per data transfer
                                    occurring over the last second."
                           ::= { xioHubBiBusInfoEntry 5 } 


            xioHubBiNumReq  OBJECT-TYPE
                           SYNTAX  INTEGER  
                           ACCESS  read-only
                           STATUS  mandatory
                           DESCRIPTION
                                   "Number of requests occuring over last second."
                           ::= { xioHubBiBusInfoEntry 6 } 

            xioHubBiQueDepth  OBJECT-TYPE
                           SYNTAX  INTEGER  
                           ACCESS  read-only
                           STATUS  mandatory
                           DESCRIPTION
                                   "I/O request queue depth."
                           ::= { xioHubBiBusInfoEntry 7 } 

            xioHubBiKBytesPS OBJECT-TYPE
                           SYNTAX  INTEGER
                           ACCESS  read-only
                           STATUS  mandatory
                           DESCRIPTION
                                   "Bus transfer rate, in KB/s."
                           ::= { xioHubBiBusInfoEntry 8 } 



--  **********************************************************************
--  **********************************************************************
--
--  Trap Variables Group (10)
--
--      Contains variables which comprise an SNMP Magnitude event.
--
--      Object Name  (ID) :  'xioHubTrapVariables'  (10)
--
--      Group designation : 'Tv'
--
--  **********************************************************************
--  **********************************************************************

    xioHubTvEventNum   OBJECT-TYPE
                   SYNTAX  DisplayString  (SIZE (0..11))
                   ACCESS  read-only
                   STATUS  mandatory
                   DESCRIPTION
                           "Event number generated by the Magnitude." 
                   ::= { xioHubTrapVariables 1 }      

     xioHubTvTimestamp   OBJECT-TYPE
                   SYNTAX  DisplayString  (SIZE (0..21))
                   ACCESS  read-only
                   STATUS  mandatory
                   DESCRIPTION
                           "Timestamp in YYYY/MM/DD HH:MM:SS format." 
                   ::= { xioHubTrapVariables 2 }      

    xioHubTvType   OBJECT-TYPE
                   SYNTAX  INTEGER
                   ACCESS  read-only
                   STATUS  mandatory
                   DESCRIPTION
                           "Magnitude-specific event type." 
                   ::= { xioHubTrapVariables 3 }      

    xioHubTvExtType   OBJECT-TYPE
                   SYNTAX  INTEGER
                   ACCESS  read-only
                   STATUS  mandatory
                   DESCRIPTION
                           "Extended Magnitude-specific event type." 
                   ::= { xioHubTrapVariables 4 }      

    xioHubTvFlags   OBJECT-TYPE
                   SYNTAX  INTEGER
                   ACCESS  read-only
                   STATUS  mandatory
                   DESCRIPTION
                           "Event flags (acknowledged, severity, etc)." 
                   ::= { xioHubTrapVariables 5 }      

    xioHubTvLedStatus   OBJECT-TYPE
                   SYNTAX  INTEGER
                   ACCESS  read-only
                   STATUS  mandatory
                   DESCRIPTION
                           "LED status." 
                   ::= { xioHubTrapVariables 6 }      

    xioHubTvMessage   OBJECT-TYPE
                   SYNTAX  DisplayString  (SIZE (0..256))
                   ACCESS  read-only
                   STATUS  mandatory
                   DESCRIPTION
                           "Event description." 
                   ::= { xioHubTrapVariables 7 }      

    xioHubTvAddress   OBJECT-TYPE
                   SYNTAX  DisplayString  (SIZE (0..25))
                   ACCESS  read-only
                   STATUS  mandatory
                   DESCRIPTION
                           "IP address or modem phone number of the Magnitude." 
                   ::= { xioHubTrapVariables 8 }      

    xioHubTvHubName   OBJECT-TYPE
                   SYNTAX  DisplayString  (SIZE (0..31))
                   ACCESS  read-only
                   STATUS  mandatory
                   DESCRIPTION
                           "Name of the Magnitude." 
                   ::= { xioHubTrapVariables 9 }      


--  **********************************************************************
--  **********************************************************************
--
--  Traps (20)
--              This section defines the traps that the HUB issues.
--
--      This section defines the traps which will be sent to an SNMP 
--      management console.  The HUB SNMP Agent will generate a trap for 
--      each alert message received from the Storage Hub.  
--
--      The message will have one of 4 severity types : Informational, Warning, 
--      Serious or Fatal. Each trap message will be identified by its severity.
--
--      The trap definitions use the MIB variable 'xioHubTvMessage' 
--      to specify the message text.        
--
--  **********************************************************************
--  **********************************************************************

    xioHubUnknownEvent   TRAP-TYPE
                 ENTERPRISE  xioHubTraps
                 VARIABLES  { 
						xioHubTvEventNum,
						xioHubTvTimestamp,
						xioHubTvType,
						xioHubTvExtType,
						xioHubTvFlags,
						xioHubTvLedStatus,
						xioHubTvMessage,
						xioHubTvAddress,
						xioHubTvHubName
						}
                 DESCRIPTION
                        "A Magnitude unknown event; the severity is invalid."
                 ::= 2

    xioHubInfoEvent   TRAP-TYPE
                 ENTERPRISE  xioHubTraps
                 VARIABLES  { 
						xioHubTvEventNum,
						xioHubTvTimestamp,
						xioHubTvType,
						xioHubTvExtType,
						xioHubTvFlags,
						xioHubTvLedStatus,
						xioHubTvMessage,
						xioHubTvAddress,
						xioHubTvHubName
						}
                 DESCRIPTION
                        "A Magnitude Informational event."
                 ::= 5

    xioHubWarningEvent   TRAP-TYPE
                 ENTERPRISE  xioHubTraps
                 VARIABLES  { 
						xioHubTvEventNum,
						xioHubTvTimestamp,
						xioHubTvType,
						xioHubTvExtType,
						xioHubTvFlags,
						xioHubTvLedStatus,
						xioHubTvMessage,
						xioHubTvAddress,
						xioHubTvHubName
						}
                 DESCRIPTION
                        "A Magnitude Warning event."
                 ::= 6

    xioHubSeriousEvent   TRAP-TYPE
                 ENTERPRISE  xioHubTraps
                 VARIABLES  { 
						xioHubTvEventNum,
						xioHubTvTimestamp,
						xioHubTvType,
						xioHubTvExtType,
						xioHubTvFlags,
						xioHubTvLedStatus,
						xioHubTvMessage,
						xioHubTvAddress,
						xioHubTvHubName
						}
                 DESCRIPTION
                        "A Magnitude Serious event."
                 ::= 7

    xioHubFatalEvent   TRAP-TYPE
                 ENTERPRISE  xioHubTraps
                 VARIABLES  { 
						xioHubTvEventNum,
						xioHubTvTimestamp,
						xioHubTvType,
						xioHubTvExtType,
						xioHubTvFlags,
						xioHubTvLedStatus,
						xioHubTvMessage,
						xioHubTvAddress,
						xioHubTvHubName
						}
                 DESCRIPTION
                        "A Magnitude Fatal event."
                 ::= 8



--  **********************************************************************
--  **********************************************************************
--
--  CPU Load Info Group (30)
--
--      Contains information and statisitics for CPU loading.
--
--      Object Name  (ID) :  'xioHubLoadInfo'  (30)
--
--      Group designation : 'Li'
--
--  unsigned char proc_free;
--  unsigned char fhab_free[8];
--  unsigned char fhab_mbs[8];
--  unsigned char fhab_ios[8];
--  unsigned char reserved[16];
--
--  **********************************************************************
--  **********************************************************************

 
    xioHubLiProcUsed   OBJECT-TYPE
                   SYNTAX  INTEGER
                   ACCESS  read-only
                   STATUS  mandatory
                   DESCRIPTION
                        "% of Processor Capacity Used." 
                   ::= { xioHubLoadInfo 1 }      


    xioHubLiFHabTable OBJECT-TYPE
                   SYNTAX  SEQUENCE OF XioHubLiFHabEntry
                   ACCESS  not-accessible
                   STATUS  mandatory
                   DESCRIPTION
                              "The FHab Cpu Load Variables."
                   ::= { xioHubLoadInfo 2 }      

            --  *************************************************************
            --  xioHubLiFHabTable objects 
            --  *************************************************************

           xioHubLiFHabEntry OBJECT-TYPE
                           SYNTAX  XioHubLiFHabEntry
                           ACCESS  not-accessible
                           STATUS  mandatory
                           DESCRIPTION
                                      "Hab status."
                           INDEX   { xioHubLiIndex }
                           ::= { xioHubLiFHabTable 1 }
        
                           XioHubLiFHabEntry ::=
                               SEQUENCE {
                                    xioHubLiFHabUsed
                                           INTEGER,
                                    xioHubLiFHabMbs
                                           INTEGER,
                                    xioHubLiFHabIOs
                                           INTEGER,
                                    xioHubLiIndex
                                           INTEGER
                                  }

            xioHubLiFHabUsed  OBJECT-TYPE
                              SYNTAX  INTEGER  
                              ACCESS  read-only
                              STATUS  mandatory
                              DESCRIPTION
                                   "% of HAB Processor Capacity Used."
                             ::= { xioHubLiFHabEntry 1 } 


            xioHubLiFHabMbs  OBJECT-TYPE
                              SYNTAX  INTEGER  
                              ACCESS  read-only
                              STATUS  mandatory
                              DESCRIPTION
                                   "HAB throughput in MB/s."
                             ::= { xioHubLiFHabEntry 2 } 


            xioHubLiFHabIOs  OBJECT-TYPE
                              SYNTAX  INTEGER  
                              ACCESS  read-only
                              STATUS  mandatory
                              DESCRIPTION
                                   "HAB I/Os per second."
                             ::= { xioHubLiFHabEntry 3 } 


            xioHubLiIndex  OBJECT-TYPE
                           SYNTAX  INTEGER  
                           ACCESS  read-only
                           STATUS  mandatory
                           DESCRIPTION
                                   "Li id."
                           ::= { xioHubLiFHabEntry 4 } 




--  **********************************************************************
--  **********************************************************************
--
--  Storage Device List Group (40)
--
--      Contains number and names of available storage devices.
--
--      Object Name  (ID) :  'xioHubStDevList'  (40)
--
--      Group designation : 'Sd'
--
--  unsigned char num_dev;
--    unsigned char Mag_name[100];
--
--  **********************************************************************
--  **********************************************************************

 
    xioHubStDevListNum   OBJECT-TYPE
                   SYNTAX  INTEGER
                   ACCESS  read-only
                   STATUS  mandatory
                   DESCRIPTION "Number of Storage devices." 
                   ::= { xioHubStorageDevList 1 }      


    xioHubStDevListSNTable OBJECT-TYPE
                   SYNTAX  SEQUENCE OF XioHubStDevListSNEntry
                   ACCESS  not-accessible
                   STATUS  mandatory
                   DESCRIPTION "The Storage Device Serial Numbers."
                   ::= { xioHubStorageDevList 2 }      

      xioHubStDevListSNEntry  OBJECT-TYPE
                      SYNTAX  XioHubStDevListSNEntry
                      ACCESS  not-accessible
                      STATUS  mandatory
                      DESCRIPTION "Serial Number."
                      INDEX   { xioHubStDevSNIndex }
                      ::= { xioHubStDevListSNTable 1 }
    	 
                      XioHubStDevListSNEntry ::=
                          SEQUENCE {
                               xioHubStDevListSNum
                                      INTEGER,
                               xioHubStDevSNIndex
                                      INTEGER
                             }

        xioHubStDevListSNum  OBJECT-TYPE
                          SYNTAX  INTEGER  
                          ACCESS  read-only
                          STATUS  mandatory
                          DESCRIPTION "The Storage Device Serial Number."
                         ::= { xioHubStDevListSNEntry 1 } 


        xioHubStDevSNIndex  OBJECT-TYPE
                          SYNTAX  INTEGER  
                          ACCESS  read-only
                          STATUS  mandatory
                          DESCRIPTION "The Storage Device Serial Number Index."
                         ::= { xioHubStDevListSNEntry 2 } 

    xioHubStDevListNTable OBJECT-TYPE
                   SYNTAX  SEQUENCE OF XioHubStDevListNEntry
                   ACCESS  not-accessible
                   STATUS  mandatory
                   DESCRIPTION "The Storage Device Names."
                   ::= { xioHubStorageDevList 3 }      

      xioHubStDevListNEntry  OBJECT-TYPE
                      SYNTAX  XioHubStDevListNEntry
                      ACCESS  not-accessible
                      STATUS  mandatory
                      DESCRIPTION "Name."
                      INDEX   { xioHubStDevNIndex }
                      ::= { xioHubStDevListNTable 1 }
    	 
                      XioHubStDevListNEntry ::=
                          SEQUENCE {
                               xioHubStDevListName
                                      DisplayString,
                               xioHubStDevNIndex
                                      INTEGER
                             }

        xioHubStDevListName  OBJECT-TYPE
                          SYNTAX  DisplayString  (SIZE (0..64))
                          ACCESS  read-only
                          STATUS  mandatory
                          DESCRIPTION "The Storage Device name."
                         ::= { xioHubStDevListNEntry 1 } 

        xioHubStDevNIndex  OBJECT-TYPE
                          SYNTAX  INTEGER
                          ACCESS  read-only
                          STATUS  mandatory
                          DESCRIPTION "The Storage Device name index."
                         ::= { xioHubStDevListNEntry 2 } 

    xioHubStDevListATable OBJECT-TYPE
                   SYNTAX  SEQUENCE OF XioHubStDevListAEntry
                   ACCESS  not-accessible
                   STATUS  mandatory
                   DESCRIPTION "The Storage Device Addresses."
                   ::= { xioHubStorageDevList 4 }      

      xioHubStDevListAEntry  OBJECT-TYPE
                      SYNTAX  XioHubStDevListAEntry
                      ACCESS  not-accessible
                      STATUS  mandatory
                      DESCRIPTION "Address."
                      INDEX   { xioHubStDevAIndex }
                      ::= { xioHubStDevListATable 1 }
    	 
                      XioHubStDevListAEntry ::=
                          SEQUENCE {
                               xioHubStDevListAddr
                                      DisplayString,
                               xioHubStDevAIndex
                                      INTEGER
                             }

        xioHubStDevListAddr  OBJECT-TYPE
                          SYNTAX  DisplayString  (SIZE (0..64))
                          ACCESS  read-only
                          STATUS  mandatory
                          DESCRIPTION "The Storage Device address."
                         ::= { xioHubStDevListAEntry 1 } 


        xioHubStDevAIndex  OBJECT-TYPE
                          SYNTAX  INTEGER
                          ACCESS  read-only
                          STATUS  mandatory
                          DESCRIPTION "The Storage Device address."
                         ::= { xioHubStDevListAEntry 2 } 


--  **********************************************************************
--  **********************************************************************
--
--  VDisk I/O Info Group (50)
--
--      Contains I/O statistics for the Vdisks (All 256).
--
--      Object Name  (ID) :  'xioHubVpInfo'  (50)
--
--      Group designation : 'Vp'
--
--  **********************************************************************
--  **********************************************************************

    xioHubVpInfoTable OBJECT-TYPE
                   SYNTAX  SEQUENCE OF XioHubVpInfoEntry
                   ACCESS  not-accessible
                   STATUS  mandatory
                   DESCRIPTION  "VDisk Performance info."
                   ::= { xioHubVpInfo 1 }

            --  *************************************************************
            --  xioHubHiHabInfoTable objects 
            --  *************************************************************

           xioHubVpInfoEntry OBJECT-TYPE
                           SYNTAX  XioHubVpInfoEntry
                           ACCESS  not-accessible
                           STATUS  mandatory
                           DESCRIPTION "Performance info on a VDisk."
                           INDEX   { xioHubVpId }
                           ::= { xioHubVpInfoTable 1 }
        
                           XioHubVpInfoEntry ::=
                               SEQUENCE {
                                    xioHubVpKBS
                                           INTEGER,
                                    xioHubVpIOs
                                           INTEGER,
                                    xioHubVpId
                                           INTEGER
                                  }

            xioHubVpKBS  OBJECT-TYPE
                         SYNTAX  INTEGER
                         ACCESS  read-only
                         STATUS  mandatory
                         DESCRIPTION "KiloBytes Per Second Throughput for this VDisk."
                         ::= { xioHubVpInfoEntry 1 } 

            xioHubVpIOs  OBJECT-TYPE
                         SYNTAX  INTEGER  
                         ACCESS  read-only
                         STATUS  mandatory
                         DESCRIPTION "IOs per second for this VDisk."
                         ::= { xioHubVpInfoEntry 2 } 


            xioHubVpId   OBJECT-TYPE
                         SYNTAX  INTEGER
                         ACCESS  read-only
                         STATUS  mandatory
                         DESCRIPTION "VDisk Table Index."
                         ::= { xioHubVpInfoEntry 3 } 

--  **********************************************************************
--  **********************************************************************
--
--  PDisk I/O Info Group (50)
--
--      Contains I/O statistics for the Pdisks (All 64).
--
--      Object Name  (ID) :  'xioHubPpInfo'  (60)
--
--      Group designation : 'Pp'
--
--  **********************************************************************
--  **********************************************************************

    xioHubPpInfoTable OBJECT-TYPE
                   SYNTAX  SEQUENCE OF XioHubPpInfoEntry
                   ACCESS  not-accessible
                   STATUS  mandatory
                   DESCRIPTION	"Physical Disk Performance info."
                   ::= { xioHubPpInfo 1 }

            --  *************************************************************
            --  xioHubHiHabInfoTable objects 
            --  *************************************************************

           xioHubPpInfoEntry OBJECT-TYPE
                           SYNTAX  XioHubPpInfoEntry
                           ACCESS  not-accessible
                           STATUS  mandatory
                           DESCRIPTION "Performance info on a Physical Disk."
                           INDEX   { xioHubPpId }
                           ::= { xioHubPpInfoTable 1 }
        
                           XioHubPpInfoEntry ::=
                               SEQUENCE {
                                    xioHubPpKBS
                                           INTEGER,
                                    xioHubPpIOs
                                           INTEGER,
                                    xioHubPpId
                                           INTEGER
                                  }

            xioHubPpKBS  OBJECT-TYPE
                         SYNTAX  INTEGER
                         ACCESS  read-only
                         STATUS  mandatory
                         DESCRIPTION "KiloBytes Per Second Throughput for this Physical Disk."
                         ::= { xioHubPpInfoEntry 1 } 

            xioHubPpIOs  OBJECT-TYPE
                         SYNTAX  INTEGER  
                         ACCESS  read-only
                         STATUS  mandatory
                         DESCRIPTION "IOs per second for this Physical Disk."
                         ::= { xioHubPpInfoEntry 2 } 

            xioHubPpId   OBJECT-TYPE
                         SYNTAX  INTEGER
                         ACCESS  read-only
                         STATUS  mandatory
                         DESCRIPTION "Physical Disk Table Index."
                         ::= { xioHubPpInfoEntry 3 } 


--  **********************************************************************
--  **********************************************************************
--
--  Server Info Group (60)
--
--      Contains vdisk and lun info for the Servers.
--
--      Object Name  (ID) :  'xioHubSvInfo'  (60)
--
--      Group designation : 'Sv'
--
--  **********************************************************************
--  **********************************************************************

    xioHubSvInfoTable OBJECT-TYPE
                   SYNTAX  SEQUENCE OF XioHubSvInfoEntry
                   ACCESS  not-accessible
                   STATUS  mandatory
                   DESCRIPTION  "Server info."
                   ::= { xioHubSvInfo 1 }

            --  *************************************************************
            --  xioHubHiHabInfoTable objects 
            --  *************************************************************

           xioHubSvInfoEntry OBJECT-TYPE
                           SYNTAX  XioHubSvInfoEntry
                           ACCESS  not-accessible
                           STATUS  mandatory
                           DESCRIPTION  "Info on a Server."
                           INDEX   { xioHubSvId }
                           ::= { xioHubSvInfoTable 1 }
        
                           XioHubSvInfoEntry ::=
                               SEQUENCE {
                                    xioHubSvClusterId
                                           INTEGER,
                                    xioHubSvFCalId
                                           INTEGER,
                                    xioHubSvVDiskId
                                           INTEGER,
                                    xioHubSvVDiskLUN
                                           INTEGER,
                                    xioHubSvId
                                           INTEGER,
                                    xioHubSvName
                                           DisplayString
                                  }

            xioHubSvClusterId   OBJECT-TYPE
                         SYNTAX  INTEGER  
                         ACCESS  read-only
                         STATUS  mandatory
                         DESCRIPTION "Cluster index number."
                         ::= { xioHubSvInfoEntry 1 } 

            xioHubSvFCalId   OBJECT-TYPE
                         SYNTAX  INTEGER  
                         ACCESS  read-only
                         STATUS  mandatory
                         DESCRIPTION "Fcal id."
                         ::= { xioHubSvInfoEntry 2 } 

            xioHubSvVDiskId   OBJECT-TYPE
                         SYNTAX  INTEGER  
                         ACCESS  read-only
                         STATUS  mandatory
                         DESCRIPTION "VDisk id."
                         ::= { xioHubSvInfoEntry 3 } 

            xioHubSvVDiskLUN  OBJECT-TYPE
                         SYNTAX  INTEGER
                         ACCESS  read-only
                         STATUS  mandatory
                         DESCRIPTION "LUN value for this vdisk."
                         ::= { xioHubSvInfoEntry 4 } 

            xioHubSvId   OBJECT-TYPE
                         SYNTAX  INTEGER  
                         ACCESS  read-only
                         STATUS  mandatory
                         DESCRIPTION "Server index number."
                         ::= { xioHubSvInfoEntry 5 } 

            xioHubSvName  OBJECT-TYPE
                         SYNTAX  DisplayString  (SIZE (0..8))
                         ACCESS  read-only
                         STATUS  mandatory
                         DESCRIPTION "Server Name."
                         ::= { xioHubSvInfoEntry 6 } 


END
