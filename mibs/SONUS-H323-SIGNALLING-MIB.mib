--
-- This SMIv2 module has been generated by smidump 0.2-cvs. Do not edit.
--

SONUS-H323-SIGNALLING-MIB DEFINITIONS ::= BEGIN

IMPORTS
    PerfCurrentCount
        FROM PerfHist-TC-MIB
    Integer32, IpAddress, MODULE-IDENTITY, OBJECT-TYPE
        FROM SNMPv2-SMI
    sonusSignallingMIBs
        FROM SONUS-SMI
    SonusAdminState, SonusServiceState
        FROM SONUS-TC;

sonusH323SignallingMIB MODULE-IDENTITY
    LAST-UPDATED    "200107310000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for H323 IP Call Signal Channel Management."
    ::= { sonusSignallingMIBs 6 }


sonusH323SignallingMIBObjects OBJECT IDENTIFIER
    ::= { sonusH323SignallingMIB 1 }

sonusH323SigTimerObjects OBJECT IDENTIFIER
    ::= { sonusH323SignallingMIBObjects 1 }

sonusH323SigSrvTimerT301 OBJECT-TYPE
    SYNTAX          Integer32 (0..65535)
    MAX-ACCESS      read-write
    STATUS          current
    DESCRIPTION     
            "The T301 timer (in seconds). This value applies to all calls."
    DEFVAL          { 180 }
    ::= { sonusH323SigTimerObjects 1 }

sonusH323SigSrvTimerT303 OBJECT-TYPE
    SYNTAX          Integer32 (0..127)
    MAX-ACCESS      read-write
    STATUS          current
    DESCRIPTION     
            "The T303 call timer (in seconds). This value applies to all calls."
    DEFVAL          { 4 }
    ::= { sonusH323SigTimerObjects 2 }

sonusH323SigSrvTimerT310 OBJECT-TYPE
    SYNTAX          Integer32 (0..127)
    MAX-ACCESS      read-write
    STATUS          current
    DESCRIPTION     
            "The T310 timer (in seconds). This value applies to all calls."
    DEFVAL          { 10 }
    ::= { sonusH323SigTimerObjects 3 }

sonusH323SigTimerEstablish OBJECT-TYPE
    SYNTAX          Integer32 (0..127)
    MAX-ACCESS      read-write
    STATUS          current
    DESCRIPTION     
            "The H225 signal channel establishment timer (in seconds.)  This value applies to all signal channels."
    DEFVAL          { 4 }
    ::= { sonusH323SigTimerObjects 4 }

sonusH323SigTimerTcpConnect OBJECT-TYPE
    SYNTAX          Integer32 (0..127)
    MAX-ACCESS      read-write
    STATUS          current
    DESCRIPTION     
            "The TCP connect timer (in seconds). This applies to all signal channels."
    DEFVAL          { 3 }
    ::= { sonusH323SigTimerObjects 5 }

sonusH323H225PortObjects OBJECT IDENTIFIER
    ::= { sonusH323SignallingMIBObjects 2 }

sonusH323H225PortIpAddress OBJECT-TYPE
    SYNTAX          IpAddress
    MAX-ACCESS      read-write
    STATUS          current
    DESCRIPTION     
            "IP Address of the H225 call signaling port - this is a required parameter."
    DEFVAL          { '00000000'H }
    ::= { sonusH323H225PortObjects 1 }

sonusH323H225PortNum OBJECT-TYPE
    SYNTAX          Integer32 (1..65535)
    MAX-ACCESS      read-write
    STATUS          current
    DESCRIPTION     
            "TCP port number of the H225 call signaling port (default is H323 registered port 1720)."
    ::= { sonusH323H225PortObjects 2 }

sonusH323H225PortShelfId OBJECT-TYPE
    SYNTAX          Integer32 (0..6)
    MAX-ACCESS      read-write
    STATUS          current
    DESCRIPTION     
            "The shelf number of the PNS board providing the H225 connection service. 0 means not configured."
    ::= { sonusH323H225PortObjects 3 }

sonusH323H225PortSlotNum OBJECT-TYPE
    SYNTAX          Integer32 (0..16)
    MAX-ACCESS      read-write
    STATUS          current
    DESCRIPTION     
            "The slot number of the PNS board providing the H225 connection service. 0 means not configured."
    ::= { sonusH323H225PortObjects 4 }

sonusH323H245PortObjects OBJECT IDENTIFIER
    ::= { sonusH323SignallingMIBObjects 3 }

sonusH323H245PortIpAddress OBJECT-TYPE
    SYNTAX          IpAddress
    MAX-ACCESS      read-write
    STATUS          current
    DESCRIPTION     
            "IP Address of the H245 port - this is a required parameter."
    DEFVAL          { '00000000'H }
    ::= { sonusH323H245PortObjects 1 }

sonusH323H245PortShelfId OBJECT-TYPE
    SYNTAX          Integer32 (0..6)
    MAX-ACCESS      read-write
    STATUS          current
    DESCRIPTION     
            "The shelf number of the PNS board providing the H245 connection service. 0 means not configured."
    ::= { sonusH323H245PortObjects 2 }

sonusH323H245PortSlotNum OBJECT-TYPE
    SYNTAX          Integer32 (0..16)
    MAX-ACCESS      read-write
    STATUS          current
    DESCRIPTION     
            "The slot number of the PNS board providing the H225 connection service. 0 means not configured."
    ::= { sonusH323H245PortObjects 3 }

sonusH323SigControlObjects OBJECT IDENTIFIER
    ::= { sonusH323SignallingMIBObjects 4 }

sonusH323SignalingControlMode OBJECT-TYPE
    SYNTAX          SonusServiceState
    MAX-ACCESS      read-write
    STATUS          current
    DESCRIPTION     
            "This object controls the mode of H323 service."
    DEFVAL          { outOfService }
    ::= { sonusH323SigControlObjects 1 }

sonusH323SignalingControlState OBJECT-TYPE
    SYNTAX          SonusAdminState
    MAX-ACCESS      read-write
    STATUS          current
    DESCRIPTION     
            "This object controls the state of H323 service."
    DEFVAL          { disabled }
    ::= { sonusH323SigControlObjects 2 }

sonusH323SignalingControlAction OBJECT-TYPE
    SYNTAX          INTEGER { none(1), force(2), dryup(3) }
    MAX-ACCESS      read-write
    STATUS          current
    DESCRIPTION     
            "This object controls to force all call drops or let the call  finish during a time period,
             which is controled by sonusH323SigTimerDryupTimeout."
    DEFVAL          { none }
    ::= { sonusH323SigControlObjects 3 }

sonusH323SignalingControlDryupTimeout OBJECT-TYPE
    SYNTAX          Integer32 (0..1440)
    MAX-ACCESS      read-write
    STATUS          current
    DESCRIPTION     
            "This timer controls the time (in minutes) to wait to place the H323 into out of
             service state, when the dryup command is issued. "
    DEFVAL          { 0 }
    ::= { sonusH323SigControlObjects 4 }

sonusH323FeObjects OBJECT IDENTIFIER
    ::= { sonusH323SignallingMIBObjects 5 }

sonusH323FeCurrentStatTable OBJECT-TYPE
    SYNTAX          SEQUENCE OF SonusH323FeCurrentStatEntry
    MAX-ACCESS      not-accessible
    STATUS          current
    DESCRIPTION     
            "The Sonus H323 FE Group Current statistic table."
    ::= { sonusH323FeObjects 1 }

sonusH323FeCurrentStatEntry OBJECT-TYPE
    SYNTAX          SonusH323FeCurrentStatEntry
    MAX-ACCESS      not-accessible
    STATUS          current
    DESCRIPTION     
            "An entry in the Sonus H323 FE current statistics table."
    INDEX           { sonusH323FeCurrentStatIndex }
    ::= { sonusH323FeCurrentStatTable 1 }

SonusH323FeCurrentStatEntry ::=
    SEQUENCE {
        sonusH323FeCurrentStatIndex     Integer32,
        sonusH323FeCurrentStatStatus    INTEGER,
        sonusH323FeCurrentStatInCallsCompl  PerfCurrentCount,
        sonusH323FeCurrentStatEgCallsCompl  PerfCurrentCount,
        sonusH323FeCurrentStatInCallsAttemped     PerfCurrentCount,
        sonusH323FeCurrentStatEgCallsAttemped     PerfCurrentCount,
        sonusH323FeCurrentStatH225MsgNoSent   PerfCurrentCount,
        sonusH323FeCurrentStatH225MsgBytesSent      PerfCurrentCount,
        sonusH323FeCurrentStatH225MsgNoRcv  PerfCurrentCount,
        sonusH323FeCurrentStatH225MsgBytesRcv     PerfCurrentCount,
        sonusH323FeCurrentStatH245MsgNoSent   PerfCurrentCount,
        sonusH323FeCurrentStatH245MsgBytesSent      PerfCurrentCount,
        sonusH323FeCurrentStatH245MsgNoRcv  PerfCurrentCount,
        sonusH323FeCurrentStatH245MsgBytesRcv     PerfCurrentCount,
        sonusH323FeCurrentStatActiveCalls PerfCurrentCount,
        sonusH323FeCurrentStatH225TcpPortsOpened        PerfCurrentCount,
        sonusH323FeCurrentStatH245TcpPortsOpened        PerfCurrentCount,
        sonusH323FeCurrentStatH245TcpPortsAllocated           PerfCurrentCount
    }

sonusH323FeCurrentStatIndex OBJECT-TYPE
    SYNTAX          Integer32 (1..2)
    MAX-ACCESS      read-only
    STATUS          current
    DESCRIPTION     
            "The index into the Sonus H323 current table. Index 1 stands for
             H225 Port statistics, index 2 stands for H245 port statistics."
    ::= { sonusH323FeCurrentStatEntry 1 }

sonusH323FeCurrentStatStatus OBJECT-TYPE
    SYNTAX          INTEGER { available(1), unavailable(2), dryup(3) }
    MAX-ACCESS      read-only
    STATUS          current
    DESCRIPTION     
            "The state of this H323 port current status."
    ::= { sonusH323FeCurrentStatEntry 2 }

sonusH323FeCurrentStatInCallsCompl OBJECT-TYPE
    SYNTAX          PerfCurrentCount
    MAX-ACCESS      read-only
    STATUS          current
    DESCRIPTION     
            "This object indicates the number of Ingress calls
             completed since system boots up. "
    ::= { sonusH323FeCurrentStatEntry 3 }

sonusH323FeCurrentStatEgCallsCompl OBJECT-TYPE
    SYNTAX          PerfCurrentCount
    MAX-ACCESS      read-only
    STATUS          current
    DESCRIPTION     
            "This object indicates the number of Egress calls
             completed since system boots up. "
    ::= { sonusH323FeCurrentStatEntry 4 }

sonusH323FeCurrentStatInCallsAttemped OBJECT-TYPE
    SYNTAX          PerfCurrentCount
    MAX-ACCESS      read-only
    STATUS          current
    DESCRIPTION     
            "This object indicates the number of Ingress calls
             attempted since system boots up. "
    ::= { sonusH323FeCurrentStatEntry 5 }

sonusH323FeCurrentStatEgCallsAttemped OBJECT-TYPE
    SYNTAX          PerfCurrentCount
    MAX-ACCESS      read-only
    STATUS          current
    DESCRIPTION     
            "This object indicates the number of Egress calls
             attempted since system boots up. "
    ::= { sonusH323FeCurrentStatEntry 6 }

sonusH323FeCurrentStatH225MsgNoSent OBJECT-TYPE
    SYNTAX          PerfCurrentCount
    MAX-ACCESS      read-only
    STATUS          current
    DESCRIPTION     
            "This object indicates the number of H225 messages 
             that have been sent since system boots up. "
    ::= { sonusH323FeCurrentStatEntry 7 }

sonusH323FeCurrentStatH225MsgBytesSent OBJECT-TYPE
    SYNTAX          PerfCurrentCount
    MAX-ACCESS      read-only
    STATUS          current
    DESCRIPTION     
            "This object indicates the number of bytes of H225 messages 
             that have been sent since system boots up. "
    ::= { sonusH323FeCurrentStatEntry 8 }

sonusH323FeCurrentStatH225MsgNoRcv OBJECT-TYPE
    SYNTAX          PerfCurrentCount
    MAX-ACCESS      read-only
    STATUS          current
    DESCRIPTION     
            "This object indicates the number of H225 messages 
             that have been received since system boots up. "
    ::= { sonusH323FeCurrentStatEntry 9 }

sonusH323FeCurrentStatH225MsgBytesRcv OBJECT-TYPE
    SYNTAX          PerfCurrentCount
    MAX-ACCESS      read-only
    STATUS          current
    DESCRIPTION     
            "This object indicates the number of bytes of H225 messages 
             that have been received since system boots up. "
    ::= { sonusH323FeCurrentStatEntry 10 }

sonusH323FeCurrentStatH245MsgNoSent OBJECT-TYPE
    SYNTAX          PerfCurrentCount
    MAX-ACCESS      read-only
    STATUS          current
    DESCRIPTION     
            "This object indicates the number of H245 messages 
             that have been sent since system boots up. "
    ::= { sonusH323FeCurrentStatEntry 11 }

sonusH323FeCurrentStatH245MsgBytesSent OBJECT-TYPE
    SYNTAX          PerfCurrentCount
    MAX-ACCESS      read-only
    STATUS          current
    DESCRIPTION     
            "This object indicates the number of bytes of H245 messages 
             that have been sent since system boots up. "
    ::= { sonusH323FeCurrentStatEntry 12 }

sonusH323FeCurrentStatH245MsgNoRcv OBJECT-TYPE
    SYNTAX          PerfCurrentCount
    MAX-ACCESS      read-only
    STATUS          current
    DESCRIPTION     
            "This object indicates the number of H245 messages 
             that have been received since system boots up. "
    ::= { sonusH323FeCurrentStatEntry 13 }

sonusH323FeCurrentStatH245MsgBytesRcv OBJECT-TYPE
    SYNTAX          PerfCurrentCount
    MAX-ACCESS      read-only
    STATUS          current
    DESCRIPTION     
            "This object indicates the number of bytes of H245 messages 
             that have been received since system boots up. "
    ::= { sonusH323FeCurrentStatEntry 14 }

sonusH323FeCurrentStatActiveCalls OBJECT-TYPE
    SYNTAX          PerfCurrentCount
    MAX-ACCESS      read-only
    STATUS          current
    DESCRIPTION     
            "This object indicates the number of active 
             calls at this moment."
    ::= { sonusH323FeCurrentStatEntry 15 }

sonusH323FeCurrentStatH225TcpPortsOpened OBJECT-TYPE
    SYNTAX          PerfCurrentCount
    MAX-ACCESS      read-only
    STATUS          current
    DESCRIPTION     
            "This object indicates the number of H225 TCP ports 
             opened at this moment."
    ::= { sonusH323FeCurrentStatEntry 16 }

sonusH323FeCurrentStatH245TcpPortsOpened OBJECT-TYPE
    SYNTAX          PerfCurrentCount
    MAX-ACCESS      read-only
    STATUS          current
    DESCRIPTION     
            "This object indicates the number of H245 TCP ports 
             opened at this moment."
    ::= { sonusH323FeCurrentStatEntry 17 }

sonusH323FeCurrentStatH245TcpPortsAllocated OBJECT-TYPE
    SYNTAX          PerfCurrentCount
    MAX-ACCESS      read-only
    STATUS          current
    DESCRIPTION     
            "This object indicates the number of H245 TCP ports 
             allocated at this moment."
    ::= { sonusH323FeCurrentStatEntry 18 }

END -- end of module SONUS-H323-SIGNALLING-MIB.
