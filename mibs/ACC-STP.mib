ACC-STP DEFINITIONS ::= BEGIN

    IMPORTS
		OBJECT-TYPE, IpAddress, TimeTicks, Gauge, Counter FROM RFC1155-SMI
		TRAP-TYPE FROM RFC-1215
   accTrapLogSeqNum FROM ACC-SYSTEM
	accBRG, DisplayString FROM ACC-MIB;
-- Spanning Tree Protocol Group
    accStp   OBJECT IDENTIFIER ::= { accBRG 2 }
	accStpPriority	OBJECT-TYPE   
			SYNTAX	INTEGER (0..255)
			ACCESS	read-write
			STATUS	mandatory
			DESCRIPTION
                " Among all devices participating in spanning tree, the
                   one with the highest priority (numerically lowest
                   value of this parameter) is elected as the Root
                   of the spanning tree."
			::= { accStp 1 } 
	accStpId	OBJECT-TYPE   
			SYNTAX	OCTET STRING
			ACCESS	read-only
			STATUS	mandatory
			DESCRIPTION
                " Unique bridge identifier of this bridge.  This object
                   comprises two parts, one of which is the MAC address,
                   and the other of which is the brStpPriority and is the
                   more significant part in priority comparisons."
			::= { accStp 2 } 
	accStpBrAddr	OBJECT-TYPE   
			SYNTAX	OCTET STRING
			ACCESS	read-only
			STATUS	mandatory
			DESCRIPTION
             " MAC address of this bridge."
			::= { accStp 3 }    
	accStpMode	OBJECT-TYPE   
			SYNTAX	INTEGER {
				on(1),
				off(2)
				}
			ACCESS	read-write
			STATUS	mandatory
			DESCRIPTION
                " State of this Bridge's participation in Spanning Tree.
                  Spanning Tree  takes care of network connectivity changes
                   caused by addition/removal/failure of links.
                   It avoids loops when any two networks have redundant
                   connections between them."
			::= { accStp 4 } 
	accStpFilterTime	OBJECT-TYPE   
			SYNTAX	TimeTicks
			ACCESS	read-only
			STATUS	mandatory
			DESCRIPTION
                 " Minimum time period elapsing between the
                   transmission of Hello frames through a given Bridge Port.
                   No more than two Hello frames shall be transmitted in any
                   brStpFilterTime period."
			::= { accStp 5 }
	accStpMcastAddr		OBJECT-TYPE   
			SYNTAX	OCTET STRING
			ACCESS	read-write
			STATUS	mandatory
			DESCRIPTION
                 " A unique MAC group address, recognised by all the Bridges
                   within the Bridged Local Area Network."
			::= { accStp 6 } 
	accStpTopChangeDet	OBJECT-TYPE   
			SYNTAX	INTEGER {
				no(0),
				yes(1)
				}
			ACCESS	read-only
			STATUS	mandatory
			DESCRIPTION
                " Indicates if this unit has detected the Topology
                  change indication in the hello BPDU.
		"
			::= { accStp 7 } 
	accStpTopChange		OBJECT-TYPE   
			SYNTAX	INTEGER {
				no(0),
				yes(1)
				}
			ACCESS	read-only
			STATUS	mandatory
			DESCRIPTION
                " Indicates if the STP topology of a network is in
                   process of changing.
		"
			::= { accStp 8 } 
	accStpTopChangeTimer	OBJECT-TYPE   
			SYNTAX	TimeTicks
			ACCESS	read-only
			STATUS	mandatory
			DESCRIPTION
                 " This timer serves to determine the time period for
                    which hello frames are transmitted with the
                   Topology Change flag parameter set by the Bridge when
                   it is the Root following the detection of a topology
                   change."
			::= { accStp 9 }
	accStpDesRoot	OBJECT-TYPE   
			SYNTAX	OCTET STRING
			ACCESS	read-only
			STATUS	mandatory
			DESCRIPTION
               "  The Bridge Identifier  of the device currently
                   assumed by this unit to be the Root."
			::= { accStp 10 } 
	accStpRootPathCost	OBJECT-TYPE   
			SYNTAX	INTEGER
			ACCESS	read-only
			STATUS	mandatory
			DESCRIPTION
                " Current path cost to the Root Bridge."
			::= { accStp 11 }
	accStpRootPort	OBJECT-TYPE   
			SYNTAX	OCTET STRING
			ACCESS	read-only
			STATUS	mandatory
			DESCRIPTION
               " Port Number of the one Port in the direction of the Root.
                  (Value is meaningless if this unit is the Root)."
			::= { accStp 12 } 
	accStpMaxAge	OBJECT-TYPE   
			SYNTAX	INTEGER (4..3600)
			ACCESS	read-write
			STATUS	mandatory
			DESCRIPTION
                 " The value of the Max Age parameter when the Bridge is the
                  Root or attempting to become the Root.
                  The Max Age parameter is conveyed to ensure that each Bridge
                  in a Bridged Local Area Network has a consistent value
                  against which to test the age of stored protocol information."
			::= { accStp 13 }
	accStpHelloTime		OBJECT-TYPE   
			SYNTAX	INTEGER (2..1800)
			ACCESS	read-write
			STATUS	mandatory
			DESCRIPTION
                 " Interval between Hello frames that this
                  Bridge will initiate when it is Root or is attempting
                  to be Root."
			::= { accStp 14 }
	accStpForwardDelay	OBJECT-TYPE   
			SYNTAX	INTEGER (5..3600)
			ACCESS	read-write
			STATUS	mandatory
			DESCRIPTION
                 " The time  (seconds) spent in the Listening state while
                   moving from the Blocking state to the Learning state.
                   The time  (seconds) spent in the Learning state while
                   moving from the Listening state to the Forwarding state.
                   The value  (seconds) used for the ageing time of dynamic 
                   entries in the Forwarding Database table wile the Topology
                   Change flag is set in protocol messages received from
                   the Root."
			::= { accStp 15 }
	accStpUpTime	OBJECT-TYPE   
			SYNTAX	TimeTicks
			ACCESS	read-only
			STATUS	mandatory
			DESCRIPTION
                 " "
			::= { accStp 16 }
	accStpTopChangeCnts	OBJECT-TYPE   
			SYNTAX	Counter
			ACCESS	read-only
			STATUS	mandatory
			DESCRIPTION
                   " "
			::= { accStp 17 }

END
