-- extracted from draft-jenkins-ipsec-tun-mon-mib-00.txt
-- at Sat Oct  6 06:06:31 2001

IPSEC-TUN-MON-MIB DEFINITIONS ::= BEGIN

   IMPORTS
       MODULE-IDENTITY, OBJECT-TYPE, Counter32, Counter64, Unsigned32,
        Gauge32, OBJECT-IDENTITY, experimental, NOTIFICATION-TYPE
                                       FROM SNMPv2-SMI
       TEXTUAL-CONVENTION, TruthValue FROM SNMPv2-TC
       InetAddressType, InetAddress   FROM INET-ADDRESS-MIB
       IsakmpCookie                   FROM ISAKMP-DOI-IND-MON-MIB
   ;

   ipsecTunMonModule  MODULE-IDENTITY
       LAST-UPDATED   "0010041200Z"
       ORGANIZATION   "IETF IPsec Working Group"
       CONTACT-INFO
                   "Tim Jenkins
                    Catena Networks
                    307 Legget Drive
                    Kanata, ON
                    Canada
                    K2K 3C8
                    +1 (613) 599-6430
                    tjenkins@catena.com "

       DESCRIPTION
           "The MIB module to describe logical IPsec channel and tunnel
           objects, and entity level objects and events associated with
           these objects."
       REVISION       "0010041200Z"
       DESCRIPTION
           "Initial revision."
   --  ::= { ? }
       -- bogus value currently in use
      ::= { experimental 1010 }

   --
   -- textual conventions
   --

   IpsecChanOrTunType ::= TEXTUAL-CONVENTION
       DISPLAY-HINT   "d"
       STATUS     current
       DESCRIPTION
           "A value indicating an implementation specific type for
           channels and tunnels.
           The values below are defined as examples only, and are not
           intended to imply any specific support or capability."
       SYNTAX     INTEGER {
                       unknown(0),
                       permanent(1),
                       transient(2),
                       management(3)
                   }

   --
   -- MIB root (trunk?)
   --

   ipsecTunnelMonitorMIB OBJECT-IDENTITY
       STATUS current
       DESCRIPTION
           "This is the base object identifier for all branches."
       ::= { ipsecTunMonModule 1 }

   -- first level branches

   channelObjects OBJECT-IDENTITY
       STATUS     current
       DESCRIPTION
           "This is the base object identifier for all channel related
           objects."
       ::= { ipsecTunnelMonitorMIB 1 }

   tunnelObjects OBJECT-IDENTITY
       STATUS     current
       DESCRIPTION
           "This is the base object identifier for all tunnel related
           objects."
       ::= { ipsecTunnelMonitorMIB 2 }


   -- second level branches

    channelTables OBJECT-IDENTITY
       STATUS     current
       DESCRIPTION
           "This is the base object identifier for all objects which are
           tables for channels."
       ::= { channelObjects 1 }

    channelStats OBJECT-IDENTITY
       STATUS     current
       DESCRIPTION
           "This is the base object identifier for all objects which are
           global (non-error) counters for channels."
       ::= { channelObjects 2 }

   channelErrors OBJECT-IDENTITY
       STATUS     current
       DESCRIPTION
           "This is the base object identifier for all objects which are
           global error counters for channels."
       ::= { channelObjects 3 }

   channelTraps OBJECT-IDENTITY
       STATUS     current
       DESCRIPTION
           "This is the base object identifier for all objects which are
           traps for channels."
       ::= { channelObjects 4 }

    channelTrapObjects OBJECT-IDENTITY
       STATUS     current
       DESCRIPTION
           "This is the base object identifier for objects which are
           used as part of traps for channels."
       ::= { channelObjects 5 }

   channelTrapControl OBJECT-IDENTITY
       STATUS     current
       DESCRIPTION
           "This is the base object identifier for all objects which are
           trap controls for channel traps."
       ::= { channelObjects 6 }

   channelGroups  OBJECT-IDENTITY
       STATUS     current
       DESCRIPTION
           "This is the base object identifier for all objects which
           describe the groups in the channel part of this MIB."
       ::= { channelObjects 7 }

    channelConformance  OBJECT-IDENTITY
       STATUS     current
       DESCRIPTION
           "This is the base object identifier for all objects which
           describe the conformance in the channel part of this MIB."
       ::= { channelObjects 8 }

    tunnelTables OBJECT-IDENTITY
       STATUS     current
       DESCRIPTION
           "This is the base object identifier for all objects which are
           tables for tunnels."
       ::= { tunnelObjects 1 }

    tunnelStats OBJECT-IDENTITY
       STATUS     current
       DESCRIPTION
           "This is the base object identifier for all objects which are
           global (non-error) counters for tunnels."
       ::= { tunnelObjects 2 }

   tunnelErrors OBJECT-IDENTITY
       STATUS     current
       DESCRIPTION
           "This is the base object identifier for all objects which are
           global error counters for tunnels."
       ::= { tunnelObjects 3 }

   tunnelTraps OBJECT-IDENTITY
       STATUS     current
       DESCRIPTION
           "This is the base object identifier for all objects which are
           traps for tunnels."
       ::= { tunnelObjects 4 }

    tunnelTrapObjects OBJECT-IDENTITY
       STATUS     current
       DESCRIPTION
           "This is the base object identifier for objects which are
           used as part of traps for tunnels."
       ::= { tunnelObjects 5 }

   tunnelTrapControl OBJECT-IDENTITY
       STATUS     current
       DESCRIPTION
           "This is the base object identifier for all objects which are
           trap controls for tunnel traps."
       ::= { tunnelObjects 6 }

   tunnelGroups   OBJECT-IDENTITY
       STATUS     current
       DESCRIPTION
           "This is the base object identifier for all objects which
           describe the groups in the tunnel part of this MIB."
       ::= { tunnelObjects 7 }

   tunnelConformance  OBJECT-IDENTITY
       STATUS     current
       DESCRIPTION
           "This is the base object identifier for all objects which
           describe the conformance in the tunnel part of this MIB."
       ::= { tunnelObjects 8 }


   -- the IPsec Channel statistics group
   --
   -- a collection of object providing information about channels
   -- created using IKE SAs

   currentChannels    OBJECT-TYPE
       SYNTAX     Gauge32
       MAX-ACCESS read-only
       STATUS     current
       DESCRIPTION
           "The total number of channels currently in existence in the
           entity.

           This is the same as the number of rows in the channel table,
           whether there are IKE SAs for each row or not."
       ::= { channelStats 1 }

   totalChannels  OBJECT-TYPE
       SYNTAX     Counter32
       MAX-ACCESS read-only
       STATUS     current
       DESCRIPTION
           "The total number of channels created by the entity since
           system boot.

           Channel creation is defined as the addition of a row to the
           channel table, whether an IKE SA was created at the same time
           or not."
       ::= { channelStats 2 }

   deletedChannels    OBJECT-TYPE
       SYNTAX     Counter32
       MAX-ACCESS read-only
       STATUS     current
       DESCRIPTION
           "The total number of channels deleted by the entity.

           Channel deletion is defined as the removal of a row from the
           channel table, independent of the existence of the IKE SAs
           that may have supported it.
           Note that the sum of 'currentChannels' and 'deletedChannels'
           is equal to 'totalChannels'."
       ::= { channelStats 3 }


   -- the IPsec Tunnel statistics group
   --
   -- a collection of objects providing information about tunnels
   -- created using IPsec SA suites

   currentTunnels OBJECT-TYPE
       SYNTAX     Gauge32
       MAX-ACCESS read-only
       STATUS     current
       DESCRIPTION
           "The total number of tunnels currently in existence in the
           entity.

           This is the same as the number of rows in the tunnel table,
           whether there are IPsec SA suites for each row or not."
       ::= { tunnelStats 1 }

   totalTunnels   OBJECT-TYPE
       SYNTAX     Counter32
       MAX-ACCESS read-only
       STATUS     current
       DESCRIPTION
           "The total number of tunnels created by the entity since
           system boot.

           Tunnel creation is defined as the addition of a row to the
           tunnel table, whether an IPsec SA was created at the same
           time or not."
       ::= { tunnelStats 2 }

   deletedTunnels OBJECT-TYPE
       SYNTAX     Counter32
       MAX-ACCESS read-only
       STATUS     current
       DESCRIPTION
           "The total number of tunnels deleted by the entity.

           Tunnel deletion is defined as the removal of a row from the
           tunnel table, independent of the existence of the phase 2 SA
           suites that may have supported it.

           Note that the sum of 'currentTunnels' and 'deletedTunnels'
           should is to 'totalTunnels'."
       ::= { tunnelStats 3 }

   -- the IPsec Control Channel MIB-Group
   --
   -- a collection of objects providing information about
   -- IPsec's control channels


   ipsecChannelTable OBJECT-TYPE
       SYNTAX     SEQUENCE OF IpsecChannelEntry
       MAX-ACCESS not-accessible
       STATUS     current
       DESCRIPTION
           "The (conceptual) table containing information on control
           channels.

           The number of rows in this table is, at a minimum, the same
           as the number of IKE SAs that have the same phase 1 ID pairs.
           Additional rows for channels without active phase 1 SAs may
           also appear in the table.

           The maximum number of rows is implementation dependent."
       ::= { channelTables 1 }

   ipsecChannelEntry OBJECT-TYPE
       SYNTAX     IpsecChannelEntry
       MAX-ACCESS not-accessible
       STATUS     current
       DESCRIPTION
           "An entry (conceptual row) containing the information on a
           particular control channel.

           A row in this table cannot be created or deleted by SNMP
           operations on columns of the table."
       INDEX  {
                   ipsecChannelType,
                   ipsecChannelLocalEndpoint,
                   ipsecChannelRemoteEndpoint
               }
       ::= { ipsecChannelTable 1 }

   IpsecChannelEntry  ::= SEQUENCE {
   -- indices
       ipsecChannelType                   IpsecChanOrTunType,
       ipsecChannelLocalEndpoint          Unsigned32,
       ipsecChannelRemoteEndpoint         Unsigned32,

   -- virtual channel status
       ipsecChannelCurrentSAs             Gauge32,
       ipsecChannelTotalSAs               Counter32,
       ipsecChannelDeletedSAs             Counter32,
       ipsecChannelTimeUpSeconds          Counter32, -- since SAs > 0
       ipsecChannelTimeDownSeconds        Counter32, -- since SAs = 0

   -- aggregate statistics (all SAs)
       ipsecChannelInboundOctets          Counter32,
       ipsecChannelOutboundOctets         Counter32,
       ipsecChannelInboundPackets         Counter32,
       ipsecChannelOutboundPackets        Counter32,

   -- aggregate error statistics
       ipsecChannelReceiveErrors          Counter32,
       ipsecChannelSendErrors             Counter32,

   -- IPsec tunnel (Phase 2) statistics
       ipsecChannelCurrentTunnels         Gauge32,
       ipsecChannelTotalTunnels           Counter32,
       ipsecChannelDeletedTunnels         Counter32,

   -- IPsec tunnel (Phase 2) statistics (aggregate)
       ipsecChannelTunnelInboundOctets    Counter64,
       ipsecChannelTunnelOutboundOctets   Counter64,
       ipsecChannelTunnelInboundPackets   Counter64,
       ipsecChannelTunnelOutboundPackets  Counter64,

   -- IPsec SA (Phase 2) error statistics (aggregate)
       ipsecChannelTunnelReceiveErrors    Counter32,
       ipsecChannelTunnelSendErrors       Counter32
   }


   ipsecChannelType OBJECT-TYPE
       SYNTAX     IpsecChanOrTunType
       MAX-ACCESS not-accessible
       STATUS     current
       DESCRIPTION
           "The type of control channel represented by this row.

           This is an implementation dependent value, used to assist in
           controlling how channels are sorted."
       ::= { ipsecChannelEntry 1 }

   ipsecChannelLocalEndpoint OBJECT-TYPE
       SYNTAX     Unsigned32
       MAX-ACCESS not-accessible
       STATUS     current
       DESCRIPTION
           "The index value of the row of the IKE Monitoring MIB's
           endpoint table corresponding to the local endpoint."
       ::= { ipsecChannelEntry 2 }

   ipsecChannelRemoteEndpoint OBJECT-TYPE
       SYNTAX     Unsigned32
       MAX-ACCESS not-accessible
       STATUS     current
       DESCRIPTION
           "The index value of the row of the IKE Monitoring MIB's
           endpoint table corresponding to the remote endpoint."
       ::= { ipsecChannelEntry 3 }

   ipsecChannelCurrentSAs OBJECT-TYPE
       SYNTAX     Gauge32
       MAX-ACCESS read-only
       STATUS     current
       DESCRIPTION
           "The number of IKE SAs that are currently active that make up
           this channel.

           This value may be 0 if the channel has not yet been set up,
           or the implementation does not require the existence of IKE
           SAs for the channel to exist, or if the channel is considered
           a permanent entry in the table by the implementation.

           This value should not include SA establishment attempts in
           progress."
       ::= { ipsecChannelEntry 4 }

   ipsecChannelTotalSAs OBJECT-TYPE
       SYNTAX     Counter32
       MAX-ACCESS read-only
       STATUS     current
       DESCRIPTION
           "The total number of IKE SAs that are part of this channel
           that have been created in the entity since boot time.

           This value should not include failed SA establishment
           attempts."
       ::= { ipsecChannelEntry 5 }

   ipsecChannelDeletedSAs OBJECT-TYPE
       SYNTAX     Counter32
       MAX-ACCESS read-only
       STATUS     current
       DESCRIPTION
           "The total number of IKE SAs that are part of this channel
           that have been deleted in the entity since boot time.

           The sum of 'ipsecChannelCurrentSAs' and this value should
           equal ipsecChannelTotalSAs."
       ::= { ipsecChannelEntry 6 }

   ipsecChannelTimeUpSeconds OBJECT-TYPE
       SYNTAX     Counter32
       UNITS      "seconds"
       MAX-ACCESS read-only
       STATUS     current
       DESCRIPTION
           "The total number of seconds since there has been at least
           one valid IKE SA supporting the channel. In other words, the
           number of seconds since the value of 'ipsecChannelCurrentSAs'
           changed from 0 to any other value."
       ::= { ipsecChannelEntry 7 }

   ipsecChannelTimeDownSeconds OBJECT-TYPE
       SYNTAX     Counter32
       UNITS      "seconds"
       MAX-ACCESS read-only
       STATUS     current
       DESCRIPTION
           "The total number of seconds since the last valid IKE SA
           supporting the channel was deleted. In other words, the
           number of seconds since the value of 'ipsecChannelCurrentSAs'
           changed to 0 from any other value."
       ::= { ipsecChannelEntry 8 }

   ipsecChannelInboundOctets OBJECT-TYPE
       SYNTAX     Counter32
       UNITS      "bytes"
       MAX-ACCESS read-only
       STATUS     current
       DESCRIPTION
           "The amount of traffic measured in bytes received by the
           channel. This is the sum of 'saInOctets' from the 'saEntry'
           of each IKE SA in 'saTable' that is part of this channel."
       ::= { ipsecChannelEntry 9 }

   ipsecChannelOutboundOctets OBJECT-TYPE
       SYNTAX     Counter32
       UNITS      "bytes"
       MAX-ACCESS read-only
       STATUS     current
       DESCRIPTION
           "The amount of traffic measured in bytes sent by the channel.
           This is the sum of 'saOutOctets' from the 'saEntry' of each
           IKE SA in 'saTable' that is part of this channel."
       ::= { ipsecChannelEntry 10 }

   ipsecChannelInboundPackets OBJECT-TYPE
       SYNTAX     Counter32
       MAX-ACCESS read-only
       STATUS     current
       DESCRIPTION
           "The total number of packets received by the channel. This is
           the sum of 'saInPackets' from the 'saEntry' of each IKE SA in
           'saTable' that is part of this channel."
       ::= { ipsecChannelEntry 11 }

   ipsecChannelOutboundPackets OBJECT-TYPE
       SYNTAX     Counter32
       MAX-ACCESS read-only
       STATUS     current
       DESCRIPTION
           "The total number of packets sent by the channel. This is the
           sum of 'saOutPackets' from the 'saEntry' of each IKE SA in
           'saTable' that is part of this channel."
       ::= { ipsecChannelEntry 12 }

   ipsecChannelReceiveErrors OBJECT-TYPE
       SYNTAX     Counter32
       MAX-ACCESS read-only
       STATUS     current
       DESCRIPTION
           "The total number of receive errors incurred in the channel.
           This is the sum of all receive errors from the 'saEntry' of
           each IKE SA in 'saTable' that is part of this channel."
       ::= { ipsecChannelEntry 13 }

   ipsecChannelSendErrors OBJECT-TYPE
       SYNTAX     Counter32
       MAX-ACCESS read-only
       STATUS     current
       DESCRIPTION
           "The total number of send errors incurred in the channel.
           This is the sum of all send errors from the 'saEntry' of each
           IKE SA in 'saTable' that is part of this channel."
       ::= { ipsecChannelEntry 14 }

   ipsecChannelCurrentTunnels OBJECT-TYPE
       SYNTAX     Gauge32
       MAX-ACCESS read-only
       STATUS     current
       DESCRIPTION
           "The number of IPsec tunnels that are currently active that
           were created by this channel.

           This value should not include tunnel establishment attempts
           that are in progress."
       ::= { ipsecChannelEntry 15 }

   ipsecChannelTotalTunnels OBJECT-TYPE
       SYNTAX     Counter32
       MAX-ACCESS read-only
       STATUS     current
       DESCRIPTION
           "The total number of IPsec tunnels that have been created in
           the entity by this channel since boot time.

           This value should not include failed tunnel establishment
           attempts."
       ::= { ipsecChannelEntry 16 }

   ipsecChannelDeletedTunnels OBJECT-TYPE
       SYNTAX     Counter32
       MAX-ACCESS read-only
       STATUS     current
       DESCRIPTION
           "The total number of IPsec tunnels that have been deleted by
           this channel in the entity since boot time.

           The sum of 'ipsecChannelCurrentTunnels' and this value should
           equal 'ipsecChannelTotalTunnels'."
       ::= { ipsecChannelEntry 17 }

   ipsecChannelTunnelInboundOctets OBJECT-TYPE
       SYNTAX     Counter64
       UNITS      "bytes"
       MAX-ACCESS read-only
       STATUS     current
       DESCRIPTION
           "The amount of traffic measured in bytes received by all
           tunnels created by the channel."
       ::= { ipsecChannelEntry 18 }

   ipsecChannelTunnelOutboundOctets OBJECT-TYPE
       SYNTAX     Counter64
       UNITS      "bytes"
       MAX-ACCESS read-only
       STATUS     current
       DESCRIPTION
           "The amount of traffic measured in bytes sent by all tunnels
           created by the channel."
       ::= { ipsecChannelEntry 19 }

   ipsecChannelTunnelInboundPackets OBJECT-TYPE
       SYNTAX     Counter64
       MAX-ACCESS read-only
       STATUS     current
       DESCRIPTION
           "The total number of packets received by all tunnels created
           by the channel."
       ::= { ipsecChannelEntry 20 }

   ipsecChannelTunnelOutboundPackets OBJECT-TYPE
       SYNTAX     Counter64
       MAX-ACCESS read-only
       STATUS     current
       DESCRIPTION
           "The total number of packets sent by all tunnels created by
           the channel."
       ::= { ipsecChannelEntry 21 }

   ipsecChannelTunnelReceiveErrors OBJECT-TYPE
       SYNTAX     Counter32
       MAX-ACCESS read-only
       STATUS     current
       DESCRIPTION
           "The total number of receive errors incurred in all tunnels
           created by the channel."
       ::= { ipsecChannelEntry 22 }

   ipsecChannelTunnelSendErrors OBJECT-TYPE
       SYNTAX     Counter32
       MAX-ACCESS read-only
       STATUS     current
       DESCRIPTION
           "The total number of send errors incurred in all tunnels
           created the channel."
       ::= { ipsecChannelEntry 23 }


   -- the IPsec channel SA table
   --
   -- a table providing a reference to specific IKE SAs as used by
   -- IPsec channels
   ipsecChannelSaTable OBJECT-TYPE
       SYNTAX     SEQUENCE OF IpsecChannelSaEntry
       MAX-ACCESS not-accessible
       STATUS     current
       DESCRIPTION
           "The (conceptual) table containing information on which IKE
           SAs are used in channels.

           The number of rows is the same as the number of IKE SAs in
           the entity.

           The maximum number of rows is implementation dependent."
       ::= { channelTables 2 }

   ipsecChannelSaEntry OBJECT-TYPE
       SYNTAX     IpsecChannelSaEntry
       MAX-ACCESS not-accessible
       STATUS     current
       DESCRIPTION
           "An entry (conceptual row) containing the identifiers of a
           specific IKE SA.

           A row in this table cannot be created or deleted by SNMP
           operations on columns of the table."
       INDEX  {
                   ipsecChannelType,
                   ipsecChannelLocalEndpoint,
                   ipsecChannelRemoteEndpoint,
                   ipsecChannelSaIndex
               }
       ::= { ipsecChannelSaTable 1 }

   IpsecChannelSaEntry ::= SEQUENCE {

   -- additional index to augment channel table
       ipsecChannelSaIndex                    Unsigned32,

   -- the SA specifiers
       ipsecChannelSaLocalIpAddrType          InetAddressType,
       ipsecChannelSaLocalIpAddress           InetAddress,
       ipsecChannelSaRemoteIpAddrType         InetAddressType,
       ipsecChannelSaRemoteIpAddress          InetAddress,
       ipsecChannelSaInitiatorCookie          IsakmpCookie,
       ipsecChannelSaResponderCookie          IsakmpCookie
   }


   ipsecChannelSaIndex OBJECT-TYPE
       SYNTAX     Unsigned32 (1..16777215)
       MAX-ACCESS not-accessible
       STATUS     current
       DESCRIPTION
           "A unique value, greater than zero, for each IKE SA in the
           channel. It is recommended that values are assigned
           contiguously starting from 1."
       ::= { ipsecChannelSaEntry 1 }

   ipsecChannelSaLocalIpAddrType OBJECT-TYPE
       SYNTAX     InetAddressType
       MAX-ACCESS read-only
       STATUS     current
       DESCRIPTION
           "The type of the local address used to negotiate the IKE SA
           in the channel. (The value of 'saIkeLocalIpAddressType' from
           'ikeMonModule' for this row.)"
       ::= { ipsecChannelSaEntry 2 }

   ipsecChannelSaLocalIpAddress OBJECT-TYPE
       SYNTAX     InetAddress (SIZE(4|16|20))
       MAX-ACCESS read-only
       STATUS     current
       DESCRIPTION
           "The local address used to negotiate the IKE SA in the
           channel. (The value of 'saIkeLocalIpAddress' from
           'ikeMonModule' for this row.)"
       ::= { ipsecChannelSaEntry 3 }

   ipsecChannelSaRemoteIpAddrType OBJECT-TYPE
       SYNTAX     InetAddressType
       MAX-ACCESS read-only
       STATUS     current
       DESCRIPTION
           "The type of the remote address used to negotiate the IKE SA
           in the channel. (The value of 'saIkeRemoteIpAddressType' from
           'ikeMonModule' for this row.)"
       ::= { ipsecChannelSaEntry 4 }

   ipsecChannelSaRemoteIpAddress OBJECT-TYPE
       SYNTAX     InetAddress (SIZE(4|16|20))
       MAX-ACCESS read-only
       STATUS     current
       DESCRIPTION
           "The remote address used to negotiate the IKE SA in the
           channel. (The value of 'saIkeRemoteIpAddress' from
           'ikeMonModule' for this row.)"
       ::= { ipsecChannelSaEntry 5 }

   ipsecChannelSaInitiatorCookie OBJECT-TYPE
       SYNTAX     IsakmpCookie
       MAX-ACCESS read-only
       STATUS     current
       DESCRIPTION
           "The value of the cookie used by the initiator for the IKE SA
           in the channel. (The value of 'saIkeInitiatorCookie' from
           'ikeMonModule' for this row.)"
       ::= { ipsecChannelSaEntry 6 }

   ipsecChannelSaResponderCookie OBJECT-TYPE
       SYNTAX     IsakmpCookie
       MAX-ACCESS read-only
       STATUS     current
       DESCRIPTION
           "The value of the cookie used by the responder for the IKE SA
           in the channel. (The value of 'saIkeResponderCookie' from
           'ikeMonModule' for this row.)"
       ::= { ipsecChannelSaEntry 7 }



   -- the IPsec channel SA aggregates table
   --
   -- a table providing aggregate statistics for the user-defined
   -- channel types


   ipsecChanAggTable OBJECT-TYPE
       SYNTAX     SEQUENCE OF IpsecChanAggEntry
       MAX-ACCESS not-accessible
       STATUS     current
       DESCRIPTION
           "The optional (conceptual) table containing information on
           aggregate statistics for the channel types.

           The number of rows is the same as the number of channel types
           supported by the entity.

           The maximum number of rows is implementation dependent."
       ::= { channelTables 3 }

   ipsecChanAggEntry OBJECT-TYPE
       SYNTAX     IpsecChanAggEntry
       MAX-ACCESS not-accessible
       STATUS     current
       DESCRIPTION
           "An entry (conceptual row) containing the aggregate
           statistics for a specific channel type.
           A row in this table cannot be created or deleted by SNMP
           operations on columns of the table."
       INDEX  { ipsecChanAggType }
       ::= { ipsecChanAggTable 1 }

   IpsecChanAggEntry ::= SEQUENCE {
   -- index
       ipsecChanAggType               IpsecChanOrTunType,

   -- channel counts
       ipsecChanAggCurrentChannels    Gauge32,
       ipsecChanAggTotalChannels      Counter32,
       ipsecChanAggDeletedChannels    Counter32,

   -- aggregate statistics (all SAs)
       ipsecChanAggInboundOctets      Counter64,
       ipsecChanAggOutboundOctets     Counter64,
       ipsecChanAggInboundPackets     Counter64,
       ipsecChanAggOutboundPackets    Counter64,

   -- aggregate error statistics
       ipsecChanAggReceiveErrors      Counter32,
       ipsecChanAggSendErrors         Counter32,

   -- IPsec tunnel (Phase 2) statistics
       ipsecChanAggCurrentTunnels     Gauge32,
       ipsecChanAggTotalTunnels       Counter32,
       ipsecChanAggDeletedTunnels     Counter32,

   -- IPsec tunnel (Phase 2) statistics (aggregate)
       ipsecChanAggTnlInboundOctets   Counter64,
       ipsecChanAggTnlOutboundOctets  Counter64,
       ipsecChanAggTnlInboundPackets  Counter64,
       ipsecChanAggTnlOutboundPackets Counter64,

   -- IPsec SA (Phase 2) error statistics (aggregate)
       ipsecChanAggTnlReceiveErrors   Counter32,
       ipsecChanAggTnlSendErrors      Counter32

   }


   ipsecChanAggType OBJECT-TYPE
       SYNTAX     IpsecChanOrTunType
       MAX-ACCESS not-accessible
       STATUS     current
       DESCRIPTION
           "The type of control channel for which this row aggregrates
           statistics."
       ::= { ipsecChanAggEntry 1 }

   ipsecChanAggCurrentChannels OBJECT-TYPE
       SYNTAX     Gauge32
       MAX-ACCESS read-only
       STATUS     current
       DESCRIPTION
           "The number of channels that are currently active that are of
           the specified type.

           This value should not include channel establishment attempts
           in progress."
       ::= { ipsecChanAggEntry 2 }

   ipsecChanAggTotalChannels OBJECT-TYPE
       SYNTAX     Counter32
       MAX-ACCESS read-only
       STATUS     current
       DESCRIPTION
           "The total number of channels of this type that have been
           created in the entity since boot time.

           This value should not include failed channel establishment
           attempts."
       ::= { ipsecChanAggEntry 3 }

   ipsecChanAggDeletedChannels OBJECT-TYPE
       SYNTAX     Counter32
       MAX-ACCESS read-only
       STATUS     current
       DESCRIPTION
           "The total number of channels of this type that have been
           deleted in the entity since boot time.

           The sum of 'ipsecChanAggCurrentChannels' and this value
           should equal 'ipsecChanAggTotalChannels'."
       ::= { ipsecChanAggEntry 4 }

   ipsecChanAggInboundOctets OBJECT-TYPE
       SYNTAX     Counter64
       UNITS      "bytes"
       MAX-ACCESS read-only
       STATUS     current
       DESCRIPTION
           "The total amount of traffic measured in bytes received by
           all channels of this type. This is the sum of
           'ipsecChannelInboundOctets' from the 'ipsecChannelEntry' of
           each channel in 'ipsecChannelTable' that is of this type."
       ::= { ipsecChanAggEntry 5 }

   ipsecChanAggOutboundOctets OBJECT-TYPE
       SYNTAX     Counter64
       UNITS      "bytes"
       MAX-ACCESS read-only
       STATUS     current
       DESCRIPTION
           "The total amount of traffic measured in bytes sent by all
           channels of this type. This is the sum of
           'ipsecChannelOutboundOctets' from the 'ipsecChannelEntry' of
           each channel in 'ipsecChannelTable' that is of this type."
       ::= { ipsecChanAggEntry 6 }

   ipsecChanAggInboundPackets OBJECT-TYPE
       SYNTAX     Counter64
       MAX-ACCESS read-only
       STATUS     current
       DESCRIPTION
           "The total number of packets received by all channels of this
           type. This is the sum of 'ipsecChannelInboundPackets' from
           the 'ipsecChannelEntry' of each channel in
           'ipsecChannelTable' that is of this type."
       ::= { ipsecChanAggEntry 7 }

   ipsecChanAggOutboundPackets OBJECT-TYPE
       SYNTAX     Counter64
       MAX-ACCESS read-only
       STATUS     current
       DESCRIPTION
           "The total number of packets sent by all channels of this
           type. This is the sum of 'ipsecChannelOutboundPackets' from
           the 'ipsecChannelEntry' of each channel in
           'ipsecChannelTable' that is of this type."
       ::= { ipsecChanAggEntry 8 }

   ipsecChanAggReceiveErrors OBJECT-TYPE
       SYNTAX     Counter32
       MAX-ACCESS read-only
       STATUS     current
       DESCRIPTION
           "The total number of receive errors incurred by all channels
           of this type. This is the sum of 'ipsecChannelReceiveErrors'
           from the 'ipsecChannelEntry' of each channel in
           'ipsecChannelTable' that is of this type."
       ::= { ipsecChanAggEntry 9 }

   ipsecChanAggSendErrors OBJECT-TYPE
       SYNTAX     Counter32
       MAX-ACCESS read-only
       STATUS     current
       DESCRIPTION
           "The total number of send errors incurred by all channels of
           this type. This is the sum of 'ipsecChannelSendErrors' from
           the 'ipsecChannelEntry' of each channel in
           'ipsecChannelTable' that is of this type."
       ::= { ipsecChanAggEntry 10 }

   ipsecChanAggCurrentTunnels OBJECT-TYPE
       SYNTAX     Gauge32
       MAX-ACCESS read-only
       STATUS     current
       DESCRIPTION
           "The current number of active IPsec tunnels that have been
           created by all channels of this type. This is the sum of
           'ipsecChannelCurrentTunnels' from the 'ipsecChannelEntry' of
           each channel in 'ipsecChannelTable' that is of this type."
       ::= { ipsecChanAggEntry 11 }

   ipsecChanAggTotalTunnels OBJECT-TYPE
       SYNTAX     Counter32
       MAX-ACCESS read-only
       STATUS     current
       DESCRIPTION
           "The total number of IPsec tunnels that have been created by
           all channels of this type. This is the sum of
           'ipsecChannelTotalTunnels' from the 'ipsecChannelEntry' of
           each channel in 'ipsecChannelTable' that is of this type."
       ::= { ipsecChanAggEntry 12 }

   ipsecChanAggDeletedTunnels OBJECT-TYPE
       SYNTAX     Counter32
       MAX-ACCESS read-only
       STATUS     current
       DESCRIPTION
           "The total number of IPsec tunnels that have been deleted by
           all channels of this type. This is the sum of
           'ipsecChannelDeletedTunnels' from the 'ipsecChannelEntry' of
           each channel in 'ipsecChannelTable' that is of this type.

           The sum of 'ipsecChanAggCurrentTunnels' and this value should
           equal 'ipsecChanAggTotalTunnels'."
       ::= { ipsecChanAggEntry 13 }

   ipsecChanAggTnlInboundOctets OBJECT-TYPE
       SYNTAX     Counter64
       UNITS      "bytes"
       MAX-ACCESS read-only
       STATUS     current
       DESCRIPTION
           "The amount of traffic measured in bytes received by all
           tunnels created by all channels of this type. This is the sum
           of 'ipsecChannelTunnelInboundOctets' from the
           'ipsecChannelEntry' of each channel in 'ipsecChannelTable'
           that is of this type."
       ::= { ipsecChanAggEntry 14 }

   ipsecChanAggTnlOutboundOctets OBJECT-TYPE
       SYNTAX     Counter64
       UNITS      "bytes"
       MAX-ACCESS read-only
       STATUS     current
       DESCRIPTION
           "The amount of traffic measured in bytes sent by all tunnels
           created by all channels of this type. This is the sum of
           'ipsecChannelTunnelOutboundOctets' from the
           'ipsecChannelEntry' of each channel in 'ipsecChannelTable'
           that is of this type."
       ::= { ipsecChanAggEntry 15 }

   ipsecChanAggTnlInboundPackets OBJECT-TYPE
       SYNTAX     Counter64
       MAX-ACCESS read-only
       STATUS     current
       DESCRIPTION
           "The total number of packets received by all tunnels created
           by all channels of this type. This is the sum of
           'ipsecChannelTunnelInboundPackets' from the
           'ipsecChannelEntry' of each channel in 'ipsecChannelTable'
           that is of this type."
       ::= { ipsecChanAggEntry 16 }

   ipsecChanAggTnlOutboundPackets OBJECT-TYPE
       SYNTAX     Counter64
       MAX-ACCESS read-only
       STATUS     current
       DESCRIPTION
           "The total number of packets sent by all tunnels created by
           all channels of this type. This is the sum of
           'ipsecChannelTunnelOutboundPackets' from the
           'ipsecChannelEntry' of each channel in 'ipsecChannelTable'
           that is of this type."
       ::= { ipsecChanAggEntry 17 }

   ipsecChanAggTnlReceiveErrors OBJECT-TYPE
       SYNTAX     Counter32
       MAX-ACCESS read-only
       STATUS     current
       DESCRIPTION
           "The total number of receive errors incurred in all tunnels
           created by all channels of this type. This is the sum of
           'ipsecChannelTunnelReceiveErrors' from the
           'ipsecChannelEntry' of each channel in 'ipsecChannelTable'
           that is of this type."
       ::= { ipsecChanAggEntry 18 }

   ipsecChanAggTnlSendErrors OBJECT-TYPE
       SYNTAX     Counter32
       MAX-ACCESS read-only
       STATUS     current
       DESCRIPTION
           "The total number of send errors incurred in all tunnels
           created by all channels of this type. This is the sum of
           'ipsecChannelTunnelSendErrors' from the 'ipsecChannelEntry'
           of each channel in 'ipsecChannelTable' that is of this type."
       ::= { ipsecChanAggEntry 19 }


   -- the IPsec Tunnel MIB-Group
   --
   -- a collection of objects providing information about
   -- IPsec SA suite-based virtual tunnels


   ipsecTunnelTable OBJECT-TYPE
       SYNTAX     SEQUENCE OF IpsecTunnelEntry
       MAX-ACCESS not-accessible
       STATUS     current
       DESCRIPTION
           "The (conceptual) table containing information on IPsec SA
           suite-based tunnels.

           The number of rows is, at a minimum, the same as the number
           of IPsec SA suites in the entity that have identical
           selectors. Additional rows for tunnels without active IPsec
           SA suites may also appear in the table.

           The maximum number of rows is implementation dependent."
       ::= { tunnelTables 1 }

   ipsecTunnelEntry OBJECT-TYPE
       SYNTAX     IpsecTunnelEntry
       MAX-ACCESS not-accessible
       STATUS     current
       DESCRIPTION
           "An entry (conceptual row) containing the information on a
           particular tunnel.

           A row in this table cannot be created or deleted by SNMP
           operations on columns of the table."
       INDEX  { ipsecTunnelType, ipsecTunnelId }
       ::= { ipsecTunnelTable 1 }

   IpsecTunnelEntry ::= SEQUENCE {
       ipsecTunnelType                IpsecChanOrTunType,
       ipsecTunnelId                  Unsigned32,

   -- tunnel endpoints
       ipsecTunnelLocalIpAddrType     InetAddressType,
       ipsecTunnelLocalIpAddress      InetAddress,
       ipsecTunnelRemoteIpAddrType    InetAddressType,
       ipsecTunnelRemoteIpAddress     InetAddress,

   -- creator identifiers
       ipsecTunnelRemoteEndpoint      Unsigned32,
       ipsecTunnelLocalEndpoint       Unsigned32,

   -- operational statistics
       ipsecTunnelCurrentSaSuites     Gauge32,
       ipsecTunnelTotalSaSuites       Counter32,
       ipsecTunnelDeletedSaSuites     Counter32,
       ipsecTunnelTimeUpSeconds       Counter32, -- since suites > 0
       ipsecTunnelTimeDownSeconds     Counter32, -- since suites = 0

   -- aggregate statistics
       ipsecTunnelTotalInboundOctets  Counter64,
       ipsecTunnelTotalOutboundOctets Counter64,
       ipsecTunnelTotalInboundPackets Counter64,
       ipsecTunnelTotalOutboundPackets    Counter64,

   -- aggregate error statistics
       ipsecTunnelSendErrors          Counter32,
       ipsecTunnelReceiveErrors       Counter32

   }

   ipsecTunnelType OBJECT-TYPE
       SYNTAX     IpsecChanOrTunType
       MAX-ACCESS not-accessible
       STATUS     current
       DESCRIPTION
           "The type of tunnel represented by this row.
           This is an implementation dependent value, used to assist in
           controlling how tunnels are sorted."
       ::= { ipsecTunnelEntry 1 }

   ipsecTunnelId  OBJECT-TYPE
       SYNTAX     Unsigned32
       MAX-ACCESS not-accessible
       STATUS     current
       DESCRIPTION
           "The index value of the selector table row that contains the
           selectors that are the identity of this tunnel.

           Specifically, this is the value of 'selectorIndex' from the
           appropriate row ('selectorEntry') from the table
           'selectorTable' from the MIB 'ipsecMonModule'.
           (NOTE: Should this be an OBJECT IDENTIFIER instead?)"
       ::= { ipsecTunnelEntry 2 }

   ipsecTunnelLocalIpAddrType OBJECT-TYPE
       SYNTAX     InetAddressType
       MAX-ACCESS read-only
       STATUS     current
       DESCRIPTION
           "The type of address used by the local endpoint of the
           tunnel."
       ::= { ipsecTunnelEntry 3 }

   ipsecTunnelLocalIpAddress  OBJECT-TYPE
       SYNTAX     InetAddress (SIZE(4|16|20))
       MAX-ACCESS read-only
       STATUS     current
       DESCRIPTION
           "The address used by the local endpoint of the tunnel."
       ::= { ipsecTunnelEntry 4 }

   ipsecTunnelRemoteIpAddrType    OBJECT-TYPE
       SYNTAX     InetAddressType
       MAX-ACCESS read-only
       STATUS     current
       DESCRIPTION
           "The type of address used by the remote endpoint of the
           tunnel."
       ::= { ipsecTunnelEntry 5 }

   ipsecTunnelRemoteIpAddress OBJECT-TYPE
       SYNTAX     InetAddress (SIZE(4|16|20))
       MAX-ACCESS read-only
       STATUS     current
       DESCRIPTION
           "The address used by the remote endpoint of the tunnel."
       ::= { ipsecTunnelEntry 6 }

   ipsecTunnelLocalEndpoint   OBJECT-TYPE
       SYNTAX     Unsigned32
       MAX-ACCESS read-only
       STATUS     current
       DESCRIPTION
           "The index of the local endpoint that negotiated this tunnel.

           It is the value of 'endpointIndex' from the correct row
           ('IkeEndpointEntry') of the 'ikeEndpointTable' from
           'ikeMonModule'.
           (NOTE: Should this be an OBJECT IDENTIFIER instead?)"
       ::= { ipsecTunnelEntry 7 }

   ipsecTunnelRemoteEndpoint  OBJECT-TYPE
       SYNTAX     Unsigned32
       MAX-ACCESS read-only
       STATUS     current
       DESCRIPTION
           "The index of the remote endpoint that negotiated this
           tunnel.

           It is the value of 'endpointIndex' from the correct row
           ('IkeEndpointEntry') of the 'ikeEndpointTable' from
           'ikeMonModule'."
       ::= { ipsecTunnelEntry 8 }

   ipsecTunnelCurrentSaSuites OBJECT-TYPE
       SYNTAX     Gauge32
       MAX-ACCESS read-only
       STATUS     current
       DESCRIPTION
           "The number of phase 2 SA suites that are currently active
           that make up this tunnel.

           This value may be 0 if the tunnel has not yet been set up, or
           the implementation does not require the existence of phase 2
           SA suites for the tunnel to exist, or if the tunnel is
           considered a permanent entry in the table by the
           implementation.

           This value should not include phase 2 SA suite establishment
           attempts in progress."
       ::= { ipsecTunnelEntry 9 }

   ipsecTunnelTotalSaSuites OBJECT-TYPE
       SYNTAX     Counter32
       MAX-ACCESS read-only
       STATUS     current
       DESCRIPTION
           "The total number of phase 2 SA suites that are part of this
           tunnel that have been created in the entity since boot time.

           This value should not include failed phase 2 SA suite
           establishment attempts."
       ::= { ipsecTunnelEntry 10 }

   ipsecTunnelDeletedSaSuites OBJECT-TYPE
       SYNTAX     Counter32
       MAX-ACCESS read-only
       STATUS     current
       DESCRIPTION
           "The total number of phase 2 SA suites that are part of this
           channel that have been deleted in the entity since boot time.

           The sum of 'ipsecTunnelCurrentSaSuites' and this value should
           equal 'ipsecTunnelTotalSaSuites'."
       ::= { ipsecTunnelEntry 11 }

   ipsecTunnelTimeUpSeconds OBJECT-TYPE
       SYNTAX     Counter32
       UNITS      "seconds"
       MAX-ACCESS read-only
       STATUS     current
       DESCRIPTION
           "The total number of seconds since there has been at least
           one valid phase 2 SA suite supporting the channel. In other
           words, the number of seconds since the value of
           'ipsecTunnelCurrentSaSuites' changed from 0 to any other
           value."
       ::= { ipsecTunnelEntry 12 }

   ipsecTunnelTimeDownSeconds OBJECT-TYPE
       SYNTAX     Counter32
       UNITS      "seconds"
       MAX-ACCESS read-only
       STATUS     current
       DESCRIPTION
           "The total number of seconds since the last valid phase 2 SA
           suite supporting the channel was deleted. In other words, the
           number of seconds since the value of
           'ipsecTunnelCurrentSaSuites' changed to 0 from any other
           value."
       ::= { ipsecTunnelEntry 13 }

   ipsecTunnelTotalInboundOctets OBJECT-TYPE
       SYNTAX     Counter64
       UNITS      "bytes"
       MAX-ACCESS read-only
       STATUS     current
       DESCRIPTION
           "The total amount of traffic measured in bytes received by
           the tunnel. This is the sum of 'suiteInUserOctets' from the
           'suiteEntry' of each phase 2 SA suite in 'suiteTable' that is
           part of this tunnel."
       ::= { ipsecTunnelEntry 14 }

   ipsecTunnelTotalOutboundOctets OBJECT-TYPE
       SYNTAX     Counter64
       UNITS      "bytes"
       MAX-ACCESS read-only
       STATUS     current
       DESCRIPTION
           "The total amount of traffic measured in bytes sent by the
           tunnel. This is the sum of 'suiteOutUserOctets' from the
           'suiteEntry' of each phase 2 SA suite in 'suiteTable' that is
           part of this tunnel."
       ::= { ipsecTunnelEntry 15 }

   ipsecTunnelTotalInboundPackets OBJECT-TYPE
       SYNTAX     Counter64
       MAX-ACCESS read-only
       STATUS     current
       DESCRIPTION
           "The total number of packets received by the tunnel. This is
           the sum of 'suiteInPackets' from the 'suiteEntry' of each
           phase 2 SA suite in 'suiteTable' that is part of this
           tunnel."
       ::= { ipsecTunnelEntry 16 }

   ipsecTunnelTotalOutboundPackets OBJECT-TYPE
       SYNTAX     Counter64
       MAX-ACCESS read-only
       STATUS     current
       DESCRIPTION
           "The total number of packets sent by the tunnel. This is the
           sum of 'suiteOutPackets' from the 'suiteEntry' of each phase
           2 SA suite in 'suiteTable' that is part of this tunnel."
       ::= { ipsecTunnelEntry 17 }

   ipsecTunnelSendErrors OBJECT-TYPE
       SYNTAX     Counter32
       MAX-ACCESS read-only
       STATUS     current
       DESCRIPTION
           "The total number of send errors in the tunnel. This is the
           sum of 'suiteSendErrors' from the 'suiteEntry' of each phase
           2 SA suite in 'suiteTable' that is part of this tunnel."
       ::= { ipsecTunnelEntry 18 }

   ipsecTunnelReceiveErrors OBJECT-TYPE
       SYNTAX     Counter32
       MAX-ACCESS read-only
       STATUS     current
       DESCRIPTION
           "The total number of receive errors in the tunnel. This is
           the sum of 'suiteReceiveErrors' from the 'suiteEntry' of each
           phase 2 SA suite in 'suiteTable' that is part of this
           tunnel."
       ::= { ipsecTunnelEntry 19 }


   -- the IPsec SA Suite MIB-Group
   --
   -- a collection of objects providing information about
   -- IPsec SA suites used in virtual tunnels


   ipsecTunnelSuiteTable OBJECT-TYPE
       SYNTAX     SEQUENCE OF IpsecTunnelSuiteEntry
       MAX-ACCESS not-accessible
       STATUS     current
       DESCRIPTION
           "The (conceptual) table containing information on IPsec SA
           suites.

           The number of rows is the same as the number of IPsec SA
           suites in the entity.

           The maximum number of rows is implementation dependent."
       ::= { tunnelTables 2 }

   ipsecTunnelSuiteEntry OBJECT-TYPE
       SYNTAX     IpsecTunnelSuiteEntry
       MAX-ACCESS not-accessible
       STATUS     current
       DESCRIPTION
           "An entry (conceptual row) containing the identifiers to a
           particular SA suite.

           A row in this table cannot be created or deleted by SNMP
           operations on columns of the table."

       INDEX  {
                   ipsecTunnelType,
                   ipsecTunnelId,
                   ipsecTunnelSuiteIndex
               }
       ::= { ipsecTunnelSuiteTable 1 }

   IpsecTunnelSuiteEntry ::= SEQUENCE {

   -- additional index
       ipsecTunnelSuiteIndex      Unsigned32,

   -- identifier of suite
       ipsecTunnelSuiteReference  OBJECT IDENTIFIER
   }

   ipsecTunnelSuiteIndex  OBJECT-TYPE
       SYNTAX     Unsigned32 (1..16777215)
       MAX-ACCESS not-accessible
       STATUS     current
       DESCRIPTION
           "A unique value, greater than zero, for each SA suite in the
           tunnel. It is recommended that values are assigned
           contiguously starting from 1."
       ::= { ipsecTunnelSuiteEntry 1 }

   ipsecTunnelSuiteReference  OBJECT-TYPE
       SYNTAX     OBJECT IDENTIFIER
       MAX-ACCESS read-only
       STATUS     current
       DESCRIPTION
           "The object identifier of the IPsec SA suite row that
           represents the IPsec SA suite in the tunnel.

           Specifically, the value of this object is the object
           identifier of 'suiteIndex' of the appropriate row
           ('SuiteEntry') in 'suiteTable' from 'ikeMonModule'."
       ::= { ipsecTunnelSuiteEntry 2 }



   -- the IPsec tunnel aggregates table
   --
   -- a table providing aggregate statistics for the user-defined
   -- tunnel types


   ipsecTunAggTable OBJECT-TYPE
       SYNTAX     SEQUENCE OF IpsecTunAggEntry
       MAX-ACCESS not-accessible
       STATUS     current
       DESCRIPTION
           "The optional (conceptual) table containing information on
           aggregate statistics for the tunnel types.

           The number of rows is the same as the number of tunnel types
           supported by the entity.

           The maximum number of rows is implementation dependent."
       ::= { tunnelTables 3 }

   ipsecTunAggEntry OBJECT-TYPE
       SYNTAX     IpsecTunAggEntry
       MAX-ACCESS not-accessible
       STATUS     current
       DESCRIPTION
           "An entry (conceptual row) containing the aggregate
           statistics for a specific tunnel type.

           A row in this table cannot be created or deleted by SNMP
           operations on columns of the table."
       INDEX  { ipsecTunnelType }
       ::= { ipsecTunAggTable 1 }

   IpsecTunAggEntry ::= SEQUENCE {

   -- tunnel counts of this type
       ipsecTunAggCurrentTunnels      Gauge32,
       ipsecTunAggTotalTunnels        Counter32,
       ipsecTunAggDeletedTunnels      Counter32,

   -- aggregate statistics
       ipsecTunAggInboundOctets       Counter64,
       ipsecTunAggOutboundOctets      Counter64,
       ipsecTunAggInboundPackets      Counter64,
       ipsecTunAggOutboundPackets     Counter64,

   -- aggregate error statistics
       ipsecTunAggSendErrors          Counter32,
       ipsecTunAggReceiveErrors       Counter32
   }


   ipsecTunAggCurrentTunnels OBJECT-TYPE
       SYNTAX     Gauge32
       MAX-ACCESS read-only
       STATUS     current
       DESCRIPTION
           "The number of tunnels that are currently active that are of
           the specified type.

           This value should not include tunnel establishment attempts
           in progress."
       ::= { ipsecTunAggEntry 1 }

   ipsecTunAggTotalTunnels OBJECT-TYPE
       SYNTAX     Counter32
       MAX-ACCESS read-only
       STATUS     current
       DESCRIPTION
           "The total number of tunnels of this type that have been
           created in the entity since boot time.

           This value should not include failed tunnel establishment
           attempts."
       ::= { ipsecTunAggEntry 2 }

   ipsecTunAggDeletedTunnels OBJECT-TYPE
       SYNTAX     Counter32
       MAX-ACCESS read-only
       STATUS     current
       DESCRIPTION
           "The total number of tunnels of this type that have been
           deleted in the entity since boot time.

           The sum of 'ipsecTunAggCurrentTunnels' and this value should
           equal 'ipsecTunAggTotalTunnels'."
       ::= { ipsecTunAggEntry 3 }

   ipsecTunAggInboundOctets OBJECT-TYPE
       SYNTAX     Counter64
       UNITS      "bytes"
       MAX-ACCESS read-only
       STATUS     current
       DESCRIPTION
           "The total amount of traffic measured in bytes received by
           all tunnels of this type. This is the sum of
           'ipsecTunnelInboundOctets' from the 'ipsecTunnelEntry' of
           each tunnel in 'ipsecTunnelTable' that is of this type."
       ::= { ipsecTunAggEntry 4 }

   ipsecTunAggOutboundOctets OBJECT-TYPE
       SYNTAX     Counter64
       UNITS      "bytes"
       MAX-ACCESS read-only
       STATUS     current
       DESCRIPTION
           "The total amount of traffic measured in bytes sent by all
           tunnels of this type. This is the sum of
           'ipsecTunnelOutboundOctets' from the 'ipsecTunnelEntry' of
           each tunnel in 'ipsecTunnelTable' that is of this type."
       ::= { ipsecTunAggEntry 5 }

   ipsecTunAggInboundPackets OBJECT-TYPE
       SYNTAX     Counter64
       MAX-ACCESS read-only
       STATUS     current
       DESCRIPTION
           "The total number of packets received by all tunnels of this
           type. This is the sum of 'ipsecTunnelInboundPackets' from the
           'ipsecTunnelEntry' of each tunnel in 'ipsecTunnelTable' that
           is of this type."
       ::= { ipsecTunAggEntry 6 }

   ipsecTunAggOutboundPackets OBJECT-TYPE
       SYNTAX     Counter64
       MAX-ACCESS read-only
       STATUS     current
       DESCRIPTION
           "The total number of packets sent by all tunnels of this
           type. This is the sum of 'ipsecTunnelOutboundPackets' from
           the 'ipsecTunnelEntry' of each tunnel in 'ipsecTunnelTable'
           that is of this type."
       ::= { ipsecTunAggEntry 7 }

   ipsecTunAggSendErrors OBJECT-TYPE
       SYNTAX     Counter32
       MAX-ACCESS read-only
       STATUS     current
       DESCRIPTION
           "The total number of send errors incurred by all tunnels of
           this type. This is the sum of 'ipsecTunnelSendErrors' from
           the 'ipsecTunnelEntry' of each tunnel in 'ipsecTunnelTable'
           that is of this type."
       ::= { ipsecTunAggEntry 8 }

   ipsecTunAggReceiveErrors OBJECT-TYPE
       SYNTAX     Counter32
       MAX-ACCESS read-only
       STATUS     current
       DESCRIPTION
           "The total number of receive errors incurred by all tunnels
           of this type. This is the sum of 'ipsecTunnelReceiveErrors'
           from the 'ipsecTunnelEntry' of each tunnel in
           'ipsecTunnelTable' that is of this type."
       ::= { ipsecTunAggEntry 9 }



   --
   -- table to find tunnels based on the tunnel identifiers
   --

   tunnelBySelectorsTable OBJECT-TYPE
       SYNTAX     SEQUENCE OF TunnelBySelectorsEntry
       MAX-ACCESS not-accessible
       STATUS     current
       DESCRIPTION
           "The (conceptual) table that sorts the tunnels by the
           selectors.

           The number of rows in this table is the same as the number of
           tunnels in the entity."
       ::= { tunnelTables 4 }

   tunnelBySelectorsEntry OBJECT-TYPE
       SYNTAX     TunnelBySelectorsEntry
       MAX-ACCESS not-accessible
       STATUS     current
       DESCRIPTION
           "An entry (conceptual row) referencing a particular tunnel.

           A row in this table cannot be created or deleted by SNMP
           operations on columns of the table."
       INDEX  {
                   tunnelBySelectorsHash,
                   tunnelBySelectorsIndex
               }
       ::= { tunnelBySelectorsTable 1 }

   TunnelBySelectorsEntry ::= SEQUENCE {
   -- index
       tunnelBySelectorsHash          OCTET STRING,
       tunnelBySelectorsIndex         Unsigned32,

   -- real tunnel identifiers
       tunnelBySelectorsId            Unsigned32,

   -- tunnel reference
       tunnelBySelectorsType          IpsecChanOrTunType,
       tunnelBySelectorsRef           OBJECT IDENTIFIER
   }

   tunnelBySelectorsHash  OBJECT-TYPE
       SYNTAX     OCTET STRING (SIZE(4))
       MAX-ACCESS not-accessible
       STATUS     current
       DESCRIPTION
           "The hash result of the full identifer of the tunnel. Precise
           definition to be completed."
       ::= { tunnelBySelectorsEntry 1 }

   tunnelBySelectorsIndex OBJECT-TYPE
       SYNTAX     Unsigned32 (1..16777215)
       MAX-ACCESS not-accessible
       STATUS     current
       DESCRIPTION
           "A unique value, greater than zero, for each tunnel in the
           table where the hash results of the tunnel identifiers
           collide. It is recommended that values are assigned
           contiguously starting from 1."
       ::= { tunnelBySelectorsEntry 2 }

   tunnelBySelectorsId OBJECT-TYPE
       SYNTAX     Unsigned32
       MAX-ACCESS read-only
       STATUS     current
       DESCRIPTION
           "The identifier of the tunnel.

           The value of this object is the index of the selector
           ('selectorIndex') row ('SelectorEntry') from the
           'selectorTable' that identifies this tunnel."
       ::= { tunnelBySelectorsEntry 3 }

   tunnelBySelectorsType  OBJECT-TYPE
       SYNTAX     IpsecChanOrTunType
       MAX-ACCESS read-only
       STATUS     current
       DESCRIPTION
           "The type assigned to the tunnel for which this row refers."
       ::= { tunnelBySelectorsEntry 4 }

   tunnelBySelectorsRef   OBJECT-TYPE
       SYNTAX     OBJECT IDENTIFIER
       MAX-ACCESS read-only
       STATUS     current
       DESCRIPTION
           "The object identifier of 'tunnelIndex' in the row
           ('tunnelEntry') of the 'tunnelTable' to which this row
           refers."
       ::= { tunnelBySelectorsEntry 5 }



   --
   -- trap parameters, traps and control
   --

   channelTrapLocalEndpoint OBJECT-TYPE
       SYNTAX     Unsigned32
       MAX-ACCESS accessible-for-notify
       STATUS     current
       DESCRIPTION
           "The index to an endpoint that is the local endpoint of a
           channel in a trap."
       ::= { channelTrapObjects 1 }

   channelTrapRemoteEndpoint OBJECT-TYPE
       SYNTAX     Unsigned32
       MAX-ACCESS accessible-for-notify
       STATUS     current
       DESCRIPTION
           "The index to an endpoint that is the remote endpoint of a
           channel in a trap."
       ::= { channelTrapObjects 2 }

   tunnelTrapIdentifier OBJECT-TYPE
       SYNTAX     Unsigned32
       MAX-ACCESS accessible-for-notify
       STATUS     current
       DESCRIPTION
           "The index to a selector that is the identifier of a tunnel
           in a trap."
       ::= { tunnelTrapObjects 1 }


   channelUpTrapEnable OBJECT-TYPE
       SYNTAX     TruthValue
       MAX-ACCESS read-write
       STATUS     current
       DESCRIPTION
           "Indicates whether channelUp traps should be generated."
       DEFVAL { false }
       ::= { channelTrapControl 1 }

   channelDownTrapEnable OBJECT-TYPE
       SYNTAX     TruthValue
       MAX-ACCESS read-write
       STATUS     current
       DESCRIPTION
           "Indicates whether channelDown traps should be generated."
       DEFVAL { false }
       ::= { channelTrapControl 2 }

   channelUp NOTIFICATION-TYPE
       OBJECTS
       {
           channelTrapLocalEndpoint,
           channelTrapRemoteEndpoint
       }
       STATUS current
       DESCRIPTION
           "The specified channel is now up. (In other words, the number
           of current IKE SAs supporting the channel has changed from
           zero to a non-zero value.)"
       ::= { channelTraps 1 }

   channelDown NOTIFICATION-TYPE
       OBJECTS
       {
           channelTrapLocalEndpoint,
           channelTrapRemoteEndpoint
       }
       STATUS current
       DESCRIPTION
           "The specified channel is now down. (In other words, the
           number of current IKE SAs supporting the channel has changed
           to zero from a non-zero value.)"
       ::= { channelTraps 2 }

   tunnelUpTrapEnable OBJECT-TYPE
       SYNTAX     TruthValue
       MAX-ACCESS read-write
       STATUS     current
       DESCRIPTION
           "Indicates whether tunnelUp traps should be generated."
       DEFVAL { false }
       ::= { tunnelTrapControl 1 }

   tunnelDownTrapEnable OBJECT-TYPE
       SYNTAX     TruthValue
       MAX-ACCESS read-write
       STATUS     current
       DESCRIPTION
           "Indicates whether tunnelDown traps should be generated."
       DEFVAL { false }
       ::= { tunnelTrapControl 2 }

   tunnelUp NOTIFICATION-TYPE
       OBJECTS
       {
           tunnelTrapIdentifier
       }
       STATUS current
       DESCRIPTION
           "The specified tunnel is now up. (In other words, the number
           of current phase 2 SA suites supporting the tunnel has
           changed from zero to a non-zero value.)"
       ::= { tunnelTraps 1 }

   tunnelDown NOTIFICATION-TYPE
       OBJECTS
       {
           tunnelTrapIdentifier
       }
       STATUS current
       DESCRIPTION
           "The specified tunnel is now down. (In other words, the
           number of current phase 2 SA suites supporting the tunnel has
           changed to zero from a non-zero value.)"
       ::= { tunnelTraps 2 }


   END
