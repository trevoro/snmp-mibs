------------------------------------------------------------
-- $Workfile:   pgmibhd.my  $
--   pg common header mid
-- $Archive:   S:\dslam\swdev\snmp14.2.1.16\mibs\common\pgmibhd.myv  $
-- $Revision:   1.19  $
-- $Date:   Jun 28 2000 18:00:18  $
-- $Author:   SAMUELE  $
------------------------------------------------------------

-- Copyright 1998 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.


PAIRGAIN-COMMON-HD-MIB DEFINITIONS ::= BEGIN

-- SECTION 1: Top Level Definitions


-- Imports

IMPORTS
        enterprises                     FROM RFC1155-SMI;


 -- Categories

pairgain                        OBJECT IDENTIFIER ::=   { enterprises 927 }

products                        OBJECT IDENTIFIER ::=   { pairgain 1 }
temporary                       OBJECT IDENTIFIER ::=   { pairgain 2 }
registration                    OBJECT IDENTIFIER ::=   { pairgain 3 }

-- Groups

pgainOHdsl                      OBJECT IDENTIFIER ::=   { products 1}
pgainAgent                      OBJECT IDENTIFIER ::=   { products 2 }
pgainCampus                     OBJECT IDENTIFIER ::=   { products 3 }
pgainHigain                     OBJECT IDENTIFIER ::=   { products 4 }
pgainREX                        OBJECT IDENTIFIER ::=   { products 5 }
pgainETSI                       OBJECT IDENTIFIER ::=   { products 6 }
pgainHDSL                       OBJECT IDENTIFIER ::=   { products 7 }
pgainEPhone                     OBJECT IDENTIFIER ::=   { products 8 }
pgainDSLAM                      OBJECT IDENTIFIER ::=   { products 9 }
pgainSysLog                     OBJECT IDENTIFIER ::=   { products 10 }
pgainTiger                      OBJECT IDENTIFIER ::=   { products 11 }
pgainADSL                       OBJECT IDENTIFIER ::=   { products 12 }
pgainSDSL						OBJECT IDENTIFIER ::=   { products 13 }
pgainSDSLCell					OBJECT IDENTIFIER ::=   { products 14 }
pgCampusChassis                 OBJECT IDENTIFIER ::=   { pgainCampus 1 }
pgCampusCmu                     OBJECT IDENTIFIER ::=   { pgainCampus 2 }
pgCampusLocLu                   OBJECT IDENTIFIER ::=   { pgainCampus 3 }
pgCampusRemUnit                 OBJECT IDENTIFIER ::=   { pgainCampus 4 }
pgCampusDoubler1                OBJECT IDENTIFIER ::=   { pgainCampus 5 }
pgCampusDoubler2                OBJECT IDENTIFIER ::=   { pgainCampus 6 }
pgHigainChassis                 OBJECT IDENTIFIER ::=   { pgainHigain 1 }
pgETSIChassis                   OBJECT IDENTIFIER ::=   { pgainETSI 1 }
pgEPhoneChassis                 OBJECT IDENTIFIER ::=   { pgainEPhone 1 }
pgEPhoneLocUnit                 OBJECT IDENTIFIER ::=   { pgainEPhone 2 }
pgEPhoneRemUnit                 OBJECT IDENTIFIER ::=   { pgainEPhone 3 }
pgDSLAMChassis                  OBJECT IDENTIFIER ::=   { pgainDSLAM 1 }
pgLantMIB		    			OBJECT IDENTIFIER ::=   { pgainDSLAM 2 }
pgDSLAMAlarmSeverity        	OBJECT IDENTIFIER ::=   { pgainDSLAM 3 }
pgDSLAMAlarm                	OBJECT IDENTIFIER ::=   { pgainDSLAM 4 }
pgDSLAMFlashMIB					OBJECT IDENTIFIER ::=	{ pgainDSLAM 5 }
pgService                   	OBJECT IDENTIFIER ::=   { pgainDSLAM 6 }
pgIpoaRouteMIB              	OBJECT IDENTIFIER ::=   { pgainDSLAM 7 }
pgsessionMIB            		OBJECT IDENTIFIER ::=   { pgainDSLAM 8 }
pgATMTestMIB					OBJECT IDENTIFIER ::=   { pgainDSLAM 9 }
pgIpAccessMIB					OBJECT IDENTIFIER ::=   { pgainDSLAM 10 }
pgUpcMIB						OBJECT IDENTIFIER ::=   { pgainDSLAM 11 }
pgApsMIB					   	OBJECT IDENTIFIER ::=   { pgainDSLAM 12 }
pgIISPMIB						OBJECT IDENTIFIER ::=	{ pgainDSLAM 13 }
avSubtendMIB					OBJECT IDENTIFIER ::=   { pgainDSLAM 14 }
pgAtmTcMIB					   	OBJECT IDENTIFIER ::=   { pgainDSLAM 16 }
pgds1Mib						OBJECT IDENTIFIER ::=   { pgainDSLAM 17 }
pgBackupMIB                     OBJECT IDENTIFIER ::=   { pgainDSLAM 19 }
pgTigerMIB                  	OBJECT IDENTIFIER ::=   { pgainTiger 1 }

-- Products
-- These object identifiers are for use as values for sysObjectId.

pgreg-other                     OBJECT IDENTIFIER ::=   { registration 1 }
pgreg-campus                    OBJECT IDENTIFIER ::=   { registration 2 }
pgreg-Cmu                       OBJECT IDENTIFIER ::=   { pgreg-campus 1 }
pgreg-higain                    OBJECT IDENTIFIER ::=   { registration 3 }
pgreg-Hmu                       OBJECT IDENTIFIER ::=   { pgreg-higain 1 }
pgreg-ebridge                   OBJECT IDENTIFIER ::=   { registration 4 }
pgreg-EBM                       OBJECT IDENTIFIER ::=   { pgreg-ebridge 1 }
pgreg-ETSI                      OBJECT IDENTIFIER ::=   { registration 5}
pgreg-Emu                       OBJECT IDENTIFIER ::=   { pgreg-ETSI 1}
pgreg-EPhone                    OBJECT IDENTIFIER ::=   { registration 6 }
pgreg-EPmu                      OBJECT IDENTIFIER ::=   { pgreg-EPhone 1 }
pgreg-DSLAM                     OBJECT IDENTIFIER ::=   { registration 7}
pgreg-Tiger                     OBJECT IDENTIFIER ::=   { registration 8}
pgAvidia8000                    OBJECT IDENTIFIER ::=   { pgreg-DSLAM 1 }
pgAvidia3000                    OBJECT IDENTIFIER ::=   { pgreg-DSLAM 2 }
pgAvidia2200                    OBJECT IDENTIFIER ::=   { pgreg-DSLAM 3 }

END
