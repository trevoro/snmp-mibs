Nortel-Magellan-Passport-DisdnTS014MIB
DEFINITIONS ::= BEGIN



IMPORTS

      OBJECT-TYPE
   FROM RFC-1212

      passportMIBs
   FROM Nortel-Magellan-Passport-UsefulDefinitionsMIB

      DisplayString,
      StorageType,
      RowStatus,
      Unsigned32
   FROM Nortel-Magellan-Passport-StandardTextualConventionsMIB

      NonReplicated,
      Link
   FROM Nortel-Magellan-Passport-TextualConventionsMIB

      dataSigChanIndex,
      dataSigChan
   FROM Nortel-Magellan-Passport-DataIsdnMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DisdnTS014 Enterprise MIB."

disdnTS014MIB OBJECT IDENTIFIER ::= { passportMIBs 114 }










-- DataSigChan/n TS014
-- The TS014 component defines the operational characteristics of the 
-- signalling channel's connection to the external equipment.

dataSigChanTS014 OBJECT IDENTIFIER ::= { dataSigChan 9 }



dataSigChanTS014RowStatusTable OBJECT-TYPE
   SYNTAX     SEQUENCE OF DataSigChanTS014RowStatusEntry
   ACCESS     not-accessible
   STATUS     mandatory
   DESCRIPTION
     "This entry controls the addition and deletion of 
      dataSigChanTS014 components."
::= { dataSigChanTS014 1 }

dataSigChanTS014RowStatusEntry OBJECT-TYPE
   SYNTAX     DataSigChanTS014RowStatusEntry
   ACCESS     not-accessible
   STATUS     mandatory
   DESCRIPTION
     "A single entry in the table represents a single 
      dataSigChanTS014 component."
   INDEX {
      dataSigChanIndex,
      dataSigChanTS014Index }
::= { dataSigChanTS014RowStatusTable 1 }

DataSigChanTS014RowStatusEntry ::= SEQUENCE {
   dataSigChanTS014RowStatus
      RowStatus,
   dataSigChanTS014ComponentName
      DisplayString,
   dataSigChanTS014StorageType
      StorageType,
   dataSigChanTS014Index
      NonReplicated }

dataSigChanTS014RowStatus OBJECT-TYPE
   SYNTAX     RowStatus 
   ACCESS     read-write
   STATUS     mandatory
   DESCRIPTION
     "This variable is used as the basis for SNMP naming of
      dataSigChanTS014 components.
      These components can be added and deleted."
::= { dataSigChanTS014RowStatusEntry 1 }

dataSigChanTS014ComponentName OBJECT-TYPE
   SYNTAX     DisplayString 
   ACCESS     read-only
   STATUS     mandatory
   DESCRIPTION
     "This variable provides the component's string name for
      use with the ASCII Console Interface"
::= { dataSigChanTS014RowStatusEntry 2 }

dataSigChanTS014StorageType OBJECT-TYPE
   SYNTAX     StorageType 
   ACCESS     read-only
   STATUS     mandatory
   DESCRIPTION
     "This variable represents the storage type value for the
      dataSigChanTS014 tables."
::= { dataSigChanTS014RowStatusEntry 4 }

dataSigChanTS014Index OBJECT-TYPE
   SYNTAX     NonReplicated 
   ACCESS     not-accessible
   STATUS     mandatory
   DESCRIPTION
     "This variable represents the index for the dataSigChanTS014 tables."
::= { dataSigChanTS014RowStatusEntry 10 }

dataSigChanTS014L2Table OBJECT-TYPE
   SYNTAX     SEQUENCE OF DataSigChanTS014L2Entry
   ACCESS     not-accessible
   STATUS     mandatory
   DESCRIPTION
     "This group represents the provisionable Layer 2 attributes of the 
      Q931 CCITT protocol."
::= { dataSigChanTS014 11 }

dataSigChanTS014L2Entry OBJECT-TYPE
   SYNTAX     DataSigChanTS014L2Entry
   ACCESS     not-accessible
   STATUS     mandatory
   DESCRIPTION
     "An entry in the dataSigChanTS014L2Table."
   INDEX {
      dataSigChanIndex,
      dataSigChanTS014Index }
::= { dataSigChanTS014L2Table 1 }

DataSigChanTS014L2Entry ::= SEQUENCE {
   dataSigChanTS014T23
      Unsigned32,
   dataSigChanTS014T200
      Unsigned32,
   dataSigChanTS014N200
      Unsigned32,
   dataSigChanTS014T203
      Unsigned32,
   dataSigChanTS014N201
      Unsigned32,
   dataSigChanTS014CircuitSwitchedK
      Unsigned32 }

dataSigChanTS014T23 OBJECT-TYPE
   SYNTAX     Unsigned32 (1..15)
   ACCESS     read-write
   STATUS     mandatory
   DESCRIPTION
     "This attribute specifies the layer2 enable request timer."
   DEFVAL     { 10 }
::= { dataSigChanTS014L2Entry 1 }

dataSigChanTS014T200 OBJECT-TYPE
   SYNTAX     Unsigned32 (1..20)
   ACCESS     read-write
   STATUS     mandatory
   DESCRIPTION
     "This attribute specifies the maximum time between a layer 2 frame 
      and its acknowledgement"
   DEFVAL     { 2 }
::= { dataSigChanTS014L2Entry 2 }

dataSigChanTS014N200 OBJECT-TYPE
   SYNTAX     Unsigned32 (1..8)
   ACCESS     read-write
   STATUS     mandatory
   DESCRIPTION
     "This attribute specifies the maximum number of re-transmissions of 
      a layer2 frame."
   DEFVAL     { 3 }
::= { dataSigChanTS014L2Entry 3 }

dataSigChanTS014T203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { dataSigChanTS014L2Entry 4 }

dataSigChanTS014N201 OBJECT-TYPE
   SYNTAX     Unsigned32 (4..260)
   ACCESS     read-write
   STATUS     mandatory
   DESCRIPTION
     "This attribute specifies the maximum number of octets in an 
      information field."
   DEFVAL     { 260 }
::= { dataSigChanTS014L2Entry 5 }

dataSigChanTS014CircuitSwitchedK OBJECT-TYPE
   SYNTAX     Unsigned32 (1..632)
   ACCESS     read-write
   STATUS     mandatory
   DESCRIPTION
     "This attribute specifies the maximum number of frames for B 
      channel use."
   DEFVAL     { 7 }
::= { dataSigChanTS014L2Entry 6 }

dataSigChanTS014ProvTable OBJECT-TYPE
   SYNTAX     SEQUENCE OF DataSigChanTS014ProvEntry
   ACCESS     not-accessible
   STATUS     mandatory
   DESCRIPTION
     "This group defines the general options of the d-channel signalling 
      link."
::= { dataSigChanTS014 13 }

dataSigChanTS014ProvEntry OBJECT-TYPE
   SYNTAX     DataSigChanTS014ProvEntry
   ACCESS     not-accessible
   STATUS     mandatory
   DESCRIPTION
     "An entry in the dataSigChanTS014ProvTable."
   INDEX {
      dataSigChanIndex,
      dataSigChanTS014Index }
::= { dataSigChanTS014ProvTable 1 }

DataSigChanTS014ProvEntry ::= SEQUENCE {
   dataSigChanTS014Side
      INTEGER }

dataSigChanTS014Side OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { dataSigChanTS014ProvEntry 1 }

dataSigChanTS014OperTable OBJECT-TYPE
   SYNTAX     SEQUENCE OF DataSigChanTS014OperEntry
   ACCESS     not-accessible
   STATUS     mandatory
   DESCRIPTION
     "This group provides the operational attributes for the signalling 
      protocol."
::= { dataSigChanTS014 15 }

dataSigChanTS014OperEntry OBJECT-TYPE
   SYNTAX     DataSigChanTS014OperEntry
   ACCESS     not-accessible
   STATUS     mandatory
   DESCRIPTION
     "An entry in the dataSigChanTS014OperTable."
   INDEX {
      dataSigChanIndex,
      dataSigChanTS014Index }
::= { dataSigChanTS014OperTable 1 }

DataSigChanTS014OperEntry ::= SEQUENCE {
   dataSigChanTS014ActiveChannels
      Unsigned32,
   dataSigChanTS014PeakActiveChannels
      Unsigned32,
   dataSigChanTS014DChanStatus
      INTEGER }

dataSigChanTS014ActiveChannels OBJECT-TYPE
   SYNTAX     Unsigned32 (0..128)
   ACCESS     read-only
   STATUS     mandatory
   DESCRIPTION
     "This attribute indicates the number of currently active channels. 
      This includes data and voice channels."
   DEFVAL     { 0 }
::= { dataSigChanTS014OperEntry 1 }

dataSigChanTS014PeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { dataSigChanTS014OperEntry 4 }

dataSigChanTS014DChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { dataSigChanTS014OperEntry 7 }

dataSigChanTS014ToolsTable OBJECT-TYPE
   SYNTAX     SEQUENCE OF DataSigChanTS014ToolsEntry
   ACCESS     not-accessible
   STATUS     mandatory
   DESCRIPTION
     "This group contains a series of operational attributes which turn on 
      and off several kinds of tracing."
::= { dataSigChanTS014 16 }

dataSigChanTS014ToolsEntry OBJECT-TYPE
   SYNTAX     DataSigChanTS014ToolsEntry
   ACCESS     not-accessible
   STATUS     mandatory
   DESCRIPTION
     "An entry in the dataSigChanTS014ToolsTable."
   INDEX {
      dataSigChanIndex,
      dataSigChanTS014Index }
::= { dataSigChanTS014ToolsTable 1 }

DataSigChanTS014ToolsEntry ::= SEQUENCE {
   dataSigChanTS014Tracing
      OCTET STRING }

dataSigChanTS014Tracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { dataSigChanTS014ToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

dataSigChanTS014Framer OBJECT IDENTIFIER ::= { dataSigChanTS014 2 }



dataSigChanTS014FramerRowStatusTable OBJECT-TYPE
   SYNTAX     SEQUENCE OF DataSigChanTS014FramerRowStatusEntry
   ACCESS     not-accessible
   STATUS     mandatory
   DESCRIPTION
     "This entry controls the addition and deletion of 
      dataSigChanTS014Framer components."
::= { dataSigChanTS014Framer 1 }

dataSigChanTS014FramerRowStatusEntry OBJECT-TYPE
   SYNTAX     DataSigChanTS014FramerRowStatusEntry
   ACCESS     not-accessible
   STATUS     mandatory
   DESCRIPTION
     "A single entry in the table represents a single 
      dataSigChanTS014Framer component."
   INDEX {
      dataSigChanIndex,
      dataSigChanTS014Index,
      dataSigChanTS014FramerIndex }
::= { dataSigChanTS014FramerRowStatusTable 1 }

DataSigChanTS014FramerRowStatusEntry ::= SEQUENCE {
   dataSigChanTS014FramerRowStatus
      RowStatus,
   dataSigChanTS014FramerComponentName
      DisplayString,
   dataSigChanTS014FramerStorageType
      StorageType,
   dataSigChanTS014FramerIndex
      NonReplicated }

dataSigChanTS014FramerRowStatus OBJECT-TYPE
   SYNTAX     RowStatus 
   ACCESS     read-only
   STATUS     mandatory
   DESCRIPTION
     "This variable is used as the basis for SNMP naming of
      dataSigChanTS014Framer components.
      These components cannot be added nor deleted."
::= { dataSigChanTS014FramerRowStatusEntry 1 }

dataSigChanTS014FramerComponentName OBJECT-TYPE
   SYNTAX     DisplayString 
   ACCESS     read-only
   STATUS     mandatory
   DESCRIPTION
     "This variable provides the component's string name for
      use with the ASCII Console Interface"
::= { dataSigChanTS014FramerRowStatusEntry 2 }

dataSigChanTS014FramerStorageType OBJECT-TYPE
   SYNTAX     StorageType 
   ACCESS     read-only
   STATUS     mandatory
   DESCRIPTION
     "This variable represents the storage type value for the
      dataSigChanTS014Framer tables."
::= { dataSigChanTS014FramerRowStatusEntry 4 }

dataSigChanTS014FramerIndex OBJECT-TYPE
   SYNTAX     NonReplicated 
   ACCESS     not-accessible
   STATUS     mandatory
   DESCRIPTION
     "This variable represents the index for the dataSigChanTS014Framer tables."
::= { dataSigChanTS014FramerRowStatusEntry 10 }

dataSigChanTS014FramerProvTable OBJECT-TYPE
   SYNTAX     SEQUENCE OF DataSigChanTS014FramerProvEntry
   ACCESS     not-accessible
   STATUS     mandatory
   DESCRIPTION
     "This group contains the base provisioning data for the Framer 
      component. Application or hardware interface specific provisioning 
      data is contained in other provisionable Framer groups."
::= { dataSigChanTS014Framer 10 }

dataSigChanTS014FramerProvEntry OBJECT-TYPE
   SYNTAX     DataSigChanTS014FramerProvEntry
   ACCESS     not-accessible
   STATUS     mandatory
   DESCRIPTION
     "An entry in the dataSigChanTS014FramerProvTable."
   INDEX {
      dataSigChanIndex,
      dataSigChanTS014Index,
      dataSigChanTS014FramerIndex }
::= { dataSigChanTS014FramerProvTable 1 }

DataSigChanTS014FramerProvEntry ::= SEQUENCE {
   dataSigChanTS014FramerInterfaceName
      Link }

dataSigChanTS014FramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dataSigChanTS014FramerProvEntry 1 }

dataSigChanTS014FramerStateTable OBJECT-TYPE
   SYNTAX     SEQUENCE OF DataSigChanTS014FramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dataSigChanTS014Framer 12 }

dataSigChanTS014FramerStateEntry OBJECT-TYPE
   SYNTAX     DataSigChanTS014FramerStateEntry
   ACCESS     not-accessible
   STATUS     mandatory
   DESCRIPTION
     "An entry in the dataSigChanTS014FramerStateTable."
   INDEX {
      dataSigChanIndex,
      dataSigChanTS014Index,
      dataSigChanTS014FramerIndex }
::= { dataSigChanTS014FramerStateTable 1 }

DataSigChanTS014FramerStateEntry ::= SEQUENCE {
   dataSigChanTS014FramerAdminState
      INTEGER,
   dataSigChanTS014FramerOperationalState
      INTEGER,
   dataSigChanTS014FramerUsageState
      INTEGER }

dataSigChanTS014FramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dataSigChanTS014FramerStateEntry 1 }

dataSigChanTS014FramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dataSigChanTS014FramerStateEntry 2 }

dataSigChanTS014FramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dataSigChanTS014FramerStateEntry 3 }

dataSigChanTS014FramerStatsTable OBJECT-TYPE
   SYNTAX     SEQUENCE OF DataSigChanTS014FramerStatsEntry
   ACCESS     not-accessible
   STATUS     mandatory
   DESCRIPTION
     "This group contains the operational statistics data for a Framer 
      component."
::= { dataSigChanTS014Framer 13 }

dataSigChanTS014FramerStatsEntry OBJECT-TYPE
   SYNTAX     DataSigChanTS014FramerStatsEntry
   ACCESS     not-accessible
   STATUS     mandatory
   DESCRIPTION
     "An entry in the dataSigChanTS014FramerStatsTable."
   INDEX {
      dataSigChanIndex,
      dataSigChanTS014Index,
      dataSigChanTS014FramerIndex }
::= { dataSigChanTS014FramerStatsTable 1 }

DataSigChanTS014FramerStatsEntry ::= SEQUENCE {
   dataSigChanTS014FramerFrmToIf
      Unsigned32,
   dataSigChanTS014FramerFrmFromIf
      Unsigned32,
   dataSigChanTS014FramerOctetFromIf
      Unsigned32,
   dataSigChanTS014FramerAborts
      Unsigned32,
   dataSigChanTS014FramerCrcErrors
      Unsigned32,
   dataSigChanTS014FramerLrcErrors
      Unsigned32,
   dataSigChanTS014FramerNonOctetErrors
      Unsigned32,
   dataSigChanTS014FramerOverruns
      Unsigned32,
   dataSigChanTS014FramerUnderruns
      Unsigned32,
   dataSigChanTS014FramerLargeFrmErrors
      Unsigned32 }

dataSigChanTS014FramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { dataSigChanTS014FramerStatsEntry 1 }

dataSigChanTS014FramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { dataSigChanTS014FramerStatsEntry 2 }

dataSigChanTS014FramerOctetFromIf OBJECT-TYPE
   SYNTAX     Unsigned32 (0..4294967295)
   ACCESS     read-only
   STATUS     mandatory
   DESCRIPTION
     "The number of bytes received from the link interface by Framer."
   DEFVAL     { 0 }
::= { dataSigChanTS014FramerStatsEntry 3 }

dataSigChanTS014FramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { dataSigChanTS014FramerStatsEntry 4 }

dataSigChanTS014FramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { dataSigChanTS014FramerStatsEntry 5 }

dataSigChanTS014FramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { dataSigChanTS014FramerStatsEntry 6 }

dataSigChanTS014FramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { dataSigChanTS014FramerStatsEntry 7 }

dataSigChanTS014FramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { dataSigChanTS014FramerStatsEntry 8 }

dataSigChanTS014FramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { dataSigChanTS014FramerStatsEntry 9 }

dataSigChanTS014FramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { dataSigChanTS014FramerStatsEntry 10 }




-- 
-- Version and Compliance statements
-- 



-- Object-Group Statement:
-- A list of all current accessible leaf objects.

-- OBJECTS { dataSigChanTS014FramerCrcErrors,
--           dataSigChanTS014StorageType,
--           dataSigChanTS014FramerOperationalState,
--           dataSigChanTS014FramerUnderruns,
--           dataSigChanTS014T200,
--           dataSigChanTS014FramerLargeFrmErrors,
--           dataSigChanTS014FramerOctetFromIf,
--           dataSigChanTS014T203,
--           dataSigChanTS014T23,
--           dataSigChanTS014DChanStatus,
--           dataSigChanTS014FramerAdminState,
--           dataSigChanTS014FramerOverruns,
--           dataSigChanTS014FramerLrcErrors,
--           dataSigChanTS014FramerFrmToIf,
--           dataSigChanTS014FramerRowStatus,
--           dataSigChanTS014ActiveChannels,
--           dataSigChanTS014FramerAborts,
--           dataSigChanTS014RowStatus,
--           dataSigChanTS014N201,
--           dataSigChanTS014Tracing,
--           dataSigChanTS014ComponentName,
--           dataSigChanTS014FramerNonOctetErrors,
--           dataSigChanTS014PeakActiveChannels,
--           dataSigChanTS014FramerUsageState,
--           dataSigChanTS014FramerComponentName,
--           dataSigChanTS014N200,
--           dataSigChanTS014FramerFrmFromIf,
--           dataSigChanTS014FramerInterfaceName,
--           dataSigChanTS014FramerStorageType,
--           dataSigChanTS014CircuitSwitchedK,
--           dataSigChanTS014Side }
-- STATUS  mandatory
-- DESCRIPTION
--   "A list of all current accessible leaf objects."

disdnTS014Group OBJECT IDENTIFIER ::= { disdnTS014MIB 1 }
disdnTS014GroupBE OBJECT IDENTIFIER ::= { disdnTS014Group 5 }
disdnTS014GroupBE00 OBJECT IDENTIFIER ::= { disdnTS014GroupBE 1 }
disdnTS014GroupBE00A OBJECT IDENTIFIER ::= { disdnTS014GroupBE00 2 }



-- Agent-Capabilities Statement:

-- PRODUCT-RELEASE "Passport Release 7.0 DisdnTS014."
-- STATUS          mandatory
-- DESCRIPTION     "DisdnTS014 MIB: MIB Version BE00A,
--                  Software Version BG00S4C."
-- SUPPORTS        Nortel-Magellan-Passport-DisdnTS014MIB
--    INCLUDES     { disdnTS014GroupBE00A }

disdnTS014Capabilities OBJECT IDENTIFIER ::= { disdnTS014MIB 3 }
disdnTS014CapabilitiesBE OBJECT IDENTIFIER ::= { disdnTS014Capabilities 5 }
disdnTS014CapabilitiesBE00 OBJECT IDENTIFIER ::= { disdnTS014CapabilitiesBE 1 }
disdnTS014CapabilitiesBE00A OBJECT IDENTIFIER ::= { disdnTS014CapabilitiesBE00 2 }





END
