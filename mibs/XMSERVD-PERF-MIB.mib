-- XMSERVD-PERF-MIB DEFINITIONS dumped by xmservd daemon
-- Dump was done on host "aixlab1" at Fri Sep  8 13:13:30 2000


	XMSERVD-PERF-MIB DEFINITIONS ::= BEGIN

	IMPORTS
		Counter, enterprises, OBJECT-TYPE, internet
			FROM RFC1155-SMI
		DisplayString FROM SNMPv2-TC;


	directory OBJECT IDENTIFIER ::= { internet 1 }
	mgmt OBJECT IDENTIFIER ::= { internet 2 }
	experimental OBJECT IDENTIFIER ::= { internet 3 }
	private OBJECT IDENTIFIER ::= { internet 4 }
	enterprises OBJECT IDENTIFIER ::= { private 1 }
	ibm OBJECT IDENTIFIER ::= { enterprises 2 }
	ibmAgents OBJECT IDENTIFIER ::= { ibm 3 }
	aix OBJECT IDENTIFIER ::= { ibmAgents 1 }
	aixRT OBJECT IDENTIFIER ::= { aix 1 }
	aixRISC6000 OBJECT IDENTIFIER ::= { aix 2 }
	risc6000agents OBJECT IDENTIFIER ::= { aixRISC6000 1 }
	risc6000snmpd OBJECT IDENTIFIER ::= { risc6000agents 1 }
	risc6000gated OBJECT IDENTIFIER ::= { risc6000agents 2 }
	risc6000xmservd OBJECT IDENTIFIER ::= { risc6000agents 3 }
	risc6000ibm7318 OBJECT IDENTIFIER ::= { risc6000agents 4 }
	risc6000clsmuxpd OBJECT IDENTIFIER ::= { risc6000agents 5 }
	risc6000private OBJECT IDENTIFIER ::= { aixRISC6000 2 }
	risc6000samples OBJECT IDENTIFIER ::= { risc6000private 1 }
	risc6000sampleAgents OBJECT IDENTIFIER ::= { risc6000samples 1 }
	risc6000perf OBJECT IDENTIFIER ::= { risc6000private 2 }
	xmd OBJECT IDENTIFIER ::= { risc6000perf 1 }
	risc6000public OBJECT IDENTIFIER ::= { aixRISC6000 3 }
	aix370 OBJECT IDENTIFIER ::= { aix 3 }
	aixPS2 OBJECT IDENTIFIER ::= { aix 4 }
	mvs OBJECT IDENTIFIER ::= { ibmAgents 2 }
	mvs370 OBJECT IDENTIFIER ::= { mvs 1 }
	vm OBJECT IDENTIFIER ::= { ibmAgents 3 }
	vm370 OBJECT IDENTIFIER ::= { vm 1 }
	os2 OBJECT IDENTIFIER ::= { ibmAgents 4 }
	ps2PS2 OBJECT IDENTIFIER ::= { os2 1 }
	os400 OBJECT IDENTIFIER ::= { ibmAgents 5 }
	os400as400 OBJECT IDENTIFIER ::= { os400 1 }


	xmdCPU OBJECT IDENTIFIER ::= { xmd 1 }

	xmdCPUGluser OBJECT-TYPE
		SYNTAX INTEGER
		ACCESS read-only
		STATUS mandatory
		DESCRIPTION
			"System-wide time executing in user mode (percent)"
		::= { xmdCPU 101 }

	xmdCPUGlkern OBJECT-TYPE
		SYNTAX INTEGER
		ACCESS read-only
		STATUS mandatory
		DESCRIPTION
			"System-wide time executing in kernel mode (percent)"
		::= { xmdCPU 102 }

	xmdCPUGlwait OBJECT-TYPE
		SYNTAX INTEGER
		ACCESS read-only
		STATUS mandatory
		DESCRIPTION
			"System-wide time waiting for IO (percent)"
		::= { xmdCPU 103 }

	xmdCPUGlidle OBJECT-TYPE
		SYNTAX INTEGER
		ACCESS read-only
		STATUS mandatory
		DESCRIPTION
			"System-wide time CPU is idle (percent)"
		::= { xmdCPU 104 }

	xmdCPUGluticks OBJECT-TYPE
		SYNTAX Counter
		ACCESS read-only
		STATUS mandatory
		DESCRIPTION
			"System-wide CPU ticks executing in user mode"
		::= { xmdCPU 121 }

	xmdCPUGlkticks OBJECT-TYPE
		SYNTAX Counter
		ACCESS read-only
		STATUS mandatory
		DESCRIPTION
			"System-wide CPU ticks executing in kernel mode"
		::= { xmdCPU 122 }

	xmdCPUGlwticks OBJECT-TYPE
		SYNTAX Counter
		ACCESS read-only
		STATUS mandatory
		DESCRIPTION
			"System-wide CPU ticks waiting for IO"
		::= { xmdCPU 123 }

	xmdCPUGliticks OBJECT-TYPE
		SYNTAX Counter
		ACCESS read-only
		STATUS mandatory
		DESCRIPTION
			"System-wide CPU ticks while CPU is idle"
		::= { xmdCPU 124 }

	xmdMem OBJECT IDENTIFIER ::= { xmd 2 }

	xmdMemReal OBJECT IDENTIFIER ::= { xmdMem 1 }

	xmdMemRealSize OBJECT-TYPE
		SYNTAX INTEGER
		ACCESS read-only
		STATUS mandatory
		DESCRIPTION
			"Size of physical memory (4K pages)"
		::= { xmdMemReal 1 }

	xmdMemRealNumfrb OBJECT-TYPE
		SYNTAX INTEGER
		ACCESS read-only
		STATUS mandatory
		DESCRIPTION
			"Number of pages on free list"
		::= { xmdMemReal 2 }

	xmdMemRealNoncomp OBJECT-TYPE
		SYNTAX INTEGER
		ACCESS read-only
		STATUS mandatory
		DESCRIPTION
			"Number of non-computational pages resident in memory"
		::= { xmdMemReal 3 }

	xmdMemRealComp OBJECT-TYPE
		SYNTAX INTEGER
		ACCESS read-only
		STATUS mandatory
		DESCRIPTION
			"Number of computational pages resident in memory"
		::= { xmdMemReal 4 }

	xmdMemRealNumlocal OBJECT-TYPE
		SYNTAX INTEGER
		ACCESS read-only
		STATUS mandatory
		DESCRIPTION
			"Number of local pages resident in memory"
		::= { xmdMemReal 5 }

	xmdMemRealNumclient OBJECT-TYPE
		SYNTAX INTEGER
		ACCESS read-only
		STATUS mandatory
		DESCRIPTION
			"Number of client pages resident in memory"
		::= { xmdMemReal 6 }

	xmdMemRealMaxclient OBJECT-TYPE
		SYNTAX INTEGER
		ACCESS read-only
		STATUS mandatory
		DESCRIPTION
			"Maximum number of client pages allowed"
		::= { xmdMemReal 7 }

	xmdMemRealPdecay OBJECT-TYPE
		SYNTAX INTEGER
		ACCESS read-only
		STATUS mandatory
		DESCRIPTION
			"Decay rate for repaging values"
		::= { xmdMemReal 8 }

	xmdMemRealSysrepag OBJECT-TYPE
		SYNTAX INTEGER
		ACCESS read-only
		STATUS mandatory
		DESCRIPTION
			"Global repaging rate"
		::= { xmdMemReal 9 }

	xmdMemRealEfree OBJECT-TYPE
		SYNTAX INTEGER
		ACCESS read-only
		STATUS mandatory
		DESCRIPTION
			"% memory which is free"
		::= { xmdMemReal 10 }

	xmdMemRealEpinned OBJECT-TYPE
		SYNTAX INTEGER
		ACCESS read-only
		STATUS mandatory
		DESCRIPTION
			"% memory which is pinned"
		::= { xmdMemReal 11 }

	xmdMemRealEcomp OBJECT-TYPE
		SYNTAX INTEGER
		ACCESS read-only
		STATUS mandatory
		DESCRIPTION
			"% memory allocated to computational segments"
		::= { xmdMemReal 12 }

	xmdMemRealEnoncomp OBJECT-TYPE
		SYNTAX INTEGER
		ACCESS read-only
		STATUS mandatory
		DESCRIPTION
			"% memory allocated to non-computational segments"
		::= { xmdMemReal 13 }

	xmdMemRealElocal OBJECT-TYPE
		SYNTAX INTEGER
		ACCESS read-only
		STATUS mandatory
		DESCRIPTION
			"% memory allocated to local segments"
		::= { xmdMemReal 14 }

	xmdMemRealEclnt OBJECT-TYPE
		SYNTAX INTEGER
		ACCESS read-only
		STATUS mandatory
		DESCRIPTION
			"% memory allocated to client segments"
		::= { xmdMemReal 15 }

	xmdMemRealWseguse OBJECT-TYPE
		SYNTAX INTEGER
		ACCESS read-only
		STATUS mandatory
		DESCRIPTION
			"working seg in use pages"
		::= { xmdMemReal 16 }

	xmdMemRealPseguse OBJECT-TYPE
		SYNTAX INTEGER
		ACCESS read-only
		STATUS mandatory
		DESCRIPTION
			"persistent seg in use pages"
		::= { xmdMemReal 17 }

	xmdMemRealClseguse OBJECT-TYPE
		SYNTAX INTEGER
		ACCESS read-only
		STATUS mandatory
		DESCRIPTION
			"client seg in use pages"
		::= { xmdMemReal 18 }

	xmdMemRealWsegpin OBJECT-TYPE
		SYNTAX INTEGER
		ACCESS read-only
		STATUS mandatory
		DESCRIPTION
			"working seg pinned pages"
		::= { xmdMemReal 19 }

	xmdMemRealPsegpin OBJECT-TYPE
		SYNTAX INTEGER
		ACCESS read-only
		STATUS mandatory
		DESCRIPTION
			"persistent seg pinned pages"
		::= { xmdMemReal 20 }

	xmdMemRealClsegpin OBJECT-TYPE
		SYNTAX INTEGER
		ACCESS read-only
		STATUS mandatory
		DESCRIPTION
			"client seg pinned pages"
		::= { xmdMemReal 21 }

	xmdMemVirt OBJECT IDENTIFIER ::= { xmdMem 2 }

	xmdMemVirtPagein OBJECT-TYPE
		SYNTAX Counter
		ACCESS read-only
		STATUS mandatory
		DESCRIPTION
			"4K pages read by VMM"
		::= { xmdMemVirt 1 }

	xmdMemVirtPageout OBJECT-TYPE
		SYNTAX Counter
		ACCESS read-only
		STATUS mandatory
		DESCRIPTION
			"4K pages written by VMM"
		::= { xmdMemVirt 2 }

	xmdMemVirtPgspgin OBJECT-TYPE
		SYNTAX Counter
		ACCESS read-only
		STATUS mandatory
		DESCRIPTION
			"4K pages read from paging space by VMM"
		::= { xmdMemVirt 3 }

	xmdMemVirtPgspgout OBJECT-TYPE
		SYNTAX Counter
		ACCESS read-only
		STATUS mandatory
		DESCRIPTION
			"4K pages written to paging space by VMM"
		::= { xmdMemVirt 4 }

	xmdMemVirtSio OBJECT-TYPE
		SYNTAX Counter
		ACCESS read-only
		STATUS mandatory
		DESCRIPTION
			"4K IO requests initiated by VMM"
		::= { xmdMemVirt 5 }

	xmdMemVirtIodone OBJECT-TYPE
		SYNTAX Counter
		ACCESS read-only
		STATUS mandatory
		DESCRIPTION
			"4K IO requests completed by VMM"
		::= { xmdMemVirt 6 }

	xmdMemVirtZerofill OBJECT-TYPE
		SYNTAX Counter
		ACCESS read-only
		STATUS mandatory
		DESCRIPTION
			"Page faults satisfied by zero-filling memory frames"
		::= { xmdMemVirt 7 }

	xmdMemVirtPagexct OBJECT-TYPE
		SYNTAX Counter
		ACCESS read-only
		STATUS mandatory
		DESCRIPTION
			"Total page faults"
		::= { xmdMemVirt 8 }

	xmdMemVirtPgrclm OBJECT-TYPE
		SYNTAX Counter
		ACCESS read-only
		STATUS mandatory
		DESCRIPTION
			"Page faults satisfied by page reclaims"
		::= { xmdMemVirt 9 }

	xmdMemVirtLockexct OBJECT-TYPE
		SYNTAX Counter
		ACCESS read-only
		STATUS mandatory
		DESCRIPTION
			"Page faults due to lock misses"
		::= { xmdMemVirt 10 }

	xmdMemVirtBacktrk OBJECT-TYPE
		SYNTAX Counter
		ACCESS read-only
		STATUS mandatory
		DESCRIPTION
			"Page faults while satisfying previous page-faults"
		::= { xmdMemVirt 11 }

	xmdMemVirtExfill OBJECT-TYPE
		SYNTAX Counter
		ACCESS read-only
		STATUS mandatory
		DESCRIPTION
			"Instruction page faults"
		::= { xmdMemVirt 12 }

	xmdMemVirtScan OBJECT-TYPE
		SYNTAX Counter
		ACCESS read-only
		STATUS mandatory
		DESCRIPTION
			"Physical memory 4K frames examined by VMM"
		::= { xmdMemVirt 13 }

	xmdMemVirtCycle OBJECT-TYPE
		SYNTAX Counter
		ACCESS read-only
		STATUS mandatory
		DESCRIPTION
			"Complete scans of physical memory by VMM"
		::= { xmdMemVirt 14 }

	xmdMemVirtSteal OBJECT-TYPE
		SYNTAX Counter
		ACCESS read-only
		STATUS mandatory
		DESCRIPTION
			"Physical memory 4K frames stolen by VMM"
		::= { xmdMemVirt 15 }

	xmdMemVirtFreewt OBJECT-TYPE
		SYNTAX Counter
		ACCESS read-only
		STATUS mandatory
		DESCRIPTION
			"Process waits due to page replacement"
		::= { xmdMemVirt 16 }

	xmdMemVirtExtendwt OBJECT-TYPE
		SYNTAX Counter
		ACCESS read-only
		STATUS mandatory
		DESCRIPTION
			"Process waits due to commit in progress"
		::= { xmdMemVirt 17 }

	xmdMemVirtPendiowt OBJECT-TYPE
		SYNTAX Counter
		ACCESS read-only
		STATUS mandatory
		DESCRIPTION
			"Process waits due to pageins"
		::= { xmdMemVirt 18 }

	xmdMemVirtPfavail OBJECT-TYPE
		SYNTAX INTEGER
		ACCESS read-only
		STATUS mandatory
		DESCRIPTION
			"Pages not pinned"
		::= { xmdMemVirt 19 }

	xmdMemVirtWcomrepag OBJECT-TYPE
		SYNTAX INTEGER
		ACCESS read-only
		STATUS mandatory
		DESCRIPTION
			"Weighted repage rate to computational segments"
		::= { xmdMemVirt 20 }

	xmdMemVirtWncomrepag OBJECT-TYPE
		SYNTAX INTEGER
		ACCESS read-only
		STATUS mandatory
		DESCRIPTION
			"Weighted repage rate to non-computational segments"
		::= { xmdMemVirt 21 }

	xmdMemVirtComrepag OBJECT-TYPE
		SYNTAX Counter
		ACCESS read-only
		STATUS mandatory
		DESCRIPTION
			"Repage rate to computational segments"
		::= { xmdMemVirt 22 }

	xmdMemVirtEcomrepag OBJECT-TYPE
		SYNTAX INTEGER
		ACCESS read-only
		STATUS mandatory
		DESCRIPTION
			"% of repage requests coming from computational segments"
		::= { xmdMemVirt 23 }

	xmdMemVirtNcomrepag OBJECT-TYPE
		SYNTAX Counter
		ACCESS read-only
		STATUS mandatory
		DESCRIPTION
			"Repage rate to non-computational segments"
		::= { xmdMemVirt 24 }

	xmdMemVirtEncomrepag OBJECT-TYPE
		SYNTAX INTEGER
		ACCESS read-only
		STATUS mandatory
		DESCRIPTION
			"% of repage requests coming from non-computational segments"
		::= { xmdMemVirt 25 }

	xmdMemVirtComrepl OBJECT-TYPE
		SYNTAX Counter
		ACCESS read-only
		STATUS mandatory
		DESCRIPTION
			"Page replace rate in computational segments"
		::= { xmdMemVirt 26 }

	xmdMemVirtEcomrepl OBJECT-TYPE
		SYNTAX INTEGER
		ACCESS read-only
		STATUS mandatory
		DESCRIPTION
			"% of page replace requests coming from computational segments"
		::= { xmdMemVirt 27 }

	xmdMemVirtNcomrepl OBJECT-TYPE
		SYNTAX Counter
		ACCESS read-only
		STATUS mandatory
		DESCRIPTION
			"Page replace rate in non-computational segments"
		::= { xmdMemVirt 28 }

	xmdMemVirtEncomrepl OBJECT-TYPE
		SYNTAX INTEGER
		ACCESS read-only
		STATUS mandatory
		DESCRIPTION
			"% of page replace requests coming from non-comp segments"
		::= { xmdMemVirt 29 }

	xmdMemVirtTotpends OBJECT-TYPE
		SYNTAX INTEGER
		ACCESS read-only
		STATUS mandatory
		DESCRIPTION
			"Number of page replacement pageouts pending"
		::= { xmdMemVirt 30 }

	xmdMemVirtCompends OBJECT-TYPE
		SYNTAX INTEGER
		ACCESS read-only
		STATUS mandatory
		DESCRIPTION
			"Number of computational page replacement pageouts pending"
		::= { xmdMemVirt 31 }

	xmdMemVirtNcompends OBJECT-TYPE
		SYNTAX INTEGER
		ACCESS read-only
		STATUS mandatory
		DESCRIPTION
			"Number of non-comp page replacement pageouts pending"
		::= { xmdMemVirt 32 }

	xmdMemVirtCltpends OBJECT-TYPE
		SYNTAX INTEGER
		ACCESS read-only
		STATUS mandatory
		DESCRIPTION
			"Total number of client page replacement pageouts pending"
		::= { xmdMemVirt 33 }

	xmdMemVirtNpswarn OBJECT-TYPE
		SYNTAX INTEGER
		ACCESS read-only
		STATUS mandatory
		DESCRIPTION
			"Threshold (pages) for warning user of paging space shortage"
		::= { xmdMemVirt 34 }

	xmdMemVirtNpskill OBJECT-TYPE
		SYNTAX INTEGER
		ACCESS read-only
		STATUS mandatory
		DESCRIPTION
			"Threshold for killing processes due to paging space shortage"
		::= { xmdMemVirt 35 }

	xmdMemVirtMaxfree OBJECT-TYPE
		SYNTAX INTEGER
		ACCESS read-only
		STATUS mandatory
		DESCRIPTION
			"Number of free pages attempted created by page replacement"
		::= { xmdMemVirt 36 }

	xmdMemVirtMinfree OBJECT-TYPE
		SYNTAX INTEGER
		ACCESS read-only
		STATUS mandatory
		DESCRIPTION
			"Page replacement starts when less than minfree pages are free"
		::= { xmdMemVirt 37 }

	xmdMemVirtMinperm OBJECT-TYPE
		SYNTAX INTEGER
		ACCESS read-only
		STATUS mandatory
		DESCRIPTION
			"Minimum number of non-computational pages kept resident"
		::= { xmdMemVirt 38 }

	xmdMemVirtMaxpgahead OBJECT-TYPE
		SYNTAX INTEGER
		ACCESS read-only
		STATUS mandatory
		DESCRIPTION
			"Maximum number of pageahead pages"
		::= { xmdMemVirt 39 }

	xmdMemVirtMinpgahead OBJECT-TYPE
		SYNTAX INTEGER
		ACCESS read-only
		STATUS mandatory
		DESCRIPTION
			"Minimum number of pageahead pages"
		::= { xmdMemVirt 40 }

	xmdMemVirtMaxpout OBJECT-TYPE
		SYNTAX INTEGER
		ACCESS read-only
		STATUS mandatory
		DESCRIPTION
			"Maximum pages queued for a file (write behind maximum)"
		::= { xmdMemVirt 41 }

	xmdMemVirtMinpout OBJECT-TYPE
		SYNTAX INTEGER
		ACCESS read-only
		STATUS mandatory
		DESCRIPTION
			"Minimum pages queued for a file (write behind maximum)"
		::= { xmdMemVirt 42 }

	xmdMemKmem OBJECT-TYPE
		SYNTAX SEQUENCE OF XmdMemKmemEntry
		ACCESS not-accessible
		STATUS mandatory
		DESCRIPTION
			"Kernel memory allocation statistics"
		::= { xmdMem 4 }

	xmdMemKmemEntry OBJECT-TYPE
		SYNTAX XmdMemKmemEntry
		ACCESS not-accessible
		STATUS mandatory
		DESCRIPTION
			"Element of above table"
		::= { xmdMemKmem 1 }

	XmdMemKmemEntry ::=
		SEQUENCE
		{
		   xmdMemKmemIndex INTEGER,
		   xmdMemKmemInstName DisplayString,
		   xmdMemKmemInuse INTEGER,
		   xmdMemKmemCalls Counter,
		   xmdMemKmemFailures Counter,
		   xmdMemKmemMemuse INTEGER,
		   xmdMemKmemMemmax INTEGER,
		   xmdMemKmemBlocks INTEGER
		}

	xmdMemKmemIndex OBJECT-TYPE
		SYNTAX INTEGER
		ACCESS read-only
		STATUS mandatory
		DESCRIPTION
			"Index Number"
		::= { xmdMemKmemEntry 1 }

	xmdMemKmemInstName OBJECT-TYPE
		SYNTAX DisplayString
		ACCESS read-only
		STATUS mandatory
		DESCRIPTION
			"Instance Name"
		::= { xmdMemKmemEntry 2 }

	xmdMemKmemInuse OBJECT-TYPE
		SYNTAX INTEGER
		ACCESS read-only
		STATUS mandatory
		DESCRIPTION
			"Count of kernel memory buffers in use"
		::= { xmdMemKmemEntry 3 }

	xmdMemKmemCalls OBJECT-TYPE
		SYNTAX Counter
		ACCESS read-only
		STATUS mandatory
		DESCRIPTION
			"Number of requests for a kernel memory buffer"
		::= { xmdMemKmemEntry 4 }

	xmdMemKmemFailures OBJECT-TYPE
		SYNTAX Counter
		ACCESS read-only
		STATUS mandatory
		DESCRIPTION
			"Number of failed requests for a kernel memory buffer"
		::= { xmdMemKmemEntry 5 }

	xmdMemKmemMemuse OBJECT-TYPE
		SYNTAX INTEGER
		ACCESS read-only
		STATUS mandatory
		DESCRIPTION
			"Current memory use (bytes)"
		::= { xmdMemKmemEntry 6 }

	xmdMemKmemMemmax OBJECT-TYPE
		SYNTAX INTEGER
		ACCESS read-only
		STATUS mandatory
		DESCRIPTION
			"Maximum memory ever used (bytes)"
		::= { xmdMemKmemEntry 7 }

	xmdMemKmemBlocks OBJECT-TYPE
		SYNTAX Counter
		ACCESS read-only
		STATUS mandatory
		DESCRIPTION
			"Number of times blocked for kernel map"
		::= { xmdMemKmemEntry 8 }

	xmdPagSp OBJECT-TYPE
		SYNTAX SEQUENCE OF XmdPagSpEntry
		ACCESS not-accessible
		STATUS mandatory
		DESCRIPTION
			"Paging space statistics"
		::= { xmd 3 }

	xmdPagSpEntry OBJECT-TYPE
		SYNTAX XmdPagSpEntry
		ACCESS not-accessible
		STATUS mandatory
		DESCRIPTION
			"Element of above table"
		::= { xmdPagSp 1 }

	XmdPagSpEntry ::=
		SEQUENCE
		{
		   xmdPagSpIndex INTEGER,
		   xmdPagSpInstName DisplayString,
		   xmdPagSpSize INTEGER,
		   xmdPagSpEfree INTEGER,
		   xmdPagSpIocnt INTEGER
		}

	xmdPagSpIndex OBJECT-TYPE
		SYNTAX INTEGER
		ACCESS read-only
		STATUS mandatory
		DESCRIPTION
			"Index Number"
		::= { xmdPagSpEntry 1 }

	xmdPagSpInstName OBJECT-TYPE
		SYNTAX DisplayString
		ACCESS read-only
		STATUS mandatory
		DESCRIPTION
			"Instance Name"
		::= { xmdPagSpEntry 2 }

	xmdPagSpSize OBJECT-TYPE
		SYNTAX INTEGER
		ACCESS read-only
		STATUS mandatory
		DESCRIPTION
			"Size of paging space (4K pages)"
		::= { xmdPagSpEntry 3 }

	xmdPagSpEfree OBJECT-TYPE
		SYNTAX INTEGER
		ACCESS read-only
		STATUS mandatory
		DESCRIPTION
			"Free portion of this paging space (percent)"
		::= { xmdPagSpEntry 4 }

	xmdPagSpIocnt OBJECT-TYPE
		SYNTAX INTEGER
		ACCESS read-only
		STATUS mandatory
		DESCRIPTION
			"Pending IOs for this paging space"
		::= { xmdPagSpEntry 5 }

	xmdPagSpTotalsize OBJECT-TYPE
		SYNTAX INTEGER
		ACCESS read-only
		STATUS mandatory
		DESCRIPTION
			"Total active paging space size (4K pages)"
		::= { xmdPagSp 11 }

	xmdPagSpTotalfree OBJECT-TYPE
		SYNTAX INTEGER
		ACCESS read-only
		STATUS mandatory
		DESCRIPTION
			"Total free disk paging space (4K pages)"
		::= { xmdPagSp 12 }

	xmdPagSpEtotalfree OBJECT-TYPE
		SYNTAX INTEGER
		ACCESS read-only
		STATUS mandatory
		DESCRIPTION
			"Total free disk paging space (percent)"
		::= { xmdPagSp 13 }

	xmdPagSpEtotalused OBJECT-TYPE
		SYNTAX INTEGER
		ACCESS read-only
		STATUS mandatory
		DESCRIPTION
			"Total used disk paging space (percent)"
		::= { xmdPagSp 14 }

	xmdPagSpPgspgin OBJECT-TYPE
		SYNTAX Counter
		ACCESS read-only
		STATUS mandatory
		DESCRIPTION
			"4K pages read from paging space by VMM"
		::= { xmdPagSp 15 }

	xmdPagSpPgspgout OBJECT-TYPE
		SYNTAX Counter
		ACCESS read-only
		STATUS mandatory
		DESCRIPTION
			"4K pages written to paging space by VMM"
		::= { xmdPagSp 16 }

	xmdDisk OBJECT-TYPE
		SYNTAX SEQUENCE OF XmdDiskEntry
		ACCESS not-accessible
		STATUS mandatory
		DESCRIPTION
			"Disk and CD ROM statistics"
		::= { xmd 4 }

	xmdDiskEntry OBJECT-TYPE
		SYNTAX XmdDiskEntry
		ACCESS not-accessible
		STATUS mandatory
		DESCRIPTION
			"Element of above table"
		::= { xmdDisk 1 }

	XmdDiskEntry ::=
		SEQUENCE
		{
		   xmdDiskIndex INTEGER,
		   xmdDiskInstName DisplayString,
		   xmdDiskBusy Counter,
		   xmdDiskXfer Counter,
		   xmdDiskRblk Counter,
		   xmdDiskWblk Counter
		}

	xmdDiskIndex OBJECT-TYPE
		SYNTAX INTEGER
		ACCESS read-only
		STATUS mandatory
		DESCRIPTION
			"Index Number"
		::= { xmdDiskEntry 1 }

	xmdDiskInstName OBJECT-TYPE
		SYNTAX DisplayString
		ACCESS read-only
		STATUS mandatory
		DESCRIPTION
			"Instance Name"
		::= { xmdDiskEntry 2 }

	xmdDiskBusy OBJECT-TYPE
		SYNTAX Counter
		ACCESS read-only
		STATUS mandatory
		DESCRIPTION
			"Time disk is busy (percent)"
		::= { xmdDiskEntry 3 }

	xmdDiskXfer OBJECT-TYPE
		SYNTAX Counter
		ACCESS read-only
		STATUS mandatory
		DESCRIPTION
			"Transfers to/from disk"
		::= { xmdDiskEntry 4 }

	xmdDiskRblk OBJECT-TYPE
		SYNTAX Counter
		ACCESS read-only
		STATUS mandatory
		DESCRIPTION
			"512 byte blocks read from disk"
		::= { xmdDiskEntry 5 }

	xmdDiskWblk OBJECT-TYPE
		SYNTAX Counter
		ACCESS read-only
		STATUS mandatory
		DESCRIPTION
			"512 byte blocks written to disk"
		::= { xmdDiskEntry 6 }

	xmdLAN OBJECT-TYPE
		SYNTAX SEQUENCE OF XmdLANEntry
		ACCESS not-accessible
		STATUS mandatory
		DESCRIPTION
			"LAN Interfaces"
		::= { xmd 5 }

	xmdLANEntry OBJECT-TYPE
		SYNTAX XmdLANEntry
		ACCESS not-accessible
		STATUS mandatory
		DESCRIPTION
			"Element of above table"
		::= { xmdLAN 1 }

	XmdLANEntry ::=
		SEQUENCE
		{
		   xmdLANIndex INTEGER,
		   xmdLANInstName DisplayString,
		   xmdLANBytesout Counter,
		   xmdLANKbytesout Counter,
		   xmdLANBytesin Counter,
		   xmdLANKbytesin Counter,
		   xmdLANFramesout Counter,
		   xmdLANFramesin Counter,
		   xmdLANXmiterrors Counter,
		   xmdLANRcverrors Counter,
		   xmdLANIbadpacks Counter,
		   xmdLANXmitque INTEGER,
		   xmdLANHighxmitq INTEGER,
		   xmdLANRecvintr Counter,
		   xmdLANXmitintr Counter,
		   xmdLANXmitovfl Counter,
		   xmdLANXmitdrops Counter,
		   xmdLANRecvdrops Counter
		}

	xmdLANIndex OBJECT-TYPE
		SYNTAX INTEGER
		ACCESS read-only
		STATUS mandatory
		DESCRIPTION
			"Index Number"
		::= { xmdLANEntry 1 }

	xmdLANInstName OBJECT-TYPE
		SYNTAX DisplayString
		ACCESS read-only
		STATUS mandatory
		DESCRIPTION
			"Instance Name"
		::= { xmdLANEntry 2 }

	xmdLANBytesout OBJECT-TYPE
		SYNTAX Counter
		ACCESS read-only
		STATUS mandatory
		DESCRIPTION
			"Count of bytes transmitted correctly"
		::= { xmdLANEntry 3 }

	xmdLANKbytesout OBJECT-TYPE
		SYNTAX Counter
		ACCESS read-only
		STATUS mandatory
		DESCRIPTION
			"Count of Kbytes transmitted correctly"
		::= { xmdLANEntry 4 }

	xmdLANBytesin OBJECT-TYPE
		SYNTAX Counter
		ACCESS read-only
		STATUS mandatory
		DESCRIPTION
			"Count of bytes received correctly"
		::= { xmdLANEntry 5 }

	xmdLANKbytesin OBJECT-TYPE
		SYNTAX Counter
		ACCESS read-only
		STATUS mandatory
		DESCRIPTION
			"Count of Kbytes received correctly"
		::= { xmdLANEntry 6 }

	xmdLANFramesout OBJECT-TYPE
		SYNTAX Counter
		ACCESS read-only
		STATUS mandatory
		DESCRIPTION
			"Count of frames transmitted correctly"
		::= { xmdLANEntry 7 }

	xmdLANFramesin OBJECT-TYPE
		SYNTAX Counter
		ACCESS read-only
		STATUS mandatory
		DESCRIPTION
			"Count of frames received correctly"
		::= { xmdLANEntry 8 }

	xmdLANXmiterrors OBJECT-TYPE
		SYNTAX Counter
		ACCESS read-only
		STATUS mandatory
		DESCRIPTION
			"Count of frame transmit errors at adapter level"
		::= { xmdLANEntry 9 }

	xmdLANRcverrors OBJECT-TYPE
		SYNTAX Counter
		ACCESS read-only
		STATUS mandatory
		DESCRIPTION
			"Count of frame receive errors at adapter level"
		::= { xmdLANEntry 10 }

	xmdLANIbadpacks OBJECT-TYPE
		SYNTAX Counter
		ACCESS read-only
		STATUS mandatory
		DESCRIPTION
			"Count of bad packets received from this device"
		::= { xmdLANEntry 11 }

	xmdLANXmitque OBJECT-TYPE
		SYNTAX INTEGER
		ACCESS read-only
		STATUS mandatory
		DESCRIPTION
			"Number of transmits currently queued for this device"
		::= { xmdLANEntry 12 }

	xmdLANHighxmitq OBJECT-TYPE
		SYNTAX INTEGER
		ACCESS read-only
		STATUS mandatory
		DESCRIPTION
			"Maximum transmits ever queued for this device"
		::= { xmdLANEntry 13 }

	xmdLANRecvintr OBJECT-TYPE
		SYNTAX Counter
		ACCESS read-only
		STATUS mandatory
		DESCRIPTION
			"Receive data interrupts for this device"
		::= { xmdLANEntry 14 }

	xmdLANXmitintr OBJECT-TYPE
		SYNTAX Counter
		ACCESS read-only
		STATUS mandatory
		DESCRIPTION
			"Transmit complete interrupts for this device"
		::= { xmdLANEntry 15 }

	xmdLANXmitovfl OBJECT-TYPE
		SYNTAX Counter
		ACCESS read-only
		STATUS mandatory
		DESCRIPTION
			"Count of transmit queue overflows"
		::= { xmdLANEntry 16 }

	xmdLANXmitdrops OBJECT-TYPE
		SYNTAX Counter
		ACCESS read-only
		STATUS mandatory
		DESCRIPTION
			"Count of transmit packets dropped at device driver level"
		::= { xmdLANEntry 17 }

	xmdLANRecvdrops OBJECT-TYPE
		SYNTAX Counter
		ACCESS read-only
		STATUS mandatory
		DESCRIPTION
			"Count of receive packets dropped at device driver level"
		::= { xmdLANEntry 18 }

	xmdProc OBJECT-TYPE
		SYNTAX SEQUENCE OF XmdProcEntry
		ACCESS not-accessible
		STATUS mandatory
		DESCRIPTION
			"Process statistics"
		::= { xmd 6 }


	xmdProcEntry OBJECT-TYPE
		SYNTAX XmdProcEntry
		ACCESS not-accessible
		STATUS mandatory
		DESCRIPTION
			"Element of above table"
		::= { xmdProc 1 }

	XmdProcEntry ::=
		SEQUENCE
		{
		   xmdProcIndex INTEGER,
		   xmdProcInstName DisplayString,
		   xmdProcNice INTEGER,
		   xmdProcRepage Counter,
		   xmdProcMajflt Counter,
		   xmdProcMinflt Counter,
		   xmdProcCpums Counter,
		   xmdProcCpuacc INTEGER,
		   xmdProcCpupct INTEGER,
		   xmdProcUsercpu Counter,
		   xmdProcKerncpu Counter,
		   xmdProcWorkmem INTEGER,
		   xmdProcCodemem INTEGER,
		   xmdProcPagsp INTEGER,
		   xmdProcNsignals Counter,
		   xmdProcNvcsw Counter,
		   xmdProcTsize INTEGER,
		   xmdProcMaxrss INTEGER
		}

	xmdProcIndex OBJECT-TYPE
		SYNTAX INTEGER
		ACCESS read-only
		STATUS mandatory
		DESCRIPTION
			"Index Number"
		::= { xmdProcEntry 1 }

	xmdProcInstName OBJECT-TYPE
		SYNTAX DisplayString
		ACCESS read-only
		STATUS mandatory
		DESCRIPTION
			"Instance Name"
		::= { xmdProcEntry 2 }

	xmdProcNice OBJECT-TYPE
		SYNTAX INTEGER
		ACCESS read-only
		STATUS mandatory
		DESCRIPTION
			"Process nice value"
		::= { xmdProcEntry 3 }

	xmdProcRepage OBJECT-TYPE
		SYNTAX Counter
		ACCESS read-only
		STATUS mandatory
		DESCRIPTION
			"Process repage count"
		::= { xmdProcEntry 4 }

	xmdProcMajflt OBJECT-TYPE
		SYNTAX Counter
		ACCESS read-only
		STATUS mandatory
		DESCRIPTION
			"Process page faults involving IO"
		::= { xmdProcEntry 5 }

	xmdProcMinflt OBJECT-TYPE
		SYNTAX Counter
		ACCESS read-only
		STATUS mandatory
		DESCRIPTION
			"Process page faults not involving IO"
		::= { xmdProcEntry 6 }

	xmdProcCpums OBJECT-TYPE
		SYNTAX Counter
		ACCESS read-only
		STATUS mandatory
		DESCRIPTION
			"CPU time in milliseconds in interval"
		::= { xmdProcEntry 7 }

	xmdProcCpuacc OBJECT-TYPE
		SYNTAX INTEGER
		ACCESS read-only
		STATUS mandatory
		DESCRIPTION
			"CPU time in milliseconds in life of process"
		::= { xmdProcEntry 8 }

	xmdProcCpupct OBJECT-TYPE
		SYNTAX INTEGER
		ACCESS read-only
		STATUS mandatory
		DESCRIPTION
			"CPU time in percent in interval"
		::= { xmdProcEntry 9 }

	xmdProcUsercpu OBJECT-TYPE
		SYNTAX Counter
		ACCESS read-only
		STATUS mandatory
		DESCRIPTION
			"Process CPU use in user mode (percent)"
		::= { xmdProcEntry 10 }

	xmdProcKerncpu OBJECT-TYPE
		SYNTAX Counter
		ACCESS read-only
		STATUS mandatory
		DESCRIPTION
			"Process CPU use in kernel mode (percent)"
		::= { xmdProcEntry 11 }

	xmdProcWorkmem OBJECT-TYPE
		SYNTAX INTEGER
		ACCESS read-only
		STATUS mandatory
		DESCRIPTION
			"Physical memory used by process private data (4K pages)"
		::= { xmdProcEntry 12 }

	xmdProcCodemem OBJECT-TYPE
		SYNTAX INTEGER
		ACCESS read-only
		STATUS mandatory
		DESCRIPTION
			"Physical memory used by process code (4K pages)"
		::= { xmdProcEntry 13 }

	xmdProcPagsp OBJECT-TYPE
		SYNTAX INTEGER
		ACCESS read-only
		STATUS mandatory
		DESCRIPTION
			"Page space used by process private data (4K pages)"
		::= { xmdProcEntry 14 }

	xmdProcNsignals OBJECT-TYPE
		SYNTAX Counter
		ACCESS read-only
		STATUS mandatory
		DESCRIPTION
			"Signals received by process"
		::= { xmdProcEntry 15 }

	xmdProcNvcsw OBJECT-TYPE
		SYNTAX Counter
		ACCESS read-only
		STATUS mandatory
		DESCRIPTION
			"Voluntary context switches by process"
		::= { xmdProcEntry 16 }

	xmdProcTsize OBJECT-TYPE
		SYNTAX INTEGER
		ACCESS read-only
		STATUS mandatory
		DESCRIPTION
			"Code size (bytes)"
		::= { xmdProcEntry 17 }

	xmdProcMaxrss OBJECT-TYPE
		SYNTAX INTEGER
		ACCESS read-only
		STATUS mandatory
		DESCRIPTION
			"Maximum code+data resident set size (4K pages)"
		::= { xmdProcEntry 18 }

	xmdProcPswitch OBJECT-TYPE
		SYNTAX Counter
		ACCESS read-only
		STATUS mandatory
		DESCRIPTION
			"Process context switches"
		::= { xmdProc 11 }

	xmdProcRunque OBJECT-TYPE
		SYNTAX INTEGER
		ACCESS read-only
		STATUS mandatory
		DESCRIPTION
			"Average count of processes that are waiting for the cpu"
		::= { xmdProc 12 }

	xmdProcRunocc OBJECT-TYPE
		SYNTAX INTEGER
		ACCESS read-only
		STATUS mandatory
		DESCRIPTION
			"Number of samplings of runque"
		::= { xmdProc 13 }

	xmdProcSwpque OBJECT-TYPE
		SYNTAX INTEGER
		ACCESS read-only
		STATUS mandatory
		DESCRIPTION
			"Average count of processes waiting to be paged in"
		::= { xmdProc 14 }

	xmdProcSwpocc OBJECT-TYPE
		SYNTAX INTEGER
		ACCESS read-only
		STATUS mandatory
		DESCRIPTION
			"Number of samplings of swpque"
		::= { xmdProc 15 }

	xmdProcKsched OBJECT-TYPE
		SYNTAX Counter
		ACCESS read-only
		STATUS mandatory
		DESCRIPTION
			"Number of kernel process creations"
		::= { xmdProc 16 }

	xmdProcKexit OBJECT-TYPE
		SYNTAX Counter
		ACCESS read-only
		STATUS mandatory
		DESCRIPTION
			"Number of kernel process exits"
		::= { xmdProc 17 }

	xmdSyscall OBJECT IDENTIFIER ::= { xmd 7 }

	xmdSyscallTotal OBJECT-TYPE
		SYNTAX Counter
		ACCESS read-only
		STATUS mandatory
		DESCRIPTION
			"Total system calls"
		::= { xmdSyscall 1 }

	xmdSyscallRead OBJECT-TYPE
		SYNTAX Counter
		ACCESS read-only
		STATUS mandatory
		DESCRIPTION
			"Read system calls"
		::= { xmdSyscall 2 }

	xmdSyscallWrite OBJECT-TYPE
		SYNTAX Counter
		ACCESS read-only
		STATUS mandatory
		DESCRIPTION
			"Write system calls"
		::= { xmdSyscall 3 }

	xmdSyscallFork OBJECT-TYPE
		SYNTAX Counter
		ACCESS read-only
		STATUS mandatory
		DESCRIPTION
			"Fork system calls"
		::= { xmdSyscall 4 }

	xmdSyscallExec OBJECT-TYPE
		SYNTAX Counter
		ACCESS read-only
		STATUS mandatory
		DESCRIPTION
			"Exec system calls"
		::= { xmdSyscall 5 }

	xmdSysIO OBJECT IDENTIFIER ::= { xmd 8 }

	xmdSysIOReadch OBJECT-TYPE
		SYNTAX Counter
		ACCESS read-only
		STATUS mandatory
		DESCRIPTION
			"Bytes read through the read sys call"
		::= { xmdSysIO 1 }

	xmdSysIOReadchkb OBJECT-TYPE
		SYNTAX Counter
		ACCESS read-only
		STATUS mandatory
		DESCRIPTION
			"KBytes read through the read sys call"
		::= { xmdSysIO 12 }

	xmdSysIOWritech OBJECT-TYPE
		SYNTAX Counter
		ACCESS read-only
		STATUS mandatory
		DESCRIPTION
			"Bytes written through the write sys call"
		::= { xmdSysIO 2 }

	xmdSysIOWritechkb OBJECT-TYPE
		SYNTAX Counter
		ACCESS read-only
		STATUS mandatory
		DESCRIPTION
			"KBytes written through the write sys call"
		::= { xmdSysIO 13 }

	xmdSysIOLbread OBJECT-TYPE
		SYNTAX Counter
		ACCESS read-only
		STATUS mandatory
		DESCRIPTION
			"Logical reads from a block device via buffer cache"
		::= { xmdSysIO 3 }

	xmdSysIOLbwrite OBJECT-TYPE
		SYNTAX Counter
		ACCESS read-only
		STATUS mandatory
		DESCRIPTION
			"Logical writes to a block device via buffer cache"
		::= { xmdSysIO 4 }

	xmdSysIOBread OBJECT-TYPE
		SYNTAX Counter
		ACCESS read-only
		STATUS mandatory
		DESCRIPTION
			"Physical 4K reads from a block device to buffer cache"
		::= { xmdSysIO 5 }

	xmdSysIOBwrite OBJECT-TYPE
		SYNTAX Counter
		ACCESS read-only
		STATUS mandatory
		DESCRIPTION
			"Physical 4K writes to a block device from buffer cache"
		::= { xmdSysIO 6 }

	xmdSysIOPhread OBJECT-TYPE
		SYNTAX Counter
		ACCESS read-only
		STATUS mandatory
		DESCRIPTION
			"Physical reads directly from a raw device"
		::= { xmdSysIO 7 }

	xmdSysIOPhwrite OBJECT-TYPE
		SYNTAX Counter
		ACCESS read-only
		STATUS mandatory
		DESCRIPTION
			"Physical writes directly to a raw device"
		::= { xmdSysIO 8 }

	xmdSysIOTtyraw OBJECT-TYPE
		SYNTAX Counter
		ACCESS read-only
		STATUS mandatory
		DESCRIPTION
			"Raw characters read from TTYs"
		::= { xmdSysIO 9 }

	xmdSysIOTtycan OBJECT-TYPE
		SYNTAX Counter
		ACCESS read-only
		STATUS mandatory
		DESCRIPTION
			"Processed characters read from TTYs"
		::= { xmdSysIO 10 }

	xmdSysIOTtyout OBJECT-TYPE
		SYNTAX Counter
		ACCESS read-only
		STATUS mandatory
		DESCRIPTION
			"Characters written to TTYs"
		::= { xmdSysIO 11 }

	xmdIPC OBJECT IDENTIFIER ::= { xmd 9 }

	xmdIPCMsg OBJECT IDENTIFIER ::= { xmdIPC 1 }

	xmdIPCMsgMsgmax OBJECT-TYPE
		SYNTAX INTEGER
		ACCESS read-only
		STATUS mandatory
		DESCRIPTION
			"Max message size"
		::= { xmdIPCMsg 1 }

	xmdIPCMsgQuemax OBJECT-TYPE
		SYNTAX INTEGER
		ACCESS read-only
		STATUS mandatory
		DESCRIPTION
			"Max number of bytes on queue"
		::= { xmdIPCMsg 2 }

	xmdIPCMsgQueids OBJECT-TYPE
		SYNTAX INTEGER
		ACCESS read-only
		STATUS mandatory
		DESCRIPTION
			"Number of message queue identifiers"
		::= { xmdIPCMsg 3 }

	xmdIPCMsgIdmax OBJECT-TYPE
		SYNTAX INTEGER
		ACCESS read-only
		STATUS mandatory
		DESCRIPTION
			"Max number of messages per queue id"
		::= { xmdIPCMsg 4 }

	xmdIPCSem OBJECT IDENTIFIER ::= { xmdIPC 2 }

	xmdIPCSemSemids OBJECT-TYPE
		SYNTAX INTEGER
		ACCESS read-only
		STATUS mandatory
		DESCRIPTION
			"Number of semaphore ids"
		::= { xmdIPCSem 1 }

	xmdIPCSemMaxsems OBJECT-TYPE
		SYNTAX INTEGER
		ACCESS read-only
		STATUS mandatory
		DESCRIPTION
			"Max number of semaphores per id"
		::= { xmdIPCSem 2 }

	xmdIPCSemMaxops OBJECT-TYPE
		SYNTAX INTEGER
		ACCESS read-only
		STATUS mandatory
		DESCRIPTION
			"Max number of operations per semop call"
		::= { xmdIPCSem 3 }

	xmdIPCSemMaxundo OBJECT-TYPE
		SYNTAX INTEGER
		ACCESS read-only
		STATUS mandatory
		DESCRIPTION
			"Max number of undo entries per process"
		::= { xmdIPCSem 4 }

	xmdIPCSemUndosiz OBJECT-TYPE
		SYNTAX INTEGER
		ACCESS read-only
		STATUS mandatory
		DESCRIPTION
			"Size in bytes of undo structure"
		::= { xmdIPCSem 5 }

	xmdIPCSemSemmaxv OBJECT-TYPE
		SYNTAX INTEGER
		ACCESS read-only
		STATUS mandatory
		DESCRIPTION
			"Semaphore maximum value"
		::= { xmdIPCSem 6 }

	xmdIPCSemSemmaxe OBJECT-TYPE
		SYNTAX INTEGER
		ACCESS read-only
		STATUS mandatory
		DESCRIPTION
			"Adjust on exit maximum value"
		::= { xmdIPCSem 7 }

	xmdIPCShm OBJECT IDENTIFIER ::= { xmdIPC 3 }

	xmdIPCShmShmmax OBJECT-TYPE
		SYNTAX INTEGER
		ACCESS read-only
		STATUS mandatory
		DESCRIPTION
			"Max shared memory segment size"
		::= { xmdIPCShm 1 }

	xmdIPCShmShmmin OBJECT-TYPE
		SYNTAX INTEGER
		ACCESS read-only
		STATUS mandatory
		DESCRIPTION
			"Min shared memory segment size"
		::= { xmdIPCShm 2 }

	xmdIPCShmShmids OBJECT-TYPE
		SYNTAX INTEGER
		ACCESS read-only
		STATUS mandatory
		DESCRIPTION
			"Number of shared memory identifiers"
		::= { xmdIPCShm 3 }

	xmdIPCLocks OBJECT IDENTIFIER ::= { xmdIPC 4 }

	xmdIPCLocksNumrecs OBJECT-TYPE
		SYNTAX INTEGER
		ACCESS read-only
		STATUS mandatory
		DESCRIPTION
			"Number of records configured in system"
		::= { xmdIPCLocks 1 }

	xmdIPCLocksRecsused OBJECT-TYPE
		SYNTAX INTEGER
		ACCESS read-only
		STATUS mandatory
		DESCRIPTION
			"Number of records currently in use"
		::= { xmdIPCLocks 2 }

	xmdIPCLocksOverrun OBJECT-TYPE
		SYNTAX INTEGER
		ACCESS read-only
		STATUS mandatory
		DESCRIPTION
			"Number of times system ran out of record locks"
		::= { xmdIPCLocks 3 }

	xmdIPCLocksRecstot OBJECT-TYPE
		SYNTAX INTEGER
		ACCESS read-only
		STATUS mandatory
		DESCRIPTION
			"Number records used since system boot"
		::= { xmdIPCLocks 4 }

	xmdIPCLocksRecsync OBJECT-TYPE
		SYNTAX INTEGER
		ACCESS read-only
		STATUS mandatory
		DESCRIPTION
			"Number records reserved for sync mode change"
		::= { xmdIPCLocks 5 }

	xmdFS OBJECT-TYPE
		SYNTAX SEQUENCE OF XmdFSEntry
		ACCESS not-accessible
		STATUS mandatory
		DESCRIPTION
			"File system statistics"
		::= { xmd 10 }

	xmdFSEntry OBJECT-TYPE
		SYNTAX XmdFSEntry
		ACCESS not-accessible
		STATUS mandatory
		DESCRIPTION
			"Element of above table"
		::= { xmdFS 1 }

	XmdFSEntry ::=
		SEQUENCE
		{
		   xmdFSIndex INTEGER,
		   xmdFSInstName DisplayString,
		   xmdFSFree INTEGER,
		   xmdFSPpsize INTEGER,
		   xmdFSLvcount INTEGER,
		   xmdFSPvcount INTEGER
		}

	xmdFSIndex OBJECT-TYPE
		SYNTAX INTEGER
		ACCESS read-only
		STATUS mandatory
		DESCRIPTION
			"Index Number"
		::= { xmdFSEntry 1 }

	xmdFSInstName OBJECT-TYPE
		SYNTAX DisplayString
		ACCESS read-only
		STATUS mandatory
		DESCRIPTION
			"Instance Name"
		::= { xmdFSEntry 2 }

	xmdFSFree OBJECT-TYPE
		SYNTAX INTEGER
		ACCESS read-only
		STATUS mandatory
		DESCRIPTION
			"Free space in volume group, MB"
		::= { xmdFSEntry 3 }

	xmdFSPpsize OBJECT-TYPE
		SYNTAX INTEGER
		ACCESS read-only
		STATUS mandatory
		DESCRIPTION
			"Physical partition size"
		::= { xmdFSEntry 4 }

	xmdFSLvcount OBJECT-TYPE
		SYNTAX INTEGER
		ACCESS read-only
		STATUS mandatory
		DESCRIPTION
			"Number of logical volumes in VG"
		::= { xmdFSEntry 5 }

	xmdFSPvcount OBJECT-TYPE
		SYNTAX INTEGER
		ACCESS read-only
		STATUS mandatory
		DESCRIPTION
			"Number of physical volumes in VG"
		::= { xmdFSEntry 6 }

	xmdFSIget OBJECT-TYPE
		SYNTAX Counter
		ACCESS read-only
		STATUS mandatory
		DESCRIPTION
			"Calls to inode lookup routines"
		::= { xmdFS 11 }

	xmdFSNamei OBJECT-TYPE
		SYNTAX Counter
		ACCESS read-only
		STATUS mandatory
		DESCRIPTION
			"Calls to pathname lookup routine"
		::= { xmdFS 12 }

	xmdFSDirblk OBJECT-TYPE
		SYNTAX Counter
		ACCESS read-only
		STATUS mandatory
		DESCRIPTION
			"Directory blocks scanned by directory search routine"
		::= { xmdFS 13 }

	xmdIP OBJECT IDENTIFIER ::= { xmd 11 }

	xmdIPRcvtotal OBJECT-TYPE
		SYNTAX Counter
		ACCESS read-only
		STATUS mandatory
		DESCRIPTION
			"Total IP packets received"
		::= { xmdIP 1 }

	xmdIPRcvfrag OBJECT-TYPE
		SYNTAX Counter
		ACCESS read-only
		STATUS mandatory
		DESCRIPTION
			"IP fragments received"
		::= { xmdIP 2 }

	xmdIPForward OBJECT-TYPE
		SYNTAX Counter
		ACCESS read-only
		STATUS mandatory
		DESCRIPTION
			"IP packets forwarded"
		::= { xmdIP 3 }

	xmdIPRcvdgrm OBJECT-TYPE
		SYNTAX Counter
		ACCESS read-only
		STATUS mandatory
		DESCRIPTION
			"Successfully received IP datagrams"
		::= { xmdIP 4 }

	xmdIPSnddgrm OBJECT-TYPE
		SYNTAX Counter
		ACCESS read-only
		STATUS mandatory
		DESCRIPTION
			"Transmitted IP datagrams"
		::= { xmdIP 5 }

	xmdIPReasmok OBJECT-TYPE
		SYNTAX Counter
		ACCESS read-only
		STATUS mandatory
		DESCRIPTION
			"Total packets reassembled OK"
		::= { xmdIP 6 }

	xmdIPFragok OBJECT-TYPE
		SYNTAX Counter
		ACCESS read-only
		STATUS mandatory
		DESCRIPTION
			"Output packets fragmented OK"
		::= { xmdIP 7 }

	xmdIPNetIF OBJECT-TYPE
		SYNTAX SEQUENCE OF XmdIPNetIFEntry
		ACCESS not-accessible
		STATUS mandatory
		DESCRIPTION
			"IP interface statistics"
		::= { xmdIP 10 }

	xmdIPNetIFEntry OBJECT-TYPE
		SYNTAX XmdIPNetIFEntry
		ACCESS not-accessible
		STATUS mandatory
		DESCRIPTION
			"Element of above table"
		::= { xmdIPNetIF 1 }

	XmdIPNetIFEntry ::=
		SEQUENCE
		{
		   xmdIPNetIFIndex INTEGER,
		   xmdIPNetIFInstName DisplayString,
		   xmdIPNetIFIpacket Counter,
		   xmdIPNetIFIoctet Counter,
		   xmdIPNetIFIoctetkb Counter,
		   xmdIPNetIFIerror Counter,
		   xmdIPNetIFImcastpkt Counter,
		   xmdIPNetIFIqdrop Counter,
		   xmdIPNetIFIunknproto Counter,
		   xmdIPNetIFOpacket Counter,
		   xmdIPNetIFOoctet Counter,
		   xmdIPNetIFOoctetkb Counter,
		   xmdIPNetIFOerror Counter,
		   xmdIPNetIFOmcastpkt Counter,
		   xmdIPNetIFOquelen INTEGER,
		   xmdIPNetIFOquemax INTEGER,
		   xmdIPNetIFOdrops INTEGER
		}

	xmdIPNetIFIndex OBJECT-TYPE
		SYNTAX INTEGER
		ACCESS read-only
		STATUS mandatory
		DESCRIPTION
			"Index Number"
		::= { xmdIPNetIFEntry 1 }

	xmdIPNetIFInstName OBJECT-TYPE
		SYNTAX DisplayString
		ACCESS read-only
		STATUS mandatory
		DESCRIPTION
			"Instance Name"
		::= { xmdIPNetIFEntry 2 }

	xmdIPNetIFIpacket OBJECT-TYPE
		SYNTAX Counter
		ACCESS read-only
		STATUS mandatory
		DESCRIPTION
			"Packets received"
		::= { xmdIPNetIFEntry 3 }

	xmdIPNetIFIoctet OBJECT-TYPE
		SYNTAX Counter
		ACCESS read-only
		STATUS mandatory
		DESCRIPTION
			"Bytes received"
		::= { xmdIPNetIFEntry 4 }

	xmdIPNetIFIoctetkb OBJECT-TYPE
		SYNTAX Counter
		ACCESS read-only
		STATUS mandatory
		DESCRIPTION
			"KBytes received"
		::= { xmdIPNetIFEntry 5 }

	xmdIPNetIFIerror OBJECT-TYPE
		SYNTAX Counter
		ACCESS read-only
		STATUS mandatory
		DESCRIPTION
			"Input errors"
		::= { xmdIPNetIFEntry 6 }

	xmdIPNetIFImcastpkt OBJECT-TYPE
		SYNTAX Counter
		ACCESS read-only
		STATUS mandatory
		DESCRIPTION
			"Multicast packets received"
		::= { xmdIPNetIFEntry 7 }

	xmdIPNetIFIqdrop OBJECT-TYPE
		SYNTAX Counter
		ACCESS read-only
		STATUS mandatory
		DESCRIPTION
			"Input packets dropped"
		::= { xmdIPNetIFEntry 8 }

	xmdIPNetIFIunknproto OBJECT-TYPE
		SYNTAX Counter
		ACCESS read-only
		STATUS mandatory
		DESCRIPTION
			"Packets received with unknown protocol"
		::= { xmdIPNetIFEntry 9 }

	xmdIPNetIFOpacket OBJECT-TYPE
		SYNTAX Counter
		ACCESS read-only
		STATUS mandatory
		DESCRIPTION
			"Packets transmitted"
		::= { xmdIPNetIFEntry 10 }

	xmdIPNetIFOoctet OBJECT-TYPE
		SYNTAX Counter
		ACCESS read-only
		STATUS mandatory
		DESCRIPTION
			"Bytes transmitted"
		::= { xmdIPNetIFEntry 11 }

	xmdIPNetIFOoctetkb OBJECT-TYPE
		SYNTAX Counter
		ACCESS read-only
		STATUS mandatory
		DESCRIPTION
			"KBytes transmitted"
		::= { xmdIPNetIFEntry 12 }

	xmdIPNetIFOerror OBJECT-TYPE
		SYNTAX Counter
		ACCESS read-only
		STATUS mandatory
		DESCRIPTION
			"Output errors"
		::= { xmdIPNetIFEntry 13 }

	xmdIPNetIFOmcastpkt OBJECT-TYPE
		SYNTAX Counter
		ACCESS read-only
		STATUS mandatory
		DESCRIPTION
			"Multicast packets transmitted"
		::= { xmdIPNetIFEntry 14 }

	xmdIPNetIFOquelen OBJECT-TYPE
		SYNTAX INTEGER
		ACCESS read-only
		STATUS mandatory
		DESCRIPTION
			"Number of packets in transmit queue"
		::= { xmdIPNetIFEntry 15 }

	xmdIPNetIFOquemax OBJECT-TYPE
		SYNTAX INTEGER
		ACCESS read-only
		STATUS mandatory
		DESCRIPTION
			"Maximum number of packets in transmit queue"
		::= { xmdIPNetIFEntry 16 }

	xmdIPNetIFOdrops OBJECT-TYPE
		SYNTAX Counter
		ACCESS read-only
		STATUS mandatory
		DESCRIPTION
			"Number of packets dropped from transmit queue"
		::= { xmdIPNetIFEntry 17 }

	xmdIPRouting OBJECT IDENTIFIER ::= { xmdIP 11 }

	xmdIPRoutingBadred OBJECT-TYPE
		SYNTAX Counter
		ACCESS read-only
		STATUS mandatory
		DESCRIPTION
			"Bogus redirect calls"
		::= { xmdIPRouting 1 }

	xmdIPRoutingDynamic OBJECT-TYPE
		SYNTAX Counter
		ACCESS read-only
		STATUS mandatory
		DESCRIPTION
			"Routes created by redirects"
		::= { xmdIPRouting 2 }

	xmdIPRoutingNewgate OBJECT-TYPE
		SYNTAX Counter
		ACCESS read-only
		STATUS mandatory
		DESCRIPTION
			"Routes modified by redirects"
		::= { xmdIPRouting 3 }

	xmdIPRoutingUnreach OBJECT-TYPE
		SYNTAX Counter
		ACCESS read-only
		STATUS mandatory
		DESCRIPTION
			"Lookups which failed"
		::= { xmdIPRouting 4 }

	xmdIPRoutingWildc OBJECT-TYPE
		SYNTAX Counter
		ACCESS read-only
		STATUS mandatory
		DESCRIPTION
			"Lookups satisfied by a wildcard"
		::= { xmdIPRouting 5 }

	xmdTCP OBJECT IDENTIFIER ::= { xmd 12 }

	xmdTCPConattmpt OBJECT-TYPE
		SYNTAX Counter
		ACCESS read-only
		STATUS mandatory
		DESCRIPTION
			"TCP connections initiated"
		::= { xmdTCP 1 }

	xmdTCPAccept OBJECT-TYPE
		SYNTAX Counter
		ACCESS read-only
		STATUS mandatory
		DESCRIPTION
			"TCP connections accepted"
		::= { xmdTCP 2 }

	xmdTCPConnects OBJECT-TYPE
		SYNTAX Counter
		ACCESS read-only
		STATUS mandatory
		DESCRIPTION
			"Total TCP connections established"
		::= { xmdTCP 3 }

	xmdTCPClose OBJECT-TYPE
		SYNTAX Counter
		ACCESS read-only
		STATUS mandatory
		DESCRIPTION
			"TCP connections closed"
		::= { xmdTCP 4 }

	xmdTCPSndtotal OBJECT-TYPE
		SYNTAX Counter
		ACCESS read-only
		STATUS mandatory
		DESCRIPTION
			"Total TCP packets sent"
		::= { xmdTCP 5 }

	xmdTCPSndpack OBJECT-TYPE
		SYNTAX Counter
		ACCESS read-only
		STATUS mandatory
		DESCRIPTION
			"TCP data packets sent"
		::= { xmdTCP 6 }

	xmdTCPSndbyte OBJECT-TYPE
		SYNTAX Counter
		ACCESS read-only
		STATUS mandatory
		DESCRIPTION
			"TCP data bytes sent"
		::= { xmdTCP 7 }

	xmdTCPSndkbyte OBJECT-TYPE
		SYNTAX Counter
		ACCESS read-only
		STATUS mandatory
		DESCRIPTION
			"TCP data Kbytes sent"
		::= { xmdTCP 44 }

	xmdTCPSndrexmitpack OBJECT-TYPE
		SYNTAX Counter
		ACCESS read-only
		STATUS mandatory
		DESCRIPTION
			"TCP data packets retransmitted"
		::= { xmdTCP 8 }

	xmdTCPSndrexmitbyte OBJECT-TYPE
		SYNTAX Counter
		ACCESS read-only
		STATUS mandatory
		DESCRIPTION
			"TCP data bytes retransmitted"
		::= { xmdTCP 9 }

	xmdTCPSndack OBJECT-TYPE
		SYNTAX Counter
		ACCESS read-only
		STATUS mandatory
		DESCRIPTION
			"TCP ack-only packets sent"
		::= { xmdTCP 10 }

	xmdTCPSndprobe OBJECT-TYPE
		SYNTAX Counter
		ACCESS read-only
		STATUS mandatory
		DESCRIPTION
			"TCP window probes sent"
		::= { xmdTCP 11 }

	xmdTCPSndurg OBJECT-TYPE
		SYNTAX Counter
		ACCESS read-only
		STATUS mandatory
		DESCRIPTION
			"TCP packets sent with URG only"
		::= { xmdTCP 12 }

	xmdTCPSndwinup OBJECT-TYPE
		SYNTAX Counter
		ACCESS read-only
		STATUS mandatory
		DESCRIPTION
			"TCP window update-only packets sent"
		::= { xmdTCP 13 }

	xmdTCPSndctrl OBJECT-TYPE
		SYNTAX Counter
		ACCESS read-only
		STATUS mandatory
		DESCRIPTION
			"TCP control (SYN|FIN|RST) packets sent"
		::= { xmdTCP 14 }

	xmdTCPRcvtotal OBJECT-TYPE
		SYNTAX Counter
		ACCESS read-only
		STATUS mandatory
		DESCRIPTION
			"TCP total packets received"
		::= { xmdTCP 15 }

	xmdTCPRcvpack OBJECT-TYPE
		SYNTAX Counter
		ACCESS read-only
		STATUS mandatory
		DESCRIPTION
			"TCP data packets received in sequence"
		::= { xmdTCP 16 }

	xmdTCPRcvbyte OBJECT-TYPE
		SYNTAX Counter
		ACCESS read-only
		STATUS mandatory
		DESCRIPTION
			"TCP data bytes received in sequence"
		::= { xmdTCP 17 }

	xmdTCPRcvkbyte OBJECT-TYPE
		SYNTAX Counter
		ACCESS read-only
		STATUS mandatory
		DESCRIPTION
			"TCP data Kbytes received in sequence"
		::= { xmdTCP 45 }

	xmdTCPRcvduppack OBJECT-TYPE
		SYNTAX Counter
		ACCESS read-only
		STATUS mandatory
		DESCRIPTION
			"TCP duplicate-only packets received"
		::= { xmdTCP 18 }

	xmdTCPRcvdupbyte OBJECT-TYPE
		SYNTAX Counter
		ACCESS read-only
		STATUS mandatory
		DESCRIPTION
			"TCP duplicate-only bytes received"
		::= { xmdTCP 19 }

	xmdTCPRcvpartduppack OBJECT-TYPE
		SYNTAX Counter
		ACCESS read-only
		STATUS mandatory
		DESCRIPTION
			"TCP partially duplicate packets received"
		::= { xmdTCP 20 }

	xmdTCPRcvpartdupbyte OBJECT-TYPE
		SYNTAX Counter
		ACCESS read-only
		STATUS mandatory
		DESCRIPTION
			"TCP partially duplicate bytes received"
		::= { xmdTCP 21 }

	xmdTCPRcvoopack OBJECT-TYPE
		SYNTAX Counter
		ACCESS read-only
		STATUS mandatory
		DESCRIPTION
			"TCP out-of-order packets received"
		::= { xmdTCP 22 }

	xmdTCPRcvoobyte OBJECT-TYPE
		SYNTAX Counter
		ACCESS read-only
		STATUS mandatory
		DESCRIPTION
			"TCP out-of-order bytes received"
		::= { xmdTCP 23 }

	xmdTCPRcvaftwinpack OBJECT-TYPE
		SYNTAX Counter
		ACCESS read-only
		STATUS mandatory
		DESCRIPTION
			"TCP packets received with after window data"
		::= { xmdTCP 24 }

	xmdTCPRcvaftwinbyte OBJECT-TYPE
		SYNTAX Counter
		ACCESS read-only
		STATUS mandatory
		DESCRIPTION
			"TCP bytes received after window"
		::= { xmdTCP 25 }

	xmdTCPRcvwinprobe OBJECT-TYPE
		SYNTAX Counter
		ACCESS read-only
		STATUS mandatory
		DESCRIPTION
			"TCP window-probe packets received"
		::= { xmdTCP 26 }

	xmdTCPRcvdupack OBJECT-TYPE
		SYNTAX Counter
		ACCESS read-only
		STATUS mandatory
		DESCRIPTION
			"TCP duplicate acks received"
		::= { xmdTCP 27 }

	xmdTCPRcvackpack OBJECT-TYPE
		SYNTAX Counter
		ACCESS read-only
		STATUS mandatory
		DESCRIPTION
			"TCP ack packets received"
		::= { xmdTCP 28 }

	xmdTCPRcvackbyte OBJECT-TYPE
		SYNTAX Counter
		ACCESS read-only
		STATUS mandatory
		DESCRIPTION
			"TCP bytes acknowledged by received acks"
		::= { xmdTCP 29 }

	xmdTCPRcvwinup OBJECT-TYPE
		SYNTAX Counter
		ACCESS read-only
		STATUS mandatory
		DESCRIPTION
			"TCP window update packets received"
		::= { xmdTCP 30 }

	xmdUDP OBJECT IDENTIFIER ::= { xmd 13 }

	xmdUDPRcvdgrm OBJECT-TYPE
		SYNTAX Counter
		ACCESS read-only
		STATUS mandatory
		DESCRIPTION
			"UDP packets received"
		::= { xmdUDP 1 }

	xmdUDPNoport OBJECT-TYPE
		SYNTAX Counter
		ACCESS read-only
		STATUS mandatory
		DESCRIPTION
			"No socket on port"
		::= { xmdUDP 2 }

	xmdUDPFullsock OBJECT-TYPE
		SYNTAX Counter
		ACCESS read-only
		STATUS mandatory
		DESCRIPTION
			"UDP packets not delivered, input socket full"
		::= { xmdUDP 3 }

	xmdUDPSnddgrm OBJECT-TYPE
		SYNTAX Counter
		ACCESS read-only
		STATUS mandatory
		DESCRIPTION
			"UDP packets sent"
		::= { xmdUDP 4 }

	xmdUDPNoportbc OBJECT-TYPE
		SYNTAX Counter
		ACCESS read-only
		STATUS mandatory
		DESCRIPTION
			"No socket on port for broadcast"
		::= { xmdUDP 5 }

	xmdUDPHdrops OBJECT-TYPE
		SYNTAX Counter
		ACCESS read-only
		STATUS mandatory
		DESCRIPTION
			"Packets shorter than header"
		::= { xmdUDP 6 }

	xmdUDPBadsum OBJECT-TYPE
		SYNTAX Counter
		ACCESS read-only
		STATUS mandatory
		DESCRIPTION
			"Packets with checksum error"
		::= { xmdUDP 7 }

	xmdUDPBadlen OBJECT-TYPE
		SYNTAX Counter
		ACCESS read-only
		STATUS mandatory
		DESCRIPTION
			"Packets where data length larger than packet"
		::= { xmdUDP 8 }

	xmdUDPCachmiss OBJECT-TYPE
		SYNTAX Counter
		ACCESS read-only
		STATUS mandatory
		DESCRIPTION
			"Input packets missing pcb cache"
		::= { xmdUDP 9 }

	xmdRTime OBJECT IDENTIFIER ::= { xmd 14 }

	xmdRTimeLAN OBJECT IDENTIFIER ::= { xmdRTime 1 }

	xmdRTimeARM OBJECT IDENTIFIER ::= { xmdRTime 2 }

	xmdRPC OBJECT IDENTIFIER ::= { xmd 16 }

	xmdRPCClntCo OBJECT IDENTIFIER ::= { xmdRPC 1 }

	xmdRPCClntCoCalls OBJECT-TYPE
		SYNTAX Counter
		ACCESS read-only
		STATUS mandatory
		DESCRIPTION
			"Total NFS client RPC calls"
		::= { xmdRPCClntCo 1 }

	xmdRPCClntCoBadcalls OBJECT-TYPE
		SYNTAX Counter
		ACCESS read-only
		STATUS mandatory
		DESCRIPTION
			"Rejected NFS client RPC calls"
		::= { xmdRPCClntCo 2 }

	xmdRPCClntCoBadxids OBJECT-TYPE
		SYNTAX Counter
		ACCESS read-only
		STATUS mandatory
		DESCRIPTION
			"Bad NFS client RPC call responses"
		::= { xmdRPCClntCo 4 }

	xmdRPCClntCoTimeouts OBJECT-TYPE
		SYNTAX Counter
		ACCESS read-only
		STATUS mandatory
		DESCRIPTION
			"Timed out NFS client RPC calls with no reply"
		::= { xmdRPCClntCo 5 }

	xmdRPCClntCoNewcreds OBJECT-TYPE
		SYNTAX Counter
		ACCESS read-only
		STATUS mandatory
		DESCRIPTION
			"Total NFS client RPC authentication refreshes"
		::= { xmdRPCClntCo 6 }

	xmdRPCClntCoBadverfs OBJECT-TYPE
		SYNTAX Counter
		ACCESS read-only
		STATUS mandatory
		DESCRIPTION
			"Total NFS client RPC bad verifier in response"
		::= { xmdRPCClntCo 7 }

	xmdRPCClntCoTimers OBJECT-TYPE
		SYNTAX Counter
		ACCESS read-only
		STATUS mandatory
		DESCRIPTION
			"NFS client RPC timout greater than timeout value "
		::= { xmdRPCClntCo 8 }

	xmdRPCClntCoCantconn OBJECT-TYPE
		SYNTAX Counter
		ACCESS read-only
		STATUS mandatory
		DESCRIPTION
			"Failed NFS client RPC calls"
		::= { xmdRPCClntCo 3 }

	xmdRPCClntCoNomem OBJECT-TYPE
		SYNTAX Counter
		ACCESS read-only
		STATUS mandatory
		DESCRIPTION
			"NFS client RPC calls memory allocation failure"
		::= { xmdRPCClntCo 9 }

	xmdRPCClntCoInterrupts OBJECT-TYPE
		SYNTAX Counter
		ACCESS read-only
		STATUS mandatory
		DESCRIPTION
			"NFS client RPC calls fail due to interrupt"
		::= { xmdRPCClntCo 10 }

	xmdRPCClntCl OBJECT IDENTIFIER ::= { xmdRPC 2 }

	xmdRPCClntClCalls OBJECT-TYPE
		SYNTAX Counter
		ACCESS read-only
		STATUS mandatory
		DESCRIPTION
			"Total NFS client RPC calls"
		::= { xmdRPCClntCl 1 }

	xmdRPCClntClBadcalls OBJECT-TYPE
		SYNTAX Counter
		ACCESS read-only
		STATUS mandatory
		DESCRIPTION
			"Rejected NFS client RPC calls"
		::= { xmdRPCClntCl 2 }

	xmdRPCClntClRetrans OBJECT-TYPE
		SYNTAX Counter
		ACCESS read-only
		STATUS mandatory
		DESCRIPTION
			"Retransmitted NFS client RPC calls"
		::= { xmdRPCClntCl 3 }

	xmdRPCClntClBadxids OBJECT-TYPE
		SYNTAX Counter
		ACCESS read-only
		STATUS mandatory
		DESCRIPTION
			"Bad NFS client RPC call responses"
		::= { xmdRPCClntCl 4 }

	xmdRPCClntClTimeouts OBJECT-TYPE
		SYNTAX Counter
		ACCESS read-only
		STATUS mandatory
		DESCRIPTION
			"Timed out NFS client RPC calls with no reply"
		::= { xmdRPCClntCl 5 }

	xmdRPCClntClNewcreds OBJECT-TYPE
		SYNTAX Counter
		ACCESS read-only
		STATUS mandatory
		DESCRIPTION
			"Total NFS client RPC authentication refreshes"
		::= { xmdRPCClntCl 6 }

	xmdRPCClntClBadverfs OBJECT-TYPE
		SYNTAX Counter
		ACCESS read-only
		STATUS mandatory
		DESCRIPTION
			"Total NFS client RPC bad verifier in response"
		::= { xmdRPCClntCl 7 }

	xmdRPCClntClTimers OBJECT-TYPE
		SYNTAX Counter
		ACCESS read-only
		STATUS mandatory
		DESCRIPTION
			"NFS client RPC timout greater than timeout value "
		::= { xmdRPCClntCl 8 }

	xmdRPCClntClNomem OBJECT-TYPE
		SYNTAX Counter
		ACCESS read-only
		STATUS mandatory
		DESCRIPTION
			"NFS client RPC calls memory allocation failure"
		::= { xmdRPCClntCl 9 }

	xmdRPCClntClCantsend OBJECT-TYPE
		SYNTAX Counter
		ACCESS read-only
		STATUS mandatory
		DESCRIPTION
			"NFS client RPC calls not sent"
		::= { xmdRPCClntCl 10 }

	xmdRPCSvrCo OBJECT IDENTIFIER ::= { xmdRPC 3 }

	xmdRPCSvrCoCalls OBJECT-TYPE
		SYNTAX Counter
		ACCESS read-only
		STATUS mandatory
		DESCRIPTION
			"Total NFS server RPC requests"
		::= { xmdRPCSvrCo 1 }

	xmdRPCSvrCoBadcalls OBJECT-TYPE
		SYNTAX Counter
		ACCESS read-only
		STATUS mandatory
		DESCRIPTION
			"Rejected NFS server RPC requests"
		::= { xmdRPCSvrCo 2 }

	xmdRPCSvrCoNullrecv OBJECT-TYPE
		SYNTAX Counter
		ACCESS read-only
		STATUS mandatory
		DESCRIPTION
			"NFS server RPC calls failed due to unavailable packet"
		::= { xmdRPCSvrCo 3 }

	xmdRPCSvrCoBadlen OBJECT-TYPE
		SYNTAX Counter
		ACCESS read-only
		STATUS mandatory
		DESCRIPTION
			"NFS server RPC requests failed due to bad length"
		::= { xmdRPCSvrCo 4 }

	xmdRPCSvrCoXdrcall OBJECT-TYPE
		SYNTAX Counter
		ACCESS read-only
		STATUS mandatory
		DESCRIPTION
			"NFS server RPC requests failed due to bad header"
		::= { xmdRPCSvrCo 5 }

	xmdRPCSvrCoDupchecks OBJECT-TYPE
		SYNTAX Counter
		ACCESS read-only
		STATUS mandatory
		DESCRIPTION
			"NFS server RPC calls found in request cache"
		::= { xmdRPCSvrCo 6 }

	xmdRPCSvrCoDupreqs OBJECT-TYPE
		SYNTAX Counter
		ACCESS read-only
		STATUS mandatory
		DESCRIPTION
			"Total NFS server RPC call duplicates"
		::= { xmdRPCSvrCo 7 }

	xmdRPCSvrCl OBJECT IDENTIFIER ::= { xmdRPC 4 }

	xmdRPCSvrClCalls OBJECT-TYPE
		SYNTAX Counter
		ACCESS read-only
		STATUS mandatory
		DESCRIPTION
			"Total NFS server RPC requests"
		::= { xmdRPCSvrCl 1 }

	xmdRPCSvrClBadcalls OBJECT-TYPE
		SYNTAX Counter
		ACCESS read-only
		STATUS mandatory
		DESCRIPTION
			"Rejected NFS server RPC requests"
		::= { xmdRPCSvrCl 2 }

	xmdRPCSvrClNullrecv OBJECT-TYPE
		SYNTAX Counter
		ACCESS read-only
		STATUS mandatory
		DESCRIPTION
			"NFS server RPC calls failed due to unavailable packet"
		::= { xmdRPCSvrCl 3 }

	xmdRPCSvrClBadlen OBJECT-TYPE
		SYNTAX Counter
		ACCESS read-only
		STATUS mandatory
		DESCRIPTION
			"NFS server RPC requests failed due to bad length"
		::= { xmdRPCSvrCl 4 }

	xmdRPCSvrClXdrcall OBJECT-TYPE
		SYNTAX Counter
		ACCESS read-only
		STATUS mandatory
		DESCRIPTION
			"NFS server RPC requests failed due to bad header"
		::= { xmdRPCSvrCl 5 }

	xmdRPCSvrClDupchecks OBJECT-TYPE
		SYNTAX Counter
		ACCESS read-only
		STATUS mandatory
		DESCRIPTION
			"NFS server RPC calls found in request cache"
		::= { xmdRPCSvrCl 6 }

	xmdRPCSvrClDupreqs OBJECT-TYPE
		SYNTAX Counter
		ACCESS read-only
		STATUS mandatory
		DESCRIPTION
			"Total NFS server RPC call duplicates"
		::= { xmdRPCSvrCl 7 }

	xmdNFS OBJECT IDENTIFIER ::= { xmd 17 }

	xmdNFSClient OBJECT IDENTIFIER ::= { xmdNFS 1 }

	xmdNFSClientCalls OBJECT-TYPE
		SYNTAX Counter
		ACCESS read-only
		STATUS mandatory
		DESCRIPTION
			"Total NFS client requests"
		::= { xmdNFSClient 1 }

	xmdNFSClientBadcalls OBJECT-TYPE
		SYNTAX Counter
		ACCESS read-only
		STATUS mandatory
		DESCRIPTION
			"NFS client failed calls"
		::= { xmdNFSClient 2 }

	xmdNFSServer OBJECT IDENTIFIER ::= { xmdNFS 2 }

	xmdNFSServerCalls OBJECT-TYPE
		SYNTAX Counter
		ACCESS read-only
		STATUS mandatory
		DESCRIPTION
			"Total NFS server requests"
		::= { xmdNFSServer 1 }

	xmdNFSServerBadcalls OBJECT-TYPE
		SYNTAX Counter
		ACCESS read-only
		STATUS mandatory
		DESCRIPTION
			"NFS server failed requests"
		::= { xmdNFSServer 2 }

	xmdNFSV2Clnt OBJECT IDENTIFIER ::= { xmdNFS 3 }

	xmdNFSV2ClntNull OBJECT-TYPE
		SYNTAX Counter
		ACCESS read-only
		STATUS mandatory
		DESCRIPTION
			"NFS server null requests"
		::= { xmdNFSV2Clnt 1 }

	xmdNFSV2ClntGetattr OBJECT-TYPE
		SYNTAX Counter
		ACCESS read-only
		STATUS mandatory
		DESCRIPTION
			"NFS server getattr requests"
		::= { xmdNFSV2Clnt 2 }

	xmdNFSV2ClntSetattr OBJECT-TYPE
		SYNTAX Counter
		ACCESS read-only
		STATUS mandatory
		DESCRIPTION
			"NFS server setattr requests"
		::= { xmdNFSV2Clnt 3 }

	xmdNFSV2ClntRoot OBJECT-TYPE
		SYNTAX Counter
		ACCESS read-only
		STATUS mandatory
		DESCRIPTION
			"NFS server root requests"
		::= { xmdNFSV2Clnt 4 }

	xmdNFSV2ClntLookup OBJECT-TYPE
		SYNTAX Counter
		ACCESS read-only
		STATUS mandatory
		DESCRIPTION
			"NFS server file name lookup requests"
		::= { xmdNFSV2Clnt 5 }

	xmdNFSV2ClntReadlink OBJECT-TYPE
		SYNTAX Counter
		ACCESS read-only
		STATUS mandatory
		DESCRIPTION
			"NFS server readlink requests"
		::= { xmdNFSV2Clnt 6 }

	xmdNFSV2ClntRead OBJECT-TYPE
		SYNTAX Counter
		ACCESS read-only
		STATUS mandatory
		DESCRIPTION
			"NFS server read requests"
		::= { xmdNFSV2Clnt 7 }

	xmdNFSV2ClntWrcache OBJECT-TYPE
		SYNTAX Counter
		ACCESS read-only
		STATUS mandatory
		DESCRIPTION
			"NFS server wrcache requests"
		::= { xmdNFSV2Clnt 8 }

	xmdNFSV2ClntWrite OBJECT-TYPE
		SYNTAX Counter
		ACCESS read-only
		STATUS mandatory
		DESCRIPTION
			"NFS server write requests"
		::= { xmdNFSV2Clnt 9 }

	xmdNFSV2ClntCreate OBJECT-TYPE
		SYNTAX Counter
		ACCESS read-only
		STATUS mandatory
		DESCRIPTION
			"NFS server file creation requests"
		::= { xmdNFSV2Clnt 10 }

	xmdNFSV2ClntRemove OBJECT-TYPE
		SYNTAX Counter
		ACCESS read-only
		STATUS mandatory
		DESCRIPTION
			"NFS server file removal requests"
		::= { xmdNFSV2Clnt 11 }

	xmdNFSV2ClntRename OBJECT-TYPE
		SYNTAX Counter
		ACCESS read-only
		STATUS mandatory
		DESCRIPTION
			"NFS server file rename requests"
		::= { xmdNFSV2Clnt 12 }

	xmdNFSV2ClntLink OBJECT-TYPE
		SYNTAX Counter
		ACCESS read-only
		STATUS mandatory
		DESCRIPTION
			"NFS server link creation requests"
		::= { xmdNFSV2Clnt 13 }

	xmdNFSV2ClntSymlink OBJECT-TYPE
		SYNTAX Counter
		ACCESS read-only
		STATUS mandatory
		DESCRIPTION
			"NFS server symbolic link creation requests"
		::= { xmdNFSV2Clnt 14 }

	xmdNFSV2ClntMkdir OBJECT-TYPE
		SYNTAX Counter
		ACCESS read-only
		STATUS mandatory
		DESCRIPTION
			"NFS server directory creation requests"
		::= { xmdNFSV2Clnt 15 }

	xmdNFSV2ClntRmdir OBJECT-TYPE
		SYNTAX Counter
		ACCESS read-only
		STATUS mandatory
		DESCRIPTION
			"NFS server directory removal requests"
		::= { xmdNFSV2Clnt 16 }

	xmdNFSV2ClntReaddir OBJECT-TYPE
		SYNTAX Counter
		ACCESS read-only
		STATUS mandatory
		DESCRIPTION
			"NFS server read-directory requests"
		::= { xmdNFSV2Clnt 17 }

	xmdNFSV2ClntStatfs OBJECT-TYPE
		SYNTAX Counter
		ACCESS read-only
		STATUS mandatory
		DESCRIPTION
			"NFS server file stat requests"
		::= { xmdNFSV2Clnt 18 }

	xmdNFSV2Svr OBJECT IDENTIFIER ::= { xmdNFS 4 }

	xmdNFSV2SvrNull OBJECT-TYPE
		SYNTAX Counter
		ACCESS read-only
		STATUS mandatory
		DESCRIPTION
			"NFS server null requests"
		::= { xmdNFSV2Svr 1 }

	xmdNFSV2SvrGetattr OBJECT-TYPE
		SYNTAX Counter
		ACCESS read-only
		STATUS mandatory
		DESCRIPTION
			"NFS server getattr requests"
		::= { xmdNFSV2Svr 2 }

	xmdNFSV2SvrSetattr OBJECT-TYPE
		SYNTAX Counter
		ACCESS read-only
		STATUS mandatory
		DESCRIPTION
			"NFS server setattr requests"
		::= { xmdNFSV2Svr 3 }

	xmdNFSV2SvrRoot OBJECT-TYPE
		SYNTAX Counter
		ACCESS read-only
		STATUS mandatory
		DESCRIPTION
			"NFS server root requests"
		::= { xmdNFSV2Svr 4 }

	xmdNFSV2SvrLookup OBJECT-TYPE
		SYNTAX Counter
		ACCESS read-only
		STATUS mandatory
		DESCRIPTION
			"NFS server file name lookup requests"
		::= { xmdNFSV2Svr 5 }

	xmdNFSV2SvrReadlink OBJECT-TYPE
		SYNTAX Counter
		ACCESS read-only
		STATUS mandatory
		DESCRIPTION
			"NFS server readlink requests"
		::= { xmdNFSV2Svr 6 }

	xmdNFSV2SvrRead OBJECT-TYPE
		SYNTAX Counter
		ACCESS read-only
		STATUS mandatory
		DESCRIPTION
			"NFS server read requests"
		::= { xmdNFSV2Svr 7 }

	xmdNFSV2SvrWrcache OBJECT-TYPE
		SYNTAX Counter
		ACCESS read-only
		STATUS mandatory
		DESCRIPTION
			"NFS server cache requests"
		::= { xmdNFSV2Svr 8 }

	xmdNFSV2SvrWrite OBJECT-TYPE
		SYNTAX Counter
		ACCESS read-only
		STATUS mandatory
		DESCRIPTION
			"NFS server write requests"
		::= { xmdNFSV2Svr 9 }

	xmdNFSV2SvrCreate OBJECT-TYPE
		SYNTAX Counter
		ACCESS read-only
		STATUS mandatory
		DESCRIPTION
			"NFS server file creation requests"
		::= { xmdNFSV2Svr 10 }

	xmdNFSV2SvrRemove OBJECT-TYPE
		SYNTAX Counter
		ACCESS read-only
		STATUS mandatory
		DESCRIPTION
			"NFS server file removal requests"
		::= { xmdNFSV2Svr 11 }

	xmdNFSV2SvrRename OBJECT-TYPE
		SYNTAX Counter
		ACCESS read-only
		STATUS mandatory
		DESCRIPTION
			"NFS server file rename requests"
		::= { xmdNFSV2Svr 12 }

	xmdNFSV2SvrLink OBJECT-TYPE
		SYNTAX Counter
		ACCESS read-only
		STATUS mandatory
		DESCRIPTION
			"NFS server link creation requests"
		::= { xmdNFSV2Svr 13 }

	xmdNFSV2SvrSymlink OBJECT-TYPE
		SYNTAX Counter
		ACCESS read-only
		STATUS mandatory
		DESCRIPTION
			"NFS server symbolic link creation requests"
		::= { xmdNFSV2Svr 14 }

	xmdNFSV2SvrMkdir OBJECT-TYPE
		SYNTAX Counter
		ACCESS read-only
		STATUS mandatory
		DESCRIPTION
			"NFS server directory creation requests"
		::= { xmdNFSV2Svr 15 }

	xmdNFSV2SvrRmdir OBJECT-TYPE
		SYNTAX Counter
		ACCESS read-only
		STATUS mandatory
		DESCRIPTION
			"NFS server directory removal requests"
		::= { xmdNFSV2Svr 16 }

	xmdNFSV2SvrReaddir OBJECT-TYPE
		SYNTAX Counter
		ACCESS read-only
		STATUS mandatory
		DESCRIPTION
			"NFS server read-directory requests"
		::= { xmdNFSV2Svr 17 }

	xmdNFSV2SvrStatfs OBJECT-TYPE
		SYNTAX Counter
		ACCESS read-only
		STATUS mandatory
		DESCRIPTION
			"NFS server file stat requests"
		::= { xmdNFSV2Svr 18 }

	xmdNFSV3Clnt OBJECT IDENTIFIER ::= { xmdNFS 5 }

	xmdNFSV3ClntNull OBJECT-TYPE
		SYNTAX Counter
		ACCESS read-only
		STATUS mandatory
		DESCRIPTION
			"NFS V3 client null requests"
		::= { xmdNFSV3Clnt 1 }

	xmdNFSV3ClntGetattr OBJECT-TYPE
		SYNTAX Counter
		ACCESS read-only
		STATUS mandatory
		DESCRIPTION
			"NFS V3 client getattr requests"
		::= { xmdNFSV3Clnt 2 }

	xmdNFSV3ClntSetattr OBJECT-TYPE
		SYNTAX Counter
		ACCESS read-only
		STATUS mandatory
		DESCRIPTION
			"NFS V3 client setattr requests"
		::= { xmdNFSV3Clnt 3 }

	xmdNFSV3ClntLookup OBJECT-TYPE
		SYNTAX Counter
		ACCESS read-only
		STATUS mandatory
		DESCRIPTION
			"NFS V3 client file name lookup requests"
		::= { xmdNFSV3Clnt 4 }

	xmdNFSV3ClntAccess OBJECT-TYPE
		SYNTAX Counter
		ACCESS read-only
		STATUS mandatory
		DESCRIPTION
			"NFS V3 client access requests"
		::= { xmdNFSV3Clnt 5 }

	xmdNFSV3ClntReadlink OBJECT-TYPE
		SYNTAX Counter
		ACCESS read-only
		STATUS mandatory
		DESCRIPTION
			"NFS V3 client readlink requests"
		::= { xmdNFSV3Clnt 6 }

	xmdNFSV3ClntRead OBJECT-TYPE
		SYNTAX Counter
		ACCESS read-only
		STATUS mandatory
		DESCRIPTION
			"NFS V3 client read requests"
		::= { xmdNFSV3Clnt 7 }

	xmdNFSV3ClntWrite OBJECT-TYPE
		SYNTAX Counter
		ACCESS read-only
		STATUS mandatory
		DESCRIPTION
			"NFS V3 client write requests"
		::= { xmdNFSV3Clnt 8 }

	xmdNFSV3ClntCreate OBJECT-TYPE
		SYNTAX Counter
		ACCESS read-only
		STATUS mandatory
		DESCRIPTION
			"NFS V3 client file creation requests"
		::= { xmdNFSV3Clnt 9 }

	xmdNFSV3ClntMkdir OBJECT-TYPE
		SYNTAX Counter
		ACCESS read-only
		STATUS mandatory
		DESCRIPTION
			"NFS V3 client directory creation requests"
		::= { xmdNFSV3Clnt 14 }

	xmdNFSV3ClntSymlink OBJECT-TYPE
		SYNTAX Counter
		ACCESS read-only
		STATUS mandatory
		DESCRIPTION
			"NFS V3 client symbolic link creation requests"
		::= { xmdNFSV3Clnt 10 }

	xmdNFSV3ClntMknod OBJECT-TYPE
		SYNTAX Counter
		ACCESS read-only
		STATUS mandatory
		DESCRIPTION
			"NFS V3 client mknod creation requests"
		::= { xmdNFSV3Clnt 11 }

	xmdNFSV3ClntRemove OBJECT-TYPE
		SYNTAX Counter
		ACCESS read-only
		STATUS mandatory
		DESCRIPTION
			"NFS V3 client file removal requests"
		::= { xmdNFSV3Clnt 12 }

	xmdNFSV3ClntRmdir OBJECT-TYPE
		SYNTAX Counter
		ACCESS read-only
		STATUS mandatory
		DESCRIPTION
			"NFS V3 client directory removal requests"
		::= { xmdNFSV3Clnt 13 }

	xmdNFSV3ClntRename OBJECT-TYPE
		SYNTAX Counter
		ACCESS read-only
		STATUS mandatory
		DESCRIPTION
			"NFS V3 client file rename requests"
		::= { xmdNFSV3Clnt 15 }

	xmdNFSV3ClntLink OBJECT-TYPE
		SYNTAX Counter
		ACCESS read-only
		STATUS mandatory
		DESCRIPTION
			"NFS V3 client link creation requests"
		::= { xmdNFSV3Clnt 16 }

	xmdNFSV3ClntReaddir OBJECT-TYPE
		SYNTAX Counter
		ACCESS read-only
		STATUS mandatory
		DESCRIPTION
			"NFS V3 client read-directory requests"
		::= { xmdNFSV3Clnt 17 }

	xmdNFSV3ClntReaddir-plus OBJECT-TYPE
		SYNTAX Counter
		ACCESS read-only
		STATUS mandatory
		DESCRIPTION
			"NFS V3 client read-directory plus requests"
		::= { xmdNFSV3Clnt 18 }

	xmdNFSV3ClntFsstat OBJECT-TYPE
		SYNTAX Counter
		ACCESS read-only
		STATUS mandatory
		DESCRIPTION
			"NFS V3 client file stat requests"
		::= { xmdNFSV3Clnt 19 }

	xmdNFSV3ClntFsinfo OBJECT-TYPE
		SYNTAX Counter
		ACCESS read-only
		STATUS mandatory
		DESCRIPTION
			"NFS V3 client file info requests"
		::= { xmdNFSV3Clnt 20 }

	xmdNFSV3ClntPathconf OBJECT-TYPE
		SYNTAX Counter
		ACCESS read-only
		STATUS mandatory
		DESCRIPTION
			"NFS V3 client path configure requests"
		::= { xmdNFSV3Clnt 21 }

	xmdNFSV3ClntCommit OBJECT-TYPE
		SYNTAX Counter
		ACCESS read-only
		STATUS mandatory
		DESCRIPTION
			"NFS V3 client commit requests"
		::= { xmdNFSV3Clnt 22 }

	xmdNFSV3Svr OBJECT IDENTIFIER ::= { xmdNFS 6 }

	xmdNFSV3SvrNull OBJECT-TYPE
		SYNTAX Counter
		ACCESS read-only
		STATUS mandatory
		DESCRIPTION
			"NFS server null requests"
		::= { xmdNFSV3Svr 1 }

	xmdNFSV3SvrGetattr OBJECT-TYPE
		SYNTAX Counter
		ACCESS read-only
		STATUS mandatory
		DESCRIPTION
			"NFS server getattr requests"
		::= { xmdNFSV3Svr 2 }

	xmdNFSV3SvrSetattr OBJECT-TYPE
		SYNTAX Counter
		ACCESS read-only
		STATUS mandatory
		DESCRIPTION
			"NFS server setattr requests"
		::= { xmdNFSV3Svr 3 }

	xmdNFSV3SvrLookup OBJECT-TYPE
		SYNTAX Counter
		ACCESS read-only
		STATUS mandatory
		DESCRIPTION
			"NFS server file name lookup requests"
		::= { xmdNFSV3Svr 4 }

	xmdNFSV3SvrAccess OBJECT-TYPE
		SYNTAX Counter
		ACCESS read-only
		STATUS mandatory
		DESCRIPTION
			"NFS server file access requests"
		::= { xmdNFSV3Svr 5 }

	xmdNFSV3SvrReadlink OBJECT-TYPE
		SYNTAX Counter
		ACCESS read-only
		STATUS mandatory
		DESCRIPTION
			"NFS server readlink requests"
		::= { xmdNFSV3Svr 6 }

	xmdNFSV3SvrRead OBJECT-TYPE
		SYNTAX Counter
		ACCESS read-only
		STATUS mandatory
		DESCRIPTION
			"NFS server read requests"
		::= { xmdNFSV3Svr 7 }

	xmdNFSV3SvrWrite OBJECT-TYPE
		SYNTAX Counter
		ACCESS read-only
		STATUS mandatory
		DESCRIPTION
			"NFS server write requests"
		::= { xmdNFSV3Svr 8 }

	xmdNFSV3SvrCreate OBJECT-TYPE
		SYNTAX Counter
		ACCESS read-only
		STATUS mandatory
		DESCRIPTION
			"NFS server file creation requests"
		::= { xmdNFSV3Svr 9 }

	xmdNFSV3SvrMkdir OBJECT-TYPE
		SYNTAX Counter
		ACCESS read-only
		STATUS mandatory
		DESCRIPTION
			"NFS server director6 creation requests"
		::= { xmdNFSV3Svr 10 }

	xmdNFSV3SvrSymlink OBJECT-TYPE
		SYNTAX Counter
		ACCESS read-only
		STATUS mandatory
		DESCRIPTION
			"NFS server symbolic link creation requests"
		::= { xmdNFSV3Svr 11 }

	xmdNFSV3SvrMknod OBJECT-TYPE
		SYNTAX Counter
		ACCESS read-only
		STATUS mandatory
		DESCRIPTION
			"NFS server mknode creation requests"
		::= { xmdNFSV3Svr 12 }

	xmdNFSV3SvrRemove OBJECT-TYPE
		SYNTAX Counter
		ACCESS read-only
		STATUS mandatory
		DESCRIPTION
			"NFS server file removal requests"
		::= { xmdNFSV3Svr 13 }

	xmdNFSV3SvrRmdir OBJECT-TYPE
		SYNTAX Counter
		ACCESS read-only
		STATUS mandatory
		DESCRIPTION
			"NFS server directory removal requests"
		::= { xmdNFSV3Svr 14 }

	xmdNFSV3SvrRename OBJECT-TYPE
		SYNTAX Counter
		ACCESS read-only
		STATUS mandatory
		DESCRIPTION
			"NFS server file rename requests"
		::= { xmdNFSV3Svr 15 }

	xmdNFSV3SvrLink OBJECT-TYPE
		SYNTAX Counter
		ACCESS read-only
		STATUS mandatory
		DESCRIPTION
			"NFS server link creation requests"
		::= { xmdNFSV3Svr 16 }

	xmdNFSV3SvrReaddir OBJECT-TYPE
		SYNTAX Counter
		ACCESS read-only
		STATUS mandatory
		DESCRIPTION
			"NFS server read-directory requests"
		::= { xmdNFSV3Svr 17 }

	xmdNFSV3SvrReaddir-plus OBJECT-TYPE
		SYNTAX Counter
		ACCESS read-only
		STATUS mandatory
		DESCRIPTION
			"NFS server read-directory plus requests"
		::= { xmdNFSV3Svr 18 }

	xmdNFSV3SvrFsstat OBJECT-TYPE
		SYNTAX Counter
		ACCESS read-only
		STATUS mandatory
		DESCRIPTION
			"NFS server file stat requests"
		::= { xmdNFSV3Svr 19 }

	xmdNFSV3SvrFsinfo OBJECT-TYPE
		SYNTAX Counter
		ACCESS read-only
		STATUS mandatory
		DESCRIPTION
			"NFS server file info requests"
		::= { xmdNFSV3Svr 20 }

	xmdNFSV3SvrPathconf OBJECT-TYPE
		SYNTAX Counter
		ACCESS read-only
		STATUS mandatory
		DESCRIPTION
			"NFS server path configure requests"
		::= { xmdNFSV3Svr 21 }

	xmdNFSV3SvrCommit OBJECT-TYPE
		SYNTAX Counter
		ACCESS read-only
		STATUS mandatory
		DESCRIPTION
			"NFS server commit requests"
		::= { xmdNFSV3Svr 22 }

	xmdDCE OBJECT IDENTIFIER ::= { xmd 28 }

	xmdSpmi OBJECT IDENTIFIER ::= { xmd 98 }

	xmdSpmiUsers OBJECT-TYPE
		SYNTAX INTEGER
		ACCESS read-only
		STATUS mandatory
		DESCRIPTION
			"Count of common shared memory users"
		::= { xmdSpmi 1 }

	xmdSpmiStatsets OBJECT-TYPE
		SYNTAX INTEGER
		ACCESS read-only
		STATUS mandatory
		DESCRIPTION
			"Count of defined StatSets"
		::= { xmdSpmi 2 }

	xmdSpmiDdscount OBJECT-TYPE
		SYNTAX INTEGER
		ACCESS read-only
		STATUS mandatory
		DESCRIPTION
			"Count of active dynamic data suppliers"
		::= { xmdSpmi 3 }

	xmdSpmiConsumers OBJECT-TYPE
		SYNTAX INTEGER
		ACCESS read-only
		STATUS mandatory
		DESCRIPTION
			"Count of active data consumers"
		::= { xmdSpmi 4 }

	xmdSpmiComused OBJECT-TYPE
		SYNTAX INTEGER
		ACCESS read-only
		STATUS mandatory
		DESCRIPTION
			"kbytes of common shared memory in use"
		::= { xmdSpmi 5 }

	xmdSpmiHotsets OBJECT-TYPE
		SYNTAX INTEGER
		ACCESS read-only
		STATUS mandatory
		DESCRIPTION
			"Count of defined HotSets"
		::= { xmdSpmi 6 }

	xmdDDS OBJECT IDENTIFIER ::= { xmd 99 }

	END
