-- ZyXEL Communications Corporation
-- Private Enterprise MIB definition 
  
-- This file describes the ZyXEL Communications Corporation Enterprise MIB.
-- It contains ZyXEL products OIDs, and common managed objects.

-- $Log: ZYXEL-DIAGNOSTIC-MIB.mib $ 
-- Revision 1.1  2014/04/08 09:16:46  ZhongWei 
-- Initial revision 
-- Revision 1.1  2013/06/04 10:50:35  Zhongwei_Lin 
-- Initial revision 

ZYXEL-DIAGNOSTIC-MIB DEFINITIONS ::= BEGIN

    IMPORTS                          
	OBJECT-TYPE
		FROM SNMPv2-SMI			-- RFC2578	
	esMgmt			
		FROM ZYXEL-ES-SMI;

	zyxelDiagnostic MODULE-IDENTITY
		LAST-UPDATED	"201305060000Z"    
		ORGANIZATION "Enterprise Solution ZyXEL"     
		CONTACT-INFO
			""	   
		DESCRIPTION
			"The subtree for diagnostic"
		::= { esMgmt 95 }

	zyxelLocatorLedStatus   	OBJECT IDENTIFIER ::= { zyxelDiagnostic 1 }

-- ******************************************************************
-- *
-- * 1.zyxelLocatorLedStatus
-- *
-- ******************************************************************  
	
--	1.zyxelLocatorLedStatus
        zyLocatorLed OBJECT-TYPE
        SYNTAX  INTEGER (0..1440)
        MAX-ACCESS  read-write
        STATUS  current
        DESCRIPTION
        "Locator LED blinking time in minutes."
        ::= { zyxelLocatorLedStatus 1 }

END
