GWIAMIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

novell          OBJECT IDENTIFIER   ::= { enterprises  23 }
gateways        OBJECT IDENTIFIER   ::= { novell        2 }
gwia          OBJECT IDENTIFIER   ::= { gateways     70 }
gwiaInfo      OBJECT IDENTIFIER   ::= { gwia        1 }
gwiaTrapInfo  OBJECT IDENTIFIER   ::= { gwia        2 }
gwiaTraps     OBJECT IDENTIFIER   ::= { gwia        3 }


-- ================================= GWIA GWE Get/Set Variables =========
gwiaGatewayName OBJECT-TYPE
       SYNTAX  DisplayString (SIZE (0..255))
       ACCESS  read-only
       STATUS  mandatory
       DESCRIPTION
       "The GroupWise Internet Agent name."
   ::= { gwiaInfo 1 }
 
gwiaTimeUp OBJECT-TYPE
       SYNTAX  TimeTicks
       ACCESS  read-only
       STATUS  mandatory
       DESCRIPTION
      "Uptime of the GroupWise Internet Agent."
   ::= { gwiaInfo 2 }

gwiaLinkGroupWise OBJECT-TYPE
       SYNTAX  DisplayString (SIZE (0..5))
       ACCESS  read-only
       STATUS  mandatory
       DESCRIPTION
      "GroupWise Internet Agent Link: UP or DOWN"
   ::= { gwiaInfo 3 }

gwiaLinkFrgn OBJECT-TYPE
       SYNTAX  DisplayString (SIZE (0..5))
       ACCESS  read-only
       STATUS  mandatory
       DESCRIPTION
      "GroupWise Internet Agent Foreign Link: UP or DOWN"
   ::= { gwiaInfo 4 }

gwiaStatBytesOut OBJECT-TYPE
       SYNTAX  Counter
       ACCESS  read-only
       STATUS  mandatory
       DESCRIPTION
      "The number of message bytes sent to GroupWise Internet Agent."
   ::= { gwiaInfo 5 }
 
gwiaStatBytesIn OBJECT-TYPE
       SYNTAX  Counter
       ACCESS  read-only
       STATUS  mandatory
       DESCRIPTION
      "The number of message bytes received from GroupWise Internet Agent."
   ::= { gwiaInfo 6 }
 
gwiaStatMsgsOut OBJECT-TYPE
       SYNTAX  Counter
       ACCESS  read-only
       STATUS  mandatory
       DESCRIPTION
      "The number of messages sent to GroupWise Internet Agent."
   ::= { gwiaInfo 7 }
 
gwiaStatMsgsIn OBJECT-TYPE
       SYNTAX  Counter
       ACCESS  read-only
       STATUS  mandatory
       DESCRIPTION
      "The number of messages received from GroupWise Internet Agent."
   ::= { gwiaInfo 8 }
 
gwiaStatStatusesOut OBJECT-TYPE
       SYNTAX  Counter
       ACCESS  read-only
       STATUS  mandatory
       DESCRIPTION
      "The number of statuses sent to GroupWise Internet Agent."
   ::= { gwiaInfo 9 }
 
gwiaStatStatusesIn OBJECT-TYPE
       SYNTAX  Counter
       ACCESS  read-only
       STATUS  mandatory
       DESCRIPTION
      "The number of statuses received from GroupWise Internet Agent."
   ::= { gwiaInfo 10 }
 
gwiaStatErrorsOut OBJECT-TYPE
       SYNTAX  Counter
       ACCESS  read-only
       STATUS  mandatory
       DESCRIPTION
      "The number of failed transfers to GroupWise Internet Agent."
   ::= { gwiaInfo 11 }
 
gwiaStatErrorsIn OBJECT-TYPE
       SYNTAX  Counter
       ACCESS  read-only
       STATUS  mandatory
       DESCRIPTION
      "The number of failed transfers from GroupWise Internet Agent."
   ::= { gwiaInfo 12 }

gwiaStatTimeReset OBJECT-TYPE
       SYNTAX  TimeTicks
       ACCESS  read-only
       STATUS  mandatory
       DESCRIPTION
      "Time since statistics were reset on GroupWise Internet Agent."
   ::= { gwiaInfo 13 }

gwiaQueueWpcsout OBJECT-TYPE
       SYNTAX  Counter
       ACCESS  read-only
       STATUS  mandatory
       DESCRIPTION
      "The number of messages to be processed by GroupWise Internet Agent (WPCSOUT)."
   ::= { gwiaInfo 14 }

gwiaQueueWpcsin OBJECT-TYPE
       SYNTAX  Counter
       ACCESS  read-only
       STATUS  mandatory
       DESCRIPTION
      "The number of messages to be processed by GroupWise Message Server (WPCSIN)."
   ::= { gwiaInfo 15 }

gwiaQueueGwhold OBJECT-TYPE
       SYNTAX  Counter
       ACCESS  read-only
       STATUS  mandatory
       DESCRIPTION
      "The number messages holding for later processing by GroupWise Internet Agent (GWHOLD)."
   ::= { gwiaInfo 16 }

gwiaQueueGwprob OBJECT-TYPE
       SYNTAX  Counter
       ACCESS  read-only
       STATUS  mandatory
       DESCRIPTION
      "The number messages in GroupWise Internet Agent's problem directory (GWPROB)."
   ::= { gwiaInfo 17 }

gwiaStatInterval OBJECT-TYPE
       SYNTAX  TimeTicks
       ACCESS  read-only
       STATUS  mandatory
       DESCRIPTION
      "Statistics interval for the GroupWise Internet Agent."
   ::= { gwiaInfo 18 }

gwiaStatIntervalMsgsOut OBJECT-TYPE
       SYNTAX  Counter
       ACCESS  read-only
       STATUS  mandatory
       DESCRIPTION
      "The number of messages sent to GroupWise Internet Agent in statistics interval."
   ::= { gwiaInfo 19 }
 
gwiaStatIntervalMsgsIn OBJECT-TYPE
       SYNTAX  Counter
       ACCESS  read-only
       STATUS  mandatory
       DESCRIPTION
      "The number of messages received from GroupWise Internet Agent in statistics interval."
   ::= { gwiaInfo 20 }
 
gwiaStatIntervalStatusesOut OBJECT-TYPE
       SYNTAX  Counter
       ACCESS  read-only
       STATUS  mandatory
       DESCRIPTION
      "The number of statuses sent to GroupWise Internet Agent in statistics interval."
   ::= { gwiaInfo 21 }
 
gwiaStatIntervalStatusesIn OBJECT-TYPE
       SYNTAX  Counter
       ACCESS  read-only
       STATUS  mandatory
       DESCRIPTION
      "The number of statuses received from GroupWise Internet Agent in statistics interval."
   ::= { gwiaInfo 22 }
 
gwiaStatIntervalErrorsOut OBJECT-TYPE
       SYNTAX  Counter
       ACCESS  read-only
       STATUS  mandatory
       DESCRIPTION
      "The number of failed transfers to GroupWise Internet Agent in statistics interval."
   ::= { gwiaInfo 23 }
 
gwiaStatIntervalErrorsIn OBJECT-TYPE
       SYNTAX  Counter
       ACCESS  read-only
       STATUS  mandatory
       DESCRIPTION
      "The number of failed transfers from GroupWise Internet Agent in statistics interval."
   ::= { gwiaInfo 24 }

gwiaQThresholdCheckInterval OBJECT-TYPE
       SYNTAX  Counter
       ACCESS  read-write
       STATUS  mandatory
       DESCRIPTION
      "The number of minutes between directory scans or directory threshold traps for GroupWise Internet Agent."
   ::= { gwiaInfo 25 }

gwiaQThresholdWpcsout OBJECT-TYPE
       SYNTAX  Counter
       ACCESS  read-write
       STATUS  mandatory
       DESCRIPTION
      "The number of messages waiting for GroupWise Internet Agent before firing threshold trap (WPCSOUT)."
   ::= { gwiaInfo 26 }

gwiaQThresholdWpcsin OBJECT-TYPE
       SYNTAX  Counter
       ACCESS  read-write
       STATUS  mandatory
       DESCRIPTION
      "The number of messages waiting for Message Server from GroupWise Internet Agent before firing threshold trap (WPCSIN)."
   ::= { gwiaInfo 27 }

gwiaQThresholdGwhold OBJECT-TYPE
       SYNTAX  Counter
       ACCESS  read-write
       STATUS  mandatory
       DESCRIPTION
      "The number of defered messages waiting for GroupWise Internet Agent before firing threshold trap (GWHOLD)."
   ::= { gwiaInfo 28 }

gwiaQThresholdGwprob OBJECT-TYPE
       SYNTAX  Counter
       ACCESS  read-write
       STATUS  mandatory
       DESCRIPTION
      "The number of problem messages GroupWise Internet Agent moved before firing threshold trap (GWPROB)."
   ::= { gwiaInfo 29 }

gwiaThresholdMsgSizeIn OBJECT-TYPE
       SYNTAX  Counter
       ACCESS  read-write
       STATUS  mandatory
       DESCRIPTION
      "The max size of an incoming message GroupWise Internet Agent can process before firing threshold trap."
   ::= { gwiaInfo 30 }

gwiaThresholdMsgSizeOut OBJECT-TYPE
       SYNTAX  Counter
       ACCESS  read-write
       STATUS  mandatory
       DESCRIPTION
      "The max size of an outgoing message GroupWise Internet Agent can process before firing threshold trap."
   ::= { gwiaInfo 31 }

gwiaActionResetStats OBJECT-TYPE
       SYNTAX  INTEGER {
       reset(1)
}
       ACCESS  write-only
       STATUS  mandatory
       DESCRIPTION
      "Reset GroupWise Internet Agent statistics."
   ::= { gwiaInfo 32 }

gwiaActionRestartGateway OBJECT-TYPE
       SYNTAX  INTEGER {
       restart(1)
}
       ACCESS  write-only
       STATUS  mandatory
       DESCRIPTION
      "Restart GroupWise Internet Agent."
   ::= { gwiaInfo 33 }

gwiaHTTPPort OBJECT-TYPE
       SYNTAX  INTEGER 
       ACCESS  read-only
       STATUS  mandatory
       DESCRIPTION
      "HTTP port used by the agent"
   ::= { gwiaInfo 34 }



-- ============================= GWIA specific Get/Set Variables =========

gwiasmtpdThreadsAvailSend OBJECT-TYPE
       SYNTAX  Counter
       ACCESS  read-only
       STATUS  mandatory
       DESCRIPTION
      "The number of SMTP Daemon send threads available."
   ::= { gwiaInfo 48 }

gwiasmtpdThreadsAvailReceive OBJECT-TYPE
       SYNTAX  Counter
       ACCESS  read-only
       STATUS  mandatory
       DESCRIPTION
      "The number of SMTP Daemon receive threads available."
   ::= { gwiaInfo 49 }


gwiasmtpdThreadsActiveSend OBJECT-TYPE
       SYNTAX  Counter
       ACCESS  read-only
       STATUS  mandatory
       DESCRIPTION
      "The number of SMTP Daemon send threads active."
   ::= { gwiaInfo 50 }


gwiasmtpdThreadsActiveReceive OBJECT-TYPE
       SYNTAX  Counter
       ACCESS  read-only
       STATUS  mandatory
       DESCRIPTION
      "The number of SMTP Daemon receive threads active."
   ::= { gwiaInfo 51 }


gwiasmtpdErrorsMXLookup OBJECT-TYPE
       SYNTAX  Counter
       ACCESS  read-only
       STATUS  mandatory
       DESCRIPTION
      "The number of SMTP Daemon DNS MX lookup errors."
   ::= { gwiaInfo 52 }


gwiasmtpdErrorsHostsUnknown OBJECT-TYPE
       SYNTAX  Counter
       ACCESS  read-only
       STATUS  mandatory
       DESCRIPTION
      "The number of SMTP Daemon unknown destination hosts."
   ::= { gwiaInfo 53 }


gwiasmtpdErrorsHostsDown OBJECT-TYPE
       SYNTAX  Counter
       ACCESS  read-only
       STATUS  mandatory
       DESCRIPTION
      "The number of SMTP Daemon TCP/IP connect errors."
   ::= { gwiaInfo 54 }


gwiasmtpdErrorsTCPRead OBJECT-TYPE
       SYNTAX  Counter
       ACCESS  read-only
       STATUS  mandatory
       DESCRIPTION
      "The number of SMTP Daemon TCP/IP read errors."
   ::= { gwiaInfo 55 }


gwiasmtpdErrorsTCPWrite OBJECT-TYPE
       SYNTAX  Counter
       ACCESS  read-only
       STATUS  mandatory
       DESCRIPTION
      "The number of SMTP Daemon TCP/IP write errors."
   ::= { gwiaInfo 56 }


gwiasmtpdMessagesIn OBJECT-TYPE
       SYNTAX  Counter
       ACCESS  read-only
       STATUS  mandatory
       DESCRIPTION
      "The number of SMTP Daemon messages received."
   ::= { gwiaInfo 57 }


gwiasmtpdMessagesOut OBJECT-TYPE
       SYNTAX  Counter
       ACCESS  read-only
       STATUS  mandatory
       DESCRIPTION
      "The number of SMTP Daemon messages sent."
   ::= { gwiaInfo 58 }

gwiasmtpQThresholdSend OBJECT-TYPE
       SYNTAX  Counter
       ACCESS  read-write
       STATUS  mandatory
       DESCRIPTION
      "The number of send messages GroupWise Internet Agent can queue to daemon before firing threshold trap (SEND)."
   ::= { gwiaInfo 59 }

gwiasmtpQThresholdReceive OBJECT-TYPE
       SYNTAX  Counter
       ACCESS  read-write
       STATUS  mandatory
       DESCRIPTION
      "The number of messages queued by daemon for GroupWise Internet Agent before firing threshold trap (RECEIVE)."
   ::= { gwiaInfo 60 }

gwiasmtpQThresholdDefer OBJECT-TYPE
       SYNTAX  Counter
       ACCESS  read-write
       STATUS  mandatory
       DESCRIPTION
      "The number of messages to have daemon retry sending for GroupWise Internet Agent before firing threshold trap (DEFER)."
   ::= { gwiaInfo 61 }

gwiasmtpQueueSend OBJECT-TYPE
       SYNTAX  Counter
       ACCESS  read-only
       STATUS  mandatory
       DESCRIPTION
      "The number of messages queued to daemon for GroupWise Internet Agent (SEND)."
   ::= { gwiaInfo 62 }

gwiasmtpQueueReceive OBJECT-TYPE
       SYNTAX  Counter
       ACCESS  read-only
       STATUS  mandatory
       DESCRIPTION
      "The number of messages queued to GroupWise Internet Agent from SMTP daemon (RECEIVE)."
   ::= { gwiaInfo 63 }

gwiasmtpQueueDefer OBJECT-TYPE
       SYNTAX  Counter
       ACCESS  read-only
       STATUS  mandatory
       DESCRIPTION
      "The number of messages queued to retry for SMTP daemon on GroupWise Internet Agent (DEFER)."
   ::= { gwiaInfo 64 }

gwiapop3SessionsAvail OBJECT-TYPE
       SYNTAX  Counter
       ACCESS  read-only
       STATUS  mandatory
       DESCRIPTION
      "The number of POP3 Server sessions available."
   ::= { gwiaInfo 65 }

gwiapop3SessionsActive OBJECT-TYPE
       SYNTAX  Counter
       ACCESS  read-only
       STATUS  mandatory
       DESCRIPTION
      "The number of POP3 Server sessions currently active."
   ::= { gwiaInfo 66 }

gwiapop3SessionsTotal OBJECT-TYPE
       SYNTAX  Counter
       ACCESS  read-only
       STATUS  mandatory
       DESCRIPTION
      "The total number of POP3 Server sessions."
   ::= { gwiaInfo 67 }

gwiapop3MessagesSent OBJECT-TYPE
       SYNTAX  Counter
       ACCESS  read-only
       STATUS  mandatory
       DESCRIPTION
      "The number of POP3 messages downloaded."
   ::= { gwiaInfo 68 }

gwiapop3StoreLoginErrs OBJECT-TYPE
       SYNTAX  Counter
       ACCESS  read-only
       STATUS  mandatory
       DESCRIPTION
      "Errors logging in to GroupWise Post Office."
   ::= { gwiaInfo 69 }

gwiapop3StoreRetrievalErrs OBJECT-TYPE
       SYNTAX  Counter
       ACCESS  read-only
       STATUS  mandatory
       DESCRIPTION
      "Errors retrieving messages from a GroupWise Post Office."
   ::= { gwiaInfo 70 }

gwiapop3ConversionErrs OBJECT-TYPE
       SYNTAX  Counter
       ACCESS  read-only
       STATUS  mandatory
       DESCRIPTION
      "Errors converting messages for POP3 download."
   ::= { gwiaInfo 71 }

gwiapop3UnknownUsers OBJECT-TYPE
       SYNTAX  Counter
       ACCESS  read-only
       STATUS  mandatory
       DESCRIPTION
      "Count of unknown users when logging into POP3 server."
   ::= { gwiaInfo 72 }

gwiapop3BadPassword OBJECT-TYPE
       SYNTAX  Counter
       ACCESS  read-only
       STATUS  mandatory
       DESCRIPTION
      "Count of bad passwords when logging into POP3 server."
   ::= { gwiaInfo 73 }

gwiapop3AccessDenied OBJECT-TYPE
       SYNTAX  Counter
       ACCESS  read-only
       STATUS  mandatory
       DESCRIPTION
      "Count of users denied access when logging into POP3 server."
   ::= { gwiaInfo 74 }

gwiapop3ErrorsTCPRead OBJECT-TYPE
       SYNTAX  Counter
       ACCESS  read-only
       STATUS  mandatory
       DESCRIPTION
      "The number of POP3 Server TCP/IP read errors."
   ::= { gwiaInfo 75 }

gwiapop3ErrorsTCPWrite OBJECT-TYPE
       SYNTAX  Counter
       ACCESS  read-only
       STATUS  mandatory
       DESCRIPTION
      "The number of POP3 Server TCP/IP write errors."
   ::= { gwiaInfo 76 }

gwiaLdapPublic OBJECT-TYPE
       SYNTAX  Counter
       ACCESS  read-only
       STATUS  mandatory
       DESCRIPTION
      "The number of LDAP Server Public binds."
   ::= { gwiaInfo 77 }

gwiaLdapAuth OBJECT-TYPE
       SYNTAX  Counter
       ACCESS  read-only
       STATUS  mandatory
       DESCRIPTION
      "The number of LDAP Server Authenticated binds."
   ::= { gwiaInfo 78 }

gwiaLdapThreadsFree OBJECT-TYPE
       SYNTAX  Counter
       ACCESS  read-only
       STATUS  mandatory
       DESCRIPTION
      "The number of LDAP Server Free Threads."
   ::= { gwiaInfo 79 }

gwiaLdapSearchReq OBJECT-TYPE
       SYNTAX  Counter
       ACCESS  read-only
       STATUS  mandatory
       DESCRIPTION
      "The number of LDAP Server Search requests."
   ::= { gwiaInfo 80 }

gwiaLdapReturnedItems OBJECT-TYPE
       SYNTAX  Counter
       ACCESS  read-only
       STATUS  mandatory
       DESCRIPTION
      "The number of LDAP Server Returned Entries."
   ::= { gwiaInfo 81 }

gwiaLdapActive OBJECT-TYPE
       SYNTAX  Counter
       ACCESS  read-only
       STATUS  mandatory
       DESCRIPTION
      "The number of LDAP Server Active binds."
   ::= { gwiaInfo 82 }

gwiaimap4SessionsAvail OBJECT-TYPE
       SYNTAX  Counter
       ACCESS  read-only
       STATUS  mandatory
       DESCRIPTION
      "The number of IMAP4 Server sessions available."
   ::= { gwiaInfo 83 }

gwiaimap4SessionsActive OBJECT-TYPE
       SYNTAX  Counter
       ACCESS  read-only
       STATUS  mandatory
       DESCRIPTION
      "The number of IMAP4 Server sessions currently active."
   ::= { gwiaInfo 84 }

gwiaimap4SessionsTotal OBJECT-TYPE
       SYNTAX  Counter
       ACCESS  read-only
       STATUS  mandatory
       DESCRIPTION
      "The total number of IMAP4 Server sessions."
   ::= { gwiaInfo 85 }

gwiaimap4MessagesSent OBJECT-TYPE
       SYNTAX  Counter
       ACCESS  read-only
       STATUS  mandatory
       DESCRIPTION
      "The number of IMAP4 messages downloaded."
   ::= { gwiaInfo 86 }

gwiaimap4StoreLoginErrs OBJECT-TYPE
       SYNTAX  Counter
       ACCESS  read-only
       STATUS  mandatory
       DESCRIPTION
      "Errors logging in to GroupWise Post Office."
   ::= { gwiaInfo 87 }

gwiaimap4StoreRetrievalErrs OBJECT-TYPE
       SYNTAX  Counter
       ACCESS  read-only
       STATUS  mandatory
       DESCRIPTION
      "Errors retrieving messages from a GroupWise Post Office."
   ::= { gwiaInfo 88 }

gwiaimap4ConversionErrs OBJECT-TYPE
       SYNTAX  Counter
       ACCESS  read-only
       STATUS  mandatory
       DESCRIPTION
      "Errors converting messages for IMAP4 download."
   ::= { gwiaInfo 89 }

gwiaimap4UnknownUsers OBJECT-TYPE
       SYNTAX  Counter
       ACCESS  read-only
       STATUS  mandatory
       DESCRIPTION
      "Count of unknown users when logging into IMAP4 server."
   ::= { gwiaInfo 90 }

gwiaimap4BadPassword OBJECT-TYPE
       SYNTAX  Counter
       ACCESS  read-only
       STATUS  mandatory
       DESCRIPTION
      "Count of bad passwords when logging into IMAP4 server."
   ::= { gwiaInfo 91 }

gwiaimap4AccessDenied OBJECT-TYPE
       SYNTAX  Counter
       ACCESS  read-only
       STATUS  mandatory
       DESCRIPTION
      "Count of users denied access when logging into IMAP4 server."
   ::= { gwiaInfo 92 }

gwiaimap4ErrorsTCPRead OBJECT-TYPE
       SYNTAX  Counter
       ACCESS  read-only
       STATUS  mandatory
       DESCRIPTION
      "The number of IMAP4 Server TCP/IP read errors."
   ::= { gwiaInfo 93 }

gwiaimap4ErrorsTCPWrite OBJECT-TYPE
       SYNTAX  Counter
       ACCESS  read-only
       STATUS  mandatory
       DESCRIPTION
      "The number of IMAP4 Server TCP/IP write errors."
   ::= { gwiaInfo 94 }



-- ================================================== gwiaTrapInfo ========
-- The gwiaTrapInfo group
-- These objects are used only in traps produced by gwia
 
gwiaTrapTime OBJECT-TYPE
		SYNTAX  INTEGER
		ACCESS  not-accessible
		STATUS  mandatory
		DESCRIPTION "The time the trap occurred. Seconds since Jan 1, 1970 (GMT)"
	::= { gwiaTrapInfo 1 }

gwiaTrapDomainName OBJECT-TYPE
       SYNTAX  DisplayString (SIZE (0..255))
       ACCESS  not-accessible
       STATUS  mandatory
       DESCRIPTION "The Domain for which this gateway operates."
   ::= { gwiaTrapInfo 2 }

 
-- ============================================== gwia GWE Traps =========
gwiaStartTrap TRAP-TYPE
		ENTERPRISE    gwiaTraps
		VARIABLES     {gwiaTrapTime, gwiaGatewayName}
		DESCRIPTION   "GroupWise Internet Agent start."
		--NMS Trap annotation
		--#TYPE       "GroupWise Internet Agent start."
		--#SUMMARY    "GroupWise Internet Agent %s has started."
		--#ARGUMENTS  {1}
		--#SEVERITY   INFORMATIONAL
		--#TIMEINDEX  0
		--#STATE      OPERATIONAL
		::= 1

gwiaStopTrap TRAP-TYPE
		ENTERPRISE    gwiaTraps
		VARIABLES     {gwiaTrapTime, gwiaGatewayName}
		DESCRIPTION   "GroupWise Internet Agent stop."
		--NMS Trap annotation
		--#TYPE       "GroupWise Internet Agent stop."
		--#SUMMARY    "GroupWise Internet Agent %s has stopped."
		--#ARGUMENTS  {1}
		--#SEVERITY   CRITICAL
		--#TIMEINDEX  0
		--#STATE      NONOPERATIONAL
		::= 2

gwiaRestartTrap TRAP-TYPE
		ENTERPRISE    gwiaTraps
		VARIABLES     {gwiaTrapTime, gwiaGatewayName}
		DESCRIPTION   "GroupWise Internet Agent restart."
		--NMS Trap annotation
		--#TYPE       "GroupWise Internet Agent restart."
		--#SUMMARY    "GroupWise Internet Agent %s has been restarted."
		--#ARGUMENTS  {1}
		--#SEVERITY   INFORMATIONAL
		--#TIMEINDEX  0
		--#STATE      OPERATIONAL
		::= 3
 
gwiaGroupWiseLinkTrap TRAP-TYPE
		ENTERPRISE    gwiaTraps
		VARIABLES     {gwiaTrapTime, gwiaGatewayName}
		DESCRIPTION   "GroupWise Link lost by GroupWise Internet Agent"
		--NMS Trap annotation
		--#TYPE       "GroupWise Link lost by GroupWise Internet Agent"
		--#SUMMARY    "GroupWise Internet Agent %s has lost its GroupWise Link"
		--#ARGUMENTS  {1}
		--#SEVERITY   INFORMATIONAL
		--#TIMEINDEX  0
		--#STATE      OPERATIONAL
		::= 4

gwiaMovedToProbTrap TRAP-TYPE
		ENTERPRISE    gwiaTraps
		VARIABLES     {gwiaTrapTime, gwiaGatewayName}
		DESCRIPTION   "Problem message moved to GWPROB directory for GroupWise Internet Agent"
		--NMS Trap annotation
		--#TYPE       "Problem message moved to GWPROB directory for GroupWise Internet Agent"
		--#SUMMARY    "GroupWise Internet Agent %s moved a problem message to GWPROB"
		--#ARGUMENTS  {1}
		--#SEVERITY   INFORMATIONAL
		--#TIMEINDEX  0
		--#STATE      OPERATIONAL
		::= 6

gwiaWpcsoutThreshTrap TRAP-TYPE
		ENTERPRISE    gwiaTraps
		VARIABLES     {gwiaTrapTime, gwiaGatewayName}
		DESCRIPTION   "Threshold for messages to be processed by GroupWise Internet Agent has been exceeded (WPCSOUT)"
		--NMS Trap annotation
		--#TYPE       "Threshold for messages to be processed by GroupWise Internet Agent has been exceeded (WPCSOUT)"
		--#SUMMARY    "GroupWise Internet Agent %s has exceeded its threshold for messages to be processed (WPCSOUT)"
		--#ARGUMENTS  {1}
		--#SEVERITY   INFORMATIONAL
		--#TIMEINDEX  0
		--#STATE      OPERATIONAL
		::= 7

gwiaWpcsinThreshTrap TRAP-TYPE
		ENTERPRISE    gwiaTraps
		VARIABLES     {gwiaTrapTime, gwiaGatewayName}
		DESCRIPTION   "The threshold for processed messages by GroupWise Internet Agent has been exceeded (WPCSIN)"
		--NMS Trap annotation
		--#TYPE       "The threshold for processed messages by GroupWise Internet Agent has been exceeded (WPCSIN)"
		--#SUMMARY    "GroupWise Internet Agent %s has exceeded its threshold for processed messages (WPCSIN)"
		--#ARGUMENTS  {1}
		--#SEVERITY   INFORMATIONAL
		--#TIMEINDEX  0
		--#STATE      OPERATIONAL
		::= 8

gwiaGwholdThreshTrap TRAP-TYPE
		ENTERPRISE    gwiaTraps
		VARIABLES     {gwiaTrapTime, gwiaGatewayName}
		DESCRIPTION   "The threshold for defered messages in hold area for GroupWise Internet Agent has been exceeded (GWHOLD)"
		--NMS Trap annotation
		--#TYPE       "The threshold for defered messages in hold area for GroupWise Internet Agent has been exceeded (GWHOLD)"
		--#SUMMARY    "GroupWise Internet Agent %s has exceeded its threshold for defered messages (GWHOLD)"
		--#ARGUMENTS  {1}
		--#SEVERITY   INFORMATIONAL
		--#TIMEINDEX  0
		--#STATE      OPERATIONAL
		::= 9

gwiaGwprobThreshTrap TRAP-TYPE
		ENTERPRISE    gwiaTraps
		VARIABLES     {gwiaTrapTime, gwiaGatewayName}
		DESCRIPTION   "The threshold for problem messages in problem area for GroupWise Internet Agent has been exceeded (GWPROB)"
		--NMS Trap annotation
		--#TYPE       "The threshold for problem messages in problem area for GroupWise Internet Agent has been exceeded (GWPROB)"
		--#SUMMARY    "GroupWise Internet Agent %s has exceeded its threshold for problem messages (GWPROB)"
		--#ARGUMENTS  {1}
		--#SEVERITY   INFORMATIONAL
		--#TIMEINDEX  0
		--#STATE      OPERATIONAL
		::= 10


gwiaInSizeThreshTrap TRAP-TYPE
		ENTERPRISE    gwiaTraps
		VARIABLES     {gwiaTrapTime, gwiaGatewayName}
		DESCRIPTION   "The threshold for a incomming message for GroupWise Internet Agent has been exceeded"
		--NMS Trap annotation
		--#TYPE       "The threshold for a incomming message for GroupWise Internet Agent has been exceeded"
		--#SUMMARY    "GroupWise Internet Agent %s has exceeded its threshold for a incomming message"
		--#ARGUMENTS  {1}
		--#SEVERITY   INFORMATIONAL
		--#TIMEINDEX  0
		--#STATE      OPERATIONAL
		::= 11

gwiaOutSizeThreshTrap TRAP-TYPE
		ENTERPRISE    gwiaTraps
		VARIABLES     {gwiaTrapTime, gwiaGatewayName}
		DESCRIPTION   "The threshold for a outgoing message for GroupWise Internet Agent has been exceeded"
		--NMS Trap annotation
		--#TYPE       "The threshold for a outgoing message for GroupWise Internet Agent has been exceeded"
		--#SUMMARY    "GroupWise Internet Agent %s has exceeded its threshold for a outgoing message"
		--#ARGUMENTS  {1}
		--#SEVERITY   INFORMATIONAL
		--#TIMEINDEX  0
		--#STATE      OPERATIONAL
		::= 12




-- ======================================== gwia specific Traps =========

gwiasmtpReadErrorTrap TRAP-TYPE
		ENTERPRISE    gwiaTraps
		VARIABLES     {gwiaTrapTime, gwiaGatewayName}
		DESCRIPTION   "TCP/IP read error on GroupWise Internet Agent SMTP daemon"
		--NMS Trap annotation
		--#TYPE       "TCP/IP read error on GroupWise Internet Agent SMTP daemon"
		--#SUMMARY    "GroupWise Internet Agent %s had a TCP/IP read error - connection dropped"
		--#ARGUMENTS  {1}
		--#SEVERITY   INFORMATIONAL
		--#TIMEINDEX  0
		--#STATE      OPERATIONAL
		::= 48

gwiasmtpWriteErrorTrap TRAP-TYPE
		ENTERPRISE    gwiaTraps
		VARIABLES     {gwiaTrapTime, gwiaGatewayName}
		DESCRIPTION   "TCP/IP write error on GroupWise Internet Agent SMTP daemon"
		--NMS Trap annotation
		--#TYPE       "TCP/IP write error on GroupWise Internet Agent SMTP daemon"
		--#SUMMARY    "GroupWise Internet Agent %s had a TCP/IP write error - connection dropped"
		--#ARGUMENTS  {1}
		--#SEVERITY   INFORMATIONAL
		--#TIMEINDEX  0
		--#STATE      OPERATIONAL
		::= 49

gwiasmtpSendThreshTrap TRAP-TYPE
		ENTERPRISE    gwiaTraps
		VARIABLES     {gwiaTrapTime, gwiaGatewayName}
		DESCRIPTION   "The threshold for messages in SMTP daemon send area for GroupWise Internet Agent has been exceeded (SEND)"
		--NMS Trap annotation
		--#TYPE       "The threshold for messages in SMTP daemon send area for GroupWise Internet Agent has been exceeded (SEND)"
		--#SUMMARY    "GroupWise Internet Agent %s has exceeded its threshold for daemon send messages (SEND)"
		--#ARGUMENTS  {1}
		--#SEVERITY   INFORMATIONAL
		--#TIMEINDEX  0
		--#STATE      OPERATIONAL
		::= 50

gwiasmtpReceiveThreshTrap TRAP-TYPE
		ENTERPRISE    gwiaTraps
		VARIABLES     {gwiaTrapTime, gwiaGatewayName}
		DESCRIPTION   "The threshold for messages in SMTP daemon receive area for GroupWise Internet Agent has been exceeded (RECEIVE)"
		--NMS Trap annotation
		--#TYPE       "The threshold for messages in SMTP daemon receive area for GroupWise Internet Agent has been exceeded (RECEIVE)"
		--#SUMMARY    "GroupWise Internet Agent %s has exceeded its threshold for received daemon messages (RECEIVE)"
		--#ARGUMENTS  {1}
		--#SEVERITY   INFORMATIONAL
		--#TIMEINDEX  0
		--#STATE      OPERATIONAL
		::= 51

gwiasmtpDeferThreshTrap TRAP-TYPE
		ENTERPRISE    gwiaTraps
		VARIABLES     {gwiaTrapTime, gwiaGatewayName}
		DESCRIPTION   "The threshold for messages in SMTP daemon defer area for GroupWise Internet Agent has been exceeded (DEFER)"
		--NMS Trap annotation
		--#TYPE       "The threshold for messages in SMTP daemon defer area for GroupWise Internet Agent has been exceeded (DEFER)"
		--#SUMMARY    "GroupWise Internet Agent %s has exceeded its threshold for daemon defer messages (DEFER)"
		--#ARGUMENTS  {1}
		--#SEVERITY   INFORMATIONAL
		--#TIMEINDEX  0
		--#STATE      OPERATIONAL
		::= 52



END
