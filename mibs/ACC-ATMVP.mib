ACC-ATMVP DEFINITIONS ::= BEGIN

    IMPORTS
   	 OBJECT-TYPE, Counter FROM RFC1155-SMI
		 accTrapLogSeqNum FROM ACC-SYSTEM
	accBRG, DisplayString, RowStatus, IfIndex, SmdsAddress
             FROM ACC-MIB
        accSysInfo FROM ACC-SYSTEM;

-- ACC ATM Virtual Port Group
--
--
-- ACC ATM Virtual port support and services
--
accAtmVp		OBJECT IDENTIFIER ::= { accBRG 73 }
--
-- The Virtual port table
--
accVpTable             	OBJECT-TYPE         
SYNTAX              	SEQUENCE OF AccVpEntry             
ACCESS          	not-accessible           
STATUS              	mandatory           
DESCRIPTION         
	" The Virtual port table. "
::= { accAtmVp 1 }
accVpEntry             	OBJECT-TYPE         
SYNTAX              	AccVpEntry               
ACCESS          	not-accessible                
STATUS              	mandatory           
DESCRIPTION         
	" An entry in the virtual port table. "
INDEX			{ oVirtualPortName }
::= { accVpTable 1 }
AccVpEntry ::=
      SEQUENCE {
	 oVirtualPortName        	IfIndex,
	 oVirtualPortAdminState  	INTEGER,
	 oVirtualPortOperState   	INTEGER,
	 oVirtualPortProtocol    	INTEGER,
	 oVirtualPortQueueMode   	INTEGER,
	 oVirtualPortCongestion  	INTEGER,
	 oVirtualPortPhysicalPort	INTEGER
}
oVirtualPortName		OBJECT-TYPE
SYNTAX				IfIndex 
ACCESS				read-only
STATUS				mandatory
DESCRIPTION
	"IfIndex for virtual port. "
::= { accVpEntry 1 }
oVirtualPortAdminState		OBJECT-TYPE
SYNTAX				INTEGER { up(1), down(2) }
ACCESS				read-write
STATUS				mandatory
DESCRIPTION
	" The Admin state of a virtual port. "
::= { accVpEntry 2 }
oVirtualPortOperState		OBJECT-TYPE
SYNTAX				INTEGER  { up(1), down(2) }
ACCESS				read-only
STATUS				mandatory
DESCRIPTION
	" The operational state of a virtual port. "
::= { accVpEntry 3 }
oVirtualPortProtocol		OBJECT-TYPE
SYNTAX				INTEGER { none(1), 
					  lane(2),
					  rfc1483(3),
					  cip(4),
					  ppp(5),
					  frf5(6) }
ACCESS				read-only
STATUS				mandatory
DESCRIPTION
	" The protocol used over a virtual port. "
::= { accVpEntry 4 }
oVirtualPortQueueMode		OBJECT-TYPE
SYNTAX				INTEGER { express(1) }
ACCESS				read-only
STATUS				mandatory
DESCRIPTION
	" Queuing mode used. Currently only EXPRESS queueing. "
::= { accVpEntry 5 }
oVirtualPortCongestion		OBJECT-TYPE
SYNTAX				INTEGER 
ACCESS				read-only
STATUS				mandatory
DESCRIPTION
	" The congestion percent. "
::= { accVpEntry 6 }
oVirtualPortPhysicalPort		OBJECT-TYPE
SYNTAX					INTEGER 
ACCESS					read-only
STATUS					mandatory
DESCRIPTION
	" The physical port associated with a virtual port. "
::= { accVpEntry 7 }
--
-- Scalars
--
accAtmVpScalarGrp	OBJECT IDENTIFIER ::= { accAtmVp 2 }
oVirtualPortCount1483Br		OBJECT-TYPE
SYNTAX				INTEGER 
ACCESS				read-write
STATUS				mandatory
DESCRIPTION
	" The RFC1483 virtual port count. "
::= { accAtmVpScalarGrp 1 }
oVirtualPortCountCIP		OBJECT-TYPE
SYNTAX				INTEGER 
ACCESS				read-write
STATUS				mandatory
DESCRIPTION
	" The CIP virtual port count. "
::= { accAtmVpScalarGrp 2 }
oVirtualPortCountTunnel		OBJECT-TYPE
SYNTAX				INTEGER 
ACCESS				read-write
STATUS				mandatory
DESCRIPTION
	" The Tunnel virtual port count. "
::= { accAtmVpScalarGrp 3 }
oVirtualPortCountFrf		OBJECT-TYPE
SYNTAX				INTEGER 
ACCESS				read-write
STATUS				mandatory
DESCRIPTION
	" The FRF virtual port count. "
::= { accAtmVpScalarGrp 4 }
oVirtualPortCountPpp		OBJECT-TYPE
SYNTAX				INTEGER 
ACCESS				read-write
STATUS				mandatory
DESCRIPTION
	" The PPP over ATM virtual port count. "
::= { accAtmVpScalarGrp 6 }
oVirtualPortCountVFR		OBJECT-TYPE
SYNTAX				INTEGER 
ACCESS				read-write
STATUS				mandatory
DESCRIPTION
	" The Virtual Frame Relay virtual port count. "
::= { accAtmVpScalarGrp 7 }
oVirtualPortCountXOT		OBJECT-TYPE
SYNTAX				INTEGER 
ACCESS				read-write
STATUS				mandatory
DESCRIPTION
	" The XOT virtual port count. "
::= { accAtmVpScalarGrp 8 }
--
-- ATM VP statistics group
--
accAtmVpStatsGrp	OBJECT IDENTIFIER ::= { accAtmVp 3 }
--
-- The Virtual port statistics table (general)
--
accVpStatTable         	OBJECT-TYPE         
SYNTAX              	SEQUENCE OF AccVpStatEntry             
ACCESS          	not-accessible           
STATUS              	mandatory           
DESCRIPTION         
	" The virtual port statistics table. "
::= { accAtmVpStatsGrp 1 }
accVpStatEntry         	OBJECT-TYPE         
SYNTAX              	AccVpStatEntry               
ACCESS          	not-accessible                
STATUS              	mandatory           
DESCRIPTION         
	" An entry in the virtual port statistics table. "
INDEX			{ oVpStatName }
::= { accVpStatTable 1 }
AccVpStatEntry ::=
      SEQUENCE {
	 oVpStatName             	IfIndex,
	 oVpStatInPackets         	Counter,
	 oVpStatOutPackets        	Counter,
	 oVpStatInOctets          	Counter,
	 oVpStatOutOctets         	Counter,
	 oVpStatInDiscards        	Counter,
	 oVpStatOutDiscards       	Counter,
	 oVpStatNumChangeds       	Counter,
	 oVpStatInErrs            	Counter,
	 oVpStatOutErrs           	Counter
}
oVpStatName		OBJECT-TYPE
SYNTAX			IfIndex 
ACCESS			read-only
STATUS			mandatory
DESCRIPTION
	" ifIndex of the Virtual port. "
::= { accVpStatEntry 1 }
oVpStatInPackets	OBJECT-TYPE
SYNTAX			Counter 
ACCESS			read-only
STATUS			mandatory
DESCRIPTION
	" Received packets. "
::= { accVpStatEntry 2 }
oVpStatOutPackets		OBJECT-TYPE
SYNTAX				Counter 
ACCESS				read-only
STATUS				mandatory
DESCRIPTION
	" Packets sent out. "
::= { accVpStatEntry 3 }
oVpStatInOctets		OBJECT-TYPE
SYNTAX			Counter 
ACCESS			read-only
STATUS			mandatory
DESCRIPTION
	" Octets received. "
::= { accVpStatEntry 4 }
oVpStatOutOctets	OBJECT-TYPE
SYNTAX			Counter 
ACCESS			read-only
STATUS			mandatory
DESCRIPTION
	" Octets sent out. "
::= { accVpStatEntry 5 }
oVpStatInDiscards		OBJECT-TYPE
SYNTAX				Counter 
ACCESS				read-only
STATUS				mandatory
DESCRIPTION
	" Number of receive discards. "
::= { accVpStatEntry 6 }
oVpStatOutDiscards		OBJECT-TYPE
SYNTAX				Counter 
ACCESS				read-only
STATUS				mandatory
DESCRIPTION
	" Number of transmit discards. "
::= { accVpStatEntry 7 }
oVpStatNumChangeds		OBJECT-TYPE
SYNTAX				Counter 
ACCESS				read-only
STATUS				mandatory
DESCRIPTION
	" Number of changes. "
::= { accVpStatEntry 8 }
oVpStatInErrs		OBJECT-TYPE
SYNTAX			Counter 
ACCESS			read-only
STATUS			mandatory
DESCRIPTION
	" Number of received packets in error. "
::= { accVpStatEntry 9 }
oVpStatOutErrs		OBJECT-TYPE
SYNTAX			Counter 
ACCESS			read-only
STATUS			mandatory
DESCRIPTION
	" Number of packets attempted to transmit that were in error. "
::= { accVpStatEntry 10 }
--
-- ATM FRF group
--
accAtmVpFrfGrp		OBJECT IDENTIFIER ::= { accAtmVp 4 }
--
-- The FRF configuration table
--
vpAtmFrfTable         	OBJECT-TYPE         
SYNTAX              	SEQUENCE OF VpAtmFrfEntry             
ACCESS          	not-accessible           
STATUS              	mandatory           
DESCRIPTION         
	" The FRF (Frame relay network interworking over ATM) table. "
::= { accAtmVpFrfGrp 1 }
vpAtmFrfEntry         	OBJECT-TYPE         
SYNTAX              	VpAtmFrfEntry               
ACCESS          	not-accessible                
STATUS              	mandatory           
DESCRIPTION         
	" An entry in the FRF table. "
INDEX               	{ oVpAtmFrfName }
::= { vpAtmFrfTable 1 }
VpAtmFrfEntry ::=
      SEQUENCE {
	 oVpAtmFrfName           	IfIndex,
	 oVpAtmFrfRetryTimer     	INTEGER,
	 oVpAtmFrfRetryCount     	INTEGER,
	 oVpAtmFrfDlciLimit      	INTEGER,
	 oVpAtmFrfAddrLength     	INTEGER,
	 oVpAtmFrfPvcDlciStart   	INTEGER,
	 oVpAtmFrfPvcDlciEnd     	INTEGER,
	 oVpAtmFrfPvcVpi         	INTEGER,
	 oVpAtmFrfPvcVci         	INTEGER,
	 oVpAtmFrfCongTimeOut    	INTEGER,
	 oVpAtmFrfCellLossPrioIn 	INTEGER,
	 oVpAtmFrfCellLossPrioOut	INTEGER,
	 oVpAtmFrfClpMode        	INTEGER
}
oVpAtmFrfName		OBJECT-TYPE
SYNTAX			IfIndex 
ACCESS			read-only		
STATUS			mandatory
DESCRIPTION
	" The internal name for this port"
::= { vpAtmFrfEntry 1 }
oVpAtmFrfRetryTimer		OBJECT-TYPE
SYNTAX				INTEGER 
ACCESS				read-write
STATUS				mandatory
DESCRIPTION
	" The amount of time before retrying to reconnect the circuit"
::= { vpAtmFrfEntry 2 }
oVpAtmFrfRetryCount		OBJECT-TYPE
SYNTAX				INTEGER 
ACCESS				read-write
STATUS				mandatory
DESCRIPTION
	" The number of times to retry the connection before declaring that
		the circuit is down "
::= { vpAtmFrfEntry 3 }
oVpAtmFrfDlciLimit		OBJECT-TYPE
SYNTAX				INTEGER 
ACCESS				read-write
STATUS				mandatory
DESCRIPTION
	" The number of DLCI that can be active on this port "
::= { vpAtmFrfEntry 4 }
oVpAtmFrfAddrLength		OBJECT-TYPE
SYNTAX				INTEGER 
ACCESS				read-write
STATUS				mandatory
DESCRIPTION
	" The Frame Relay address length for this port"
::= { vpAtmFrfEntry 5 }
oVpAtmFrfPvcDlciStart		OBJECT-TYPE
SYNTAX				INTEGER 
ACCESS				read-write
STATUS				mandatory
DESCRIPTION
	" The starting DLCI number for this port"
::= { vpAtmFrfEntry 6 }
oVpAtmFrfPvcDlciEnd		OBJECT-TYPE
SYNTAX				INTEGER 
ACCESS				read-write
STATUS				mandatory
DESCRIPTION
	" The ending DLCI number for this port"
::= { vpAtmFrfEntry 7 }
oVpAtmFrfPvcVpi		OBJECT-TYPE
SYNTAX			INTEGER 
ACCESS			read-write
STATUS			mandatory
DESCRIPTION
	" The VPI for the circuit that needs to be created over this port"
::= { vpAtmFrfEntry 8 }
oVpAtmFrfPvcVci		OBJECT-TYPE
SYNTAX			INTEGER 
ACCESS			read-write
STATUS			mandatory
DESCRIPTION
	" The VCI for the circuit that needs to be created overt his port"
::= { vpAtmFrfEntry 9 }
oVpAtmFrfCongTimeOut		OBJECT-TYPE
SYNTAX				INTEGER 
ACCESS				read-write
STATUS				mandatory
DESCRIPTION
	" The amount of time that needs to elapse in seconds before declaring
		that the circuit is down due to congestion"
::= { vpAtmFrfEntry 10 }
oVpAtmFrfCellLossPrioIn		OBJECT-TYPE
SYNTAX				INTEGER 
ACCESS				read-write
STATUS				mandatory
DESCRIPTION
	" The CLP for incoming cells"
::= { vpAtmFrfEntry 11 }
oVpAtmFrfCellLossPrioOut		OBJECT-TYPE
SYNTAX					INTEGER 
ACCESS					read-write
STATUS					mandatory
DESCRIPTION
	" The CLP for outgoing cells"
::= { vpAtmFrfEntry 12 }
oVpAtmFrfClpMode		OBJECT-TYPE
SYNTAX				INTEGER 
ACCESS				read-write
STATUS				mandatory
DESCRIPTION
	" The CLP mode for mapping from the DE bit "
::= { vpAtmFrfEntry 13 }
--
-- PPP over ATM group
--
accAtmVpPppGrp		OBJECT IDENTIFIER ::= { accAtmVp 5 }
--
-- The PPP over ATM configuration table 
--
vpAtmPppTable          	OBJECT-TYPE         
SYNTAX              	SEQUENCE OF VpAtmPppEntry             
ACCESS          	not-accessible           
STATUS              	mandatory           
DESCRIPTION         
	" The PPP over ATM configuration table. "
::= { accAtmVpPppGrp 1 }
vpAtmPppEntry          	OBJECT-TYPE         
SYNTAX              	VpAtmPppEntry               
ACCESS          	not-accessible                
STATUS              	mandatory           
DESCRIPTION         
	" An entry in the PPP over ATM configuration table. "
INDEX               	{ oVpAtmPppName }
::= { vpAtmPppTable 1 }
VpAtmPppEntry ::=
      SEQUENCE {
	 oVpAtmPppName           	IfIndex,
	 oVpAtmPppRetryTimer     	INTEGER,
	 oVpAtmPppRetryCount     	INTEGER,
	 oVpAtmPppVpi            	INTEGER,
	 oVpAtmPppVci            	INTEGER,
	 oVpAtmPppCongTimeOut    	INTEGER,
	 oVpAtmPppMuxType        	INTEGER
}
oVpAtmPppName		OBJECT-TYPE
SYNTAX			IfIndex 
ACCESS			read-only
STATUS			mandatory
DESCRIPTION
	" The internal name for this port"
::= { vpAtmPppEntry 1 }
oVpAtmPppRetryTimer		OBJECT-TYPE
SYNTAX				INTEGER 
ACCESS				read-write
STATUS				mandatory
DESCRIPTION
	" The amount of time to wait before retrying the connection"
::= { vpAtmPppEntry 2 }
oVpAtmPppRetryCount		OBJECT-TYPE
SYNTAX				INTEGER 
ACCESS				read-write
STATUS				mandatory
DESCRIPTION
	" The number of time to retry for the connection if it not up"
::= { vpAtmPppEntry 3 }
oVpAtmPppVpi		OBJECT-TYPE
SYNTAX			INTEGER 
ACCESS			read-write
STATUS			mandatory
DESCRIPTION
	" The VPI for the circuit that needs to be created over this port"
::= { vpAtmPppEntry 4 }
oVpAtmPppVci		OBJECT-TYPE
SYNTAX			INTEGER 
ACCESS			read-write
STATUS			mandatory
DESCRIPTION
	" The VCI for the circuit that needs to be created over this port"
::= { vpAtmPppEntry 5 }
oVpAtmPppCongTimeOut		OBJECT-TYPE
SYNTAX				INTEGER 
ACCESS				read-write
STATUS				mandatory
DESCRIPTION
	" The amount of time to wait for the congestion to clear out before
		declaring the circuit to be down"
::= { vpAtmPppEntry 6 }
oVpAtmPppMuxType		OBJECT-TYPE
SYNTAX				INTEGER 
ACCESS				read-write
STATUS				mandatory
DESCRIPTION
	" The multiplexing that needs to be done over this port"
::= { vpAtmPppEntry 7 }
--
-- RFC1483 group
--
accAtmVp1483Grp		OBJECT IDENTIFIER ::= { accAtmVp 6 }
--
-- Multiprotocol encapsulation over ATM configuration table
-- RFC1483
--
vpAtm1483Table         	OBJECT-TYPE         
SYNTAX              	SEQUENCE OF VpAtm1483Entry             
ACCESS          	not-accessible           
STATUS              	mandatory           
DESCRIPTION         	
	" The RFC1483 configuration table. "
::= { accAtmVp1483Grp 1 }
vpAtm1483Entry         	OBJECT-TYPE         
SYNTAX              	VpAtm1483Entry               
ACCESS          	not-accessible                
STATUS              	mandatory           
DESCRIPTION         
	" An entry in the RFC1483 configuration table. "
INDEX               	{ oVpAtm1483Name }
::= { vpAtm1483Table 1 }
VpAtm1483Entry ::=
      SEQUENCE {
	 oVpAtm1483Name          	IfIndex,
	 oVpAtm1483RetryTimer    	INTEGER,
	 oVpAtm1483RetryCount    	INTEGER,
	 oVpAtm1483Vpi           	INTEGER,
	 oVpAtm1483Vci           	INTEGER,
	 oVpAtm1483CongTimeOut   	INTEGER,
	 oVpAtm1483MuxType       	INTEGER
}
oVpAtm1483Name		OBJECT-TYPE
SYNTAX			IfIndex 
ACCESS			read-only
STATUS			mandatory
DESCRIPTION
	" The internal name for this port"
::= { vpAtm1483Entry 1 }
oVpAtm1483RetryTimer		OBJECT-TYPE
SYNTAX				INTEGER 
ACCESS				read-write
STATUS				mandatory
DESCRIPTION
	" The amount of time to wait before retrying the connection"
::= { vpAtm1483Entry 2 }
oVpAtm1483RetryCount		OBJECT-TYPE
SYNTAX				INTEGER 
ACCESS				read-write
STATUS				mandatory
DESCRIPTION
	" The number of time to retry for the connection if it not up"
::= { vpAtm1483Entry 3 }
oVpAtm1483Vpi		OBJECT-TYPE
SYNTAX			INTEGER 
ACCESS			read-write
STATUS			mandatory
DESCRIPTION
	" The VPI for the circuit that needs to be created over this port"
::= { vpAtm1483Entry 4 }
oVpAtm1483Vci		OBJECT-TYPE
SYNTAX			INTEGER 
ACCESS			read-write
STATUS			mandatory
DESCRIPTION
	" The VCI for the circuit that needs to be created over this port"
::= { vpAtm1483Entry 5 }
oVpAtm1483CongTimeOut		OBJECT-TYPE
SYNTAX				INTEGER 
ACCESS				read-write
STATUS				mandatory
DESCRIPTION
	" The amount of time to wait for the congestion to clear out before
                declaring the circuit to be down"
::= { vpAtm1483Entry 6 }
oVpAtm1483MuxType		OBJECT-TYPE
SYNTAX				INTEGER 
ACCESS				read-write
STATUS				mandatory
DESCRIPTION
	" The multiplexing that needs to be done over this port"
::= { vpAtm1483Entry 7 }
--
-- Classical IP over ATM group
--
accAtmVpCipGrp		OBJECT IDENTIFIER ::= { accAtmVp 7 }
--
-- The Classical IP over ATM (CIP) configuration table
--
vpAtmCipTable          	OBJECT-TYPE         
SYNTAX              	SEQUENCE OF VpAtmCipEntry             
ACCESS          	not-accessible           
STATUS              	mandatory           
DESCRIPTION         
	" The Classical IP over ATM configuration table. "
::= { accAtmVpCipGrp 1 }
vpAtmCipEntry          	OBJECT-TYPE         
SYNTAX              	VpAtmCipEntry               
ACCESS          	not-accessible                
STATUS              	mandatory           
DESCRIPTION         
	" An entry in the CIP table. "
INDEX               	{ oVpAtmCipName }
::= { vpAtmCipTable 1 }
VpAtmCipEntry ::=
      SEQUENCE {
	 oVpAtmCipName           	IfIndex,
	 oVpAtmCipRetryTimer     	INTEGER,
	 oVpAtmCipRetryCount     	INTEGER,
	 oVpAtmCipMode           	INTEGER,
	 oVpAtmCipAging          	INTEGER,
	 oVpAtmCipAddrType       	INTEGER,
	 oVpAtmCipLocalAddress   	DisplayString,
	 oVpAtmCipServerAddress  	DisplayString,
	 oVpAtmCipServerVccType  	INTEGER,
	 oVpAtmCipMtu            	INTEGER,
	 oVpAtmCipPcr            	INTEGER
}
oVpAtmCipName		OBJECT-TYPE
SYNTAX			IfIndex 
ACCESS			read-only
STATUS			mandatory
DESCRIPTION
	" The internal name for this port"
::= { vpAtmCipEntry 1 }
oVpAtmCipRetryTimer		OBJECT-TYPE
SYNTAX				INTEGER 
ACCESS				read-write
STATUS				mandatory
DESCRIPTION
	" The amount of time to wait before retrying the connection"
::= { vpAtmCipEntry 2 }
oVpAtmCipRetryCount		OBJECT-TYPE
SYNTAX				INTEGER 
ACCESS				read-write
STATUS				mandatory
DESCRIPTION
	" The number of time to retry for the connection if it not up"
::= { vpAtmCipEntry 3 }
oVpAtmCipMode		OBJECT-TYPE
SYNTAX			INTEGER 
ACCESS			read-write
STATUS			mandatory
DESCRIPTION
	" The operation mode for this CIP port"
::= { vpAtmCipEntry 4 }
oVpAtmCipAging		OBJECT-TYPE
SYNTAX			INTEGER 
ACCESS			read-write
STATUS			mandatory
DESCRIPTION
	" The time that needs to elapse in seconds before aging this circuit"
::= { vpAtmCipEntry 5 }
oVpAtmCipAddrType		OBJECT-TYPE
SYNTAX				INTEGER 
ACCESS				read-write
STATUS				mandatory
DESCRIPTION
	" The type of address supported ovwer this port"
::= { vpAtmCipEntry 6 }
oVpAtmCipLocalAddress		OBJECT-TYPE
SYNTAX				DisplayString 
ACCESS				read-write
STATUS				mandatory
DESCRIPTION
	" The local address for this port that is used in identifying this 
		instance on the atm network"
::= { vpAtmCipEntry 7 }
oVpAtmCipServerAddress		OBJECT-TYPE
SYNTAX				DisplayString 
ACCESS				read-write
STATUS				mandatory
DESCRIPTION
	" The address at which the server is reachable"
::= { vpAtmCipEntry 8 }
oVpAtmCipServerVccType		OBJECT-TYPE
SYNTAX				INTEGER 
ACCESS				read-write
STATUS				mandatory
DESCRIPTION
	" The curcuit types the server will be able to accept"
::= { vpAtmCipEntry 9 }
oVpAtmCipMtu		OBJECT-TYPE
SYNTAX			INTEGER 
ACCESS			read-write
STATUS			mandatory
DESCRIPTION
	" The MTU for this port"
::= { vpAtmCipEntry 10 }
oVpAtmCipPcr		OBJECT-TYPE
SYNTAX			INTEGER 
ACCESS			read-write
STATUS			mandatory
DESCRIPTION
	" The PCR to be used for the circuts over this port"
::= { vpAtmCipEntry 11 }

END
