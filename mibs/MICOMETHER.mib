--
-- MIB Revision Dated: 05-31-96 
-- 
-- 
-- MIB Revision : 1.0 dated 1-17-97
-- Change Desc. : None. 
-- 
--
-- Added access privilages to capabilities field  
-- By Sanjeev Gaur on 4/22/97  
-- 
--
-- *** RELEASE 3.0 ***
-- MIB Revision : 1.1 dated 6-24-98
-- Change Desc. : Obsoleted counter reset table,
--				  mcmEthCntrZeroTable. -A. Llanes
--
    MICOMETHER DEFINITIONS ::= BEGIN

    IMPORTS
	    micom-oscar 
		    FROM MICOM-OSCAR-MIB
            OBJECT-TYPE
                    FROM RFC-1212;


    --  this is the MIB module for MICOM Ethernet objects

   mcmEth    OBJECT IDENTIFIER ::= { micom-oscar 10 }

  -- The Counter Reset Group


   mcmEthCntr    OBJECT IDENTIFIER ::= { mcmEth 1 }


mcmEthCntrZeroTable OBJECT-TYPE
        SYNTAX  SEQUENCE OF McmEthCntrZeroEntry
        ACCESS  not-accessible
        STATUS  obsolete
	DESCRIPTION
	  "NAME = ;
       DESC = This table was obsoleted as of release \
	      	  3.0; and is included here only to support \
	          backwards compatibility for software \
	          versions prior to release 3.0. \
	   		  A table that contains the ethernet Port\
              specific information regarding counters\
              that can be Zeroed.;
	   HELP = A table that contains port-specific \
		  information for the MICOM Port Counter \
		  Zeroing.;
	   CAPABILITIES = NET_CFG, VPN_CFG;"
              ::= { mcmEthCntr 1 }

          mcmEthCntrZeroEntry OBJECT-TYPE
        SYNTAX  McmEthCntrZeroEntry
        ACCESS  not-accessible
        STATUS  obsolete
	DESCRIPTION
	  "NAME = ;
       DESC = This object was obsoleted as of release \
	      	  3.0; and is included here only to support \
	          backwards compatibility for software \
	          versions prior to release 3.0. \
	   		  The list of information maintained by\
              the ethernet Port specific to the\
              ethernet counters.;
	   HELP = A list of information maintained by \
		  every port about the MICOM E-type Filter \
		  parameters for that port.;
	   CAPABILITIES = ;"
              INDEX   { mcmEthCntrZeroPort }
              ::= { mcmEthCntrZeroTable 1 }

          McmEthCntrZeroEntry ::=
              SEQUENCE {
                  mcmEthCntrZeroPort
                      INTEGER,
                  mcmEthStatsGrpCounterZero
                      INTEGER,
                  mcmEthCollStatsGrpCounterZero
                      INTEGER
	}


mcmEthCntrZeroPort OBJECT-TYPE
	SYNTAX	INTEGER
	ACCESS	read-write
	STATUS	obsolete
	DESCRIPTION
	  "NAME = ;
       DESC = This object was obsoleted as of release \
	      	  3.0; and is included here only to support \
	          backwards compatibility for software \
	          versions prior to release 3.0. \
	   		  The ethernet Port that these counters\
              pertain to.;
	   HELP = The Port to which this entry pertains.;
	   CAPABILITIES = ;"
	::= { mcmEthCntrZeroEntry 1 }

mcmEthStatsGrpCounterZero OBJECT-TYPE
        SYNTAX  INTEGER { reset(1), other(2) }
	ACCESS	write-only
        STATUS obsolete 
	DESCRIPTION
	  "NAME = ;
       DESC = This object was obsoleted as of release \
	      	  3.0; and is included here only to support \
	          backwards compatibility for software \
	          versions prior to release 3.0. \
	   		  When reset counter information is performed,\
              the ethernet statistic group counter info.\
              collected will reset to zero.;
	   HELP = When set to reset, the StatsGrp Counters \
		  should be zeroed out.;
	   CAPABILITIES = ;"
        ::= { mcmEthCntrZeroEntry 2 }

mcmEthCollStatsGrpCounterZero OBJECT-TYPE
        SYNTAX  INTEGER { reset(1), other(2) }
	ACCESS	write-only
        STATUS  obsolete 
	DESCRIPTION
	  "NAME = ;
       DESC = This object was obsoleted as of release \
	      	  3.0; and is included here only to support \
	          backwards compatibility for software \
	          versions prior to release 3.0. \
	   		  When reset counter information is performed,\
              the ethernet collusion statistics group counter\
              information collected will reset to Zero.;
	   HELP = When set to reset, the Collision StatsGrp \
		  Counters should be zeroed out.;
	   CAPABILITIES = ;"
        ::= { mcmEthCntrZeroEntry 3 }

END
