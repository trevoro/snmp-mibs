Nortel-Magellan-Passport-AtmNetworkingMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      Gauge32,
      Integer32,
      Unsigned32
   FROM Nortel-Magellan-Passport-StandardTextualConventionsMIB

      AsciiString,
      NonReplicated,
      HexString,
      FixedPoint1,
      AsciiStringIndex,
      IntegerSequence
   FROM Nortel-Magellan-Passport-TextualConventionsMIB

      atmIfVccIndex,
      atmIfVptIndex,
      atmIfVcc,
      atmIfVpcIndex,
      atmIfVpc,
      atmIfVptVccIndex,
      atmIfIndex,
      atmIfVptVcc
   FROM Nortel-Magellan-Passport-AtmCoreMIB;




-- LAST-UPDATED   "9904150000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmNetworking Enterprise MIB."

atmNetworkingMIB OBJECT IDENTIFIER ::= { passportMIBs 42 }










-- AtmRouting
-- This component contains the provisionable and operational 
-- attributes related to ATM PNNI routing. 
-- 
-- The Dna subcomponents can be listed to view all the provisioned 
-- and registered ATM end system addresses and prefixes stored 
-- against any of the Uni, Iisp or Pnni interfaces.
-- 
-- The Pnni subcomponent can be provisioned to identify that this 
-- Passport node participates in a PNNI hierarchy. 
-- 
-- The ConfiguredNode subcomponents are indexed by level in the 
-- PNNI hierarchy (a value between 0 and 104), and define 
-- configuration information.

aRtg OBJECT IDENTIFIER ::= { components 95 }



aRtgRowStatusTable OBJECT-TYPE
   SYNTAX     SEQUENCE OF ARtgRowStatusEntry
   ACCESS     not-accessible
   STATUS     mandatory
   DESCRIPTION
     "This entry controls the addition and deletion of 
      aRtg components."
::= { aRtg 1 }

aRtgRowStatusEntry OBJECT-TYPE
   SYNTAX     ARtgRowStatusEntry
   ACCESS     not-accessible
   STATUS     mandatory
   DESCRIPTION
     "A single entry in the table represents a single 
      aRtg component."
   INDEX {
      aRtgIndex }
::= { aRtgRowStatusTable 1 }

ARtgRowStatusEntry ::= SEQUENCE {
   aRtgRowStatus
      RowStatus,
   aRtgComponentName
      DisplayString,
   aRtgStorageType
      StorageType,
   aRtgIndex
      NonReplicated }

aRtgRowStatus OBJECT-TYPE
   SYNTAX     RowStatus 
   ACCESS     read-write
   STATUS     mandatory
   DESCRIPTION
     "This variable is used as the basis for SNMP naming of
      aRtg components.
      These components can be added and deleted."
::= { aRtgRowStatusEntry 1 }

aRtgComponentName OBJECT-TYPE
   SYNTAX     DisplayString 
   ACCESS     read-only
   STATUS     mandatory
   DESCRIPTION
     "This variable provides the component's string name for
      use with the ASCII Console Interface"
::= { aRtgRowStatusEntry 2 }

aRtgStorageType OBJECT-TYPE
   SYNTAX     StorageType 
   ACCESS     read-only
   STATUS     mandatory
   DESCRIPTION
     "This variable represents the storage type value for the
      aRtg tables."
::= { aRtgRowStatusEntry 4 }

aRtgIndex OBJECT-TYPE
   SYNTAX     NonReplicated 
   ACCESS     not-accessible
   STATUS     mandatory
   DESCRIPTION
     "This variable represents the index for the aRtg tables."
::= { aRtgRowStatusEntry 10 }

aRtgStatsTable OBJECT-TYPE
   SYNTAX     SEQUENCE OF ARtgStatsEntry
   ACCESS     not-accessible
   STATUS     mandatory
   DESCRIPTION
     "This group contains the statistical operational attributes of an ARtg 
      component."
::= { aRtg 10 }

aRtgStatsEntry OBJECT-TYPE
   SYNTAX     ARtgStatsEntry
   ACCESS     not-accessible
   STATUS     mandatory
   DESCRIPTION
     "An entry in the aRtgStatsTable."
   INDEX {
      aRtgIndex }
::= { aRtgStatsTable 1 }

ARtgStatsEntry ::= SEQUENCE {
   aRtgRoutingAttempts
      Counter32,
   aRtgFailedRoutingAttempts
      Counter32 }

aRtgRoutingAttempts OBJECT-TYPE
   SYNTAX     Counter32 
   ACCESS     read-only
   STATUS     mandatory
   DESCRIPTION
     "This attribute counts the total number of calls routed. The counter 
      wraps when it exceeds the maximum value."
::= { aRtgStatsEntry 1 }

aRtgFailedRoutingAttempts OBJECT-TYPE
   SYNTAX     Counter32 
   ACCESS     read-only
   STATUS     mandatory
   DESCRIPTION
     "This attribute counts the total number of calls which were not 
      successfully routed.The counter wraps when it exceeds the 
      maximum value."
::= { aRtgStatsEntry 2 }

-- 
-- *** THIS SUBTREE CURRENTLY NOT IMPLEMENTED ***
-- 

-- ARtg Dna/<ATM address>
-- This component represents an ATM NSAP address that has been 
-- provisioned or dynamically registered through ILMI.

aRtgDna OBJECT IDENTIFIER ::= { aRtg 2 }



aRtgDnaRowStatusTable OBJECT-TYPE
   SYNTAX     SEQUENCE OF ARtgDnaRowStatusEntry
   ACCESS     not-accessible
   STATUS     mandatory
   DESCRIPTION
     "*** THIS TABLE CURRENTLY NOT IMPLEMENTED ***

      This entry controls the addition and deletion of 
      aRtgDna components."
::= { aRtgDna 1 }

aRtgDnaRowStatusEntry OBJECT-TYPE
   SYNTAX     ARtgDnaRowStatusEntry
   ACCESS     not-accessible
   STATUS     mandatory
   DESCRIPTION
     "A single entry in the table represents a single 
      aRtgDna component."
   INDEX {
      aRtgIndex,
      aRtgDnaIndex }
::= { aRtgDnaRowStatusTable 1 }

ARtgDnaRowStatusEntry ::= SEQUENCE {
   aRtgDnaRowStatus
      RowStatus,
   aRtgDnaComponentName
      DisplayString,
   aRtgDnaStorageType
      StorageType,
   aRtgDnaIndex
      AsciiStringIndex }

aRtgDnaRowStatus OBJECT-TYPE
   SYNTAX     RowStatus 
   ACCESS     read-only
   STATUS     mandatory
   DESCRIPTION
     "This variable is used as the basis for SNMP naming of
      aRtgDna components.
      These components cannot be added nor deleted."
::= { aRtgDnaRowStatusEntry 1 }

aRtgDnaComponentName OBJECT-TYPE
   SYNTAX     DisplayString 
   ACCESS     read-only
   STATUS     mandatory
   DESCRIPTION
     "This variable provides the component's string name for
      use with the ASCII Console Interface"
::= { aRtgDnaRowStatusEntry 2 }

aRtgDnaStorageType OBJECT-TYPE
   SYNTAX     StorageType 
   ACCESS     read-only
   STATUS     mandatory
   DESCRIPTION
     "This variable represents the storage type value for the
      aRtgDna tables."
::= { aRtgDnaRowStatusEntry 4 }

aRtgDnaIndex OBJECT-TYPE
   SYNTAX     AsciiStringIndex (SIZE (1..40))
   ACCESS     not-accessible
   STATUS     mandatory
   DESCRIPTION
     "This variable represents the index for the aRtgDna tables."
::= { aRtgDnaRowStatusEntry 10 }

-- 
-- *** THIS SUBTREE CURRENTLY NOT IMPLEMENTED ***
-- 

-- ARtg Dna/<ATM address> DestInfo/<n>
-- This component represents a destination associated with the parent 
-- Dna.

aRtgDnaDestInfo OBJECT IDENTIFIER ::= { aRtgDna 2 }



aRtgDnaDestInfoRowStatusTable OBJECT-TYPE
   SYNTAX     SEQUENCE OF ARtgDnaDestInfoRowStatusEntry
   ACCESS     not-accessible
   STATUS     mandatory
   DESCRIPTION
     "*** THIS TABLE CURRENTLY NOT IMPLEMENTED ***

      This entry controls the addition and deletion of 
      aRtgDnaDestInfo components."
::= { aRtgDnaDestInfo 1 }

aRtgDnaDestInfoRowStatusEntry OBJECT-TYPE
   SYNTAX     ARtgDnaDestInfoRowStatusEntry
   ACCESS     not-accessible
   STATUS     mandatory
   DESCRIPTION
     "A single entry in the table represents a single 
      aRtgDnaDestInfo component."
   INDEX {
      aRtgIndex,
      aRtgDnaIndex,
      aRtgDnaDestInfoIndex }
::= { aRtgDnaDestInfoRowStatusTable 1 }

ARtgDnaDestInfoRowStatusEntry ::= SEQUENCE {
   aRtgDnaDestInfoRowStatus
      RowStatus,
   aRtgDnaDestInfoComponentName
      DisplayString,
   aRtgDnaDestInfoStorageType
      StorageType,
   aRtgDnaDestInfoIndex
      Integer32 }

aRtgDnaDestInfoRowStatus OBJECT-TYPE
   SYNTAX     RowStatus 
   ACCESS     read-only
   STATUS     mandatory
   DESCRIPTION
     "This variable is used as the basis for SNMP naming of
      aRtgDnaDestInfo components.
      These components cannot be added nor deleted."
::= { aRtgDnaDestInfoRowStatusEntry 1 }

aRtgDnaDestInfoComponentName OBJECT-TYPE
   SYNTAX     DisplayString 
   ACCESS     read-only
   STATUS     mandatory
   DESCRIPTION
     "This variable provides the component's string name for
      use with the ASCII Console Interface"
::= { aRtgDnaDestInfoRowStatusEntry 2 }

aRtgDnaDestInfoStorageType OBJECT-TYPE
   SYNTAX     StorageType 
   ACCESS     read-only
   STATUS     mandatory
   DESCRIPTION
     "This variable represents the storage type value for the
      aRtgDnaDestInfo tables."
::= { aRtgDnaDestInfoRowStatusEntry 4 }

aRtgDnaDestInfoIndex OBJECT-TYPE
   SYNTAX     Integer32 (0..50)
   ACCESS     not-accessible
   STATUS     mandatory
   DESCRIPTION
     "This variable represents the index for the aRtgDnaDestInfo tables."
::= { aRtgDnaDestInfoRowStatusEntry 10 }

aRtgDnaDestInfoOperTable OBJECT-TYPE
   SYNTAX     SEQUENCE OF ARtgDnaDestInfoOperEntry
   ACCESS     not-accessible
   STATUS     mandatory
   DESCRIPTION
     "*** THIS TABLE CURRENTLY NOT IMPLEMENTED ***

      This group contains the operational attributes for the DestInfo 
      component."
::= { aRtgDnaDestInfo 10 }

aRtgDnaDestInfoOperEntry OBJECT-TYPE
   SYNTAX     ARtgDnaDestInfoOperEntry
   ACCESS     not-accessible
   STATUS     mandatory
   DESCRIPTION
     "An entry in the aRtgDnaDestInfoOperTable."
   INDEX {
      aRtgIndex,
      aRtgDnaIndex,
      aRtgDnaDestInfoIndex }
::= { aRtgDnaDestInfoOperTable 1 }

ARtgDnaDestInfoOperEntry ::= SEQUENCE {
   aRtgDnaDestInfoType
      INTEGER,
   aRtgDnaDestInfoScope
      INTEGER,
   aRtgDnaDestInfoStdComponentName
      RowPointer,
   aRtgDnaDestInfoReachability
      INTEGER }

aRtgDnaDestInfoType OBJECT-TYPE
   SYNTAX     INTEGER  {
                 primary(0),
                 alternate(1),
                 registered(2),
                 default(3) }
   ACCESS     read-only
   STATUS     mandatory
   DESCRIPTION
     "This attribute indicates the type of the address at the destination 
      interface. Provisioned addresses are assigned a type of  primary or  
      alternate; ATM routing will try primary routes and then the 
      alternate routes if none of the primary routes succeed. The type 
      registered is used for dynamic addresses registered through ILMI. 
      The type default is used for Soft PVC addresses."
::= { aRtgDnaDestInfoOperEntry 1 }

aRtgDnaDestInfoScope OBJECT-TYPE
   SYNTAX     INTEGER (-1..104)
   ACCESS     read-only
   STATUS     mandatory
   DESCRIPTION
     "This attribute indicates the highest level (meaning the lowest level 
      number) in the hierarchy that the address will be advertised to.
      
      A value of -1 indicates that the scope is not applicable since this 
      node has not been configured as a PNNI node."
::= { aRtgDnaDestInfoOperEntry 2 }

aRtgDnaDestInfoStdComponentName OBJECT-TYPE
   SYNTAX     RowPointer 
   ACCESS     read-only
   STATUS     mandatory
   DESCRIPTION
     "This attribute represents a component name of the interface through 
      which the address can be reached."
::= { aRtgDnaDestInfoOperEntry 3 }

aRtgDnaDestInfoReachability OBJECT-TYPE
   SYNTAX     INTEGER  {
                 internal(0),
                 exterior(1) }
   ACCESS     read-only
   STATUS     mandatory
   DESCRIPTION
     "This attribute indicates whether the address is internal or exterior."
::= { aRtgDnaDestInfoOperEntry 4 }


-- ARtg Pnni
-- This component contains the provisionable and operational 
-- attributes for a PNNI node. Provisioning the Pnni component under 
-- the ARtg component indicates that this switch has PNNI routing 
-- capability. 
-- The Pnni component must have one and only one ConfiguredNode 
-- subcomponent.

aRtgPnni OBJECT IDENTIFIER ::= { aRtg 3 }



aRtgPnniRowStatusTable OBJECT-TYPE
   SYNTAX     SEQUENCE OF ARtgPnniRowStatusEntry
   ACCESS     not-accessible
   STATUS     mandatory
   DESCRIPTION
     "This entry controls the addition and deletion of 
      aRtgPnni components."
::= { aRtgPnni 1 }

aRtgPnniRowStatusEntry OBJECT-TYPE
   SYNTAX     ARtgPnniRowStatusEntry
   ACCESS     not-accessible
   STATUS     mandatory
   DESCRIPTION
     "A single entry in the table represents a single 
      aRtgPnni component."
   INDEX {
      aRtgIndex,
      aRtgPnniIndex }
::= { aRtgPnniRowStatusTable 1 }

ARtgPnniRowStatusEntry ::= SEQUENCE {
   aRtgPnniRowStatus
      RowStatus,
   aRtgPnniComponentName
      DisplayString,
   aRtgPnniStorageType
      StorageType,
   aRtgPnniIndex
      NonReplicated }

aRtgPnniRowStatus OBJECT-TYPE
   SYNTAX     RowStatus 
   ACCESS     read-write
   STATUS     mandatory
   DESCRIPTION
     "This variable is used as the basis for SNMP naming of
      aRtgPnni components.
      These components can be added and deleted."
::= { aRtgPnniRowStatusEntry 1 }

aRtgPnniComponentName OBJECT-TYPE
   SYNTAX     DisplayString 
   ACCESS     read-only
   STATUS     mandatory
   DESCRIPTION
     "This variable provides the component's string name for
      use with the ASCII Console Interface"
::= { aRtgPnniRowStatusEntry 2 }

aRtgPnniStorageType OBJECT-TYPE
   SYNTAX     StorageType 
   ACCESS     read-only
   STATUS     mandatory
   DESCRIPTION
     "This variable represents the storage type value for the
      aRtgPnni tables."
::= { aRtgPnniRowStatusEntry 4 }

aRtgPnniIndex OBJECT-TYPE
   SYNTAX     NonReplicated 
   ACCESS     not-accessible
   STATUS     mandatory
   DESCRIPTION
     "This variable represents the index for the aRtgPnni tables."
::= { aRtgPnniRowStatusEntry 10 }

aRtgPnniProvTable OBJECT-TYPE
   SYNTAX     SEQUENCE OF ARtgPnniProvEntry
   ACCESS     not-accessible
   STATUS     mandatory
   DESCRIPTION
     "This group contains the generic provisionable attributes of a Pnni 
      component."
::= { aRtgPnni 10 }

aRtgPnniProvEntry OBJECT-TYPE
   SYNTAX     ARtgPnniProvEntry
   ACCESS     not-accessible
   STATUS     mandatory
   DESCRIPTION
     "An entry in the aRtgPnniProvTable."
   INDEX {
      aRtgIndex,
      aRtgPnniIndex }
::= { aRtgPnniProvTable 1 }

ARtgPnniProvEntry ::= SEQUENCE {
   aRtgPnniNodeAddressPrefix
      HexString,
   aRtgPnniDefaultScope
      Unsigned32,
   aRtgPnniDomain
      AsciiString,
   aRtgPnniRestrictTransit
      INTEGER,
   aRtgPnniMaxReroutesOnCrankback
      Unsigned32 }

aRtgPnniNodeAddressPrefix OBJECT-TYPE
   SYNTAX     HexString (SIZE (0..19))
   ACCESS     read-write
   STATUS     mandatory
   DESCRIPTION
     "This attribute specifies the ATM address of this node. It allows the 
      default node address to be overridden. If this attribute is set to the 
      null string, then the default node address prefix is assumed, and 
      computed as follows: the value provisioned for the ModuleData 
      component's nodePrefix attribute, followed by a unique MAC 
      address (6 octets)."
::= { aRtgPnniProvEntry 1 }

aRtgPnniDefaultScope OBJECT-TYPE
   SYNTAX     Unsigned32 (0..104)
   ACCESS     read-write
   STATUS     mandatory
   DESCRIPTION
     "This attribute specifies the default PNNI scope for ATM addresses 
      associated with this node. The PNNI scope determines the level to 
      which the address will be advertised within the PNNI routing 
      domain. A provisioned Addr component may override the default 
      scope in a PnniInfo subcomponent.
      
      A value of 0 means that all addresses which do not have 
      provisioned scopes will be advertised globally within the PNNI 
      routing domain.
      
      The value specified must be numerically smaller than or equal to 
      that of the lowest level at which this node is configured in the PNNI 
      hierarchy."
   DEFVAL     { 0 }
::= { aRtgPnniProvEntry 2 }

aRtgPnniDomain OBJECT-TYPE
   SYNTAX     AsciiString (SIZE (1..32))
   ACCESS     read-write
   STATUS     mandatory
   DESCRIPTION
     "This attribute specifies the routing domain name. This attribute 
      should be set identically for all nodes in the same routing domain."
   DEFVAL     { '31'H }  -- "1"
::= { aRtgPnniProvEntry 3 }

aRtgPnniRestrictTransit OBJECT-TYPE
   SYNTAX     INTEGER  {
                 false(0),
                 true(1) }
   ACCESS     read-write
   STATUS     mandatory
   DESCRIPTION
     "This attribute specifies if the node should restrict tandeming of 
      SVCs. 
      
      If this attribute is set to true, then other lowest level nodes in the 
      PNNI hierarchy will avoid traversing this node during route 
      computation."
   DEFVAL     { false }
::= { aRtgPnniProvEntry 4 }

aRtgPnniMaxReroutesOnCrankback OBJECT-TYPE
   SYNTAX     Unsigned32 (0..20)
   ACCESS     read-write
   STATUS     mandatory
   DESCRIPTION
     "This attribute specifies the number of alternate routing attempts 
      before a call requiring crank back is rejected."
   DEFVAL     { 1 }
::= { aRtgPnniProvEntry 5 }

aRtgPnniPglParmsTable OBJECT-TYPE
   SYNTAX     SEQUENCE OF ARtgPnniPglParmsEntry
   ACCESS     not-accessible
   STATUS     mandatory
   DESCRIPTION
     "This group contains the provisionable attributes for the peer group 
      leader election timer parameters of a Pnni component."
::= { aRtgPnni 11 }

aRtgPnniPglParmsEntry OBJECT-TYPE
   SYNTAX     ARtgPnniPglParmsEntry
   ACCESS     not-accessible
   STATUS     mandatory
   DESCRIPTION
     "An entry in the aRtgPnniPglParmsTable."
   INDEX {
      aRtgIndex,
      aRtgPnniIndex }
::= { aRtgPnniPglParmsTable 1 }

ARtgPnniPglParmsEntry ::= SEQUENCE {
   aRtgPnniPglInitTime
      Unsigned32,
   aRtgPnniOverrideDelay
      Unsigned32,
   aRtgPnniReElectionInterval
      Unsigned32 }

aRtgPnniPglInitTime OBJECT-TYPE
   SYNTAX     Unsigned32 (0..65535)
   ACCESS     read-write
   STATUS     mandatory
   DESCRIPTION
     "This attribute specifies how long this node will delay advertising its 
      choice of preferred peer group leader after having initialized 
      operation and reached the full peer state with at least one neighbor 
      in the peer group."
   DEFVAL     { 15 }
::= { aRtgPnniPglParmsEntry 1 }

aRtgPnniOverrideDelay OBJECT-TYPE
   SYNTAX     Unsigned32 (1..65535)
   ACCESS     read-write
   STATUS     mandatory
   DESCRIPTION
     "This attribute specifies how long a node will wait for itself to be 
      declared the preferred peer group leader by unanimous agreement 
      among its peers."
   DEFVAL     { 30 }
::= { aRtgPnniPglParmsEntry 2 }

aRtgPnniReElectionInterval OBJECT-TYPE
   SYNTAX     Unsigned32 (1..65535)
   ACCESS     read-write
   STATUS     mandatory
   DESCRIPTION
     "This attribute specifies how long this node will wait after losing 
      connectivity to the current peer group leader before re-starting the 
      process of electing a new peer group leader."
   DEFVAL     { 15 }
::= { aRtgPnniPglParmsEntry 3 }

aRtgPnniHlParmsTable OBJECT-TYPE
   SYNTAX     SEQUENCE OF ARtgPnniHlParmsEntry
   ACCESS     not-accessible
   STATUS     mandatory
   DESCRIPTION
     "This group contains the default provisionable Hello protocol 
      parameters."
::= { aRtgPnni 12 }

aRtgPnniHlParmsEntry OBJECT-TYPE
   SYNTAX     ARtgPnniHlParmsEntry
   ACCESS     not-accessible
   STATUS     mandatory
   DESCRIPTION
     "An entry in the aRtgPnniHlParmsTable."
   INDEX {
      aRtgIndex,
      aRtgPnniIndex }
::= { aRtgPnniHlParmsTable 1 }

ARtgPnniHlParmsEntry ::= SEQUENCE {
   aRtgPnniHelloHoldDown
      FixedPoint1,
   aRtgPnniHelloInterval
      Unsigned32,
   aRtgPnniHelloInactivityFactor
      Unsigned32 }

aRtgPnniHelloHoldDown OBJECT-TYPE
   SYNTAX     FixedPoint1 (1..655350)
   ACCESS     read-write
   STATUS     mandatory
   DESCRIPTION
     "This attribute is used to limit the rate at which this node sends out 
      Hello packets. Specifically, it specifies the default minimum amount 
      of time between successive Hellos used by routing control channels 
      on this node."
   DEFVAL     { 10 }
::= { aRtgPnniHlParmsEntry 1 }

aRtgPnniHelloInterval OBJECT-TYPE
   SYNTAX     Unsigned32 (1..65535)
   ACCESS     read-write
   STATUS     mandatory
   DESCRIPTION
     "This attribute specifies the default duration of the Hello Timer in 
      seconds for routing control channels on this node. Every 
      helloInterval seconds, this node will send out a Hello packet to the 
      neighbor node, subject to the helloHoldDown timer having expired 
      at least once since the last Hello packet was sent."
   DEFVAL     { 15 }
::= { aRtgPnniHlParmsEntry 2 }

aRtgPnniHelloInactivityFactor OBJECT-TYPE
   SYNTAX     Unsigned32 (1..65535)
   ACCESS     read-write
   STATUS     mandatory
   DESCRIPTION
     "This attribute specifies the default number of Hello intervals 
      allowed to pass without receiving a Hello from the neighbor node, 
      before an attempt is made to re-stage, for routing control channels 
      on this node. The hello inactivity timer is enabled in the 
      oneWayInside, twoWayInside, oneWayOutside, twoWayOutside 
      and commonOutside (see the helloState attribute on the Rcc 
      component for a description of these states). Note that the value for 
      the Hello interval used in the calculation is the one specified in the 
      Hello packet from the neighbor node."
   DEFVAL     { 5 }
::= { aRtgPnniHlParmsEntry 3 }

aRtgPnniPtseParmsTable OBJECT-TYPE
   SYNTAX     SEQUENCE OF ARtgPnniPtseParmsEntry
   ACCESS     not-accessible
   STATUS     mandatory
   DESCRIPTION
     "This group contains the provisionable attributes for the PTSE timer 
      values of a Pnni component."
::= { aRtgPnni 13 }

aRtgPnniPtseParmsEntry OBJECT-TYPE
   SYNTAX     ARtgPnniPtseParmsEntry
   ACCESS     not-accessible
   STATUS     mandatory
   DESCRIPTION
     "An entry in the aRtgPnniPtseParmsTable."
   INDEX {
      aRtgIndex,
      aRtgPnniIndex }
::= { aRtgPnniPtseParmsTable 1 }

ARtgPnniPtseParmsEntry ::= SEQUENCE {
   aRtgPnniPtseHoldDown
      FixedPoint1,
   aRtgPnniPtseRefreshInterval
      Unsigned32,
   aRtgPnniPtseLifetimeFactor
      Unsigned32,
   aRtgPnniRequestRxmtInterval
      Unsigned32,
   aRtgPnniPeerDelayedAckInterval
      FixedPoint1 }

aRtgPnniPtseHoldDown OBJECT-TYPE
   SYNTAX     FixedPoint1 (1..655350)
   ACCESS     read-write
   STATUS     mandatory
   DESCRIPTION
     "This attribute is used to limit the rate at which this node sends out 
      PTSE packets. Specifically, it specifies the minimum amount of 
      time in seconds that this node must wait between sending 
      successive PTSE packets."
   DEFVAL     { 10 }
::= { aRtgPnniPtseParmsEntry 1 }

aRtgPnniPtseRefreshInterval OBJECT-TYPE
   SYNTAX     Unsigned32 (300..65535)
   ACCESS     read-write
   STATUS     mandatory
   DESCRIPTION
     "This attribute specifies the duration of the PTSE Timer. Every 
      ptseRefreshInterval seconds, this node will send out a self-
      originated PTSE packet to the neighbor node, subject to the 
      ptseHoldDown timer having expired at least once since the last 
      PTSE packet was sent."
   DEFVAL     { 1800 }
::= { aRtgPnniPtseParmsEntry 2 }

aRtgPnniPtseLifetimeFactor OBJECT-TYPE
   SYNTAX     Unsigned32 (101..1000)
   ACCESS     read-write
   STATUS     mandatory
   DESCRIPTION
     "This attribute specifies the lifetime multiplier. The result of 
      multiplying the ptseRefreshInterval by this value is used as the 
      initial lifetime that this node places into PTSEs."
   DEFVAL     { 200 }
::= { aRtgPnniPtseParmsEntry 3 }

aRtgPnniRequestRxmtInterval OBJECT-TYPE
   SYNTAX     Unsigned32 (1..65535)
   ACCESS     read-write
   STATUS     mandatory
   DESCRIPTION
     "This attribute specifies the period between retransmissions of 
      unacknowledged Database Summary packets, PTSE Request 
      packets and PTSPs."
   DEFVAL     { 5 }
::= { aRtgPnniPtseParmsEntry 4 }

aRtgPnniPeerDelayedAckInterval OBJECT-TYPE
   SYNTAX     FixedPoint1 (1..655350)
   ACCESS     read-write
   STATUS     mandatory
   DESCRIPTION
     "This attribute specifies the minimum amount of time between 
      transmissions of delayed PTSE acknowledgment packets."
   DEFVAL     { 1 }
::= { aRtgPnniPtseParmsEntry 5 }

aRtgPnniThreshParmsTable OBJECT-TYPE
   SYNTAX     SEQUENCE OF ARtgPnniThreshParmsEntry
   ACCESS     not-accessible
   STATUS     mandatory
   DESCRIPTION
     "This group contains the provisionable attributes for the change 
      thresholds of a ARtg Pnni component."
::= { aRtgPnni 14 }

aRtgPnniThreshParmsEntry OBJECT-TYPE
   SYNTAX     ARtgPnniThreshParmsEntry
   ACCESS     not-accessible
   STATUS     mandatory
   DESCRIPTION
     "An entry in the aRtgPnniThreshParmsTable."
   INDEX {
      aRtgIndex,
      aRtgPnniIndex }
::= { aRtgPnniThreshParmsTable 1 }

ARtgPnniThreshParmsEntry ::= SEQUENCE {
   aRtgPnniAvcrMt
      Unsigned32,
   aRtgPnniAvcrPm
      Unsigned32 }

aRtgPnniAvcrMt OBJECT-TYPE
   SYNTAX     Unsigned32 (1..99)
   ACCESS     read-write
   STATUS     mandatory
   DESCRIPTION
     "This attribute when multiplied by the Maximum Cell Rate specifies 
      the minimum threshold used in the algorithms that determine 
      significant change for average cell rate parameters."
   DEFVAL     { 3 }
::= { aRtgPnniThreshParmsEntry 1 }

aRtgPnniAvcrPm OBJECT-TYPE
   SYNTAX     Unsigned32 (1..99)
   ACCESS     read-write
   STATUS     mandatory
   DESCRIPTION
     "This attribute when multiplied by the current Available Cell Rate 
      specifies the threshold used in the algorithms that determine 
      significant change for AvCR parameters. If the resulting threshold is 
      lower than minimum threshold, minimum threshold will be used.
      
      Increasing the value of the attribute increases the range of 
      insignificance and reduces the amount of PTSP flooding due to 
      changes in resource availability."
   DEFVAL     { 50 }
::= { aRtgPnniThreshParmsEntry 2 }

aRtgPnniOperTable OBJECT-TYPE
   SYNTAX     SEQUENCE OF ARtgPnniOperEntry
   ACCESS     not-accessible
   STATUS     mandatory
   DESCRIPTION
     "This group contains the generic operational attributes of an ARtg 
      Pnni component."
::= { aRtgPnni 15 }

aRtgPnniOperEntry OBJECT-TYPE
   SYNTAX     ARtgPnniOperEntry
   ACCESS     not-accessible
   STATUS     mandatory
   DESCRIPTION
     "An entry in the aRtgPnniOperTable."
   INDEX {
      aRtgIndex,
      aRtgPnniIndex }
::= { aRtgPnniOperTable 1 }

ARtgPnniOperEntry ::= SEQUENCE {
   aRtgPnniTopologyMemoryExhaustion
      INTEGER }

aRtgPnniTopologyMemoryExhaustion OBJECT-TYPE
   SYNTAX     INTEGER  {
                 false(0),
                 true(1) }
   ACCESS     read-only
   STATUS     mandatory
   DESCRIPTION
     "This attribute indicates if the topology database is overloaded. 
      A node goes into a database overload state when it fails to store the 
      complete topology database due to insufficient memory in the node. 
      A node in this state performs resynchronization periodically by 
      restarting all its Neighbor Peer Finite State Machines. The node will 
      stay in this state until it synchronizes with all of its neighbors 
      without any overload problems. When this attribute is set an alarm 
      will be issued."
::= { aRtgPnniOperEntry 2 }

aRtgPnniStatsTable OBJECT-TYPE
   SYNTAX     SEQUENCE OF ARtgPnniStatsEntry
   ACCESS     not-accessible
   STATUS     mandatory
   DESCRIPTION
     "This group contains the statistical operational attributes of a ARtg 
      Pnni component."
::= { aRtgPnni 16 }

aRtgPnniStatsEntry OBJECT-TYPE
   SYNTAX     ARtgPnniStatsEntry
   ACCESS     not-accessible
   STATUS     mandatory
   DESCRIPTION
     "An entry in the aRtgPnniStatsTable."
   INDEX {
      aRtgIndex,
      aRtgPnniIndex }
::= { aRtgPnniStatsTable 1 }

ARtgPnniStatsEntry ::= SEQUENCE {
   aRtgPnniRoutingAttempts
      Counter32,
   aRtgPnniFailedRoutingAttempts
      Counter32,
   aRtgPnniCallsRerouted
      Counter32 }

aRtgPnniRoutingAttempts OBJECT-TYPE
   SYNTAX     Counter32 
   ACCESS     read-only
   STATUS     mandatory
   DESCRIPTION
     "This attribute counts successful PNNI routing attempts. The counter 
      wraps when it exceeds the maximum value."
::= { aRtgPnniStatsEntry 1 }

aRtgPnniFailedRoutingAttempts OBJECT-TYPE
   SYNTAX     Counter32 
   ACCESS     read-only
   STATUS     mandatory
   DESCRIPTION
     "This attribute counts failed PNNI routing attempts. The counter 
      wraps when it exceeds the maximum value."
::= { aRtgPnniStatsEntry 2 }

aRtgPnniCallsRerouted OBJECT-TYPE
   SYNTAX     Counter32 
   ACCESS     read-only
   STATUS     mandatory
   DESCRIPTION
     "This attribute counts successful PNNI alternate routing attempts. 
      The counter wraps when it exceeds the maximum value."
::= { aRtgPnniStatsEntry 3 }

aRtgPnniOptMetricTable OBJECT-TYPE
   SYNTAX     SEQUENCE OF ARtgPnniOptMetricEntry
   ACCESS     not-accessible
   STATUS     mandatory
   DESCRIPTION
     "This attribute is a vector that specifies the optimization metric for 
      each ATM service category. The optimization metric is used during 
      Generic Connection Admission Control (GCAC) route 
      computation.
      
      Setting the value to cdv for a particular service category will cause 
      GCAC to optimize for cell delay variation on call setups requiring 
      that service category.
      
      Setting the value to maxCtd for a particular service category will 
      cause GCAC to optimize for maximum cell transfer delay on call 
      setups requiring that service category.
      
      Setting the value to aw for a particular service category will cause 
      GCAC to optimize for administrative weight on call setups 
      requiring that service category."
::= { aRtgPnni 386 }

aRtgPnniOptMetricEntry OBJECT-TYPE
   SYNTAX     ARtgPnniOptMetricEntry
   ACCESS     not-accessible
   STATUS     mandatory
   DESCRIPTION
     "An entry in the aRtgPnniOptMetricTable."
   INDEX {
      aRtgIndex,
      aRtgPnniIndex,
      aRtgPnniOptMetricIndex }
::= { aRtgPnniOptMetricTable 1 }

ARtgPnniOptMetricEntry ::= SEQUENCE {
   aRtgPnniOptMetricIndex
      INTEGER,
   aRtgPnniOptMetricValue
      INTEGER }

aRtgPnniOptMetricIndex OBJECT-TYPE
   SYNTAX     INTEGER  {
                 cbr(1),
                 rtVbr(2),
                 nrtVbr(3),
                 ubr(4) }
   ACCESS     not-accessible
   STATUS     mandatory
   DESCRIPTION
     "This variable represents the aRtgPnniOptMetricTable
      specific index for the aRtgPnniOptMetricTable."
::= { aRtgPnniOptMetricEntry 1 }

aRtgPnniOptMetricValue OBJECT-TYPE
   SYNTAX     INTEGER  {
                 cdv(0),
                 maxCtd(1),
                 aw(2) }
   ACCESS     read-write
   STATUS     mandatory
   DESCRIPTION
     "This variable represents an individual value for the
      aRtgPnniOptMetricTable."
::= { aRtgPnniOptMetricEntry 2 }


-- ARtg Pnni RouteFinder
-- This component is used to compute a list of routes to a specified 
-- destination which satisfy certain traffic and routing requirements.
-- 
-- To display a list of computed routes:
-- - set the route computation criteria
-- - issue the Run command

aRtgPnniRf OBJECT IDENTIFIER ::= { aRtgPnni 2 }



aRtgPnniRfRowStatusTable OBJECT-TYPE
   SYNTAX     SEQUENCE OF ARtgPnniRfRowStatusEntry
   ACCESS     not-accessible
   STATUS     mandatory
   DESCRIPTION
     "This entry controls the addition and deletion of 
      aRtgPnniRf components."
::= { aRtgPnniRf 1 }

aRtgPnniRfRowStatusEntry OBJECT-TYPE
   SYNTAX     ARtgPnniRfRowStatusEntry
   ACCESS     not-accessible
   STATUS     mandatory
   DESCRIPTION
     "A single entry in the table represents a single 
      aRtgPnniRf component."
   INDEX {
      aRtgIndex,
      aRtgPnniIndex,
      aRtgPnniRfIndex }
::= { aRtgPnniRfRowStatusTable 1 }

ARtgPnniRfRowStatusEntry ::= SEQUENCE {
   aRtgPnniRfRowStatus
      RowStatus,
   aRtgPnniRfComponentName
      DisplayString,
   aRtgPnniRfStorageType
      StorageType,
   aRtgPnniRfIndex
      NonReplicated }

aRtgPnniRfRowStatus OBJECT-TYPE
   SYNTAX     RowStatus 
   ACCESS     read-only
   STATUS     mandatory
   DESCRIPTION
     "This variable is used as the basis for SNMP naming of
      aRtgPnniRf components.
      These components cannot be added nor deleted."
::= { aRtgPnniRfRowStatusEntry 1 }

aRtgPnniRfComponentName OBJECT-TYPE
   SYNTAX     DisplayString 
   ACCESS     read-only
   STATUS     mandatory
   DESCRIPTION
     "This variable provides the component's string name for
      use with the ASCII Console Interface"
::= { aRtgPnniRfRowStatusEntry 2 }

aRtgPnniRfStorageType OBJECT-TYPE
   SYNTAX     StorageType 
   ACCESS     read-only
   STATUS     mandatory
   DESCRIPTION
     "This variable represents the storage type value for the
      aRtgPnniRf tables."
::= { aRtgPnniRfRowStatusEntry 4 }

aRtgPnniRfIndex OBJECT-TYPE
   SYNTAX     NonReplicated 
   ACCESS     not-accessible
   STATUS     mandatory
   DESCRIPTION
     "This variable represents the index for the aRtgPnniRf tables."
::= { aRtgPnniRfRowStatusEntry 10 }

aRtgPnniRfCriteriaTable OBJECT-TYPE
   SYNTAX     SEQUENCE OF ARtgPnniRfCriteriaEntry
   ACCESS     not-accessible
   STATUS     mandatory
   DESCRIPTION
     "This group contains the attributes specifying the routing criteria for 
      the route computation."
::= { aRtgPnniRf 10 }

aRtgPnniRfCriteriaEntry OBJECT-TYPE
   SYNTAX     ARtgPnniRfCriteriaEntry
   ACCESS     not-accessible
   STATUS     mandatory
   DESCRIPTION
     "An entry in the aRtgPnniRfCriteriaTable."
   INDEX {
      aRtgIndex,
      aRtgPnniIndex,
      aRtgPnniRfIndex }
::= { aRtgPnniRfCriteriaTable 1 }

ARtgPnniRfCriteriaEntry ::= SEQUENCE {
   aRtgPnniRfDestinationAddress
      HexString,
   aRtgPnniRfMaxRoutes
      Unsigned32,
   aRtgPnniRfTxTrafficDescType
      INTEGER,
   aRtgPnniRfRxTrafficDescType
      INTEGER,
   aRtgPnniRfAtmServiceCategory
      INTEGER,
   aRtgPnniRfFwdQosClass
      INTEGER,
   aRtgPnniRfBwdQosClass
      INTEGER,
   aRtgPnniRfBearerClassBbc
      INTEGER,
   aRtgPnniRfTransferCapabilityBbc
      INTEGER,
   aRtgPnniRfClippingBbc
      INTEGER,
   aRtgPnniRfBestEffort
      INTEGER,
   aRtgPnniRfOptimizationMetric
      INTEGER }

aRtgPnniRfDestinationAddress OBJECT-TYPE
   SYNTAX     HexString (SIZE (1..20))
   ACCESS     read-write
   STATUS     mandatory
   DESCRIPTION
     "This attribute specifies the destination NSAP address to be used for 
      the computation. If this attribute specifies an invalid address then no 
      routes will be found."
::= { aRtgPnniRfCriteriaEntry 1 }

aRtgPnniRfMaxRoutes OBJECT-TYPE
   SYNTAX     Unsigned32 (1..15)
   ACCESS     read-write
   STATUS     mandatory
   DESCRIPTION
     "This attribute specifies a ceiling on the number of routes to be 
      computed."
   DEFVAL     { 1 }
::= { aRtgPnniRfCriteriaEntry 2 }

aRtgPnniRfTxTrafficDescType OBJECT-TYPE
   SYNTAX     INTEGER  {
                 n1(1),
                 n2(2),
                 n3(3),
                 n4(4),
                 n5(5),
                 n6(6),
                 n7(7),
                 n8(8) }
   ACCESS     read-write
   STATUS     mandatory
   DESCRIPTION
     "This attribute specifies the type of traffic management which is 
      applied to the transmit direction as defined in the ATM Forum. The 
      txTrafficDescType determines the number and meaning of the 
      parameters in the txTrafficDescParm attribute."
   DEFVAL     { n1 }
::= { aRtgPnniRfCriteriaEntry 3 }

aRtgPnniRfRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { aRtgPnniRfCriteriaEntry 5 }

aRtgPnniRfAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     mandatory
   DESCRIPTION
     "This attribute specifies the ATM service category for both directions 
      of the connection. 
      
      If this attribute is set to derivedFromBBC, the Broadband Bearer 
      Capability (BBC) and bestEffort attributes are used to determine the 
      atmServiceCategory of this connection. 
      
      If this attribute is set to other than derivedFromBBC, the value of 
      this attribute is used to override the provisioned BBC IE parameters. 
      In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. 
      VBR real time service may support statistical multiplexing of real 
      time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. VBR non-real time service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { aRtgPnniRfCriteriaEntry 6 }

aRtgPnniRfFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. 
      
      Class 1 supports a QOS that will meet Service Class A performance 
      requirements (Circuit emulation, constant bit rate video).
      
      Class 2 supports a QOS that will meet Service Class B performance 
      requirements (Variable bit rate audio and video).
      
      Class 3 supports a QOS that will meet Service Class C performance 
      requirements (Connection-Oriented Data Transfer).
      
      Class 4 supports a QOS that will meet Service Class D performance 
      requirements (Connectionless Data Transfer).
      
      Class 0 is the unspecified bit rate QOS class; no objective is 
      specified for the performance parameters."
   DEFVAL     { n0 }
::= { aRtgPnniRfCriteriaEntry 10 }

aRtgPnniRfBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection.
      
      Class 1 supports a QOS that will meet Service Class A performance 
      requirements (Circuit emulation, constant bit rate video).
      
      Class 2 supports a QOS that will meet Service Class B performance 
      requirements (Variable bit rate audio and video).
      
      Class 3 supports a QOS that will meet Service Class C performance 
      requirements (Connection-Oriented Data Transfer).
      
      Class 4 supports a QOS that will meet Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { aRtgPnniRfCriteriaEntry 11 }

aRtgPnniRfBearerClassBbc OBJECT-TYPE
   SYNTAX     INTEGER  {
                 a(1),
                 c(3),
                 x(16),
                 derivedFromServiceCategory(31) }
   ACCESS     read-write
   STATUS     mandatory
   DESCRIPTION
     "This attribute specifies the bearer capability. It is one of the 
      Broadband Bearer Capability (BBC) attributes. The purpose of the 
      BBC information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol."
   DEFVAL     { derivedFromServiceCategory }
::= { aRtgPnniRfCriteriaEntry 12 }

aRtgPnniRfTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability : TrafficType, Timing>
      0 : NoIndication, NoIndication
      1 : NoIndication, yes
      2 : NoIndication, no
      5 : CBR, yes
      8 : VBR, NoIndication
      9 : VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value NoIndication for traffic type is used if the user has not set 
      the traffic type; this is also the case for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { aRtgPnniRfCriteriaEntry 13 }

aRtgPnniRfClippingBbc OBJECT-TYPE
   SYNTAX     INTEGER  {
                 no(0),
                 yes(1) }
   ACCESS     read-write
   STATUS     mandatory
   DESCRIPTION
     "This attribute specifies the value for the clipping susceptibility 
      parameter in the BBC IE. This attribute is only used for SPVC 
      connections. It is one of the Broadband Bearer Capability attributes.
      
      Clipping is an impairment in which the first fraction of a second of 
      information to be transferred is lost. It occurs after a call is 
      answered and before an associated connection is switched through."
   DEFVAL     { no }
::= { aRtgPnniRfCriteriaEntry 14 }

aRtgPnniRfBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor IE. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both.
      DESCRIPTION"
   DEFVAL     { derivedFromServiceCategory }
::= { aRtgPnniRfCriteriaEntry 15 }

aRtgPnniRfOptimizationMetric OBJECT-TYPE
   SYNTAX     INTEGER  {
                 cdv(0),
                 maxCtd(1),
                 aw(2) }
   ACCESS     read-write
   STATUS     mandatory
   DESCRIPTION
     "This attribute specifies the optimization metric to be used in the 
      route computation; one of cell delay variation (cdv), maximum cell 
      transfer delay (maxCtd), or administrative weight (aw)."
   DEFVAL     { aw }
::= { aRtgPnniRfCriteriaEntry 16 }

aRtgPnniRfRxTdpTable OBJECT-TYPE
   SYNTAX     SEQUENCE OF ARtgPnniRfRxTdpEntry
   ACCESS     not-accessible
   STATUS     mandatory
   DESCRIPTION
     "This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      will be taken from the txTrafficDescParm."
::= { aRtgPnniRf 388 }

aRtgPnniRfRxTdpEntry OBJECT-TYPE
   SYNTAX     ARtgPnniRfRxTdpEntry
   ACCESS     not-accessible
   STATUS     mandatory
   DESCRIPTION
     "An entry in the aRtgPnniRfRxTdpTable."
   INDEX {
      aRtgIndex,
      aRtgPnniIndex,
      aRtgPnniRfIndex,
      aRtgPnniRfRxTdpIndex }
::= { aRtgPnniRfRxTdpTable 1 }

ARtgPnniRfRxTdpEntry ::= SEQUENCE {
   aRtgPnniRfRxTdpIndex
      Integer32,
   aRtgPnniRfRxTdpValue
      Unsigned32 }

aRtgPnniRfRxTdpIndex OBJECT-TYPE
   SYNTAX     Integer32 (1..5)
   ACCESS     not-accessible
   STATUS     mandatory
   DESCRIPTION
     "This variable represents the aRtgPnniRfRxTdpTable
      specific index for the aRtgPnniRfRxTdpTable."
::= { aRtgPnniRfRxTdpEntry 1 }

aRtgPnniRfRxTdpValue OBJECT-TYPE
   SYNTAX     Unsigned32 (0..2147483647)
   ACCESS     read-write
   STATUS     mandatory
   DESCRIPTION
     "This variable represents an individual value for the
      aRtgPnniRfRxTdpTable."
::= { aRtgPnniRfRxTdpEntry 2 }

aRtgPnniRfTxTdpTable OBJECT-TYPE
   SYNTAX     SEQUENCE OF ARtgPnniRfTxTdpEntry
   ACCESS     not-accessible
   STATUS     mandatory
   DESCRIPTION
     "This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic will be shaped 
      at the next rate less than the PCR. 
      
      For txTrafficDescType 6, 7 and 8, the transmit traffic will be shaped 
      at the highest available rate which is between PCR and SCR. 
      However, if there is no available shaping rate between PCR and 
      SCR, traffic will be shaped at the next rate above the PCR."
::= { aRtgPnniRf 389 }

aRtgPnniRfTxTdpEntry OBJECT-TYPE
   SYNTAX     ARtgPnniRfTxTdpEntry
   ACCESS     not-accessible
   STATUS     mandatory
   DESCRIPTION
     "An entry in the aRtgPnniRfTxTdpTable."
   INDEX {
      aRtgIndex,
      aRtgPnniIndex,
      aRtgPnniRfIndex,
      aRtgPnniRfTxTdpIndex }
::= { aRtgPnniRfTxTdpTable 1 }

ARtgPnniRfTxTdpEntry ::= SEQUENCE {
   aRtgPnniRfTxTdpIndex
      Integer32,
   aRtgPnniRfTxTdpValue
      Unsigned32 }

aRtgPnniRfTxTdpIndex OBJECT-TYPE
   SYNTAX     Integer32 (1..5)
   ACCESS     not-accessible
   STATUS     mandatory
   DESCRIPTION
     "This variable represents the aRtgPnniRfTxTdpTable
      specific index for the aRtgPnniRfTxTdpTable."
::= { aRtgPnniRfTxTdpEntry 1 }

aRtgPnniRfTxTdpValue OBJECT-TYPE
   SYNTAX     Unsigned32 (0..2147483647)
   ACCESS     read-write
   STATUS     mandatory
   DESCRIPTION
     "This variable represents an individual value for the
      aRtgPnniRfTxTdpTable."
::= { aRtgPnniRfTxTdpEntry 2 }

aRtgPnniRfFqpTable OBJECT-TYPE
   SYNTAX     SEQUENCE OF ARtgPnniRfFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { aRtgPnniRf 390 }

aRtgPnniRfFqpEntry OBJECT-TYPE
   SYNTAX     ARtgPnniRfFqpEntry
   ACCESS     not-accessible
   STATUS     mandatory
   DESCRIPTION
     "An entry in the aRtgPnniRfFqpTable."
   INDEX {
      aRtgIndex,
      aRtgPnniIndex,
      aRtgPnniRfIndex,
      aRtgPnniRfFqpIndex }
::= { aRtgPnniRfFqpTable 1 }

ARtgPnniRfFqpEntry ::= SEQUENCE {
   aRtgPnniRfFqpIndex
      INTEGER,
   aRtgPnniRfFqpValue
      Unsigned32 }

aRtgPnniRfFqpIndex OBJECT-TYPE
   SYNTAX     INTEGER  {
                 cdv(0),
                 ctd(1),
                 clr(2) }
   ACCESS     not-accessible
   STATUS     mandatory
   DESCRIPTION
     "This variable represents the aRtgPnniRfFqpTable
      specific index for the aRtgPnniRfFqpTable."
::= { aRtgPnniRfFqpEntry 1 }

aRtgPnniRfFqpValue OBJECT-TYPE
   SYNTAX     Unsigned32 (0..2147483647)
   ACCESS     read-write
   STATUS     mandatory
   DESCRIPTION
     "This variable represents an individual value for the
      aRtgPnniRfFqpTable."
::= { aRtgPnniRfFqpEntry 2 }

aRtgPnniRfBqpTable OBJECT-TYPE
   SYNTAX     SEQUENCE OF ARtgPnniRfBqpEntry
   ACCESS     not-accessible
   STATUS     mandatory
   DESCRIPTION
     "This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { aRtgPnniRf 393 }

aRtgPnniRfBqpEntry OBJECT-TYPE
   SYNTAX     ARtgPnniRfBqpEntry
   ACCESS     not-accessible
   STATUS     mandatory
   DESCRIPTION
     "An entry in the aRtgPnniRfBqpTable."
   INDEX {
      aRtgIndex,
      aRtgPnniIndex,
      aRtgPnniRfIndex,
      aRtgPnniRfBqpIndex }
::= { aRtgPnniRfBqpTable 1 }

ARtgPnniRfBqpEntry ::= SEQUENCE {
   aRtgPnniRfBqpIndex
      INTEGER,
   aRtgPnniRfBqpValue
      Unsigned32 }

aRtgPnniRfBqpIndex OBJECT-TYPE
   SYNTAX     INTEGER  {
                 cdv(0),
                 ctd(1),
                 clr(2) }
   ACCESS     not-accessible
   STATUS     mandatory
   DESCRIPTION
     "This variable represents the aRtgPnniRfBqpTable
      specific index for the aRtgPnniRfBqpTable."
::= { aRtgPnniRfBqpEntry 1 }

aRtgPnniRfBqpValue OBJECT-TYPE
   SYNTAX     Unsigned32 (0..2147483647)
   ACCESS     read-write
   STATUS     mandatory
   DESCRIPTION
     "This variable represents an individual value for the
      aRtgPnniRfBqpTable."
::= { aRtgPnniRfBqpEntry 2 }


-- ARtg Pnni ConfiguredNode/<level>
-- This component represents the participation of this node at one level 
-- in the PNNI hierarchy.

aRtgPnniCfgNode OBJECT IDENTIFIER ::= { aRtgPnni 3 }



aRtgPnniCfgNodeRowStatusTable OBJECT-TYPE
   SYNTAX     SEQUENCE OF ARtgPnniCfgNodeRowStatusEntry
   ACCESS     not-accessible
   STATUS     mandatory
   DESCRIPTION
     "This entry controls the addition and deletion of 
      aRtgPnniCfgNode components."
::= { aRtgPnniCfgNode 1 }

aRtgPnniCfgNodeRowStatusEntry OBJECT-TYPE
   SYNTAX     ARtgPnniCfgNodeRowStatusEntry
   ACCESS     not-accessible
   STATUS     mandatory
   DESCRIPTION
     "A single entry in the table represents a single 
      aRtgPnniCfgNode component."
   INDEX {
      aRtgIndex,
      aRtgPnniIndex,
      aRtgPnniCfgNodeIndex }
::= { aRtgPnniCfgNodeRowStatusTable 1 }

ARtgPnniCfgNodeRowStatusEntry ::= SEQUENCE {
   aRtgPnniCfgNodeRowStatus
      RowStatus,
   aRtgPnniCfgNodeComponentName
      DisplayString,
   aRtgPnniCfgNodeStorageType
      StorageType,
   aRtgPnniCfgNodeIndex
      Integer32 }

aRtgPnniCfgNodeRowStatus OBJECT-TYPE
   SYNTAX     RowStatus 
   ACCESS     read-write
   STATUS     mandatory
   DESCRIPTION
     "This variable is used as the basis for SNMP naming of
      aRtgPnniCfgNode components.
      These components can be added and deleted."
::= { aRtgPnniCfgNodeRowStatusEntry 1 }

aRtgPnniCfgNodeComponentName OBJECT-TYPE
   SYNTAX     DisplayString 
   ACCESS     read-only
   STATUS     mandatory
   DESCRIPTION
     "This variable provides the component's string name for
      use with the ASCII Console Interface"
::= { aRtgPnniCfgNodeRowStatusEntry 2 }

aRtgPnniCfgNodeStorageType OBJECT-TYPE
   SYNTAX     StorageType 
   ACCESS     read-only
   STATUS     mandatory
   DESCRIPTION
     "This variable represents the storage type value for the
      aRtgPnniCfgNode tables."
::= { aRtgPnniCfgNodeRowStatusEntry 4 }

aRtgPnniCfgNodeIndex OBJECT-TYPE
   SYNTAX     Integer32 (0..104)
   ACCESS     not-accessible
   STATUS     mandatory
   DESCRIPTION
     "This variable represents the index for the aRtgPnniCfgNode tables."
::= { aRtgPnniCfgNodeRowStatusEntry 10 }

aRtgPnniCfgNodeProvTable OBJECT-TYPE
   SYNTAX     SEQUENCE OF ARtgPnniCfgNodeProvEntry
   ACCESS     not-accessible
   STATUS     mandatory
   DESCRIPTION
     "This group contains the provisionable attributes of a 
      ConfiguredNode component."
::= { aRtgPnniCfgNode 10 }

aRtgPnniCfgNodeProvEntry OBJECT-TYPE
   SYNTAX     ARtgPnniCfgNodeProvEntry
   ACCESS     not-accessible
   STATUS     mandatory
   DESCRIPTION
     "An entry in the aRtgPnniCfgNodeProvTable."
   INDEX {
      aRtgIndex,
      aRtgPnniIndex,
      aRtgPnniCfgNodeIndex }
::= { aRtgPnniCfgNodeProvTable 1 }

ARtgPnniCfgNodeProvEntry ::= SEQUENCE {
   aRtgPnniCfgNodeNodeId
      HexString,
   aRtgPnniCfgNodePeerGroupId
      HexString }

aRtgPnniCfgNodeNodeId OBJECT-TYPE
   SYNTAX     HexString (SIZE (0..22))
   ACCESS     read-write
   STATUS     mandatory
   DESCRIPTION
     "This attribute specifies the node id of the configured node. If this 
      attribute is set to null, then the node id is computed as follows:
      
      If this is the lowest configured node, then the node id is computed 
      as the level (one octet), followed by the integer value 160 (one 
      octet), followed by the node address (20 octets).
      
      If this is not the lowest configured node, then the node id is 
      computed as the level (one octet), followed by the 14 octet peer 
      group id of the child peer group which the LGN represents, 
      followed by the ESI specified in the node address (6 octets), 
      followed by the integer value 0 (one octet)."
::= { aRtgPnniCfgNodeProvEntry 2 }

aRtgPnniCfgNodePeerGroupId OBJECT-TYPE
   SYNTAX     HexString (SIZE (0..14))
   ACCESS     read-write
   STATUS     mandatory
   DESCRIPTION
     "This attribute allows the peer group id of the Logical Group Node 
      (LGN) to be set. The peer group id is specified by 28 hex digits 
      where the first octet represents the level of the node and the 
      remaining 13 octets form the End System Address. If this attribute 
      is set to the null string then the peer group id is computed as 
      follows:
      
      The peer group id for a lowest level node is computed to be the 
      node's level (one octet), followed by the first <level> bits of the 
      node's address, followed by zero or more padding 0 bits.
      
      The peer group id for an LGN is computed to be the LGN's level 
      (one octet), followed by the first <level> bits of the id of the peer 
      group which this LGN represents."
::= { aRtgPnniCfgNodeProvEntry 3 }

aRtgPnniCfgNodeOperTable OBJECT-TYPE
   SYNTAX     SEQUENCE OF ARtgPnniCfgNodeOperEntry
   ACCESS     not-accessible
   STATUS     mandatory
   DESCRIPTION
     "This group contains the generic operational attributes of a 
      ConfiguredNode component."
::= { aRtgPnniCfgNode 11 }

aRtgPnniCfgNodeOperEntry OBJECT-TYPE
   SYNTAX     ARtgPnniCfgNodeOperEntry
   ACCESS     not-accessible
   STATUS     mandatory
   DESCRIPTION
     "An entry in the aRtgPnniCfgNodeOperTable."
   INDEX {
      aRtgIndex,
      aRtgPnniIndex,
      aRtgPnniCfgNodeIndex }
::= { aRtgPnniCfgNodeOperTable 1 }

ARtgPnniCfgNodeOperEntry ::= SEQUENCE {
   aRtgPnniCfgNodeNodeAddress
      HexString,
   aRtgPnniCfgNodeOpNodeId
      HexString,
   aRtgPnniCfgNodeOpPeerGroupId
      HexString,
   aRtgPnniCfgNodeNumNeighbors
      Unsigned32,
   aRtgPnniCfgNodeNumRccs
      Unsigned32,
   aRtgPnniCfgNodeCurrentLeadershipPriority
      Unsigned32,
   aRtgPnniCfgNodePglElectionState
      INTEGER }

aRtgPnniCfgNodeNodeAddress OBJECT-TYPE
   SYNTAX     HexString (SIZE (20))
   ACCESS     read-only
   STATUS     mandatory
   DESCRIPTION
     "This attribute indicates the address of the node at this level.
      
      At the lowest level, the nodeAddress is determined by the value of 
      the nodeAddressPrefix attribute for the ARtg Pnni component 
      followed by the level of this CfgNode.
      
      For LGNs, the nodeAddress is the same as the nodeAddress of the 
      node at the lowest level, with the selector field set to the level of the 
      peer group containing the LGN."
::= { aRtgPnniCfgNodeOperEntry 1 }

aRtgPnniCfgNodeOpNodeId OBJECT-TYPE
   SYNTAX     HexString (SIZE (22))
   ACCESS     read-only
   STATUS     mandatory
   DESCRIPTION
     "This attribute indicates the node id of the node at this level. The 
      default node id is computed as follows:
      
      If this is the lowest level node, then the default node id is computed 
      as the level (one octet), followed by the integer value 160 (one 
      octet), followed by the node address (20 octets).
      
      If this is not the lowest level node, then the default node id is 
      computed as the level (one octet), followed by the 14 octet peer 
      group id of the child peer group which the LGN represents, 
      followed by the ESI specified in the node address (6 octets), 
      followed by the integer value 0 (one octet)."
::= { aRtgPnniCfgNodeOperEntry 2 }

aRtgPnniCfgNodeOpPeerGroupId OBJECT-TYPE
   SYNTAX     HexString (SIZE (14))
   ACCESS     read-only
   STATUS     mandatory
   DESCRIPTION
     "This attribute indicates the peer group id of the node at this level. 
      The value is determined by the provisioned peerGroupId attribute."
::= { aRtgPnniCfgNodeOperEntry 3 }

aRtgPnniCfgNodeNumNeighbors OBJECT-TYPE
   SYNTAX     Unsigned32 (0..65535)
   ACCESS     read-only
   STATUS     mandatory
   DESCRIPTION
     "This attribute indicates the number of PNNI nodes which are 
      neighbors of this node at this level."
::= { aRtgPnniCfgNodeOperEntry 4 }

aRtgPnniCfgNodeNumRccs OBJECT-TYPE
   SYNTAX     Unsigned32 (0..65535)
   ACCESS     read-only
   STATUS     mandatory
   DESCRIPTION
     "This attribute indicates the number of Routing Control Channels to 
      this node's neighbors at this level."
::= { aRtgPnniCfgNodeOperEntry 5 }

aRtgPnniCfgNodeCurrentLeadershipPriority OBJECT-TYPE
   SYNTAX     Unsigned32 (0..205)
   ACCESS     read-only
   STATUS     mandatory
   DESCRIPTION
     "This attribute indicates the leadership priority of the node that this 
      node believes should be the peer group leader at this point in time."
::= { aRtgPnniCfgNodeOperEntry 6 }

aRtgPnniCfgNodePglElectionState OBJECT-TYPE
   SYNTAX     INTEGER  {
                 starting(0),
                 awaiting(1),
                 awaitingFull(2),
                 initialDelay(3),
                 calculating(4),
                 operNotPgl(5),
                 operPgl(6),
                 awaitUnanimity(7),
                 hungElection(8),
                 awaitReElection(9) }
   ACCESS     read-only
   STATUS     mandatory
   DESCRIPTION
     "This attribute indicates the current state of the peer group leader 
      election process. The following are the possible values for this 
      attribute:
      
      starting: the initial state of the state machine.
      
      awaiting: the node has started the Hello Finite State Machine on at 
      least one link, and no peer has been found yet.
      
      awaitingFull: no database synchronization process has been 
      completed yet but at least one neighboring peer has been found.
      
      initialDelay: Database synchronization has been completed with at 
      least one neighboring peer. The node must wait pglInitTime second 
      before it can select and advertise its preferred Peer Group Leader 
      (PGL).
      
      calculating: the node is in the process of calculating what its new 
      choice for preferred PGL will be.
      
      operNotPgl: a non PGL node is in the process of determining which 
      node has the highest priority to be PGL by examining PTSEs sent 
      by other nodes.
      
      operPgl: a PGL node is in the process of determining if another 
      node has a higher priority than itself by examining PTSEs sent by 
      other nodes.
      
      awaitUnanimity: the node has chosen itself as PGL. If the node has 
      been elected unanimously, it generates a Unanimity event. It waits 
      for unanimity or expiration of the overrideDelay timer before 
      declaring itself peer group leader.
      
      hungElection: the node has chosen itself as PGL with less than 2/3 
      of the other nodes advertising it as their preferred PGL. In this case 
      either this node should change its choice of preferred PGL, or the 
      other nodes are going to accept it as PGL.
      
      awaitReElection: the node has lost connectivity to the current PGL. 
      The connectivity must be reestablished before the 
      reElectionInterval timer fires, otherwise the election is redone."
::= { aRtgPnniCfgNodeOperEntry 7 }


-- ARtg Pnni CfgNode/<level> SummaryAddress/<address>, 
-- <prefixLength>, <reachability>
-- A summary address is an abbreviation of a set of addresses, 
-- represented by an address prefix that all of the summarized 
-- addresses have in common.
-- A suppressed summary address is used to suppress the 
-- advertisement of addresses which match this prefix, regardless of 
-- scope.
-- 
-- The prefixLength specifies the number of prefix bits of the address 
-- and reachability specifies whether the address is to summarize 
-- internal or exterior addresses.
-- 
-- An internal address is an address of a destination that is directly 
-- attached to the logical node. An exterior address is an address of a 
-- destination that is located outside of the PNNI routing domain but 
-- can be reached through a port attached to the logical node.

aRtgPnniCfgNodeSAddr OBJECT IDENTIFIER ::= { aRtgPnniCfgNode 2 }



aRtgPnniCfgNodeSAddrRowStatusTable OBJECT-TYPE
   SYNTAX     SEQUENCE OF ARtgPnniCfgNodeSAddrRowStatusEntry
   ACCESS     not-accessible
   STATUS     mandatory
   DESCRIPTION
     "This entry controls the addition and deletion of 
      aRtgPnniCfgNodeSAddr components."
::= { aRtgPnniCfgNodeSAddr 1 }

aRtgPnniCfgNodeSAddrRowStatusEntry OBJECT-TYPE
   SYNTAX     ARtgPnniCfgNodeSAddrRowStatusEntry
   ACCESS     not-accessible
   STATUS     mandatory
   DESCRIPTION
     "A single entry in the table represents a single 
      aRtgPnniCfgNodeSAddr component."
   INDEX {
      aRtgIndex,
      aRtgPnniIndex,
      aRtgPnniCfgNodeIndex,
      aRtgPnniCfgNodeSAddrAddressIndex,
      aRtgPnniCfgNodeSAddrPrefixLengthIndex,
      aRtgPnniCfgNodeSAddrReachabilityIndex }
::= { aRtgPnniCfgNodeSAddrRowStatusTable 1 }

ARtgPnniCfgNodeSAddrRowStatusEntry ::= SEQUENCE {
   aRtgPnniCfgNodeSAddrRowStatus
      RowStatus,
   aRtgPnniCfgNodeSAddrComponentName
      DisplayString,
   aRtgPnniCfgNodeSAddrStorageType
      StorageType,
   aRtgPnniCfgNodeSAddrAddressIndex
      HexString,
   aRtgPnniCfgNodeSAddrPrefixLengthIndex
      Integer32,
   aRtgPnniCfgNodeSAddrReachabilityIndex
      INTEGER }

aRtgPnniCfgNodeSAddrRowStatus OBJECT-TYPE
   SYNTAX     RowStatus 
   ACCESS     read-write
   STATUS     mandatory
   DESCRIPTION
     "This variable is used as the basis for SNMP naming of
      aRtgPnniCfgNodeSAddr components.
      These components can be added and deleted."
::= { aRtgPnniCfgNodeSAddrRowStatusEntry 1 }

aRtgPnniCfgNodeSAddrComponentName OBJECT-TYPE
   SYNTAX     DisplayString 
   ACCESS     read-only
   STATUS     mandatory
   DESCRIPTION
     "This variable provides the component's string name for
      use with the ASCII Console Interface"
::= { aRtgPnniCfgNodeSAddrRowStatusEntry 2 }

aRtgPnniCfgNodeSAddrStorageType OBJECT-TYPE
   SYNTAX     StorageType 
   ACCESS     read-only
   STATUS     mandatory
   DESCRIPTION
     "This variable represents the storage type value for the
      aRtgPnniCfgNodeSAddr tables."
::= { aRtgPnniCfgNodeSAddrRowStatusEntry 4 }

aRtgPnniCfgNodeSAddrAddressIndex OBJECT-TYPE
   SYNTAX     HexString (SIZE (19))
   ACCESS     not-accessible
   STATUS     mandatory
   DESCRIPTION
     "This variable represents an index for the aRtgPnniCfgNodeSAddr tables."
::= { aRtgPnniCfgNodeSAddrRowStatusEntry 10 }

aRtgPnniCfgNodeSAddrPrefixLengthIndex OBJECT-TYPE
   SYNTAX     Integer32 (1..152)
   ACCESS     not-accessible
   STATUS     mandatory
   DESCRIPTION
     "This variable represents an index for the aRtgPnniCfgNodeSAddr tables."
::= { aRtgPnniCfgNodeSAddrRowStatusEntry 11 }

aRtgPnniCfgNodeSAddrReachabilityIndex OBJECT-TYPE
   SYNTAX     INTEGER  {
                 internal(0),
                 exterior(1) }
   ACCESS     not-accessible
   STATUS     mandatory
   DESCRIPTION
     "This variable represents an index for the aRtgPnniCfgNodeSAddr tables."
::= { aRtgPnniCfgNodeSAddrRowStatusEntry 12 }

aRtgPnniCfgNodeSAddrProvTable OBJECT-TYPE
   SYNTAX     SEQUENCE OF ARtgPnniCfgNodeSAddrProvEntry
   ACCESS     not-accessible
   STATUS     mandatory
   DESCRIPTION
     "This group contains the provisionable attributes of a 
      SummaryAddress component. 
      
      A summary address is an abbreviation of a set of addresses, 
      represented by an address prefix that all of the summarized 
      addresses have in common.
      A suppressed summary address is used to suppress the 
      advertisement of addresses which match this prefix, regardless of 
      scope."
::= { aRtgPnniCfgNodeSAddr 10 }

aRtgPnniCfgNodeSAddrProvEntry OBJECT-TYPE
   SYNTAX     ARtgPnniCfgNodeSAddrProvEntry
   ACCESS     not-accessible
   STATUS     mandatory
   DESCRIPTION
     "An entry in the aRtgPnniCfgNodeSAddrProvTable."
   INDEX {
      aRtgIndex,
      aRtgPnniIndex,
      aRtgPnniCfgNodeIndex,
      aRtgPnniCfgNodeSAddrAddressIndex,
      aRtgPnniCfgNodeSAddrPrefixLengthIndex,
      aRtgPnniCfgNodeSAddrReachabilityIndex }
::= { aRtgPnniCfgNodeSAddrProvTable 1 }

ARtgPnniCfgNodeSAddrProvEntry ::= SEQUENCE {
   aRtgPnniCfgNodeSAddrSuppress
      INTEGER }

aRtgPnniCfgNodeSAddrSuppress OBJECT-TYPE
   SYNTAX     INTEGER  {
                 false(0),
                 true(1) }
   ACCESS     read-write
   STATUS     mandatory
   DESCRIPTION
     "This attribute specifies whether or not the address should be 
      suppressed. If this attribute is set to true, then all addresses 
      matching that prefix will not be advertised above this level."
   DEFVAL     { false }
::= { aRtgPnniCfgNodeSAddrProvEntry 2 }

aRtgPnniCfgNodeSAddrOperTable OBJECT-TYPE
   SYNTAX     SEQUENCE OF ARtgPnniCfgNodeSAddrOperEntry
   ACCESS     not-accessible
   STATUS     mandatory
   DESCRIPTION
     "This group contains the operational attributes of a SummaryAddress 
      component."
::= { aRtgPnniCfgNodeSAddr 11 }

aRtgPnniCfgNodeSAddrOperEntry OBJECT-TYPE
   SYNTAX     ARtgPnniCfgNodeSAddrOperEntry
   ACCESS     not-accessible
   STATUS     mandatory
   DESCRIPTION
     "An entry in the aRtgPnniCfgNodeSAddrOperTable."
   INDEX {
      aRtgIndex,
      aRtgPnniIndex,
      aRtgPnniCfgNodeIndex,
      aRtgPnniCfgNodeSAddrAddressIndex,
      aRtgPnniCfgNodeSAddrPrefixLengthIndex,
      aRtgPnniCfgNodeSAddrReachabilityIndex }
::= { aRtgPnniCfgNodeSAddrOperTable 1 }

ARtgPnniCfgNodeSAddrOperEntry ::= SEQUENCE {
   aRtgPnniCfgNodeSAddrState
      INTEGER,
   aRtgPnniCfgNodeSAddrScope
      INTEGER }

aRtgPnniCfgNodeSAddrState OBJECT-TYPE
   SYNTAX     INTEGER  {
                 advertising(0),
                 suppressing(1),
                 inactive(2) }
   ACCESS     read-only
   STATUS     mandatory
   DESCRIPTION
     "This attribute indicates the state of the address: one of advertising, 
      suppressing or inactive.
      inactive: the summary address has been configured but is not 
      suppressing or summarizing any ATM addresses. 
      suppressing: the summary address has suppressed at least one ATM 
      address on the node.
      advertising: the summary address is summarizing at least one ATM 
      address on the node."
::= { aRtgPnniCfgNodeSAddrOperEntry 1 }

aRtgPnniCfgNodeSAddrScope OBJECT-TYPE
   SYNTAX     INTEGER (-1..104)
   ACCESS     read-only
   STATUS     mandatory
   DESCRIPTION
     "This attribute indicates the scope of the summary address. The 
      scope corresponds to the scope of the underlying summarized 
      address with the highest advertised scope. A value of -1 means the 
      scope is unknown."
::= { aRtgPnniCfgNodeSAddrOperEntry 2 }

-- 
-- *** THIS SUBTREE CURRENTLY NOT IMPLEMENTED ***
-- 

-- ARtg Pnni CfgNode/n Neighbor/<node id>
-- This component represents the operational attributes for a neighbor 
-- node at this level. 

aRtgPnniCfgNodeNbr OBJECT IDENTIFIER ::= { aRtgPnniCfgNode 3 }



aRtgPnniCfgNodeNbrRowStatusTable OBJECT-TYPE
   SYNTAX     SEQUENCE OF ARtgPnniCfgNodeNbrRowStatusEntry
   ACCESS     not-accessible
   STATUS     mandatory
   DESCRIPTION
     "*** THIS TABLE CURRENTLY NOT IMPLEMENTED ***

      This entry controls the addition and deletion of 
      aRtgPnniCfgNodeNbr components."
::= { aRtgPnniCfgNodeNbr 1 }

aRtgPnniCfgNodeNbrRowStatusEntry OBJECT-TYPE
   SYNTAX     ARtgPnniCfgNodeNbrRowStatusEntry
   ACCESS     not-accessible
   STATUS     mandatory
   DESCRIPTION
     "A single entry in the table represents a single 
      aRtgPnniCfgNodeNbr component."
   INDEX {
      aRtgIndex,
      aRtgPnniIndex,
      aRtgPnniCfgNodeIndex,
      aRtgPnniCfgNodeNbrIndex }
::= { aRtgPnniCfgNodeNbrRowStatusTable 1 }

ARtgPnniCfgNodeNbrRowStatusEntry ::= SEQUENCE {
   aRtgPnniCfgNodeNbrRowStatus
      RowStatus,
   aRtgPnniCfgNodeNbrComponentName
      DisplayString,
   aRtgPnniCfgNodeNbrStorageType
      StorageType,
   aRtgPnniCfgNodeNbrIndex
      HexString }

aRtgPnniCfgNodeNbrRowStatus OBJECT-TYPE
   SYNTAX     RowStatus 
   ACCESS     read-only
   STATUS     mandatory
   DESCRIPTION
     "This variable is used as the basis for SNMP naming of
      aRtgPnniCfgNodeNbr components.
      These components cannot be added nor deleted."
::= { aRtgPnniCfgNodeNbrRowStatusEntry 1 }

aRtgPnniCfgNodeNbrComponentName OBJECT-TYPE
   SYNTAX     DisplayString 
   ACCESS     read-only
   STATUS     mandatory
   DESCRIPTION
     "This variable provides the component's string name for
      use with the ASCII Console Interface"
::= { aRtgPnniCfgNodeNbrRowStatusEntry 2 }

aRtgPnniCfgNodeNbrStorageType OBJECT-TYPE
   SYNTAX     StorageType 
   ACCESS     read-only
   STATUS     mandatory
   DESCRIPTION
     "This variable represents the storage type value for the
      aRtgPnniCfgNodeNbr tables."
::= { aRtgPnniCfgNodeNbrRowStatusEntry 4 }

aRtgPnniCfgNodeNbrIndex OBJECT-TYPE
   SYNTAX     HexString (SIZE (22))
   ACCESS     not-accessible
   STATUS     mandatory
   DESCRIPTION
     "This variable represents the index for the aRtgPnniCfgNodeNbr tables."
::= { aRtgPnniCfgNodeNbrRowStatusEntry 10 }

aRtgPnniCfgNodeNbrOperTable OBJECT-TYPE
   SYNTAX     SEQUENCE OF ARtgPnniCfgNodeNbrOperEntry
   ACCESS     not-accessible
   STATUS     mandatory
   DESCRIPTION
     "*** THIS TABLE CURRENTLY NOT IMPLEMENTED ***

      This group contains the operational attributes of a Neighbor 
      component."
::= { aRtgPnniCfgNodeNbr 10 }

aRtgPnniCfgNodeNbrOperEntry OBJECT-TYPE
   SYNTAX     ARtgPnniCfgNodeNbrOperEntry
   ACCESS     not-accessible
   STATUS     mandatory
   DESCRIPTION
     "An entry in the aRtgPnniCfgNodeNbrOperTable."
   INDEX {
      aRtgIndex,
      aRtgPnniIndex,
      aRtgPnniCfgNodeIndex,
      aRtgPnniCfgNodeNbrIndex }
::= { aRtgPnniCfgNodeNbrOperTable 1 }

ARtgPnniCfgNodeNbrOperEntry ::= SEQUENCE {
   aRtgPnniCfgNodeNbrPeerState
      INTEGER }

aRtgPnniCfgNodeNbrPeerState OBJECT-TYPE
   SYNTAX     INTEGER  {
                 npDown(0),
                 negotiating(1),
                 exchanging(2),
                 loading(3),
                 full(4) }
   ACCESS     read-only
   STATUS     mandatory
   DESCRIPTION
     "This attribute indicates the state of the routing database exchange 
      with the peer node.
      
      npDown: there are no active links (i.e. in the twoWayInside Hello 
      state) to the neighboring peer.
      
      negotiating: the first step in creating an adjacency between the two 
      neighboring peers; this step determines which node is the master, 
      and what the initial DS sequence number will be.
      
      exchanging: the node describes its topology database by sending 
      Database Summary packets to the neighboring peer. 
      
      loading: a full sequence of Database Summary packets has been 
      exchanged with the neighboring peer, and the required PTSEs are 
      requested and at least one has not yet been received.
      
      full: All PTSEs known to be available have been received from the 
      neighboring peer. At this point the all ports leading to the neighbor 
      node will be flooded in PTSEs within the peer group."
::= { aRtgPnniCfgNodeNbrOperEntry 2 }

aRtgPnniCfgNodeNbrStatsTable OBJECT-TYPE
   SYNTAX     SEQUENCE OF ARtgPnniCfgNodeNbrStatsEntry
   ACCESS     not-accessible
   STATUS     mandatory
   DESCRIPTION
     "*** THIS TABLE CURRENTLY NOT IMPLEMENTED ***

      This group contains the statistical operational attributes of a 
      Neighbor component."
::= { aRtgPnniCfgNodeNbr 11 }

aRtgPnniCfgNodeNbrStatsEntry OBJECT-TYPE
   SYNTAX     ARtgPnniCfgNodeNbrStatsEntry
   ACCESS     not-accessible
   STATUS     mandatory
   DESCRIPTION
     "An entry in the aRtgPnniCfgNodeNbrStatsTable."
   INDEX {
      aRtgIndex,
      aRtgPnniIndex,
      aRtgPnniCfgNodeIndex,
      aRtgPnniCfgNodeNbrIndex }
::= { aRtgPnniCfgNodeNbrStatsTable 1 }

ARtgPnniCfgNodeNbrStatsEntry ::= SEQUENCE {
   aRtgPnniCfgNodeNbrPtspRx
      Counter32,
   aRtgPnniCfgNodeNbrPtspTx
      Counter32,
   aRtgPnniCfgNodeNbrPtseRx
      Counter32,
   aRtgPnniCfgNodeNbrPtseTx
      Counter32,
   aRtgPnniCfgNodeNbrPtseReqRx
      Counter32,
   aRtgPnniCfgNodeNbrPtseReqTx
      Counter32,
   aRtgPnniCfgNodeNbrPtseAcksRx
      Counter32,
   aRtgPnniCfgNodeNbrPtseAcksTx
      Counter32,
   aRtgPnniCfgNodeNbrDbSummariesRx
      Counter32,
   aRtgPnniCfgNodeNbrDbSummariesTx
      Counter32,
   aRtgPnniCfgNodeNbrBadPtspRx
      Counter32,
   aRtgPnniCfgNodeNbrBadPtseRx
      Counter32,
   aRtgPnniCfgNodeNbrBadPtseReqRx
      Counter32,
   aRtgPnniCfgNodeNbrBadPtseAckRx
      Counter32,
   aRtgPnniCfgNodeNbrBadDbSummariesRx
      Counter32 }

aRtgPnniCfgNodeNbrPtspRx OBJECT-TYPE
   SYNTAX     Counter32 
   ACCESS     read-only
   STATUS     mandatory
   DESCRIPTION
     "This attribute counts the PNNI Topology State Packets received 
      from the neighbor node. The counter wraps when it exceeds the 
      maximum value."
::= { aRtgPnniCfgNodeNbrStatsEntry 1 }

aRtgPnniCfgNodeNbrPtspTx OBJECT-TYPE
   SYNTAX     Counter32 
   ACCESS     read-only
   STATUS     mandatory
   DESCRIPTION
     "This attribute counts the total number of PTSPs send to the 
      neighbor node.The counter wraps when it exceeds the maximum 
      value."
::= { aRtgPnniCfgNodeNbrStatsEntry 2 }

aRtgPnniCfgNodeNbrPtseRx OBJECT-TYPE
   SYNTAX     Counter32 
   ACCESS     read-only
   STATUS     mandatory
   DESCRIPTION
     "This attribute counts the total number of PTSEs received from the 
      neighbor node. The counter wraps when it exceeds the maximum 
      value."
::= { aRtgPnniCfgNodeNbrStatsEntry 3 }

aRtgPnniCfgNodeNbrPtseTx OBJECT-TYPE
   SYNTAX     Counter32 
   ACCESS     read-only
   STATUS     mandatory
   DESCRIPTION
     "This attribute counts the total number of PTSEs sent to the neighbor 
      node. The counter wraps when it exceeds the maximum value."
::= { aRtgPnniCfgNodeNbrStatsEntry 4 }

aRtgPnniCfgNodeNbrPtseReqRx OBJECT-TYPE
   SYNTAX     Counter32 
   ACCESS     read-only
   STATUS     mandatory
   DESCRIPTION
     "This attribute counts the total number of PTSE requests received 
      from the neighbor node. The counter wraps when it exceeds the 
      maximum value."
::= { aRtgPnniCfgNodeNbrStatsEntry 5 }

aRtgPnniCfgNodeNbrPtseReqTx OBJECT-TYPE
   SYNTAX     Counter32 
   ACCESS     read-only
   STATUS     mandatory
   DESCRIPTION
     "This attribute counts the total number of PTSE requests sent to the 
      neighbor node. The counter wraps when it exceeds the maximum 
      value."
::= { aRtgPnniCfgNodeNbrStatsEntry 6 }

aRtgPnniCfgNodeNbrPtseAcksRx OBJECT-TYPE
   SYNTAX     Counter32 
   ACCESS     read-only
   STATUS     mandatory
   DESCRIPTION
     "This attribute counts the total number of PTSE acknowledgments 
      received from the neighbor node. The counter wraps when it 
      exceeds the maximum value."
::= { aRtgPnniCfgNodeNbrStatsEntry 7 }

aRtgPnniCfgNodeNbrPtseAcksTx OBJECT-TYPE
   SYNTAX     Counter32 
   ACCESS     read-only
   STATUS     mandatory
   DESCRIPTION
     "This attribute counts the total number of PTSE acknowledgments 
      sent to the neighbor node. The counter wraps when it exceeds the 
      maximum value."
::= { aRtgPnniCfgNodeNbrStatsEntry 8 }

aRtgPnniCfgNodeNbrDbSummariesRx OBJECT-TYPE
   SYNTAX     Counter32 
   ACCESS     read-only
   STATUS     mandatory
   DESCRIPTION
     "This attribute counts the number of database summary packets 
      received from the neighbor. The counter wraps when it exceeds the 
      maximum value."
::= { aRtgPnniCfgNodeNbrStatsEntry 9 }

aRtgPnniCfgNodeNbrDbSummariesTx OBJECT-TYPE
   SYNTAX     Counter32 
   ACCESS     read-only
   STATUS     mandatory
   DESCRIPTION
     "This attribute counts the number of database summary packets 
      transmitted to the neighbor. The counter wraps when it exceeds the 
      maximum value."
::= { aRtgPnniCfgNodeNbrStatsEntry 10 }

aRtgPnniCfgNodeNbrBadPtspRx OBJECT-TYPE
   SYNTAX     Counter32 
   ACCESS     read-only
   STATUS     mandatory
   DESCRIPTION
     "This attribute counts the total number of invalid PTSP packets 
      received from the neighbor node. The counter wraps when it 
      exceeds the maximum value."
::= { aRtgPnniCfgNodeNbrStatsEntry 11 }

aRtgPnniCfgNodeNbrBadPtseRx OBJECT-TYPE
   SYNTAX     Counter32 
   ACCESS     read-only
   STATUS     mandatory
   DESCRIPTION
     "This attribute counts the total number of invalid PTSE packets 
      received to the neighbor node. The counter wraps when it exceeds 
      the maximum value."
::= { aRtgPnniCfgNodeNbrStatsEntry 12 }

aRtgPnniCfgNodeNbrBadPtseReqRx OBJECT-TYPE
   SYNTAX     Counter32 
   ACCESS     read-only
   STATUS     mandatory
   DESCRIPTION
     "This attribute counts the total number of invalid PTSE requests 
      received from the neighbor node. The counter wraps when it 
      exceeds the maximum value."
::= { aRtgPnniCfgNodeNbrStatsEntry 13 }

aRtgPnniCfgNodeNbrBadPtseAckRx OBJECT-TYPE
   SYNTAX     Counter32 
   ACCESS     read-only
   STATUS     mandatory
   DESCRIPTION
     "This attribute counts the total number of invalid PTSE 
      acknowledgments received from the neighbor node. The counter 
      wraps when it exceeds the maximum value."
::= { aRtgPnniCfgNodeNbrStatsEntry 14 }

aRtgPnniCfgNodeNbrBadDbSummariesRx OBJECT-TYPE
   SYNTAX     Counter32 
   ACCESS     read-only
   STATUS     mandatory
   DESCRIPTION
     "This attribute counts the total number of invalid database summary 
      packets received from the neighbor. The counter wraps when it 
      exceeds the maximum value."
::= { aRtgPnniCfgNodeNbrStatsEntry 15 }

aRtgPnniCfgNodeNbrRccListTable OBJECT-TYPE
   SYNTAX     SEQUENCE OF ARtgPnniCfgNodeNbrRccListEntry
   ACCESS     not-accessible
   STATUS     mandatory
   DESCRIPTION
     "*** THIS TABLE CURRENTLY NOT IMPLEMENTED ***

      This attribute indicates the component names of all Routing Control 
      Channels to the neighbor PNNI node."
::= { aRtgPnniCfgNodeNbr 385 }

aRtgPnniCfgNodeNbrRccListEntry OBJECT-TYPE
   SYNTAX     ARtgPnniCfgNodeNbrRccListEntry
   ACCESS     not-accessible
   STATUS     mandatory
   DESCRIPTION
     "An entry in the aRtgPnniCfgNodeNbrRccListTable."
   INDEX {
      aRtgIndex,
      aRtgPnniIndex,
      aRtgPnniCfgNodeIndex,
      aRtgPnniCfgNodeNbrIndex,
      aRtgPnniCfgNodeNbrRccListValue }
::= { aRtgPnniCfgNodeNbrRccListTable 1 }

ARtgPnniCfgNodeNbrRccListEntry ::= SEQUENCE {
   aRtgPnniCfgNodeNbrRccListValue
      RowPointer }

aRtgPnniCfgNodeNbrRccListValue OBJECT-TYPE
   SYNTAX     RowPointer 
   ACCESS     read-only
   STATUS     mandatory
   DESCRIPTION
     "This variable represents both the value and the index for the
      aRtgPnniCfgNodeNbrRccListTable."
::= { aRtgPnniCfgNodeNbrRccListEntry 1 }


-- ARtg Pnni CfgNode/<level> DefSAddr
-- A default summary address is an internal summary address 
-- computed for every logical group node as follows:
-- If this is not the lowest configured node, then the default summary 
-- address is identical to the peer group id that this logical group 
-- represents.
-- If this is the lowest configured node but not at level 104, then the 
-- default summary address is the 13-octet prefix of the node's 
-- address.
-- A node at level 104 has no default summary address.

aRtgPnniCfgNodeDefSAddr OBJECT IDENTIFIER ::= { aRtgPnniCfgNode 4 }



aRtgPnniCfgNodeDefSAddrRowStatusTable OBJECT-TYPE
   SYNTAX     SEQUENCE OF ARtgPnniCfgNodeDefSAddrRowStatusEntry
   ACCESS     not-accessible
   STATUS     mandatory
   DESCRIPTION
     "This entry controls the addition and deletion of 
      aRtgPnniCfgNodeDefSAddr components."
::= { aRtgPnniCfgNodeDefSAddr 1 }

aRtgPnniCfgNodeDefSAddrRowStatusEntry OBJECT-TYPE
   SYNTAX     ARtgPnniCfgNodeDefSAddrRowStatusEntry
   ACCESS     not-accessible
   STATUS     mandatory
   DESCRIPTION
     "A single entry in the table represents a single 
      aRtgPnniCfgNodeDefSAddr component."
   INDEX {
      aRtgIndex,
      aRtgPnniIndex,
      aRtgPnniCfgNodeIndex,
      aRtgPnniCfgNodeDefSAddrIndex }
::= { aRtgPnniCfgNodeDefSAddrRowStatusTable 1 }

ARtgPnniCfgNodeDefSAddrRowStatusEntry ::= SEQUENCE {
   aRtgPnniCfgNodeDefSAddrRowStatus
      RowStatus,
   aRtgPnniCfgNodeDefSAddrComponentName
      DisplayString,
   aRtgPnniCfgNodeDefSAddrStorageType
      StorageType,
   aRtgPnniCfgNodeDefSAddrIndex
      NonReplicated }

aRtgPnniCfgNodeDefSAddrRowStatus OBJECT-TYPE
   SYNTAX     RowStatus 
   ACCESS     read-only
   STATUS     mandatory
   DESCRIPTION
     "This variable is used as the basis for SNMP naming of
      aRtgPnniCfgNodeDefSAddr components.
      These components cannot be added nor deleted."
::= { aRtgPnniCfgNodeDefSAddrRowStatusEntry 1 }

aRtgPnniCfgNodeDefSAddrComponentName OBJECT-TYPE
   SYNTAX     DisplayString 
   ACCESS     read-only
   STATUS     mandatory
   DESCRIPTION
     "This variable provides the component's string name for
      use with the ASCII Console Interface"
::= { aRtgPnniCfgNodeDefSAddrRowStatusEntry 2 }

aRtgPnniCfgNodeDefSAddrStorageType OBJECT-TYPE
   SYNTAX     StorageType 
   ACCESS     read-only
   STATUS     mandatory
   DESCRIPTION
     "This variable represents the storage type value for the
      aRtgPnniCfgNodeDefSAddr tables."
::= { aRtgPnniCfgNodeDefSAddrRowStatusEntry 4 }

aRtgPnniCfgNodeDefSAddrIndex OBJECT-TYPE
   SYNTAX     NonReplicated 
   ACCESS     not-accessible
   STATUS     mandatory
   DESCRIPTION
     "This variable represents the index for the aRtgPnniCfgNodeDefSAddr tables."
::= { aRtgPnniCfgNodeDefSAddrRowStatusEntry 10 }

aRtgPnniCfgNodeDefSAddrDefAddrTable OBJECT-TYPE
   SYNTAX     SEQUENCE OF ARtgPnniCfgNodeDefSAddrDefAddrEntry
   ACCESS     not-accessible
   STATUS     mandatory
   DESCRIPTION
     "This group contains the operational attributes of a 
      DefSummaryAddress component."
::= { aRtgPnniCfgNodeDefSAddr 10 }

aRtgPnniCfgNodeDefSAddrDefAddrEntry OBJECT-TYPE
   SYNTAX     ARtgPnniCfgNodeDefSAddrDefAddrEntry
   ACCESS     not-accessible
   STATUS     mandatory
   DESCRIPTION
     "An entry in the aRtgPnniCfgNodeDefSAddrDefAddrTable."
   INDEX {
      aRtgIndex,
      aRtgPnniIndex,
      aRtgPnniCfgNodeIndex,
      aRtgPnniCfgNodeDefSAddrIndex }
::= { aRtgPnniCfgNodeDefSAddrDefAddrTable 1 }

ARtgPnniCfgNodeDefSAddrDefAddrEntry ::= SEQUENCE {
   aRtgPnniCfgNodeDefSAddrAddress
      HexString }

aRtgPnniCfgNodeDefSAddrAddress OBJECT-TYPE
   SYNTAX     HexString (SIZE (13))
   ACCESS     read-only
   STATUS     mandatory
   DESCRIPTION
     "This attribute indicates the default summary address of the node at 
      this level."
::= { aRtgPnniCfgNodeDefSAddrDefAddrEntry 1 }

aRtgPnniCfgNodeDefSAddrOperTable OBJECT-TYPE
   SYNTAX     SEQUENCE OF ARtgPnniCfgNodeDefSAddrOperEntry
   ACCESS     not-accessible
   STATUS     mandatory
   DESCRIPTION
     "This group contains the operational attributes of a SummaryAddress 
      component."
::= { aRtgPnniCfgNodeDefSAddr 11 }

aRtgPnniCfgNodeDefSAddrOperEntry OBJECT-TYPE
   SYNTAX     ARtgPnniCfgNodeDefSAddrOperEntry
   ACCESS     not-accessible
   STATUS     mandatory
   DESCRIPTION
     "An entry in the aRtgPnniCfgNodeDefSAddrOperTable."
   INDEX {
      aRtgIndex,
      aRtgPnniIndex,
      aRtgPnniCfgNodeIndex,
      aRtgPnniCfgNodeDefSAddrIndex }
::= { aRtgPnniCfgNodeDefSAddrOperTable 1 }

ARtgPnniCfgNodeDefSAddrOperEntry ::= SEQUENCE {
   aRtgPnniCfgNodeDefSAddrState
      INTEGER,
   aRtgPnniCfgNodeDefSAddrScope
      INTEGER }

aRtgPnniCfgNodeDefSAddrState OBJECT-TYPE
   SYNTAX     INTEGER  {
                 advertising(0),
                 suppressing(1),
                 inactive(2) }
   ACCESS     read-only
   STATUS     mandatory
   DESCRIPTION
     "This attribute indicates the state of the address: one of advertising, 
      suppressing or inactive.
      inactive: the summary address has been configured but is not 
      suppressing or summarizing any ATM addresses. 
      suppressing: the summary address has suppressed at least one ATM 
      address on the node.
      advertising: the summary address is summarizing at least one ATM 
      address on the node."
::= { aRtgPnniCfgNodeDefSAddrOperEntry 1 }

aRtgPnniCfgNodeDefSAddrScope OBJECT-TYPE
   SYNTAX     INTEGER (-1..104)
   ACCESS     read-only
   STATUS     mandatory
   DESCRIPTION
     "This attribute indicates the scope of the summary address. The 
      scope corresponds to the scope of the underlying summarized 
      address with the highest advertised scope. A value of -1 means the 
      scope is unknown."
::= { aRtgPnniCfgNodeDefSAddrOperEntry 2 }

-- 
-- *** THIS SUBTREE CURRENTLY NOT IMPLEMENTED ***
-- 

-- ARtg Pnni Topology/<level>
-- 
-- The Topology component provides access to information in this 
-- node's PNNI topology database for a particular level in the PNNI 
-- hierarchy.

aRtgPnniTop OBJECT IDENTIFIER ::= { aRtgPnni 4 }



aRtgPnniTopRowStatusTable OBJECT-TYPE
   SYNTAX     SEQUENCE OF ARtgPnniTopRowStatusEntry
   ACCESS     not-accessible
   STATUS     mandatory
   DESCRIPTION
     "*** THIS TABLE CURRENTLY NOT IMPLEMENTED ***

      This entry controls the addition and deletion of 
      aRtgPnniTop components."
::= { aRtgPnniTop 1 }

aRtgPnniTopRowStatusEntry OBJECT-TYPE
   SYNTAX     ARtgPnniTopRowStatusEntry
   ACCESS     not-accessible
   STATUS     mandatory
   DESCRIPTION
     "A single entry in the table represents a single 
      aRtgPnniTop component."
   INDEX {
      aRtgIndex,
      aRtgPnniIndex,
      aRtgPnniTopIndex }
::= { aRtgPnniTopRowStatusTable 1 }

ARtgPnniTopRowStatusEntry ::= SEQUENCE {
   aRtgPnniTopRowStatus
      RowStatus,
   aRtgPnniTopComponentName
      DisplayString,
   aRtgPnniTopStorageType
      StorageType,
   aRtgPnniTopIndex
      Integer32 }

aRtgPnniTopRowStatus OBJECT-TYPE
   SYNTAX     RowStatus 
   ACCESS     read-only
   STATUS     mandatory
   DESCRIPTION
     "This variable is used as the basis for SNMP naming of
      aRtgPnniTop components.
      These components cannot be added nor deleted."
::= { aRtgPnniTopRowStatusEntry 1 }

aRtgPnniTopComponentName OBJECT-TYPE
   SYNTAX     DisplayString 
   ACCESS     read-only
   STATUS     mandatory
   DESCRIPTION
     "This variable provides the component's string name for
      use with the ASCII Console Interface"
::= { aRtgPnniTopRowStatusEntry 2 }

aRtgPnniTopStorageType OBJECT-TYPE
   SYNTAX     StorageType 
   ACCESS     read-only
   STATUS     mandatory
   DESCRIPTION
     "This variable represents the storage type value for the
      aRtgPnniTop tables."
::= { aRtgPnniTopRowStatusEntry 4 }

aRtgPnniTopIndex OBJECT-TYPE
   SYNTAX     Integer32 (0..104)
   ACCESS     not-accessible
   STATUS     mandatory
   DESCRIPTION
     "This variable represents the index for the aRtgPnniTop tables."
::= { aRtgPnniTopRowStatusEntry 10 }

aRtgPnniTopOperTable OBJECT-TYPE
   SYNTAX     SEQUENCE OF ARtgPnniTopOperEntry
   ACCESS     not-accessible
   STATUS     mandatory
   DESCRIPTION
     "*** THIS TABLE CURRENTLY NOT IMPLEMENTED ***

      This group contains the operational attributes of a Topology 
      component."
::= { aRtgPnniTop 10 }

aRtgPnniTopOperEntry OBJECT-TYPE
   SYNTAX     ARtgPnniTopOperEntry
   ACCESS     not-accessible
   STATUS     mandatory
   DESCRIPTION
     "An entry in the aRtgPnniTopOperTable."
   INDEX {
      aRtgIndex,
      aRtgPnniIndex,
      aRtgPnniTopIndex }
::= { aRtgPnniTopOperTable 1 }

ARtgPnniTopOperEntry ::= SEQUENCE {
   aRtgPnniTopPtsesInDatabase
      Gauge32,
   aRtgPnniTopPglNodeId
      HexString,
   aRtgPnniTopActiveParentNodeId
      HexString,
   aRtgPnniTopPreferredPglNodeId
      HexString }

aRtgPnniTopPtsesInDatabase OBJECT-TYPE
   SYNTAX     Gauge32 (0..4294967295)
   ACCESS     read-only
   STATUS     mandatory
   DESCRIPTION
     "This attribute indicates the number of PTSEs in storage in this 
      node's topology database for this level."
::= { aRtgPnniTopOperEntry 1 }

aRtgPnniTopPglNodeId OBJECT-TYPE
   SYNTAX     HexString (SIZE (0..22))
   ACCESS     read-only
   STATUS     mandatory
   DESCRIPTION
     "This attribute indicates the node id of the peer group leader. If this 
      attribute is empty, it indicates the Peer Group Level node id is 
      unknown."
::= { aRtgPnniTopOperEntry 2 }

aRtgPnniTopActiveParentNodeId OBJECT-TYPE
   SYNTAX     HexString (SIZE (0..22))
   ACCESS     read-only
   STATUS     mandatory
   DESCRIPTION
     "This attribute indicates the node identifier being used by the LGN 
      representing this peer group at the next higher level peer group."
::= { aRtgPnniTopOperEntry 3 }

aRtgPnniTopPreferredPglNodeId OBJECT-TYPE
   SYNTAX     HexString (SIZE (0..22))
   ACCESS     read-only
   STATUS     mandatory
   DESCRIPTION
     "This attribute represents the node in database with the highest Peer 
      Group Level (PGL) priority. If this attribute is empty, it indicates 
      the preferred PGL node id is unknown."
::= { aRtgPnniTopOperEntry 4 }

-- 
-- *** THIS SUBTREE CURRENTLY NOT IMPLEMENTED ***
-- 

-- ARtg Pnni Top/<level> Node/<node id>
-- This component represents the nodal information stored in this 
-- node's topology database.
-- 
-- The reachable ATM end system addresses (both interior and 
-- exterior reachable addresses) advertised by the node can be listed 
-- through the Addr subcomponent instances.
-- 
-- All advertised links associated with the node can be listed through 
-- the Link subcomponent instances which are indexed by their port id.

aRtgPnniTopNode OBJECT IDENTIFIER ::= { aRtgPnniTop 2 }



aRtgPnniTopNodeRowStatusTable OBJECT-TYPE
   SYNTAX     SEQUENCE OF ARtgPnniTopNodeRowStatusEntry
   ACCESS     not-accessible
   STATUS     mandatory
   DESCRIPTION
     "*** THIS TABLE CURRENTLY NOT IMPLEMENTED ***

      This entry controls the addition and deletion of 
      aRtgPnniTopNode components."
::= { aRtgPnniTopNode 1 }

aRtgPnniTopNodeRowStatusEntry OBJECT-TYPE
   SYNTAX     ARtgPnniTopNodeRowStatusEntry
   ACCESS     not-accessible
   STATUS     mandatory
   DESCRIPTION
     "A single entry in the table represents a single 
      aRtgPnniTopNode component."
   INDEX {
      aRtgIndex,
      aRtgPnniIndex,
      aRtgPnniTopIndex,
      aRtgPnniTopNodeIndex }
::= { aRtgPnniTopNodeRowStatusTable 1 }

ARtgPnniTopNodeRowStatusEntry ::= SEQUENCE {
   aRtgPnniTopNodeRowStatus
      RowStatus,
   aRtgPnniTopNodeComponentName
      DisplayString,
   aRtgPnniTopNodeStorageType
      StorageType,
   aRtgPnniTopNodeIndex
      HexString }

aRtgPnniTopNodeRowStatus OBJECT-TYPE
   SYNTAX     RowStatus 
   ACCESS     read-only
   STATUS     mandatory
   DESCRIPTION
     "This variable is used as the basis for SNMP naming of
      aRtgPnniTopNode components.
      These components cannot be added nor deleted."
::= { aRtgPnniTopNodeRowStatusEntry 1 }

aRtgPnniTopNodeComponentName OBJECT-TYPE
   SYNTAX     DisplayString 
   ACCESS     read-only
   STATUS     mandatory
   DESCRIPTION
     "This variable provides the component's string name for
      use with the ASCII Console Interface"
::= { aRtgPnniTopNodeRowStatusEntry 2 }

aRtgPnniTopNodeStorageType OBJECT-TYPE
   SYNTAX     StorageType 
   ACCESS     read-only
   STATUS     mandatory
   DESCRIPTION
     "This variable represents the storage type value for the
      aRtgPnniTopNode tables."
::= { aRtgPnniTopNodeRowStatusEntry 4 }

aRtgPnniTopNodeIndex OBJECT-TYPE
   SYNTAX     HexString (SIZE (22))
   ACCESS     not-accessible
   STATUS     mandatory
   DESCRIPTION
     "This variable represents the index for the aRtgPnniTopNode tables."
::= { aRtgPnniTopNodeRowStatusEntry 10 }

-- 
-- *** THIS SUBTREE CURRENTLY NOT IMPLEMENTED ***
-- 

-- ARtg Pnni Top Node/<node id> Address/<address>, 
-- <prefixLength>, <reachability>
-- This component represents an address advertised by the parent 
-- node. The instance value is a 38 hex digit string. 
-- 
-- The prefixLength specifies the number of significant bits in the 
-- address. 
-- 
-- The reachability specifies whether the address is internal or 
-- exterior.
-- An internal reachable address is an address of a destination that is 
-- directly attached to the logical node advertising the address. An 
-- exterior reachable address is an address that can be reached 
-- through a PNNI routing domain, but which is not located in that 
-- PNNI routing domain.

aRtgPnniTopNodeAddr OBJECT IDENTIFIER ::= { aRtgPnniTopNode 2 }



aRtgPnniTopNodeAddrRowStatusTable OBJECT-TYPE
   SYNTAX     SEQUENCE OF ARtgPnniTopNodeAddrRowStatusEntry
   ACCESS     not-accessible
   STATUS     mandatory
   DESCRIPTION
     "*** THIS TABLE CURRENTLY NOT IMPLEMENTED ***

      This entry controls the addition and deletion of 
      aRtgPnniTopNodeAddr components."
::= { aRtgPnniTopNodeAddr 1 }

aRtgPnniTopNodeAddrRowStatusEntry OBJECT-TYPE
   SYNTAX     ARtgPnniTopNodeAddrRowStatusEntry
   ACCESS     not-accessible
   STATUS     mandatory
   DESCRIPTION
     "A single entry in the table represents a single 
      aRtgPnniTopNodeAddr component."
   INDEX {
      aRtgIndex,
      aRtgPnniIndex,
      aRtgPnniTopIndex,
      aRtgPnniTopNodeIndex,
      aRtgPnniTopNodeAddrAddressIndex,
      aRtgPnniTopNodeAddrPrefixLengthIndex,
      aRtgPnniTopNodeAddrReachabilityIndex }
::= { aRtgPnniTopNodeAddrRowStatusTable 1 }

ARtgPnniTopNodeAddrRowStatusEntry ::= SEQUENCE {
   aRtgPnniTopNodeAddrRowStatus
      RowStatus,
   aRtgPnniTopNodeAddrComponentName
      DisplayString,
   aRtgPnniTopNodeAddrStorageType
      StorageType,
   aRtgPnniTopNodeAddrAddressIndex
      HexString,
   aRtgPnniTopNodeAddrPrefixLengthIndex
      Integer32,
   aRtgPnniTopNodeAddrReachabilityIndex
      INTEGER }

aRtgPnniTopNodeAddrRowStatus OBJECT-TYPE
   SYNTAX     RowStatus 
   ACCESS     read-only
   STATUS     mandatory
   DESCRIPTION
     "This variable is used as the basis for SNMP naming of
      aRtgPnniTopNodeAddr components.
      These components cannot be added nor deleted."
::= { aRtgPnniTopNodeAddrRowStatusEntry 1 }

aRtgPnniTopNodeAddrComponentName OBJECT-TYPE
   SYNTAX     DisplayString 
   ACCESS     read-only
   STATUS     mandatory
   DESCRIPTION
     "This variable provides the component's string name for
      use with the ASCII Console Interface"
::= { aRtgPnniTopNodeAddrRowStatusEntry 2 }

aRtgPnniTopNodeAddrStorageType OBJECT-TYPE
   SYNTAX     StorageType 
   ACCESS     read-only
   STATUS     mandatory
   DESCRIPTION
     "This variable represents the storage type value for the
      aRtgPnniTopNodeAddr tables."
::= { aRtgPnniTopNodeAddrRowStatusEntry 4 }

aRtgPnniTopNodeAddrAddressIndex OBJECT-TYPE
   SYNTAX     HexString (SIZE (19))
   ACCESS     not-accessible
   STATUS     mandatory
   DESCRIPTION
     "This variable represents an index for the aRtgPnniTopNodeAddr tables."
::= { aRtgPnniTopNodeAddrRowStatusEntry 10 }

aRtgPnniTopNodeAddrPrefixLengthIndex OBJECT-TYPE
   SYNTAX     Integer32 (1..152)
   ACCESS     not-accessible
   STATUS     mandatory
   DESCRIPTION
     "This variable represents an index for the aRtgPnniTopNodeAddr tables."
::= { aRtgPnniTopNodeAddrRowStatusEntry 11 }

aRtgPnniTopNodeAddrReachabilityIndex OBJECT-TYPE
   SYNTAX     INTEGER  {
                 internal(0),
                 exterior(1) }
   ACCESS     not-accessible
   STATUS     mandatory
   DESCRIPTION
     "This variable represents an index for the aRtgPnniTopNodeAddr tables."
::= { aRtgPnniTopNodeAddrRowStatusEntry 12 }

aRtgPnniTopNodeAddrOperTable OBJECT-TYPE
   SYNTAX     SEQUENCE OF ARtgPnniTopNodeAddrOperEntry
   ACCESS     not-accessible
   STATUS     mandatory
   DESCRIPTION
     "*** THIS TABLE CURRENTLY NOT IMPLEMENTED ***

      This attribute group contains the operational attributes for the 
      Address component."
::= { aRtgPnniTopNodeAddr 10 }

aRtgPnniTopNodeAddrOperEntry OBJECT-TYPE
   SYNTAX     ARtgPnniTopNodeAddrOperEntry
   ACCESS     not-accessible
   STATUS     mandatory
   DESCRIPTION
     "An entry in the aRtgPnniTopNodeAddrOperTable."
   INDEX {
      aRtgIndex,
      aRtgPnniIndex,
      aRtgPnniTopIndex,
      aRtgPnniTopNodeIndex,
      aRtgPnniTopNodeAddrAddressIndex,
      aRtgPnniTopNodeAddrPrefixLengthIndex,
      aRtgPnniTopNodeAddrReachabilityIndex }
::= { aRtgPnniTopNodeAddrOperTable 1 }

ARtgPnniTopNodeAddrOperEntry ::= SEQUENCE {
   aRtgPnniTopNodeAddrScope
      Unsigned32 }

aRtgPnniTopNodeAddrScope OBJECT-TYPE
   SYNTAX     Unsigned32 (0..104)
   ACCESS     read-only
   STATUS     mandatory
   DESCRIPTION
     "This attribute specifies the scope of the ATM address, which is the 
      highest level to which this address will be advertised in the PNNI 
      hierarchy."
::= { aRtgPnniTopNodeAddrOperEntry 1 }

-- 
-- *** THIS SUBTREE CURRENTLY NOT IMPLEMENTED ***
-- 

-- ARtg Pnni Top/<level> Node/<node id> Link/<port id>
-- This component represents the link information stored in this node's 
-- topology database.
-- 
-- All advertised links associated with the node can be listed through 
-- the Link subcomponent instances which are indexed by their port id.

aRtgPnniTopNodeLink OBJECT IDENTIFIER ::= { aRtgPnniTopNode 3 }



aRtgPnniTopNodeLinkRowStatusTable OBJECT-TYPE
   SYNTAX     SEQUENCE OF ARtgPnniTopNodeLinkRowStatusEntry
   ACCESS     not-accessible
   STATUS     mandatory
   DESCRIPTION
     "*** THIS TABLE CURRENTLY NOT IMPLEMENTED ***

      This entry controls the addition and deletion of 
      aRtgPnniTopNodeLink components."
::= { aRtgPnniTopNodeLink 1 }

aRtgPnniTopNodeLinkRowStatusEntry OBJECT-TYPE
   SYNTAX     ARtgPnniTopNodeLinkRowStatusEntry
   ACCESS     not-accessible
   STATUS     mandatory
   DESCRIPTION
     "A single entry in the table represents a single 
      aRtgPnniTopNodeLink component."
   INDEX {
      aRtgIndex,
      aRtgPnniIndex,
      aRtgPnniTopIndex,
      aRtgPnniTopNodeIndex,
      aRtgPnniTopNodeLinkIndex }
::= { aRtgPnniTopNodeLinkRowStatusTable 1 }

ARtgPnniTopNodeLinkRowStatusEntry ::= SEQUENCE {
   aRtgPnniTopNodeLinkRowStatus
      RowStatus,
   aRtgPnniTopNodeLinkComponentName
      DisplayString,
   aRtgPnniTopNodeLinkStorageType
      StorageType,
   aRtgPnniTopNodeLinkIndex
      Integer32 }

aRtgPnniTopNodeLinkRowStatus OBJECT-TYPE
   SYNTAX     RowStatus 
   ACCESS     read-only
   STATUS     mandatory
   DESCRIPTION
     "This variable is used as the basis for SNMP naming of
      aRtgPnniTopNodeLink components.
      These components cannot be added nor deleted."
::= { aRtgPnniTopNodeLinkRowStatusEntry 1 }

aRtgPnniTopNodeLinkComponentName OBJECT-TYPE
   SYNTAX     DisplayString 
   ACCESS     read-only
   STATUS     mandatory
   DESCRIPTION
     "This variable provides the component's string name for
      use with the ASCII Console Interface"
::= { aRtgPnniTopNodeLinkRowStatusEntry 2 }

aRtgPnniTopNodeLinkStorageType OBJECT-TYPE
   SYNTAX     StorageType 
   ACCESS     read-only
   STATUS     mandatory
   DESCRIPTION
     "This variable represents the storage type value for the
      aRtgPnniTopNodeLink tables."
::= { aRtgPnniTopNodeLinkRowStatusEntry 4 }

aRtgPnniTopNodeLinkIndex OBJECT-TYPE
   SYNTAX     Integer32 (0..268435455)
   ACCESS     not-accessible
   STATUS     mandatory
   DESCRIPTION
     "This variable represents the index for the aRtgPnniTopNodeLink tables."
::= { aRtgPnniTopNodeLinkRowStatusEntry 10 }

aRtgPnniTopNodeLinkOperTable OBJECT-TYPE
   SYNTAX     SEQUENCE OF ARtgPnniTopNodeLinkOperEntry
   ACCESS     not-accessible
   STATUS     mandatory
   DESCRIPTION
     "*** THIS TABLE CURRENTLY NOT IMPLEMENTED ***

      This group contains the operational attributes of a Link component."
::= { aRtgPnniTopNodeLink 10 }

aRtgPnniTopNodeLinkOperEntry OBJECT-TYPE
   SYNTAX     ARtgPnniTopNodeLinkOperEntry
   ACCESS     not-accessible
   STATUS     mandatory
   DESCRIPTION
     "An entry in the aRtgPnniTopNodeLinkOperTable."
   INDEX {
      aRtgIndex,
      aRtgPnniIndex,
      aRtgPnniTopIndex,
      aRtgPnniTopNodeIndex,
      aRtgPnniTopNodeLinkIndex }
::= { aRtgPnniTopNodeLinkOperTable 1 }

ARtgPnniTopNodeLinkOperEntry ::= SEQUENCE {
   aRtgPnniTopNodeLinkRemoteNodeId
      HexString,
   aRtgPnniTopNodeLinkRemotePortId
      Unsigned32 }

aRtgPnniTopNodeLinkRemoteNodeId OBJECT-TYPE
   SYNTAX     HexString (SIZE (22))
   ACCESS     read-only
   STATUS     mandatory
   DESCRIPTION
     "This attribute indicates the id of the node at the far end of this link."
::= { aRtgPnniTopNodeLinkOperEntry 1 }

aRtgPnniTopNodeLinkRemotePortId OBJECT-TYPE
   SYNTAX     Unsigned32 (0..4294967295)
   ACCESS     read-only
   STATUS     mandatory
   DESCRIPTION
     "This attribute indicates the node's port id at the far end of this link."
::= { aRtgPnniTopNodeLinkOperEntry 2 }

-- 
-- *** THIS SUBTREE CURRENTLY NOT IMPLEMENTED ***
-- 

-- ARtg Pnni Port/<n>
-- This component represents a port advertised within the PNNI 
-- routing domain.

aRtgPnniPort OBJECT IDENTIFIER ::= { aRtgPnni 5 }



aRtgPnniPortRowStatusTable OBJECT-TYPE
   SYNTAX     SEQUENCE OF ARtgPnniPortRowStatusEntry
   ACCESS     not-accessible
   STATUS     mandatory
   DESCRIPTION
     "*** THIS TABLE CURRENTLY NOT IMPLEMENTED ***

      This entry controls the addition and deletion of 
      aRtgPnniPort components."
::= { aRtgPnniPort 1 }

aRtgPnniPortRowStatusEntry OBJECT-TYPE
   SYNTAX     ARtgPnniPortRowStatusEntry
   ACCESS     not-accessible
   STATUS     mandatory
   DESCRIPTION
     "A single entry in the table represents a single 
      aRtgPnniPort component."
   INDEX {
      aRtgIndex,
      aRtgPnniIndex,
      aRtgPnniPortIndex }
::= { aRtgPnniPortRowStatusTable 1 }

ARtgPnniPortRowStatusEntry ::= SEQUENCE {
   aRtgPnniPortRowStatus
      RowStatus,
   aRtgPnniPortComponentName
      DisplayString,
   aRtgPnniPortStorageType
      StorageType,
   aRtgPnniPortIndex
      Integer32 }

aRtgPnniPortRowStatus OBJECT-TYPE
   SYNTAX     RowStatus 
   ACCESS     read-only
   STATUS     mandatory
   DESCRIPTION
     "This variable is used as the basis for SNMP naming of
      aRtgPnniPort components.
      These components cannot be added nor deleted."
::= { aRtgPnniPortRowStatusEntry 1 }

aRtgPnniPortComponentName OBJECT-TYPE
   SYNTAX     DisplayString 
   ACCESS     read-only
   STATUS     mandatory
   DESCRIPTION
     "This variable provides the component's string name for
      use with the ASCII Console Interface"
::= { aRtgPnniPortRowStatusEntry 2 }

aRtgPnniPortStorageType OBJECT-TYPE
   SYNTAX     StorageType 
   ACCESS     read-only
   STATUS     mandatory
   DESCRIPTION
     "This variable represents the storage type value for the
      aRtgPnniPort tables."
::= { aRtgPnniPortRowStatusEntry 4 }

aRtgPnniPortIndex OBJECT-TYPE
   SYNTAX     Integer32 (0..268435455)
   ACCESS     not-accessible
   STATUS     mandatory
   DESCRIPTION
     "This variable represents the index for the aRtgPnniPort tables."
::= { aRtgPnniPortRowStatusEntry 10 }

aRtgPnniPortOperTable OBJECT-TYPE
   SYNTAX     SEQUENCE OF ARtgPnniPortOperEntry
   ACCESS     not-accessible
   STATUS     mandatory
   DESCRIPTION
     "*** THIS TABLE CURRENTLY NOT IMPLEMENTED ***

      This group contains the operational attributes of a Port component."
::= { aRtgPnniPort 10 }

aRtgPnniPortOperEntry OBJECT-TYPE
   SYNTAX     ARtgPnniPortOperEntry
   ACCESS     not-accessible
   STATUS     mandatory
   DESCRIPTION
     "An entry in the aRtgPnniPortOperTable."
   INDEX {
      aRtgIndex,
      aRtgPnniIndex,
      aRtgPnniPortIndex }
::= { aRtgPnniPortOperTable 1 }

ARtgPnniPortOperEntry ::= SEQUENCE {
   aRtgPnniPortStdComponentName
      RowPointer }

aRtgPnniPortStdComponentName OBJECT-TYPE
   SYNTAX     RowPointer 
   ACCESS     read-only
   STATUS     mandatory
   DESCRIPTION
     "This attribute indicates the component name of the port."
::= { aRtgPnniPortOperEntry 1 }


-- AtmCallRouter
-- This component represents the database that contains all the static 
-- (provisioned) DNAs and dynamically registered DNAs (via ILMI) 
-- used for source call routing for ATM switched connection setups..

atmCR OBJECT IDENTIFIER ::= { components 113 }



atmCRRowStatusTable OBJECT-TYPE
   SYNTAX     SEQUENCE OF AtmCRRowStatusEntry
   ACCESS     not-accessible
   STATUS     mandatory
   DESCRIPTION
     "This entry controls the addition and deletion of 
      atmCR components."
::= { atmCR 1 }

atmCRRowStatusEntry OBJECT-TYPE
   SYNTAX     AtmCRRowStatusEntry
   ACCESS     not-accessible
   STATUS     mandatory
   DESCRIPTION
     "A single entry in the table represents a single 
      atmCR component."
   INDEX {
      atmCRIndex }
::= { atmCRRowStatusTable 1 }

AtmCRRowStatusEntry ::= SEQUENCE {
   atmCRRowStatus
      RowStatus,
   atmCRComponentName
      DisplayString,
   atmCRStorageType
      StorageType,
   atmCRIndex
      NonReplicated }

atmCRRowStatus OBJECT-TYPE
   SYNTAX     RowStatus 
   ACCESS     read-write
   STATUS     mandatory
   DESCRIPTION
     "This variable is used as the basis for SNMP naming of
      atmCR components.
      These components can be added and deleted."
::= { atmCRRowStatusEntry 1 }

atmCRComponentName OBJECT-TYPE
   SYNTAX     DisplayString 
   ACCESS     read-only
   STATUS     mandatory
   DESCRIPTION
     "This variable provides the component's string name for
      use with the ASCII Console Interface"
::= { atmCRRowStatusEntry 2 }

atmCRStorageType OBJECT-TYPE
   SYNTAX     StorageType 
   ACCESS     read-only
   STATUS     mandatory
   DESCRIPTION
     "This variable represents the storage type value for the
      atmCR tables."
::= { atmCRRowStatusEntry 4 }

atmCRIndex OBJECT-TYPE
   SYNTAX     NonReplicated 
   ACCESS     not-accessible
   STATUS     mandatory
   DESCRIPTION
     "This variable represents the index for the atmCR tables."
::= { atmCRRowStatusEntry 10 }

atmCRProvTable OBJECT-TYPE
   SYNTAX     SEQUENCE OF AtmCRProvEntry
   ACCESS     not-accessible
   STATUS     mandatory
   DESCRIPTION
     "This group represents the provisioned attributes for the 
      AtmCallRouter component."
::= { atmCR 10 }

atmCRProvEntry OBJECT-TYPE
   SYNTAX     AtmCRProvEntry
   ACCESS     not-accessible
   STATUS     mandatory
   DESCRIPTION
     "An entry in the atmCRProvTable."
   INDEX {
      atmCRIndex }
::= { atmCRProvTable 1 }

AtmCRProvEntry ::= SEQUENCE {
   atmCRNodeAddress
      AsciiString }

atmCRNodeAddress OBJECT-TYPE
   SYNTAX     AsciiString (SIZE (26))
   ACCESS     read-write
   STATUS     obsolete
   DESCRIPTION
     "This attribute specifies the NSAP address prefix used for ILMI 
      purposes."
::= { atmCRProvEntry 1 }

atmCRStatsTable OBJECT-TYPE
   SYNTAX     SEQUENCE OF AtmCRStatsEntry
   ACCESS     not-accessible
   STATUS     obsolete
   DESCRIPTION
     "This group represents the operational attributes for the 
      AtmCallRouter component."
::= { atmCR 11 }

atmCRStatsEntry OBJECT-TYPE
   SYNTAX     AtmCRStatsEntry
   ACCESS     not-accessible
   STATUS     obsolete
   DESCRIPTION
     "An entry in the atmCRStatsTable."
   INDEX {
      atmCRIndex }
::= { atmCRStatsTable 1 }

AtmCRStatsEntry ::= SEQUENCE {
   atmCRCallsRouted
      Counter32,
   atmCRCallsFailed
      Counter32 }

atmCRCallsRouted OBJECT-TYPE
   SYNTAX     Counter32 
   ACCESS     read-only
   STATUS     obsolete
   DESCRIPTION
     "This attribute counts the total number of calls routed."
::= { atmCRStatsEntry 1 }

atmCRCallsFailed OBJECT-TYPE
   SYNTAX     Counter32 
   ACCESS     read-only
   STATUS     obsolete
   DESCRIPTION
     "This attribute specifies the number of calls that failed to route."
::= { atmCRStatsEntry 2 }

-- 
-- *** THIS SUBTREE CURRENTLY NOT IMPLEMENTED ***
-- 

-- AtmCallRouter AtmDna/<STRING(1..40)>
-- This component represents an ATM NSAP address that has been 
-- provisioned or dynamically registered via ILMI.

atmCRDna OBJECT IDENTIFIER ::= { atmCR 2 }



atmCRDnaRowStatusTable OBJECT-TYPE
   SYNTAX     SEQUENCE OF AtmCRDnaRowStatusEntry
   ACCESS     not-accessible
   STATUS     mandatory
   DESCRIPTION
     "*** THIS TABLE CURRENTLY NOT IMPLEMENTED ***

      This entry controls the addition and deletion of 
      atmCRDna components."
::= { atmCRDna 1 }

atmCRDnaRowStatusEntry OBJECT-TYPE
   SYNTAX     AtmCRDnaRowStatusEntry
   ACCESS     not-accessible
   STATUS     mandatory
   DESCRIPTION
     "A single entry in the table represents a single 
      atmCRDna component."
   INDEX {
      atmCRIndex,
      atmCRDnaIndex }
::= { atmCRDnaRowStatusTable 1 }

AtmCRDnaRowStatusEntry ::= SEQUENCE {
   atmCRDnaRowStatus
      RowStatus,
   atmCRDnaComponentName
      DisplayString,
   atmCRDnaStorageType
      StorageType,
   atmCRDnaIndex
      AsciiStringIndex }

atmCRDnaRowStatus OBJECT-TYPE
   SYNTAX     RowStatus 
   ACCESS     read-only
   STATUS     mandatory
   DESCRIPTION
     "This variable is used as the basis for SNMP naming of
      atmCRDna components.
      These components cannot be added nor deleted."
::= { atmCRDnaRowStatusEntry 1 }

atmCRDnaComponentName OBJECT-TYPE
   SYNTAX     DisplayString 
   ACCESS     read-only
   STATUS     mandatory
   DESCRIPTION
     "This variable provides the component's string name for
      use with the ASCII Console Interface"
::= { atmCRDnaRowStatusEntry 2 }

atmCRDnaStorageType OBJECT-TYPE
   SYNTAX     StorageType 
   ACCESS     read-only
   STATUS     mandatory
   DESCRIPTION
     "This variable represents the storage type value for the
      atmCRDna tables."
::= { atmCRDnaRowStatusEntry 4 }

atmCRDnaIndex OBJECT-TYPE
   SYNTAX     AsciiStringIndex (SIZE (1..40))
   ACCESS     not-accessible
   STATUS     mandatory
   DESCRIPTION
     "This variable represents the index for the atmCRDna tables."
::= { atmCRDnaRowStatusEntry 10 }

atmCRDnaDestinationNameTable OBJECT-TYPE
   SYNTAX     SEQUENCE OF AtmCRDnaDestinationNameEntry
   ACCESS     not-accessible
   STATUS     obsolete
   DESCRIPTION
     "*** THIS TABLE CURRENTLY NOT IMPLEMENTED ***

      This attribute indicates which components have this address 
      provisioned or dynamically registered via ILMI."
::= { atmCRDna 289 }

atmCRDnaDestinationNameEntry OBJECT-TYPE
   SYNTAX     AtmCRDnaDestinationNameEntry
   ACCESS     not-accessible
   STATUS     obsolete
   DESCRIPTION
     "An entry in the atmCRDnaDestinationNameTable."
   INDEX {
      atmCRIndex,
      atmCRDnaIndex,
      atmCRDnaDestinationNameValue }
::= { atmCRDnaDestinationNameTable 1 }

AtmCRDnaDestinationNameEntry ::= SEQUENCE {
   atmCRDnaDestinationNameValue
      RowPointer }

atmCRDnaDestinationNameValue OBJECT-TYPE
   SYNTAX     RowPointer 
   ACCESS     read-only
   STATUS     obsolete
   DESCRIPTION
     "This variable represents both the value and the index for the
      atmCRDnaDestinationNameTable."
::= { atmCRDnaDestinationNameEntry 1 }


-- AtmIf/n Vpc/vpi SourcePvp
-- This component represents the source end of a soft PVP.

atmIfVpcSrc OBJECT IDENTIFIER ::= { atmIfVpc 6 }



atmIfVpcSrcRowStatusTable OBJECT-TYPE
   SYNTAX     SEQUENCE OF AtmIfVpcSrcRowStatusEntry
   ACCESS     not-accessible
   STATUS     mandatory
   DESCRIPTION
     "This entry controls the addition and deletion of 
      atmIfVpcSrc components."
::= { atmIfVpcSrc 1 }

atmIfVpcSrcRowStatusEntry OBJECT-TYPE
   SYNTAX     AtmIfVpcSrcRowStatusEntry
   ACCESS     not-accessible
   STATUS     mandatory
   DESCRIPTION
     "A single entry in the table represents a single 
      atmIfVpcSrc component."
   INDEX {
      atmIfIndex,
      atmIfVpcIndex,
      atmIfVpcSrcIndex }
::= { atmIfVpcSrcRowStatusTable 1 }

AtmIfVpcSrcRowStatusEntry ::= SEQUENCE {
   atmIfVpcSrcRowStatus
      RowStatus,
   atmIfVpcSrcComponentName
      DisplayString,
   atmIfVpcSrcStorageType
      StorageType,
   atmIfVpcSrcIndex
      NonReplicated }

atmIfVpcSrcRowStatus OBJECT-TYPE
   SYNTAX     RowStatus 
   ACCESS     read-write
   STATUS     mandatory
   DESCRIPTION
     "This variable is used as the basis for SNMP naming of
      atmIfVpcSrc components.
      These components can be added and deleted."
::= { atmIfVpcSrcRowStatusEntry 1 }

atmIfVpcSrcComponentName OBJECT-TYPE
   SYNTAX     DisplayString 
   ACCESS     read-only
   STATUS     mandatory
   DESCRIPTION
     "This variable provides the component's string name for
      use with the ASCII Console Interface"
::= { atmIfVpcSrcRowStatusEntry 2 }

atmIfVpcSrcStorageType OBJECT-TYPE
   SYNTAX     StorageType 
   ACCESS     read-only
   STATUS     mandatory
   DESCRIPTION
     "This variable represents the storage type value for the
      atmIfVpcSrc tables."
::= { atmIfVpcSrcRowStatusEntry 4 }

atmIfVpcSrcIndex OBJECT-TYPE
   SYNTAX     NonReplicated 
   ACCESS     not-accessible
   STATUS     mandatory
   DESCRIPTION
     "This variable represents the index for the atmIfVpcSrc tables."
::= { atmIfVpcSrcRowStatusEntry 10 }

atmIfVpcSrcProvTable OBJECT-TYPE
   SYNTAX     SEQUENCE OF AtmIfVpcSrcProvEntry
   ACCESS     not-accessible
   STATUS     mandatory
   DESCRIPTION
     "This attribute group contains the provisionable attributes of the 
      AtmIf/n Vpc/vpi SrcPvp component."
::= { atmIfVpcSrc 10 }

atmIfVpcSrcProvEntry OBJECT-TYPE
   SYNTAX     AtmIfVpcSrcProvEntry
   ACCESS     not-accessible
   STATUS     mandatory
   DESCRIPTION
     "An entry in the atmIfVpcSrcProvTable."
   INDEX {
      atmIfIndex,
      atmIfVpcIndex,
      atmIfVpcSrcIndex }
::= { atmIfVpcSrcProvTable 1 }

AtmIfVpcSrcProvEntry ::= SEQUENCE {
   atmIfVpcSrcCallingAddress
      HexString,
   atmIfVpcSrcCalledAddress
      HexString,
   atmIfVpcSrcCalledVpi
      Unsigned32 }

atmIfVpcSrcCallingAddress OBJECT-TYPE
   SYNTAX     HexString (SIZE (0..20))
   ACCESS     read-write
   STATUS     mandatory
   DESCRIPTION
     "This attribute specifies the calling address of the soft PVP. If it is a 
      null string, then the calling address is the address of the current 
      interface (that is, where the soft PVC originates)."
   DEFVAL     { ''H }  -- ""
::= { atmIfVpcSrcProvEntry 1 }

atmIfVpcSrcCalledAddress OBJECT-TYPE
   SYNTAX     HexString (SIZE (20))
   ACCESS     read-write
   STATUS     mandatory
   DESCRIPTION
     "This attribute specifies the called (remote) address of the soft PVP."
::= { atmIfVpcSrcProvEntry 2 }

atmIfVpcSrcCalledVpi OBJECT-TYPE
   SYNTAX     Unsigned32 (1..4095)
   ACCESS     read-write
   STATUS     mandatory
   DESCRIPTION
     "This attribute specifies the called VPI of the soft PVP."
::= { atmIfVpcSrcProvEntry 3 }

atmIfVpcSrcOperTable OBJECT-TYPE
   SYNTAX     SEQUENCE OF AtmIfVpcSrcOperEntry
   ACCESS     not-accessible
   STATUS     mandatory
   DESCRIPTION
     "This attribute group contains the operational attributes associated 
      with the SrcPvp or SrcPvc component."
::= { atmIfVpcSrc 11 }

atmIfVpcSrcOperEntry OBJECT-TYPE
   SYNTAX     AtmIfVpcSrcOperEntry
   ACCESS     not-accessible
   STATUS     mandatory
   DESCRIPTION
     "An entry in the atmIfVpcSrcOperTable."
   INDEX {
      atmIfIndex,
      atmIfVpcIndex,
      atmIfVpcSrcIndex }
::= { atmIfVpcSrcOperTable 1 }

AtmIfVpcSrcOperEntry ::= SEQUENCE {
   atmIfVpcSrcState
      INTEGER,
   atmIfVpcSrcRetryCount
      Counter32,
   atmIfVpcSrcLastFailureCauseCode
      Unsigned32,
   atmIfVpcSrcLastFailureDiagCode
      AsciiString }

atmIfVpcSrcState OBJECT-TYPE
   SYNTAX     INTEGER  {
                 active(0),
                 inactive(1) }
   ACCESS     read-only
   STATUS     mandatory
   DESCRIPTION
     "This attribute indicates the state of the soft PVP or soft PVC."
::= { atmIfVpcSrcOperEntry 1 }

atmIfVpcSrcRetryCount OBJECT-TYPE
   SYNTAX     Counter32 
   ACCESS     read-only
   STATUS     mandatory
   DESCRIPTION
     "This attribute indicates the number of failed attempts to set up the 
      soft PVP or soft PVC since the last time the connection failed."
::= { atmIfVpcSrcOperEntry 2 }

atmIfVpcSrcLastFailureCauseCode OBJECT-TYPE
   SYNTAX     Unsigned32 (0..255)
   ACCESS     read-only
   STATUS     mandatory
   DESCRIPTION
     "This attribute contains the cause code in the last transmitted 
      signalling message that contains the CAUSE information element. 
      The cause code is used to describe the reason for generating certain 
      signalling messages. 
      The default value for this attribute is set to 0."
::= { atmIfVpcSrcOperEntry 3 }

atmIfVpcSrcLastFailureDiagCode OBJECT-TYPE
   SYNTAX     AsciiString (SIZE (0..8))
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to NULL."
::= { atmIfVpcSrcOperEntry 4 }


-- AtmIf/n Vpc/vpi Rp
-- AtmIf/n Vcc/vpi.vci Rp
-- AtmIf/n Vpt/vpi Vcc/vci Rp
-- 
-- The RelayPoint component is used to establish a single hop of a 
-- Switched connection. When linked together, two Rps within a 
-- module, the associated connections are configured to relay ATM 
-- cells to one another. 

atmIfVpcRp OBJECT IDENTIFIER ::= { atmIfVpc 7 }



atmIfVpcRpRowStatusTable OBJECT-TYPE
   SYNTAX     SEQUENCE OF AtmIfVpcRpRowStatusEntry
   ACCESS     not-accessible
   STATUS     mandatory
   DESCRIPTION
     "This entry controls the addition and deletion of 
      atmIfVpcRp components."
::= { atmIfVpcRp 1 }

atmIfVpcRpRowStatusEntry OBJECT-TYPE
   SYNTAX     AtmIfVpcRpRowStatusEntry
   ACCESS     not-accessible
   STATUS     mandatory
   DESCRIPTION
     "A single entry in the table represents a single 
      atmIfVpcRp component."
   INDEX {
      atmIfIndex,
      atmIfVpcIndex,
      atmIfVpcRpIndex }
::= { atmIfVpcRpRowStatusTable 1 }

AtmIfVpcRpRowStatusEntry ::= SEQUENCE {
   atmIfVpcRpRowStatus
      RowStatus,
   atmIfVpcRpComponentName
      DisplayString,
   atmIfVpcRpStorageType
      StorageType,
   atmIfVpcRpIndex
      NonReplicated }

atmIfVpcRpRowStatus OBJECT-TYPE
   SYNTAX     RowStatus 
   ACCESS     read-only
   STATUS     mandatory
   DESCRIPTION
     "This variable is used as the basis for SNMP naming of
      atmIfVpcRp components.
      These components cannot be added nor deleted."
::= { atmIfVpcRpRowStatusEntry 1 }

atmIfVpcRpComponentName OBJECT-TYPE
   SYNTAX     DisplayString 
   ACCESS     read-only
   STATUS     mandatory
   DESCRIPTION
     "This variable provides the component's string name for
      use with the ASCII Console Interface"
::= { atmIfVpcRpRowStatusEntry 2 }

atmIfVpcRpStorageType OBJECT-TYPE
   SYNTAX     StorageType 
   ACCESS     read-only
   STATUS     mandatory
   DESCRIPTION
     "This variable represents the storage type value for the
      atmIfVpcRp tables."
::= { atmIfVpcRpRowStatusEntry 4 }

atmIfVpcRpIndex OBJECT-TYPE
   SYNTAX     NonReplicated 
   ACCESS     not-accessible
   STATUS     mandatory
   DESCRIPTION
     "This variable represents the index for the atmIfVpcRp tables."
::= { atmIfVpcRpRowStatusEntry 10 }

atmIfVpcRpOperTable OBJECT-TYPE
   SYNTAX     SEQUENCE OF AtmIfVpcRpOperEntry
   ACCESS     not-accessible
   STATUS     mandatory
   DESCRIPTION
     "This attribute group contains the operational attributes for the 
      AtmRelayPoint component."
::= { atmIfVpcRp 10 }

atmIfVpcRpOperEntry OBJECT-TYPE
   SYNTAX     AtmIfVpcRpOperEntry
   ACCESS     not-accessible
   STATUS     mandatory
   DESCRIPTION
     "An entry in the atmIfVpcRpOperTable."
   INDEX {
      atmIfIndex,
      atmIfVpcIndex,
      atmIfVpcRpIndex }
::= { atmIfVpcRpOperTable 1 }

AtmIfVpcRpOperEntry ::= SEQUENCE {
   atmIfVpcRpNextHop
      RowPointer }

atmIfVpcRpNextHop OBJECT-TYPE
   SYNTAX     RowPointer 
   ACCESS     read-only
   STATUS     obsolete
   DESCRIPTION
     "This attribute indicates the component name of the Rp component 
      with which this Rp component is associated."
::= { atmIfVpcRpOperEntry 1 }

atmIfVpcRpNextHopsTable OBJECT-TYPE
   SYNTAX     SEQUENCE OF AtmIfVpcRpNextHopsEntry
   ACCESS     not-accessible
   STATUS     mandatory
   DESCRIPTION
     "This attribute indicates the component name(s) of the Rp 
      component(s) with which this Rp component is associated. This 
      attribute can have more than one component name only when the 
      Vcc distributionType is pointToMultipoint and the callDirection is 
      fromLink."
::= { atmIfVpcRp 430 }

atmIfVpcRpNextHopsEntry OBJECT-TYPE
   SYNTAX     AtmIfVpcRpNextHopsEntry
   ACCESS     not-accessible
   STATUS     mandatory
   DESCRIPTION
     "An entry in the atmIfVpcRpNextHopsTable."
   INDEX {
      atmIfIndex,
      atmIfVpcIndex,
      atmIfVpcRpIndex,
      atmIfVpcRpNextHopsValue }
::= { atmIfVpcRpNextHopsTable 1 }

AtmIfVpcRpNextHopsEntry ::= SEQUENCE {
   atmIfVpcRpNextHopsValue
      RowPointer }

atmIfVpcRpNextHopsValue OBJECT-TYPE
   SYNTAX     RowPointer 
   ACCESS     read-only
   STATUS     mandatory
   DESCRIPTION
     "This variable represents both the value and the index for the
      atmIfVpcRpNextHopsTable."
::= { atmIfVpcRpNextHopsEntry 1 }


-- AtmIf/n Vpc/vpi DestinationPvp
-- This component represents the destination end of a soft PVP.

atmIfVpcDst OBJECT IDENTIFIER ::= { atmIfVpc 8 }



atmIfVpcDstRowStatusTable OBJECT-TYPE
   SYNTAX     SEQUENCE OF AtmIfVpcDstRowStatusEntry
   ACCESS     not-accessible
   STATUS     mandatory
   DESCRIPTION
     "This entry controls the addition and deletion of 
      atmIfVpcDst components."
::= { atmIfVpcDst 1 }

atmIfVpcDstRowStatusEntry OBJECT-TYPE
   SYNTAX     AtmIfVpcDstRowStatusEntry
   ACCESS     not-accessible
   STATUS     mandatory
   DESCRIPTION
     "A single entry in the table represents a single 
      atmIfVpcDst component."
   INDEX {
      atmIfIndex,
      atmIfVpcIndex,
      atmIfVpcDstIndex }
::= { atmIfVpcDstRowStatusTable 1 }

AtmIfVpcDstRowStatusEntry ::= SEQUENCE {
   atmIfVpcDstRowStatus
      RowStatus,
   atmIfVpcDstComponentName
      DisplayString,
   atmIfVpcDstStorageType
      StorageType,
   atmIfVpcDstIndex
      NonReplicated }

atmIfVpcDstRowStatus OBJECT-TYPE
   SYNTAX     RowStatus 
   ACCESS     read-only
   STATUS     mandatory
   DESCRIPTION
     "This variable is used as the basis for SNMP naming of
      atmIfVpcDst components.
      These components cannot be added nor deleted."
::= { atmIfVpcDstRowStatusEntry 1 }

atmIfVpcDstComponentName OBJECT-TYPE
   SYNTAX     DisplayString 
   ACCESS     read-only
   STATUS     mandatory
   DESCRIPTION
     "This variable provides the component's string name for
      use with the ASCII Console Interface"
::= { atmIfVpcDstRowStatusEntry 2 }

atmIfVpcDstStorageType OBJECT-TYPE
   SYNTAX     StorageType 
   ACCESS     read-only
   STATUS     mandatory
   DESCRIPTION
     "This variable represents the storage type value for the
      atmIfVpcDst tables."
::= { atmIfVpcDstRowStatusEntry 4 }

atmIfVpcDstIndex OBJECT-TYPE
   SYNTAX     NonReplicated 
   ACCESS     not-accessible
   STATUS     mandatory
   DESCRIPTION
     "This variable represents the index for the atmIfVpcDst tables."
::= { atmIfVpcDstRowStatusEntry 10 }

atmIfVpcDstOperTable OBJECT-TYPE
   SYNTAX     SEQUENCE OF AtmIfVpcDstOperEntry
   ACCESS     not-accessible
   STATUS     mandatory
   DESCRIPTION
     "This attribute group contains the operational attributes for the 
      AtmIf/n Vpc/vpi DstPvp component."
::= { atmIfVpcDst 10 }

atmIfVpcDstOperEntry OBJECT-TYPE
   SYNTAX     AtmIfVpcDstOperEntry
   ACCESS     not-accessible
   STATUS     mandatory
   DESCRIPTION
     "An entry in the atmIfVpcDstOperTable."
   INDEX {
      atmIfIndex,
      atmIfVpcIndex,
      atmIfVpcDstIndex }
::= { atmIfVpcDstOperTable 1 }

AtmIfVpcDstOperEntry ::= SEQUENCE {
   atmIfVpcDstCalledAddress
      HexString,
   atmIfVpcDstCallingAddress
      AsciiString,
   atmIfVpcDstCallingVpi
      AsciiString }

atmIfVpcDstCalledAddress OBJECT-TYPE
   SYNTAX     HexString (SIZE (20))
   ACCESS     read-only
   STATUS     mandatory
   DESCRIPTION
     "This attribute indicates the called address of the soft PVP."
::= { atmIfVpcDstOperEntry 1 }

atmIfVpcDstCallingAddress OBJECT-TYPE
   SYNTAX     AsciiString (SIZE (7..40))
   ACCESS     read-only
   STATUS     mandatory
   DESCRIPTION
     "This attribute indicates the calling (remote) address of the soft PVP. 
      If the address in not known, then the value of this address is 
      Unknown."
::= { atmIfVpcDstOperEntry 2 }

atmIfVpcDstCallingVpi OBJECT-TYPE
   SYNTAX     AsciiString (SIZE (1..7))
   ACCESS     read-only
   STATUS     mandatory
   DESCRIPTION
     "This attribute represents the calling (remote) VPI of the soft PVP. If 
      the VPI value is not known, the attribute value is set to Unknown."
::= { atmIfVpcDstOperEntry 3 }


-- AtmIf/n Vcc/vpi.vci SrcPvc
-- AtmIf/n Vpt/vpi Vcc/vci SrcPvc
-- 
-- This component represents the source end of a soft PVC.

atmIfVccSrc OBJECT IDENTIFIER ::= { atmIfVcc 8 }



atmIfVccSrcRowStatusTable OBJECT-TYPE
   SYNTAX     SEQUENCE OF AtmIfVccSrcRowStatusEntry
   ACCESS     not-accessible
   STATUS     mandatory
   DESCRIPTION
     "This entry controls the addition and deletion of 
      atmIfVccSrc components."
::= { atmIfVccSrc 1 }

atmIfVccSrcRowStatusEntry OBJECT-TYPE
   SYNTAX     AtmIfVccSrcRowStatusEntry
   ACCESS     not-accessible
   STATUS     mandatory
   DESCRIPTION
     "A single entry in the table represents a single 
      atmIfVccSrc component."
   INDEX {
      atmIfIndex,
      atmIfVccIndex,
      atmIfVccSrcIndex }
::= { atmIfVccSrcRowStatusTable 1 }

AtmIfVccSrcRowStatusEntry ::= SEQUENCE {
   atmIfVccSrcRowStatus
      RowStatus,
   atmIfVccSrcComponentName
      DisplayString,
   atmIfVccSrcStorageType
      StorageType,
   atmIfVccSrcIndex
      NonReplicated }

atmIfVccSrcRowStatus OBJECT-TYPE
   SYNTAX     RowStatus 
   ACCESS     read-write
   STATUS     mandatory
   DESCRIPTION
     "This variable is used as the basis for SNMP naming of
      atmIfVccSrc components.
      These components can be added and deleted."
::= { atmIfVccSrcRowStatusEntry 1 }

atmIfVccSrcComponentName OBJECT-TYPE
   SYNTAX     DisplayString 
   ACCESS     read-only
   STATUS     mandatory
   DESCRIPTION
     "This variable provides the component's string name for
      use with the ASCII Console Interface"
::= { atmIfVccSrcRowStatusEntry 2 }

atmIfVccSrcStorageType OBJECT-TYPE
   SYNTAX     StorageType 
   ACCESS     read-only
   STATUS     mandatory
   DESCRIPTION
     "This variable represents the storage type value for the
      atmIfVccSrc tables."
::= { atmIfVccSrcRowStatusEntry 4 }

atmIfVccSrcIndex OBJECT-TYPE
   SYNTAX     NonReplicated 
   ACCESS     not-accessible
   STATUS     mandatory
   DESCRIPTION
     "This variable represents the index for the atmIfVccSrc tables."
::= { atmIfVccSrcRowStatusEntry 10 }

atmIfVccSrcProvTable OBJECT-TYPE
   SYNTAX     SEQUENCE OF AtmIfVccSrcProvEntry
   ACCESS     not-accessible
   STATUS     mandatory
   DESCRIPTION
     "This attribute group contains the provisionable attributes of the 
      SourcePvc component."
::= { atmIfVccSrc 10 }

atmIfVccSrcProvEntry OBJECT-TYPE
   SYNTAX     AtmIfVccSrcProvEntry
   ACCESS     not-accessible
   STATUS     mandatory
   DESCRIPTION
     "An entry in the atmIfVccSrcProvTable."
   INDEX {
      atmIfIndex,
      atmIfVccIndex,
      atmIfVccSrcIndex }
::= { atmIfVccSrcProvTable 1 }

AtmIfVccSrcProvEntry ::= SEQUENCE {
   atmIfVccSrcRemoteAddress
      HexString,
   atmIfVccSrcRemoteVpiVci
      IntegerSequence,
   atmIfVccSrcCallingAddress
      HexString,
   atmIfVccSrcCalledAddress
      HexString,
   atmIfVccSrcCalledVpiVci
      IntegerSequence }

atmIfVccSrcRemoteAddress OBJECT-TYPE
   SYNTAX     HexString (SIZE (20))
   ACCESS     read-write
   STATUS     obsolete
   DESCRIPTION
     "This attribute represents the remote address of the soft PVC."
::= { atmIfVccSrcProvEntry 1 }

atmIfVccSrcRemoteVpiVci OBJECT-TYPE
   SYNTAX     IntegerSequence (SIZE (3..9))
   ACCESS     read-write
   STATUS     obsolete
   DESCRIPTION
     "This attribute represents the remote VPI and VCI of the soft PVC."
::= { atmIfVccSrcProvEntry 2 }

atmIfVccSrcCallingAddress OBJECT-TYPE
   SYNTAX     HexString (SIZE (0..20))
   ACCESS     read-write
   STATUS     mandatory
   DESCRIPTION
     "This attribute represents the calling address of the soft PVC. If it is 
      a null string, then the calling address is the address of the current 
      interface (that is, where the soft PVC originates)."
   DEFVAL     { ''H }  -- ""
::= { atmIfVccSrcProvEntry 3 }

atmIfVccSrcCalledAddress OBJECT-TYPE
   SYNTAX     HexString (SIZE (20))
   ACCESS     read-write
   STATUS     mandatory
   DESCRIPTION
     "This attribute represents the called (remote) address of the soft 
      PVC."
::= { atmIfVccSrcProvEntry 4 }

atmIfVccSrcCalledVpiVci OBJECT-TYPE
   SYNTAX     IntegerSequence (SIZE (3..10))
   ACCESS     read-write
   STATUS     mandatory
   DESCRIPTION
     "This attribute represents the remote VPI and VCI of the soft PVC."
::= { atmIfVccSrcProvEntry 5 }

atmIfVccSrcOperTable OBJECT-TYPE
   SYNTAX     SEQUENCE OF AtmIfVccSrcOperEntry
   ACCESS     not-accessible
   STATUS     mandatory
   DESCRIPTION
     "This attribute group contains the operational attributes associated 
      with the SrcPvp or SrcPvc component."
::= { atmIfVccSrc 11 }

atmIfVccSrcOperEntry OBJECT-TYPE
   SYNTAX     AtmIfVccSrcOperEntry
   ACCESS     not-accessible
   STATUS     mandatory
   DESCRIPTION
     "An entry in the atmIfVccSrcOperTable."
   INDEX {
      atmIfIndex,
      atmIfVccIndex,
      atmIfVccSrcIndex }
::= { atmIfVccSrcOperTable 1 }

AtmIfVccSrcOperEntry ::= SEQUENCE {
   atmIfVccSrcState
      INTEGER,
   atmIfVccSrcRetryCount
      Counter32,
   atmIfVccSrcLastFailureCauseCode
      Unsigned32,
   atmIfVccSrcLastFailureDiagCode
      AsciiString }

atmIfVccSrcState OBJECT-TYPE
   SYNTAX     INTEGER  {
                 active(0),
                 inactive(1) }
   ACCESS     read-only
   STATUS     mandatory
   DESCRIPTION
     "This attribute indicates the state of the soft PVP or soft PVC."
::= { atmIfVccSrcOperEntry 1 }

atmIfVccSrcRetryCount OBJECT-TYPE
   SYNTAX     Counter32 
   ACCESS     read-only
   STATUS     mandatory
   DESCRIPTION
     "This attribute indicates the number of failed attempts to set up the 
      soft PVP or soft PVC since the last time the connection failed."
::= { atmIfVccSrcOperEntry 2 }

atmIfVccSrcLastFailureCauseCode OBJECT-TYPE
   SYNTAX     Unsigned32 (0..255)
   ACCESS     read-only
   STATUS     mandatory
   DESCRIPTION
     "This attribute contains the cause code in the last transmitted 
      signalling message that contains the CAUSE information element. 
      The cause code is used to describe the reason for generating certain 
      signalling messages. 
      The default value for this attribute is set to 0."
::= { atmIfVccSrcOperEntry 3 }

atmIfVccSrcLastFailureDiagCode OBJECT-TYPE
   SYNTAX     AsciiString (SIZE (0..8))
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to NULL."
::= { atmIfVccSrcOperEntry 4 }


-- AtmIf/n Vcc/vpi.vci Ep
-- AtmIf/n Vpt/vpi Vcc/vci Ep
-- 
-- The EndPoint component of the application associated with the 
-- VCC is used to link a switched VCC to an application that sends 
-- and receives frames using the connection. 

atmIfVccEp OBJECT IDENTIFIER ::= { atmIfVcc 9 }



atmIfVccEpRowStatusTable OBJECT-TYPE
   SYNTAX     SEQUENCE OF AtmIfVccEpRowStatusEntry
   ACCESS     not-accessible
   STATUS     mandatory
   DESCRIPTION
     "This entry controls the addition and deletion of 
      atmIfVccEp components."
::= { atmIfVccEp 1 }

atmIfVccEpRowStatusEntry OBJECT-TYPE
   SYNTAX     AtmIfVccEpRowStatusEntry
   ACCESS     not-accessible
   STATUS     mandatory
   DESCRIPTION
     "A single entry in the table represents a single 
      atmIfVccEp component."
   INDEX {
      atmIfIndex,
      atmIfVccIndex,
      atmIfVccEpIndex }
::= { atmIfVccEpRowStatusTable 1 }

AtmIfVccEpRowStatusEntry ::= SEQUENCE {
   atmIfVccEpRowStatus
      RowStatus,
   atmIfVccEpComponentName
      DisplayString,
   atmIfVccEpStorageType
      StorageType,
   atmIfVccEpIndex
      NonReplicated }

atmIfVccEpRowStatus OBJECT-TYPE
   SYNTAX     RowStatus 
   ACCESS     read-only
   STATUS     mandatory
   DESCRIPTION
     "This variable is used as the basis for SNMP naming of
      atmIfVccEp components.
      These components cannot be added nor deleted."
::= { atmIfVccEpRowStatusEntry 1 }

atmIfVccEpComponentName OBJECT-TYPE
   SYNTAX     DisplayString 
   ACCESS     read-only
   STATUS     mandatory
   DESCRIPTION
     "This variable provides the component's string name for
      use with the ASCII Console Interface"
::= { atmIfVccEpRowStatusEntry 2 }

atmIfVccEpStorageType OBJECT-TYPE
   SYNTAX     StorageType 
   ACCESS     read-only
   STATUS     mandatory
   DESCRIPTION
     "This variable represents the storage type value for the
      atmIfVccEp tables."
::= { atmIfVccEpRowStatusEntry 4 }

atmIfVccEpIndex OBJECT-TYPE
   SYNTAX     NonReplicated 
   ACCESS     not-accessible
   STATUS     mandatory
   DESCRIPTION
     "This variable represents the index for the atmIfVccEp tables."
::= { atmIfVccEpRowStatusEntry 10 }

atmIfVccEpOperTable OBJECT-TYPE
   SYNTAX     SEQUENCE OF AtmIfVccEpOperEntry
   ACCESS     not-accessible
   STATUS     mandatory
   DESCRIPTION
     "This attribute group contains the operational attributes for the 
      AtmEndPoint component."
::= { atmIfVccEp 10 }

atmIfVccEpOperEntry OBJECT-TYPE
   SYNTAX     AtmIfVccEpOperEntry
   ACCESS     not-accessible
   STATUS     mandatory
   DESCRIPTION
     "An entry in the atmIfVccEpOperTable."
   INDEX {
      atmIfIndex,
      atmIfVccIndex,
      atmIfVccEpIndex }
::= { atmIfVccEpOperTable 1 }

AtmIfVccEpOperEntry ::= SEQUENCE {
   atmIfVccEpApplicationName
      RowPointer }

atmIfVccEpApplicationName OBJECT-TYPE
   SYNTAX     RowPointer 
   ACCESS     read-only
   STATUS     mandatory
   DESCRIPTION
     "This attribute indicates the component name associated with the 
      application associated with the switched VCC."
::= { atmIfVccEpOperEntry 1 }


-- AtmIf/n Vpc/vpi Rp
-- AtmIf/n Vcc/vpi.vci Rp
-- AtmIf/n Vpt/vpi Vcc/vci Rp
-- 
-- The RelayPoint component is used to establish a single hop of a 
-- Switched connection. When linked together, two Rps within a 
-- module, the associated connections are configured to relay ATM 
-- cells to one another. 

atmIfVccRp OBJECT IDENTIFIER ::= { atmIfVcc 10 }



atmIfVccRpRowStatusTable OBJECT-TYPE
   SYNTAX     SEQUENCE OF AtmIfVccRpRowStatusEntry
   ACCESS     not-accessible
   STATUS     mandatory
   DESCRIPTION
     "This entry controls the addition and deletion of 
      atmIfVccRp components."
::= { atmIfVccRp 1 }

atmIfVccRpRowStatusEntry OBJECT-TYPE
   SYNTAX     AtmIfVccRpRowStatusEntry
   ACCESS     not-accessible
   STATUS     mandatory
   DESCRIPTION
     "A single entry in the table represents a single 
      atmIfVccRp component."
   INDEX {
      atmIfIndex,
      atmIfVccIndex,
      atmIfVccRpIndex }
::= { atmIfVccRpRowStatusTable 1 }

AtmIfVccRpRowStatusEntry ::= SEQUENCE {
   atmIfVccRpRowStatus
      RowStatus,
   atmIfVccRpComponentName
      DisplayString,
   atmIfVccRpStorageType
      StorageType,
   atmIfVccRpIndex
      NonReplicated }

atmIfVccRpRowStatus OBJECT-TYPE
   SYNTAX     RowStatus 
   ACCESS     read-only
   STATUS     mandatory
   DESCRIPTION
     "This variable is used as the basis for SNMP naming of
      atmIfVccRp components.
      These components cannot be added nor deleted."
::= { atmIfVccRpRowStatusEntry 1 }

atmIfVccRpComponentName OBJECT-TYPE
   SYNTAX     DisplayString 
   ACCESS     read-only
   STATUS     mandatory
   DESCRIPTION
     "This variable provides the component's string name for
      use with the ASCII Console Interface"
::= { atmIfVccRpRowStatusEntry 2 }

atmIfVccRpStorageType OBJECT-TYPE
   SYNTAX     StorageType 
   ACCESS     read-only
   STATUS     mandatory
   DESCRIPTION
     "This variable represents the storage type value for the
      atmIfVccRp tables."
::= { atmIfVccRpRowStatusEntry 4 }

atmIfVccRpIndex OBJECT-TYPE
   SYNTAX     NonReplicated 
   ACCESS     not-accessible
   STATUS     mandatory
   DESCRIPTION
     "This variable represents the index for the atmIfVccRp tables."
::= { atmIfVccRpRowStatusEntry 10 }

atmIfVccRpOperTable OBJECT-TYPE
   SYNTAX     SEQUENCE OF AtmIfVccRpOperEntry
   ACCESS     not-accessible
   STATUS     mandatory
   DESCRIPTION
     "This attribute group contains the operational attributes for the 
      AtmRelayPoint component."
::= { atmIfVccRp 10 }

atmIfVccRpOperEntry OBJECT-TYPE
   SYNTAX     AtmIfVccRpOperEntry
   ACCESS     not-accessible
   STATUS     mandatory
   DESCRIPTION
     "An entry in the atmIfVccRpOperTable."
   INDEX {
      atmIfIndex,
      atmIfVccIndex,
      atmIfVccRpIndex }
::= { atmIfVccRpOperTable 1 }

AtmIfVccRpOperEntry ::= SEQUENCE {
   atmIfVccRpNextHop
      RowPointer }

atmIfVccRpNextHop OBJECT-TYPE
   SYNTAX     RowPointer 
   ACCESS     read-only
   STATUS     obsolete
   DESCRIPTION
     "This attribute indicates the component name of the Rp component 
      with which this Rp component is associated."
::= { atmIfVccRpOperEntry 1 }

atmIfVccRpNextHopsTable OBJECT-TYPE
   SYNTAX     SEQUENCE OF AtmIfVccRpNextHopsEntry
   ACCESS     not-accessible
   STATUS     mandatory
   DESCRIPTION
     "This attribute indicates the component name(s) of the Rp 
      component(s) with which this Rp component is associated. This 
      attribute can have more than one component name only when the 
      Vcc distributionType is pointToMultipoint and the callDirection is 
      fromLink."
::= { atmIfVccRp 430 }

atmIfVccRpNextHopsEntry OBJECT-TYPE
   SYNTAX     AtmIfVccRpNextHopsEntry
   ACCESS     not-accessible
   STATUS     mandatory
   DESCRIPTION
     "An entry in the atmIfVccRpNextHopsTable."
   INDEX {
      atmIfIndex,
      atmIfVccIndex,
      atmIfVccRpIndex,
      atmIfVccRpNextHopsValue }
::= { atmIfVccRpNextHopsTable 1 }

AtmIfVccRpNextHopsEntry ::= SEQUENCE {
   atmIfVccRpNextHopsValue
      RowPointer }

atmIfVccRpNextHopsValue OBJECT-TYPE
   SYNTAX     RowPointer 
   ACCESS     read-only
   STATUS     mandatory
   DESCRIPTION
     "This variable represents both the value and the index for the
      atmIfVccRpNextHopsTable."
::= { atmIfVccRpNextHopsEntry 1 }


-- AtmIf/n Vcc/vpi.vci DstPvc
-- AtmIf/n Vpt/vpi Vcc/vci DstPvc
-- 
-- This component represents the destination end of a soft PVC.

atmIfVccDst OBJECT IDENTIFIER ::= { atmIfVcc 11 }



atmIfVccDstRowStatusTable OBJECT-TYPE
   SYNTAX     SEQUENCE OF AtmIfVccDstRowStatusEntry
   ACCESS     not-accessible
   STATUS     mandatory
   DESCRIPTION
     "This entry controls the addition and deletion of 
      atmIfVccDst components."
::= { atmIfVccDst 1 }

atmIfVccDstRowStatusEntry OBJECT-TYPE
   SYNTAX     AtmIfVccDstRowStatusEntry
   ACCESS     not-accessible
   STATUS     mandatory
   DESCRIPTION
     "A single entry in the table represents a single 
      atmIfVccDst component."
   INDEX {
      atmIfIndex,
      atmIfVccIndex,
      atmIfVccDstIndex }
::= { atmIfVccDstRowStatusTable 1 }

AtmIfVccDstRowStatusEntry ::= SEQUENCE {
   atmIfVccDstRowStatus
      RowStatus,
   atmIfVccDstComponentName
      DisplayString,
   atmIfVccDstStorageType
      StorageType,
   atmIfVccDstIndex
      NonReplicated }

atmIfVccDstRowStatus OBJECT-TYPE
   SYNTAX     RowStatus 
   ACCESS     read-only
   STATUS     mandatory
   DESCRIPTION
     "This variable is used as the basis for SNMP naming of
      atmIfVccDst components.
      These components cannot be added nor deleted."
::= { atmIfVccDstRowStatusEntry 1 }

atmIfVccDstComponentName OBJECT-TYPE
   SYNTAX     DisplayString 
   ACCESS     read-only
   STATUS     mandatory
   DESCRIPTION
     "This variable provides the component's string name for
      use with the ASCII Console Interface"
::= { atmIfVccDstRowStatusEntry 2 }

atmIfVccDstStorageType OBJECT-TYPE
   SYNTAX     StorageType 
   ACCESS     read-only
   STATUS     mandatory
   DESCRIPTION
     "This variable represents the storage type value for the
      atmIfVccDst tables."
::= { atmIfVccDstRowStatusEntry 4 }

atmIfVccDstIndex OBJECT-TYPE
   SYNTAX     NonReplicated 
   ACCESS     not-accessible
   STATUS     mandatory
   DESCRIPTION
     "This variable represents the index for the atmIfVccDst tables."
::= { atmIfVccDstRowStatusEntry 10 }

atmIfVccDstOperTable OBJECT-TYPE
   SYNTAX     SEQUENCE OF AtmIfVccDstOperEntry
   ACCESS     not-accessible
   STATUS     mandatory
   DESCRIPTION
     "This attribute group contains the operational attributes for the 
      DestinationPvc component."
::= { atmIfVccDst 10 }

atmIfVccDstOperEntry OBJECT-TYPE
   SYNTAX     AtmIfVccDstOperEntry
   ACCESS     not-accessible
   STATUS     mandatory
   DESCRIPTION
     "An entry in the atmIfVccDstOperTable."
   INDEX {
      atmIfIndex,
      atmIfVccIndex,
      atmIfVccDstIndex }
::= { atmIfVccDstOperTable 1 }

AtmIfVccDstOperEntry ::= SEQUENCE {
   atmIfVccDstCalledAddress
      HexString,
   atmIfVccDstCallingAddress
      AsciiString,
   atmIfVccDstCallingVpiVci
      AsciiString }

atmIfVccDstCalledAddress OBJECT-TYPE
   SYNTAX     HexString (SIZE (20))
   ACCESS     read-only
   STATUS     mandatory
   DESCRIPTION
     "This attribute represents the called address of the soft PVC."
::= { atmIfVccDstOperEntry 3 }

atmIfVccDstCallingAddress OBJECT-TYPE
   SYNTAX     AsciiString (SIZE (7..40))
   ACCESS     read-only
   STATUS     mandatory
   DESCRIPTION
     "This attribute represents the remote address of the soft PVC. If the 
      address in not known, then the value of this address is Unknown."
::= { atmIfVccDstOperEntry 4 }

atmIfVccDstCallingVpiVci OBJECT-TYPE
   SYNTAX     AsciiString (SIZE (7..9))
   ACCESS     read-only
   STATUS     mandatory
   DESCRIPTION
     "This attribute represents the remote VPI and VCI of the soft PVC. If 
      the VPI and VCI values are not known, this attribute is set to 
      Unknown."
::= { atmIfVccDstOperEntry 5 }


-- AtmIf/n Vcc/vpi.vci SrcPvc
-- AtmIf/n Vpt/vpi Vcc/vci SrcPvc
-- 
-- This component represents the source end of a soft PVC.

atmIfVptVccSrc OBJECT IDENTIFIER ::= { atmIfVptVcc 8 }



atmIfVptVccSrcRowStatusTable OBJECT-TYPE
   SYNTAX     SEQUENCE OF AtmIfVptVccSrcRowStatusEntry
   ACCESS     not-accessible
   STATUS     mandatory
   DESCRIPTION
     "This entry controls the addition and deletion of 
      atmIfVptVccSrc components."
::= { atmIfVptVccSrc 1 }

atmIfVptVccSrcRowStatusEntry OBJECT-TYPE
   SYNTAX     AtmIfVptVccSrcRowStatusEntry
   ACCESS     not-accessible
   STATUS     mandatory
   DESCRIPTION
     "A single entry in the table represents a single 
      atmIfVptVccSrc component."
   INDEX {
      atmIfIndex,
      atmIfVptIndex,
      atmIfVptVccIndex,
      atmIfVptVccSrcIndex }
::= { atmIfVptVccSrcRowStatusTable 1 }

AtmIfVptVccSrcRowStatusEntry ::= SEQUENCE {
   atmIfVptVccSrcRowStatus
      RowStatus,
   atmIfVptVccSrcComponentName
      DisplayString,
   atmIfVptVccSrcStorageType
      StorageType,
   atmIfVptVccSrcIndex
      NonReplicated }

atmIfVptVccSrcRowStatus OBJECT-TYPE
   SYNTAX     RowStatus 
   ACCESS     read-write
   STATUS     mandatory
   DESCRIPTION
     "This variable is used as the basis for SNMP naming of
      atmIfVptVccSrc components.
      These components can be added and deleted."
::= { atmIfVptVccSrcRowStatusEntry 1 }

atmIfVptVccSrcComponentName OBJECT-TYPE
   SYNTAX     DisplayString 
   ACCESS     read-only
   STATUS     mandatory
   DESCRIPTION
     "This variable provides the component's string name for
      use with the ASCII Console Interface"
::= { atmIfVptVccSrcRowStatusEntry 2 }

atmIfVptVccSrcStorageType OBJECT-TYPE
   SYNTAX     StorageType 
   ACCESS     read-only
   STATUS     mandatory
   DESCRIPTION
     "This variable represents the storage type value for the
      atmIfVptVccSrc tables."
::= { atmIfVptVccSrcRowStatusEntry 4 }

atmIfVptVccSrcIndex OBJECT-TYPE
   SYNTAX     NonReplicated 
   ACCESS     not-accessible
   STATUS     mandatory
   DESCRIPTION
     "This variable represents the index for the atmIfVptVccSrc tables."
::= { atmIfVptVccSrcRowStatusEntry 10 }

atmIfVptVccSrcProvTable OBJECT-TYPE
   SYNTAX     SEQUENCE OF AtmIfVptVccSrcProvEntry
   ACCESS     not-accessible
   STATUS     mandatory
   DESCRIPTION
     "This attribute group contains the provisionable attributes of the 
      SourcePvc component."
::= { atmIfVptVccSrc 10 }

atmIfVptVccSrcProvEntry OBJECT-TYPE
   SYNTAX     AtmIfVptVccSrcProvEntry
   ACCESS     not-accessible
   STATUS     mandatory
   DESCRIPTION
     "An entry in the atmIfVptVccSrcProvTable."
   INDEX {
      atmIfIndex,
      atmIfVptIndex,
      atmIfVptVccIndex,
      atmIfVptVccSrcIndex }
::= { atmIfVptVccSrcProvTable 1 }

AtmIfVptVccSrcProvEntry ::= SEQUENCE {
   atmIfVptVccSrcRemoteAddress
      HexString,
   atmIfVptVccSrcRemoteVpiVci
      IntegerSequence,
   atmIfVptVccSrcCallingAddress
      HexString,
   atmIfVptVccSrcCalledAddress
      HexString,
   atmIfVptVccSrcCalledVpiVci
      IntegerSequence }

atmIfVptVccSrcRemoteAddress OBJECT-TYPE
   SYNTAX     HexString (SIZE (20))
   ACCESS     read-write
   STATUS     obsolete
   DESCRIPTION
     "This attribute represents the remote address of the soft PVC."
::= { atmIfVptVccSrcProvEntry 1 }

atmIfVptVccSrcRemoteVpiVci OBJECT-TYPE
   SYNTAX     IntegerSequence (SIZE (3..9))
   ACCESS     read-write
   STATUS     obsolete
   DESCRIPTION
     "This attribute represents the remote VPI and VCI of the soft PVC."
::= { atmIfVptVccSrcProvEntry 2 }

atmIfVptVccSrcCallingAddress OBJECT-TYPE
   SYNTAX     HexString (SIZE (0..20))
   ACCESS     read-write
   STATUS     mandatory
   DESCRIPTION
     "This attribute represents the calling address of the soft PVC. If it is 
      a null string, then the calling address is the address of the current 
      interface (that is, where the soft PVC originates)."
   DEFVAL     { ''H }  -- ""
::= { atmIfVptVccSrcProvEntry 3 }

atmIfVptVccSrcCalledAddress OBJECT-TYPE
   SYNTAX     HexString (SIZE (20))
   ACCESS     read-write
   STATUS     mandatory
   DESCRIPTION
     "This attribute represents the called (remote) address of the soft 
      PVC."
::= { atmIfVptVccSrcProvEntry 4 }

atmIfVptVccSrcCalledVpiVci OBJECT-TYPE
   SYNTAX     IntegerSequence (SIZE (3..10))
   ACCESS     read-write
   STATUS     mandatory
   DESCRIPTION
     "This attribute represents the remote VPI and VCI of the soft PVC."
::= { atmIfVptVccSrcProvEntry 5 }

atmIfVptVccSrcOperTable OBJECT-TYPE
   SYNTAX     SEQUENCE OF AtmIfVptVccSrcOperEntry
   ACCESS     not-accessible
   STATUS     mandatory
   DESCRIPTION
     "This attribute group contains the operational attributes associated 
      with the SrcPvp or SrcPvc component."
::= { atmIfVptVccSrc 11 }

atmIfVptVccSrcOperEntry OBJECT-TYPE
   SYNTAX     AtmIfVptVccSrcOperEntry
   ACCESS     not-accessible
   STATUS     mandatory
   DESCRIPTION
     "An entry in the atmIfVptVccSrcOperTable."
   INDEX {
      atmIfIndex,
      atmIfVptIndex,
      atmIfVptVccIndex,
      atmIfVptVccSrcIndex }
::= { atmIfVptVccSrcOperTable 1 }

AtmIfVptVccSrcOperEntry ::= SEQUENCE {
   atmIfVptVccSrcState
      INTEGER,
   atmIfVptVccSrcRetryCount
      Counter32,
   atmIfVptVccSrcLastFailureCauseCode
      Unsigned32,
   atmIfVptVccSrcLastFailureDiagCode
      AsciiString }

atmIfVptVccSrcState OBJECT-TYPE
   SYNTAX     INTEGER  {
                 active(0),
                 inactive(1) }
   ACCESS     read-only
   STATUS     mandatory
   DESCRIPTION
     "This attribute indicates the state of the soft PVP or soft PVC."
::= { atmIfVptVccSrcOperEntry 1 }

atmIfVptVccSrcRetryCount OBJECT-TYPE
   SYNTAX     Counter32 
   ACCESS     read-only
   STATUS     mandatory
   DESCRIPTION
     "This attribute indicates the number of failed attempts to set up the 
      soft PVP or soft PVC since the last time the connection failed."
::= { atmIfVptVccSrcOperEntry 2 }

atmIfVptVccSrcLastFailureCauseCode OBJECT-TYPE
   SYNTAX     Unsigned32 (0..255)
   ACCESS     read-only
   STATUS     mandatory
   DESCRIPTION
     "This attribute contains the cause code in the last transmitted 
      signalling message that contains the CAUSE information element. 
      The cause code is used to describe the reason for generating certain 
      signalling messages. 
      The default value for this attribute is set to 0."
::= { atmIfVptVccSrcOperEntry 3 }

atmIfVptVccSrcLastFailureDiagCode OBJECT-TYPE
   SYNTAX     AsciiString (SIZE (0..8))
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to NULL."
::= { atmIfVptVccSrcOperEntry 4 }


-- AtmIf/n Vcc/vpi.vci Ep
-- AtmIf/n Vpt/vpi Vcc/vci Ep
-- 
-- The EndPoint component of the application associated with the 
-- VCC is used to link a switched VCC to an application that sends 
-- and receives frames using the connection. 

atmIfVptVccEp OBJECT IDENTIFIER ::= { atmIfVptVcc 9 }



atmIfVptVccEpRowStatusTable OBJECT-TYPE
   SYNTAX     SEQUENCE OF AtmIfVptVccEpRowStatusEntry
   ACCESS     not-accessible
   STATUS     mandatory
   DESCRIPTION
     "This entry controls the addition and deletion of 
      atmIfVptVccEp components."
::= { atmIfVptVccEp 1 }

atmIfVptVccEpRowStatusEntry OBJECT-TYPE
   SYNTAX     AtmIfVptVccEpRowStatusEntry
   ACCESS     not-accessible
   STATUS     mandatory
   DESCRIPTION
     "A single entry in the table represents a single 
      atmIfVptVccEp component."
   INDEX {
      atmIfIndex,
      atmIfVptIndex,
      atmIfVptVccIndex,
      atmIfVptVccEpIndex }
::= { atmIfVptVccEpRowStatusTable 1 }

AtmIfVptVccEpRowStatusEntry ::= SEQUENCE {
   atmIfVptVccEpRowStatus
      RowStatus,
   atmIfVptVccEpComponentName
      DisplayString,
   atmIfVptVccEpStorageType
      StorageType,
   atmIfVptVccEpIndex
      NonReplicated }

atmIfVptVccEpRowStatus OBJECT-TYPE
   SYNTAX     RowStatus 
   ACCESS     read-only
   STATUS     mandatory
   DESCRIPTION
     "This variable is used as the basis for SNMP naming of
      atmIfVptVccEp components.
      These components cannot be added nor deleted."
::= { atmIfVptVccEpRowStatusEntry 1 }

atmIfVptVccEpComponentName OBJECT-TYPE
   SYNTAX     DisplayString 
   ACCESS     read-only
   STATUS     mandatory
   DESCRIPTION
     "This variable provides the component's string name for
      use with the ASCII Console Interface"
::= { atmIfVptVccEpRowStatusEntry 2 }

atmIfVptVccEpStorageType OBJECT-TYPE
   SYNTAX     StorageType 
   ACCESS     read-only
   STATUS     mandatory
   DESCRIPTION
     "This variable represents the storage type value for the
      atmIfVptVccEp tables."
::= { atmIfVptVccEpRowStatusEntry 4 }

atmIfVptVccEpIndex OBJECT-TYPE
   SYNTAX     NonReplicated 
   ACCESS     not-accessible
   STATUS     mandatory
   DESCRIPTION
     "This variable represents the index for the atmIfVptVccEp tables."
::= { atmIfVptVccEpRowStatusEntry 10 }

atmIfVptVccEpOperTable OBJECT-TYPE
   SYNTAX     SEQUENCE OF AtmIfVptVccEpOperEntry
   ACCESS     not-accessible
   STATUS     mandatory
   DESCRIPTION
     "This attribute group contains the operational attributes for the 
      AtmEndPoint component."
::= { atmIfVptVccEp 10 }

atmIfVptVccEpOperEntry OBJECT-TYPE
   SYNTAX     AtmIfVptVccEpOperEntry
   ACCESS     not-accessible
   STATUS     mandatory
   DESCRIPTION
     "An entry in the atmIfVptVccEpOperTable."
   INDEX {
      atmIfIndex,
      atmIfVptIndex,
      atmIfVptVccIndex,
      atmIfVptVccEpIndex }
::= { atmIfVptVccEpOperTable 1 }

AtmIfVptVccEpOperEntry ::= SEQUENCE {
   atmIfVptVccEpApplicationName
      RowPointer }

atmIfVptVccEpApplicationName OBJECT-TYPE
   SYNTAX     RowPointer 
   ACCESS     read-only
   STATUS     mandatory
   DESCRIPTION
     "This attribute indicates the component name associated with the 
      application associated with the switched VCC."
::= { atmIfVptVccEpOperEntry 1 }


-- AtmIf/n Vpc/vpi Rp
-- AtmIf/n Vcc/vpi.vci Rp
-- AtmIf/n Vpt/vpi Vcc/vci Rp
-- 
-- The RelayPoint component is used to establish a single hop of a 
-- Switched connection. When linked together, two Rps within a 
-- module, the associated connections are configured to relay ATM 
-- cells to one another. 

atmIfVptVccRp OBJECT IDENTIFIER ::= { atmIfVptVcc 10 }



atmIfVptVccRpRowStatusTable OBJECT-TYPE
   SYNTAX     SEQUENCE OF AtmIfVptVccRpRowStatusEntry
   ACCESS     not-accessible
   STATUS     mandatory
   DESCRIPTION
     "This entry controls the addition and deletion of 
      atmIfVptVccRp components."
::= { atmIfVptVccRp 1 }

atmIfVptVccRpRowStatusEntry OBJECT-TYPE
   SYNTAX     AtmIfVptVccRpRowStatusEntry
   ACCESS     not-accessible
   STATUS     mandatory
   DESCRIPTION
     "A single entry in the table represents a single 
      atmIfVptVccRp component."
   INDEX {
      atmIfIndex,
      atmIfVptIndex,
      atmIfVptVccIndex,
      atmIfVptVccRpIndex }
::= { atmIfVptVccRpRowStatusTable 1 }

AtmIfVptVccRpRowStatusEntry ::= SEQUENCE {
   atmIfVptVccRpRowStatus
      RowStatus,
   atmIfVptVccRpComponentName
      DisplayString,
   atmIfVptVccRpStorageType
      StorageType,
   atmIfVptVccRpIndex
      NonReplicated }

atmIfVptVccRpRowStatus OBJECT-TYPE
   SYNTAX     RowStatus 
   ACCESS     read-only
   STATUS     mandatory
   DESCRIPTION
     "This variable is used as the basis for SNMP naming of
      atmIfVptVccRp components.
      These components cannot be added nor deleted."
::= { atmIfVptVccRpRowStatusEntry 1 }

atmIfVptVccRpComponentName OBJECT-TYPE
   SYNTAX     DisplayString 
   ACCESS     read-only
   STATUS     mandatory
   DESCRIPTION
     "This variable provides the component's string name for
      use with the ASCII Console Interface"
::= { atmIfVptVccRpRowStatusEntry 2 }

atmIfVptVccRpStorageType OBJECT-TYPE
   SYNTAX     StorageType 
   ACCESS     read-only
   STATUS     mandatory
   DESCRIPTION
     "This variable represents the storage type value for the
      atmIfVptVccRp tables."
::= { atmIfVptVccRpRowStatusEntry 4 }

atmIfVptVccRpIndex OBJECT-TYPE
   SYNTAX     NonReplicated 
   ACCESS     not-accessible
   STATUS     mandatory
   DESCRIPTION
     "This variable represents the index for the atmIfVptVccRp tables."
::= { atmIfVptVccRpRowStatusEntry 10 }

atmIfVptVccRpOperTable OBJECT-TYPE
   SYNTAX     SEQUENCE OF AtmIfVptVccRpOperEntry
   ACCESS     not-accessible
   STATUS     mandatory
   DESCRIPTION
     "This attribute group contains the operational attributes for the 
      AtmRelayPoint component."
::= { atmIfVptVccRp 10 }

atmIfVptVccRpOperEntry OBJECT-TYPE
   SYNTAX     AtmIfVptVccRpOperEntry
   ACCESS     not-accessible
   STATUS     mandatory
   DESCRIPTION
     "An entry in the atmIfVptVccRpOperTable."
   INDEX {
      atmIfIndex,
      atmIfVptIndex,
      atmIfVptVccIndex,
      atmIfVptVccRpIndex }
::= { atmIfVptVccRpOperTable 1 }

AtmIfVptVccRpOperEntry ::= SEQUENCE {
   atmIfVptVccRpNextHop
      RowPointer }

atmIfVptVccRpNextHop OBJECT-TYPE
   SYNTAX     RowPointer 
   ACCESS     read-only
   STATUS     obsolete
   DESCRIPTION
     "This attribute indicates the component name of the Rp component 
      with which this Rp component is associated."
::= { atmIfVptVccRpOperEntry 1 }

atmIfVptVccRpNextHopsTable OBJECT-TYPE
   SYNTAX     SEQUENCE OF AtmIfVptVccRpNextHopsEntry
   ACCESS     not-accessible
   STATUS     mandatory
   DESCRIPTION
     "This attribute indicates the component name(s) of the Rp 
      component(s) with which this Rp component is associated. This 
      attribute can have more than one component name only when the 
      Vcc distributionType is pointToMultipoint and the callDirection is 
      fromLink."
::= { atmIfVptVccRp 430 }

atmIfVptVccRpNextHopsEntry OBJECT-TYPE
   SYNTAX     AtmIfVptVccRpNextHopsEntry
   ACCESS     not-accessible
   STATUS     mandatory
   DESCRIPTION
     "An entry in the atmIfVptVccRpNextHopsTable."
   INDEX {
      atmIfIndex,
      atmIfVptIndex,
      atmIfVptVccIndex,
      atmIfVptVccRpIndex,
      atmIfVptVccRpNextHopsValue }
::= { atmIfVptVccRpNextHopsTable 1 }

AtmIfVptVccRpNextHopsEntry ::= SEQUENCE {
   atmIfVptVccRpNextHopsValue
      RowPointer }

atmIfVptVccRpNextHopsValue OBJECT-TYPE
   SYNTAX     RowPointer 
   ACCESS     read-only
   STATUS     mandatory
   DESCRIPTION
     "This variable represents both the value and the index for the
      atmIfVptVccRpNextHopsTable."
::= { atmIfVptVccRpNextHopsEntry 1 }


-- AtmIf/n Vcc/vpi.vci DstPvc
-- AtmIf/n Vpt/vpi Vcc/vci DstPvc
-- 
-- This component represents the destination end of a soft PVC.

atmIfVptVccDst OBJECT IDENTIFIER ::= { atmIfVptVcc 11 }



atmIfVptVccDstRowStatusTable OBJECT-TYPE
   SYNTAX     SEQUENCE OF AtmIfVptVccDstRowStatusEntry
   ACCESS     not-accessible
   STATUS     mandatory
   DESCRIPTION
     "This entry controls the addition and deletion of 
      atmIfVptVccDst components."
::= { atmIfVptVccDst 1 }

atmIfVptVccDstRowStatusEntry OBJECT-TYPE
   SYNTAX     AtmIfVptVccDstRowStatusEntry
   ACCESS     not-accessible
   STATUS     mandatory
   DESCRIPTION
     "A single entry in the table represents a single 
      atmIfVptVccDst component."
   INDEX {
      atmIfIndex,
      atmIfVptIndex,
      atmIfVptVccIndex,
      atmIfVptVccDstIndex }
::= { atmIfVptVccDstRowStatusTable 1 }

AtmIfVptVccDstRowStatusEntry ::= SEQUENCE {
   atmIfVptVccDstRowStatus
      RowStatus,
   atmIfVptVccDstComponentName
      DisplayString,
   atmIfVptVccDstStorageType
      StorageType,
   atmIfVptVccDstIndex
      NonReplicated }

atmIfVptVccDstRowStatus OBJECT-TYPE
   SYNTAX     RowStatus 
   ACCESS     read-only
   STATUS     mandatory
   DESCRIPTION
     "This variable is used as the basis for SNMP naming of
      atmIfVptVccDst components.
      These components cannot be added nor deleted."
::= { atmIfVptVccDstRowStatusEntry 1 }

atmIfVptVccDstComponentName OBJECT-TYPE
   SYNTAX     DisplayString 
   ACCESS     read-only
   STATUS     mandatory
   DESCRIPTION
     "This variable provides the component's string name for
      use with the ASCII Console Interface"
::= { atmIfVptVccDstRowStatusEntry 2 }

atmIfVptVccDstStorageType OBJECT-TYPE
   SYNTAX     StorageType 
   ACCESS     read-only
   STATUS     mandatory
   DESCRIPTION
     "This variable represents the storage type value for the
      atmIfVptVccDst tables."
::= { atmIfVptVccDstRowStatusEntry 4 }

atmIfVptVccDstIndex OBJECT-TYPE
   SYNTAX     NonReplicated 
   ACCESS     not-accessible
   STATUS     mandatory
   DESCRIPTION
     "This variable represents the index for the atmIfVptVccDst tables."
::= { atmIfVptVccDstRowStatusEntry 10 }

atmIfVptVccDstOperTable OBJECT-TYPE
   SYNTAX     SEQUENCE OF AtmIfVptVccDstOperEntry
   ACCESS     not-accessible
   STATUS     mandatory
   DESCRIPTION
     "This attribute group contains the operational attributes for the 
      DestinationPvc component."
::= { atmIfVptVccDst 10 }

atmIfVptVccDstOperEntry OBJECT-TYPE
   SYNTAX     AtmIfVptVccDstOperEntry
   ACCESS     not-accessible
   STATUS     mandatory
   DESCRIPTION
     "An entry in the atmIfVptVccDstOperTable."
   INDEX {
      atmIfIndex,
      atmIfVptIndex,
      atmIfVptVccIndex,
      atmIfVptVccDstIndex }
::= { atmIfVptVccDstOperTable 1 }

AtmIfVptVccDstOperEntry ::= SEQUENCE {
   atmIfVptVccDstCalledAddress
      HexString,
   atmIfVptVccDstCallingAddress
      AsciiString,
   atmIfVptVccDstCallingVpiVci
      AsciiString }

atmIfVptVccDstCalledAddress OBJECT-TYPE
   SYNTAX     HexString (SIZE (20))
   ACCESS     read-only
   STATUS     mandatory
   DESCRIPTION
     "This attribute represents the called address of the soft PVC."
::= { atmIfVptVccDstOperEntry 3 }

atmIfVptVccDstCallingAddress OBJECT-TYPE
   SYNTAX     AsciiString (SIZE (7..40))
   ACCESS     read-only
   STATUS     mandatory
   DESCRIPTION
     "This attribute represents the remote address of the soft PVC. If the 
      address in not known, then the value of this address is Unknown."
::= { atmIfVptVccDstOperEntry 4 }

atmIfVptVccDstCallingVpiVci OBJECT-TYPE
   SYNTAX     AsciiString (SIZE (7..9))
   ACCESS     read-only
   STATUS     mandatory
   DESCRIPTION
     "This attribute represents the remote VPI and VCI of the soft PVC. If 
      the VPI and VCI values are not known, this attribute is set to 
      Unknown."
::= { atmIfVptVccDstOperEntry 5 }




-- 
-- Version and Compliance statements
-- 



-- Object-Group Statement:
-- A list of all current accessible leaf objects.

-- OBJECTS { atmIfVptVccSrcLastFailureDiagCode,
--           atmIfVccRpNextHopsValue,
--           aRtgPnniCfgNodeDefSAddrScope,
--           aRtgPnniCallsRerouted,
--           atmIfVptVccDstRowStatus,
--           aRtgPnniRfDestinationAddress,
--           atmIfVpcRpNextHopsValue,
--           aRtgPnniRfRowStatus,
--           atmIfVptVccRpComponentName,
--           atmCRDnaStorageType,
--           aRtgPnniTopNodeLinkRowStatus,
--           aRtgPnniTopNodeAddrComponentName,
--           aRtgPnniTopNodeComponentName,
--           aRtgPnniCfgNodeRowStatus,
--           aRtgPnniPortStorageType,
--           atmIfVpcRpComponentName,
--           atmIfVpcSrcLastFailureDiagCode,
--           aRtgPnniTopNodeLinkStorageType,
--           aRtgPnniNodeAddressPrefix,
--           atmIfVpcSrcCallingAddress,
--           aRtgPnniCfgNodeNodeId,
--           atmIfVpcSrcCalledVpi,
--           aRtgPnniPeerDelayedAckInterval,
--           aRtgPnniCfgNodeNodeAddress,
--           aRtgPnniCfgNodeDefSAddrComponentName,
--           atmIfVpcDstCallingAddress,
--           aRtgPnniCfgNodeNbrPtseAcksRx,
--           atmIfVpcDstComponentName,
--           aRtgPnniPtseHoldDown,
--           aRtgPnniTopStorageType,
--           aRtgRoutingAttempts,
--           aRtgPnniPtseLifetimeFactor,
--           aRtgPnniCfgNodeNbrStorageType,
--           atmIfVccSrcCallingAddress,
--           aRtgPnniRfBwdQosClass,
--           atmCRDnaRowStatus,
--           aRtgPnniCfgNodeNbrPtseReqTx,
--           atmIfVpcDstCalledAddress,
--           aRtgDnaComponentName,
--           aRtgPnniStorageType,
--           aRtgDnaDestInfoType,
--           aRtgPnniPortRowStatus,
--           aRtgPnniCfgNodeSAddrScope,
--           atmIfVptVccSrcState,
--           aRtgPnniRfClippingBbc,
--           aRtgPnniRoutingAttempts,
--           aRtgPnniDefaultScope,
--           atmCRDnaComponentName,
--           atmIfVccDstCalledAddress,
--           atmIfVptVccSrcRowStatus,
--           aRtgPnniRfBqpValue,
--           atmIfVptVccEpStorageType,
--           aRtgPnniRfRxTdpValue,
--           aRtgPnniRfBestEffort,
--           aRtgPnniCfgNodePeerGroupId,
--           aRtgPnniCfgNodeNbrPtspRx,
--           aRtgPnniOverrideDelay,
--           aRtgPnniCfgNodeDefSAddrState,
--           atmIfVptVccSrcRetryCount,
--           atmIfVccSrcCalledVpiVci,
--           aRtgPnniCfgNodeOpNodeId,
--           atmIfVccDstRowStatus,
--           atmIfVptVccRpStorageType,
--           aRtgPnniRowStatus,
--           atmIfVccDstStorageType,
--           aRtgPnniCfgNodeNbrPtseReqRx,
--           aRtgPnniTopNodeAddrStorageType,
--           aRtgPnniTopNodeStorageType,
--           atmIfVptVccEpRowStatus,
--           aRtgPnniTopNodeLinkRemotePortId,
--           atmIfVccSrcComponentName,
--           aRtgPnniPortStdComponentName,
--           aRtgPnniCfgNodeSAddrSuppress,
--           aRtgDnaDestInfoComponentName,
--           atmIfVpcSrcComponentName,
--           aRtgPnniCfgNodeNbrPeerState,
--           atmIfVpcDstStorageType,
--           atmIfVccDstCallingAddress,
--           atmIfVpcSrcState,
--           aRtgPnniRequestRxmtInterval,
--           aRtgPnniCfgNodeNumRccs,
--           atmIfVptVccRpRowStatus,
--           aRtgPnniCfgNodeOpPeerGroupId,
--           aRtgPnniCfgNodeNbrDbSummariesTx,
--           aRtgPnniCfgNodeDefSAddrStorageType,
--           atmIfVpcDstCallingVpi,
--           aRtgPnniCfgNodeNbrBadPtseAckRx,
--           aRtgPnniCfgNodeDefSAddrAddress,
--           aRtgPnniRfOptimizationMetric,
--           atmCRComponentName,
--           aRtgPnniAvcrMt,
--           atmIfVpcSrcCalledAddress,
--           aRtgPnniCfgNodeCurrentLeadershipPriority,
--           aRtgPnniPglInitTime,
--           atmIfVccSrcLastFailureDiagCode,
--           aRtgPnniTopNodeAddrRowStatus,
--           aRtgDnaStorageType,
--           aRtgPnniRfTxTrafficDescType,
--           aRtgPnniCfgNodeNbrPtseTx,
--           aRtgPnniCfgNodeNbrRowStatus,
--           atmIfVccSrcState,
--           aRtgPnniCfgNodeSAddrComponentName,
--           aRtgPnniRfTransferCapabilityBbc,
--           atmIfVpcDstRowStatus,
--           aRtgPnniCfgNodeNbrRccListValue,
--           atmIfVccSrcStorageType,
--           aRtgPnniTopActiveParentNodeId,
--           aRtgPnniRfMaxRoutes,
--           atmIfVccRpComponentName,
--           atmIfVccSrcRowStatus,
--           aRtgPnniCfgNodeDefSAddrRowStatus,
--           aRtgPnniHelloInterval,
--           aRtgPnniCfgNodeNbrDbSummariesRx,
--           aRtgPnniTopNodeRowStatus,
--           aRtgPnniRfTxTdpValue,
--           aRtgPnniCfgNodeNbrBadPtseReqRx,
--           aRtgPnniHelloInactivityFactor,
--           atmIfVptVccEpApplicationName,
--           aRtgPnniCfgNodeNbrPtseRx,
--           atmIfVptVccDstCallingVpiVci,
--           aRtgPnniCfgNodeNbrPtspTx,
--           aRtgPnniPtseRefreshInterval,
--           aRtgPnniRestrictTransit,
--           aRtgDnaRowStatus,
--           aRtgPnniMaxReroutesOnCrankback,
--           atmIfVptVccSrcStorageType,
--           atmIfVptVccSrcCallingAddress,
--           aRtgPnniFailedRoutingAttempts,
--           aRtgPnniRfRxTrafficDescType,
--           aRtgPnniCfgNodeNumNeighbors,
--           aRtgPnniRfComponentName,
--           aRtgDnaDestInfoStorageType,
--           atmIfVpcSrcStorageType,
--           aRtgPnniTopNodeLinkComponentName,
--           aRtgPnniCfgNodeSAddrState,
--           aRtgPnniCfgNodeComponentName,
--           atmIfVccDstComponentName,
--           aRtgPnniTopologyMemoryExhaustion,
--           atmIfVptVccDstCalledAddress,
--           aRtgPnniTopPreferredPglNodeId,
--           atmIfVpcSrcRowStatus,
--           atmIfVptVccRpNextHopsValue,
--           atmIfVccEpStorageType,
--           aRtgPnniRfBearerClassBbc,
--           aRtgDnaDestInfoReachability,
--           atmIfVccSrcLastFailureCauseCode,
--           aRtgPnniCfgNodeNbrBadPtseRx,
--           aRtgPnniAvcrPm,
--           aRtgPnniTopNodeAddrScope,
--           aRtgPnniTopRowStatus,
--           atmIfVptVccDstComponentName,
--           atmIfVptVccSrcCalledVpiVci,
--           atmIfVccSrcRetryCount,
--           aRtgDnaDestInfoRowStatus,
--           aRtgPnniCfgNodeSAddrStorageType,
--           atmCRStorageType,
--           aRtgPnniCfgNodeNbrBadDbSummariesRx,
--           atmIfVpcRpStorageType,
--           aRtgPnniReElectionInterval,
--           aRtgPnniOptMetricValue,
--           aRtgPnniPortComponentName,
--           atmIfVpcSrcRetryCount,
--           atmIfVccRpStorageType,
--           atmIfVptVccEpComponentName,
--           aRtgPnniCfgNodePglElectionState,
--           atmIfVccDstCallingVpiVci,
--           atmIfVptVccSrcCalledAddress,
--           atmIfVptVccDstStorageType,
--           atmCRRowStatus,
--           aRtgPnniRfFwdQosClass,
--           aRtgComponentName,
--           aRtgRowStatus,
--           aRtgPnniTopPtsesInDatabase,
--           atmIfVccRpRowStatus,
--           atmIfVptVccSrcComponentName,
--           aRtgPnniCfgNodeNbrPtseAcksTx,
--           aRtgPnniTopComponentName,
--           aRtgPnniCfgNodeNbrComponentName,
--           atmIfVptVccDstCallingAddress,
--           atmIfVccEpRowStatus,
--           aRtgPnniCfgNodeSAddrRowStatus,
--           atmIfVptVccSrcLastFailureCauseCode,
--           aRtgFailedRoutingAttempts,
--           aRtgPnniRfStorageType,
--           aRtgPnniComponentName,
--           aRtgDnaDestInfoStdComponentName,
--           aRtgPnniTopPglNodeId,
--           atmIfVpcSrcLastFailureCauseCode,
--           atmIfVccSrcCalledAddress,
--           aRtgPnniCfgNodeStorageType,
--           aRtgPnniRfFqpValue,
--           atmIfVccEpApplicationName,
--           aRtgPnniTopNodeLinkRemoteNodeId,
--           aRtgStorageType,
--           aRtgPnniCfgNodeNbrBadPtspRx,
--           atmIfVpcRpRowStatus,
--           aRtgPnniRfAtmServiceCategory,
--           aRtgDnaDestInfoScope,
--           atmIfVccEpComponentName,
--           aRtgPnniHelloHoldDown,
--           aRtgPnniDomain }
-- STATUS  mandatory
-- DESCRIPTION
--   "A list of all current accessible leaf objects."

atmNetworkingGroup OBJECT IDENTIFIER ::= { atmNetworkingMIB 1 }
atmNetworkingGroupBE OBJECT IDENTIFIER ::= { atmNetworkingGroup 5 }
atmNetworkingGroupBE01 OBJECT IDENTIFIER ::= { atmNetworkingGroupBE 2 }
atmNetworkingGroupBE01A OBJECT IDENTIFIER ::= { atmNetworkingGroupBE01 2 }



-- Agent-Capabilities Statement:

-- PRODUCT-RELEASE "Passport Release 7.0 AtmNetworking."
-- STATUS          mandatory
-- DESCRIPTION     "AtmNetworking MIB: MIB Version BE01A,
--                  Software Version BG00S4C."
-- SUPPORTS        Nortel-Magellan-Passport-AtmNetworkingMIB
--    INCLUDES     { atmNetworkingGroupBE01A }

atmNetworkingCapabilities OBJECT IDENTIFIER ::= { atmNetworkingMIB 3 }
atmNetworkingCapabilitiesBE OBJECT IDENTIFIER ::= { atmNetworkingCapabilities 5 }
atmNetworkingCapabilitiesBE01 OBJECT IDENTIFIER ::= { atmNetworkingCapabilitiesBE 2 }
atmNetworkingCapabilitiesBE01A OBJECT IDENTIFIER ::= { atmNetworkingCapabilitiesBE01 2 }





END
