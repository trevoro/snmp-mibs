-- $Header: spool.doc 1.1 94/12/07 $
 
-->#
--># Copyright (C) Siemens AG 1998
-->#               All rights reserved
-->#
-->#protocol specification
-->%PROTOCOL SNMP
-->#
-->#path to commands
-->%PATH /usr/sbin:/usr/bin:/sbin:/var/spool/Spool/config/cmd
-->#
-->#configuration
-->%REMCONFIG NO
-->%REMOPERATION NO
-->#
 
Spool-MIB DEFINITIONS ::= BEGIN
 
--
-- Title:   MIB for the Spool V4.x - Extension
-- Date:    November, 1994
-- Authors: Horst Lauber, Philosys Software GmbH c/o PD242
--          Anton Tobies, Schaefer & Tobies Software und Consulting GmbH
--
 
 
IMPORTS
        enterprises
            FROM RFC1155-SMI
        DisplayString
            FROM RFC1213-MIB
        OBJECT-TYPE
            FROM RFC-1212;
 
 
sni                     OBJECT IDENTIFIER ::= { enterprises 231 }
sniProductMibs          OBJECT IDENTIFIER ::= { sni 2 }
sniSpool                OBJECT IDENTIFIER ::= { sniProductMibs 12 }
sniSpoolObjects         OBJECT IDENTIFIER ::= { sniSpool 1 }
sniSpoolDevTable        OBJECT IDENTIFIER ::= { sniSpoolObjects 1 }
sniSpoolSrvTable        OBJECT IDENTIFIER ::= { sniSpoolObjects 2 }
sniSpoolSpvTable        OBJECT IDENTIFIER ::= { sniSpoolObjects 3 }
sniSpoolDgrTable        OBJECT IDENTIFIER ::= { sniSpoolObjects 4 }
sniSpoolHostTable       OBJECT IDENTIFIER ::= { sniSpoolObjects 5 }
sniSpoolJobTable        OBJECT IDENTIFIER ::= { sniSpoolObjects 6 }
--sniSpoolDprintTable     OBJECT IDENTIFIER ::= { sniSpoolObjects 7 }
 
-- Device Table
 
spoolDevTabNum             OBJECT-TYPE
        SYNTAX  INTEGER
        ACCESS  read-only
        STATUS  mandatory
        DESCRIPTION
                "The number of entries in the table spoolDevTab"
        ::= { sniSpoolDevTable 1 }
 
spoolDevTab             OBJECT-TYPE
        SYNTAX  SEQUENCE OF SpoolDevTabEntry
        ACCESS  not-accessible
        STATUS  mandatory
        DESCRIPTION
                "The spool device table"
        ::= { sniSpoolDevTable 2 }
 
spoolDevTabEntry        OBJECT-TYPE
        SYNTAX  SpoolDevTabEntry
        ACCESS  not-accessible
        STATUS  mandatory
        DESCRIPTION
                "An entry in the device table"
        INDEX   { spoolDevTabIndex }
        ::= { spoolDevTab 1 }
 
-- The following table is an extract of two SPOOL data structures:
-- sta_dv_ext
--     which reports the current state of a device (printer) and
-- ECM_printer
--     which holds the definition of a device object.
-- For more information see SPOOL header files xprint.h and client.h
 
SpoolDevTabEntry ::=
        SEQUENCE {
                spoolDevTabIndex                INTEGER,
                spoolDevName                    DisplayString,
                spoolDevState                   INTEGER,
                spoolDevSpoolin                 INTEGER,
                spoolDevSpoolout                INTEGER,
                spoolDevErrorMsg                DisplayString,
                spoolDevStaDate                 DisplayString,
                spoolDevPriority                INTEGER,
                spoolDevWaitingJobs             INTEGER,
                spoolDevCurForm                 DisplayString,
                spoolDevActJid                  DisplayString,
                spoolDevHost                    DisplayString,
                spoolDevAdmin                   DisplayString,
                spoolDevPcl                     DisplayString,
                spoolDevDftForm                 DisplayString,
                spoolDevSupervisor              DisplayString,
                spoolDevAdmComment              DisplayString,
                spoolDevUsrComment              DisplayString,
                spoolDevEnablePoll              INTEGER
        }
 
spoolDevTabIndex        OBJECT-TYPE
        SYNTAX  INTEGER
        ACCESS  read-only
        STATUS  mandatory
        DESCRIPTION
                "A unique value for each entry, its value ranges between
                1 and the value of spoolDevTabNum"
        ::= { spoolDevTabEntry 1 }
 
spoolDevName            OBJECT-TYPE
        SYNTAX  DisplayString (SIZE (0..63))
        ACCESS  read-only
        STATUS  mandatory
        DESCRIPTION
                "A unique device identfier string"
        ::= { spoolDevTabEntry 2 }
 
spoolDevState           OBJECT-TYPE
        SYNTAX  INTEGER {
                        active (1),
                        inactive (2),
                        error (3)
                }
        ACCESS  read-write
        STATUS  mandatory
        DESCRIPTION
                "The current state of the device, it has one of these
                values: ACTIVE, NOT_ACTIVE, DEVICE_ERROR"
        ::= { spoolDevTabEntry 3 }
 
spoolDevSpoolin         OBJECT-TYPE
        SYNTAX  INTEGER {
                        on (1),
                        off (2)
                }
        ACCESS  read-write
        STATUS  mandatory
        DESCRIPTION
                "Current state of the spoolin queue,
                 it is either ON or OFF"
        ::= { spoolDevTabEntry 4 }
 
spoolDevSpoolout        OBJECT-TYPE
        SYNTAX  INTEGER {
                        on (1),
                        off (2)
                }
        ACCESS  read-write
        STATUS  mandatory
        DESCRIPTION
                "Current state of the spoolout queue,
                 it is either ON or OFF"
        ::= { spoolDevTabEntry 5 }
 
spoolDevErrorMsg        OBJECT-TYPE
        SYNTAX  DisplayString
        ACCESS  read-only
        STATUS  mandatory
        DESCRIPTION
                "The error message in case of DEVICE_ERROR"
        ::= { spoolDevTabEntry 6 }
 
spoolDevStaDate         OBJECT-TYPE
        SYNTAX  DisplayString (SIZE (0..63))
        ACCESS  read-only
        STATUS  mandatory
        DESCRIPTION
                "The date of last state modification" 
        ::= { spoolDevTabEntry 7 }
 
spoolDevPriority        OBJECT-TYPE
        SYNTAX  INTEGER (0..65535)
        ACCESS  read-only
        STATUS  mandatory
        DESCRIPTION
                "The minimum priority a job must have to be printed on
                this device" 
        ::= { spoolDevTabEntry 8 }
 
spoolDevWaitingJobs     OBJECT-TYPE
        SYNTAX  INTEGER (0..4294967296)
        ACCESS  read-only
        STATUS  mandatory
        DESCRIPTION
                "The number of jobs that are waiting for the device" 
        ::= { spoolDevTabEntry 9 }
 
spoolDevCurForm         OBJECT-TYPE
        SYNTAX  DisplayString (SIZE (0..63))
        ACCESS  read-only
        STATUS  mandatory
        DESCRIPTION
                "Currently mounted form" 
        ::= { spoolDevTabEntry 10 }
 
spoolDevActJid          OBJECT-TYPE
        SYNTAX  DisplayString
        ACCESS  read-only
        STATUS  mandatory
        DESCRIPTION
                "Job that is currently printing" 
        ::= { spoolDevTabEntry 11 }
 
spoolDevHost            OBJECT-TYPE
        SYNTAX  DisplayString (SIZE (0..63))
        ACCESS  read-only
        STATUS  mandatory
        DESCRIPTION
                "Name of the host the printer is connected to" 
        ::= { spoolDevTabEntry 12 }
 
spoolDevAdmin           OBJECT-TYPE
        SYNTAX  DisplayString (SIZE (0..63))
        ACCESS  read-only
        STATUS  mandatory
        DESCRIPTION
                "Name of the printer administrator" 
        ::= { spoolDevTabEntry 13 }
 
spoolDevPcl             OBJECT-TYPE
        SYNTAX  DisplayString (SIZE (0..63))
        ACCESS  read-only
        STATUS  mandatory
        DESCRIPTION
                "Printer control language used by the printer" 
        ::= { spoolDevTabEntry 14 }
 
spoolDevDftForm         OBJECT-TYPE
        SYNTAX  DisplayString (SIZE (0..63))
        ACCESS  read-only
        STATUS  mandatory
        DESCRIPTION
                "The default form used by the printer" 
        ::= { spoolDevTabEntry 15 }
 
spoolDevSupervisor      OBJECT-TYPE
        SYNTAX  DisplayString (SIZE (0..63))
        ACCESS  read-only
        STATUS  mandatory
        DESCRIPTION
                "The supervisor of the printer" 
        ::= { spoolDevTabEntry 16 }
 
spoolDevAdmComment      OBJECT-TYPE
        SYNTAX  DisplayString (SIZE (0..255))
        ACCESS  read-write
        STATUS  mandatory
        DESCRIPTION
                "Comment for the administrator."
        ::= { spoolDevTabEntry 17 }
 
spoolDevUsrComment      OBJECT-TYPE
        SYNTAX  DisplayString (SIZE (0..255))
        ACCESS  read-only
        STATUS  mandatory
        DESCRIPTION
                "Comment for the user."
        ::= { spoolDevTabEntry 18 }
 
spoolDevEnablePoll      OBJECT-TYPE
        SYNTAX  INTEGER {
                        on (1),
                        off (2)
                }
        ACCESS  read-write
        STATUS  mandatory
        DESCRIPTION
                "Current state of the enable poll option,
                 it is either ON or OFF"
        ::= { spoolDevTabEntry 19 }
 
-- Server Table
 
spoolSrvTabNum          OBJECT-TYPE
        SYNTAX  INTEGER
        ACCESS  read-only
        STATUS  mandatory
        DESCRIPTION
                "The number of entries in the tabel spoolSrvTab"
        ::= { sniSpoolSrvTable 1 }
 
spoolSrvTab             OBJECT-TYPE
        SYNTAX  SEQUENCE OF SpoolSrvTabEntry
        ACCESS  not-accessible
        STATUS  mandatory
        DESCRIPTION
                "The spool server table"
        ::= { sniSpoolSrvTable 2 }
 
spoolSrvTabEntry        OBJECT-TYPE
        SYNTAX  SpoolSrvTabEntry
        ACCESS  not-accessible
        STATUS  mandatory
        DESCRIPTION
                "An entry in the server table"
        INDEX   { spoolSrvTabIndex }
        ::= { spoolSrvTab 1 }
 
-- The following table is an extract of two SPOOL data structures:
-- sta_sv_ext
--      which reports the current state of a server 
-- Xp_server
--      which holds the definition of a server object.
 
SpoolSrvTabEntry ::=
        SEQUENCE {
                spoolSrvTabIndex                INTEGER,
                spoolSrvName                    DisplayString,
                spoolSrvAdmin                   DisplayString,
                spoolSrvHost                    DisplayString,
                spoolSrvSchedPolicy             DisplayString,
                spoolSrvState                   INTEGER,
                spoolSrvSpoolin                 INTEGER,
                spoolSrvSpoolout                INTEGER,
                spoolSrvLoadLevel               INTEGER,
                spoolSrvMaxJobs                 INTEGER,
                spoolSrvWaitingJobs             INTEGER
        }
 
spoolSrvTabIndex        OBJECT-TYPE
        SYNTAX  INTEGER
        ACCESS  read-only
        STATUS  mandatory
        DESCRIPTION
                "A unique value for each entry, its value ranges between
                 1 and the value of spoolSrvTabNum"
        ::= { spoolSrvTabEntry 1 }
 
spoolSrvName            OBJECT-TYPE
        SYNTAX  DisplayString (SIZE (0..63))
        ACCESS  read-only
        STATUS  mandatory
        DESCRIPTION
                "A unique server identifier string"
        ::= { spoolSrvTabEntry 2 }
 
spoolSrvAdmin           OBJECT-TYPE
        SYNTAX  DisplayString (SIZE (0..63))
        ACCESS  read-only
        STATUS  mandatory
        DESCRIPTION
                "Name of the server's administrator"
        ::= { spoolSrvTabEntry 3 }
 
spoolSrvHost            OBJECT-TYPE
        SYNTAX  DisplayString (SIZE (0..63))
        ACCESS  read-only
        STATUS  mandatory
        DESCRIPTION
                "Name of the administrator's host"
        ::= { spoolSrvTabEntry 4 }
 
spoolSrvSchedPolicy     OBJECT-TYPE
        SYNTAX  DisplayString (SIZE (0..63))
        ACCESS  read-only
        STATUS  mandatory
        DESCRIPTION
                "Scheduling policy of the server"
        ::= { spoolSrvTabEntry 5 }
 
spoolSrvState           OBJECT-TYPE
        SYNTAX  INTEGER {
                        active (1),
                        inactive (2),
                        shutdown (3)
                }
        ACCESS  read-only
        STATUS  mandatory
        DESCRIPTION
                "The current state of the server, it has one of these
                values: ACTIVE, NOT_ACTIVE, SHUTDOWN"
        ::= { spoolSrvTabEntry 6 }
 
spoolSrvSpoolin         OBJECT-TYPE
        SYNTAX  INTEGER {
                        on (1),
                        off (2)
                }
        ACCESS  read-only
        STATUS  mandatory
        DESCRIPTION
                "Current state of the spoolin queue,
                it is either ON or OFF"
        ::= { spoolSrvTabEntry 7 }
 
spoolSrvSpoolout        OBJECT-TYPE
        SYNTAX  INTEGER {
                        on (1),
                        off (2)
                }
        ACCESS  read-only
        STATUS  mandatory
        DESCRIPTION
                "Current state of the spoolout queue,
                it is either ON or OFF"
        ::= { spoolSrvTabEntry 8 }
 
spoolSrvLoadLevel       OBJECT-TYPE
        SYNTAX  INTEGER (0..100)
        ACCESS  read-only
        STATUS  mandatory
        DESCRIPTION
                "Load level of the server"
        ::= { spoolSrvTabEntry 9 }
 
spoolSrvMaxJobs         OBJECT-TYPE
        SYNTAX  INTEGER (-1..4294967296)
        ACCESS  read-only
        STATUS  mandatory
        DESCRIPTION
                "Maximal allowed print jobs"
        ::= { spoolSrvTabEntry 10 }
 
spoolSrvWaitingJobs     OBJECT-TYPE
        SYNTAX  INTEGER (0..4294967296)
        ACCESS  read-only
        STATUS  mandatory
        DESCRIPTION
                "The number of waiting jobs"
        ::= { spoolSrvTabEntry 11 }
 
-- Supervisor Table
 
spoolSpvTabNum          OBJECT-TYPE
        SYNTAX  INTEGER
        ACCESS  read-only
        STATUS  mandatory
        DESCRIPTION
                "The number of entries in the tabel spoolSpvTab"
        ::= { sniSpoolSpvTable 1 }
 
spoolSpvTab             OBJECT-TYPE
        SYNTAX  SEQUENCE OF SpoolSpvTabEntry
        ACCESS  not-accessible
        STATUS  mandatory
        DESCRIPTION
                "The spool supervisor table"
        ::= { sniSpoolSpvTable 2 }
 
spoolSpvTabEntry        OBJECT-TYPE
        SYNTAX  SpoolSpvTabEntry
        ACCESS  not-accessible
        STATUS  mandatory
        DESCRIPTION
                "An entry in the supervisor table"
        INDEX   { spoolSpvTabIndex }
        ::= { spoolSpvTab 1 }
 
-- The following table is an extract of two SPOOL data structures:
-- sta_sp_ext
--      which reports the current state of a supervisor 
-- Xp_superv
--      which holds the definition of a supervisor object.
 
SpoolSpvTabEntry ::=
        SEQUENCE {
                spoolSpvTabIndex                INTEGER,
                spoolSpvName                    DisplayString,
                spoolSpvServName                DisplayString,
                spoolSpvAdmin                   DisplayString,
                spoolSpvHost                    DisplayString,
                spoolSpvState                   INTEGER
        }
 
spoolSpvTabIndex        OBJECT-TYPE
        SYNTAX  INTEGER
        ACCESS  read-only
        STATUS  mandatory
        DESCRIPTION
                "A unique value for each entry, its value ranges between
                 1 and the value of spoolSpvTabNum"
        ::= { spoolSpvTabEntry 1 }
 
spoolSpvName            OBJECT-TYPE
        SYNTAX  DisplayString (SIZE (0..63))
        ACCESS  read-only
        STATUS  mandatory
        DESCRIPTION
                "A unique supervisor identifier string"
        ::= { spoolSpvTabEntry 2 }
 
spoolSpvServName        OBJECT-TYPE
        SYNTAX  DisplayString (SIZE (0..63))
        ACCESS  read-only
        STATUS  mandatory
        DESCRIPTION
                "The name of the supervisor's server"
        ::= { spoolSpvTabEntry 3 }
 
spoolSpvAdmin           OBJECT-TYPE
        SYNTAX  DisplayString (SIZE (0..63))
        ACCESS  read-only
        STATUS  mandatory
        DESCRIPTION
                "Name of the supervisors's administrator"
        ::= { spoolSpvTabEntry 4 }
 
spoolSpvHost            OBJECT-TYPE
        SYNTAX  DisplayString (SIZE (0..63))
        ACCESS  read-only
        STATUS  mandatory
        DESCRIPTION
                "Name of the supervisors's host"
        ::= { spoolSpvTabEntry 5 }
 
spoolSpvState           OBJECT-TYPE
        SYNTAX  INTEGER {
                        active (1),
                        inactive (2),
                        shutdown (3)
                }
        ACCESS  read-only
        STATUS  mandatory
        DESCRIPTION
                "The current state of the supervisor, it has one of these
                values: ACTIVE, NOT_ACTIVE, SHUTDOWN"
        ::= { spoolSpvTabEntry 6 }
 
-- Device Group Table
 
spoolDgrTabNum          OBJECT-TYPE
        SYNTAX  INTEGER
        ACCESS  read-only
        STATUS  mandatory
        DESCRIPTION
                "The number of entries in the table spoolDgrTab"
        ::= { sniSpoolDgrTable 1 }
 
spoolDgrTab             OBJECT-TYPE
        SYNTAX  SEQUENCE OF SpoolDgrTabEntry
        ACCESS  not-accessible
        STATUS  mandatory
        DESCRIPTION
                "The spool device group table"
        ::= { sniSpoolDgrTable 2 }
 
spoolDgrTabEntry        OBJECT-TYPE
        SYNTAX  SpoolDgrTabEntry
        ACCESS  not-accessible
        STATUS  mandatory
        DESCRIPTION
                "An entry in the device group table"
        INDEX   { spoolDgrTabIndex }
        ::= { spoolDgrTab 1 }
 
-- The following table is an extract of two SPOOL data structures:
-- sta_dg_ext
--      which reports the current state of a device group 
-- Xp_dgroup
--      which holds the definition of a device group object.
 
SpoolDgrTabEntry ::=
        SEQUENCE {
                spoolDgrTabIndex                INTEGER,
                spoolDgrName                    DisplayString,
                spoolDgrAdmin                   DisplayString,
                spoolDgrDeviceList              DisplayString,
                spoolDgrSpoolin                 INTEGER,
                spoolDgrDate                    DisplayString,
                spoolDgrComment                 DisplayString
        }
 
spoolDgrTabIndex        OBJECT-TYPE
        SYNTAX  INTEGER
        ACCESS  read-only
        STATUS  mandatory
        DESCRIPTION
                "A unique value for each entry, its value ranges between
                 1 and the value of spoolDgrTabNum"
        ::= { spoolDgrTabEntry 1 }
 
spoolDgrName            OBJECT-TYPE
        SYNTAX  DisplayString (SIZE (0..63))
        ACCESS  read-only
        STATUS  mandatory
        DESCRIPTION
                "A unique device group identifier string"
        ::= { spoolDgrTabEntry 2 }
 
spoolDgrAdmin           OBJECT-TYPE
        SYNTAX  DisplayString (SIZE (0..63))
        ACCESS  read-only
        STATUS  mandatory
        DESCRIPTION
                "The name of the administrator of the device group"
        ::= { spoolDgrTabEntry 3 }
 
spoolDgrDeviceList      OBJECT-TYPE
        SYNTAX  DisplayString (SIZE (0..63))
        ACCESS  read-only
        STATUS  mandatory
        DESCRIPTION
                "The list of printer devices"
        ::= { spoolDgrTabEntry 4 }
 
spoolDgrSpoolin         OBJECT-TYPE
        SYNTAX  INTEGER {
                        on (1),
                        off (2)
                }
        ACCESS  read-only
        STATUS  mandatory
        DESCRIPTION
                "Current state of the spoolin queue,
                it is either ON or OFF"
        ::= { spoolDgrTabEntry 5 }
 
spoolDgrDate            OBJECT-TYPE
        SYNTAX  DisplayString (SIZE (0..63))
        ACCESS  read-only
        STATUS  mandatory
        DESCRIPTION
                "The date of the last state modification"
        ::= { spoolDgrTabEntry 6 }
 
spoolDgrComment         OBJECT-TYPE
        SYNTAX  DisplayString (SIZE (0..63))
        ACCESS  read-only
        STATUS  mandatory
        DESCRIPTION
                "Comment for the last state modification"
        ::= { spoolDgrTabEntry 7 }
 
-- Host/System Group Table
 
spoolHostTabNum         OBJECT-TYPE
        SYNTAX  INTEGER
        ACCESS  read-only
        STATUS  mandatory
        DESCRIPTION
                "The number of entries in the table spoolHostTab"
        ::= { sniSpoolHostTable 1 }
 
spoolHostTab            OBJECT-TYPE
        SYNTAX  SEQUENCE OF SpoolHostTabEntry
        ACCESS  not-accessible
        STATUS  mandatory
        DESCRIPTION
                "The spool host group table"
        ::= { sniSpoolHostTable 2 }
 
spoolHostTabEntry       OBJECT-TYPE
        SYNTAX  SpoolHostTabEntry
        ACCESS  not-accessible
        STATUS  mandatory
        DESCRIPTION
                "An entry in the host group table"
        INDEX   { spoolHostTabIndex }
        ::= { spoolHostTab 1 }
 
-- The following table is an extract of two SPOOL data structures:
-- sta_ho_ext
--      which reports the current state of a host
-- Xp_host
--      which holds the definition of a host object
-- Xp_sys
--      which holds the definition of a system object.
 
SpoolHostTabEntry ::=
        SEQUENCE {
                spoolHostTabIndex               INTEGER,
                spoolHostName                   DisplayString,
                spoolHostDestination            DisplayString,
                spoolHostSuppHost               DisplayString,
                spoolHostResponsibility         INTEGER,
                spoolHostState                  INTEGER
        }
 
spoolHostTabIndex       OBJECT-TYPE
        SYNTAX  INTEGER
        ACCESS  read-only
        STATUS  mandatory
        DESCRIPTION
                "A unique value for each entry, its value ranges between
                 1 and the value of spoolHostTabNum"
        ::= { spoolHostTabEntry 1 }
 
spoolHostName           OBJECT-TYPE
        SYNTAX  DisplayString (SIZE (0..63))
        ACCESS  read-only
        STATUS  mandatory
        DESCRIPTION
                "A unique host identifier string"
        ::= { spoolHostTabEntry 2 }
 
spoolHostDestination    OBJECT-TYPE
        SYNTAX  DisplayString (SIZE (0..63))
        ACCESS  read-only
        STATUS  mandatory
        DESCRIPTION
                "The name of the host's standard printer"
        ::= { spoolHostTabEntry 5 }
 
spoolHostSuppHost       OBJECT-TYPE
        SYNTAX  DisplayString (SIZE (0..63))
        ACCESS  read-only
        STATUS  mandatory
        DESCRIPTION
                "The name of the host which database is used
                 by this host (only for parasite hosts)"
        ::= { spoolHostTabEntry 6 }
 
spoolHostResponsibility OBJECT-TYPE
        SYNTAX  INTEGER {
                        potmaster (1),
                        slave (2),
                        parasite (3)
                }
        ACCESS  read-only
        STATUS  mandatory
        DESCRIPTION
                "The responsibility of the host."
        ::= { spoolHostTabEntry 7 }
 
spoolHostState          OBJECT-TYPE
        SYNTAX  INTEGER {
                        active (1),
                        activemaster (2),
                        inactive (3),
                        shutdown (4)
                }
        ACCESS  read-only
        STATUS  mandatory
        DESCRIPTION
                "The current state of the host, it has one of these
                values: ACTIVE, ACTIVE_MASTER, NOT_ACTIVE, SHUTDOWN"
        ::= { spoolHostTabEntry 8 }
 
-- Job Group Table
 
spoolJobTabNum          OBJECT-TYPE
        SYNTAX  INTEGER
        ACCESS  read-only
        STATUS  mandatory
        DESCRIPTION
                "The number of entries in the table spoolJobTab"
        ::= { sniSpoolJobTable 1 }
 
spoolJobTab             OBJECT-TYPE
        SYNTAX  SEQUENCE OF SpoolJobTabEntry
        ACCESS  not-accessible
        STATUS  mandatory
        DESCRIPTION
                "The spool host group table"
        ::= { sniSpoolJobTable 2 }
 
spoolJobTabEntry        OBJECT-TYPE
        SYNTAX  SpoolJobTabEntry
        ACCESS  not-accessible
        STATUS  mandatory
        DESCRIPTION
                "An entry in the job table"
        INDEX   { spoolJobTabIndex }
        ::= { spoolJobTab 1 }
 
-- The following table is an extract of two SPOOL data structures:
-- sta_jo_ext
--      which reports the current state of a job
-- Xp_job
--      which holds the definition of a job object
 
SpoolJobTabEntry ::=
        SEQUENCE {
                spoolJobTabIndex                INTEGER,
                spoolJobGlobalJid               DisplayString,
                spoolJobLocalJid                INTEGER,
                spoolJobTitle                   DisplayString,
                spoolJobComment                 DisplayString,
                spoolJobOriginator              DisplayString,
                spoolJobOrigHost                DisplayString,
                spoolJobOrigTime                DisplayString,
                spoolJobDestination             DisplayString,
                spoolJobPriority                INTEGER,
                spoolJobSecurityLevel           INTEGER,
                spoolJobFileList                DisplayString,
                spoolJobTotalSize               INTEGER,
                spoolJobRawMode                 INTEGER,
                spoolJobStartTime               DisplayString,
                spoolJobDelTime                 DisplayString,
                spoolJobRetTime                 INTEGER,
                spoolJobDevName                 DisplayString,
                spoolJobState                   INTEGER,
                spoolJobErrorMsg                DisplayString,
                spoolJobRank                    INTEGER,
                spoolJobRqCopies                INTEGER,
                spoolJobPrCopies                INTEGER,
                spoolJobPrPercent               INTEGER
        }
 
spoolJobTabIndex        OBJECT-TYPE
        SYNTAX  INTEGER
        ACCESS  read-only
        STATUS  mandatory
        DESCRIPTION
                "A unique value for each entry, its value ranges between
                 1 and the value of spoolJobTabNum"
        ::= { spoolJobTabEntry 1 }
 
spoolJobGlobalJid       OBJECT-TYPE
        SYNTAX  DisplayString (SIZE (0..63))
        ACCESS  read-only
        STATUS  mandatory
        DESCRIPTION
                "A unique (network-wide) job identifier string"
        ::= { spoolJobTabEntry 2 }
 
spoolJobLocalJid        OBJECT-TYPE
        SYNTAX  INTEGER (0..65535)
        ACCESS  read-only
        STATUS  mandatory
        DESCRIPTION
                "A unique (on local host) job identifier string"
        ::= { spoolJobTabEntry 3 }
 
spoolJobTitle           OBJECT-TYPE
        SYNTAX  DisplayString (SIZE (0..63))
        ACCESS  read-only
        STATUS  mandatory
        DESCRIPTION
                "Job title"
        ::= { spoolJobTabEntry 4 }
 
spoolJobComment         OBJECT-TYPE
        SYNTAX  DisplayString (SIZE (0..63))
        ACCESS  read-only
        STATUS  mandatory
        DESCRIPTION
                "Comment for the job"
        ::= { spoolJobTabEntry 5 }
 
spoolJobOriginator      OBJECT-TYPE
        SYNTAX  DisplayString (SIZE (0..63))
        ACCESS  read-only
        STATUS  mandatory
        DESCRIPTION
                "Originator of the job"
        ::= { spoolJobTabEntry 6 }
 
spoolJobOrigHost        OBJECT-TYPE
        SYNTAX  DisplayString (SIZE (0..63))
        ACCESS  read-only
        STATUS  mandatory
        DESCRIPTION
                "Origination host of the job"
        ::= { spoolJobTabEntry 7 }
 
spoolJobOrigTime        OBJECT-TYPE
        SYNTAX  DisplayString (SIZE (0..63))
        ACCESS  read-only
        STATUS  mandatory
        DESCRIPTION
                "Origination date/time of the job"
        ::= { spoolJobTabEntry 8 }
 
spoolJobDestination     OBJECT-TYPE
        SYNTAX  DisplayString (SIZE (0..63))
        ACCESS  read-write
        STATUS  mandatory
        DESCRIPTION
                "Destination device of the job"
        ::= { spoolJobTabEntry 9 }
 
spoolJobPriority        OBJECT-TYPE
        SYNTAX  INTEGER (0..65535)
        ACCESS  read-write
        STATUS  mandatory
        DESCRIPTION
                "Priority of the job"
        ::= { spoolJobTabEntry 10 }
 
spoolJobSecurityLevel   OBJECT-TYPE
        SYNTAX  INTEGER {
                        unclassified (1),
                        sensitive (2),
                        confidential (3),
                        secret (4),
                        topsecret (5)
                }
        ACCESS  read-only
        STATUS  mandatory
        DESCRIPTION
                "Security level of the job"
        ::= { spoolJobTabEntry 11 }
 
spoolJobFileList        OBJECT-TYPE
        SYNTAX  DisplayString (SIZE (0..63))
        ACCESS  read-only
        STATUS  mandatory
        DESCRIPTION
                "File list of the job"
        ::= { spoolJobTabEntry 12 }
 
spoolJobTotalSize       OBJECT-TYPE
        SYNTAX  INTEGER (0..4294967296)
        ACCESS  read-only
        STATUS  mandatory
        DESCRIPTION
                "Total size (in Bytes) of the job."
        ::= { spoolJobTabEntry 13 }
 
spoolJobRawMode         OBJECT-TYPE
        SYNTAX  INTEGER {
                        on (1),
                        off (2)
                }
        ACCESS  read-only
        STATUS  mandatory
        DESCRIPTION
                "Whether job is printed in raw mode."
        ::= { spoolJobTabEntry 14 }
 
spoolJobStartTime       OBJECT-TYPE
        SYNTAX  DisplayString (SIZE (0..63))
        ACCESS  read-only
        STATUS  mandatory
        DESCRIPTION
                "Start time of the job."
        ::= { spoolJobTabEntry 15 }
 
spoolJobDelTime         OBJECT-TYPE
        SYNTAX  DisplayString (SIZE (0..63))
        ACCESS  read-only
        STATUS  mandatory
        DESCRIPTION
                "Deletion time of the job."
        ::= { spoolJobTabEntry 16 }
 
spoolJobRetTime         OBJECT-TYPE
        SYNTAX  INTEGER (-1..4294967296)
        ACCESS  read-only
        STATUS  mandatory
        DESCRIPTION
                "Retention time of the job (in minutes)."
        ::= { spoolJobTabEntry 17 }
 
spoolJobDevName         OBJECT-TYPE
        SYNTAX  DisplayString (SIZE (0..63))
        ACCESS  read-only
        STATUS  mandatory
        DESCRIPTION
                "Actual device on which the job is printed."
        ::= { spoolJobTabEntry 18 }
 
spoolJobState           OBJECT-TYPE
        SYNTAX  INTEGER {
                        active (1),
                        wait (2),
                        suspend (3),
                        top (4),
                        data-filtering (5),
                        file-transfer (6),
                        error (7),
                        terminated (8),
                        interrupted (9),
                        cancel (10)
                }
        ACCESS  read-write
        STATUS  mandatory
        DESCRIPTION
                "State of the job."
        ::= { spoolJobTabEntry 19 }
 
spoolJobErrorMsg        OBJECT-TYPE
        SYNTAX  DisplayString (SIZE (0..63))
        ACCESS  read-only
        STATUS  mandatory
        DESCRIPTION
                "The error message in case of state == DEVICE_ERROR."
        ::= { spoolJobTabEntry 20 }
 
spoolJobRank            OBJECT-TYPE
        SYNTAX  INTEGER (0..65535)
        ACCESS  read-only
        STATUS  mandatory
        DESCRIPTION
                "Rank in the job queue."
        ::= { spoolJobTabEntry 21 }
 
spoolJobRqCopies        OBJECT-TYPE
        SYNTAX  INTEGER (0..65535)
        ACCESS  read-only
        STATUS  mandatory
        DESCRIPTION
                "Requested copies."
        ::= { spoolJobTabEntry 22 }
 
spoolJobPrCopies        OBJECT-TYPE
        SYNTAX  INTEGER (0..65535)
        ACCESS  read-only
        STATUS  mandatory
        DESCRIPTION
                "Printed copies."
        ::= { spoolJobTabEntry 23 }
 
spoolJobPrPercent       OBJECT-TYPE
        SYNTAX  INTEGER (0..65535)
        ACCESS  read-only
        STATUS  mandatory
        DESCRIPTION
                "Percent printed."
        ::= { spoolJobTabEntry 24 }
 
-- Dprint Group Table    (object group number 7 reserved for DPRINT objects
--                        by Mr. Tixhon, SWN EPSC1)
-- spoolDprintTabNum          OBJECT-TYPE
--         SYNTAX  INTEGER
--         ACCESS  read-only
--         STATUS  mandatory
--         DESCRIPTION
--                 "The number of entries in the table spoolDprintTab"
--         ::= { sniSpoolDprintTable 1 }
--
-- spoolDprintTab             OBJECT-TYPE
--         SYNTAX  SEQUENCE OF SpoolDprintTabEntry
--         ACCESS  not-accessible
--         STATUS  mandatory
--         DESCRIPTION
--                 "The spool host group table"
--         ::= { sniSpoolDprintTable 2 }
--
-- spoolDprintTabEntry        OBJECT-TYPE
--         SYNTAX  SpoolDprintTabEntry
--         ACCESS  not-accessible
--         STATUS  mandatory
--         DESCRIPTION
--                 "An entry in the Dprint table"
--         INDEX   { spoolDprintTabIndex }
--         ::= { spoolDprintTab 1 }
--
-- SpoolDprintTabEntry ::=
--         SEQUENCE {
--                 spoolDprintTabIndex                INTEGER,
--                 spoolDprintObj1                    DisplayString,
--                 spoolDprintObj2                    DisplayString
--         }
--
-- spoolDprintTabIndex        OBJECT-TYPE
--         SYNTAX  INTEGER
--         ACCESS  read-only
--         STATUS  mandatory
--         DESCRIPTION
--                 "A unique value for each entry, its value ranges between
--                  1 and the value of spoolDprintTabNum"
--         ::= { spoolDprintTabEntry 1 }
--
-- spoolDprintObj1       OBJECT-TYPE
--         SYNTAX  DisplayString (SIZE (0..63))
--         ACCESS  read-only
--         STATUS  mandatory
--         DESCRIPTION " "
--         ::= { spoolDprintTabEntry 2 }
--
-- spoolDprintObj2       OBJECT-TYPE
--         SYNTAX  DisplayString (SIZE (0..63))
--         ACCESS  read-only
--         STATUS  mandatory
--         DESCRIPTION " "
--         ::= { spoolDprintTabEntry 3 }
--
 
END
