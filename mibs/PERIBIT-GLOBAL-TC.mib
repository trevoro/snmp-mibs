PERIBIT-GLOBAL-TC DEFINITIONS ::= BEGIN

	IMPORTS
		MODULE-IDENTITY
			FROM SNMPv2-SMI
		TEXTUAL-CONVENTION
			FROM SNMPv2-TC
		pnModules
			FROM PERIBIT-GLOBAL-REG;

	pnGlobalTcModule MODULE-IDENTITY
		LAST-UPDATED			"200107292200Z"
		ORGANIZATION			"Peribit Networks, Inc"
		CONTACT-INFO			"
					Customer Support
					Peribit Networks, Inc.
					2300 Central Expressway
					Santa Clara, CA 95050

					+1 866-PERIBIT
					support@peribit.com"

		DESCRIPTION				"
			A MIB module containing textual conventions
			for Peribit Networks' enterprise MIB modules.
			These textual conventions are used across all Peribit products."

		REVISION				"200403151400Z"
		DESCRIPTION				"
			Add sr100 chassis type."

		REVISION				"200306262000Z"
		DESCRIPTION				"
			Add sr80 chassis type."

		REVISION				"200211071900Z"
		DESCRIPTION				"
			Add sr20 chassis type."

		REVISION				"200107292200Z"
		DESCRIPTION				"
			Rev 1.0
			Initial version of MIB module PERIBIT-GLOBAL-TC."

		::= { pnModules 2 }

	-- No Peribit textual conventions yet!

	TcAppName ::= TEXTUAL-CONVENTION
		DISPLAY-HINT			"64a"
		STATUS					current
		DESCRIPTION				"
			Represents the name of an application.

			This has all the restrictions of the DisplayString textual
			convention with the following additional ones:

			- Only the following characters/character ranges are allowed:
				0-9
				A-Z
				a-z
				:./#$&_-+()'
				<space>

			Any object defined using this syntax may not exceed 64
			characters in length."
		SYNTAX       OCTET STRING (SIZE (0..64))

	TcChassisType ::= TEXTUAL-CONVENTION
		STATUS					current
		DESCRIPTION				"
			Enumerates all possible chassis types for Peribit devices."
		SYNTAX
			INTEGER
			{
				pnOther(1),
				pnSr50(2),
				pnSr20(3),
				pnSr80(4),
				pnSr100(5),
				pnSm500(6),
				pnSr15(7)
			}
END

-- End - PERIBIT-GLOBAL-TC Module

-- ========================================================================
-- Start - PERIBIT-COMMON-MIB Module

-- MIB for the common MIB objects implemented by all
-- Peribit devices.
--
-- The convention described in "Understanding SNMP MIBs"
-- (David Perkins, Evan McGinnis), Chapter 8, has generally been followed.
