BAS-CHASSIS-MIB DEFINITIONS ::= BEGIN

IMPORTS
    MODULE-IDENTITY, OBJECT-TYPE,
    IpAddress, Integer32                FROM SNMPv2-SMI
    RowStatus, TruthValue, DateAndTime  FROM SNMPv2-TC
    basChassisInfo, BasChassisId,
    BasSlotId, BasInterfaceId,
    BasLogicalPortId, BasCardClass      FROM BAS-MIB;


basChassisInfoMib MODULE-IDENTITY
    LAST-UPDATED "9901180900Z"
    ORGANIZATION "Broadband Access Systems"
    CONTACT-INFO
        " Tech Support
          Broadband Access Systems
          201 Forest Street
          Marlboro, MA  01752
          U.S.A.
		  
          508-485-8200
          support@basystems.com"
    DESCRIPTION
        "This MIB module defines the Chassis Mib
         for a Broadband Access System Chassis cards."
    ::= { basChassisInfo 1 }


basChassisObjects       OBJECT IDENTIFIER ::= { basChassisInfoMib 1 }
basChassisDhcpRelayObjects OBJECT IDENTIFIER ::= { basChassisInfoMib 2 }
--
-- ----------------------------------------------------------------------
--
-- Bas Mgr Configuration Object
--
-- ----------------------------------------------------------------------
--

basChassisInfoTable OBJECT-TYPE
    SYNTAX      SEQUENCE OF BasChassisInfoEntry
    MAX-ACCESS  not-accessible
    STATUS      current
    DESCRIPTION
        "Info about this slot."
    ::= { basChassisObjects 1 }

basChassisInfoEntry OBJECT-TYPE
    SYNTAX		BasChassisInfoEntry
    MAX-ACCESS	not-accessible
    STATUS		current
    DESCRIPTION
        "Chassis and slot and Agent information."
    INDEX { basChassisInfoChassis, basChassisInfoSlot,
            basChassisInfoIf, basChassisInfoLPort }
    ::= { basChassisInfoTable 1 }

BasChassisInfoEntry ::=
    SEQUENCE {
        basChassisInfoChassis                   BasChassisId,
        basChassisInfoSlot                      BasSlotId,
        basChassisInfoIf                        BasInterfaceId,
        basChassisInfoLPort                     BasLogicalPortId,
        basChassisInfoChassisId                 BasChassisId,
        basChassisInfoClusterId                 Integer32,
        basChassisInfoLdapServerIpAddr          IpAddress,
        basChassisInfoLdapServerPort            INTEGER,
        basChassisInfoLdapServerUserName        OCTET STRING,
        basChassisInfoLdapServerPassword        OCTET STRING,
        basChassisInfoLdapServerEnable          INTEGER,
	basChassisIsProvisioningServer          TruthValue,
	basChassisIsProvServerOnThisChassis     TruthValue	
    }

basChassisInfoChassis OBJECT-TYPE
    SYNTAX      BasChassisId
    MAX-ACCESS  not-accessible
    STATUS      current
    DESCRIPTION
        "The BAS Chassis ID of this card."
    ::= { basChassisInfoEntry 1 }

basChassisInfoSlot OBJECT-TYPE
    SYNTAX      BasSlotId
    MAX-ACCESS  not-accessible
    STATUS      current
    DESCRIPTION
        "The BAS Slot ID of this card."
    ::= { basChassisInfoEntry 2 }

basChassisInfoIf OBJECT-TYPE
    SYNTAX      BasInterfaceId
    MAX-ACCESS  not-accessible
    STATUS      current
    DESCRIPTION
        "The BAS interface ID of this card."
    ::= { basChassisInfoEntry 3 }

basChassisInfoLPort OBJECT-TYPE
    SYNTAX      BasLogicalPortId
    MAX-ACCESS  not-accessible
    STATUS      current
    DESCRIPTION
        "The BAS logical port ID of this card."
    ::= { basChassisInfoEntry 4 }

basChassisInfoChassisId OBJECT-TYPE
    SYNTAX      BasChassisId
    MAX-ACCESS  read-write
    STATUS      current
    DESCRIPTION
        "The BAS Chassis ID."
    ::= { basChassisInfoEntry 5 }

basChassisInfoClusterId OBJECT-TYPE
    SYNTAX      Integer32
    MAX-ACCESS  read-write
    STATUS      current
    DESCRIPTION
        "The BAS Chassis ID."
    ::= { basChassisInfoEntry 6 }

basChassisInfoLdapServerIpAddr OBJECT-TYPE
    SYNTAX      IpAddress
    MAX-ACCESS  read-write
    STATUS      current
    DESCRIPTION
        "The LDAP Server IP Address Object"
    ::= { basChassisInfoEntry 7 }

basChassisInfoLdapServerPort OBJECT-TYPE
    SYNTAX      INTEGER(0..65535)
    MAX-ACCESS  read-write
    STATUS      current
    DESCRIPTION
        "The LDAP Server Port Object"
    ::= { basChassisInfoEntry 8 }

basChassisInfoLdapServerUserName OBJECT-TYPE
    SYNTAX      OCTET STRING (SIZE(0..255))
    MAX-ACCESS  read-write
    STATUS      current
    DESCRIPTION
        "The LDAP Server username Object"
    ::= { basChassisInfoEntry 9 }

basChassisInfoLdapServerPassword OBJECT-TYPE
    SYNTAX      OCTET STRING (SIZE(0..255))
    MAX-ACCESS  read-write
    STATUS      current
    DESCRIPTION
        "The LDAP Server Password Object"
    ::= { basChassisInfoEntry 10 }

basChassisInfoLdapServerEnable OBJECT-TYPE
    SYNTAX      INTEGER {
                        enable(1),
                        disable(2)
                        }
    MAX-ACCESS  read-write
    STATUS      current
    DESCRIPTION
        "The LDAP Server status Object"
    ::= { basChassisInfoEntry 11 }

basChassisIsProvisioningServer  OBJECT-TYPE
        SYNTAX      TruthValue
        MAX-ACCESS  read-create
        STATUS      current
        DESCRIPTION
            "Indicates whether the Provisioning Server is enabled
             or not."
        DEFVAL { false }
        ::= { basChassisInfoEntry 12 }

basChassisIsProvServerOnThisChassis  OBJECT-TYPE
        SYNTAX      TruthValue
        MAX-ACCESS  read-create
        STATUS      current
        DESCRIPTION
            "Indicates whether the Provisioning Server is on this
        chassis or not."
        DEFVAL { false }
        ::= { basChassisInfoEntry 13 }

basChassisManagerTable OBJECT-TYPE
    SYNTAX      SEQUENCE OF BasChassisManagerEntry
    MAX-ACCESS  not-accessible
    STATUS      current
    DESCRIPTION
        "Info about this slot."
    ::= { basChassisObjects 2 }

basChassisManagerEntry OBJECT-TYPE
    SYNTAX		BasChassisManagerEntry
    MAX-ACCESS	not-accessible
    STATUS		current
    DESCRIPTION
        "Chassis and slot and Agent Managerrmation."
    INDEX { basChassisManagerChassis, basChassisManagerSlot,
            basChassisManagerIf, basChassisManagerLPort }
	::= { basChassisManagerTable 1 }

BasChassisManagerEntry ::=
    SEQUENCE {
        basChassisManagerChassis                BasChassisId,
        basChassisManagerSlot                   BasSlotId,
        basChassisManagerIf                     BasInterfaceId,
        basChassisManagerLPort                  BasLogicalPortId,
        basChassisManagerAgentTcpPort           INTEGER,
        basChassisManagerPriority               INTEGER,
        basChassisManagerScope                  INTEGER,
	basChassisManagerDateAndTime		DateAndTime
    }

basChassisManagerChassis OBJECT-TYPE
    SYNTAX      BasChassisId
    MAX-ACCESS  not-accessible
    STATUS      current
    DESCRIPTION
        "The BAS Chassis ID of this card."
    ::= { basChassisManagerEntry 1 }

basChassisManagerSlot OBJECT-TYPE
    SYNTAX      BasSlotId
    MAX-ACCESS  not-accessible
    STATUS      current
    DESCRIPTION
        "The BAS Slot ID of this card."
    ::= { basChassisManagerEntry 2 }

basChassisManagerIf OBJECT-TYPE
    SYNTAX      BasInterfaceId
    MAX-ACCESS  not-accessible
    STATUS      current
    DESCRIPTION
        "The BAS interface ID of this card."
    ::= { basChassisManagerEntry 3 }

basChassisManagerLPort OBJECT-TYPE
    SYNTAX      BasLogicalPortId
    MAX-ACCESS  not-accessible
    STATUS      current
    DESCRIPTION
        "The BAS logical port ID of this card."
    ::= { basChassisManagerEntry 4 }

basChassisManagerAgentTcpPort OBJECT-TYPE
    SYNTAX      INTEGER(1..65535)
    MAX-ACCESS  read-write
    STATUS      current
    DESCRIPTION
        "The BAS Agentx Tcp Port Object"
    ::= { basChassisManagerEntry 5 }

basChassisManagerPriority OBJECT-TYPE
    SYNTAX      INTEGER {
                        primary(1),
                        secondary(2)
                        }
    MAX-ACCESS  read-write
    STATUS      current
    DESCRIPTION
        "The BAS Chassis manager priority Object"
    ::= { basChassisManagerEntry 6 }

basChassisManagerScope OBJECT-TYPE
    SYNTAX      INTEGER {
                        bca(1),
                        ca(2)
                        }
    MAX-ACCESS  read-write
    STATUS      current
    DESCRIPTION
        "The BAS Chassis manager Object"
    ::= { basChassisManagerEntry 7 }

basChassisManagerDateAndTime OBJECT-TYPE
    SYNTAX DateAndTime
    MAX-ACCESS read-only
    STATUS current
    DESCRIPTION
         "The BCM notion of the local date and time of
          day."
    ::= { basChassisManagerEntry 8}
 
-- the BAS Chassis DHCP Relay Server table

basChassisDhcpRelayServerTable OBJECT-TYPE
    SYNTAX      SEQUENCE OF BasChassisDhcpRelayServerEntry
    MAX-ACCESS  not-accessible
    STATUS      current
    DESCRIPTION
        "A list of DHCP Relay Server entries."
    ::= { basChassisDhcpRelayObjects 1 }

basChassisDhcpRelayServerEntry OBJECT-TYPE
    SYNTAX      BasChassisDhcpRelayServerEntry
    MAX-ACCESS  not-accessible
    STATUS      current
    DESCRIPTION
        "An entry containing management information applicable
        to a particular DHCP Relay Server."
    INDEX {basChassisDhcpRelayServerChassis,
	   basChassisDhcpRelayServerSlot,
	   basChassisDhcpRelayServerIf,
	   basChassisDhcpRelayServerLPort,
           basChassisDhcpRelayServerAddress,
	   basChassisDhcpRelayServerType	
           }
    ::= { basChassisDhcpRelayServerTable 1 }

BasChassisDhcpRelayServerEntry ::=
    SEQUENCE {
    basChassisDhcpRelayServerChassis	 BasChassisId,   
    basChassisDhcpRelayServerSlot	 BasSlotId,      
    basChassisDhcpRelayServerIf		 BasInterfaceId, 
    basChassisDhcpRelayServerLPort       BasLogicalPortId,
    basChassisDhcpRelayServerAddress     IpAddress,
    basChassisDhcpRelayServerType        INTEGER,
    basChassisDhcpRelayServerStatus      RowStatus
    }
    
    
basChassisDhcpRelayServerChassis OBJECT-TYPE
    SYNTAX		BasChassisId
    MAX-ACCESS	not-accessible
    STATUS		current
    DESCRIPTION
        "The BAS Chassis ID of the Card."
    ::= { basChassisDhcpRelayServerEntry 1 }

basChassisDhcpRelayServerSlot OBJECT-TYPE
    SYNTAX		BasSlotId
    MAX-ACCESS	not-accessible
    STATUS		current
    DESCRIPTION
        "The BAS Slot ID of the Card."
    ::= { basChassisDhcpRelayServerEntry 2 }

basChassisDhcpRelayServerIf OBJECT-TYPE
    SYNTAX		BasInterfaceId
    MAX-ACCESS	not-accessible
    STATUS		current
    DESCRIPTION
        "The BAS interface ID of the Card."
    ::= { basChassisDhcpRelayServerEntry 3 }

basChassisDhcpRelayServerLPort OBJECT-TYPE
    SYNTAX		BasLogicalPortId
    MAX-ACCESS	not-accessible
    STATUS		current
    DESCRIPTION
        "The BAS logical port ID of the Card."
    ::= { basChassisDhcpRelayServerEntry 4 }

basChassisDhcpRelayServerAddress OBJECT-TYPE
    SYNTAX      IpAddress 
    MAX-ACCESS  not-accessible
    STATUS      current
    DESCRIPTION
        "Address of DHCP Relay Server on this forwarder."
    DEFVAL {2}
    ::= { basChassisDhcpRelayServerEntry 5 }

basChassisDhcpRelayServerType OBJECT-TYPE
    SYNTAX      INTEGER {
		unauthorized(1),
                authorized(2),
                cablemodem(3)
                }
    MAX-ACCESS  not-accessible
    STATUS      current
    DESCRIPTION
        "Type of DHCP server. When picking a DHCP server, \
        choice is made depending on type."
    DEFVAL {1}
    ::= { basChassisDhcpRelayServerEntry 6 }

basChassisDhcpRelayServerStatus OBJECT-TYPE
    SYNTAX      RowStatus
    MAX-ACCESS  read-create
    STATUS      current
    DESCRIPTION
        "Adding and deleting the Server."
    DEFVAL {1}
    ::= { basChassisDhcpRelayServerEntry 7 }

--
-- ----------------------------------------------------------------------
--
-- End
--
-- ----------------------------------------------------------------------
--

END
