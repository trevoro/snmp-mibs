--			Ascend mibmgw MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBMGW-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmediaGatewayProfile  OBJECT IDENTIFIER ::= { configuration 170}

	-- The mibmediaGatewayProfile table
	--
	-- This table contains parameters for the mibmediaGatewayProfile profile
	--

    mibmediaGatewayProfileTable	OBJECT-TYPE
	SYNTAX		SEQUENCE OF MibmediaGatewayProfileEntry
	ACCESS		not-accessible
	STATUS		mandatory
	DESCRIPTION	"A list of mibmediaGatewayProfile profile entries."
	::= { mibmediaGatewayProfile 1 }

    mibmediaGatewayProfileEntry	OBJECT-TYPE
	SYNTAX		MibmediaGatewayProfileEntry
	ACCESS		not-accessible
	STATUS		mandatory
	DESCRIPTION	"A mibmediaGatewayProfile entry containing objects that
			 maps to the parameters of mibmediaGatewayProfile profile."
	INDEX		{ mediaGatewayProfile-Name }
	::= { mibmediaGatewayProfileTable 1 }

    MibmediaGatewayProfileEntry ::=
	SEQUENCE {
	    mediaGatewayProfile-Name
		DisplayString,
	    mediaGatewayProfile-Active
		INTEGER,
	    mediaGatewayProfile-ProtocolType
		INTEGER,
	    mediaGatewayProfile-MgSigAddress-Type
		INTEGER,
	    mediaGatewayProfile-MgSigAddress-IpAddress
		IpAddress,
	    mediaGatewayProfile-MgRtpAddress-Type
		INTEGER,
	    mediaGatewayProfile-MgRtpAddress-IpAddress
		IpAddress,
	    mediaGatewayProfile-H248Options-EncodingFormat
		INTEGER,
	    mediaGatewayProfile-H248Options-MaxResponseTime
		INTEGER,
	    mediaGatewayProfile-H248Options-Heartbeat-Enabled
		INTEGER,
	    mediaGatewayProfile-H248Options-Heartbeat-Interval
		INTEGER,
	    mediaGatewayProfile-H248Options-DigitmapOptions-StartTimer
		INTEGER,
	    mediaGatewayProfile-H248Options-DigitmapOptions-ShortTimer
		INTEGER,
	    mediaGatewayProfile-H248Options-DigitmapOptions-LongTimer
		INTEGER,
	    mediaGatewayProfile-IpdcOptions-BayId
		DisplayString,
	    mediaGatewayProfile-IpdcOptions-SystemType
		DisplayString,
	    mediaGatewayProfile-TransportOptions-Type
		INTEGER,
	    mediaGatewayProfile-VoipOptions-PacketAudioMode
		INTEGER,
	    mediaGatewayProfile-VoipOptions-FramesPerPacket
		INTEGER,
	    mediaGatewayProfile-VoipOptions-SilenceDetCng
		INTEGER,
	    mediaGatewayProfile-VoipOptions-EnaAdapJitterBuffer
		INTEGER,
	    mediaGatewayProfile-VoipOptions-MaxJitterBufferSize
		INTEGER,
	    mediaGatewayProfile-VoipOptions-InitialJitterBufferSize
		INTEGER,
	    mediaGatewayProfile-VoipOptions-VoiceAnnDir
		DisplayString,
	    mediaGatewayProfile-VoipOptions-VoiceAnnEnc
		INTEGER,
	    mediaGatewayProfile-VoipOptions-CallInterDigitTimeout
		INTEGER,
	    mediaGatewayProfile-VoipOptions-SilenceThreshold
		INTEGER,
	    mediaGatewayProfile-VoipOptions-DtmfTonePassing
		INTEGER,
	    mediaGatewayProfile-VoipOptions-Maxcalls
		INTEGER,
	    mediaGatewayProfile-VoipOptions-Rfc2833PayloadType
		INTEGER,
	    mediaGatewayProfile-VoipOptions-G711TransparentData
		INTEGER,
	    mediaGatewayProfile-VoipOptions-RtpProblemReporting-Enable
		INTEGER,
	    mediaGatewayProfile-VoipOptions-RtpProblemReporting-MultMediaRcptOkTime
		INTEGER,
	    mediaGatewayProfile-VoipOptions-RtpProblemReporting-NoMediaRcptOkTime
		INTEGER,
	    mediaGatewayProfile-DialedGwOptions-CallHairpin
		INTEGER,
	    mediaGatewayProfile-DialedGwOptions-TrunkQuiesce
		INTEGER,
	    mediaGatewayProfile-DialedGwOptions-TrunkPrefix
		INTEGER,
	    mediaGatewayProfile-DialedGwOptions-StartLocalRingTone
		INTEGER,
	    mediaGatewayProfile-DialedGwOptions-MediaWaitForConnect
		INTEGER,
	    mediaGatewayProfile-RtFaxOptions-RtFaxEnable
		INTEGER,
	    mediaGatewayProfile-RtFaxOptions-EcmEnable
		INTEGER,
	    mediaGatewayProfile-RtFaxOptions-LowLatencyMode
		INTEGER,
	    mediaGatewayProfile-RtFaxOptions-CommandSpoof
		INTEGER,
	    mediaGatewayProfile-RtFaxOptions-LocalRetransmitLsf
		INTEGER,
	    mediaGatewayProfile-RtFaxOptions-PacketRedundancy
		INTEGER,
	    mediaGatewayProfile-RtFaxOptions-FixedPackets
		INTEGER,
	    mediaGatewayProfile-RtFaxOptions-MaxDataRate
		INTEGER,
	    mediaGatewayProfile-RtFaxOptions-AllowCtc
		INTEGER,
	    mediaGatewayProfile-TosRtpOptions-Active
		INTEGER,
	    mediaGatewayProfile-TosRtpOptions-Precedence
		INTEGER,
	    mediaGatewayProfile-TosRtpOptions-TypeOfService
		INTEGER,
	    mediaGatewayProfile-TosRtpOptions-ApplyTo
		INTEGER,
	    mediaGatewayProfile-TosRtpOptions-MarkingType
		INTEGER,
	    mediaGatewayProfile-TosRtpOptions-Dscp
		DisplayString,
	    mediaGatewayProfile-TosSigOptions-Active
		INTEGER,
	    mediaGatewayProfile-TosSigOptions-Precedence
		INTEGER,
	    mediaGatewayProfile-TosSigOptions-TypeOfService
		INTEGER,
	    mediaGatewayProfile-TosSigOptions-ApplyTo
		INTEGER,
	    mediaGatewayProfile-TosSigOptions-MarkingType
		INTEGER,
	    mediaGatewayProfile-TosSigOptions-Dscp
		DisplayString,
	    mediaGatewayProfile-SipOptions-T1Timer
		INTEGER,
	    mediaGatewayProfile-SipOptions-T2Timer
		INTEGER,
	    mediaGatewayProfile-SipOptions-InviteRetries
		INTEGER,
	    mediaGatewayProfile-SipOptions-NonInviteRetries
		INTEGER,
	    mediaGatewayProfile-SipOptions-PrimaryProxy-IpAddress
		IpAddress,
	    mediaGatewayProfile-SipOptions-PrimaryProxy-Name
		DisplayString,
	    mediaGatewayProfile-SipOptions-PrimaryProxy-PortNumber
		INTEGER,
	    mediaGatewayProfile-SipOptions-PrimaryProxy-MessageFormat
		INTEGER,
	    mediaGatewayProfile-SipOptions-SecondaryProxy-IpAddress
		IpAddress,
	    mediaGatewayProfile-SipOptions-SecondaryProxy-Name
		DisplayString,
	    mediaGatewayProfile-SipOptions-SecondaryProxy-PortNumber
		INTEGER,
	    mediaGatewayProfile-SipOptions-SecondaryProxy-MessageFormat
		INTEGER,
	    mediaGatewayProfile-SipOptions-RegistrationProxy-IpAddress
		IpAddress,
	    mediaGatewayProfile-SipOptions-RegistrationProxy-Name
		DisplayString,
	    mediaGatewayProfile-SipOptions-RegistrationProxy-PortNumber
		INTEGER,
	    mediaGatewayProfile-SipOptions-RegistrationProxy-MessageFormat
		INTEGER,
	    mediaGatewayProfile-SipOptions-RegistrationProxy-RegisterInterval
		INTEGER,
	    mediaGatewayProfile-SipOptions-TrustedProxy-AuthenticateMessages
		INTEGER,
	    mediaGatewayProfile-SipOptions-UnknownAni
		DisplayString,
	    mediaGatewayProfile-SipOptions-BlockedAni
		DisplayString,
	    mediaGatewayProfile-SipOptions-PrivacyProxyRequire
		INTEGER,
	    mediaGatewayProfile-SipOptions-OnholdMinutes
		INTEGER,
	    mediaGatewayProfile-SipOptions-Support100rel
		INTEGER,
	    mediaGatewayProfile-SipOptions-Internationalize
		INTEGER,
	    mediaGatewayProfile-SipOptions-InternationalPrefix
		INTEGER,
	    mediaGatewayProfile-SipOptions-CountryCode
		DisplayString,
	    mediaGatewayProfile-SipOptions-NationalDestinationCode
		DisplayString,
	    mediaGatewayProfile-SipOptions-CallTransferMethod
		INTEGER,
	    mediaGatewayProfile-SipOptions-NotifyTimer
		INTEGER,
	    mediaGatewayProfile-Voip2ipOptions-DtmfTonePassing
		INTEGER,
	    mediaGatewayProfile-Voip2ipOptions-RtpTranslatorMode
		INTEGER,
	    mediaGatewayProfile-Voip2ipOptions-MaxNumErasures
		INTEGER,
	    mediaGatewayProfile-Voip2ipOptions-JitterBufferSize
		INTEGER,
	    mediaGatewayProfile-Action-o
		INTEGER
	}

    mediaGatewayProfile-Name	OBJECT-TYPE
	SYNTAX	DisplayString
	ACCESS	read-only
	STATUS	mandatory
	DESCRIPTION	"The name of the Media Gateway profile labels the MGC(s) that we are communicating with. Multiple MEDIA-GATEWAY profiles can be created if virtual media gateways are used. The name of the controlling media gateway should also be configured in the respective T1/E1 line profile(s)."
	::= { mibmediaGatewayProfileEntry 1 }

    mediaGatewayProfile-Active	OBJECT-TYPE
	SYNTAX	INTEGER {
		    no (1),
		    yes (2)
		}
	ACCESS	read-write
	STATUS	mandatory
	DESCRIPTION	"When set to 'no', interface to the Media Gateway MGC specified in this profile is disabled."
	::= { mibmediaGatewayProfileEntry 2 }

    mediaGatewayProfile-ProtocolType	OBJECT-TYPE
	SYNTAX	INTEGER {
		    h248 (1),
		    sip (3)
		}
	ACCESS	read-write
	STATUS	mandatory
	DESCRIPTION	"The type of the signaling protocol to use."
	::= { mibmediaGatewayProfileEntry 3 }

    mediaGatewayProfile-MgSigAddress-Type	OBJECT-TYPE
	SYNTAX	INTEGER {
		    systemDefault (1),
		    specific (2),
		    interfaceDependent (3)
		}
	ACCESS	read-write
	STATUS	mandatory
	DESCRIPTION	"Defines how the Media Gateway's source IP address is obtained."
	::= { mibmediaGatewayProfileEntry 4 }

    mediaGatewayProfile-MgSigAddress-IpAddress	OBJECT-TYPE
	SYNTAX	IpAddress
	ACCESS	read-write
	STATUS	mandatory
	DESCRIPTION	"MG's IP address to be used for signaling. Valid only if type=specific."
	::= { mibmediaGatewayProfileEntry 5 }

    mediaGatewayProfile-MgRtpAddress-Type	OBJECT-TYPE
	SYNTAX	INTEGER {
		    systemDefault (1),
		    specific (2),
		    interfaceDependent (3)
		}
	ACCESS	read-write
	STATUS	mandatory
	DESCRIPTION	"Defines how the Media Gateway's source IP address is obtained."
	::= { mibmediaGatewayProfileEntry 6 }

    mediaGatewayProfile-MgRtpAddress-IpAddress	OBJECT-TYPE
	SYNTAX	IpAddress
	ACCESS	read-write
	STATUS	mandatory
	DESCRIPTION	"MG's IP address to be used for signaling. Valid only if type=specific."
	::= { mibmediaGatewayProfileEntry 7 }

    mediaGatewayProfile-H248Options-EncodingFormat	OBJECT-TYPE
	SYNTAX	INTEGER {
		    text (1),
		    binary (2)
		}
	ACCESS	read-write
	STATUS	mandatory
	DESCRIPTION	"Protocol text or binary encoding. Only text encoding is supported currently."
	::= { mibmediaGatewayProfileEntry 8 }

    mediaGatewayProfile-H248Options-MaxResponseTime	OBJECT-TYPE
	SYNTAX	INTEGER
	ACCESS	read-write
	STATUS	mandatory
	DESCRIPTION	"Maximum response time value in milliseconds."
	::= { mibmediaGatewayProfileEntry 9 }

    mediaGatewayProfile-H248Options-Heartbeat-Enabled	OBJECT-TYPE
	SYNTAX	INTEGER {
		    no (1),
		    yes (2)
		}
	ACCESS	read-write
	STATUS	mandatory
	DESCRIPTION	"When set to yes, TNT will generate signaling heartbeat to MGC at the configured interval."
	::= { mibmediaGatewayProfileEntry 10 }

    mediaGatewayProfile-H248Options-Heartbeat-Interval	OBJECT-TYPE
	SYNTAX	INTEGER
	ACCESS	read-write
	STATUS	mandatory
	DESCRIPTION	"Time interval between heartbeat messages, in milliseconds."
	::= { mibmediaGatewayProfileEntry 11 }

    mediaGatewayProfile-H248Options-DigitmapOptions-StartTimer	OBJECT-TYPE
	SYNTAX	INTEGER
	ACCESS	read-write
	STATUS	mandatory
	DESCRIPTION	"DigitMap start timer in milliseconds"
	::= { mibmediaGatewayProfileEntry 12 }

    mediaGatewayProfile-H248Options-DigitmapOptions-ShortTimer	OBJECT-TYPE
	SYNTAX	INTEGER
	ACCESS	read-write
	STATUS	mandatory
	DESCRIPTION	"DigitMap short timer in milliseconds"
	::= { mibmediaGatewayProfileEntry 13 }

    mediaGatewayProfile-H248Options-DigitmapOptions-LongTimer	OBJECT-TYPE
	SYNTAX	INTEGER
	ACCESS	read-write
	STATUS	mandatory
	DESCRIPTION	"DigitMap long timer in milliseconds"
	::= { mibmediaGatewayProfileEntry 14 }

    mediaGatewayProfile-IpdcOptions-BayId	OBJECT-TYPE
	SYNTAX	DisplayString
	ACCESS	read-write
	STATUS	mandatory
	DESCRIPTION	"Bay ID defines the bay this device belongs to. Used for registration purposes only. The content of this field is reported to the gateway during the device registration process."
	::= { mibmediaGatewayProfileEntry 15 }

    mediaGatewayProfile-IpdcOptions-SystemType	OBJECT-TYPE
	SYNTAX	DisplayString
	ACCESS	read-write
	STATUS	mandatory
	DESCRIPTION	"Model ID and/or type of equipment. Used for device registration only. Must be listed in the database on the Gateway."
	::= { mibmediaGatewayProfileEntry 16 }

    mediaGatewayProfile-TransportOptions-Type	OBJECT-TYPE
	SYNTAX	INTEGER {
		    tcp (1),
		    udp (2)
		}
	ACCESS	read-write
	STATUS	mandatory
	DESCRIPTION	"Transport layer to be used for signaling traffic. H248 supports TCP/TPKT and SIP uses UDP."
	::= { mibmediaGatewayProfileEntry 17 }

    mediaGatewayProfile-VoipOptions-PacketAudioMode	OBJECT-TYPE
	SYNTAX	INTEGER {
		    g711Ulaw (1),
		    g711Alaw (2),
		    g723 (3),
		    g729 (4),
		    g72364kps (5),
		    rt24 (6),
		    g728 (7),
		    frgsm (8)
		}
	ACCESS	read-write
	STATUS	mandatory
	DESCRIPTION	"Audio Coder to be used for voice packetization."
	::= { mibmediaGatewayProfileEntry 18 }

    mediaGatewayProfile-VoipOptions-FramesPerPacket	OBJECT-TYPE
	SYNTAX	INTEGER
	ACCESS	read-write
	STATUS	mandatory
	DESCRIPTION	"Voice Frames Per RTP Packet. One (1) through four (4) are valid values but must be two (2) if packet audio mode was set to one of the flavors of G.711."
	::= { mibmediaGatewayProfileEntry 19 }

    mediaGatewayProfile-VoipOptions-SilenceDetCng	OBJECT-TYPE
	SYNTAX	INTEGER {
		    no (1),
		    yes (2),
		    cngOnly (3)
		}
	ACCESS	read-write
	STATUS	mandatory
	DESCRIPTION	"Silence Detection and Comfort Noise Generation selection."
	::= { mibmediaGatewayProfileEntry 20 }

    mediaGatewayProfile-VoipOptions-EnaAdapJitterBuffer	OBJECT-TYPE
	SYNTAX	INTEGER {
		    no (1),
		    yes (2)
		}
	ACCESS	read-write
	STATUS	mandatory
	DESCRIPTION	"Enable Adaptive Jtr Buf"
	::= { mibmediaGatewayProfileEntry 21 }

    mediaGatewayProfile-VoipOptions-MaxJitterBufferSize	OBJECT-TYPE
	SYNTAX	INTEGER
	ACCESS	read-write
	STATUS	mandatory
	DESCRIPTION	"Max Jtr Buf Size"
	::= { mibmediaGatewayProfileEntry 22 }

    mediaGatewayProfile-VoipOptions-InitialJitterBufferSize	OBJECT-TYPE
	SYNTAX	INTEGER
	ACCESS	read-write
	STATUS	mandatory
	DESCRIPTION	"Initial Jtr Buf Size"
	::= { mibmediaGatewayProfileEntry 23 }

    mediaGatewayProfile-VoipOptions-VoiceAnnDir	OBJECT-TYPE
	SYNTAX	DisplayString
	ACCESS	read-write
	STATUS	mandatory
	DESCRIPTION	"Pc Flash Card Voice Announcement Directory"
	::= { mibmediaGatewayProfileEntry 24 }

    mediaGatewayProfile-VoipOptions-VoiceAnnEnc	OBJECT-TYPE
	SYNTAX	INTEGER {
		    g711Ulaw (1),
		    g729 (4)
		}
	ACCESS	read-write
	STATUS	mandatory
	DESCRIPTION	"Voice announcement file encoding"
	::= { mibmediaGatewayProfileEntry 25 }

    mediaGatewayProfile-VoipOptions-CallInterDigitTimeout	OBJECT-TYPE
	SYNTAX	INTEGER
	ACCESS	read-write
	STATUS	mandatory
	DESCRIPTION	"Inter Digit Timeout"
	::= { mibmediaGatewayProfileEntry 26 }

    mediaGatewayProfile-VoipOptions-SilenceThreshold	OBJECT-TYPE
	SYNTAX	INTEGER
	ACCESS	read-write
	STATUS	mandatory
	DESCRIPTION	"Silence Thresh (dB inc)"
	::= { mibmediaGatewayProfileEntry 27 }

    mediaGatewayProfile-VoipOptions-DtmfTonePassing	OBJECT-TYPE
	SYNTAX	INTEGER {
		    inband (1),
		    outofband (2),
		    rtp (3)
		}
	ACCESS	read-write
	STATUS	mandatory
	DESCRIPTION	"DTMF Tone Passing"
	::= { mibmediaGatewayProfileEntry 28 }

    mediaGatewayProfile-VoipOptions-Maxcalls	OBJECT-TYPE
	SYNTAX	INTEGER
	ACCESS	read-write
	STATUS	mandatory
	DESCRIPTION	"Maximum Voip Calls"
	::= { mibmediaGatewayProfileEntry 29 }

    mediaGatewayProfile-VoipOptions-Rfc2833PayloadType	OBJECT-TYPE
	SYNTAX	INTEGER
	ACCESS	read-write
	STATUS	mandatory
	DESCRIPTION	"Value to assign to payload type for rfc2833 used for rtp transport of DTMF tones."
	::= { mibmediaGatewayProfileEntry 30 }

    mediaGatewayProfile-VoipOptions-G711TransparentData	OBJECT-TYPE
	SYNTAX	INTEGER {
		    no (1),
		    yes (2)
		}
	ACCESS	read-write
	STATUS	mandatory
	DESCRIPTION	"G711 Transparent Fax/Data"
	::= { mibmediaGatewayProfileEntry 31 }

    mediaGatewayProfile-VoipOptions-RtpProblemReporting-Enable	OBJECT-TYPE
	SYNTAX	INTEGER {
		    no (1),
		    yes (2)
		}
	ACCESS	read-write
	STATUS	mandatory
	DESCRIPTION	"Enable/Disable RTP (potential) problem detection and reporting."
	::= { mibmediaGatewayProfileEntry 87 }

    mediaGatewayProfile-VoipOptions-RtpProblemReporting-MultMediaRcptOkTime	OBJECT-TYPE
	SYNTAX	INTEGER
	ACCESS	read-write
	STATUS	mandatory
	DESCRIPTION	"(1-65535 seconds) Maximum time allowed to recive multiple rtp streams and still not consider it rogue."
	::= { mibmediaGatewayProfileEntry 88 }

    mediaGatewayProfile-VoipOptions-RtpProblemReporting-NoMediaRcptOkTime	OBJECT-TYPE
	SYNTAX	INTEGER
	ACCESS	read-write
	STATUS	mandatory
	DESCRIPTION	"(1-65535 seconds) A message will be generated if no rtp was received in this time. The consecutive reporting time will be exponential."
	::= { mibmediaGatewayProfileEntry 89 }

    mediaGatewayProfile-DialedGwOptions-CallHairpin	OBJECT-TYPE
	SYNTAX	INTEGER {
		    disabled (1),
		    enabled (2)
		}
	ACCESS	read-write
	STATUS	mandatory
	DESCRIPTION	"Hairpin call (ingress)"
	::= { mibmediaGatewayProfileEntry 32 }

    mediaGatewayProfile-DialedGwOptions-TrunkQuiesce	OBJECT-TYPE
	SYNTAX	INTEGER {
		    disabled (1),
		    enabled (2)
		}
	ACCESS	read-write
	STATUS	mandatory
	DESCRIPTION	"Trunk Quiesce (ingress)"
	::= { mibmediaGatewayProfileEntry 33 }

    mediaGatewayProfile-DialedGwOptions-TrunkPrefix	OBJECT-TYPE
	SYNTAX	INTEGER {
		    disabled (1),
		    enabled (2)
		}
	ACCESS	read-write
	STATUS	mandatory
	DESCRIPTION	"Apply Trunk prefix to DNIS. For egress trunk selection."
	::= { mibmediaGatewayProfileEntry 34 }

    mediaGatewayProfile-DialedGwOptions-StartLocalRingTone	OBJECT-TYPE
	SYNTAX	INTEGER {
		    ringToneOnAlerting (1),
		    ringToneOnFirstMessage (2),
		    ringToneOnCallProgress (3)
		}
	ACCESS	read-write
	STATUS	mandatory
	DESCRIPTION	"When to start local ring tone (ingress)."
	::= { mibmediaGatewayProfileEntry 35 }

    mediaGatewayProfile-DialedGwOptions-MediaWaitForConnect	OBJECT-TYPE
	SYNTAX	INTEGER {
		    disabled (1),
		    enabled (2)
		}
	ACCESS	read-write
	STATUS	mandatory
	DESCRIPTION	"Start media flow after Q931 connect message (egress - for SIP 200 message)."
	::= { mibmediaGatewayProfileEntry 36 }

    mediaGatewayProfile-RtFaxOptions-RtFaxEnable	OBJECT-TYPE
	SYNTAX	INTEGER {
		    no (1),
		    yes (2)
		}
	ACCESS	read-write
	STATUS	mandatory
	DESCRIPTION	"Enable/Disable the Real-Time Fax Feature."
	::= { mibmediaGatewayProfileEntry 37 }

    mediaGatewayProfile-RtFaxOptions-EcmEnable	OBJECT-TYPE
	SYNTAX	INTEGER {
		    no (1),
		    yes (2)
		}
	ACCESS	read-write
	STATUS	mandatory
	DESCRIPTION	"Enable/Disable Error Correction Mode."
	::= { mibmediaGatewayProfileEntry 38 }

    mediaGatewayProfile-RtFaxOptions-LowLatencyMode	OBJECT-TYPE
	SYNTAX	INTEGER {
		    no (1),
		    yes (2)
		}
	ACCESS	read-write
	STATUS	mandatory
	DESCRIPTION	"Enable/Disable Low Latency Mode."
	::= { mibmediaGatewayProfileEntry 39 }

    mediaGatewayProfile-RtFaxOptions-CommandSpoof	OBJECT-TYPE
	SYNTAX	INTEGER {
		    no (1),
		    yes (2)
		}
	ACCESS	read-write
	STATUS	mandatory
	DESCRIPTION	"Enable/Disable a particular T.30 command spoof."
	::= { mibmediaGatewayProfileEntry 40 }

    mediaGatewayProfile-RtFaxOptions-LocalRetransmitLsf	OBJECT-TYPE
	SYNTAX	INTEGER {
		    no (1),
		    yes (2)
		}
	ACCESS	read-write
	STATUS	mandatory
	DESCRIPTION	"Enable/Disable local low speed frame retransmission"
	::= { mibmediaGatewayProfileEntry 41 }

    mediaGatewayProfile-RtFaxOptions-PacketRedundancy	OBJECT-TYPE
	SYNTAX	INTEGER
	ACCESS	read-write
	STATUS	mandatory
	DESCRIPTION	"UDP Packet Redundancy."
	::= { mibmediaGatewayProfileEntry 42 }

    mediaGatewayProfile-RtFaxOptions-FixedPackets	OBJECT-TYPE
	SYNTAX	INTEGER {
		    no (1),
		    yes (2)
		}
	ACCESS	read-write
	STATUS	mandatory
	DESCRIPTION	"Use fixed size image data packets"
	::= { mibmediaGatewayProfileEntry 43 }

    mediaGatewayProfile-RtFaxOptions-MaxDataRate	OBJECT-TYPE
	SYNTAX	INTEGER {
		    n-2400 (2401),
		    n-4800 (4801),
		    n-9600 (9601),
		    n-14400 (14401)
		}
	ACCESS	read-write
	STATUS	mandatory
	DESCRIPTION	"Maximum Negotiated Data Rate"
	::= { mibmediaGatewayProfileEntry 44 }

    mediaGatewayProfile-RtFaxOptions-AllowCtc	OBJECT-TYPE
	SYNTAX	INTEGER {
		    no (1),
		    yes (2)
		}
	ACCESS	read-write
	STATUS	mandatory
	DESCRIPTION	"Enable extended ECM correction beyond four retransmissions"
	::= { mibmediaGatewayProfileEntry 45 }

    mediaGatewayProfile-TosRtpOptions-Active	OBJECT-TYPE
	SYNTAX	INTEGER {
		    no (1),
		    yes (2)
		}
	ACCESS	read-write
	STATUS	mandatory
	DESCRIPTION	"Activate type of service for this connection."
	::= { mibmediaGatewayProfileEntry 46 }

    mediaGatewayProfile-TosRtpOptions-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibmediaGatewayProfileEntry 47 }

    mediaGatewayProfile-TosRtpOptions-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibmediaGatewayProfileEntry 48 }

    mediaGatewayProfile-TosRtpOptions-ApplyTo	OBJECT-TYPE
	SYNTAX	INTEGER {
		    incoming (1025),
		    outgoing (2049),
		    both (3073)
		}
	ACCESS	read-write
	STATUS	mandatory
	DESCRIPTION	"Define how the type-of-service applies to data flow for this connection."
	::= { mibmediaGatewayProfileEntry 49 }

    mediaGatewayProfile-TosRtpOptions-MarkingType	OBJECT-TYPE
	SYNTAX	INTEGER {
		    precedenceTos (1),
		    dscp (2)
		}
	ACCESS	read-write
	STATUS	mandatory
	DESCRIPTION	"Select type of packet marking."
	::= { mibmediaGatewayProfileEntry 50 }

    mediaGatewayProfile-TosRtpOptions-Dscp	OBJECT-TYPE
	SYNTAX	DisplayString
	ACCESS	read-write
	STATUS	mandatory
	DESCRIPTION	"DSCP tag to be used in marking of the packets (if marking-type = dscp)."
	::= { mibmediaGatewayProfileEntry 51 }

    mediaGatewayProfile-TosSigOptions-Active	OBJECT-TYPE
	SYNTAX	INTEGER {
		    no (1),
		    yes (2)
		}
	ACCESS	read-write
	STATUS	mandatory
	DESCRIPTION	"Activate type of service for this connection."
	::= { mibmediaGatewayProfileEntry 90 }

    mediaGatewayProfile-TosSigOptions-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibmediaGatewayProfileEntry 91 }

    mediaGatewayProfile-TosSigOptions-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibmediaGatewayProfileEntry 92 }

    mediaGatewayProfile-TosSigOptions-ApplyTo	OBJECT-TYPE
	SYNTAX	INTEGER {
		    incoming (1025),
		    outgoing (2049),
		    both (3073)
		}
	ACCESS	read-write
	STATUS	mandatory
	DESCRIPTION	"Define how the type-of-service applies to data flow for this connection."
	::= { mibmediaGatewayProfileEntry 93 }

    mediaGatewayProfile-TosSigOptions-MarkingType	OBJECT-TYPE
	SYNTAX	INTEGER {
		    precedenceTos (1),
		    dscp (2)
		}
	ACCESS	read-write
	STATUS	mandatory
	DESCRIPTION	"Select type of packet marking."
	::= { mibmediaGatewayProfileEntry 94 }

    mediaGatewayProfile-TosSigOptions-Dscp	OBJECT-TYPE
	SYNTAX	DisplayString
	ACCESS	read-write
	STATUS	mandatory
	DESCRIPTION	"DSCP tag to be used in marking of the packets (if marking-type = dscp)."
	::= { mibmediaGatewayProfileEntry 95 }

    mediaGatewayProfile-SipOptions-T1Timer	OBJECT-TYPE
	SYNTAX	INTEGER
	ACCESS	read-write
	STATUS	mandatory
	DESCRIPTION	"T1 timer value in milliseconds."
	::= { mibmediaGatewayProfileEntry 52 }

    mediaGatewayProfile-SipOptions-T2Timer	OBJECT-TYPE
	SYNTAX	INTEGER
	ACCESS	read-write
	STATUS	mandatory
	DESCRIPTION	"T2 timer value in milliseconds."
	::= { mibmediaGatewayProfileEntry 53 }

    mediaGatewayProfile-SipOptions-InviteRetries	OBJECT-TYPE
	SYNTAX	INTEGER
	ACCESS	read-write
	STATUS	mandatory
	DESCRIPTION	"Number of invite retries."
	::= { mibmediaGatewayProfileEntry 54 }

    mediaGatewayProfile-SipOptions-NonInviteRetries	OBJECT-TYPE
	SYNTAX	INTEGER
	ACCESS	read-write
	STATUS	mandatory
	DESCRIPTION	"Number of non-invite retries."
	::= { mibmediaGatewayProfileEntry 55 }

    mediaGatewayProfile-SipOptions-PrimaryProxy-IpAddress	OBJECT-TYPE
	SYNTAX	IpAddress
	ACCESS	read-write
	STATUS	mandatory
	DESCRIPTION	"IP addr of primary proxy."
	::= { mibmediaGatewayProfileEntry 56 }

    mediaGatewayProfile-SipOptions-PrimaryProxy-Name	OBJECT-TYPE
	SYNTAX	DisplayString
	ACCESS	read-write
	STATUS	mandatory
	DESCRIPTION	"Domain name of primary proxy"
	::= { mibmediaGatewayProfileEntry 57 }

    mediaGatewayProfile-SipOptions-PrimaryProxy-PortNumber	OBJECT-TYPE
	SYNTAX	INTEGER
	ACCESS	read-write
	STATUS	mandatory
	DESCRIPTION	"Primary proxy TCP/UDP port number."
	::= { mibmediaGatewayProfileEntry 58 }

    mediaGatewayProfile-SipOptions-PrimaryProxy-MessageFormat	OBJECT-TYPE
	SYNTAX	INTEGER {
		    compact (1),
		    long (2)
		}
	ACCESS	read-write
	STATUS	mandatory
	DESCRIPTION	"Proxy message format"
	::= { mibmediaGatewayProfileEntry 59 }

    mediaGatewayProfile-SipOptions-SecondaryProxy-IpAddress	OBJECT-TYPE
	SYNTAX	IpAddress
	ACCESS	read-write
	STATUS	mandatory
	DESCRIPTION	"IP addr of secondary proxy."
	::= { mibmediaGatewayProfileEntry 60 }

    mediaGatewayProfile-SipOptions-SecondaryProxy-Name	OBJECT-TYPE
	SYNTAX	DisplayString
	ACCESS	read-write
	STATUS	mandatory
	DESCRIPTION	"Domain name of secondary proxy"
	::= { mibmediaGatewayProfileEntry 61 }

    mediaGatewayProfile-SipOptions-SecondaryProxy-PortNumber	OBJECT-TYPE
	SYNTAX	INTEGER
	ACCESS	read-write
	STATUS	mandatory
	DESCRIPTION	"Secondary proxy TCP/UDP port number."
	::= { mibmediaGatewayProfileEntry 62 }

    mediaGatewayProfile-SipOptions-SecondaryProxy-MessageFormat	OBJECT-TYPE
	SYNTAX	INTEGER {
		    compact (1),
		    long (2)
		}
	ACCESS	read-write
	STATUS	mandatory
	DESCRIPTION	"Proxy message format"
	::= { mibmediaGatewayProfileEntry 63 }

    mediaGatewayProfile-SipOptions-RegistrationProxy-IpAddress	OBJECT-TYPE
	SYNTAX	IpAddress
	ACCESS	read-write
	STATUS	mandatory
	DESCRIPTION	"IP addr of registration proxy."
	::= { mibmediaGatewayProfileEntry 64 }

    mediaGatewayProfile-SipOptions-RegistrationProxy-Name	OBJECT-TYPE
	SYNTAX	DisplayString
	ACCESS	read-write
	STATUS	mandatory
	DESCRIPTION	"Domain name of registration proxy"
	::= { mibmediaGatewayProfileEntry 65 }

    mediaGatewayProfile-SipOptions-RegistrationProxy-PortNumber	OBJECT-TYPE
	SYNTAX	INTEGER
	ACCESS	read-write
	STATUS	mandatory
	DESCRIPTION	"Registration proxy TCP/UDP port number."
	::= { mibmediaGatewayProfileEntry 66 }

    mediaGatewayProfile-SipOptions-RegistrationProxy-MessageFormat	OBJECT-TYPE
	SYNTAX	INTEGER {
		    compact (1),
		    long (2)
		}
	ACCESS	read-write
	STATUS	mandatory
	DESCRIPTION	"Proxy message format"
	::= { mibmediaGatewayProfileEntry 67 }

    mediaGatewayProfile-SipOptions-RegistrationProxy-RegisterInterval	OBJECT-TYPE
	SYNTAX	INTEGER
	ACCESS	read-write
	STATUS	mandatory
	DESCRIPTION	"Time, in minutes, between requests (0 = disabled)."
	::= { mibmediaGatewayProfileEntry 68 }

    mediaGatewayProfile-SipOptions-TrustedProxy-AuthenticateMessages	OBJECT-TYPE
	SYNTAX	INTEGER {
		    disabled (1),
		    enabled (2)
		}
	ACCESS	read-write
	STATUS	mandatory
	DESCRIPTION	"Enable SIP authentication"
	::= { mibmediaGatewayProfileEntry 69 }

    mediaGatewayProfile-SipOptions-UnknownAni	OBJECT-TYPE
	SYNTAX	DisplayString
	ACCESS	read-write
	STATUS	mandatory
	DESCRIPTION	"Unknown ANI string"
	::= { mibmediaGatewayProfileEntry 70 }

    mediaGatewayProfile-SipOptions-BlockedAni	OBJECT-TYPE
	SYNTAX	DisplayString
	ACCESS	read-write
	STATUS	mandatory
	DESCRIPTION	"Unknown ANI string"
	::= { mibmediaGatewayProfileEntry 71 }

    mediaGatewayProfile-SipOptions-PrivacyProxyRequire	OBJECT-TYPE
	SYNTAX	INTEGER {
		    disabled (1),
		    enabled (2)
		}
	ACCESS	read-write
	STATUS	mandatory
	DESCRIPTION	"Include Proxy Require header for Remote Party privacy for INVITEs"
	::= { mibmediaGatewayProfileEntry 96 }

    mediaGatewayProfile-SipOptions-OnholdMinutes	OBJECT-TYPE
	SYNTAX	INTEGER
	ACCESS	read-write
	STATUS	mandatory
	DESCRIPTION	"Minutes to wait before a call on hold will disconnect. (range 0 to 1440)"
	::= { mibmediaGatewayProfileEntry 72 }

    mediaGatewayProfile-SipOptions-Support100rel	OBJECT-TYPE
	SYNTAX	INTEGER {
		    disabled (1),
		    enabled (2)
		}
	ACCESS	read-write
	STATUS	mandatory
	DESCRIPTION	"Enable support for SIP 100rel reliable responses"
	::= { mibmediaGatewayProfileEntry 73 }

    mediaGatewayProfile-SipOptions-Internationalize	OBJECT-TYPE
	SYNTAX	INTEGER {
		    no (1),
		    yes (2)
		}
	ACCESS	read-write
	STATUS	mandatory
	DESCRIPTION	"Enable Internationalization of phone number URIs. When set to yes, uses international-prefix, country-code, and national-destination-code settings for prefixes to phone, number URIs depending on TON setting in Q.931 setup."
	::= { mibmediaGatewayProfileEntry 74 }

    mediaGatewayProfile-SipOptions-InternationalPrefix	OBJECT-TYPE
	SYNTAX	INTEGER {
		    no (1),
		    yes (2)
		}
	ACCESS	read-write
	STATUS	mandatory
	DESCRIPTION	"When set to yes, will prepend + to phone number URIs for all Q.931 TON settings of International. When internationalization is set to yes, will also prepend to TON settings of National and Subscriber."
	::= { mibmediaGatewayProfileEntry 75 }

    mediaGatewayProfile-SipOptions-CountryCode	OBJECT-TYPE
	SYNTAX	DisplayString
	ACCESS	read-write
	STATUS	mandatory
	DESCRIPTION	"Country Code prepended to SIP URIs. Valid when internationalize = yes and trunk groups are not enabled or not provisioned."
	::= { mibmediaGatewayProfileEntry 76 }

    mediaGatewayProfile-SipOptions-NationalDestinationCode	OBJECT-TYPE
	SYNTAX	DisplayString
	ACCESS	read-write
	STATUS	mandatory
	DESCRIPTION	"National Destination code prepended to SIP URIs. Valid when internationalize = yes and trunk groups are not enabled or not provisioned."
	::= { mibmediaGatewayProfileEntry 77 }

    mediaGatewayProfile-SipOptions-CallTransferMethod	OBJECT-TYPE
	SYNTAX	INTEGER {
		    ipTransfer (1),
		    pstnTransfer (2)
		}
	ACCESS	read-write
	STATUS	mandatory
	DESCRIPTION	"Type of call transfer invoked by receipt of REFER request"
	::= { mibmediaGatewayProfileEntry 97 }

    mediaGatewayProfile-SipOptions-NotifyTimer	OBJECT-TYPE
	SYNTAX	INTEGER
	ACCESS	read-write
	STATUS	mandatory
	DESCRIPTION	"Seconds to wait before a call will disconnect after sending a NOTIFY request if no response is received. (range 0 to 600) Set notify-timer to zero to disable."
	::= { mibmediaGatewayProfileEntry 98 }

    mediaGatewayProfile-Voip2ipOptions-DtmfTonePassing	OBJECT-TYPE
	SYNTAX	INTEGER {
		    inband (1),
		    outofband (2),
		    rtp (3)
		}
	ACCESS	read-write
	STATUS	mandatory
	DESCRIPTION	"DTMF Tone Passing."
	::= { mibmediaGatewayProfileEntry 99 }

    mediaGatewayProfile-Voip2ipOptions-RtpTranslatorMode	OBJECT-TYPE
	SYNTAX	INTEGER
	ACCESS	read-write
	STATUS	mandatory
	DESCRIPTION	"RTP translator mode. In mode 0 the WAG acts as a strict RTP translator with no jitter buffer. In mode 1 the WAG acts as a RTP translator with a configurable jitter buffer."
	::= { mibmediaGatewayProfileEntry 100 }

    mediaGatewayProfile-Voip2ipOptions-MaxNumErasures	OBJECT-TYPE
	SYNTAX	INTEGER
	ACCESS	read-write
	STATUS	mandatory
	DESCRIPTION	"Maximum number of erasure frames that the WAG will generate when it encounters lost or late packets."
	::= { mibmediaGatewayProfileEntry 101 }

    mediaGatewayProfile-Voip2ipOptions-JitterBufferSize	OBJECT-TYPE
	SYNTAX	INTEGER
	ACCESS	read-write
	STATUS	mandatory
	DESCRIPTION	"The size of the WAG Jitter buffer - only applicable to rtp-translator-mode 1."
	::= { mibmediaGatewayProfileEntry 102 }

    mediaGatewayProfile-Action-o	OBJECT-TYPE
	SYNTAX	INTEGER {
		    noAction (1),
		    createProfile (2),
		    deleteProfile (3)
		}
	ACCESS	read-write
	STATUS	mandatory
	DESCRIPTION	""
	::= { mibmediaGatewayProfileEntry 78 }


	-- The mibmediaGatewayProfile__sip_options__trusted_proxy__table table
	--
	-- This table contains parameters for the mibmediaGatewayProfile__sip_options__trusted_proxy__table profile
	--

    mibmediaGatewayProfile-SipOptions-TrustedProxy-TableTable	OBJECT-TYPE
	SYNTAX		SEQUENCE OF MibmediaGatewayProfile-SipOptions-TrustedProxy-TableEntry
	ACCESS		not-accessible
	STATUS		mandatory
	DESCRIPTION	"A list of mibmediaGatewayProfile__sip_options__trusted_proxy__table profile entries."
	::= { mibmediaGatewayProfile 2 }

    mibmediaGatewayProfile-SipOptions-TrustedProxy-TableEntry	OBJECT-TYPE
	SYNTAX		MibmediaGatewayProfile-SipOptions-TrustedProxy-TableEntry
	ACCESS		not-accessible
	STATUS		mandatory
	DESCRIPTION	"A mibmediaGatewayProfile__sip_options__trusted_proxy__table entry containing objects that
			 maps to the parameters of mibmediaGatewayProfile__sip_options__trusted_proxy__table profile."
	INDEX		{ mediaGatewayProfile-SipOptions-TrustedProxy-Table-Name, mediaGatewayProfile-SipOptions-TrustedProxy-Table-Index-o }
	::= { mibmediaGatewayProfile-SipOptions-TrustedProxy-TableTable 1 }

    MibmediaGatewayProfile-SipOptions-TrustedProxy-TableEntry ::=
	SEQUENCE {
	    mediaGatewayProfile-SipOptions-TrustedProxy-Table-Name
		DisplayString,
	    mediaGatewayProfile-SipOptions-TrustedProxy-Table-Index-o
		INTEGER,
	    mediaGatewayProfile-SipOptions-TrustedProxy-Table-HostName
		DisplayString,
	    mediaGatewayProfile-SipOptions-TrustedProxy-Table-IpAddress
		IpAddress
	}

    mediaGatewayProfile-SipOptions-TrustedProxy-Table-Name	OBJECT-TYPE
	SYNTAX	DisplayString
	ACCESS	read-only
	STATUS	mandatory
	DESCRIPTION	""
	::= { mibmediaGatewayProfile-SipOptions-TrustedProxy-TableEntry 1 }

    mediaGatewayProfile-SipOptions-TrustedProxy-Table-Index-o	OBJECT-TYPE
	SYNTAX	INTEGER
	ACCESS	read-only
	STATUS	mandatory
	DESCRIPTION	""
	::= { mibmediaGatewayProfile-SipOptions-TrustedProxy-TableEntry 2 }

    mediaGatewayProfile-SipOptions-TrustedProxy-Table-HostName	OBJECT-TYPE
	SYNTAX	DisplayString
	ACCESS	read-write
	STATUS	mandatory
	DESCRIPTION	"SIP proxy host name."
	::= { mibmediaGatewayProfile-SipOptions-TrustedProxy-TableEntry 3 }

    mediaGatewayProfile-SipOptions-TrustedProxy-Table-IpAddress	OBJECT-TYPE
	SYNTAX	IpAddress
	ACCESS	read-write
	STATUS	mandatory
	DESCRIPTION	"SIP proxy host IP address."
	::= { mibmediaGatewayProfile-SipOptions-TrustedProxy-TableEntry 4 }


	-- The mibmediaGatewayProfile__h248_options__digitmap_options__map table
	--
	-- This table contains parameters for the mibmediaGatewayProfile__h248_options__digitmap_options__map profile
	--

    mibmediaGatewayProfile-H248Options-DigitmapOptions-MapTable	OBJECT-TYPE
	SYNTAX		SEQUENCE OF MibmediaGatewayProfile-H248Options-DigitmapOptions-MapEntry
	ACCESS		not-accessible
	STATUS		mandatory
	DESCRIPTION	"A list of mibmediaGatewayProfile__h248_options__digitmap_options__map profile entries."
	::= { mibmediaGatewayProfile 3 }

    mibmediaGatewayProfile-H248Options-DigitmapOptions-MapEntry	OBJECT-TYPE
	SYNTAX		MibmediaGatewayProfile-H248Options-DigitmapOptions-MapEntry
	ACCESS		not-accessible
	STATUS		mandatory
	DESCRIPTION	"A mibmediaGatewayProfile__h248_options__digitmap_options__map entry containing objects that
			 maps to the parameters of mibmediaGatewayProfile__h248_options__digitmap_options__map profile."
	INDEX		{ mediaGatewayProfile-H248Options-DigitmapOptions-Map-Name, mediaGatewayProfile-H248Options-DigitmapOptions-Map-Index-o }
	::= { mibmediaGatewayProfile-H248Options-DigitmapOptions-MapTable 1 }

    MibmediaGatewayProfile-H248Options-DigitmapOptions-MapEntry ::=
	SEQUENCE {
	    mediaGatewayProfile-H248Options-DigitmapOptions-Map-Name
		DisplayString,
	    mediaGatewayProfile-H248Options-DigitmapOptions-Map-Index-o
		INTEGER,
	    mediaGatewayProfile-H248Options-DigitmapOptions-Map-ReferenceName
		DisplayString,
	    mediaGatewayProfile-H248Options-DigitmapOptions-Map-Value
		DisplayString
	}

    mediaGatewayProfile-H248Options-DigitmapOptions-Map-Name	OBJECT-TYPE
	SYNTAX	DisplayString
	ACCESS	read-only
	STATUS	mandatory
	DESCRIPTION	""
	::= { mibmediaGatewayProfile-H248Options-DigitmapOptions-MapEntry 1 }

    mediaGatewayProfile-H248Options-DigitmapOptions-Map-Index-o	OBJECT-TYPE
	SYNTAX	INTEGER
	ACCESS	read-only
	STATUS	mandatory
	DESCRIPTION	""
	::= { mibmediaGatewayProfile-H248Options-DigitmapOptions-MapEntry 2 }

    mediaGatewayProfile-H248Options-DigitmapOptions-Map-ReferenceName	OBJECT-TYPE
	SYNTAX	DisplayString
	ACCESS	read-write
	STATUS	mandatory
	DESCRIPTION	"The reference name of the digitmap."
	::= { mibmediaGatewayProfile-H248Options-DigitmapOptions-MapEntry 3 }

    mediaGatewayProfile-H248Options-DigitmapOptions-Map-Value	OBJECT-TYPE
	SYNTAX	DisplayString
	ACCESS	read-write
	STATUS	mandatory
	DESCRIPTION	"The value of the digitmap. Since | is treated as a special symbol for the command line interface, use ! as the separator in the digitmap value, i.e. 0!00![1-7]xxx!8xxx!Exx!9011x."
	::= { mibmediaGatewayProfile-H248Options-DigitmapOptions-MapEntry 4 }


	-- The mibmediaGatewayProfile__mgc_address table
	--
	-- This table contains parameters for the mibmediaGatewayProfile__mgc_address profile
	--

    mibmediaGatewayProfile-MgcAddressTable	OBJECT-TYPE
	SYNTAX		SEQUENCE OF MibmediaGatewayProfile-MgcAddressEntry
	ACCESS		not-accessible
	STATUS		mandatory
	DESCRIPTION	"A list of mibmediaGatewayProfile__mgc_address profile entries."
	::= { mibmediaGatewayProfile 4 }

    mibmediaGatewayProfile-MgcAddressEntry	OBJECT-TYPE
	SYNTAX		MibmediaGatewayProfile-MgcAddressEntry
	ACCESS		not-accessible
	STATUS		mandatory
	DESCRIPTION	"A mibmediaGatewayProfile__mgc_address entry containing objects that
			 maps to the parameters of mibmediaGatewayProfile__mgc_address profile."
	INDEX		{ mediaGatewayProfile-MgcAddress-Name, mediaGatewayProfile-MgcAddress-Index-o }
	::= { mibmediaGatewayProfile-MgcAddressTable 1 }

    MibmediaGatewayProfile-MgcAddressEntry ::=
	SEQUENCE {
	    mediaGatewayProfile-MgcAddress-Name
		DisplayString,
	    mediaGatewayProfile-MgcAddress-Index-o
		INTEGER,
	    mediaGatewayProfile-MgcAddress-Vrouter
		DisplayString,
	    mediaGatewayProfile-MgcAddress-IpAddress
		IpAddress,
	    mediaGatewayProfile-MgcAddress-PortNumber
		INTEGER
	}

    mediaGatewayProfile-MgcAddress-Name	OBJECT-TYPE
	SYNTAX	DisplayString
	ACCESS	read-only
	STATUS	mandatory
	DESCRIPTION	""
	::= { mibmediaGatewayProfile-MgcAddressEntry 1 }

    mediaGatewayProfile-MgcAddress-Index-o	OBJECT-TYPE
	SYNTAX	INTEGER
	ACCESS	read-only
	STATUS	mandatory
	DESCRIPTION	""
	::= { mibmediaGatewayProfile-MgcAddressEntry 2 }

    mediaGatewayProfile-MgcAddress-Vrouter	OBJECT-TYPE
	SYNTAX	DisplayString
	ACCESS	read-write
	STATUS	mandatory
	DESCRIPTION	"Vrouter the Media Gateway Controller is reachable through. Leave empty if global vrouter is used."
	::= { mibmediaGatewayProfile-MgcAddressEntry 3 }

    mediaGatewayProfile-MgcAddress-IpAddress	OBJECT-TYPE
	SYNTAX	IpAddress
	ACCESS	read-write
	STATUS	mandatory
	DESCRIPTION	"Media Gateway Controller's IP address."
	::= { mibmediaGatewayProfile-MgcAddressEntry 4 }

    mediaGatewayProfile-MgcAddress-PortNumber	OBJECT-TYPE
	SYNTAX	INTEGER
	ACCESS	read-write
	STATUS	mandatory
	DESCRIPTION	"Media Gateway Controller's TCP/UDP port number."
	::= { mibmediaGatewayProfile-MgcAddressEntry 5 }

END
