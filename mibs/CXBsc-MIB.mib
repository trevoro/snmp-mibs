CXBsc-MIB DEFINITIONS ::= BEGIN

IMPORTS
	Counter, TimeTicks	FROM  RFC1155-SMI
	OBJECT-TYPE		FROM  RFC-1212
	cxBsc, SapIndex, Alias
				FROM  CXProduct-SMI;

-- Proprietary   Data Types

--  Global Constants

BscCuIndex           ::= INTEGER  (0..64)
BscDevIndex          ::= INTEGER  (0..127)

BscRowStatus    ::= INTEGER     {                               
      invalid (1),
      valid   (2)
      }

BscAckMode  ::= INTEGER {                               -- a command could be acknowledged either
      endToEnd        (1),                                       -- local or remote.
      local                 (2)
      }

BscOperationalMode  ::=   INTEGER {
      offline   (1),
      online    (2)
      }

BscBlockSize   ::= INTEGER {
	block128                (1),
         	block256                (2),
         	block512                (3),
         	block1k                  (4),
         	block2k                  (5),
         	block3000              (6),
         	block5k                  (7)
	 }	


BscStatusSense  ::= INTEGER {
	notSet		(1),
	isSet		(2)
	}


bscSapTable     			OBJECT-TYPE
       	SYNTAX           		SEQUENCE OF BscSapEntry
       	ACCESS    		not-accessible
       	STATUS            		mandatory
       	DESCRIPTION
     		"A table  containing configuration information
		about all the service access point. "
       	::= { cxBsc 10 }


bscSapEntry     			OBJECT-TYPE
     	SYNTAX   		BscSapEntry
     	ACCESS    		not-accessible
     	STATUS    		mandatory
     	DESCRIPTION
          		"The parameters for a particular service access   
    		point."
     	INDEX     { 
               		bscSapNumber 
               	    }
    	::= { bscSapTable 1 }


BscSapEntry ::=
        	SEQUENCE {
-- Parameters
   	bscSapNumber      		SapIndex,
   	bscSapRowStatus               	BscRowStatus,
   	bscSapType                  		INTEGER,
   	bscSapInterfaceType    		INTEGER,
   	bscSapAlias                  		Alias,
   	bscSapCompanionAlias 		Alias,
    	bscSapSnalcRef			INTEGER,
   	bscPollIntAfterAckTimer  	TimeTicks,
-- Control
   	bscSapControl              		INTEGER,
-- Status
   	bscSapOperationalMode   		BscOperationalMode,
	bscSapLinkStatus			INTEGER,
-- Statistics
	bscSapLinkChange		Counter,
   	bscSapOverrun            		Counter,
   	bscSapParityError         		Counter,
	bscSapCrcError            		Counter,
   	bscSapBlockReject         		Counter
}


 -- The Objects for the Service Access Point Configuration Table
 bscSapNumber       		OBJECT-TYPE
     	SYNTAX            		SapIndex
     	ACCESS        		read-only
     	STATUS        		mandatory
     	DESCRIPTION
   		"Identifies  the  service  access   point   by   a
          		numerical  value.  This value is used as a index 
   		in the saps table. Values are unique  per  service
          		access point."
   	::= { bscSapEntry 1 }


 bscSapRowStatus 		OBJECT-TYPE
     	SYNTAX        		BscRowStatus
     	ACCESS    		read-write
     	STATUS    		mandatory
     	DESCRIPTION
          		"Indicates  whether the particular service  access
          		point is configured within the MIB.
   		Service access point entries (rows) may be created
          		by  setting  this  object  value  to  'valid',  or
          		deleted   by   changing  this  object   value   to
          		'invalid'.   Whether  or  not  the  row   actually
          		disappears is left to the implementation  so  this
          		object  may  actually read as 'invalid'  for  some
          		arbitrary length of time."
     	::= { bscSapEntry 2 }


bscSapType 			OBJECT-TYPE
	SYNTAX		INTEGER {
					lower	(1),
					upper 	(2)
				}
	ACCESS		read-write
	STATUS		mandatory
	DESCRIPTION
		"Identifies the service access point by type:'lower'
		identifies a SAP leading to a physical BSC port. 
		'Upper' 	identifies a SAP acting as an internal 
		inter-layer logical port."
	DEFVAL		{ lower }
	::={ bscSapEntry 3 }










bscSapInterfaceType 		OBJECT-TYPE
     	SYNTAX   		INTEGER      {
					terminalInterfaceUnit   (1),
					hostInterfaceUnit          (2)
            				}
     	ACCESS    		read-write
     	STATUS    		mandatory
     	DESCRIPTION
          		"Identifies  the  type of controller: either TIU or HIU."
     	DEFVAL  		{ terminalInterfaceUnit }
     	::= { bscSapEntry 4 }


bscSapAlias     			OBJECT-TYPE
     	SYNTAX    		Alias
     	ACCESS    		read-write
     	STATUS    		mandatory
     	DESCRIPTION
          		"Identifies the service access point by a  textual
          		name. Names are unique per service access point."
     	::= { bscSapEntry 5}


bscSapCompanionAlias 		OBJECT-TYPE
     	SYNTAX    		Alias
     	ACCESS    		read-write
     	STATUS    		mandatory
     	DESCRIPTION
          		"Identifies the  `lower' service access  point  that
          		will communicate with this service access point by
          		a textual name.
          		Names are unique per service access point. Used to
          		bind the BSC Sap with the COP driver sap."
     	::= { bscSapEntry 6 }


bscSapSnalcRef 			OBJECT-TYPE
	SYNTAX		INTEGER  (0..8)
	ACCESS		read-write
	STATUS		mandatory
	DESCRIPTION
		"Identifies which upper sap is associated to the lower
		sap within the BSC module. Applies only to lower BSC saps."
	::={ bscSapEntry 7 }










bscPollIntAfterAckTimer 		OBJECT-TYPE
     	SYNTAX    		TimeTicks
     	ACCESS    		read-write
     	STATUS    		mandatory
     	DESCRIPTION
		"This object applies only to a service access point 
		functioning as a TIU. 
		Determines the length of time allowed to elapse between 
		the reception of an acknowledgment to a poll and the 
		transmission of the next poll. Certain control units require 
		a delay in order to successfully respond to polls.

		Since multiple BSC logical links may share the same 
		SAP (i.e., multiple control units communicating on the 
		same physical link), this timer applies globally to all 
		logical links using this SAP. 

		Range of values: 1 - 250 (in tenths of a second), a value of
		0 disables the timer. "
	DEFVAL {0}
     	::= { bscSapEntry 8 }

-- gap (11) to gap (19) for future Parameters
-- Control


bscSapControl   			OBJECT-TYPE
       	SYNTAX            		INTEGER        
					{
         					clearStats      (1)
				            	}
       	ACCESS    		write-only
       	STATUS            		mandatory
       	DESCRIPTION
       		"Control associated with the specified service access point."
       	::= { bscSapEntry  20 }


-- gap (21) to gap (29) for future Parameters
-- States & Statuses


bscSapOperationalMode 		OBJECT-TYPE
     	SYNTAX                	BscOperationalMode
     	ACCESS        		read-only
     	STATUS                 	mandatory
     	DESCRIPTION
          		"Identifies the service access point as being
          		active or non-active with the new configuration."
     	::={ bscSapEntry  30}


bscSapLinkStatus 		OBJECT-TYPE
	SYNTAX		INTEGER {
					down		(1),
					up		(2)
					}
	ACCESS		read-only
	STATUS		mandatory
	DESCRIPTION
		"Indicates the physical status of the sap with respect to its associated cop."
	::={ bscSapEntry 31 }


-- gap (32) to gap (39) for future Parameters
-- Statistics


bscSapLinkChange 		OBJECT-TYPE
	SYNTAX		Counter
	ACCESS		read-only
	STATUS		mandatory
	DESCRIPTION
		"Indicates the number of times the physical link has been brought up."
	::= { bscSapEntry  40 }

bscSapOverrun	 		OBJECT-TYPE
       	SYNTAX    		Counter        
       	ACCESS    		read-only
       	STATUS            		mandatory
       	DESCRIPTION
		"Identifies the number of block overrun's received by this 
		sap." 
       	::= { bscSapEntry  41 }     
   

bscSapParityError		OBJECT-TYPE
       	SYNTAX    		Counter        
       	ACCESS    		read-only
       	STATUS            		mandatory
       	DESCRIPTION
		"Identifies the number of blocks received with parity errors."
	::= { bscSapEntry  42 }     


bscSapCrcError	 		OBJECT-TYPE
       	SYNTAX    		Counter        
       	ACCESS    		read-only
       	STATUS            		mandatory
       	DESCRIPTION
		"Identifies the number of  blocks with CRC errors."  
	::= { bscSapEntry  43 }


bscSapBlockReject		OBJECT-TYPE
       	SYNTAX    		Counter        
       	ACCESS    		read-only
       	STATUS            		mandatory
       	DESCRIPTION
		"Identifies the number of blocks received whose frame size is greater than that configured."
       	::= { bscSapEntry  44 }


--  3270 Controller Unit Family Configuration Table
--      A sap could control several 3270 controller units (CU)
--      parameters required to configure the link service access point
--      controls available to manipulate the 3270 controller units family


bscCuTable  			OBJECT-TYPE
   	SYNTAX          		SEQUENCE OF BscCuEntry
   	ACCESS   		not-accessible
   	STATUS           		mandatory
    	DESCRIPTION
     		"A  table  containing configuration information 
		 about all the 3270 controller units."
   	::= { cxBsc 11 }


bscCuEntry  			OBJECT-TYPE
     	SYNTAX    		BscCuEntry
     	ACCESS    		not-accessible
     	STATUS    		mandatory
     	DESCRIPTION
          		"The parameters for a particular controller unit."       
     	INDEX  {
		bscCuSapNumber,
		bscCuNumber 
		}
     	::= { bscCuTable 1 }


BscCuEntry ::=
     	SEQUENCE {
-- Parameters
	bscCuSapNumber              	SapIndex,
   	bscCuNumber			BscCuIndex,
	bscCuRowStatus              		BscRowStatus,   
     	bscCuHwdType                		INTEGER,
	bscCuMaxBlockLength 		BscBlockSize,
	bscCuPollTimeout           		INTEGER,
	bscCuDelayTimer		INTEGER,
	bscCuRetryCounter  		INTEGER,
	bscCuETBAck                 		BscAckMode,
	bscCuETXAck                 		BscAckMode,
-- Control
	bscCuControl              		INTEGER,
-- Status
   	bscCuOperationalMode  		BscOperationalMode,
	bscCuConnectionStatus		INTEGER,
-- Statistics
	bscCuConnectRequest		Counter,
	bscCuDisconnectRequest		Counter,
	bscCuDisconnectIndication	Counter,
	bscCuEndToEndConnectCnf	Counter,
	bscCuSnalcRxRnr		Counter,
	bscCuSnalcRxRr			Counter
   }
   

-- The Objects for the Service Access Point Configuration Table
-- Parameters        











bscCuSapNumber      		OBJECT-TYPE
     	SYNTAX                	SapIndex
     	ACCESS        		read-only
     	STATUS                 	mandatory
     	DESCRIPTION
   		"Identifies  the sap associated with this controller
		unit. Each controller unit has an address and the address 
     		has to be unique with one sap. However, the address is 
		not required to be unique between saps. This object is an
		index in the sap Table. Values are unique."
     	::= { bscCuEntry 1 }


bscCuNumber          		OBJECT-TYPE      
     	SYNTAX          		BscCuIndex       
     	ACCESS          		read-only
     	STATUS          		mandatory
     	DESCRIPTION
		"Identifies the address of this controller unit.
		 The address has to be unique for a specified sap."
	::= { bscCuEntry 2 }


bscCuRowStatus      		OBJECT-TYPE
     	SYNTAX   		BscRowStatus
     	ACCESS    		read-write
     	STATUS    		mandatory
     	DESCRIPTION
          		"Indicates  whether the particular service  access
          		point is configured within the MIB.
		Controller unit  entries (rows) may be created
          		by  setting  this  object  value  to  'valid',  or
          		deleted   by   changing  this  object   value   to
          		'invalid'.   Whether  or  not  the  row   actually
          		disappears is left to the implementation  so  this
          		object  may  actually read as 'invalid'  for  some
          		arbitrary length of time."
     	::= { bscCuEntry 3 }


bscCuHwdType  			OBJECT-TYPE
     	SYNTAX  		INTEGER       {
      					cu3271          (1),
      					cu3274          (2),
      					cu3275          (3),
      					cu3276          (4),
      					cuMES           (5)
      					      				}
     	ACCESS     		read-write
     	STATUS    		mandatory
     	DESCRIPTION
          		"Identifies the controller unit type."
	DEFVAL	{ cu3275 }
     	::= { bscCuEntry 4 } 

bscCuMaxBlockLength    	OBJECT-TYPE
       	SYNTAX 	BscBlockSize	
       	ACCESS    		read-write
       	STATUS            		mandatory
       	DESCRIPTION
   		"Identifies the maximal length of the blocks exchanged 
		between the host/terminal and the BSC module. The value is 
		measured  in octets and is specified by the BSC protocol. 
		The DEFVAL value will be 'block3000' or 'block256', 
		depending if the sap is configurated as 'hostInterfaceUnit' 
		or 'terminalInterfaceUnit' (see the object 'bscSapInterfaceType'). " 
       	DEFVAL     		{ block256}
       	::= { bscCuEntry  5 }
bscCuPollTimeout    		OBJECT-TYPE
       	SYNTAX            		INTEGER        (1..250)
	ACCESS    		read-write
       	STATUS            		mandatory
       	DESCRIPTION
   		"Identifies the number of seconds a station waits 
		for an answer. The value is measured  in tenth of seconds."
	DEFVAL		{ 30 } 
       	::= { bscCuEntry  6 }     


bscCuDelayTimer    		OBJECT-TYPE
       	SYNTAX            		INTEGER        (1..250)
	ACCESS    		read-write
       	STATUS            		mandatory
       	DESCRIPTION
   		"Identifies the number of seconds the emulated  station  may delay  the sending of a 			  block. Timer 
		is in tenth of seconds."
	DEFVAL		{ 20 } 
       	::= { bscCuEntry  7 }


bscCuRetryCounter      		OBJECT-TYPE
       	SYNTAX            		INTEGER        (1..50)
       	ACCESS    		read-write
       	STATUS            		mandatory
       	DESCRIPTION
   		"Identifies the number of retries are executed, 
		before a command fails. It is used  by the host/terminal 
		and the BSC layer."
	DEFVAL		{  3 }
       	::= { bscCuEntry  8 }








bscCuETBAck            		OBJECT-TYPE
      	SYNTAX       		BscAckMode
     	ACCESS        		read-write
     	STATUS        		mandatory
      	DESCRIPTION
   		"Identifies if the acknowledgement is local or end to 
		end for ETBs. The ETB is a trailer block delimitator..
		The 'endToEnd' means each block  is 
		acknowledged to the sender after receiving a confirmation 
		from the remote BSC. The 'local' means the block 
		is acknowledged locally. The block initiator is notified
    		the block  was received by the peer BSC layer."  
     	DEFVAL               	{ local }   
     	::= { bscCuEntry  9}


bscCuETXAck            		OBJECT-TYPE
      	SYNTAX       		BscAckMode
     	ACCESS        		read-write
     	STATUS        		mandatory
      	DESCRIPTION
   		"Identifies if the acknowledgement is local or end to 
		end for ETXs. The ETX is a trailer command delimitator..
		The 'endToEnd' means the command is 
		acknowledged to the sender after receiving a confirmation 
		from the remote BSC. The 'local' means the command 
		is acknowledged locally. The command initiator is notified
    		the command was completed by the BSC layer. It doesn't 
		garranty the command was completed by the remote BSC."  
     	DEFVAL               	{ endToEnd  }   
     	::= { bscCuEntry  10}


-- gap (11) to gap (19) for future Parameters
-- Control


bscCuControl   			OBJECT-TYPE
       	SYNTAX            		INTEGER        
					{
         					clearStats      (1)
				            	}
       	ACCESS    		write-only
       	STATUS            		mandatory
       	DESCRIPTION
       		"Control associated with the specified service access point."
       	::= { bscCuEntry  20 }


-- gap (21) to (29) for future Parameters
-- Status



bscCuOperationalMode 		OBJECT-TYPE
     	SYNTAX  		BscOperationalMode
     	ACCESS    		read-only
     	STATUS    		mandatory
     	DESCRIPTION
          		"Identifies the service access point as being
          		active or non-active with the new configuration."
     	::={ bscCuEntry 30 }


bscCuConnectionStatus 		OBJECT-TYPE
     	SYNTAX    		INTEGER {
					nonExistantX25Connection	(1),
					snalcConnectionRequested	(2),
					snalcConnectionConfirmationSent	(3),
					x25ConnectionEstablished		(4)
					}
     	ACCESS    		read-only
     	STATUS    		mandatory
     	DESCRIPTION
		"Indicates the X25 connection status of this link. "
	::={ bscCuEntry 31 }


-- gap (32) to gap (39) for future Parameters
-- Statistics


bscCuConnectRequest 		OBJECT-TYPE
       	SYNTAX    		Counter        
       	ACCESS    		read-only
       	STATUS            		mandatory
       	DESCRIPTION
		"Number of connection requests coming from the upper SNALC layer." 
       	::= { bscCuEntry  45 }


bscCuDisconnectRequest 	OBJECT-TYPE
       	SYNTAX    		Counter        
       	ACCESS    		read-only
       	STATUS            		mandatory
       	DESCRIPTION
		"Number of  disconnection requests coming from the upper SNALC layer." 
       	::= { bscCuEntry  46 }


bscCuDisconnectIndication	OBJECT-TYPE
       	SYNTAX    		Counter        
       	ACCESS    		read-only
       	STATUS            		mandatory
       	DESCRIPTION
		"Number of  disconnections sent to the upper SNALC layer. " 
       	::= { bscCuEntry  47 }

bscCuEndToEndConnectCnf 	OBJECT-TYPE
       	SYNTAX    		Counter        
       	ACCESS    		read-only
       	STATUS            		mandatory
       	DESCRIPTION
		"Number of  end-to-end connections seen by the controller. Message sent by the
		  Snalc. " 
       	::= { bscCuEntry  48 }


bscCuSnalcRxRnr	 	OBJECT-TYPE
       	SYNTAX    		Counter        
       	ACCESS    		read-only
       	STATUS            		mandatory
       	DESCRIPTION
		"Number of RNR 's received from the SNALC module due to X.25 or LLC2 flow control." 
	::= { bscCuEntry  49 }


bscCuSnalcRxRr		 	OBJECT-TYPE
       	SYNTAX    		Counter        
       	ACCESS    		read-only
       	STATUS            		mandatory
       	DESCRIPTION
		"Number of RR 's received from the SNALC module due to X.25 or LLC2 flow control." 
	::= { bscCuEntry  50 }



























bscDevTable  			OBJECT-TYPE
   	SYNTAX          		SEQUENCE OF BscDevEntry
   	ACCESS   		not-accessible
   	STATUS           		mandatory
   	DESCRIPTION
     		"A  table  containing configuration information 
		about all the devices controlled by this module."
   	::= { cxBsc 12 }


bscDevEntry  			OBJECT-TYPE
     	SYNTAX    		BscDevEntry
     	ACCESS    		not-accessible
     	STATUS    		mandatory
     	DESCRIPTION
          		"The parameters for a particular controller unit."       
     	INDEX  {
		bscDevSapNumber,
		bscDevCuNumber,
       		bscDevNumber
       		}
     	::= { bscDevTable 1 }


BscDevEntry ::=
     	SEQUENCE 	{
-- Parameters
	bscDevSapNumber		SapIndex,
	bscDevCuNumber       		BscCuIndex,
   	bscDevNumber 			BscDevIndex,
   	bscDevRowStatus      		BscRowStatus,
	bscDevType			INTEGER,	
-- Control
	bscDevControl			INTEGER,
-- State	
	bscDevOperationalMode 		BscOperationalMode,
	bscDevConnectionStatus		INTEGER,
	bscDevState			INTEGER,
	bscDevSSDeviceBusy		BscStatusSense,
	bscDevSSUnitSpecify		BscStatusSense,
	bscDevSSDeviceEnd		BscStatusSense,
	bscDevSSTransmissionCheck	BscStatusSense,	
	bscDevSSCommandReject	BscStatusSense,	
	bscDevSSInterventionRequired	BscStatusSense,
	bscDevSSEquipmentCheck	BscStatusSense,
	bscDevSSDataCheck		BscStatusSense,
	bscDevSSControlCheck		BscStatusSense,
	bscDevSSOperationCheck		BscStatusSense,	
-- Statistics
	bscDevGeneralPoll		Counter,
	bscDevSpecificPoll		Counter,
	bscDevDeviceSelection		Counter,
	bscDevTestRequest		Counter,
	bscDevHostWrite			Counter,
	bscDevHostRead			Counter,
	bscDevHostControl		Counter,
	bscDevCuShortRead		Counter,
	bscDevTxBlocks             	  	Counter,
   	bscDevRxBlocks               		Counter,
	bscDevStatusSense		Counter,
	bscDevError            		Counter,
   	bscDevErrTimeout             	Counter,
	bscDevCircuitEnable		Counter,
	bscDevCircuitDisconnect		Counter,
	bscDevCircuitRequest		Counter,
	bscDevTxCommands		Counter,
	bscDevRxCommands		Counter,
	bscDevCommandsQueued		Counter,
	bscDevBlocksQueued	Counter,
	bscDevTxRvi			Counter,
	bscDevRxRvi			Counter,
	bscDevTxTtd			Counter,
	bscDevRxTtd			Counter,
	bscDevTxWack			Counter,
	bscDevRxWack			Counter
}



--  parameters


bscDevSapNumber		OBJECT-TYPE
     	SYNTAX                	SapIndex
     	ACCESS        		read-only
     	STATUS                 	mandatory
     	DESCRIPTION
          		"Identifies  the  sap to which  this device 
		is attached. "
   	::= { bscDevEntry  1 }


bscDevCuNumber       		OBJECT-TYPE
     	SYNTAX                	BscCuIndex
     	ACCESS        		read-only
     	STATUS                 	mandatory
     	DESCRIPTION
          		"Identifies  the  address of the controller unit
		 to which  this device is attached. "
   	::= { bscDevEntry 2 }








bscDevNumber  		OBJECT-TYPE
     	SYNTAX                 	BscDevIndex
     	ACCESS         		read-only
     	STATUS                 	mandatory
     	DESCRIPTION
		"Identifies the address of this device.  The 
		address has to be unique for a specified for 
		a controller unit."
	::= { bscDevEntry 3 }
bscDevRowStatus      		OBJECT-TYPE
     	SYNTAX   		BscRowStatus
     	ACCESS    		read-write
     	STATUS    		mandatory
     	DESCRIPTION
          		"Indicates  whether the particular service  access
          		point is configured within the MIB. Controller unit  
		entries (rows) may be created by  setting  this object 
 		value  to  'valid',  or deleted   by   changing  this 
		object   value   to 'invalid'.   Whether or not the row
		actually disappears is left to the implementation so this
          		object may actually read as 'invalid'  for some arbitrary
		 length of time."
     	::= { bscDevEntry  4 }


bscDevType			OBJECT-TYPE
     	SYNTAX   		INTEGER	{
					display	(1),
					printer	(2)
				}
     	ACCESS    		read-write
     	STATUS    		mandatory
     	DESCRIPTION
          		"Indicates  whether the device is a printer or a
		display."
	DEFVAL		{ display }	
     	::= { bscDevEntry  5 }
		

-- gap (5) to gap (19) for future Parameters
-- Control


bscDevControl   		OBJECT-TYPE
       	SYNTAX            		INTEGER        
					{
         					clearStats      (1)
				            	}
       	ACCESS    		write-only
       	STATUS            		mandatory
       	DESCRIPTION
       		"Control associated with the specified service access point."
       	::= { bscDevEntry  20 }


-- gap (21) to gap (29) for future Parameters
-- Status


bscDevOperationalMode 	OBJECT-TYPE
     	SYNTAX  		BscOperationalMode
     	ACCESS    		read-only
     	STATUS    		mandatory
     	DESCRIPTION
          		"Identifies the device as being active or 
		non-active with the new configuration."
     	::={ bscDevEntry 30 }


bscDevConnectionStatus		OBJECT-TYPE
     	SYNTAX    		INTEGER {
					nonExistantLogicalConnection	(1),
					circuitRequestSent		(2),
					circuitEnableReceived		(3),
					circuitEnableSent 		(4),
					dataMode 			(5)
				}
	ACCESS    		read-only
     	STATUS    		mandatory
     	DESCRIPTION
		"Indicates the current status of the device's logical connection  with regard to the network. "
	DEFVAL		{ nonExistantLogicalConnection }	
	::= { bscDevEntry 31 }
























bscDevState	      OBJECT-TYPE
	SYNTAX     INTEGER {
			hiuWaitForNextPoll				(1),	
			hiuWaitingForStatusSenseAcknowledgment		(2),	  
			hiuSendNextMessageOnAcknowledgment         	(3),
			hiuSendEotOnAcknowledgment                  		(4),
			hiuReceiveCommandMode                        		(5),
			hiuReadWaitForResponse                     		(6),
			hiuWaitForCuReadEtx                        		(7),	
			hiuSendNextTransparent                       		(8),
			hiuWaitingForRviResponse                    		(9),
			hiuWaitingForWackResponse                   		(10),
			hiuSendNextOnNak                            		(11),
			hiuDeviceStateReserved-1			(12),
			hiuDeviceStateReserved-2                     		(13),
			hiuDeviceStateReserved-3                     		(14),
			tiuWaitForNextPoll                          		(15),
			tiuSentSpecificPoll                          			(16),
			tiuSentSelectivePoll                         		(17),
			tiuStatusSenseReceived                       		(18),
			tiuSendNextMessageOnAcknowledgment         	(19),
			tiuSendEotOnTransparentAcknowledgment      	(20),
			tiuSendEotOnAcknowledgment                  		(21),
			tiuDataPending                                			(22),
			tiuReceivingCommand                           		(23),
			tiuParityCursorCheckDetected                		(24),
			tiuReadWaitForResponse                      		(25),
			tiuWaitingForSnalcData                      		(26),
			tiuSendNextAfterNak                         		(27),
			tiuTerminatePolling                           		(28),
			tiuEndTestRequest				(29)
		     }	
	ACCESS    		read-only
     	STATUS    		mandatory
     	DESCRIPTION
		"Indicates the state of this link. "
	::={ bscDevEntry 32 }







bscDevSSDeviceBusy		OBJECT-TYPE
     	SYNTAX    		BscStatusSense
	ACCESS    		read-only
     	STATUS    		mandatory
     	DESCRIPTION
		"The current bit information found in the last status sense message received/transmitted."
	DEFVAL		{ notSet }	
	::= { bscDevEntry 33 }


bscDevSSUnitSpecify 		OBJECT-TYPE
     	SYNTAX    		BscStatusSense
	ACCESS    		read-only
     	STATUS    		mandatory
     	DESCRIPTION
		"The current bit information found in the last status sense message received/transmitted."
	DEFVAL		{ notSet }	
	::= { bscDevEntry 34 }


bscDevSSDeviceEnd 		OBJECT-TYPE
     	SYNTAX    		BscStatusSense
	ACCESS    		read-only
     	STATUS    		mandatory
     	DESCRIPTION
		"The current bit information found in the last status sense message received/transmitted."
	DEFVAL		{ notSet }	
	::= { bscDevEntry 35 }


bscDevSSTransmissionCheck 	OBJECT-TYPE
     	SYNTAX    		BscStatusSense
	ACCESS    		read-only
     	STATUS    		mandatory
     	DESCRIPTION
		"The current bit information found in the last status sense message received/transmitted."
	DEFVAL		{ notSet }	
	::= { bscDevEntry 36 }


bscDevSSCommandReject 	OBJECT-TYPE
     	SYNTAX    		BscStatusSense
	ACCESS    		read-only
     	STATUS    		mandatory
     	DESCRIPTION
		"The current bit information found in the last status sense message received/transmitted."
	DEFVAL		{ notSet }	
	::= { bscDevEntry 37 }


bscDevSSInterventionRequired 	OBJECT-TYPE
     	SYNTAX    		BscStatusSense
	ACCESS    		read-only
     	STATUS    		mandatory
     	DESCRIPTION
		"The current bit information found in the last status sense message received/transmitted."
	DEFVAL		{ notSet }	
	::= { bscDevEntry 38 }






bscDevSSEquipmentCheck 	OBJECT-TYPE
     	SYNTAX    		BscStatusSense
	ACCESS    		read-only
     	STATUS    		mandatory
     	DESCRIPTION
		"The current bit information found in the last status sense message received/transmitted."
	DEFVAL		{ notSet }	
	::= { bscDevEntry 39 }


bscDevSSDataCheck 		OBJECT-TYPE
     	SYNTAX    		BscStatusSense
	ACCESS    		read-only
     	STATUS    		mandatory
     	DESCRIPTION
		"The current bit information found in the last status sense message received/transmitted."
	DEFVAL		{ notSet }	
	::= { bscDevEntry 40 }


bscDevSSControlCheck 		OBJECT-TYPE
     	SYNTAX    		BscStatusSense
	ACCESS    		read-only
     	STATUS    		mandatory
     	DESCRIPTION
		"The current bit information found in the last status sense message received/transmitted."
	DEFVAL		{ notSet }	
	::= { bscDevEntry 41 }


bscDevSSOperationCheck		OBJECT-TYPE
     	SYNTAX    		BscStatusSense
	ACCESS    		read-only
     	STATUS    		mandatory
     	DESCRIPTION
		"The current bit information found in the last status sense message received/transmitted."
	DEFVAL		{ notSet }	
	::= { bscDevEntry 42 }


-- gap (42) to gap (59) for future Parameters
-- Statistics



bscDevGeneralPoll   		OBJECT-TYPE
       	SYNTAX    		Counter        
       	ACCESS    		read-only
       	STATUS            		mandatory
       	DESCRIPTION
		"Number of general polls transmitted/received." 
       	::= { bscDevEntry 60 }


bscDevSpecificPoll   		OBJECT-TYPE
       	SYNTAX    		Counter        
       	ACCESS    		read-only
       	STATUS            		mandatory
       	DESCRIPTION
		"Number of specific polls transmitted/received." 
       	::= { bscDevEntry 61 }


bscDevDeviceSelection		OBJECT-TYPE
       	SYNTAX    		Counter        
       	ACCESS    		read-only 
       	STATUS            		mandatory
       	DESCRIPTION
		"Number of device selections transmitted/received." 
       	::= { bscDevEntry 62 }


bscDevTestRequest 		OBJECT-TYPE
       	SYNTAX    		Counter        
       	ACCESS    		read-only 
       	STATUS            		mandatory
       	DESCRIPTION
		"Number of test request messages received." 
       	::= { bscDevEntry 63 }


bscDevHostWrite 		OBJECT-TYPE
       	SYNTAX    		Counter        
       	ACCESS    		read-only 
       	STATUS            		mandatory
       	DESCRIPTION
		"Number of host initiated write commands." 
       	::= { bscDevEntry 64 }


bscDevHostRead 		OBJECT-TYPE
       	SYNTAX    		Counter        
       	ACCESS    		read-only 
       	STATUS            		mandatory
       	DESCRIPTION
		"Number of host initiated read commands which need a direct response." 
       	::= { bscDevEntry 65 }



bscDevHostControl 		OBJECT-TYPE
       	SYNTAX    		Counter        
       	ACCESS    		read-only 
       	STATUS            		mandatory
       	DESCRIPTION
		"Number of host initiated control commands." 
       	::= { bscDevEntry 66 }

bscDevCuShortRead 		OBJECT-TYPE
       	SYNTAX    		Counter        
       	ACCESS    		read-only 
       	STATUS            		mandatory
       	DESCRIPTION
		"Number of controller initiated short read commands." 
       	::= { bscDevEntry 67 }


bscDevTxBlocks       		OBJECT-TYPE
       	SYNTAX    		Counter        
       	ACCESS    		read-only 
       	STATUS            		mandatory
       	DESCRIPTION
		"Identifies the number of blocks transmited by 
		this controller unit." 
       	::= { bscDevEntry 68 }     


bscDevRxBlocks       		OBJECT-TYPE
       	SYNTAX    		Counter        
       	ACCESS    		read-only 
       	STATUS            		mandatory
       	DESCRIPTION
		"Identifies the number of blocks received by this 
		controller unit." 
       	::= { bscDevEntry 69  }    


bscDevStatusSense       		OBJECT-TYPE
       	SYNTAX    		Counter        
       	ACCESS    		read-only
       	STATUS            		mandatory
       	DESCRIPTION	
		"Identifies the number of status/sense messages
		received by the device." 
       	::= { bscDevEntry  70 }









bscDevError	       		OBJECT-TYPE
       	SYNTAX    		Counter        
       	ACCESS    		read-only
       	STATUS            		mandatory
       	DESCRIPTION	
		"Identifies the number of blocks in errors (other 
		than BCC) received by this controller unit." 
       	::= { bscDevEntry  71}
bscDevErrTimeout 		OBJECT-TYPE
       	SYNTAX    		Counter        
       	ACCESS    		read-only
       	STATUS            		mandatory
       	DESCRIPTION
		"Identifies the number of timeouts for this controller unit." 
       	::= { bscDevEntry  72}


bscDevCircuitEnable 		OBJECT-TYPE
       	SYNTAX    		Counter        
       	ACCESS    		read-only
       	STATUS            		mandatory
       	DESCRIPTION
		"Number of  device connection requests (or enable) coming from the DSP module through the 
                              upper SNALC layer." 
       	::= { bscDevEntry  73 }


bscDevCircuitDisconnect	 	OBJECT-TYPE
       	SYNTAX    		Counter        
       	ACCESS    		read-only
       	STATUS            		mandatory
       	DESCRIPTION
		"Number of  device disconnection requests (or disable) coming from the DSP module through the 
                              upper SNALC layer." 
       	::= { bscDevEntry  74 }


bscDevCircuitRequest	 	OBJECT-TYPE
       	SYNTAX    		Counter        
       	ACCESS    		read-only
       	STATUS            		mandatory
       	DESCRIPTION
		"Number of  circuit requests sent (TIU) or received (HIU)  to/from the DSP module 			through the  upper SNALC layer." 
       	::= { bscDevEntry  75 }


bscDevTxCommands	 	OBJECT-TYPE
       	SYNTAX    		Counter        
       	ACCESS    		read-only
       	STATUS            		mandatory
       	DESCRIPTION
		"Number of complete commands transmitted to the host or controller/device."
	::= { bscDevEntry  76 }






bscDevRxCommands	 	OBJECT-TYPE
       	SYNTAX    		Counter        
       	ACCESS    		read-only
       	STATUS            		mandatory
       	DESCRIPTION
		"Number of complete commands received from  the host or controller/device."
	::= { bscDevEntry  77 }

	
bscDevCommandsQueued	 	OBJECT-TYPE
       	SYNTAX    		Counter        
       	ACCESS    		read-only
       	STATUS            		mandatory
       	DESCRIPTION
		"Number of  commands queued."
	::= { bscDevEntry  78 }


bscDevBlocksQueued	 	OBJECT-TYPE
       	SYNTAX    		Counter        
       	ACCESS    		read-only
       	STATUS            		mandatory
       	DESCRIPTION
		"Number of  blocks queued."
	::= { bscDevEntry  79 }


bscDevTxRvi	 	OBJECT-TYPE
       	SYNTAX    		Counter        
       	ACCESS    		read-only
       	STATUS            		mandatory
       	DESCRIPTION
		"Number of  transmitted  RVI's to the host. (HIU)."
	::= { bscDevEntry  80 }


bscDevRxRvi	 	OBJECT-TYPE
       	SYNTAX    		Counter        
       	ACCESS    		read-only
       	STATUS            		mandatory
       	DESCRIPTION
		"Number of  received RVI's from the  controller/device."
	::= { bscDevEntry  81 }

bscDevTxTtd		 	OBJECT-TYPE
       	SYNTAX    		Counter        
       	ACCESS    		read-only
       	STATUS            		mandatory
       	DESCRIPTION
		"Number of  transmitted text delays,  TTD, to the  controller/device.(TIU)"
	::= { bscDevEntry  82 }



bscDevRxTtd	 	OBJECT-TYPE
       	SYNTAX    		Counter        
       	ACCESS    		read-only
       	STATUS            		mandatory
       	DESCRIPTION
		"Number of  received text delay's, TTD, from the host.(HIU)"
	::= { bscDevEntry  83 }


bscDevTxWack	 		OBJECT-TYPE
       	SYNTAX    		Counter        
       	ACCESS    		read-only
       	STATUS            		mandatory
       	DESCRIPTION
		"Number of  transmitted WACK's to the host.(HIU)."
	::= { bscDevEntry  84 }

bscDevRxWack	 		OBJECT-TYPE
       	SYNTAX    		Counter        
       	ACCESS    		read-only
       	STATUS            		mandatory
       	DESCRIPTION
		"Number of recieved WACK's from the controller/device."
	::= { bscDevEntry  85 }

END
