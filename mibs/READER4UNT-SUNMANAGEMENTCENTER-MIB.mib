-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
READER4UNT-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }


alarm	OBJECT IDENTIFIER ::= { reader4unt 46 }
sunwafb-entry	OBJECT IDENTIFIER ::= { sunwafbTbl 1 }
sunSmTreeProp	OBJECT IDENTIFIER ::= { networkEntry 1 }
sunSmNodeName	OBJECT IDENTIFIER ::= { networkEntry 2 }
entry-no	OBJECT IDENTIFIER ::= { networkEntry 3 }
device-type	OBJECT IDENTIFIER ::= { networkEntry 4 }
ether	OBJECT IDENTIFIER ::= { networkEntry 5 }
inet	OBJECT IDENTIFIER ::= { networkEntry 6 }
interface-name	OBJECT IDENTIFIER ::= { networkEntry 7 }
node-hierarchy	OBJECT IDENTIFIER ::= { networkEntry 8 }
symbolic-name	OBJECT IDENTIFIER ::= { networkEntry 9 }
reg	OBJECT IDENTIFIER ::= { networkEntry 10 }
sunSmTreeProp	OBJECT IDENTIFIER ::= { temp-monitor-entry 1 }
sunSmNodeName	OBJECT IDENTIFIER ::= { temp-monitor-entry 2 }
entry-no	OBJECT IDENTIFIER ::= { temp-monitor-entry 3 }
name	OBJECT IDENTIFIER ::= { temp-monitor-entry 4 }
temperature	OBJECT IDENTIFIER ::= { temp-monitor-entry 5 }
warning	OBJECT IDENTIFIER ::= { temp-monitor-entry 6 }
shutdown	OBJECT IDENTIFIER ::= { temp-monitor-entry 7 }
circuit-breaker-entry	OBJECT IDENTIFIER ::= { circuit-breakerTbl 1 }
cpu-unitTbl	OBJECT IDENTIFIER ::= { cpu-unit 1 }
sunSmTreeProp	OBJECT IDENTIFIER ::= { leds 1 }
sunSmNodeName	OBJECT IDENTIFIER ::= { leds 2 }
sunSmTreeProp	OBJECT IDENTIFIER ::= { memory-module-group-entry 1 }
sunSmNodeName	OBJECT IDENTIFIER ::= { memory-module-group-entry 2 }
entry-no	OBJECT IDENTIFIER ::= { memory-module-group-entry 3 }
id	OBJECT IDENTIFIER ::= { memory-module-group-entry 4 }
size	OBJECT IDENTIFIER ::= { memory-module-group-entry 5 }
sysctrlTbl	OBJECT IDENTIFIER ::= { sysctrl 1 }
sunSmTreeProp	OBJECT IDENTIFIER ::= { simm-entry 1 }
sunSmNodeName	OBJECT IDENTIFIER ::= { simm-entry 2 }
entry-no	OBJECT IDENTIFIER ::= { simm-entry 3 }
board-reference-number	OBJECT IDENTIFIER ::= { simm-entry 4 }
fru	OBJECT IDENTIFIER ::= { simm-entry 5 }
size	OBJECT IDENTIFIER ::= { simm-entry 6 }
slot	OBJECT IDENTIFIER ::= { simm-entry 7 }
type	OBJECT IDENTIFIER ::= { simm-entry 8 }
status	OBJECT IDENTIFIER ::= { simm-entry 9 }
eepromTbl	OBJECT IDENTIFIER ::= { eeprom 1 }
sunSmTreeProp	OBJECT IDENTIFIER ::= { circuit-breakers 1 }
sunSmNodeName	OBJECT IDENTIFIER ::= { circuit-breakers 2 }
fruid-entry	OBJECT IDENTIFIER ::= { fruidTbl 1 }
sunSmTreeProp	OBJECT IDENTIFIER ::= { memory-controller-entry 1 }
sunSmNodeName	OBJECT IDENTIFIER ::= { memory-controller-entry 2 }
entry-no	OBJECT IDENTIFIER ::= { memory-controller-entry 3 }
pathname-element	OBJECT IDENTIFIER ::= { memory-controller-entry 4 }
state	OBJECT IDENTIFIER ::= { memory-controller-entry 5 }
flashprom-entry	OBJECT IDENTIFIER ::= { flashpromTbl 1 }
sunSmTreeProp	OBJECT IDENTIFIER ::= { lominfo 1 }
sunSmNodeName	OBJECT IDENTIFIER ::= { lominfo 2 }
prod-id	OBJECT IDENTIFIER ::= { lominfo 3 }
ser-char	OBJECT IDENTIFIER ::= { lominfo 4 }
version	OBJECT IDENTIFIER ::= { lominfo 5 }
sunSmTreeProp	OBJECT IDENTIFIER ::= { sunwUltra-10 1 }
sunSmNodeName	OBJECT IDENTIFIER ::= { sunwUltra-10 2 }
slotTbl	OBJECT IDENTIFIER ::= { slot 1 }
sunSmTreeProp	OBJECT IDENTIFIER ::= { fruEntry 1 }
sunSmNodeName	OBJECT IDENTIFIER ::= { fruEntry 2 }
entry-no	OBJECT IDENTIFIER ::= { fruEntry 3 }
status	OBJECT IDENTIFIER ::= { fruEntry 4 }
sunSmTreeProp	OBJECT IDENTIFIER ::= { io-controllerEntry 1 }
sunSmNodeName	OBJECT IDENTIFIER ::= { io-controllerEntry 2 }
entry-no	OBJECT IDENTIFIER ::= { io-controllerEntry 3 }
board-num	OBJECT IDENTIFIER ::= { io-controllerEntry 4 }
clock-frequency	OBJECT IDENTIFIER ::= { io-controllerEntry 5 }
device-type	OBJECT IDENTIFIER ::= { io-controllerEntry 6 }
instance	OBJECT IDENTIFIER ::= { io-controllerEntry 7 }
model	OBJECT IDENTIFIER ::= { io-controllerEntry 8 }
reg	OBJECT IDENTIFIER ::= { io-controllerEntry 9 }
upa-mid	OBJECT IDENTIFIER ::= { io-controllerEntry 10 }
upa-portid	OBJECT IDENTIFIER ::= { io-controllerEntry 11 }
version-no	OBJECT IDENTIFIER ::= { io-controllerEntry 12 }
fruTbl	OBJECT IDENTIFIER ::= { fru 1 }
psuTbl	OBJECT IDENTIFIER ::= { psu 1 }
io-controllerEntry	OBJECT IDENTIFIER ::= { io-controllerTbl 1 }
sunwffbTbl	OBJECT IDENTIFIER ::= { sunwffb 1 }
cpu-unit-entry	OBJECT IDENTIFIER ::= { cpu-unitTbl 1 }
sunSmTreeProp	OBJECT IDENTIFIER ::= { sunwafb-entry 1 }
sunSmNodeName	OBJECT IDENTIFIER ::= { sunwafb-entry 2 }
entry-no	OBJECT IDENTIFIER ::= { sunwafb-entry 3 }
dram3	OBJECT IDENTIFIER ::= { sunwafb-entry 4 }
dac	OBJECT IDENTIFIER ::= { sunwafb-entry 5 }
fbc-version	OBJECT IDENTIFIER ::= { sunwafb-entry 6 }
board-type	OBJECT IDENTIFIER ::= { sunwafb-entry 7 }
buffer	OBJECT IDENTIFIER ::= { sunwafb-entry 8 }
device-type	OBJECT IDENTIFIER ::= { sunwafb-entry 9 }
height	OBJECT IDENTIFIER ::= { sunwafb-entry 10 }
model	OBJECT IDENTIFIER ::= { sunwafb-entry 11 }
revision	OBJECT IDENTIFIER ::= { sunwafb-entry 12 }
upa-portid	OBJECT IDENTIFIER ::= { sunwafb-entry 13 }
width	OBJECT IDENTIFIER ::= { sunwafb-entry 14 }
eeprom-entry	OBJECT IDENTIFIER ::= { eepromTbl 1 }
tsalarminfo-entry	OBJECT IDENTIFIER ::= { tsalarminfoTbl 1 }
simmTbl	OBJECT IDENTIFIER ::= { simm 1 }
sunSmTreeProp	OBJECT IDENTIFIER ::= { sunwUltraSPARC-IIi-cEngine 1 }
sunSmNodeName	OBJECT IDENTIFIER ::= { sunwUltraSPARC-IIi-cEngine 2 }
sunSmTreeProp	OBJECT IDENTIFIER ::= { alarms 1 }
sunSmNodeName	OBJECT IDENTIFIER ::= { alarms 2 }
memory-module-group-entry	OBJECT IDENTIFIER ::= { memory-module-groupTbl 1 }
tapeTbl	OBJECT IDENTIFIER ::= { tape 1 }
sunSmTreeProp	OBJECT IDENTIFIER ::= { io-unitEntry 1 }
sunSmNodeName	OBJECT IDENTIFIER ::= { io-unitEntry 2 }
entry-no	OBJECT IDENTIFIER ::= { io-unitEntry 3 }
board-num	OBJECT IDENTIFIER ::= { io-unitEntry 4 }
device-id	OBJECT IDENTIFIER ::= { io-unitEntry 5 }
instance	OBJECT IDENTIFIER ::= { io-unitEntry 6 }
reg	OBJECT IDENTIFIER ::= { io-unitEntry 7 }
sunSmTreeProp	OBJECT IDENTIFIER ::= { eeprom-entry 1 }
sunSmNodeName	OBJECT IDENTIFIER ::= { eeprom-entry 2 }
entry-no	OBJECT IDENTIFIER ::= { eeprom-entry 3 }
model	OBJECT IDENTIFIER ::= { eeprom-entry 4 }
reg	OBJECT IDENTIFIER ::= { eeprom-entry 5 }
ffb-entry	OBJECT IDENTIFIER ::= { ffbTbl 1 }
sunSmTreeProp	OBJECT IDENTIFIER ::= { ffb-entry 1 }
sunSmNodeName	OBJECT IDENTIFIER ::= { ffb-entry 2 }
entry-no	OBJECT IDENTIFIER ::= { ffb-entry 3 }
buffer	OBJECT IDENTIFIER ::= { ffb-entry 4 }
device-type	OBJECT IDENTIFIER ::= { ffb-entry 5 }
model	OBJECT IDENTIFIER ::= { ffb-entry 6 }
pathname-element	OBJECT IDENTIFIER ::= { ffb-entry 7 }
system-ledTbl	OBJECT IDENTIFIER ::= { system-led 1 }
sunwafbTbl	OBJECT IDENTIFIER ::= { sunwafb 1 }
sunSmTreeProp	OBJECT IDENTIFIER ::= { voltage-sensor-entry 1 }
sunSmNodeName	OBJECT IDENTIFIER ::= { voltage-sensor-entry 2 }
entry-no	OBJECT IDENTIFIER ::= { voltage-sensor-entry 3 }
name	OBJECT IDENTIFIER ::= { voltage-sensor-entry 4 }
status	OBJECT IDENTIFIER ::= { voltage-sensor-entry 5 }
shutdown-enabled	OBJECT IDENTIFIER ::= { voltage-sensor-entry 6 }
afb-entry	OBJECT IDENTIFIER ::= { afbTbl 1 }
sunSmTreeProp	OBJECT IDENTIFIER ::= { circuit-breaker-entry 1 }
sunSmNodeName	OBJECT IDENTIFIER ::= { circuit-breaker-entry 2 }
entry-no	OBJECT IDENTIFIER ::= { circuit-breaker-entry 3 }
name	OBJECT IDENTIFIER ::= { circuit-breaker-entry 4 }
status	OBJECT IDENTIFIER ::= { circuit-breaker-entry 5 }
psu-entry	OBJECT IDENTIFIER ::= { psuTbl 1 }
reader4unt	OBJECT IDENTIFIER ::= { config 6 }
simm-entry	OBJECT IDENTIFIER ::= { simmTbl 1 }
flashpromTbl	OBJECT IDENTIFIER ::= { flashprom 1 }
sunSmTreeProp	OBJECT IDENTIFIER ::= { sunwUltraAX-i2 1 }
sunSmNodeName	OBJECT IDENTIFIER ::= { sunwUltraAX-i2 2 }
sunSmTreeProp	OBJECT IDENTIFIER ::= { fans 1 }
sunSmNodeName	OBJECT IDENTIFIER ::= { fans 2 }
io-deviceEntry	OBJECT IDENTIFIER ::= { io-deviceTbl 1 }
sunSmTreeProp	OBJECT IDENTIFIER ::= { event-entry 1 }
sunSmNodeName	OBJECT IDENTIFIER ::= { event-entry 2 }
entry-no	OBJECT IDENTIFIER ::= { event-entry 3 }
data	OBJECT IDENTIFIER ::= { event-entry 4 }
memory-entry	OBJECT IDENTIFIER ::= { memoryTbl 1 }
memoryTbl	OBJECT IDENTIFIER ::= { memory 1 }
sunSmTreeProp	OBJECT IDENTIFIER ::= { sunwUltra-60 1 }
sunSmNodeName	OBJECT IDENTIFIER ::= { sunwUltra-60 2 }
ot-monitorTbl	OBJECT IDENTIFIER ::= { ot-monitor 1 }
temp-monitorTbl	OBJECT IDENTIFIER ::= { ot-monitor 2 }
eventTbl	OBJECT IDENTIFIER ::= { event 1 }
sunSmTreeProp	OBJECT IDENTIFIER ::= { system 1 }
sunSmNodeName	OBJECT IDENTIFIER ::= { system 2 }
os	OBJECT IDENTIFIER ::= { system 3 }
os-version	OBJECT IDENTIFIER ::= { system 4 }
system-clock-frequency	OBJECT IDENTIFIER ::= { system 5 }
architecture	OBJECT IDENTIFIER ::= { system 6 }
hostname	OBJECT IDENTIFIER ::= { system 7 }
machine	OBJECT IDENTIFIER ::= { system 8 }
platform	OBJECT IDENTIFIER ::= { system 9 }
sample	OBJECT IDENTIFIER ::= { system 10 }
serial-number	OBJECT IDENTIFIER ::= { system 11 }
timestamp	OBJECT IDENTIFIER ::= { system 12 }
timestamp-raw	OBJECT IDENTIFIER ::= { system 13 }
total-disks	OBJECT IDENTIFIER ::= { system 14 }
total-memory	OBJECT IDENTIFIER ::= { system 15 }
total-processors	OBJECT IDENTIFIER ::= { system 16 }
total-tape-devices	OBJECT IDENTIFIER ::= { system 17 }
total-model-changes	OBJECT IDENTIFIER ::= { system 18 }
total-config-changes	OBJECT IDENTIFIER ::= { system 19 }
module-status	OBJECT IDENTIFIER ::= { system 20 }
module-status-severity	OBJECT IDENTIFIER ::= { system 21 }
sunSmTreeProp	OBJECT IDENTIFIER ::= { psus 1 }
sunSmNodeName	OBJECT IDENTIFIER ::= { psus 2 }
sunSmTreeProp	OBJECT IDENTIFIER ::= { sunwffb-entry 1 }
sunSmNodeName	OBJECT IDENTIFIER ::= { sunwffb-entry 2 }
entry-no	OBJECT IDENTIFIER ::= { sunwffb-entry 3 }
dram3	OBJECT IDENTIFIER ::= { sunwffb-entry 4 }
dac	OBJECT IDENTIFIER ::= { sunwffb-entry 5 }
fbc-version	OBJECT IDENTIFIER ::= { sunwffb-entry 6 }
board-type	OBJECT IDENTIFIER ::= { sunwffb-entry 7 }
buffer	OBJECT IDENTIFIER ::= { sunwffb-entry 8 }
device-type	OBJECT IDENTIFIER ::= { sunwffb-entry 9 }
height	OBJECT IDENTIFIER ::= { sunwffb-entry 10 }
model	OBJECT IDENTIFIER ::= { sunwffb-entry 11 }
revision	OBJECT IDENTIFIER ::= { sunwffb-entry 12 }
upa-portid	OBJECT IDENTIFIER ::= { sunwffb-entry 13 }
width	OBJECT IDENTIFIER ::= { sunwffb-entry 14 }
tsalarminfoTbl	OBJECT IDENTIFIER ::= { tsalarminfo 1 }
sunSmTreeProp	OBJECT IDENTIFIER ::= { asr 1 }
sunSmNodeName	OBJECT IDENTIFIER ::= { asr 2 }
reset-enabled	OBJECT IDENTIFIER ::= { asr 3 }
watchdog-enabled	OBJECT IDENTIFIER ::= { asr 4 }
watchdog-timeout	OBJECT IDENTIFIER ::= { asr 5 }
networkEntry	OBJECT IDENTIFIER ::= { networkTbl 1 }
voltage-sensorTbl	OBJECT IDENTIFIER ::= { voltage-sensor 1 }
temp-monitor-entry	OBJECT IDENTIFIER ::= { temp-monitorTbl 1 }
sunSmTreeProp	OBJECT IDENTIFIER ::= { solt-entry 1 }
sunSmNodeName	OBJECT IDENTIFIER ::= { solt-entry 2 }
entry-no	OBJECT IDENTIFIER ::= { solt-entry 3 }
slot-num	OBJECT IDENTIFIER ::= { solt-entry 4 }
fanTbl	OBJECT IDENTIFIER ::= { fan 1 }
solt-entry	OBJECT IDENTIFIER ::= { slotTbl 1 }
sunSmTreeProp	OBJECT IDENTIFIER ::= { io-deviceEntry 1 }
sunSmNodeName	OBJECT IDENTIFIER ::= { io-deviceEntry 2 }
entry-no	OBJECT IDENTIFIER ::= { io-deviceEntry 3 }
device-type	OBJECT IDENTIFIER ::= { io-deviceEntry 4 }
disk-count	OBJECT IDENTIFIER ::= { io-deviceEntry 5 }
instance	OBJECT IDENTIFIER ::= { io-deviceEntry 6 }
model	OBJECT IDENTIFIER ::= { io-deviceEntry 7 }
node-hierarchy	OBJECT IDENTIFIER ::= { io-deviceEntry 8 }
network-count	OBJECT IDENTIFIER ::= { io-deviceEntry 9 }
reg	OBJECT IDENTIFIER ::= { io-deviceEntry 10 }
tape-count	OBJECT IDENTIFIER ::= { io-deviceEntry 11 }
sunSmTreeProp	OBJECT IDENTIFIER ::= { cpu-unit-entry 1 }
sunSmNodeName	OBJECT IDENTIFIER ::= { cpu-unit-entry 2 }
entry-no	OBJECT IDENTIFIER ::= { cpu-unit-entry 3 }
board-hash	OBJECT IDENTIFIER ::= { cpu-unit-entry 4 }
board-num	OBJECT IDENTIFIER ::= { cpu-unit-entry 5 }
clock-frequency	OBJECT IDENTIFIER ::= { cpu-unit-entry 6 }
cpu-type	OBJECT IDENTIFIER ::= { cpu-unit-entry 7 }
dcache-size	OBJECT IDENTIFIER ::= { cpu-unit-entry 8 }
device-type	OBJECT IDENTIFIER ::= { cpu-unit-entry 9 }
ecache-size	OBJECT IDENTIFIER ::= { cpu-unit-entry 10 }
fru	OBJECT IDENTIFIER ::= { cpu-unit-entry 11 }
icache-size	OBJECT IDENTIFIER ::= { cpu-unit-entry 12 }
model	OBJECT IDENTIFIER ::= { cpu-unit-entry 13 }
pathname-element	OBJECT IDENTIFIER ::= { cpu-unit-entry 14 }
processor-id	OBJECT IDENTIFIER ::= { cpu-unit-entry 15 }
reg	OBJECT IDENTIFIER ::= { cpu-unit-entry 16 }
status	OBJECT IDENTIFIER ::= { cpu-unit-entry 17 }
unit	OBJECT IDENTIFIER ::= { cpu-unit-entry 18 }
upa-mid	OBJECT IDENTIFIER ::= { cpu-unit-entry 19 }
upa-portid	OBJECT IDENTIFIER ::= { cpu-unit-entry 20 }
io-deviceTbl	OBJECT IDENTIFIER ::= { io-device 1 }
sunSmTreeProp	OBJECT IDENTIFIER ::= { psu-entry 1 }
sunSmNodeName	OBJECT IDENTIFIER ::= { psu-entry 2 }
entry-no	OBJECT IDENTIFIER ::= { psu-entry 3 }
inputA	OBJECT IDENTIFIER ::= { psu-entry 4 }
inputB	OBJECT IDENTIFIER ::= { psu-entry 5 }
output	OBJECT IDENTIFIER ::= { psu-entry 6 }
status	OBJECT IDENTIFIER ::= { psu-entry 7 }
io-controllerTbl	OBJECT IDENTIFIER ::= { io-controller 1 }
sunSmTreeProp	OBJECT IDENTIFIER ::= { tapeEntry 1 }
sunSmNodeName	OBJECT IDENTIFIER ::= { tapeEntry 2 }
entry-no	OBJECT IDENTIFIER ::= { tapeEntry 3 }
device-type	OBJECT IDENTIFIER ::= { tapeEntry 4 }
fru	OBJECT IDENTIFIER ::= { tapeEntry 5 }
instance	OBJECT IDENTIFIER ::= { tapeEntry 6 }
model	OBJECT IDENTIFIER ::= { tapeEntry 7 }
node-hierarchy	OBJECT IDENTIFIER ::= { tapeEntry 8 }
tape-name	OBJECT IDENTIFIER ::= { tapeEntry 9 }
status	OBJECT IDENTIFIER ::= { tapeEntry 10 }
target	OBJECT IDENTIFIER ::= { tapeEntry 11 }
system-led-entry	OBJECT IDENTIFIER ::= { system-ledTbl 1 }
sunSmTreeProp	OBJECT IDENTIFIER ::= { alarm-entry 1 }
sunSmNodeName	OBJECT IDENTIFIER ::= { alarm-entry 2 }
entry-no	OBJECT IDENTIFIER ::= { alarm-entry 3 }
state	OBJECT IDENTIFIER ::= { alarm-entry 4 }
sunSmTreeProp	OBJECT IDENTIFIER ::= { temp-monitors 1 }
sunSmNodeName	OBJECT IDENTIFIER ::= { temp-monitors 2 }
sunSmTreeProp	OBJECT IDENTIFIER ::= { sunwUltra-30 1 }
sunSmNodeName	OBJECT IDENTIFIER ::= { sunwUltra-30 2 }
sunSmTreeProp	OBJECT IDENTIFIER ::= { fan-entry 1 }
sunSmNodeName	OBJECT IDENTIFIER ::= { fan-entry 2 }
entry-no	OBJECT IDENTIFIER ::= { fan-entry 3 }
status	OBJECT IDENTIFIER ::= { fan-entry 4 }
alarm-entry	OBJECT IDENTIFIER ::= { alarmTbl 1 }
io-unitEntry	OBJECT IDENTIFIER ::= { io-unitTbl 1 }
sunSmTreeProp	OBJECT IDENTIFIER ::= { voltage-sensors 1 }
sunSmNodeName	OBJECT IDENTIFIER ::= { voltage-sensors 2 }
tapeEntry	OBJECT IDENTIFIER ::= { tapeTbl 1 }
sunSmTreeProp	OBJECT IDENTIFIER ::= { events 1 }
sunSmNodeName	OBJECT IDENTIFIER ::= { events 2 }
circuit-breakerTbl	OBJECT IDENTIFIER ::= { circuit-breaker 1 }
ot-monitor-entry	OBJECT IDENTIFIER ::= { ot-monitorTbl 1 }
sunSmTreeProp	OBJECT IDENTIFIER ::= { diskEntry 1 }
sunSmNodeName	OBJECT IDENTIFIER ::= { diskEntry 2 }
entry-no	OBJECT IDENTIFIER ::= { diskEntry 3 }
device-type	OBJECT IDENTIFIER ::= { diskEntry 4 }
disk-name	OBJECT IDENTIFIER ::= { diskEntry 5 }
fru	OBJECT IDENTIFIER ::= { diskEntry 6 }
instance	OBJECT IDENTIFIER ::= { diskEntry 7 }
node-hierarchy	OBJECT IDENTIFIER ::= { diskEntry 8 }
target	OBJECT IDENTIFIER ::= { diskEntry 9 }
memory-controller-entry	OBJECT IDENTIFIER ::= { memory-controllerTbl 1 }
sunSmTreeProp	OBJECT IDENTIFIER ::= { memory-entry 1 }
sunSmNodeName	OBJECT IDENTIFIER ::= { memory-entry 2 }
entry-no	OBJECT IDENTIFIER ::= { memory-entry 3 }
pathname-element	OBJECT IDENTIFIER ::= { memory-entry 4 }
total-memory	OBJECT IDENTIFIER ::= { memory-entry 5 }
event-entry	OBJECT IDENTIFIER ::= { eventTbl 1 }
sunSmTreeProp	OBJECT IDENTIFIER ::= { system-led-entry 1 }
sunSmNodeName	OBJECT IDENTIFIER ::= { system-led-entry 2 }
entry-no	OBJECT IDENTIFIER ::= { system-led-entry 3 }
label	OBJECT IDENTIFIER ::= { system-led-entry 4 }
sys-led-alarm	OBJECT IDENTIFIER ::= { system-led-entry 5 }
state	OBJECT IDENTIFIER ::= { system-led-entry 6 }
memory-controllerTbl	OBJECT IDENTIFIER ::= { memory-controller 1 }
voltage-sensor-entry	OBJECT IDENTIFIER ::= { voltage-sensorTbl 1 }
ffbTbl	OBJECT IDENTIFIER ::= { ffb 1 }
sunSmTreeProp	OBJECT IDENTIFIER ::= { sunwUltra-5-10 1 }
sunSmNodeName	OBJECT IDENTIFIER ::= { sunwUltra-5-10 2 }
diskTbl	OBJECT IDENTIFIER ::= { disk 1 }
sunSmTreeProp	OBJECT IDENTIFIER ::= { fault-indicator 1 }
sunSmNodeName	OBJECT IDENTIFIER ::= { fault-indicator 2 }
state	OBJECT IDENTIFIER ::= { fault-indicator 3 }
sunSmTreeProp	OBJECT IDENTIFIER ::= { flashprom-entry 1 }
sunSmNodeName	OBJECT IDENTIFIER ::= { flashprom-entry 2 }
entry-no	OBJECT IDENTIFIER ::= { flashprom-entry 3 }
model	OBJECT IDENTIFIER ::= { flashprom-entry 4 }
reg	OBJECT IDENTIFIER ::= { flashprom-entry 5 }
fruidTbl	OBJECT IDENTIFIER ::= { fruid 1 }
sunSmTreeProp	OBJECT IDENTIFIER ::= { sunwUltra-1 1 }
sunSmNodeName	OBJECT IDENTIFIER ::= { sunwUltra-1 2 }
sunSmTreeProp	OBJECT IDENTIFIER ::= { sunwUltra-2 1 }
sunSmNodeName	OBJECT IDENTIFIER ::= { sunwUltra-2 2 }
sunSmTreeProp	OBJECT IDENTIFIER ::= { sysctrl-entry 1 }
sunSmNodeName	OBJECT IDENTIFIER ::= { sysctrl-entry 2 }
entry-no	OBJECT IDENTIFIER ::= { sysctrl-entry 3 }
instance	OBJECT IDENTIFIER ::= { sysctrl-entry 4 }
reg	OBJECT IDENTIFIER ::= { sysctrl-entry 5 }
rcr4u209	OBJECT IDENTIFIER ::= { hardware-rules 1 }
rcr4u210	OBJECT IDENTIFIER ::= { hardware-rules 2 }
rcr4u211	OBJECT IDENTIFIER ::= { hardware-rules 3 }
rcr4u212	OBJECT IDENTIFIER ::= { hardware-rules 4 }
rcr4u213	OBJECT IDENTIFIER ::= { hardware-rules 5 }
rcr4u214	OBJECT IDENTIFIER ::= { hardware-rules 6 }
rcr4u215	OBJECT IDENTIFIER ::= { hardware-rules 7 }
rcr4u216	OBJECT IDENTIFIER ::= { hardware-rules 8 }
rcr4u217	OBJECT IDENTIFIER ::= { hardware-rules 9 }
rcr4u219	OBJECT IDENTIFIER ::= { hardware-rules 10 }
rcr4u220	OBJECT IDENTIFIER ::= { hardware-rules 11 }
rcr4u221	OBJECT IDENTIFIER ::= { hardware-rules 12 }
sunSmTreeProp	OBJECT IDENTIFIER ::= { sunwUltra-4 1 }
sunSmNodeName	OBJECT IDENTIFIER ::= { sunwUltra-4 2 }
sunSmTreeProp	OBJECT IDENTIFIER ::= { sunwUltra-5 1 }
sunSmNodeName	OBJECT IDENTIFIER ::= { sunwUltra-5 2 }
sunSmTreeProp	OBJECT IDENTIFIER ::= { tsalarminfo-entry 1 }
sunSmNodeName	OBJECT IDENTIFIER ::= { tsalarminfo-entry 2 }
entry-no	OBJECT IDENTIFIER ::= { tsalarminfo-entry 3 }
fruEntry	OBJECT IDENTIFIER ::= { fruTbl 1 }
sunSmTreeProp	OBJECT IDENTIFIER ::= { sunwNetra-T4 1 }
sunSmNodeName	OBJECT IDENTIFIER ::= { sunwNetra-T4 2 }
sunSmTreeProp	OBJECT IDENTIFIER ::= { system-board 1 }
sunSmNodeName	OBJECT IDENTIFIER ::= { system-board 2 }
sunSmTreeProp	OBJECT IDENTIFIER ::= { fruid-entry 1 }
sunSmNodeName	OBJECT IDENTIFIER ::= { fruid-entry 2 }
entry-no	OBJECT IDENTIFIER ::= { fruid-entry 3 }
fru-description	OBJECT IDENTIFIER ::= { fruid-entry 4 }
fru-shortname	OBJECT IDENTIFIER ::= { fruid-entry 5 }
initial-hw-dash-level	OBJECT IDENTIFIER ::= { fruid-entry 6 }
initial-hw-rev-level	OBJECT IDENTIFIER ::= { fruid-entry 7 }
manufacturer-loc	OBJECT IDENTIFIER ::= { fruid-entry 8 }
path	OBJECT IDENTIFIER ::= { fruid-entry 9 }
sun-part-no	OBJECT IDENTIFIER ::= { fruid-entry 10 }
sun-serial-no	OBJECT IDENTIFIER ::= { fruid-entry 11 }
unix-timestamp32	OBJECT IDENTIFIER ::= { fruid-entry 12 }
vendor-name	OBJECT IDENTIFIER ::= { fruid-entry 13 }
networkTbl	OBJECT IDENTIFIER ::= { network 1 }
io-unitTbl	OBJECT IDENTIFIER ::= { io-unit 1 }
sunSmTreeProp	OBJECT IDENTIFIER ::= { ot-monitor-entry 1 }
sunSmNodeName	OBJECT IDENTIFIER ::= { ot-monitor-entry 2 }
entry-no	OBJECT IDENTIFIER ::= { ot-monitor-entry 3 }
name	OBJECT IDENTIFIER ::= { ot-monitor-entry 4 }
status	OBJECT IDENTIFIER ::= { ot-monitor-entry 5 }
memory-module-groupTbl	OBJECT IDENTIFIER ::= { memory-module-group 1 }
alarmTbl	OBJECT IDENTIFIER ::= { alarm 1 }
afbTbl	OBJECT IDENTIFIER ::= { afb 1 }
system	OBJECT IDENTIFIER ::= { reader4unt 1 }
system-board	OBJECT IDENTIFIER ::= { reader4unt 2 }
sunwUltra-1	OBJECT IDENTIFIER ::= { reader4unt 3 }
sunwUltra-2	OBJECT IDENTIFIER ::= { reader4unt 4 }
sunwUltra-4	OBJECT IDENTIFIER ::= { reader4unt 5 }
sunwUltra-30	OBJECT IDENTIFIER ::= { reader4unt 6 }
sunwUltra-60	OBJECT IDENTIFIER ::= { reader4unt 7 }
sunwUltra-80	OBJECT IDENTIFIER ::= { reader4unt 8 }
sunwUltra-5	OBJECT IDENTIFIER ::= { reader4unt 9 }
sunwUltra-10	OBJECT IDENTIFIER ::= { reader4unt 10 }
sunwUltra-5-10	OBJECT IDENTIFIER ::= { reader4unt 11 }
sunwUltraSPARC-IIi-cEngine	OBJECT IDENTIFIER ::= { reader4unt 12 }
sunwUltraAX-i2	OBJECT IDENTIFIER ::= { reader4unt 13 }
sunwNetra-T4	OBJECT IDENTIFIER ::= { reader4unt 14 }
sunwNetra-T12	OBJECT IDENTIFIER ::= { reader4unt 15 }
slot	OBJECT IDENTIFIER ::= { reader4unt 16 }
cpu-unit	OBJECT IDENTIFIER ::= { reader4unt 17 }
psus	OBJECT IDENTIFIER ::= { reader4unt 18 }
psu	OBJECT IDENTIFIER ::= { reader4unt 19 }
simm	OBJECT IDENTIFIER ::= { reader4unt 20 }
flashprom	OBJECT IDENTIFIER ::= { reader4unt 21 }
eeprom	OBJECT IDENTIFIER ::= { reader4unt 22 }
sysctrl	OBJECT IDENTIFIER ::= { reader4unt 23 }
fans	OBJECT IDENTIFIER ::= { reader4unt 24 }
fan	OBJECT IDENTIFIER ::= { reader4unt 25 }
memory	OBJECT IDENTIFIER ::= { reader4unt 26 }
memory-controller	OBJECT IDENTIFIER ::= { reader4unt 27 }
memory-module-group	OBJECT IDENTIFIER ::= { reader4unt 28 }
ffb	OBJECT IDENTIFIER ::= { reader4unt 29 }
afb	OBJECT IDENTIFIER ::= { reader4unt 30 }
sunwffb	OBJECT IDENTIFIER ::= { reader4unt 31 }
sunwafb	OBJECT IDENTIFIER ::= { reader4unt 32 }
hardware-rules	OBJECT IDENTIFIER ::= { reader4unt 33 }
io-controller	OBJECT IDENTIFIER ::= { reader4unt 34 }
io-device	OBJECT IDENTIFIER ::= { reader4unt 35 }
disk	OBJECT IDENTIFIER ::= { reader4unt 36 }
tape	OBJECT IDENTIFIER ::= { reader4unt 37 }
network	OBJECT IDENTIFIER ::= { reader4unt 38 }
io-unit	OBJECT IDENTIFIER ::= { reader4unt 39 }
fru	OBJECT IDENTIFIER ::= { reader4unt 40 }
lominfo	OBJECT IDENTIFIER ::= { reader4unt 41 }
asr	OBJECT IDENTIFIER ::= { reader4unt 42 }
events	OBJECT IDENTIFIER ::= { reader4unt 43 }
event	OBJECT IDENTIFIER ::= { reader4unt 44 }
alarms	OBJECT IDENTIFIER ::= { reader4unt 45 }
fault-indicator	OBJECT IDENTIFIER ::= { reader4unt 47 }
leds	OBJECT IDENTIFIER ::= { reader4unt 48 }
system-led	OBJECT IDENTIFIER ::= { reader4unt 49 }
tsalarminfo	OBJECT IDENTIFIER ::= { reader4unt 50 }
temp-monitors	OBJECT IDENTIFIER ::= { reader4unt 51 }
ot-monitor	OBJECT IDENTIFIER ::= { reader4unt 52 }
voltage-sensors	OBJECT IDENTIFIER ::= { reader4unt 53 }
voltage-sensor	OBJECT IDENTIFIER ::= { reader4unt 54 }
circuit-breakers	OBJECT IDENTIFIER ::= { reader4unt 55 }
circuit-breaker	OBJECT IDENTIFIER ::= { reader4unt 56 }
fruinfo	OBJECT IDENTIFIER ::= { reader4unt 57 }
fruid	OBJECT IDENTIFIER ::= { reader4unt 58 }
sysctrl-entry	OBJECT IDENTIFIER ::= { sysctrlTbl 1 }
sunSmTreeProp	OBJECT IDENTIFIER ::= { sunwNetra-T12 1 }
sunSmNodeName	OBJECT IDENTIFIER ::= { sunwNetra-T12 2 }
sunSmTreeProp	OBJECT IDENTIFIER ::= { afb-entry 1 }
sunSmNodeName	OBJECT IDENTIFIER ::= { afb-entry 2 }
entry-no	OBJECT IDENTIFIER ::= { afb-entry 3 }
buffer	OBJECT IDENTIFIER ::= { afb-entry 4 }
device-type	OBJECT IDENTIFIER ::= { afb-entry 5 }
model	OBJECT IDENTIFIER ::= { afb-entry 6 }
pathname-element	OBJECT IDENTIFIER ::= { afb-entry 7 }
sunSmTreeProp	OBJECT IDENTIFIER ::= { sunwUltra-80 1 }
sunSmNodeName	OBJECT IDENTIFIER ::= { sunwUltra-80 2 }
sunwffb-entry	OBJECT IDENTIFIER ::= { sunwffbTbl 1 }
fan-entry	OBJECT IDENTIFIER ::= { fanTbl 1 }
diskEntry	OBJECT IDENTIFIER ::= { diskTbl 1 }
sunSmTreeProp	OBJECT IDENTIFIER ::= { fruinfo 1 }
sunSmNodeName	OBJECT IDENTIFIER ::= { fruinfo 2 }

END
