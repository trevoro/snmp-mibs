-- *****************************************************************
-- Smartoptics SiteLight Network Element MIB
--
-- Nov 2000, Dirk Lutz
--
-- Copyright (c) 1999-2000 by Smartoptics AS
-- All rights reserved.
-- *****************************************************************

SL-NE-MIB DEFINITIONS ::= BEGIN

IMPORTS
	MODULE-IDENTITY, OBJECT-TYPE,
	enterprises, NOTIFICATION-TYPE 		FROM SNMPv2-SMI
	DisplayString, TruthValue	  		FROM SNMPv2-TC
	MODULE-COMPLIANCE, OBJECT-GROUP,
	NOTIFICATION-GROUP                  FROM SNMPv2-CONF
	InterfaceIndex		               	FROM IF-MIB;


smartoptics MODULE-IDENTITY
	LAST-UPDATED "200009260000Z"
	ORGANIZATION "Smartoptics"
	CONTACT-INFO
		"d.lutz@Smartoptics.com"
	DESCRIPTION
		"The MIB module is the root of the PL extension mibs."
	::= { enterprises 4515 }

sitelight 	OBJECT IDENTIFIER ::= { smartoptics 1 }
plproduct 	OBJECT IDENTIFIER ::= { smartoptics 100 }

-- Values for the sysObjectId

sone 		OBJECT IDENTIFIER ::= { plproduct 1 }  

t-4400r		OBJECT IDENTIFIER ::= { sone 1 }    -- t-4400 Root
t-4408 		OBJECT IDENTIFIER ::= { sone 10 }  	-- t-4408 

t-4900r   	OBJECT IDENTIFIER ::= { sone 1000 }    	-- t-4900 Root
t-4904 		OBJECT IDENTIFIER ::= { t-4904 1 }  	-- t-4904 & t-4902 
t-4808		OBJECT IDENTIFIER ::= { t-4808 2 }  	-- t-4808
t-4910  	OBJECT IDENTIFIER ::= { t-4910 3 }  	-- t-4910 (not longer available)
t-ROADM-2	OBJECT IDENTIFIER ::= { t-ROADM-2 }  	-- t-ROADM-2  
t-4906  	OBJECT IDENTIFIER ::= { t-4906 5 }  	-- t-4906  
t-1608  	OBJECT IDENTIFIER ::= { t-1608 6 }  	-- t-1608  
t-4900-IL  	OBJECT IDENTIFIER ::= { t-4900-IL 7 }  	-- t-4900-IL  
t-1608-CRY	OBJECT IDENTIFIER ::= { t-1608-CRY 8 }  -- t-1608-CRY  

t-4920r  	OBJECT IDENTIFIER ::= { sone 2000 }     -- t-4920 Root
t-4920  	OBJECT IDENTIFIER ::= { t-4920 1 }   	-- t-4920 

t-9900r 	OBJECT IDENTIFIER ::= { sone 2100 }  	-- t-9900 Root
t-9910  	OBJECT IDENTIFIER ::= { t-9910 1 }  	-- t-9910 
t-9910-C  	OBJECT IDENTIFIER ::= { t-9910-C 2 }  	-- t-9910-C 
t-9901  	OBJECT IDENTIFIER ::= { t-9901 3 }  	-- t-9901 CFP to CFP


t-ROADM-nro	OBJECT IDENTIFIER ::= { sone 2200 }  	-- New t-ROADM Root
t-ROADM-4ro1 	OBJECT IDENTIFIER ::= { t-ROADM-nro 1 }  	-- t-ROADM-4 Type A 
t-ROADM-4ro2  	OBJECT IDENTIFIER ::= { t-ROADM-nro 2 }  	-- t-ROADM-4 Type B 
t-ROADM-4ro3  	OBJECT IDENTIFIER ::= { t-ROADM-nro 3 }  	-- t-ROADM-4 Type C


-- The root for the service mibs

slService 	OBJECT IDENTIFIER ::= { sitelight 1 }

END
