--
--          Computer Network Technology, Corp.
--              6000 Nathan Lane North
--              Plymouth, Minnesota  55442
--
--                phone:  (763) 268-6000
--                  fax:  (763) 268-6800
--              support:  1-800-NET-TECH
--                email:  cnt.com
--
--      MIB Version:     1.0
--      Product Family:  CNT Zeus(2) Subagent(4) Transport(6)
--
-- +------------+ if you change this mib, you increment the version number.
-- | Attention! | Also, this MIB is supported by the master agent, and
-- +------------+ that agent must also be compiled with this mib version.
--

CNT246-MIB DEFINITIONS ::= BEGIN
 
        IMPORTS
                MODULE-IDENTITY, OBJECT-TYPE,
                Integer32, Counter64, TimeTicks,
                enterprises, IpAddress, Counter32
                        FROM SNMPv2-SMI
                DisplayString
                        FROM SNMPv2-TC;

        cnt2Transport MODULE-IDENTITY
                LAST-UPDATED "0103090000Z"
                ORGANIZATION "Computer Network Technology Corporation"
                CONTACT-INFO "Computer Network Technology Technical Support
                              6000 Nathan Lane North
                              Plymouth, Minnesota  55442
                              telephone:  (763) 268-6000
                              fax: (763) 268-6800
                              support: 1-800-NET-TECH"
                DESCRIPTION  "This defines the CNT Transport MIB.
                              The Transport layer provides network link for
                              CNT proprietary traffic."
                REVISION     "0103090000Z"
                DESCRIPTION  "Created."
                ::= { enterprises cnt(333) cnt2(2) cnt2Subagent(4) 6 }


        --- cnt2Subagent      OBJECT IDENTIFIER  ::=  {  cnt  4  }

        --- cnt2Transport        OBJECT IDENTIFIER  ::=  {  cnt2Subagent  6  }


cnt2TransportTable    OBJECT-TYPE
        SYNTAX     SEQUENCE OF Cnt2TransportEntry
        MAX-ACCESS not-accessible
        STATUS     current
        DESCRIPTION
                   "A list of Transport network link entries."
         ::=  { cnt2Transport  1 }

cnt2TransportEntry    OBJECT-TYPE
        SYNTAX     Cnt2TransportEntry
        MAX-ACCESS not-accessible
        STATUS     current
        DESCRIPTION
                   "A Transport network link entry."
        INDEX      {  cnt2TransportSlotIndex, cnt2TransportIndex  }
        ::=  { cnt2TransportTable 1 }

Cnt2TransportEntry  ::=  SEQUENCE {
        cnt2TransportSlotIndex         Integer32,
        cnt2TransportIndex             Integer32,
        cnt2TransportBus               Integer32,
        cnt2TransportVid               Integer32,
        cnt2TransportLinkType          INTEGER,
        cnt2TransportLinkDesc          DisplayString,
        cnt2TransportLinkStatus        INTEGER,
        cnt2TransportIPtosPrecedence   INTEGER,
        cnt2TransportIPtosDelay        INTEGER,
        cnt2TransportIPtosThruput      INTEGER,
        cnt2TransportIPtosRelibility   INTEGER,
        cnt2TransportRemoteIp          IpAddress,
        cnt2TransportProtocol          INTEGER,
        cnt2TransportCompressionOption INTEGER,
        cnt2TransportMaxXmitRate       Integer32,
        cnt2TransportResetTime         TimeTicks,
        cnt2TransportInPkts            Counter32,
        cnt2TransportInOctets          Counter64,
        cnt2TransportOutPkts           Counter32,
        cnt2TransportOutOctets         Counter64,
        cnt2TransportRexmit            Counter32,
        cnt2TransportOosHigh           Counter32,
        cnt2TransportStatsReset        INTEGER,
        cnt2TransportRawOutOctets      Counter64,
        cnt2TransportRawInOctets       Counter64,
        cnt2TransportWindowSize        Integer32,
        cnt2TransportSegmentSize       Integer32,
        cnt2TransportSegmentSizeHi     Integer32,
        cnt2TransportRoundTripTimer    Integer32,
        cnt2TransportHoldCount         Counter32,
        cnt2TransportHoldCountRatio1   Counter32,
        cnt2TransportHoldCountRatio2   Counter32,
        cnt2TransportHoldCountRatio3   Counter32,
        cnt2TransportTotalDisconnect   Counter32

        }

cnt2TransportSlotIndex OBJECT-TYPE 
        SYNTAX     Integer32 
        MAX-ACCESS read-only 
        STATUS     current
        DESCRIPTION
                  "The slot index for this Transport entry"
        ::=  {  cnt2TransportEntry  1  }

cnt2TransportIndex OBJECT-TYPE 
        SYNTAX     Integer32 
        MAX-ACCESS read-only 
        STATUS     current
        DESCRIPTION
                  "The relative index of the bus number in this Transport entry"
        ::=  {  cnt2TransportEntry  2  }

cnt2TransportBus OBJECT-TYPE 
        SYNTAX     Integer32 
        MAX-ACCESS read-only 
        STATUS     current
        DESCRIPTION
                  "The network link bus number"
        ::=  {  cnt2TransportEntry  3  }

cnt2TransportVid OBJECT-TYPE 
        SYNTAX     Integer32 
        MAX-ACCESS read-only 
        STATUS     current
        DESCRIPTION
                  "The virtual circuit number VCI.  If ATM is used, make
                   sure this Vid is configured the same as the VCI.  Failure
                   to do so will cause unexpected results"
        ::=  {  cnt2TransportEntry  4  }

cnt2TransportLinkType OBJECT-TYPE 
        SYNTAX     INTEGER {
                           atm(8),           -- ATM OC3
                           ethernet(9),      -- Ethernet
                           fibrechannel(10), -- Fiber Channel
                           fddi(11),         -- FDDI
                           ds3e3(12),        -- DS3/E3
                           lane(13),         -- LAN Emulation
                           ipv4(14),         -- IP
                           unknown(99)       -- Unknown Link type
                   }
        MAX-ACCESS read-only 
        STATUS     current
        DESCRIPTION
                  "The Link type supported by the CNT Transport layer. " 
        ::=  {  cnt2TransportEntry  5  }

cnt2TransportLinkDesc OBJECT-TYPE 
        SYNTAX     DisplayString 
        MAX-ACCESS read-only 
        STATUS     current
        DESCRIPTION
                  "The description of the network link suported by the
                   CNT Transport layer"
        ::=  {  cnt2TransportEntry  6  }

cnt2TransportLinkStatus OBJECT-TYPE 
        SYNTAX     INTEGER {
                           up(1),   -- the link connection is up
                           down(2)  -- the link connection is down
                   }
        MAX-ACCESS read-only 
        STATUS     current
        DESCRIPTION
                  "The network link's status. The link status indicates
                   if there is communication between the local node and
                   the remote node. "
        ::=  {  cnt2TransportEntry  7  }

cnt2TransportIPtosPrecedence OBJECT-TYPE 
        SYNTAX     INTEGER {
                           routine(1),
                           priority(2),
                           immediate(3),
                           flash(4),
                           flashOverride(5),
                           criticECP(6),
                           internetworkControl(7),
                           networkControl(8)
                   }
        MAX-ACCESS read-write 
        STATUS     current
        DESCRIPTION
                  "The service precedence of IP Type of Service use by this
                   link. There is an 8 bit field in an IP datagram that
                   specifies the type of service a datagram is requesting (or
                   hinting). It may then be used by the network to determine
                   paths and precedence for a given datagram. The specific
                   bits used may vary depending on the network (see RFC 791
                   for more details). The IpServiceType attribute can be used
                   on a per circuit basis to specify the bits to be set in the
                   IP datagram's service type field. Each Transport IP datagram
                   destined for the DestionationIpAddress will have this field
                   set. This attributes only applicable to IP providers. The
                   service precedence is in bit 0-2 of the 8 bit IP Type of
                   Service field."
        ::=  {  cnt2TransportEntry  8  }

cnt2TransportIPtosDelay OBJECT-TYPE 
        SYNTAX     INTEGER {
                           normal(1), -- Normal Delay
                           low(2)     -- Low Delay
                   }
        MAX-ACCESS read-write 
        STATUS     current
        DESCRIPTION
                  "The IP Type of Service Delay option use by this link.
                   The Delay bit is in bit 3 of the 8 bit IP Type of Service
                   field."
        ::=  {  cnt2TransportEntry  9  }

cnt2TransportIPtosThruput  OBJECT-TYPE 
        SYNTAX     INTEGER {
                           normal(1), -- Normal Throughput
                           high(2)    -- High Throughput
                   }
        MAX-ACCESS read-write 
        STATUS     current
        DESCRIPTION
                  "The IP Type of Service Throughput option use by this link.
                   The Throughput bit is in bit 4 of the 8 bit IP Type of
                   Service field."
        ::=  {  cnt2TransportEntry  10  }

cnt2TransportIPtosRelibility  OBJECT-TYPE 
        SYNTAX     INTEGER {
                           normal(1), -- Normal Relibility
                           high(2)    -- High Relibility
                   }
        MAX-ACCESS read-write 
        STATUS     current
        DESCRIPTION
                  "The IP Type of Service Relibility option use by this link.
                   The Relibility bit is in bit 5 of the 8 bit IP Type of
                   Service field."
        ::=  {  cnt2TransportEntry  11  }

cnt2TransportRemoteIp OBJECT-TYPE 
        SYNTAX     IpAddress 
        MAX-ACCESS read-only 
        STATUS     current
        DESCRIPTION
                  "The remote IP address. This address is set when Transport is
                   configured."
                  DEFVAL    { 0 }
        ::=  {  cnt2TransportEntry  12  }

cnt2TransportProtocol OBJECT-TYPE 
        SYNTAX     INTEGER {
                           sap(1)   -- SAP 0x869e type
                   }
        MAX-ACCESS read-only 
        STATUS     current
        DESCRIPTION
                  "The protocol used by this link. At the moment the only
                   protocol is SAP."
        ::=  {  cnt2TransportEntry  13  }

cnt2TransportCompressionOption OBJECT-TYPE 
        SYNTAX     INTEGER {
                           on (1),
                           off (2)
                   } 
        MAX-ACCESS read-write 
        STATUS     current
        DESCRIPTION
                  "Reflects whether compression option is turned on/off."
        ::=  {  cnt2TransportEntry  14  }

cnt2TransportMaxXmitRate OBJECT-TYPE 
        SYNTAX     Integer32 
        MAX-ACCESS read-write 
        STATUS     current
        DESCRIPTION
                  "The Maximum Transfer Rate of this link."
        ::=  {  cnt2TransportEntry  15  }

cnt2TransportResetTime OBJECT-TYPE 
        SYNTAX     TimeTicks 
        MAX-ACCESS read-only 
        STATUS     current
        DESCRIPTION
                  "The time, in seconds, when the stats was last reset."
        ::=  {  cnt2TransportEntry  16  }

cnt2TransportInPkts OBJECT-TYPE 
        SYNTAX     Counter32 
        MAX-ACCESS read-only 
        STATUS     current
        DESCRIPTION
                  "The number of packets transmitted to the link"
        ::=  {  cnt2TransportEntry  17  }

cnt2TransportInOctets OBJECT-TYPE 
        SYNTAX     Counter64 
        MAX-ACCESS read-only 
        STATUS     current
        DESCRIPTION
                  "The number of bytes transmitted to the link "
        ::=  {  cnt2TransportEntry  18  }

cnt2TransportOutPkts OBJECT-TYPE 
        SYNTAX     Counter32 
        MAX-ACCESS read-only 
        STATUS     current
        DESCRIPTION
                  "The number of packets transmitted out from the link"
        ::=  {  cnt2TransportEntry  19  }

cnt2TransportOutOctets OBJECT-TYPE 
        SYNTAX     Counter64 
        MAX-ACCESS read-only 
        STATUS     current
        DESCRIPTION
                  "The number of bytes transmitted out from the link "
        ::=  {  cnt2TransportEntry  20  }

cnt2TransportRexmit OBJECT-TYPE 
        SYNTAX     Counter32 
        MAX-ACCESS read-only 
        STATUS     current
        DESCRIPTION
                  "The number of packets being retransmitted"
        ::=  {  cnt2TransportEntry  21  }

cnt2TransportOosHigh OBJECT-TYPE 
        SYNTAX     Counter32 
        MAX-ACCESS read-only 
        STATUS     current
        DESCRIPTION
                  "The number of out of sequence packets received"
        ::=  {  cnt2TransportEntry  22  }

cnt2TransportStatsReset OBJECT-TYPE 
        SYNTAX     INTEGER {
                           all(1)   -- Reset all Transport statistics 
                   }
        MAX-ACCESS read-write 
        STATUS     current
        DESCRIPTION
                  "Setting this will result the Transport statistic to be reset"
        ::=  {  cnt2TransportEntry  23  }

cnt2TransportRawOutOctets OBJECT-TYPE 
        SYNTAX     Counter64 
        MAX-ACCESS read-only 
        STATUS     current
        DESCRIPTION
                  "The number of bytes transmitted out from the lower interface
		   of Transport layer. This is the amount of data after 
		   Compression plus Transport header. "
        ::=  {  cnt2TransportEntry  24  }

cnt2TransportRawInOctets OBJECT-TYPE 
        SYNTAX     Counter64 
        MAX-ACCESS read-only 
        STATUS     current
        DESCRIPTION
                  "The number of bytes received in from the lower interface
		   of Transport layer. This is the amount of data after 
		   Compression plus Transport header. "
        ::=  {  cnt2TransportEntry  25  }

cnt2TransportWindowSize OBJECT-TYPE 
        SYNTAX     Integer32 
        MAX-ACCESS read-only 
        STATUS     current
        DESCRIPTION
                  "The current window size, value is number buffers outstanding
		   on the connection"
        ::=  {  cnt2TransportEntry  26  }

cnt2TransportSegmentSize OBJECT-TYPE 
        SYNTAX     Integer32 
        MAX-ACCESS read-only 
        STATUS     current
        DESCRIPTION
                  " Range from (0 to 65532) If this value is non-zero, 
                    this value is used for segmentation. If equal to 0, 
                    then TransportSegmentSizeHi is what being used."
        ::=  {  cnt2TransportEntry  27  }

cnt2TransportSegmentSizeHi OBJECT-TYPE 
        SYNTAX     Integer32 
        MAX-ACCESS read-only 
        STATUS     current
        DESCRIPTION
                  " Range from (0 to 65532) If this value is used when 
                    TransportSegmentSize is set to 0. This value is
		    passed in from user layer's MTU size."
        ::=  {  cnt2TransportEntry  28  }


cnt2TransportRoundTripTimer OBJECT-TYPE 
        SYNTAX     Integer32 
        MAX-ACCESS read-only 
        STATUS     current
        DESCRIPTION
                  "The current round trip timer. each count is in 50msec."
        ::=  {  cnt2TransportEntry  29  }

cnt2TransportHoldCount OBJECT-TYPE 
        SYNTAX     Counter32 
        MAX-ACCESS read-only 
        STATUS     current
        DESCRIPTION
                  "The current hold count."
        ::=  {  cnt2TransportEntry  30  }

cnt2TransportHoldCountRatio1 OBJECT-TYPE 
        SYNTAX     Counter32 
        MAX-ACCESS read-only 
        STATUS     current
        DESCRIPTION
                  "Incremented when an ack is received and there is no data 
                   on the hold queue and there is no outstanding (unacked) data.
		   It indicates that transmission is idled until more data 
		   is received from the user."
        ::=  {  cnt2TransportEntry  31  }

cnt2TransportHoldCountRatio2 OBJECT-TYPE 
        SYNTAX     Counter32 
        MAX-ACCESS read-only 
        STATUS     current
        DESCRIPTION
                  "Incremented when an ack is received and there is no data 
                   on the hold queue but there is outstanding (unacked) data."
        ::=  {  cnt2TransportEntry  32  }

cnt2TransportHoldCountRatio3 OBJECT-TYPE 
        SYNTAX     Counter32 
        MAX-ACCESS read-only 
        STATUS     current
        DESCRIPTION
                  "Incremented when an ack is received and there is data 
                   on the hold queue ready to be sent."
        ::=  {  cnt2TransportEntry  33  }

cnt2TransportTotalDisconnect OBJECT-TYPE 
        SYNTAX     Counter32 
        MAX-ACCESS read-only 
        STATUS     current
        DESCRIPTION
                  "Total disconnects at Transport Layer."
        ::=  {  cnt2TransportEntry  34  }

END
