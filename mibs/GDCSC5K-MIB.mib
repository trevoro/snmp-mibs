-- *****************************************************************************
--                            	gdcsc5k.mib
-- *****************************************************************************
-- Copyright 1993 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive licence to use
-- this Specification in connection with the management of GDC's products.
--
-- This Specification is supplied "AS IS," and GDC makes no warranty,
-- either expressed or implied, as to the use operation, condition, or
-- performance of the Specification.

-- Revision History
-- Version   Date	Name		Description
-- 1.00A     27-Feb-95  M. Cyr          Initial Revision
-- 1.00B     01-Dec-95  C. Amorossi	Added gdcSc5000Shelf, gdcSc5000Highways,
--                                      gdcSc5000LTUConfig
-- 1.00C     19-Jun-96  C. Amorossi     Made gdcSc5000TimingTable obsolete
--					Modified description of sc5000ShelfNodeTypes
--                                      Added sc5000CircuitTable
-- 1.00D     02-Jul-96  C. Amorossi
--                                      Added sc5000ShelfClockMode,
--                                      sc5000ShelfClocks, sc5000ShelfAutoClockRevert,
--                                      sc5000ShelfRevertToPrimaryClk
-- *****************************************************************************

GDCSC5K-MIB DEFINITIONS ::= BEGIN

IMPORTS
	enterprises		FROM RFC1155-SMI
	OBJECT-TYPE		FROM RFC-1212
	DisplayString		FROM RFC1213-MIB
	SCinstance		FROM GDCMACRO-MIB;



gdc			OBJECT IDENTIFIER ::= { enterprises 498 }
sc              	OBJECT IDENTIFIER ::= { gdc 3 }
sc5000			OBJECT IDENTIFIER ::= { sc 2 }

gdcSc5000Version  	OBJECT IDENTIFIER ::= { sc5000 1 }
gdcSc5000Timing		OBJECT IDENTIFIER ::= { sc5000 2 }
gdcSc5000Shelf    	OBJECT IDENTIFIER ::= { sc5000 3 }
gdcSc5000Highways 	OBJECT IDENTIFIER ::= { sc5000 4 }
gdcSc5000LTUConfig	OBJECT IDENTIFIER ::= { sc5000 5 }
gdcSc5000Circuit        OBJECT IDENTIFIER ::= { sc5000 6 }

-- *****************************************************************************
--                        	Version group
--	Implementation of this group is mandatory for all systems.
-- *****************************************************************************

gdcSc5000MIBVersion		OBJECT-TYPE
	SYNTAX	DisplayString (SIZE (5))
	ACCESS	read-only
	STATUS  mandatory
	DESCRIPTION
		"The version number of the MIB, to allow products to 
		know which MIB is being supported.  The version number
		will be x.yzT where x is a major revision (1-9), y is a minor
		revision(0-9), z is a typo revision (0-9) and T indicates the
		MIB is still a test revision(A-Z).  When a release is complete
		no T should exist."
	::= { gdcSc5000Version 1 }

-- *****************************************************************************
--                           	Timing group
--	            Implementation of this group is optional.
-- *****************************************************************************

gdcSc5000TimingTable	OBJECT-TYPE
	SYNTAX	SEQUENCE OF GdcSc5000TimingEntry
	ACCESS	not-accessible
	STATUS	obsolete
	DESCRIPTION
		"A table that contains information about the 
		 source of shelf timing in the system. "
	::= { gdcSc5000Timing 1 }


gdcSc5000TimingEntry	OBJECT-TYPE
	SYNTAX	GdcSc5000TimingEntry
	ACCESS	not-accessible
	STATUS	obsolete
	DESCRIPTION
		"A list of information for each node in the system. "
	INDEX	{ gdcSc5000TimingIndex }
	::= { gdcSc5000TimingTable 1 }


GdcSc5000TimingEntry ::=
	SEQUENCE {
		gdcSc5000TimingIndex
			SCinstance,
		gdcSc5000SrcShelfTiming
			INTEGER
	}


gdcSc5000TimingIndex	OBJECT-TYPE
	SYNTAX	SCinstance
	ACCESS	read-only
	STATUS	obsolete
	DESCRIPTION
		"The value indicates the node number for which this
		entry contains management information.  The gdcSc5000TimingIndex
		is based off of the IFindex in MIB-II.  The gdcSc5000TimingIndex
		value is used to indicate the slot, line and drop of 
		the node in the SCM shelf that is being addressed.  
		
		The index is defined as: ssllddii.
		where ss is from 1-32, ll is 1,dd  is 0 and ii is 0. "


	::= { gdcSc5000TimingEntry 1 }

gdcSc5000SrcShelfTiming	OBJECT-TYPE
         SYNTAX INTEGER {
     	                  inhibit(1),	
			  fourMegClk(2),
			  eightKiloClk(3),
			  fourMegAnd8kClk(4)		
                         }
	 ACCESS read-write
    	 STATUS obsolete
   	 DESCRIPTION
     		 "Identifies which unit or units are the source of shelf 
		  timing defined as follows:

			If one unit is defined as fourMegClk(2)
				then only one other unit may be defined
				as eightKiloClk(3) and the remaining units
				must be defined as inhibit(1).

			If one unit is defined as eightKiloClk(3) 
				then only one other unit may be defined as
				fourMegClk(2) and the remaining units must
				be defined as inhibit(1).

			If one unit is defined as fourMegAnd8kClk(4)
				then the remaining units must be defined
				as inhibit(1). "

         ::= { gdcSc5000TimingEntry 2}

-- *****************************************************************************
-- 				Shelf group
--  This group provides information about the network elements that are 
--  currently active in the shelf.   
-- *****************************************************************************

sc5000ShelfNodeTypes	OBJECT-TYPE
	SYNTAX	OCTET STRING (SIZE (32))
	ACCESS  read-only
	STATUS  mandatory
	DESCRIPTION
		"Each octet contains the Node Type of the card occupying
		 the slot. Values are as follows:
			empty 		0
			vf288 		1
			sc5001 		2
			sc5520		3
			datx2011	4
			sc700G2		6
			sc700G3 	7
			sc616		12
			sc702G2		15
                        sc5034		17
                        scdualV34	18
			sc613           19
			sc5553          20
			sc611		21
			sc710d2  	23
			sc700grRP	24
			sc710d2RP	26
			mp7002          29
			uas7616		30
			scm		31
			sc521		32
			sc5002		33"
	::= { gdcSc5000Shelf 1 }

sc5000ShelfAdminStatus	OBJECT-TYPE
	SYNTAX	OCTET STRING (SIZE (32))
	ACCESS  read-write
	STATUS  mandatory
	DESCRIPTION
		"Each octet xx contains the Admin Statuses of the Network 
		 Elements(NEs) occupying slot xx.  Each octet is 
		 bitmapped as follows:

			bit 7:\
			bit 6:  Admin Status of NE in slot xx, line 4 

			bit 5:\
			bit 4:  Admin Status of NE in slot xx, line 3
			
			bit 3:\
			bit 2:  Admin Status of NE in slot xx, line 2
			
			bit 1:\
			bit 0:  Admin Status of NE in slot xx, line 1

		 Values per pair of bits are:

			01 Up
			10 Down
			00 No NE present"
	::= { gdcSc5000Shelf 2 }

sc5000ShelfOperStatus	OBJECT-TYPE
	SYNTAX	OCTET STRING (SIZE (32))
	ACCESS  read-only
	STATUS  mandatory
	DESCRIPTION
		"Each octet xx contains the Operational Statuses of the Network 
		 Elements(NEs) occupying slot xx.  Each octet is 
		 bitmapped as follows:

			bit 7:\
			bit 6:  Oper Status of NE in slot xx, line 4 

			bit 5:\
			bit 4:  Oper Status of NE in slot xx, line 3
			
			bit 3:\
			bit 2:  Oper Status of NE in slot xx, line 2
			
			bit 1:\
			bit 0:  Oper Status of NE in slot xx, line 1

		 Values per pair of bits are:

			01 Up
			10 Down
			00 No NE present"	
	::= { gdcSc5000Shelf 3 }


sc5000ShelfClockProvider	OBJECT-TYPE
	SYNTAX	OCTET STRING (SIZE (4))
	ACCESS	read-write
	STATUS 	obsolete
	DESCRIPTION
		"Octet 1 contains the slot number of the card providing the
		 4MHz clock.
		 Octet 2 contains the line number of the card providing the
		 4MHz clock.
		 Octet 3 contains the slot number of the card providing the
		 8kHz clock.
		 Octet 4 contains the line number of the card providing the
		 8kHz clock.
		 A value of 0 indicates that no card is providing the clock."
	::= { gdcSc5000Shelf 4 }

sc5000ShelfLTUHwayAssgn	OBJECT-TYPE
	SYNTAX	OCTET STRING (SIZE (4))
	ACCESS	read-write
	STATUS 	mandatory
	DESCRIPTION
		"Octet 1 contains the slot number of the LTU responsible for
		 Highway 1.
		 Octet 2 contains the slot number of the LTU responsible for
		 Highway 2.
		 Octet 3 contains the slot number of the LTU responsible for
		 Highway 3.
		 Octet 4 contains the slot number of the LTU responsible for
		 Highway 4.
		 If Highway x does not have an LTU then the value in Octet
		 x is 00."
	::= { gdcSc5000Shelf 5 }

sc5000ShelfClockMode	OBJECT-TYPE
	SYNTAX INTEGER {
			primary(1),	
			fallback(2),
			none(3)
		       }
	ACCESS	read-only
	STATUS 	mandatory
	DESCRIPTION
		"Indicates which LTU is supplying the clocks, LTU designated
		 as the primary or fallback. none(3) will only occur when the
		 SCM determines that neither of the cards assigned to be the
		 clock provider exists."
	::= { gdcSc5000Shelf 6 }

sc5000ShelfClocks	OBJECT-TYPE
	SYNTAX	OCTET STRING (SIZE (8))
	ACCESS	read-write
	STATUS 	mandatory
	DESCRIPTION
		"Octet 1 contains the slot number of the primary LTU 
		 responsible for providing the shelf clock.

		 Octet 2 contains the line number of the primary LTU 
		 responsible for providing the shelf clock.

		 Octet 3 contains the primary timing source.  Values are
		 internal (1), network (2), external (3), cascade (4), and
		 station (5).

		 Octet 4 contains the slot number of the DSE responsible
		 for providing the external timing source to the primary LTU.

		 Octet 5 contains the line number of the DSE responsible
		 for providing the external timing source to the primary LTU.

		 Octet 6 contains the slot number of the fallback LTU 
		 responsible for providing the shelf clock.

		 Octet 7 contains the line number of the fallback LTU 
		 responsible for providing the shelf clock.

		 Octet 8 contains the fallback timing source.  Values are
		 internal (1), network (2), cascade (4), and station (5)."
	::= { gdcSc5000Shelf 7 }

sc5000ShelfAutoClockRevert	OBJECT-TYPE
	SYNTAX INTEGER {
			enable(1),	
			disable(2)
		       }
	ACCESS	read-write
	STATUS 	mandatory
	DESCRIPTION
		"enable(1) indicates that the SCM will allow the primary 
		 LTU to resume providing the system timing."
	::= { gdcSc5000Shelf 8 }

sc5000ShelfRevertToPrimaryClk		OBJECT-TYPE
	SYNTAX INTEGER {
			normal(1), -- read-only
			execute(2) -- write-only
		       }
	ACCESS	read-write
	STATUS 	mandatory
	DESCRIPTION
		"execute(2) forces the primary LTU to resume providing
		 the system timing."
	::= { gdcSc5000Shelf 9 }

-- *****************************************************************************
-- 				Highway group
-- *****************************************************************************

sc5000HighwayTable	OBJECT-TYPE
	SYNTAX	SEQUENCE OF Sc5000HighwayEntry
	ACCESS	not-accessible
	STATUS	mandatory
	DESCRIPTION
		"A table that contains information about Highway and 
		 Time Slot allocation."
	::= { gdcSc5000Highways 1 }


sc5000HighwayEntry	OBJECT-TYPE
	SYNTAX	Sc5000HighwayEntry
	ACCESS	not-accessible
	STATUS	mandatory
	DESCRIPTION
		"A list of information for each highway."
	INDEX	{ sc5000HighwayNumber }
	::= { sc5000HighwayTable 1 }


Sc5000HighwayEntry ::=
	SEQUENCE {
		sc5000HighwayNumber
		INTEGER,
		sc5000HighwayAllocation
		OCTET STRING
	}


sc5000HighwayNumber	OBJECT-TYPE
	SYNTAX	INTEGER (1..4)
	ACCESS	read-only
	STATUS	mandatory
	DESCRIPTION
		"The value indicates the highway to be configured."
	::= { sc5000HighwayEntry 1 }

sc5000HighwayAllocation	OBJECT-TYPE
	SYNTAX	OCTET STRING (SIZE(96))
	ACCESS	read-write
	STATUS	mandatory
	DESCRIPTION
		"There are 3 Octets per Time Slot.
		 Octets 1,2,3 are representative of Time Slot 1,
		 Octets 4,5,6 are representative of Time Slot 2, etc.
		 In each grouping, the first octet indicates the shelf slot 
		 (1-32) to which the time slot has been assigned. 		 
		 The second octet indicates the line (1-4) to which the time
		 slot has been assigned.
		 The third octet defines the allocation for the time slot. The
		 values are as follows:
			1 = available
			2 = not available
			3 = Private Line (DSE Data)
			4 = SN/Restoral  (DBU data)
		If a time slot has not been assigned then the grouping is 
		00:00:01"
	::= { sc5000HighwayEntry 2 }

-- *****************************************************************************
-- 				LTU Configuration Group
-- *****************************************************************************

sc5000LTUConfigTable OBJECT-TYPE
	SYNTAX	SEQUENCE OF Sc5000LTUConfigEntry
	ACCESS	not-accessible
	STATUS	mandatory
	DESCRIPTION
		"A table that contains information about the configuration
		 of the LTUs in the shelf."
	::= { gdcSc5000LTUConfig 1 }

sc5000LTUConfigEntry	OBJECT-TYPE
	SYNTAX	Sc5000LTUConfigEntry
	ACCESS	not-accessible
	STATUS	mandatory
	DESCRIPTION
		"A list of information for each LTU in the shelf."
	INDEX	{ sc5000SlotNumber }
	::= { sc5000LTUConfigTable 1 }

Sc5000LTUConfigEntry ::=
	SEQUENCE {
		sc5000SlotNumber
		INTEGER,
		sc5000DS0Assign
		OCTET STRING,
		sc5000ConfigCSUMode		
		INTEGER
	}

sc5000SlotNumber	OBJECT-TYPE
	SYNTAX	INTEGER (1..32)
	ACCESS	read-only
	STATUS	mandatory
	DESCRIPTION
		"The value indicates shelf slot containing the LTU."
	::= { sc5000LTUConfigEntry 1 }

sc5000DS0Assign	OBJECT-TYPE
	SYNTAX	OCTET STRING (SIZE (32))
	ACCESS	read-write
	STATUS mandatory
	DESCRIPTION
		"One Octet per DS0.  Values are as follows:
			1 = Highway
			2 = Cascade
			3 = Busy Out
			4 = Not Present"
	::= { sc5000LTUConfigEntry 2 }

sc5000ConfigCSUMode	OBJECT-TYPE
	SYNTAX	INTEGER	{
			csuMode(1),
			concentratorMode(2)
			} 
	ACCESS	read-write
	STATUS	mandatory
	DESCRIPTION
		 " 'csuMode' indicates the unit is operating as a T1 channel
		   service unit with the payload from the network interface
		   connected to the payload of the cascade interface.

		   'concentratorMode' indicates the unit is operating as a T1
		    channel service unit with the T1 payloads groomed to 
		    cross connect within the shelf and the network and cascade
		    interfaces. "
	::= { sc5000LTUConfigEntry 3 }


-- *****************************************************************************
-- 				SC5000 Circuit Group
-- *****************************************************************************

sc5000CircuitTable	OBJECT-TYPE
	SYNTAX	SEQUENCE OF Sc5000CircuitEntry
	ACCESS	not-accessible
	STATUS	mandatory
	DESCRIPTION
		"A table that contains information about  
		 sc5000 circuits."
	::= { gdcSc5000Circuit 1 }


sc5000CircuitEntry	OBJECT-TYPE
	SYNTAX	Sc5000CircuitEntry
	ACCESS	not-accessible
	STATUS	mandatory
	DESCRIPTION
		"A list of information for each node in the system."
	INDEX	{ sc5000CircuitIndex }
	::= { sc5000CircuitTable 1 }


Sc5000CircuitEntry ::=
	SEQUENCE {
	sc5000CircuitIndex	SCinstance,
	sc5000CircuitType	INTEGER
	}


sc5000CircuitIndex	OBJECT-TYPE
	SYNTAX	SCinstance
	ACCESS	read-only
	STATUS	mandatory
	DESCRIPTION
	"Integer value which uniquely identifies the node to which this
    	entry is applicable. SCinstance is defined to be ssllddcc where:
    	ss (byte value) - physical shelf slot location (01-32)
    	ll (byte value) - line number (01-128)
    	dd (byte value) - drop number (00-31)
    	cc (byte value) - channel or extension number"
	::= { sc5000CircuitEntry 1 }


sc5000CircuitType	OBJECT-TYPE
        SYNTAX INTEGER {
	point-to-point(1),
	multipoint(2)
    	}	
    	ACCESS read-only
    	STATUS mandatory
    	DESCRIPTION
	"This object defines the circuit type."
    	::= { sc5000CircuitEntry 2 }

END
