--
-- CDM-570Traps.my
-- MIB generated by MG-SOFT Visual MIB Builder Version 2.1 Build 199
-- Wednesday, January 26, 2005 at 15:26:09
--

	CDM-570Traps DEFINITIONS ::= BEGIN

		IMPORTS 
			cdm570UnitAlarms, cdm570TxAlarms, cdm570RxAlarms, cdm570			
				FROM CDM-570			
			TRAP-TYPE			
				FROM RFC-1215;
	
	
	
--
-- Trap definitions
--
	
		cdm570LUnitAlarm TRAP-TYPE
			ENTERPRISE cdm570
			VARIABLES { cdm570UnitAlarms }
			DESCRIPTION
				"Unit Alarm Trap"
			::=  6247241
			
		cdm570LTxTrafficAlarm TRAP-TYPE
			ENTERPRISE cdm570
			VARIABLES { cdm570TxAlarms }
			DESCRIPTION
				"Tx Traffic Alarm Trap"
			::=  6247242
			
		cdm570LRxTrafficAlarm TRAP-TYPE
			ENTERPRISE cdm570
			VARIABLES { cdm570RxAlarms }
			DESCRIPTION
				"Rx Traffic Alarm Trap"
			::=  6247243
			
	
	END

--
-- CDM-570Traps.my
--
