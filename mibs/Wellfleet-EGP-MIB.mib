Wellfleet-EGP-MIB DEFINITIONS ::= BEGIN

-- Created by mdl2asn version 3.1
-- Creation date: Wed Aug 30 16:40:42 EDT 1995


    IMPORTS

      IpAddress, Counter
        FROM RFC1155-SMI
      OBJECT-TYPE
        FROM RFC-1212
      wfEgpGroup
        FROM Wellfleet-COMMON-MIB;


    wfEgp		OBJECT IDENTIFIER ::= { wfEgpGroup 1 }

    wfEgpDelete OBJECT-TYPE
        SYNTAX	INTEGER {
    		    created(1),
    		    deleted(2)
    		}
        ACCESS	read-write
        STATUS	mandatory
        DESCRIPTION
                "Create/Delete parameter for determining whether
                or not EGP is configured on this slot."
        DEFVAL	{ created }
        ::= { wfEgp 1 }

    wfEgpDisable OBJECT-TYPE
        SYNTAX	INTEGER {
    		    enabled(1),
    		    disabled(2)
    		}
        ACCESS	read-write
        STATUS	mandatory
        DESCRIPTION
                "Enable/Disable parameter for determining whether
                or not to startup EGP."
        DEFVAL	{ enabled }
        ::= { wfEgp 2 }

    wfEgpInMsgs OBJECT-TYPE
        SYNTAX	Counter
        ACCESS	read-only
        STATUS	mandatory
        DESCRIPTION
                "The aggregate number of EGP messages received in the box
                without error. This is part of the EGP group in Mib2. "
        ::= { wfEgp 3 }

    wfEgpInErrors OBJECT-TYPE
        SYNTAX	Counter
        ACCESS	read-only
        STATUS	mandatory
        DESCRIPTION
                "The total number of all EGP messages received in the box
                that had errors. This is part of the EGP group in Mib2. "
        ::= { wfEgp 4 }

    wfEgpOutMsgs OBJECT-TYPE
        SYNTAX	Counter
        ACCESS	read-only
        STATUS	mandatory
        DESCRIPTION
                "The total number of EGP locally generated messages from
                the box. This is part of the EGP group in Mib2. "
        ::= { wfEgp 5 }

    wfEgpOutErrors OBJECT-TYPE
        SYNTAX	Counter
        ACCESS	read-only
        STATUS	mandatory
        DESCRIPTION
                "The total number of locally generated EGP messages from
                the box that had errors. This is part of the EGP group in
                Mib2. "
        ::= { wfEgp 6 }

    wfEgpLocalAs OBJECT-TYPE
        SYNTAX	INTEGER(1..65535)
        ACCESS	read-write
        STATUS	mandatory
        DESCRIPTION
                "The NIC-assigned decimal number that identifies the local
                autonomous system."
        ::= { wfEgp 7 }

    wfEgpNeighTable OBJECT-TYPE
        SYNTAX	SEQUENCE OF WfEgpNeighEntry
        ACCESS	not-accessible
        STATUS	mandatory
        DESCRIPTION
                "The EGP Neighbor table contains information regarding this EGP
                router's EGP neighbors on a particular interface. This table
                follows the egpNeighTable exactly as specified in he EGP group
                in Mib 2."
        ::= { wfEgpGroup 2 }

    wfEgpNeighEntry OBJECT-TYPE
        SYNTAX	WfEgpNeighEntry
        ACCESS	not-accessible
        STATUS	mandatory
        DESCRIPTION
                "An entry in the EGP Neighbor table"
        INDEX	{ wfEgpNeighAddr }
        ::= { wfEgpNeighTable 1 }

    WfEgpNeighEntry ::= SEQUENCE {
    	    wfEgpNeighState
    		INTEGER,
    	    wfEgpNeighAddr
    		IpAddress,
    	    wfEgpNeighAs
    		INTEGER,
    	    wfEgpNeighInMsgs
    		Counter,
    	    wfEgpNeighInErrs
    		Counter,
    	    wfEgpNeighOutMsgs
    		Counter,
    	    wfEgpNeighOutErrs
    		Counter,
    	    wfEgpNeighInErrMsgs
    		Counter,
    	    wfEgpNeighOutErrMsgs
    		Counter,
    	    wfEgpNeighStateUps
    		Counter,
    	    wfEgpNeighStateDowns
    		Counter,
    	    wfEgpNeighIntervalHello
    		INTEGER,
    	    wfEgpNeighIntervalPoll
    		INTEGER,
    	    wfEgpNeighMode
    		INTEGER,
    	    wfEgpNeighEvent
    		INTEGER,
    	    wfEgpNeighBadAsns
    		Counter,
    	    wfEgpNeighBadCodes
    		Counter,
    	    wfEgpNeighBadHellos
    		Counter,
    	    wfEgpNeighBadIHUs
    		Counter,
    	    wfEgpNeighBadStatuses
    		Counter,
    	    wfEgpNeighBadChecksums
    		Counter,
    	    wfEgpNeighBadTypes
    		Counter,
    	    wfEgpNeighBadVersions
    		Counter,
    	    wfEgpNeighCmdOutOfSeqs
    		Counter,
    	    wfEgpNeighCmdRejects
    		Counter
        }

    wfEgpNeighState OBJECT-TYPE
        SYNTAX	INTEGER {
    		    idle(1),
    		    acquisition(2),
    		    down(3),
    		    up(4),
    		    cease(5)
    		}
        ACCESS	read-only
        STATUS	mandatory
        DESCRIPTION
                "The EGP state of the local system with respect to this
                entry's EGP neighbor.  Each EGP state is represented by a
                value that is one greater than the numerical value associated
                with said state in RFC 904."
        ::= { wfEgpNeighEntry 1 }

    wfEgpNeighAddr OBJECT-TYPE
        SYNTAX	IpAddress
        ACCESS	read-only
        STATUS	mandatory
        DESCRIPTION
                "The IP address of this entry's EGP neighbor."
        ::= { wfEgpNeighEntry 2 }

    wfEgpNeighAs OBJECT-TYPE
        SYNTAX	INTEGER
        ACCESS	read-only
        STATUS	mandatory
        DESCRIPTION
                "The NIC-assigned decimal number that identifies the remote
                autonomous system (AS) of this EGP peer. Zero should be
                specified if the AS number of the neighbor is not yet known."
        ::= { wfEgpNeighEntry 3 }

    wfEgpNeighInMsgs OBJECT-TYPE
        SYNTAX	Counter
        ACCESS	read-only
        STATUS	mandatory
        DESCRIPTION
                "The number of EGP messages received without error from
                this EGP peer. "
        ::= { wfEgpNeighEntry 4 }

    wfEgpNeighInErrs OBJECT-TYPE
        SYNTAX	Counter
        ACCESS	read-only
        STATUS	mandatory
        DESCRIPTION
                "The number of EGP messages received from this EGP peer
                that proved to be in error (e.g., bad EGP checksum)."
        ::= { wfEgpNeighEntry 5 }

    wfEgpNeighOutMsgs OBJECT-TYPE
        SYNTAX	Counter
        ACCESS	read-only
        STATUS	mandatory
        DESCRIPTION
                "The number of locally generated EGP messages to this
                EGP peer."
        ::= { wfEgpNeighEntry 6 }

    wfEgpNeighOutErrs OBJECT-TYPE
        SYNTAX	Counter
        ACCESS	read-only
        STATUS	mandatory
        DESCRIPTION
                "The number of locally generated EGP messages not sent
                to this EGP peer due to resource limitations within
                an EGP entity."
        ::= { wfEgpNeighEntry 7 }

    wfEgpNeighInErrMsgs OBJECT-TYPE
        SYNTAX	Counter
        ACCESS	read-only
        STATUS	mandatory
        DESCRIPTION
                "The number of EGP-defined error messages received
                from this EGP peer."
        ::= { wfEgpNeighEntry 8 }

    wfEgpNeighOutErrMsgs OBJECT-TYPE
        SYNTAX	Counter
        ACCESS	read-only
        STATUS	mandatory
        DESCRIPTION
                "The number of EGP-defined error messages sent to
                this EGP peer."
        ::= { wfEgpNeighEntry 9 }

    wfEgpNeighStateUps OBJECT-TYPE
        SYNTAX	Counter
        ACCESS	read-only
        STATUS	mandatory
        DESCRIPTION
                "The number of EGP state transitions to the UP state
                with this EGP peer."
        ::= { wfEgpNeighEntry 10 }

    wfEgpNeighStateDowns OBJECT-TYPE
        SYNTAX	Counter
        ACCESS	read-only
        STATUS	mandatory
        DESCRIPTION
                "The number of EGP state transitions from the UP state
                to any other state with this EGP peer."
        ::= { wfEgpNeighEntry 11 }

    wfEgpNeighIntervalHello OBJECT-TYPE
        SYNTAX	INTEGER
        ACCESS	read-only
        STATUS	mandatory
        DESCRIPTION
                "The interval between EGP Hello command retransmissions (in
                seconds).  This represents the t1 timer as defined in RFC 904."
        ::= { wfEgpNeighEntry 12 }

    wfEgpNeighIntervalPoll OBJECT-TYPE
        SYNTAX	INTEGER
        ACCESS	read-only
        STATUS	mandatory
        DESCRIPTION
                "The interval between EGP poll command retransmissions (in
                seconds).  This represents the t3 timer as defined in RFC 904."
        ::= { wfEgpNeighEntry 13 }

    wfEgpNeighMode OBJECT-TYPE
        SYNTAX	INTEGER {
    		    active(1),
    		    passive(2)
    		}
        ACCESS	read-only
        STATUS	mandatory
        DESCRIPTION
                "The polling mode of this EGP entity, either passive
                or active."
        ::= { wfEgpNeighEntry 14 }

    wfEgpNeighEvent OBJECT-TYPE
        SYNTAX	INTEGER
        ACCESS	read-only
        STATUS	mandatory
        DESCRIPTION
                "The EGP event that occurred on the local interface with respect
                to this entry's EGP neighbor.  "
        ::= { wfEgpNeighEntry 15 }

    wfEgpNeighBadAsns OBJECT-TYPE
        SYNTAX	Counter
        ACCESS	read-only
        STATUS	mandatory
        DESCRIPTION
                "The number of received EGP messages that contained an
                unrecognized AS number in the EGP header."
        ::= { wfEgpNeighEntry 16 }

    wfEgpNeighBadCodes OBJECT-TYPE
        SYNTAX	Counter
        ACCESS	read-only
        STATUS	mandatory
        DESCRIPTION
                "The number of received EGP messages that contained an
                unrecognized value in the Code field in the EGP header."
        ::= { wfEgpNeighEntry 17 }

    wfEgpNeighBadHellos OBJECT-TYPE
        SYNTAX	Counter
        ACCESS	read-only
        STATUS	mandatory
        DESCRIPTION
                "The number of unexpected Hello neighbor reachability
                messages received by EGP.  A Hello message is unexpected
                when received from a passive peer."
        ::= { wfEgpNeighEntry 18 }

    wfEgpNeighBadIHUs OBJECT-TYPE
        SYNTAX	Counter
        ACCESS	read-only
        STATUS	mandatory
        DESCRIPTION
                "The number of unexpected I Hear You neighbor reachability
                messages received by EGP.  A I Hear You message is unexpected
                when received in the absence of a prior Hello message."
        ::= { wfEgpNeighEntry 19 }

    wfEgpNeighBadStatuses OBJECT-TYPE
        SYNTAX	Counter
        ACCESS	read-only
        STATUS	mandatory
        DESCRIPTION
                "The number of received EGP messages that contained an
                unrecognized value in the Status field in the EGP header."
        ::= { wfEgpNeighEntry 20 }

    wfEgpNeighBadChecksums OBJECT-TYPE
        SYNTAX	Counter
        ACCESS	read-only
        STATUS	mandatory
        DESCRIPTION
                "The number of received EGP messages that contained a
                faulty checksum in the EGP header."
        ::= { wfEgpNeighEntry 21 }

    wfEgpNeighBadTypes OBJECT-TYPE
        SYNTAX	Counter
        ACCESS	read-only
        STATUS	mandatory
        DESCRIPTION
                "The number of received EGP messages that contained an
                unrecognized value in the Type field in the EGP header."
        ::= { wfEgpNeighEntry 22 }

    wfEgpNeighBadVersions OBJECT-TYPE
        SYNTAX	Counter
        ACCESS	read-only
        STATUS	mandatory
        DESCRIPTION
                "The number of received EGP messages that contained an
                invalid EGP Version number in the EGP header. This EGP
                implementation supports EGP Version 2."
        ::= { wfEgpNeighEntry 23 }

    wfEgpNeighCmdOutOfSeqs OBJECT-TYPE
        SYNTAX	Counter
        ACCESS	read-only
        STATUS	mandatory
        DESCRIPTION
                "The number of times EGP received an out-of-sequence command
                message.  An out-of-sequence message indicates that a prior
                message, issued by an EGP peer, has been missed."
        ::= { wfEgpNeighEntry 24 }

    wfEgpNeighCmdRejects OBJECT-TYPE
        SYNTAX	Counter
        ACCESS	read-only
        STATUS	mandatory
        DESCRIPTION
                "The number of times EGP refused to respond to a received
                command. Such refusal could be generated by receipt of a
                neighbor acquisition message from an unknown AS, or by
                receipt of a faulty EGP message (for example, one with a
                bad checksum) from a known neighbor."
        ::= { wfEgpNeighEntry 25 }

    wfEgpCfgNeighTable OBJECT-TYPE
        SYNTAX	SEQUENCE OF WfEgpCfgNeighEntry
        ACCESS	not-accessible
        STATUS	mandatory
        DESCRIPTION
                "This table is used to configure the parameters for a relationship
                with a particular local EGP neighbor. This table is proprietary
                and not part of the standard EGP MIB. "
        ::= { wfEgpGroup 3 }

    wfEgpCfgNeighEntry OBJECT-TYPE
        SYNTAX	WfEgpCfgNeighEntry
        ACCESS	not-accessible
        STATUS	mandatory
        DESCRIPTION
                "An entry in the EGP Cfg Neighbor table"
        INDEX	{ wfEgpCfgNeighRemoteAddr }
        ::= { wfEgpCfgNeighTable 1 }

    WfEgpCfgNeighEntry ::= SEQUENCE {
    	    wfEgpCfgNeighDelete
    		INTEGER,
    	    wfEgpCfgNeighDisable
    		INTEGER,
    	    wfEgpCfgNeighState
    		INTEGER,
    	    wfEgpCfgNeighLocalAddr
    		IpAddress,
    	    wfEgpCfgNeighRemoteAddr
    		IpAddress,
    	    wfEgpCfgNeighGatewayMode
    		INTEGER,
    	    wfEgpCfgNeighAcqMode
    		INTEGER,
    	    wfEgpCfgNeighPollMode
    		INTEGER,
    	    wfEgpCfgNeighHelloTimer
    		INTEGER,
    	    wfEgpCfgNeighPollTimer
    		INTEGER
        }

    wfEgpCfgNeighDelete OBJECT-TYPE
        SYNTAX	INTEGER {
    		    created(1),
    		    deleted(2)
    		}
        ACCESS	read-write
        STATUS	mandatory
        DESCRIPTION
                "Create/Delete parameter. Users perform an SNMP SET
                operation on this object to create/delete an EGP
                neighbor relationship with the specified local IP
                address. "
        DEFVAL	{ created }
        ::= { wfEgpCfgNeighEntry 1 }

    wfEgpCfgNeighDisable OBJECT-TYPE
        SYNTAX	INTEGER {
    		    enabled(1),
    		    disabled(2)
    		}
        ACCESS	read-write
        STATUS	mandatory
        DESCRIPTION
                "Enable/Disable parameter. Users perforn an SNMP SET
                operation on this object to enable/disable an EGP
                Neighbor relationship with the specified local IP address.
                Default is enabled.
                This variable is also used to trigger operator-initiated
                Start and Stop events in the EGP FSM.  It takes the place
                of the egpNeighEventTrigger variable. When set, this variable
                causes a Start or Stop event on the specified neighbor, as
                specified on pages 8-10 of RFC 904. Briefly, a Start event
                causes an Idle peer to begin neighbor acquisition and a
                non-Idle peer to reinitiate neighbor acquisition.  A stop
                event causes a non-Idle peer to return to the Idle state
                until a Start event occurs, either via egpNeighEventTrigger
                or otherwise. This parameter is part of MIB 2.
                NOTE: The FSM is only affected if EGP is Enabled on the
                slot."
        DEFVAL	{ enabled }
        ::= { wfEgpCfgNeighEntry 2 }

    wfEgpCfgNeighState OBJECT-TYPE
        SYNTAX	INTEGER {
    		    up(1),
    		    down(2),
    		    init(3),
    		    notpresent(4)
    		}
        ACCESS	read-only
        STATUS	mandatory
        DESCRIPTION
                "This parameter relfects the current state of the specified
                EGP neighbor relationship with specfied local IP address. "
        DEFVAL	{ notpresent }
        ::= { wfEgpCfgNeighEntry 3 }

    wfEgpCfgNeighLocalAddr OBJECT-TYPE
        SYNTAX	IpAddress
        ACCESS	read-only
        STATUS	mandatory
        DESCRIPTION
                "The IP address of the local interface that provides the
                EGP connection to the remote autonomous system."
        ::= { wfEgpCfgNeighEntry 4 }

    wfEgpCfgNeighRemoteAddr OBJECT-TYPE
        SYNTAX	IpAddress
        ACCESS	read-only
        STATUS	mandatory
        DESCRIPTION
                "The IP address of the remote interface that provides the
                EGP connection to the remote autonomous system."
        ::= { wfEgpCfgNeighEntry 5 }

    wfEgpCfgNeighGatewayMode OBJECT-TYPE
        SYNTAX	INTEGER {
    		    noncore(1),
    		    core(2)
    		}
        ACCESS	read-write
        STATUS	mandatory
        DESCRIPTION
                "This parameter specifies the EGP gateway mode of this IP
                interface. The two modes are core and non-core. When the
                interface is configured in non-core mode, it will advertise
                and forward only traffic that originated or is destined
                for a local network within its AS. When configured for
                this mode, certain EGP Export Route Filters are auto-
                matically configured for this interface. When the interface
                is configured in Core mode, it can advertise and forward
                traffic to networks interior or exterior to its local AS.
                The default is Core mode."
        DEFVAL	{ core }
        ::= { wfEgpCfgNeighEntry 6 }

    wfEgpCfgNeighAcqMode OBJECT-TYPE
        SYNTAX	INTEGER {
    		    active(1),
    		    passive(2)
    		}
        ACCESS	read-write
        STATUS	mandatory
        DESCRIPTION
                "This parameter specifies which of the two neighbors will
                initiate EGP connections. This configures the mode for the
                local EGP neighbor.  Note: At least one neighbor must be
                in the Active mode."
        DEFVAL	{ passive }
        ::= { wfEgpCfgNeighEntry 7 }

    wfEgpCfgNeighPollMode OBJECT-TYPE
        SYNTAX	INTEGER {
    		    active(1),
    		    passive(2),
    		    both(3)
    		}
        ACCESS	read-write
        STATUS	mandatory
        DESCRIPTION
                "This parameter specifies the type of neighbor reachability
                algorithm this local EGP neighbor will execute.  "
        DEFVAL	{ both }
        ::= { wfEgpCfgNeighEntry 8 }

    wfEgpCfgNeighHelloTimer OBJECT-TYPE
        SYNTAX	INTEGER(30..120)
        ACCESS	read-write
        STATUS	mandatory
        DESCRIPTION
                "This parameter specifies the interval between EGP Hello
                command retransmissions (in seconds) by the local EGP neighbor.
                This represents the t1 timer as defined in RFC 904."
        DEFVAL	{ 60 }
        ::= { wfEgpCfgNeighEntry 9 }

    wfEgpCfgNeighPollTimer OBJECT-TYPE
        SYNTAX	INTEGER(120..480)
        ACCESS	read-write
        STATUS	mandatory
        DESCRIPTION
                "This parameter specifies the interval between EGP poll
                command retransmissions (in hundredths of a second) by the
                local EGP neighbor. This represents the t3 timer as defined
                in RFC 904."
        DEFVAL	{ 180 }
        ::= { wfEgpCfgNeighEntry 10 }

    END  -- Wellfleet-EGP-MIB
