--
-- StoneBeat FullCluster MIB file begins
--

SBFC-MIB DEFINITIONS ::= BEGIN

--
-- Change as necessary
--

IMPORTS
        private, NetworkAddress, IpAddress, Counter, Gauge,
		TimeTicks, enterprises
            FROM RFC1155-SMI
	OBJECT-TYPE 				
	    FROM RFC-1212
	DisplayString 				
	    FROM RFC1213-MIB;

stonesoft	OBJECT IDENTIFIER ::= { enterprises 1369 }
stoneSystem	OBJECT IDENTIFIER ::= { stonesoft 1 }
products	OBJECT IDENTIFIER ::= { stonesoft 2 }
fullCluster     OBJECT IDENTIFIER ::= { products 2 } 
sbfcModule      OBJECT IDENTIFIER ::= { fullCluster 4 }
sbfcDriver      OBJECT IDENTIFIER ::= { fullCluster 5 }

	agentDescr OBJECT-TYPE
		SYNTAX  DisplayString (SIZE (0..255))
		ACCESS  read-only
		STATUS  mandatory
		DESCRIPTION
			"The SNMP agent's description of itself."
              ::= { stoneSystem 1 }

	agentVersion OBJECT-TYPE
		SYNTAX  DisplayString (SIZE (0..255))
		ACCESS  read-only
		STATUS  mandatory
		DESCRIPTION
			"The SNMP agent mib version."
              ::= { stoneSystem 2 }

        sbfcClusterID OBJECT-TYPE
                SYNTAX INTEGER
                ACCESS read-only
                STATUS mandatory
                DESCRIPTION
                        "The StoneBeat cluster ID."
              ::= { fullCluster 1 }

        sbfcMemberID OBJECT-TYPE
                SYNTAX INTEGER
                ACCESS read-only
                STATUS mandatory
                DESCRIPTION
                        "The ID of this node in the StoneBeat FullCluster."
              ::= { fullCluster 2 }

        sbfcModuleVersion OBJECT-TYPE
                SYNTAX DisplayString (SIZE (0..255))
                ACCESS read-only
                STATUS mandatory
                DESCRIPTION
                        "The version of the StoneBeat FullCluster
                         module on this host."
              ::= { sbfcModule 1 }
              
        sbfcModulePatchLevel OBJECT-TYPE
                SYNTAX DisplayString (SIZE (0..255))
                ACCESS read-only
                STATUS mandatory
                DESCRIPTION
                        "The patch level of the StoneBeat FullCluster
                         module"
              ::= { sbfcModule 2 }

        sbfcDriverPatchLevel OBJECT-TYPE
                SYNTAX DisplayString (SIZE (0..255))
                ACCESS read-only
                STATUS mandatory
                DESCRIPTION
                        "The patch level of the StoneBeat FullCluster
                         driver"
              ::= { sbfcDriver 2 }

        sbfcDriverVersion OBJECT-TYPE
                SYNTAX DisplayString (SIZE (0..255))
                ACCESS read-only
                STATUS mandatory
                DESCRIPTION
                        "The version of the StoneBeat FullCluster
                         driver on this host."
              ::= { sbfcDriver 1 }

        sbfcMaxNodeID OBJECT-TYPE
                SYNTAX INTEGER
                ACCESS read-only
                STATUS mandatory
                DESCRIPTION
                        "The maximum number of nodes in this cluster and
                         at the same time the highes possible index in
                         the status sequences."
              ::= { fullCluster 3 }

        sbfcOSName OBJECT-TYPE
                SYNTAX DisplayString (SIZE (0..255))
                ACCESS read-only
                STATUS mandatory
                DESCRIPTION
                        "Name of the operating system"
              ::= { fullCluster 6 }

        sbfcOSVersion OBJECT-TYPE
                SYNTAX DisplayString (SIZE (0..255))
                ACCESS read-only
                STATUS mandatory
                DESCRIPTION
                        "Operating system version"
              ::= { fullCluster 7 }

        sbfcAgeOfStatus OBJECT-TYPE
                SYNTAX INTEGER
                ACCESS read-only
                STATUS mandatory
                DESCRIPTION
                        "Time in seconds since we got the cluster status"
              ::= { fullCluster 8 }
                
        sbfcNodeTable OBJECT-TYPE
                SYNTAX SEQUENCE OF SbfcNodeEntry
                ACCESS not-accessible
                STATUS mandatory
                DESCRIPTION
                        "A list of node entries. The number of entries
                         is given by sbfcMaxNodeID."
              ::= { fullCluster 9 }

        sbfcNodeEntry OBJECT-TYPE
                SYNTAX SbfcNodeEntry
                ACCESS not-accessible
                STATUS mandatory
                DESCRIPTION
                        "A node entry containing object describing
                         each node in the cluster."
              ::= { sbfcNodeTable 1 }

        SbfcNodeEntry ::=
            SEQUENCE {
                sbfcNodeID
                    INTEGER,
                sbfcNodeStatus
                    INTEGER,
                sbfcNodeLoad
                    INTEGER,
                sbfcNodeControlIP
                    IpAddress,
                sbfcNodeControlPort
                    INTEGER
            }
        
        sbfcNodeID OBJECT-TYPE
                SYNTAX INTEGER (1..65535)
                ACCESS read-only
                STATUS mandatory
                DESCRIPTION
                        "A unique value for each node. Its value ranges 
                         between 1 and the value of sbfcMaxNodeID."
              ::= { sbfcNodeEntry 1 }

        sbfcNodeStatus OBJECT-TYPE
                SYNTAX INTEGER {
                        offline(1),
                        going-online(2),
                        online(3),
                        going-offline(4),
                        unknown(5),
                        offline-ready-for-restart(6),
                        online-ready-for-restart(7),
                        locked-offline(8),
                        going-locked-offline(9),
                        locked-online(10),
                        going-locked-online(11),
                        locked-offline-ready-for-restart(12),
                        locked-online-ready-for-restart(13),
                        standby(14),
                        going-standby(15),
                        standby-ready-for-restart(16)
                }
                ACCESS read-only
                STATUS mandatory
                DESCRIPTION
                        "The node status"
              ::= { sbfcNodeEntry 2 }

        sbfcNodeLoad OBJECT-TYPE
                SYNTAX INTEGER
                ACCESS read-only
                STATUS mandatory
                DESCRIPTION
                        "The load level of this node. The value is a
                         percentage of the capacity of the node."
              ::= { sbfcNodeEntry 3 }

        sbfcNodeCapacity OBJECT-TYPE
                SYNTAX INTEGER
                ACCESS read-only
                STATUS mandatory
                DESCRIPTION
                        "The capacity of this node"
              ::= { sbfcNodeEntry 4 }

        sbfcNodeControlIp OBJECT-TYPE
                SYNTAX IpAddress
                ACCESS read-only
                STATUS mandatory        
                DESCRIPTION
                        "The control IP address of this node"
              ::= { sbfcNodeEntry 5 }

        sbfcNodeControlPort OBJECT-TYPE
                SYNTAX INTEGER (0..65535)
                ACCESS read-only
                STATUS mandatory
                DESCRIPTION
                        "The control port number of this node
                         0 denotes NULL"
              ::= { sbfcNodeEntry 6 }                         


END

--
-- StoneBeat FullCluster MIB file ends
--
