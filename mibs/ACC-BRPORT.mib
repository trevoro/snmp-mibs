ACC-BRPORT DEFINITIONS ::= BEGIN

    IMPORTS
 	 OBJECT-TYPE, Counter, Gauge FROM RFC1155-SMI
	 accTrapLogSeqNum FROM ACC-SYSTEM
	accBRG, DisplayString FROM ACC-MIB;

-- Bridge Port Group
      accBrPort  OBJECT IDENTIFIER ::= { accBRG 3 }
	accBrPortInfo	OBJECT IDENTIFIER ::= { accBrPort 1 }
	  accBrPortStats OBJECT IDENTIFIER ::= { accBrPortInfo 1 }
	    accBrPortInNUcastPkts	OBJECT-TYPE   
			SYNTAX	Counter
			ACCESS	read-only
			STATUS	mandatory
			DESCRIPTION
                          " Number of non-unicast packets received"
			::= { accBrPortStats 1 }
	    accBrPortInUcastPkts	OBJECT-TYPE   
			SYNTAX	Counter
			ACCESS	read-only
			STATUS	mandatory
			DESCRIPTION
                         " Number of unicast packets received"
			::= { accBrPortStats 2 }
	    accBrPortInDupPkts	OBJECT-TYPE   
			SYNTAX	Counter
			ACCESS	read-only
			STATUS	mandatory
			DESCRIPTION
                         " Number of in packets duplicated"
			::= { accBrPortStats 3 }
	    accBrPortOutNUcastPkts	OBJECT-TYPE   
			SYNTAX	Counter
			ACCESS	read-only
			STATUS	mandatory
			DESCRIPTION
                         " Number of non-unicast packets sent"
			::= { accBrPortStats 4 }
	    accBrPortOutUcastPkts	OBJECT-TYPE   
			SYNTAX	Counter
			ACCESS	read-only
			STATUS	mandatory
			DESCRIPTION
                         " Number of unicast packets sent"
			::= { accBrPortStats 5 }
	    accBrPortStpInPkts	OBJECT-TYPE   
			SYNTAX	Counter
			ACCESS	read-only
			STATUS	mandatory
			DESCRIPTION
                         " Number of spanning tree packets recieved"
			::= { accBrPortStats 6 }
	    accBrPortStpOutPkts		OBJECT-TYPE   
			SYNTAX	Counter
			ACCESS	read-only
			STATUS	mandatory
			DESCRIPTION
                         " Number of spanning tree packets sent"
			::= { accBrPortStats 7 }
	    accBrPortOutDelayDiscPkts	OBJECT-TYPE   
			SYNTAX	Counter
			ACCESS	read-only
			STATUS	mandatory
			DESCRIPTION
                         " Number of output packets dropped because
                           they were held in queue too long"
			::= { accBrPortStats 8 }
	    accBrPortOutPrioDiscPkts	OBJECT-TYPE   
			SYNTAX	Counter
			ACCESS	read-only
			STATUS	mandatory
			DESCRIPTION
                         " Packets discarded on ouput by the
                           protocol priority filter mechanism"
			::= { accBrPortStats 9 }
	    accBrPortOutQLen	OBJECT-TYPE   
			SYNTAX	Gauge
			ACCESS	read-only
			STATUS	mandatory
			DESCRIPTION
                         " Length of port output queue"
			::= { accBrPortStats 10 }
	    accBrPortInDiscPkts		OBJECT-TYPE   
			SYNTAX	Counter
			ACCESS	read-only
			STATUS	mandatory
			DESCRIPTION
                         " Number of bridge packets discarded
                           at input"
			::= { accBrPortStats 11 }
	  accBrPortStpPriority	OBJECT-TYPE   
			SYNTAX	INTEGER (0..255)
			ACCESS	read-write
			STATUS	mandatory
			DESCRIPTION
                         " Relative STP priority of this port"
			::= { accBrPortInfo 2 }
	  accBrPortId	OBJECT-TYPE   
			SYNTAX	OCTET STRING
			ACCESS	read-only
			STATUS	mandatory
			DESCRIPTION
                         " Port ID"
			::= { accBrPortInfo 3 }
	  accBrPortState	OBJECT-TYPE   
			SYNTAX	INTEGER {
				disabled(0),
				blocking(1),
				listening(2),
				learning(3),
				forwarding(4)
				}
			ACCESS	read-write
			STATUS	mandatory
			DESCRIPTION
			 " accBrPortState reports the operational status
			   of the port; it is writable for backward
			   compatibility (writes also update
			   accBrPortAdminStatus).
			   "
			::= { accBrPortInfo 5 }
	  accBrPortStpPathCost	OBJECT-TYPE   
			SYNTAX	INTEGER (0..65535)
			ACCESS	read-write
			STATUS	mandatory
			DESCRIPTION
                         " Path cost"
			::= { accBrPortInfo 6 }
	  accBrPortStpDesRoot	OBJECT-TYPE   
			SYNTAX	OCTET STRING
			ACCESS	read-only
			STATUS	mandatory
			DESCRIPTION
                         " Designated root"
			::= { accBrPortInfo 7 }
	  accBrPortStpDesCost	OBJECT-TYPE   
			SYNTAX	INTEGER (0..65535)
			ACCESS	read-only
			STATUS	mandatory
			DESCRIPTION
                         " Cost to designated root"
			::= { accBrPortInfo 8 }
	  accBrPortStpDesBridge		OBJECT-TYPE   
			SYNTAX	OCTET STRING
			ACCESS	read-only
			STATUS	mandatory
			DESCRIPTION
                         " Designated bridge"
			::= { accBrPortInfo 9 }
	  accBrPortStpDesPort	OBJECT-TYPE   
			SYNTAX	OCTET STRING
			ACCESS	read-only
			STATUS	mandatory
			DESCRIPTION
                         " Designated port"
			::= { accBrPortInfo 10 }
	  accBrPortAdminStatus OBJECT-TYPE   
			SYNTAX	INTEGER {
				enabled(1),
				disabled(2)
				}
			ACCESS	read-write
			STATUS	mandatory
			DESCRIPTION
			 " accBrPortAdminStatus reports the administrative
			   status of the port; an update to this variable
			   is effective immediately.  Note that the
			   operational status may be disabled even though
			   accBrPortAdminStatus is enabled, if the bridge
			   port's protocol type is incompatible with the
			   associated physical port protocol type."
			::= { accBrPortInfo 11 }
	  accBrPortLine OBJECT-TYPE	
			SYNTAX	INTEGER
			ACCESS	read-write
			STATUS	mandatory
			DESCRIPTION
			 " Index of physical port associated with this bridge
			   port."
			::= { accBrPortInfo 12 }
	  accBrPortProtocol	OBJECT-TYPE	
                        SYNTAX  INTEGER  {
			  	enet(1),
			  	x25(2),
			  	lapb(3),
			  	ffr(4),
			  	other(5),
			  	token-ring(6),
			  	smds(7),
			  	ppp(8),
			  	fddi(9),
			  	dial(10),
			  	multilink(11)
			  	}
			ACCESS	read-write
			STATUS	mandatory
			DESCRIPTION
			 " Note that these enumerated values match those in
			   accSlotProtocol. "
			::= { accBrPortInfo 13 }
	  accBrPortFrDlci	OBJECT-TYPE	
			SYNTAX	INTEGER
			ACCESS	read-write
			STATUS	mandatory
			DESCRIPTION
                         " Frame Relay DLCI for this port"
			::= { accBrPortInfo 14 }
	  accBrPortIndex	OBJECT-TYPE
			SYNTAX	INTEGER
			ACCESS	read-only
			STATUS	mandatory
			DESCRIPTION
                         " Bridge Port Index"
			::= { accBrPortInfo 15 }
	  accBrPortXBridgeStatus	OBJECT-TYPE
			SYNTAX	INTEGER {
				enabled(1),
				disabled(2)
				}
			ACCESS	read-only
			STATUS	mandatory
			DESCRIPTION
                         " Bridge Port translating bridge status"
			::= { accBrPortInfo 16 }

END
