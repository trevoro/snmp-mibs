-- GWWEB MIB
-- Novell GroupWise Web Access Management Information Base (MIB)
-- Copyright (C) 1994, 1995, 1996, 1997, 1998 Novell Inc.,  All Rights Reserved
-- Naming Tree: 1.3.6.1.4.1.23
--      iso(1) org(3) dod(6) internet(1) private(4) enterprises(1) novell(23)
-- Date: April 1, 1998

GWWEB-MIB DEFINITIONS ::= BEGIN

IMPORTS
		  Counter, TimeTicks, Gauge, enterprises  FROM RFC1155-SMI
		  DisplayString                           FROM RFC1213-MIB
        TRAP-TYPE                               FROM RFC-1215
		  OBJECT-TYPE                             FROM RFC-1212;

novell               OBJECT IDENTIFIER   ::= { enterprises        23 }
mibDoc               OBJECT IDENTIFIER   ::= { novell             2 }
gwWeb              OBJECT IDENTIFIER   ::= { mibDoc             77 }
gwWebAccess            OBJECT IDENTIFIER   ::= { gwWeb            1 }

-- ====================================== webAccess Get Variables =========
gwWebAccessTable OBJECT-TYPE
	SYNTAX SEQUENCE OF WEBAccessEntry
	ACCESS not-accessible
	STATUS mandatory
	DESCRIPTION "A table of WebAccess objects"
	::= { gwWebAccess 1 }

webAccessEntry OBJECT-TYPE
	SYNTAX WEBAccessEntry
	ACCESS not-accessible
	STATUS mandatory
	DESCRIPTION "An entry in the WebAccess Table"
	INDEX  { gwWebAccessIndex }
	::= { gwWebAccessTable 1 }

WEBAccessEntry ::=
	SEQUENCE {
			gwWebAccessIndex             INTEGER,
			gwWebAccessName              DisplayString,
			gwWebAccessCompletedRequests Counter,
			gwWebAccessFailedRequests    Counter,
         gwWebAccessTotalThreads      Counter,
         gwWebAccessBusyThreads       Counter,
         gwWebAccessPeakBusyThread    Counter,
         gwWebAccessCurrentUsers      Counter,
         gwWebAccessTotalUsers        Counter,
         gwWebAccessPeakUsers         Counter,
			gwWebAccessUptime            TimeTicks,
			gwWebAccessOS           	   DisplayString,
			gwWebAccessVersion		      DisplayString,
			gwWebAccessHTTPPort           INTEGER
			}

gwWebAccessIndex OBJECT-TYPE
		 SYNTAX  INTEGER
		 ACCESS  read-write
		 STATUS  mandatory
		 DESCRIPTION
		 "Index into the WebAccess table"
	::= { webAccessEntry 1 }

gwWebAccessName OBJECT-TYPE
		 SYNTAX  DisplayString (SIZE (0..255))
		 ACCESS  read-only
		 STATUS  mandatory
		 DESCRIPTION
		 "The name of this WebAccess agent."
	::= { webAccessEntry 2 }

gwWebAccessCompletedRequests OBJECT-TYPE
		 SYNTAX  Counter
		 ACCESS  read-only
		 STATUS  mandatory
		 DESCRIPTION
		"The number of completed requests."
	::= { webAccessEntry 3 }

gwWebAccessFailedRequests OBJECT-TYPE
		 SYNTAX  Counter
		 ACCESS  read-only
		 STATUS  mandatory
		 DESCRIPTION
		"The number of failed requests."
	::= { webAccessEntry 4 }

gwWebAccessTotalThreads OBJECT-TYPE
		 SYNTAX  Counter
		 ACCESS  read-only
		 STATUS  mandatory
		 DESCRIPTION
		"The number of threads."
	::= { webAccessEntry 5}

gwWebAccessBusyThreads OBJECT-TYPE
		 SYNTAX  Counter
		 ACCESS  read-only
		 STATUS  mandatory
		 DESCRIPTION
		"The number of currently busy threads."
	::= { webAccessEntry 6}

gwWebAccessPeakBusyThreads OBJECT-TYPE
		 SYNTAX  Counter
		 ACCESS  read-only
		 STATUS  mandatory
		 DESCRIPTION
		"The peak number of busy threads."
	::= { webAccessEntry 7}

gwWebAccessCurrentUsers OBJECT-TYPE
		 SYNTAX  Counter
		 ACCESS  read-only
		 STATUS  mandatory
		 DESCRIPTION
		"The number of current users."
	::= { webAccessEntry 8}

gwWebAccessTotalUsers OBJECT-TYPE
		 SYNTAX  Counter
		 ACCESS  read-only
		 STATUS  mandatory
		 DESCRIPTION
		"The total number of users."
	::= { webAccessEntry 9}

gwWebAccessPeakUsers OBJECT-TYPE
		 SYNTAX  Counter
		 ACCESS  read-only
		 STATUS  mandatory
		 DESCRIPTION
		"The peak number of users."
	::= { webAccessEntry 10 }

gwWebAccessUptime OBJECT-TYPE
		 SYNTAX  TimeTicks
		 ACCESS  read-only
		 STATUS  mandatory
		 DESCRIPTION
		"Uptime of this WebAccess agent."
	::= { webAccessEntry 11}

gwWebAccessOS OBJECT-TYPE
		 SYNTAX  DisplayString (SIZE (0..64))
		 ACCESS  read-only
		 STATUS  mandatory
		 DESCRIPTION
		 "Operating System name and version"
	::= { webAccessEntry 12 }

gwWebAccessVersion OBJECT-TYPE
		 SYNTAX  DisplayString (SIZE (0..64))
		 ACCESS  read-only
		 STATUS  mandatory
		 DESCRIPTION
		 "Version and date of this WebAccess agent."
	::= { webAccessEntry 13 }

gwWebAccessHTTPPort OBJECT-TYPE
		 SYNTAX  INTEGER
		 ACCESS  read-write
		 STATUS  mandatory
		 DESCRIPTION
		 "HTTP Port for this WebAccess agent"
	::= { webAccessEntry 14 }

END
