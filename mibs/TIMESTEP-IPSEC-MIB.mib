TIMESTEP-IPSEC-MIB 

	-- EXCLUDE		snmpV2
 
 DEFINITIONS ::= BEGIN

     IMPORTS
         MODULE-IDENTITY, OBJECT-TYPE, Counter32, Gauge32, Integer32, Unsigned32,
         IpAddress, NOTIFICATION-TYPE             FROM SNMPv2-SMI
         DateAndTime, TruthValue                  FROM SNMPv2-TC
		 timestep                                 FROM TIMESTEP-MIB;

     ipsecMIB MODULE-IDENTITY
         LAST-UPDATED "9811091200Z"
         ORGANIZATION "IETF IPSec Working Group"
         CONTACT-INFO
                 "   Newbridge Corporation
                     362 Terry Fox Drive
                     Kanata, ON  K0A 2H0
                     Canada

                     1-800-383-8211
                     tsupport@newbridge.com"

         DESCRIPTION
               "The MIB module to describe generic IPSec objects,
               transient and permanent virtual tunnels created by IPSec
               SAs, and entity level IPSec objects and events."
         REVISION      "9811091200000"
         DESCRIPTION
                 "Initial revision."
		::= { timestep 10 }


     ipsecMIBObjects OBJECT IDENTIFIER ::= { ipsecMIB 1 }

     ipsec      OBJECT IDENTIFIER ::= { ipsecMIBObjects 1 }




  -- the IPSec IKE MIB-Group
  --
  -- a collection of objects providing information about
  -- IPSec's IKE SAs and the virtual phase 1 SA tunnels

  ipsecIkeSaTable OBJECT-TYPE
      SYNTAX     SEQUENCE OF IpsecIkeSaEntry
      MAX-ACCESS not-accessible
      STATUS     current
      DESCRIPTION
              "The (conceptual) table containing information on IPSec's
               IKE SAs."
      ::= { ipsec 1 }

  ipsecIkeSaEntry OBJECT-TYPE
      SYNTAX     IpsecIkeSaEntry
      MAX-ACCESS not-accessible
      STATUS     current
      DESCRIPTION
              "An entry (conceptual row) containing the information on
               a particular IKE SA."
      INDEX      { ipsecIkeSaIndex }
      ::= { ipsecIkeSaTable 1 }

  IpsecIkeSaEntry ::= SEQUENCE {
     ipsecIkeSaIndex                  Integer32,

  -- peer information
     ipsecIkeSaPeerIpAddress          IpAddress,
     ipsecIkeSaPeerPortNumber         INTEGER,
     ipsecIkeSaAuthMethod             Integer32,
     ipsecIkeSaPeerIdType             Integer32,
     ipsecIkeSaPeerId                 OCTET STRING,
     ipsecIkeSaPeerCertSerialNum      OCTET STRING,
     ipsecIkeSaPeerCertIssuer         OCTET STRING,

  -- virtual link status
     ipsecIkeSaType                   INTEGER,
     ipsecIkeSaStatus                 INTEGER,

  -- security algorithm information
     ipsecIkeSaEncAlg                 INTEGER,
     ipsecIkeSaEncKeyLength           Integer32,
     ipsecIkeSaHashAlg                Integer32,
     ipsecIkeSaDifHelGroupDesc        Integer32,
     ipsecIkeSaDifHelGroupType        Integer32,
     ipsecIkeSaDifHelFieldSize        Integer32,
     ipsecIkeSaPRF                    Integer32,
     ipsecIkeSaPFS                    TruthValue,

  -- identifier information
     ipsecIkeSaInitiatorCookie        OCTET STRING,
     ipsecIkeSaResponderCookie        OCTET STRING,

  -- expiration limits, current SA
     ipsecIkeSaTimeStart              DateAndTime,
     ipsecIkeSaTimeLimit              Gauge32,    -- in seconds
     ipsecIkeSaTrafficLimit           Gauge32,    -- in kbytes

  -- current SA's operating statistics
     ipsecIkeSaInboundTraffic         Counter32,  -- in bytes
     ipsecIkeSaOutboundTraffic        Counter32,  -- in bytes
     ipsecIkeSaInboundPackets         Counter32,
     ipsecIkeSaOutboundPackets        Counter32,

   -- aggregate statistics (all SAs)
     ipsecIkeSaTotalSaNum             Counter32,
     ipsecIkeSaFirstTimeStart         DateAndTime,
     ipsecIkeSaTotalInboundTraffic    Counter32,  -- in bytes
     ipsecIkeSaTotalOutboundTraffic   Counter32,  -- in bytes
     ipsecIkeSaTotalInboundPackets    Counter32,
     ipsecIkeSaTotalOutboundPackets   Counter32,

  -- aggregate error statistics
     ipsecIkeSaDecryptErrors          Counter32,
     ipsecIkeSaHashErrors             Counter32,
     ipsecIkeSaOtherReceiveErrors     Counter32,
     ipsecIkeSaSendErrors             Counter32,

  -- IPSec SA (Phase 2) statistics (aggregate)
     ipsecIkeSaIpsecInboundTraffic    Counter32,
     ipsecIkeSaIpsecOutboundTraffic   Counter32,
     ipsecIkeSaIpsecInboundPackets    Counter32,
     ipsecIkeSaIpsecOutboundPackets   Counter32,

  -- IPSec SA (Phase 2) error statistics (aggregate)
     ipsecIkeSaIpsecDecryptErrors     Counter32,
     ipsecIkeSaIpsecAuthErrors        Counter32,
     ipsecIkeSaIpsecReplayErrors      Counter32,
     ipsecIkeSaIpsecOtherReceiveErrors  Counter32,
     ipsecIkeSaIpsecSendErrors        Counter32

  }

  ipsecIkeSaIndex OBJECT-TYPE
      SYNTAX      Integer32 (1..16777215)
      MAX-ACCESS  read-only
      STATUS      current
      DESCRIPTION
              "A unique value, greater than zero, for each tunnel
               interface.  It is recommended that values are assigned
               contiguously starting from 1.

               The value for each tunnel interface must remain constant
               at least from one re-initialization of entity's network
               management system to the next re-initialization.

               Further, the value for tunnel interfaces that are marked
               as permanent must remain constant across all re-
               initializations of the network management system."
      ::= { ipsecIkeSaEntry 1 }

   ipsecIkeSaPeerIpAddress OBJECT-TYPE
      SYNTAX      IpAddress
      MAX-ACCESS  read-only
      STATUS      current
      DESCRIPTION
              "The IP address of the peer that this SA was negotiated
               with, or 0 if unknown."
      ::= { ipsecIkeSaEntry 2 }

  ipsecIkeSaPeerPortNumber OBJECT-TYPE
      SYNTAX      INTEGER (0..65535)
      MAX-ACCESS  read-only
      STATUS      current
      DESCRIPTION
              "The port number of the peer that this SA was negotiated
               with, or 0 if the default ISAKMP port number (500)."
      ::= { ipsecIkeSaEntry 3 }

 ipsecIkeSaAuthMethod OBJECT-TYPE
      SYNTAX      Integer32 (0..65535)
      MAX-ACCESS  read-only
      STATUS      current
      DESCRIPTION
              "The authentication method used to authenticate the
               peers.

               Note that this does not include the specific method of
               authentication if extended authenticated is used.

               Specific values are used as described in the ISAKMP Class
               Values of Authentication Method from Appendix A of
               [IKE]."
      ::= { ipsecIkeSaEntry 4 }

  ipsecIkeSaPeerIdType OBJECT-TYPE
      SYNTAX      Integer32 (0..256)
      MAX-ACCESS  read-only
      STATUS      current
      DESCRIPTION
              "The type of ID used by the peer.

               Specific values are used as described in Section 4.6.2.1
               of [IPDOI]."
      ::= { ipsecIkeSaEntry 5 }

  ipsecIkeSaPeerId OBJECT-TYPE
      SYNTAX      OCTET STRING (SIZE (0..511))
      MAX-ACCESS  read-only
      STATUS      current
      DESCRIPTION
              "The ID of the peer this SA was negotiated with.

               The length may require truncation under some conditions."
      ::= { ipsecIkeSaEntry 6 }

  ipsecIkeSaPeerCertSerialNum OBJECT-TYPE
      SYNTAX      OCTET STRING (SIZE (0..63))
      MAX-ACCESS  read-only
      STATUS      current
       DESCRIPTION
               "The serial number of the certificate of the peer this SA
               was negotiated with.

               This object has no meaning if a certificate was not used
               in authenticating the peer."
      ::= { ipsecIkeSaEntry 7 }

  ipsecIkeSaPeerCertIssuer OBJECT-TYPE
      SYNTAX      OCTET STRING (SIZE (0..511))
      MAX-ACCESS  read-only
      STATUS      current
      DESCRIPTION
              "The serial number of the certificate of the peer this SA
               was negotiated with.

               This object has no meaning if a certificate was not used
               in authenticating the peer."
      ::= { ipsecIkeSaEntry 8 }

  ipsecIkeSaType OBJECT-TYPE
      SYNTAX      INTEGER { transient(1), permanent(2) }
      MAX-ACCESS  read-only
      STATUS      current
      DESCRIPTION
              "The type of virtual tunnel represented by this row.

               A transient link will disappear from the table when
               the SAs needed for it cannot be established. A
               permanent link will shows its status in the
               ipsecIkeSaStatus object."
      ::= { ipsecIkeSaEntry 9 }

  ipsecIkeSaStatus OBJECT-TYPE
      SYNTAX      INTEGER
                  { neverTried(0), linkUp(1), linkDown(2) }
      MAX-ACCESS  read-only
      STATUS      current
      DESCRIPTION
              "The status of the virtual tunnel represented by this
               row, if the tunnel is configured as permanent.

               'neverTried' means that no attempt to set-up the link
               has been done. 'linkUp' means that the link is up and
               operating normally. 'linkDown' means that the link was
               up, but has gone down."
      ::= { ipsecIkeSaEntry 10 }

  ipsecIkeSaEncAlg OBJECT-TYPE
      SYNTAX      INTEGER (0..65535)
      MAX-ACCESS  read-only
      STATUS      current
      DESCRIPTION
              "A unique value representing the encryption algorithm
               applied to traffic carried by this SA or 0 if there
               is no encryption applied.

               Specific values are used as described in the ISAKMP
               Class Values of Encryption Algorithms from Appendix A
               of [IKE]."
      ::= { ipsecIkeSaEntry 11 }

  ipsecIkeSaEncKeyLength OBJECT-TYPE
      SYNTAX      Integer32
      MAX-ACCESS  read-only
      STATUS      current
      DESCRIPTION
              "The length of the encryption key in bits used for
               algorithm specified in the ipsecIkeSaEncAlg object or 0
               if the key length is implicit in the specified
               algorithm or there is no encryption specified."
      ::= { ipsecIkeSaEntry 12 }

  ipsecIkeSaHashAlg OBJECT-TYPE
      SYNTAX      Integer32 (0..65535)
      MAX-ACCESS  read-only
      STATUS      current
      DESCRIPTION
              "A unique value representing the hash algorithm applied
               to traffic carried by this SA or 0 if there is no
               encryption applied.

               Specific values are used as described in the ISAKMP Class
               Values of Hash Algorithms from Appendix A of [IKE]."
      ::= { ipsecIkeSaEntry 13 }

 ipsecIkeSaDifHelGroupDesc OBJECT-TYPE
      SYNTAX      Integer32 (0..65535)
      MAX-ACCESS  read-only
      STATUS      current
      DESCRIPTION
              "A unique value representing the Diffie-Hellman group
               description used or 0 if the group is unknown.

               Specific values are used as described in the ISAKMP Class
               Values of Group Description from Appendix A of [IKE]."
      ::= { ipsecIkeSaEntry 14 }

  ipsecIkeSaDifHelGroupType OBJECT-TYPE
      SYNTAX      Integer32 (0..65535)
      MAX-ACCESS  read-only
      STATUS      current
      DESCRIPTION
              "A unique value representing the Diffie-Hellman group
               type used or 0 if the group is unknown.

               Specific values are used as described in the ISAKMP Class
               Values of Group Type from Appendix A of [IKE]."
      ::= { ipsecIkeSaEntry 15 }

  ipsecIkeSaDifHelFieldSize OBJECT-TYPE
      SYNTAX      Integer32
      MAX-ACCESS  read-only
      STATUS      current
      DESCRIPTION
              "The field size, in bits, of a Diffie-Hellman group."
      ::= { ipsecIkeSaEntry 16 }

  ipsecIkeSaPRF OBJECT-TYPE
      SYNTAX      Integer32 (0..65535)
      MAX-ACCESS  read-only
      STATUS      current
      DESCRIPTION
              "The pseudo-random functions used, or 0 if not used or if
               unknown.

               Specific values are used as described in the ISAKMP Class
               Values of PRF from Appendix A of [IKE] (which specifies
               none at the present time)."
      ::= { ipsecIkeSaEntry 17 }

  ipsecIkeSaPFS OBJECT-TYPE
      SYNTAX      TruthValue
      MAX-ACCESS  read-only
      STATUS      current
      DESCRIPTION
              "A value that indicates that perfect forward secrecy is
               used for all IPSec SAs created by this IKE SA."
      ::= { ipsecIkeSaEntry 18 }

  ipsecIkeSaInitiatorCookie OBJECT-TYPE
      SYNTAX      OCTET STRING (SIZE (16))
      MAX-ACCESS  read-only
      STATUS      current
      DESCRIPTION
              "The value of the cookie used by the initiator for the
               current phase 1 SA."
      ::= { ipsecIkeSaEntry 19 }

  ipsecIkeSaResponderCookie OBJECT-TYPE
      SYNTAX      OCTET STRING (SIZE (16))
      MAX-ACCESS  read-only
      STATUS      current
      DESCRIPTION
              "The value of the cookie used by the responder for the
               current phase 1 SA."
      ::= { ipsecIkeSaEntry 20 }

  ipsecIkeSaTimeStart OBJECT-TYPE
      SYNTAX      DateAndTime
      MAX-ACCESS  read-only
      STATUS      current
      DESCRIPTION
              "The date and time that the current SA within the link
               was set up.

               It is not the date and time that the virtual tunnel was
               set up."
      ::= { ipsecIkeSaEntry 21 }

  ipsecIkeSaTimeLimit OBJECT-TYPE
      SYNTAX      Gauge32
      MAX-ACCESS  read-only
      STATUS      current
      DESCRIPTION
              "The maximum lifetime in seconds of the current SA
               supporting the virtual tunnel, or 0 if there is no time
               constraint on its expiration."
      ::= { ipsecIkeSaEntry 22 }

   ipsecIkeSaTrafficLimit OBJECT-TYPE
      SYNTAX      Gauge32
      MAX-ACCESS  read-only
      STATUS      current
      DESCRIPTION
              "The maximum traffic in 1024-byte blocks that the current
               SA supporting the virtual tunnel is allowed to support,
               or 0 if there is no traffic constraint on its
               expiration."
      ::= { ipsecIkeSaEntry 23 }

   ipsecIkeSaInboundTraffic OBJECT-TYPE
      SYNTAX      Counter32
      MAX-ACCESS  read-only
      STATUS      current
      DESCRIPTION
              "The amount traffic measured in bytes handled in the
               current SA in the inbound direction. "
      ::= { ipsecIkeSaEntry 24 }

  ipsecIkeSaOutboundTraffic OBJECT-TYPE
      SYNTAX      Counter32
      MAX-ACCESS  read-only
      STATUS      current
      DESCRIPTION
              "The amount traffic measured in bytes handled in the
               current SA in the outbound direction. "
      ::= { ipsecIkeSaEntry 25 }

  ipsecIkeSaInboundPackets OBJECT-TYPE
      SYNTAX      Counter32
      MAX-ACCESS  read-only
      STATUS      current
      DESCRIPTION
              "The number of packets handled in the current SA in the
               inbound direction. "
      ::= { ipsecIkeSaEntry 26 }

  ipsecIkeSaOutboundPackets OBJECT-TYPE
      SYNTAX      Counter32
      MAX-ACCESS  read-only
      STATUS      current
      DESCRIPTION
              "The number of packets handled in the current SA in the
               outbound direction. "
      ::= { ipsecIkeSaEntry 27 }

   ipsecIkeSaTotalSaNum OBJECT-TYPE
      SYNTAX      Counter32
      MAX-ACCESS  read-only
      STATUS      current
      DESCRIPTION
              "The total number of SAs, including the current SA, that
               have been set up to support this virtual tunnel."
      ::= { ipsecIkeSaEntry 28 }

  ipsecIkeSaFirstTimeStart OBJECT-TYPE
      SYNTAX      DateAndTime
      MAX-ACCESS  read-only
      STATUS      current
      DESCRIPTION
              "The data and time that this virtual tunnel was
               originally set up.

               It is not the time that the current SA was set up.

               If this is a permanent virtual tunnel, it is reset when
               the tunnel goes to the 'linkUp' state."
      ::= { ipsecIkeSaEntry 29 }

  ipsecIkeSaTotalInboundTraffic OBJECT-TYPE
      SYNTAX      Counter32
      MAX-ACCESS  read-only
      STATUS      current
     DESCRIPTION
              "The total amount of traffic measured in bytes handled in
               the tunnel in the inbound direction. In other words, it
               is the aggregate value of all inbound traffic carried by
               all SAs ever set up to support the virtual tunnel.

               If this is a permanent virtual tunnel, it is not reset to
               zero when the tunnel goes to the 'linkUp' state."
      ::= { ipsecIkeSaEntry 30 }

  ipsecIkeSaTotalOutboundTraffic OBJECT-TYPE
      SYNTAX      Counter32
      MAX-ACCESS  read-only
      STATUS      current
      DESCRIPTION
              "The total amount of traffic measured in bytes handled in
               the tunnel in the outbound direction. In other words, it
               is the aggregate value of all inbound traffic carried by
               all SAs ever set up to support the virtual tunnel.

               If this is a permanent virtual tunnel, it is not reset to
               zero when the tunnel goes to the 'linkUp' state."
      ::= { ipsecIkeSaEntry 31 }

   ipsecIkeSaTotalInboundPackets OBJECT-TYPE
      SYNTAX      Counter32
      MAX-ACCESS  read-only
      STATUS      current
      DESCRIPTION
              "The total number of packets handled by the virtual
               tunnel since it became active in the inbound direction.
               In other words, it is the aggregate value of the number
               of inbound packets carried by all SAs ever set up to
               support the virtual tunnel.

               If this is a permanent virtual tunnel, it is not reset to
               zero when the tunnel goes to the 'linkUp' state."
      ::= { ipsecIkeSaEntry 32 }

  ipsecIkeSaTotalOutboundPackets OBJECT-TYPE
      SYNTAX      Counter32
      MAX-ACCESS  read-only
      STATUS      current
      DESCRIPTION
              "The total number of packets handled by the virtual
               tunnel since it became active in the outbound direction.
               In other words, it is the aggregate value of the number
               of outbound packets carried by all SAs ever set up to
               support the virtual tunnel.

               If this is a permanent virtual tunnel, it is not reset to
               zero when the tunnel goes to the 'linkUp' state."
      ::= { ipsecIkeSaEntry 33 }

  ipsecIkeSaDecryptErrors OBJECT-TYPE
      SYNTAX      Counter32
      MAX-ACCESS  read-only
      STATUS      current
      DESCRIPTION
               "The total number of inbound packets to this SA discarded
               due to decryption errors.

               Note that this refers to IKE protocol packets, and not to
               packets carried by SAs set up by the SAs supporting this
               tunnel.

               If this is a permanent virtual tunnel, it is not reset to
               zero when the tunnel goes to the 'linkUp' state."
      ::= { ipsecIkeSaEntry 34 }

  ipsecIkeSaHashErrors OBJECT-TYPE
      SYNTAX      Counter32
      MAX-ACCESS  read-only
      STATUS      current
      DESCRIPTION
              "The total number of inbound packets to this SA discarded
               due to hash errors.

               Note that this refers to IKE protocol packets, and not to
               packets carried by SAs set up by the SAs supporting this
               tunnel.

               If this is a permanent virtual tunnel, it is not reset to
               zero when the tunnel goes to the 'linkUp' state."
      ::= { ipsecIkeSaEntry 35 }

  ipsecIkeSaOtherReceiveErrors OBJECT-TYPE
      SYNTAX      Counter32
      MAX-ACCESS  read-only
      STATUS      current
      DESCRIPTION
              "The total number of inbound packets to this SA discarded
               for reasons other than bad hashes or decryption errors.
               This may include packets dropped to a lack of receive
               buffer space.

               Note that this refers to IKE protocol packets, and not to
               packets carried by SAs set up by the SAs supporting this
               tunnel.

               If this is a permanent virtual tunnel, it is not reset to
               zero when the tunnel goes to the 'linkUp' state."
      ::= { ipsecIkeSaEntry 36 }

  ipsecIkeSaSendErrors OBJECT-TYPE
      SYNTAX      Counter32
      MAX-ACCESS  read-only
      STATUS      current
      DESCRIPTION
              "The total number of outbound packets from this SA
               discarded for any reason. This may include packets
               dropped to a lack of transmit buffer space.

               Note that this refers to IKE protocol packets, and not to
               packets carried by SAs set up by the SAs supporting this
               tunnel.

               If this is a permanent virtual tunnel, it is not reset to
               zero when the tunnel goes to the 'linkUp' state."
      ::= { ipsecIkeSaEntry 37 }

  ipsecIkeSaIpsecInboundTraffic OBJECT-TYPE
      SYNTAX      Counter32
      MAX-ACCESS  read-only
      STATUS      current
      DESCRIPTION
              "The total amount of inbound traffic measured in bytes
               handled by all IPSec SAs set up by phase 1 SAs supporting
               this tunnel.

               If this is a permanent virtual tunnel, it is not reset to
               zero when the tunnel goes to the 'linkUp' state."
      ::= { ipsecIkeSaEntry 38 }

  ipsecIkeSaIpsecOutboundTraffic OBJECT-TYPE
      SYNTAX      Counter32
      MAX-ACCESS  read-only
      STATUS      current
     DESCRIPTION
              "The total amount of outbound traffic measured in bytes
               handled by all IPSec SAs set up by phase 1 SAs supporting
               this tunnel.

               If this is a permanent virtual tunnel, it is not reset to
               zero when the tunnel goes to the 'linkUp' state."
      ::= { ipsecIkeSaEntry 39 }

  ipsecIkeSaIpsecInboundPackets OBJECT-TYPE
      SYNTAX      Counter32
      MAX-ACCESS  read-only
      STATUS      current
      DESCRIPTION
              "The total number of inbound packets handled by all IPSec
               SAs set up by phase 1 SAs supporting this tunnel.
               If this is a permanent virtual tunnel, it is not reset to
               zero when the tunnel goes to the 'linkUp' state."
      ::= { ipsecIkeSaEntry 40 }

  ipsecIkeSaIpsecOutboundPackets OBJECT-TYPE
      SYNTAX      Counter32
      MAX-ACCESS  read-only
      STATUS      current
      DESCRIPTION
              "The total number of outbound packets handled by all
               IPSec SAs set up by phase 1 SAs supporting this tunnel.

               If this is a permanent virtual tunnel, it is not reset to
               zero when the tunnel goes to the 'linkUp' state."
      ::= { ipsecIkeSaEntry 41 }

  ipsecIkeSaIpsecDecryptErrors OBJECT-TYPE
      SYNTAX      Counter32
      MAX-ACCESS  read-only
      STATUS      current
       DESCRIPTION
              "The total number of inbound packets discarded by all
               IPSec SAs due to decryption errors.

               If this is a permanent virtual tunnel, it is not reset to
               zero when the tunnel goes to the 'linkUp' state."
      ::= { ipsecIkeSaEntry 42 }

  ipsecIkeSaIpsecAuthErrors OBJECT-TYPE
      SYNTAX      Counter32
      MAX-ACCESS  read-only
      STATUS      current
      DESCRIPTION
              "The total number of inbound packets discarded by all
               IPSec SAs due to authentication errors. This includes
               hash failures in IPSec SAs using ESP and AH.

               If this is a permanent virtual tunnel, it is not reset to
               zero when the tunnel goes to the 'linkUp' state."
      ::= { ipsecIkeSaEntry 43 }

  ipsecIkeSaIpsecReplayErrors OBJECT-TYPE
      SYNTAX      Counter32
      MAX-ACCESS  read-only
      STATUS      current
      DESCRIPTION
              "The total number of inbound packets discarded by all
               IPSec SAs due to replay errors.

               If this is a permanent virtual tunnel, it is not reset to
               zero when the tunnel goes to the 'linkUp' state."
      ::= { ipsecIkeSaEntry 44 }

  ipsecIkeSaIpsecOtherReceiveErrors OBJECT-TYPE
      SYNTAX      Counter32
      MAX-ACCESS  read-only
      STATUS      current
       DESCRIPTION
              "The total number of inbound packets discarded by all
               IPSec SAs due to errors other than authentication,
               decryption or replay errors. This may include packets
               dropped due to lack of receive buffers.

               If this is a permanent virtual tunnel, it is not reset to
               zero when the tunnel goes to the 'linkUp' state."
      ::= { ipsecIkeSaEntry 45 }

   ipsecIkeSaIpsecSendErrors OBJECT-TYPE
      SYNTAX      Counter32
      MAX-ACCESS  read-only
      STATUS      current
      DESCRIPTION
              "The total number of outbound packets discarded by all
               IPSec SAs due to any error. This may include packets
               dropped due to lack of receive buffers.

               If this is a permanent virtual tunnel, it is not reset to
               zero when the tunnel goes to the 'linkUp' state."
      ::= { ipsecIkeSaEntry 46 }

  -- the IPSec Tunnel MIB-Group
  --
  -- a collection of objects providing information about
  -- IPSec SA-based virtual tunnels


  ipsecTunnelTable OBJECT-TYPE
      SYNTAX     SEQUENCE OF IpsecTunnelEntry
      MAX-ACCESS not-accessible
      STATUS     current
      DESCRIPTION
              "The (conceptual) table containing information on IPSec
               SA-based tunnels."
      ::= { ipsec 2 }

  ipsecTunnelEntry OBJECT-TYPE
      SYNTAX     IpsecTunnelEntry
      MAX-ACCESS not-accessible
      STATUS     current
      DESCRIPTION
              "An entry (conceptual row) containing the information on
               a particular configured tunnel."
      INDEX      { ipsecTunnelIndex }
      ::= { ipsecTunnelTable 1 }

  IpsecTunnelEntry ::= SEQUENCE {
     ipsecTunnelIndex      Integer32,
     ipsecTunnelIkeSa      Integer32, -- if not static
     ipsecTunnelType       INTEGER, -- static, transient, permanent

  -- tunnel identifiers
     ipsecTunnelLocalAddressOrStart          IpAddress,
     ipsecTunnelLocalAddressMaskOrEnd        IpAddress,
     ipsecTunnelRemoteAddressOrStart         IpAddress,
     ipsecTunnelRemoteAddressMaskOrEnd       IpAddress,
     ipsecTunnelProtocol                     Integer32,
     ipsecTunnelLocalPort                    Integer32,
     ipsecTunnelRemotePort                   Integer32,



  -- tunnel security services description
     ipsecTunnelMode                  INTEGER,
     ipsecTunnelEspEncAlg             Integer32,
     ipsecTunnelEspEncKeyLength       Integer32,
     ipsecTunnelEspAuthAlg            Integer32,
     ipsecTunnelAhAuthAlg             Integer32,
     ipsecTunnelCompAlg               Integer32,

  -- aggregate statistics
     ipsecTunnelStartTime             DateAndTime,
     ipsecTunnelCurrentSaNum          Gauge32,
     ipsecTunnelTotalSaNum            Counter32,
     ipsecTunnelTotalInboundTraffic   Counter32,
     ipsecTunnelTotalOutboundTraffic  Counter32,
     ipsecTunnelTotalInboundPackets   Counter32,
     ipsecTunnelTotalOutboundPackets  Counter32,

  -- aggregate error statistics
     ipsecTunnelDecryptErrors         Counter32,
     ipsecTunnelAuthErrors            Counter32,
     ipsecTunnelReplayErrors          Counter32,
     ipsecTunnelPolicyErrors          Counter32,
     ipsecTunnelOtherReceiveErrors    Counter32,
     ipsecTunnelSendErrors            Counter32

  }


  ipsecTunnelIndex OBJECT-TYPE
      SYNTAX      Integer32 (1..16777215)
      MAX-ACCESS  read-only
      STATUS      current
      DESCRIPTION
              "A unique value, greater than zero, for each tunnel
               interface.  It is recommended that values are assigned
               contiguously starting from 1.

               The value for each tunnel interface must remain constant
               at least from one re-initialization of the entity's
               network management system to the next re-initialization.

               Further, the value for tunnel interfaces that are marked
               as permanent must remain constant across all re-
               initializations of the network management system."
      ::= { ipsecTunnelEntry 1 }

  ipsecTunnelIkeSa OBJECT-TYPE
      SYNTAX      Integer32 (0..2147483647)
      MAX-ACCESS  read-only
      STATUS      current
      DESCRIPTION
              "The value of the index into the IKE SA tunnel table that
               created this tunnel (ipsecIkeSaIndex), or 0 if the tunnel
               is created by a static IPSec SA."
      ::= { ipsecTunnelEntry 2 }

  ipsecTunnelType OBJECT-TYPE
      SYNTAX      INTEGER { static(0), transient(1), permanent(2) }
      MAX-ACCESS  read-only
      STATUS      current
      DESCRIPTION
              "The type of the virtual tunnel represented by this row.

               'static' means that the tunnel is supported by a single
               static IPSec SA that was setup by configuration, and not
               by using a key exchange protocol. In this case, the value
               of ipsecTunnelIkeSa must be 0."
      ::= { ipsecTunnelEntry 3 }

  ipsecTunnelLocalAddressOrStart OBJECT-TYPE
      SYNTAX     IpAddress
      MAX-ACCESS read-only
      STATUS     current
      DESCRIPTION
              "The address of or the start address (if an address
               range) of the local endpoint of the tunnel, or 0.0.0.0 if
               unknown or if the SA uses transport mode encapsulation."
      ::= { ipsecTunnelEntry 4 }

   ipsecTunnelLocalAddressMaskOrEnd OBJECT-TYPE
      SYNTAX     IpAddress
      MAX-ACCESS read-only
      STATUS     current
      DESCRIPTION
              "The mask of or the end address (if an address range) of
               the local endpoint of the tunnel, or 0.0.0.0 if unknown
               or if the SA uses transport mode encapsulation."
      ::= { ipsecTunnelEntry 5 }

   ipsecTunnelRemoteAddressOrStart OBJECT-TYPE
      SYNTAX     IpAddress
      MAX-ACCESS read-only
      STATUS     current
      DESCRIPTION
              "The address of or the start address (if an address
               range) of the remote endpoint of the tunnel, or 0.0.0.0
               if unknown or if the SA uses transport mode
               encapsulation."
      ::= { ipsecTunnelEntry 6 }

  ipsecTunnelRemoteAddressMaskOrEnd OBJECT-TYPE
      SYNTAX     IpAddress
      MAX-ACCESS read-only
      STATUS     current
      DESCRIPTION
              "The mask of or the end address (if an address range) of
               the remote endpoint of the tunnel, or 0.0.0.0 if unknown
               or if the SA uses transport mode encapsulation."
      ::= { ipsecTunnelEntry 7 }

  ipsecTunnelProtocol OBJECT-TYPE
      SYNTAX     Integer32 (0..255)
      MAX-ACCESS read-only
      STATUS     current
      DESCRIPTION
              "The number of the protocol that this tunnel carries, or
               0 if it carries any protocol."
      ::= { ipsecTunnelEntry 8 }

  ipsecTunnelLocalPort OBJECT-TYPE
      SYNTAX     Integer32 (0.. 65535)
      MAX-ACCESS read-only
      STATUS     current
      DESCRIPTION
              "The number of the local port that this tunnel carries,
               or 0 if it carries any port number."
      ::= { ipsecTunnelEntry 9 }

  ipsecTunnelRemotePort OBJECT-TYPE
      SYNTAX     Integer32 (0.. 65535)
      MAX-ACCESS read-only
      STATUS     current
      DESCRIPTION
              "The number of the remote port that this tunnel carries,
               or 0 if it carries any port number."
      ::= { ipsecTunnelEntry 10 }

  ipsecTunnelMode OBJECT-TYPE
      SYNTAX     INTEGER { transport(1), tunnel(2) }
      MAX-ACCESS read-only
      STATUS     current
      DESCRIPTION
              "The type of encapsulation used by this virtual tunnel."
      ::= { ipsecTunnelEntry 11 }

  ipsecTunnelEspEncAlg OBJECT-TYPE
      SYNTAX      Integer32 (0..255)
      MAX-ACCESS  read-only
      STATUS      current
      DESCRIPTION
              "A unique value representing the encryption algorithm
               applied to traffic carried by this SA if it uses ESP or 0
               if there is no encryption applied by ESP or if ESP is not
               used.

               Specific values are taken from section 4.4.4 of [IPDOI]."
      ::= { ipsecTunnelEntry 12 }

   ipsecTunnelEspEncKeyLength OBJECT-TYPE
      SYNTAX      Integer32
      MAX-ACCESS  read-only
      STATUS      current
      DESCRIPTION
              "The length of the encryption key in bits used for the
               algorithm specified in the ipsecTunnelEspEncAlg object,
               or 0 if the key length is implicit in the specified
               algorithm or there is no encryption specified."
      ::= { ipsecTunnelEntry 13 }

  ipsecTunnelEspAuthAlg OBJECT-TYPE
      SYNTAX      Integer32 (0..255)
      MAX-ACCESS  read-only
      STATUS      current
       DESCRIPTION
              "A unique value representing the hash algorithm applied
               to traffic carried by this SA if it uses ESP or 0 if
               there is no authentication applied by ESP or if ESP is
               not used.

               Specific values are taken from the Authentication
               Algorithm attribute values of Section 4.5 of [IPDOI]."
      ::= { ipsecTunnelEntry 14 }

  ipsecTunnelAhAuthAlg OBJECT-TYPE
      SYNTAX      Integer32 (0..255)
      MAX-ACCESS  read-only
      STATUS      current
      DESCRIPTION
              "A unique value representing the hash algorithm applied
               to traffic carried by this SA if it uses AH or 0 if AH is
               not used.

               Specific values are taken from Section 4.4.3 of [IPDOI]."
      ::= { ipsecTunnelEntry 15 }

  ipsecTunnelCompAlg OBJECT-TYPE
      SYNTAX      Integer32 (0..255)
      MAX-ACCESS  read-only
      STATUS      current
      DESCRIPTION
              "A unique value representing the compression algorithm
               applied to traffic carried by this SA if it uses IPCOMP.

               Specific values are taken from Section 4.4.5 of [IPDOI]."
      ::= { ipsecTunnelEntry 16 }

  ipsecTunnelStartTime OBJECT-TYPE
      SYNTAX      DateAndTime
      MAX-ACCESS  read-only
      STATUS      current
      DESCRIPTION
              "The date and time that this virtual tunnel was set up.
               If this is a permanent virtual tunnel, it is reset when
               the number of current SAs (ipsecTunnelCurrentSaNum)
               changes from 0 to 1."
      ::= { ipsecTunnelEntry 17 }

  ipsecTunnelCurrentSaNum OBJECT-TYPE
      SYNTAX      Gauge32
      MAX-ACCESS  read-only
      STATUS      current
      DESCRIPTION
              "The number of current SAs set up to support this virtual
               tunnel.

               If this number is 0, the tunnel must be considered down.
               Also if this number is 0, the tunnel must a permanent
               tunnel, since transient tunnels that are down do not
               appear in the table."
      ::= { ipsecTunnelEntry 18 }

   ipsecTunnelTotalSaNum OBJECT-TYPE
      SYNTAX      Counter32
      MAX-ACCESS  read-only
      STATUS      current
       DESCRIPTION
              "The total number of SAs, including all current SAs, that
               have been set up to support this virtual tunnel."
      ::= { ipsecTunnelEntry 19 }

  ipsecTunnelTotalInboundTraffic OBJECT-TYPE
      SYNTAX      Counter32
      MAX-ACCESS  read-only
      STATUS      current
      DESCRIPTION
              "The total amount of traffic measured in bytes handled in
               the tunnel in the inbound direction. In other words, it
               is the aggregate value of all inbound traffic carried by
               all IPSec SAs ever set up to support the virtual tunnel.

               If this is a permanent virtual tunnel, it is not reset to
               zero when the number of current SAs
               (ipsecTunnelCurrentSaNum) changes from 0 to 1."
      ::= { ipsecTunnelEntry 20 }

  ipsecTunnelTotalOutboundTraffic OBJECT-TYPE
      SYNTAX      Counter32
      MAX-ACCESS  read-only
      STATUS      current
      DESCRIPTION
              "The total amount of traffic measured in bytes handled in
               the tunnel in the outbound direction. In other words, it
               is the aggregate value of all inbound traffic carried by
               all IPSec SAs ever set up to support the virtual tunnel.

               If this is a permanent virtual tunnel, it is not reset to
               zero when the number of current SAs
               (ipsecTunnelCurrentSaNum) changes from 0 to 1."
      ::= { ipsecTunnelEntry 21 }

  ipsecTunnelTotalInboundPackets OBJECT-TYPE
      SYNTAX      Counter32
      MAX-ACCESS  read-only
      STATUS      current
       DESCRIPTION
              "The total number of packets handled in the tunnel in the
               inbound direction. In other words, it is the aggregate
               value of all inbound packets carried by all IPSec SAs
               ever set up to support the virtual tunnel.

               If this is a permanent virtual tunnel, it is not reset to
               zero when the number of current SAs
               (ipsecTunnelCurrentSaNum) changes from 0 to 1."
      ::= { ipsecTunnelEntry 22 }

  ipsecTunnelTotalOutboundPackets OBJECT-TYPE
      SYNTAX      Counter32
      MAX-ACCESS  read-only
      STATUS      current
      DESCRIPTION
              "The total number of packets handled in the tunnel in the
               outbound direction. In other words, it is the aggregate
               value of all outbound packets carried by all IPSec SAs
               ever set up to support the virtual tunnel.

               If this is a permanent virtual tunnel, it is not reset to
               zero when the number of current SAs
               (ipsecTunnelCurrentSaNum) changes from 0 to 1."
      ::= { ipsecTunnelEntry 23 }

  ipsecTunnelDecryptErrors OBJECT-TYPE
      SYNTAX      Counter32
      MAX-ACCESS  read-only
      STATUS      current
      DESCRIPTION
              "The total number of inbound packets discarded by this
               virtual tunnel due to decryption errors in ESP.
               If this is a permanent virtual tunnel, it is not reset to
               zero when the number of current SAs
               (ipsecTunnelCurrentSaNum) changes from 0 to 1."
      ::= { ipsecTunnelEntry 24 }

  ipsecTunnelAuthErrors OBJECT-TYPE
      SYNTAX      Counter32
      MAX-ACCESS  read-only
      STATUS      current
      DESCRIPTION
              "The total number of inbound packets discarded by this
               virtual tunnel due to authentication errors. This
               includes hash failures in IPSec SA bundles using both ESP
               and AH.

               If this is a permanent virtual tunnel, it is not resetto
               zero when the number of current SAs
               (ipsecTunnelCurrentSaNum) changes from 0 to 1."
      ::= { ipsecTunnelEntry 25 }

  ipsecTunnelReplayErrors OBJECT-TYPE
      SYNTAX      Counter32
      MAX-ACCESS  read-only
      STATUS      current
      DESCRIPTION
              "The total number of inbound packets discarded by this
               virtual tunnel due to replay errors. This includes replay
               failures in IPSec SA bundles using both ESP and AH.

               If this is a permanent virtual tunnel, it is not reset to
               zero when the number of current SAs
               (ipsecTunnelCurrentSaNum) changes from 0 to 1."
      ::= { ipsecTunnelEntry 26 }

  ipsecTunnelPolicyErrors OBJECT-TYPE
      SYNTAX      Counter32
      MAX-ACCESS  read-only
      STATUS      current
      DESCRIPTION
              "The total number of inbound packets discarded by this
               virtual tunnel due to policy errors. This includes errors
               in all transforms if SA bundles are used.

               Policy errors are due to the detection of a packet that
               was inappropriately sent into this tunnel.

               If this is a permanent virtual tunnel, it is not reset to
               zero when the number of current SAs
               (ipsecTunnelCurrentSaNum) changes from 0 to 1."
      ::= { ipsecTunnelEntry 27 }

  ipsecTunnelOtherReceiveErrors OBJECT-TYPE
      SYNTAX      Counter32
      MAX-ACCESS  read-only
      STATUS      current
      DESCRIPTION
              "The total number of inbound packets discarded by this
               virtual tunnel due to errors other than decryption,
               authentication or replay errors. This may include packets
               dropped due to a lack of receive buffers.

               If this is a permanent virtual tunnel, it is not reset to
               zero when the number of current SAs
               (ipsecTunnelCurrentSaNum) changes from 0 to 1."
      ::= { ipsecTunnelEntry 28 }

  ipsecTunnelSendErrors OBJECT-TYPE
      SYNTAX      Counter32
      MAX-ACCESS  read-only
      STATUS      current
      DESCRIPTION
              "The total number of outbound packets discarded by this
               virtual tunnel due to any error. This may include packets
               dropped due to a lack of transmit buffers.

               If this is a permanent virtual tunnel, it is not reset to
               zero when the number of current SAs
               (ipsecTunnelCurrentSaNum) changes from 0 to 1."
      ::= { ipsecTunnelEntry 29 }


  -- the IPSec SA MIB-Group
  --
  -- a collection of objects providing information about
  -- IPSec SAs


  ipsecSaTable OBJECT-TYPE
      SYNTAX     SEQUENCE OF IpsecSaEntry
      MAX-ACCESS not-accessible
      STATUS     current
      DESCRIPTION
              "The (conceptual) table containing information on IPSec
               SAs."
      ::= { ipsec 3 }

  ipsecSaEntry OBJECT-TYPE
      SYNTAX     IpsecSaEntry
      MAX-ACCESS not-accessible
      STATUS     current
      DESCRIPTION
              "An entry (conceptual row) containing the information on
               a particular IPSec SA."
      INDEX      { ipsecSaIndex }
      ::= { ipsecSaTable 1 }

  IpsecSaEntry ::= SEQUENCE {
     ipsecSaIndex        Integer32,
     ipsecSaTunnel       Integer32,  -- index from ipsecTunnelTable

  -- identification
     ipsecSaInboundEspSpi          Unsigned32,
     ipsecSaOutboundEspSpi         Unsigned32,
     ipsecSaInboundAhSpi           Unsigned32,
     ipsecSaOutboundAhSpi          Unsigned32,
     ipsecSaInboundCompCpi         INTEGER (0..65535),
     ipsecSaOutboundCompCpi        INTEGER (0..65535),

  -- expiration limits
     ipsecSaCreationTime           DateAndTime,
     ipsecSaTimeLimit              Gauge32,  -- seconds, 0 if none
     ipsecSaTrafficLimit           Gauge32,  -- bytes, 0 if none

   -- current operating statistics
     ipsecSaInboundTraffic         Counter32,
     ipsecSaOutboundTraffic        Counter32,
     ipsecSaInboundPackets         Counter32,
     ipsecSaOutboundPackets        Counter32,

  -- error statistics
     ipsecSaDecryptErrors          Counter32,
     ipsecSaAuthErrors             Counter32,
     ipsecSaReplayErrors           Counter32,
     ipsecSaOtherReceiveErrors     Counter32,
     ipsecSaSendErrors             Counter32
  }


  ipsecSaIndex OBJECT-TYPE
      SYNTAX      Integer32 (1..2147483647)
      MAX-ACCESS  read-only
      STATUS      current
      DESCRIPTION
              "A unique value, greater than zero, for each IPSec SA. It
               is recommended that values are assigned contiguously
               starting from 1."
      ::= { ipsecSaEntry 1 }

  ipsecSaTunnel OBJECT-TYPE
      SYNTAX      Integer32 (1..2147483647)
      MAX-ACCESS  read-only
      STATUS      current
      DESCRIPTION
              "The value of the index into the IPSec SA tunnel table
               that this SA supports (ipsecTunnelIndex)."
      ::= { ipsecSaEntry 2 }

  ipsecSaInboundEspSpi OBJECT-TYPE
      SYNTAX      Unsigned32
      MAX-ACCESS  read-only
      STATUS      current
      DESCRIPTION
              "The value of the SPI for the inbound SA that provides
               the ESP security service, or zero if ESP is not used."
      ::= { ipsecSaEntry 3 }

  ipsecSaOutboundEspSpi OBJECT-TYPE
      SYNTAX      Unsigned32
      MAX-ACCESS  read-only
      STATUS      current
      DESCRIPTION
              "The value of the SPI for the outbound SA that provides
               the ESP security service, or zero if ESP is not used."
      ::= { ipsecSaEntry 4 }

  ipsecSaInboundAhSpi OBJECT-TYPE
      SYNTAX      Unsigned32
      MAX-ACCESS  read-only
      STATUS      current
      DESCRIPTION
              "The value of the SPI for the inbound SA that provides
               the AH security service, or zero if AH is not used."
      ::= { ipsecSaEntry 5 }

  ipsecSaOutboundAhSpi OBJECT-TYPE
      SYNTAX      Unsigned32
      MAX-ACCESS  read-only
      STATUS      current
      DESCRIPTION
              "The value of the SPI for the outbound SA that provides
               the AH security service, or zero if AH is not used."
      ::= { ipsecSaEntry 6 }

  ipsecSaInboundCompCpi OBJECT-TYPE
      SYNTAX      INTEGER (0..65535)
      MAX-ACCESS  read-only
      STATUS      current
      DESCRIPTION
              "The value of the CPI for the inbound SA that provides IP
               compression, or zero if IPCOMP is not used."
      ::= { ipsecSaEntry 7 }

  ipsecSaOutboundCompCpi OBJECT-TYPE
      SYNTAX      INTEGER (0..65535)
      MAX-ACCESS  read-only
      STATUS      current
      DESCRIPTION
              "The value of the CPI for the outbound SA that provides
               IP compression, or zero if IPCOMP is not used."
      ::= { ipsecSaEntry 8 }

  ipsecSaCreationTime OBJECT-TYPE
      SYNTAX      DateAndTime
      MAX-ACCESS  read-only
      STATUS      current
      DESCRIPTION
              "The date and time that the current SA was set up."
      ::= { ipsecSaEntry 9 }

  ipsecSaTimeLimit OBJECT-TYPE
      SYNTAX      Gauge32
      MAX-ACCESS  read-only
      STATUS      current
      DESCRIPTION
              "The maximum lifetime in seconds of the SA, or 0 if there
               is no time constraint on its expiration."
      ::= { ipsecSaEntry 10 }

  ipsecSaTrafficLimit OBJECT-TYPE
      SYNTAX      Gauge32
      MAX-ACCESS  read-only
      STATUS      current
      DESCRIPTION
              "The maximum traffic in 1024-byte blocks that the SA is
               allowed to support, or 0 if there is no traffic
               constraint on its expiration."
      ::= { ipsecSaEntry 11 }

  ipsecSaInboundTraffic OBJECT-TYPE
      SYNTAX      Counter32
      MAX-ACCESS  read-only
      STATUS      current
      DESCRIPTION
              "The amount traffic measured in bytes handled by the SA
               in the inbound direction."
      ::= { ipsecSaEntry 12 }

   ipsecSaOutboundTraffic OBJECT-TYPE
      SYNTAX      Counter32
      MAX-ACCESS  read-only
      STATUS      current
      DESCRIPTION
              "The amount traffic measured in bytes handled by the SA
               in the outbound direction."
      ::= { ipsecSaEntry 13 }

  ipsecSaInboundPackets OBJECT-TYPE
      SYNTAX      Counter32
      MAX-ACCESS  read-only
      STATUS      current
      DESCRIPTION
              "The number of packets handled by the SA in the inbound
               direction."
      ::= { ipsecSaEntry 14 }

  ipsecSaOutboundPackets OBJECT-TYPE
      SYNTAX      Counter32
      MAX-ACCESS  read-only
      STATUS      current
      DESCRIPTION
              "The number of packets handled by the SA in the outbound
               direction."
      ::= { ipsecSaEntry 15 }

  ipsecSaDecryptErrors OBJECT-TYPE
      SYNTAX      Counter32
      MAX-ACCESS  read-only
      STATUS      current
      DESCRIPTION
              "The number of inbound packets discarded by the SA due to
               decryption errors."
      ::= { ipsecSaEntry 16 }

  ipsecSaAuthErrors OBJECT-TYPE
      SYNTAX      Counter32
      MAX-ACCESS  read-only
      STATUS      current
      DESCRIPTION
              "The number of inbound packets discarded by the SA due to
               authentication errors. This includes hash failures in
               both ESP and AH."
      ::= { ipsecSaEntry 17 }

  ipsecSaReplayErrors OBJECT-TYPE
      SYNTAX      Counter32
      MAX-ACCESS  read-only
      STATUS      current
      DESCRIPTION
              "The number of inbound packets discarded by the SA due to
               replay errors. This includes replay failures both ESP and
               AH."
      ::= { ipsecSaEntry 18 }

  ipsecSaOtherReceiveErrors OBJECT-TYPE
      SYNTAX      Counter32
      MAX-ACCESS  read-only
      STATUS      current
      DESCRIPTION
              "The number of inbound packets discarded by the SA due to
               errors other than decryption, authentication or replay
               errors. This may include decompression errors or errors
               due to a lack of receive buffers."
      ::= { ipsecSaEntry 19 }

   ipsecSaSendErrors OBJECT-TYPE
      SYNTAX      Counter32
      MAX-ACCESS  read-only
      STATUS      current
      DESCRIPTION
              "The number of outbound packets discarded by the SA due
               to any error. This may include compression errors or
               errors due to a lack of transmit buffers."
      ::= { ipsecSaEntry 20 }



  -- the IPSec Entity MIB-Group
  --
  -- a collection of objects providing information about overall IPSec
  -- status in the entity


     --
     --      Definitions of significant branches
     --
     ipsecTraps           OBJECT IDENTIFIER  ::= { ipsec 4 }
     ipsecSaCounts        OBJECT IDENTIFIER  ::= { ipsec 5 }
     ipsecPermTunStats    OBJECT IDENTIFIER  ::= { ipsec 6 }
     ipsecTransTunStats   OBJECT IDENTIFIER  ::= { ipsec 7 }
     ipsecNotifications   OBJECT IDENTIFIER  ::= { ipsec 8 }
     ipsecErrorStats      OBJECT IDENTIFIER  ::= { ipsec 9 }

  --
  -- SA counts
  --

  ipsecTotalIkeSAs OBJECT-TYPE
      SYNTAX      Counter32
      MAX-ACCESS  read-only
      STATUS      current
      DESCRIPTION
              "The total number of phase 1 SAs established by the
               entity since boot time. It is not the total number of
               tunnels established by the entity since boot time. It
               does include SAs established to support both permanent
               and transient tunnels."
      ::= { ipsecSaCounts 1 }

  ipsecTotalIpsecSAs OBJECT-TYPE
      SYNTAX      Counter32
      MAX-ACCESS  read-only
      STATUS      current
      DESCRIPTION
              "The total number of phase 2 SAs established by the
               entity since boot time. It is not the total number of
               IPSec virtual tunnels established by the entity since
               boot time. It does include SAs established to support
               permanent and transient tunnels.

               It is recommended that SA bundles or security suites be
               considered a single SA for the purposes of this
               statistic."
      ::= { ipsecSaCounts 2 }

  --
  -- permanent tunnel statistics
  --

  ipsecCnfgPermIkeTunnels OBJECT-TYPE
      SYNTAX      Gauge32
      MAX-ACCESS  read-only
      STATUS      current
      DESCRIPTION
              "The total number of phase 1 tunnels in the entity that
               are configured as permanent."
      ::= { ipsecPermTunStats 1 }

  ipsecUpPermIkeTunnels OBJECT-TYPE
      SYNTAX      Gauge32
      MAX-ACCESS  read-only
      STATUS      current
      DESCRIPTION
              "The total number of phase 1 tunnels in the entity that
               are configured as permanent and are up and available for
               use."
      ::= { ipsecPermTunStats 2 }

  ipsecCnfgPermIpsecTunnels OBJECT-TYPE
      SYNTAX      Gauge32
      MAX-ACCESS  read-only
      STATUS      current
      DESCRIPTION
              "The total number of phase 2 tunnels in the entity that
               are configured as permanent."
      ::= { ipsecPermTunStats 3 }

  ipsecUpPermIpsecTunnels OBJECT-TYPE
      SYNTAX      Gauge32
      MAX-ACCESS  read-only
      STATUS      current
      DESCRIPTION
              "The total number of phase 2 tunnels in the entity that
               are configured as permanent and are up and available for
               use."
      ::= { ipsecPermTunStats 4 }

  --
  -- transient tunnel counts
  --

  ipsecTotalTransIkeTunnels OBJECT-TYPE
      SYNTAX      Counter32
      MAX-ACCESS  read-only
      STATUS      current
      DESCRIPTION
              "The total number of transient phase 1 tunnels
               established by the entity since boot time."
      ::= { ipsecTransTunStats 1 }

  ipsecCurrentTransIkeTunnels OBJECT-TYPE
      SYNTAX      Gauge32
      MAX-ACCESS  read-only
      STATUS      current
      DESCRIPTION
              "The number of transient phase 1 tunnels in the entity
               that are up and available for use at this moment in
               time."
      ::= { ipsecTransTunStats 2 }

  ipsecTotalTransIpsecTunnels OBJECT-TYPE
      SYNTAX      Counter32
      MAX-ACCESS  read-only
      STATUS      current
      DESCRIPTION
              "The total number of transient phase 2 tunnels
               established by the entity since boot time."
      ::= { ipsecTransTunStats 3 }

  ipsecCurrentTransIpsecTunnels OBJECT-TYPE
      SYNTAX      Gauge32
      MAX-ACCESS  read-only
      STATUS      current
      DESCRIPTION
              "The number of phase 2 tunnels in the entity that are up
               and available for use at this moment in time."
      ::= { ipsecTransTunStats 4 }

  --
   -- transient SA traffic statistics
   --

   ipsecTotalTransInboundPackets OBJECT-TYPE
      SYNTAX      Counter32
      MAX-ACCESS  read-only
      STATUS      current
      DESCRIPTION
              "The total number of inbound packets carried on transient
               IPSec tunnels since boot time."
      ::= { ipsecTransTunStats 5 }

  ipsecTotalTransOutboundPackets OBJECT-TYPE
      SYNTAX      Counter32
      MAX-ACCESS  read-only
      STATUS      current
      DESCRIPTION
              "The total number of outbound packets carried on
               transient IPSec tunnels since boot time."
      ::= { ipsecTransTunStats 6 }

  ipsecTotalTransInboundTraffic OBJECT-TYPE
      SYNTAX      Counter32
      MAX-ACCESS  read-only
      STATUS      current
      DESCRIPTION
              "The total amount of inbound traffic carried on transient
               IPSec tunnels since boot time, measured in 1024-octet
               blocks."
      ::= { ipsecTransTunStats 7 }

  ipsecTotalTransOutboundTraffic OBJECT-TYPE
      SYNTAX      Counter32
      MAX-ACCESS  read-only
      STATUS      current
      DESCRIPTION
              "The total amount of outbound traffic carried on
               transient IPSec tunnels since boot time, measured in
               1024-octet blocks."
      ::= { ipsecTransTunStats 8 }
	  
  ipsecTotalTransIkeSetupFailures OBJECT-TYPE
      SYNTAX      Counter32
      MAX-ACCESS  read-only
      STATUS      current
      DESCRIPTION
              "The total number of IKE SA set up attempts that have
               failed since entity boot time. This includes SAs
               associated with transient tunnels only."
      ::= { ipsecTransTunStats 9 }

  --
  -- error counts
  --

  ipsecUnknownSpiErrors OBJECT-TYPE
      SYNTAX      Counter32
      MAX-ACCESS  read-only
      STATUS      current
       DESCRIPTION
              "The total number of packets received by the entity since
               boot time with SPIs or CPIs that were not valid."
      ::= { ipsecErrorStats 1 }

  ipsecIkeProtocolErrors OBJECT-TYPE
      SYNTAX      Counter32
      MAX-ACCESS  read-only
      STATUS      current
      DESCRIPTION
              "The total number of packets received by the entity since
               boot time with IKE protocol errors.

               This includes packets with invalid cookies, but does not
               include errors that could be associated with specific IKE
               SAs."
      ::= { ipsecErrorStats 2 }

  ipsecIpsecAuthenticationErrors OBJECT-TYPE
      SYNTAX      Counter32
      MAX-ACCESS  read-only
      STATUS      current
      DESCRIPTION
              "The total number of packets received by the entity since
               boot time with authentication errors in the IPSec SAs.

               This includes all packets in which the hash value is
               determined to be invalid."
      ::= { ipsecErrorStats 3 }

  ipsecIpsecReplayErrors OBJECT-TYPE
      SYNTAX      Counter32
      MAX-ACCESS  read-only
      STATUS      current
      DESCRIPTION
              "The total number of packets received by the entity since
               boot time with replay errors in the IPSec SAs."
      ::= { ipsecErrorStats 4 }

   ipsecIpsecPolicyErrors OBJECT-TYPE
      SYNTAX      Counter32
      MAX-ACCESS  read-only
      STATUS      current
      DESCRIPTION
              "The total number of packets received by the entity since
               boot time and discarded due to policy errors. This
               includes packets that had selectors that were invalid for
               the SA that carried them."
      ::= { ipsecErrorStats 5 }


  -- the IPSec Notify Message MIB-Group
  --
  -- a collection of objects providing information about
  -- the occurrences of notify messages


  ipsecNotifyMessageTotalCount OBJECT-TYPE
      SYNTAX      Counter32
      MAX-ACCESS  read-only
      STATUS      current
      DESCRIPTION
              "The total number of all types of notify messages sent or
               received by the entity since boot time.

               It is the sum of all occurrences in the
               'ipsecNotifyCountTable'."
      ::= { ipsecNotifications 1 }

  ipsecNotifyCountTable OBJECT-TYPE
      SYNTAX     SEQUENCE OF IpsecNotifyCountEntry
      MAX-ACCESS not-accessible
      STATUS     current
      DESCRIPTION
              "The (conceptual) table containing information on IPSec
               notify message counts.

               This table MAY be sparsely populated; that is, rows for
               which the count is 0 may be absent."
      ::= { ipsecNotifications 2 }

  ipsecNotifyCountEntry OBJECT-TYPE
      SYNTAX     IpsecNotifyCountEntry
      MAX-ACCESS not-accessible
      STATUS     current
      DESCRIPTION
              "An entry (conceptual row) containing the total number of
               occurrences of a notify message."
      INDEX      { ipsecNotifyMessage }
      ::= { ipsecNotifyCountTable 1 }

  IpsecNotifyCountEntry::= SEQUENCE {
      ipsecNotifyMessage        INTEGER,
      ipsecNotifyMessageCount   Counter32
  }

  ipsecNotifyMessage OBJECT-TYPE
      SYNTAX      INTEGER (0..65535)
      MAX-ACCESS  read-only
      STATUS      current
      DESCRIPTION
              "The value representing a specific IPSec notify message,
               or 0 if unknown.

               Values are assigned from the set of notify message types
               as defined in Section 3.14.1 of [ISAKMP]. In addition,
               the value 0 may be used for this object when the object
               is used as a trap cause, and the cause is unknown."
      ::= { ipsecNotifyCountEntry 1 }

  ipsecNotifyMessageCount OBJECT-TYPE
      SYNTAX      Counter32
      MAX-ACCESS  read-only
      STATUS      current
      DESCRIPTION
              "The total number of times the specific notify message
               has been received or sent by the entity since system
               boot."
      ::= { ipsecNotifyCountEntry 2 }



  --
  -- traps
  --

  ipsecTrapsObjects OBJECT IDENTIFIER  ::= { ipsecTraps 0 }

  ipsecTrapPermIkeNegFailure NOTIFICATION-TYPE
      OBJECTS {
               ipsecIkeSaIndex,
               ipsecNotifyMessage
               }
      STATUS  current
      DESCRIPTION
               "An attempt to negotiate a phase 1 SA for the specified
               permanent IKE tunnel failed."
      ::= { ipsecTrapsObjects 1 }

   ipsecTrapTransIkeNegFailure NOTIFICATION-TYPE
      OBJECTS {
               ipsecIkeSaPeerIpAddress,
               ipsecIkeSaPeerPortNumber,
               ipsecIkeSaAuthMethod,
               ipsecIkeSaPeerIdType,
               ipsecIkeSaPeerId,
               ipsecIkeSaPeerCertSerialNum,
               ipsecIkeSaPeerCertIssuer,
               ipsecNotifyMessage
               }
      STATUS  current
      DESCRIPTION
               "An attempt to negotiate a phase 1 SA for a transient IKE
               tunnel failed.

               This trap is different from the
               'ipsecTrapPermIkeNegFailure' trap, since this one will
               likely result in the removal of this entry from the IKE
               SA tunnel table."
      ::= { ipsecTrapsObjects 2 }

   ipsecTrapInvalidCookie NOTIFICATION-TYPE
      OBJECTS {
               ipsecIkeSaPeerIpAddress,
               ipsecIkeSaPeerPortNumber
               }
      STATUS  current
      DESCRIPTION
               "IKE packets with invalid cookies were detected from the
               specified peer.

               Implementations SHOULD send one trap per peer (within a
               reasonable time period, rather than sending one trap per
               packet."
      ::= { ipsecTrapsObjects 3 }

   ipsecTrapIpsecNegFailure NOTIFICATION-TYPE
      OBJECTS {
               ipsecIkeSaIndex,
               ipsecNotifyMessage
               }
      STATUS  current
      DESCRIPTION
               "An attempt to negotiate a phase 2 SA within the
               specified IKE tunnel failed."
      ::= { ipsecTrapsObjects 4 }

   ipsecTrapIpsecAuthFailure NOTIFICATION-TYPE
      OBJECTS {
               ipsecSaIndex
               }
      STATUS  current
      DESCRIPTION
               "IPSec packets with invalid hashes were found in the
               specified SA.

               Implementations SHOULD send one trap per SA (within a
               reasonable time period), rather than sending one trap per
               packet."
      ::= { ipsecTrapsObjects 5 }

   ipsecTrapIpsecReplayFailure NOTIFICATION-TYPE
      OBJECTS {
               ipsecSaIndex
               }
      STATUS  current
       DESCRIPTION
               "IPSec packets with invalid sequence numbers were found
               in the specified SA.

               Implementations SHOULD send one trap per SA (within a
               reasonable time period), rather than sending one trap per
               packet."
      ::= { ipsecTrapsObjects 6 }

   ipsecTrapIpsecPolicyFailure NOTIFICATION-TYPE
      OBJECTS {
               ipsecSaIndex
               }
      STATUS  current
      DESCRIPTION
               "IPSec packets carrying packets with invalid selectors
               for the specified SA were found.

               Implementations SHOULD send one trap per SA (within a
               reasonable time period), rather than sending one trap per
               packet."
      ::= { ipsecTrapsObjects 7 }

   ipsecTrapInvalidSpi NOTIFICATION-TYPE
      OBJECTS {
               ipsecIkeSaPeerIpAddress
               }
      STATUS  current
      DESCRIPTION
               "ESP, AH or IPCOMP packets with unknown SPIs (or CPIs)
               were detected from the specified peer.

               Implementations SHOULD send one trap per peer (within a
               reasonable time period), rather than sending one trap per
               packet."
      ::= { ipsecTrapsObjects 8 }

END
