ACC-RADIUS DEFINITIONS ::= BEGIN

    IMPORTS
	 OBJECT-TYPE, IpAddress, TimeTicks, Gauge, Counter FROM RFC1155-SMI
	 TRAP-TYPE FROM RFC-1215
       accTrapLogSeqNum FROM ACC-SYSTEM
accBRG, DisplayString, RowStatus, IfIndex, SmdsAddress
             FROM ACC-MIB;

-- Radius Group
   accRadius         OBJECT IDENTIFIER ::= { accBRG 44 }
      -- Generic Radius objects
      accRadiusNASIdentifier	OBJECT-TYPE
      	SYNTAX		OCTET STRING
      	ACCESS		read-write
      	STATUS		mandatory
      	DESCRIPTION	
      	"The string used to identify the NAS to a Radius server"
      ::= { accRadius 1 }
      accRadiusInvAttribAction  OBJECT-TYPE
        SYNTAX          INTEGER (0..90)
        ACCESS          read-write
        STATUS          mandatory
        DESCRIPTION
        "Invalid Attribute Action"
      ::= { accRadius 2 }
      accRadiusMaxPort 	OBJECT-TYPE
      	SYNTAX		INTEGER (0..90)
      	ACCESS		read-write
      	STATUS		mandatory
      	DESCRIPTION	
      	"The maximum number of simultaneous calls that can be authenticated
      	 using the Radius protocol"
      ::= { accRadius 3 }
      accRadiusPortRangeStart 	OBJECT-TYPE
      	SYNTAX		INTEGER
      	ACCESS		read-only
      	STATUS		mandatory
      	DESCRIPTION	
      	"The ifIndex for the start of the Radius port range."
      ::= { accRadius 4 }
      accRadiusPortRangeEnd 	OBJECT-TYPE
      	SYNTAX		INTEGER
      	ACCESS		read-only
      	STATUS		mandatory
      	DESCRIPTION	
      	"The ifIndex for the end of the Radius port range."
      ::= { accRadius 5 }
      accRadiusNASIpAddress    OBJECT-TYPE
        SYNTAX          IpAddress
        ACCESS          read-write
        STATUS          mandatory
        DESCRIPTION
        "The IP address used to identify the NAS to a Radius server"
      ::= { accRadius 11 }
      -- Radius Authentication Objects
      accRadiusAuth	OBJECT IDENTIFIER	::= { accRadius 6 }
      -- Radius Authentication Server Objects
      accRadiusAuthServTable	OBJECT-TYPE
      	SYNTAX		SEQUENCE OF AccRadiusAuthServEntry
      	ACCESS		not-accessible
      	STATUS		mandatory
      	DESCRIPTION
      	"Table of Radius authentication Server Information"
      ::= { accRadiusAuth 1 }
      accRadiusAuthServEntry	OBJECT-TYPE
      	SYNTAX		AccRadiusAuthServEntry
      	ACCESS		not-accessible
      	STATUS		mandatory
      	DESCRIPTION
      	"A single Radius authentication server configuration and status"
      INDEX		{ accRadiusAuthServIndex }
      ::= { accRadiusAuthServTable 1 }
      AccRadiusAuthServEntry ::=
      	SEQUENCE {
      	accRadiusAuthServIndex	INTEGER,
      	accRadiusAuthServAdState	INTEGER,
      	accRadiusAuthServAddr	IpAddress,
      	accRadiusAuthServPassword 	OCTET STRING,
      	accRadiusAuthServRetryInt	TimeTicks,
      	accRadiusAuthServRetryCnts	INTEGER,
      	accRadiusAuthServUDPPort	INTEGER,
      	accRadiusAuthServOpState	INTEGER,
      	accRadiusAuthServReqCnts	Counter,
      	accRadiusAuthServAccCnts	Counter,
      	accRadiusAuthServRejCnts	Counter,
	accRadiusAuthServAccessPart DisplayString,
	accRadiusAuthServSecure 	INTEGER
      }
      accRadiusAuthServIndex	OBJECT-TYPE
      	SYNTAX		INTEGER (1..8)
      	ACCESS		read-write
      	STATUS		mandatory
      	DESCRIPTION	
      	"The index of this entry in the server table"
      ::= { accRadiusAuthServEntry 1 }
      accRadiusAuthServAdState	OBJECT-TYPE
      	SYNTAX		INTEGER {
      			enabled (1),
      			disabled (2),
      			deleted(3)
      		}
      	ACCESS		read-write
      	STATUS		mandatory
      	DESCRIPTION	
      	"The administrative state of the server entry.  Enables (and creates 
      	if not present), disables or deletes a server entry"
      ::= { accRadiusAuthServEntry 2 }
      accRadiusAuthServAddr	OBJECT-TYPE
      	SYNTAX		IpAddress
      	ACCESS		read-write
      	STATUS		mandatory
      	DESCRIPTION	
      	"The IP address of the authentication server"
      ::= { accRadiusAuthServEntry 3 }
      accRadiusAuthServPassword OBJECT-TYPE
      	SYNTAX		OCTET STRING
      	ACCESS		read-write
      	STATUS		mandatory
      	DESCRIPTION	
      	"The secret shared between the NAS and the authentication server"
      ::= { accRadiusAuthServEntry 4 }
      accRadiusAuthServRetryInt	OBJECT-TYPE
--     	SYNTAX		INTEGER (1..60)
      	SYNTAX		TimeTicks
      	ACCESS		read-write
      	STATUS		mandatory
      	DESCRIPTION	
      	"The time in seconds to wait for a reply for an access-request from 
      	sent to the authentication server"
      ::= { accRadiusAuthServEntry 5 }
      accRadiusAuthServRetryCnts	OBJECT-TYPE
      	SYNTAX		INTEGER (1..10)
      	ACCESS		read-write
      	STATUS		mandatory
      	DESCRIPTION	
      	"The number of times to attempt to send an access-request to a server"
      ::= { accRadiusAuthServEntry 6 }
      accRadiusAuthServUDPPort	OBJECT-TYPE
      	SYNTAX		INTEGER (1..65535)
      	ACCESS		read-write
      	STATUS		mandatory
      	DESCRIPTION	
      	"The destination UDP port number on the server to send an
      	 access-request to"
      ::= { accRadiusAuthServEntry 7 }
      accRadiusAuthServOpState	OBJECT-TYPE
      	SYNTAX		INTEGER {
      			up (1),
      			down (2),
      			unknown (3),
      			disabled (4)
      		}
      	ACCESS		read-only
      	STATUS		mandatory
      	DESCRIPTION	
      	"The operational state of a server entry.  UP for a server that
      	 has responded to the last request sent to it.  DOWN for a server
      	 that did not respond to the last request sent to it.
      	 UNKNOWN for a server that we have not recently sent a request to.
      	 DISABLED for a server entry whose admin state is DISABLED"
      ::= { accRadiusAuthServEntry 8 }
      accRadiusAuthServReqCnts	OBJECT-TYPE
      	SYNTAX		Counter
      	ACCESS		read-only
      	STATUS		mandatory
      	DESCRIPTION	
      	"The number of access-requests that have been sent to a server"
      ::= { accRadiusAuthServEntry 9 }
      accRadiusAuthServAccCnts	OBJECT-TYPE
      	SYNTAX		Counter
      	ACCESS		read-only
      	STATUS		mandatory
      	DESCRIPTION	
      	"The number of access accepts that have been received from a server"
      ::= { accRadiusAuthServEntry 10 }
      accRadiusAuthServRejCnts	OBJECT-TYPE
      	SYNTAX		Counter
      	ACCESS		read-only
      	STATUS		mandatory
      	DESCRIPTION	
      	"The number of access rejects that have ben received from a server"
      ::= { accRadiusAuthServEntry 11 }
	accRadiusAuthServAccessPart OBJECT-TYPE
	    SYNTAX DisplayString -- (Size(1..16))
	    ACCESS read-write
	    STATUS obsolete
	    DESCRIPTION
	       "The access partition associated with this authentication 
	        server.  If an access partition name has been configured, this 
	        authentication server will only by used to process requests 
	        associated with the indicated access partition.  This object 
	        may also be used to configure the name of a proxy server."
	    ::= { accRadiusAuthServEntry 12 }
	accRadiusAuthServSecure OBJECT-TYPE
      	   SYNTAX		INTEGER {
      			secure (1),
      			unsecure (2)
      		}
	    ACCESS read-write
	    STATUS mandatory
	    DESCRIPTION
	       "Certain attributes are considered secure as the
	       values set may comprimise access partitions.  A server
	       must have this object set to secure to support sending
	       these secure attributes to the NAS."
	    ::= { accRadiusAuthServEntry 13 }
      -- Generic Radius Authentication Objects
      accRadiusAuthMsgLvl	OBJECT-TYPE
      	SYNTAX		INTEGER (1..7)
      	ACCESS		read-write
      	STATUS		mandatory
      	DESCRIPTION
      	"The diagnostic message level for Radius authentication."
      ::= { accRadiusAuth 2 }
      accRadiusAuthRecoverTO	OBJECT-TYPE
--      	SYNTAX		INTEGER (0..86400)
      	SYNTAX		TimeTicks
      	ACCESS		read-write
      	STATUS		mandatory
      	DESCRIPTION
      	"The time a server entry will remain in the DOWN
         state before transitioning to UNKNOWN"
      ::= { accRadiusAuth 3 }
      accRadiusAuthReqDiscs     OBJECT-TYPE
        SYNTAX          Counter
        ACCESS          read-write
        STATUS          mandatory
        DESCRIPTION
        "the number of authentication server requests discarded"
      ::= { accRadiusAuth 4 }
      accRadiusAuthRespDiscs     OBJECT-TYPE
        SYNTAX          Counter
        ACCESS          read-write
        STATUS          mandatory
        DESCRIPTION
        "the number of authentication server responses discarded"
      ::= { accRadiusAuth 5 }
      accRadiusAuthLastUser	OBJECT-TYPE
      	SYNTAX		OCTET STRING
      	ACCESS		read-only
      	STATUS		mandatory
      	DESCRIPTION
      	"The user name of the last caller we performed Radius authentication for"
      ::= { accRadiusAuth 6 }
      accRadiusAuthLastType	OBJECT-TYPE
      	SYNTAX		INTEGER {
      			access-request (1),
      			access-accept (2),
      			access-reject (3)
      		}
      	ACCESS		read-write
      	STATUS		mandatory
      	DESCRIPTION
      	"The type of the last Radius authentication frame received/transmitted"
      ::= { accRadiusAuth 7 }
      accRadiusAuthCallsRejs     OBJECT-TYPE
        SYNTAX          Counter
        ACCESS          read-write
        STATUS          mandatory
        DESCRIPTION
        "The number of calls rejected due to no replies being received from
        configured servers"
      ::= { accRadiusAuth 8 }
      accRadiusAuthConfigErrs     OBJECT-TYPE
        SYNTAX          Counter
        ACCESS          read-write
        STATUS          mandatory
        DESCRIPTION
        "the number of dynamic configuration errors"
      ::= { accRadiusAuth 9 }
      -- Radius Authentication User Debug Table
      accRadiusAuthDebugTable    OBJECT-TYPE
        SYNTAX          SEQUENCE OF AccRadiusAuthDebugEntry
        ACCESS          not-accessible
        STATUS          mandatory
        DESCRIPTION
        "Table of Radius User Debug Sessions"
      ::= { accRadiusAuth 10 }
      accRadiusAuthDebugEntry    OBJECT-TYPE
        SYNTAX          AccRadiusAuthDebugEntry
        ACCESS          not-accessible
        STATUS          mandatory
        DESCRIPTION
        "A single Radius authentication user debug session"
      INDEX             { accRadiusAuthDebugName }
      ::= { accRadiusAuthDebugTable 1 }
      AccRadiusAuthDebugEntry ::= SEQUENCE {
        accRadiusAuthDebugName  OCTET STRING,
        accRadiusAuthDebugMask        INTEGER
      }
      accRadiusAuthDebugName	OBJECT-TYPE
      	SYNTAX		OCTET STRING
      	ACCESS		read-write
      	STATUS		mandatory
      	DESCRIPTION	
      	"The name of the user to run a debug session for"
      ::= { accRadiusAuthDebugEntry 1 }
      accRadiusAuthDebugMask	OBJECT-TYPE
      	SYNTAX		INTEGER
      	ACCESS		read-write
      	STATUS		mandatory
      	DESCRIPTION	
      	"The debug mask to use for the users debug session"
      ::= { accRadiusAuthDebugEntry 2 }
      -- Radius Accounting Objects
      accRadiusAcct	OBJECT IDENTIFIER	::= { accRadius 7 }
      -- Radius Accounting Server Objects
      accRadiusAcctServTable	OBJECT-TYPE
      	SYNTAX		SEQUENCE OF AccRadiusAcctServEntry
      	ACCESS		not-accessible
      	STATUS		mandatory
      	DESCRIPTION
      	"Table of Radius accounting Server Information"
      ::= { accRadiusAcct 1 }
      accRadiusAcctServEntry	OBJECT-TYPE
      	SYNTAX		AccRadiusAcctServEntry
      	ACCESS		not-accessible
      	STATUS		mandatory
      	DESCRIPTION
      	"A single Radius accounting server configuration and status"
      INDEX		{ accRadiusAcctServIndex }
      ::= { accRadiusAcctServTable 1 }
      AccRadiusAcctServEntry ::= SEQUENCE {
      	accRadiusAcctServIndex	INTEGER,
      	accRadiusAcctServAdState	INTEGER,
      	accRadiusAcctServAddr	IpAddress,
      	accRadiusAcctServPassword 	OCTET STRING,
      	accRadiusAcctServRetryInt	TimeTicks,
      	accRadiusAcctServRetryCnts	INTEGER,
      	accRadiusAcctServUDPPort	INTEGER,
      	accRadiusAcctServOpState	INTEGER,
      	accRadiusAcctServReqCnts	Counter,
      	accRadiusAcctServAccCnts	Counter,
	accRadiusAcctServAccessPart DisplayString,
        accRadiusAcctServIBCAttrSupp    INTEGER
      }
      accRadiusAcctServIndex	OBJECT-TYPE
      	SYNTAX		INTEGER (1..8)
      	ACCESS		read-write
      	STATUS		mandatory
      	DESCRIPTION	
      	"The index of this entry in the server table"
      ::= { accRadiusAcctServEntry 1 }
      accRadiusAcctServAdState	OBJECT-TYPE
      	SYNTAX		INTEGER {
      			enabled (1),
      			disabled (2),
      			deleted(3)
      		}
      	ACCESS		read-write
      	STATUS		mandatory
      	DESCRIPTION	
      	"The administrative state of the server entry.  Enables (and creates 
      	 if not present), disables or deletes a server entry"
      ::= { accRadiusAcctServEntry 2 }
      accRadiusAcctServAddr	OBJECT-TYPE
      	SYNTAX		IpAddress
      	ACCESS		read-write
      	STATUS		mandatory
      	DESCRIPTION	
      	"The IP address of the accounting server"
      ::= { accRadiusAcctServEntry 3 }
      accRadiusAcctServPassword 	OBJECT-TYPE
      	SYNTAX		OCTET STRING
      	ACCESS		read-write
      	STATUS		mandatory
      	DESCRIPTION	
      	"The secret shared between the NAS and the accounting server"
      ::= { accRadiusAcctServEntry 4 }
      accRadiusAcctServRetryInt	OBJECT-TYPE
--     	SYNTAX		INTEGER (1..60)
      	SYNTAX		TimeTicks
      	ACCESS		read-write
      	STATUS		mandatory
      	DESCRIPTION	
      	"The time in seconds to wait for a reply for an accounting-request from 
       	 sent to the accounting server"
      ::= { accRadiusAcctServEntry 5 }
      accRadiusAcctServRetryCnts	OBJECT-TYPE
      	SYNTAX		INTEGER (1..10)
      	ACCESS		read-write
      	STATUS		mandatory
      	DESCRIPTION	
      	"The number of times to attempt to send an accounting-request to
      	 a server"
      ::= { accRadiusAcctServEntry 6 }
      accRadiusAcctServUDPPort	OBJECT-TYPE
      	SYNTAX		INTEGER (1..65535)
      	ACCESS		read-write
      	STATUS		mandatory
      	DESCRIPTION	
      	"The destination UDP port number on the server to send an
      	 accounting-request to"
      ::= { accRadiusAcctServEntry 7 }
      accRadiusAcctServOpState	OBJECT-TYPE
      	SYNTAX		INTEGER {
      			up (1),
      			down (2),
      			unknown (3),
      			disabled (4)
      		}
      	ACCESS		read-only
      	STATUS		mandatory
      	DESCRIPTION	
      	"The operational state of a server entry. UP for a server that has
      	 responded to the last request sent to it.
      	 DOWN for a server that did not respond to the last request sent to it. 	 UNKNOWN for a server that we have not recently sent a request to.
      	 DISABLED for a server entry whose admin state is DISABLED"
      ::= { accRadiusAcctServEntry 8 }
      accRadiusAcctServReqCnts	OBJECT-TYPE
      	SYNTAX		Counter
      	ACCESS		read-only
      	STATUS		mandatory
      	DESCRIPTION	
      	"The number of accounting-requests that have been sent to a server"
      ::= { accRadiusAcctServEntry 9 }
      accRadiusAcctServAccCnts	OBJECT-TYPE
      	SYNTAX		Counter
      	ACCESS		read-only
      	STATUS		mandatory
      	DESCRIPTION	
      	"The number of accounting responses that have been received from a
      	 server"
      ::= { accRadiusAcctServEntry 10 }
	accRadiusAcctServAccessPart OBJECT-TYPE
	    SYNTAX DisplayString -- (Size(1..16))
	    ACCESS read-write
	    STATUS obsolete
	    DESCRIPTION
	       "The access partition associated with this authentication 
	        server.  If an access partition name has been configured, this 
	        authentication server will only by used to process requests 
	        associated with the indicated access partition.  This object 
	        may also be used to configure the name of a proxy server."
	    ::= { accRadiusAcctServEntry 11 }
        accRadiusAcctServIBCAttrSupp OBJECT-TYPE
            SYNTAX INTEGER {
                enabled (1),
                disabled (2)
            }
            ACCESS read-write
            STATUS mandatory
            DESCRIPTION
            "Validity of the Internet Billing support feature."
            ::= { accRadiusAcctServEntry 13 }
      -- Generic Radius Accounting Objects
      accRadiusAcctMsgLvl	OBJECT-TYPE
      	SYNTAX		INTEGER (1..7)
      	ACCESS		read-write
      	STATUS		mandatory
      	DESCRIPTION
      	"The diagnostic message level for Radius accounting."
      ::= { accRadiusAcct 2 }
      accRadiusAcctRecoverTO	OBJECT-TYPE
--      	SYNTAX		INTEGER (0..86400)
      	SYNTAX		TimeTicks
      	ACCESS		read-write
      	STATUS		mandatory
      	DESCRIPTION
      	"The time a server entry will remain in the DOWN state before
      	 transitioning to UNKNOWN"
      ::= { accRadiusAcct 3 }
      accRadiusAcctReqDiscs	OBJECT-TYPE
      	SYNTAX		Counter
      	ACCESS		read-only
      	STATUS		mandatory
      	DESCRIPTION
      	"The number of accounting requests discarded due to no responses being 
      	 received from  configured servers"
      ::= { accRadiusAcct 4 }
      accRadiusAcctRespDiscs      OBJECT-TYPE
        SYNTAX          Counter
        ACCESS          read-only
        STATUS          mandatory
        DESCRIPTION
        "The number of accounting responses discarded."
      ::= { accRadiusAcct 5 }
      accRadiusAcctLastUser	OBJECT-TYPE
      	SYNTAX		OCTET STRING
      	ACCESS		read-only
      	STATUS		mandatory
      	DESCRIPTION
      	"The user name of the last caller we performed Radius accounting for"
      ::= { accRadiusAcct 6 }
      accRadiusAcctLastType	OBJECT-TYPE
      	SYNTAX		INTEGER {
      			acct-request (1),
      			acct-response (2)
      		}
      	ACCESS		read-only
      	STATUS		mandatory
      	DESCRIPTION
      	"The type of the last Radius accounting frame received/transmitted"
      ::= { accRadiusAcct 7 }
      accRadiusDebugMask     OBJECT-TYPE
        SYNTAX          INTEGER
        ACCESS          read-write
        STATUS          mandatory
        DESCRIPTION
        "Mask for turning on debugging messages"
      ::= { accRadius 8 }
      accRadiusGroupRangeStart     OBJECT-TYPE
        SYNTAX          INTEGER
        ACCESS          read-write
        STATUS          mandatory
        DESCRIPTION
        " Group range start"
      ::= { accRadius 9 }
      accRadiusGroupRangeEnd     OBJECT-TYPE
        SYNTAX          INTEGER
        ACCESS          read-write
        STATUS          mandatory
        DESCRIPTION
        " Group range end"
      ::= { accRadius 10 }
-- START MANILA_NEW
-- RADIUS Traps
      accRadiusTraps     OBJECT IDENTIFIER	::= { accRadius 12 }
	accRadiusTrapMsg OBJECT-TYPE
        SYNTAX          INTEGER
        ACCESS          read-only
        STATUS          mandatory
        DESCRIPTION
        "RADIUS trap message. "
      ::= { accRadiusTraps 1 }
-- END MANILA_NEW

        accRadiusServerDnTrap TRAP-TYPE
        ENTERPRISE   accRadiusTraps 
        VARIABLES  { accRadiusTrapMsg,
		     accRadiusAuthServAddr,
		     accRadiusAuthServOpState ,
        accTrapLogSeqNum}
        DESCRIPTION
		"When the operation state of the server goes down 
		this trap is generated. 
SEVERITY-DEFAULT: Major 
EVENTTYPE-DEFAULT: 10 
ADDITIONAL-TEXT-VARIABLES: { accTrapLogSeqNum,accRadiusTrapMsg }
PCAUSE-DEFAULT: 46 " 
 
        ::= 1  
        accRadiusUsrNameTrap TRAP-TYPE
        ENTERPRISE   accRadiusTraps 
        VARIABLES  { accRadiusTrapMsg,
                     accRadiusAuthLastUser ,
                      accTrapLogSeqNum}
        DESCRIPTION
		"If the user name length too high which is not 
		supported by the RADIUS server then this trap is 
		generated.
SEVERITY-DEFAULT: Warning 
EVENTTYPE-DEFAULT: 10 
ADDITIONAL-TEXT-VARIABLES: { accTrapLogSeqNum,accRadiusTrapMsg }
PCAUSE-DEFAULT: 4 " 
 
        ::= 2  
        accRadiusInOpportuneEvntTrap TRAP-TYPE
        ENTERPRISE   accRadiusTraps 
        VARIABLES  { accRadiusTrapMsg,
                     accRadiusNASIdentifier,
                     accRadiusAuthServRetryCnts ,
                      accTrapLogSeqNum}
        DESCRIPTION
		"Indicates that the event is not found in the list of 
		events supported.
SEVERITY-DEFAULT: Minor 
EVENTTYPE-DEFAULT: 10 
ADDITIONAL-TEXT-VARIABLES: { accTrapLogSeqNum,accRadiusTrapMsg }
PCAUSE-DEFAULT: 46 " 
 
        ::= 3  
        accRadiusEvntCfgAddNakTrap TRAP-TYPE
        ENTERPRISE   accRadiusTraps 
        VARIABLES  { accRadiusTrapMsg,
                     accRadiusAuthConfigErrs  ,
                      accTrapLogSeqNum}
        DESCRIPTION
		 "Configuration of entity <param1> failed (<param2>) 
SEVERITY-DEFAULT: Warning 
EVENTTYPE-DEFAULT: 10 
ADDITIONAL-TEXT-VARIABLES: { accTrapLogSeqNum,accRadiusTrapMsg }
PCAUSE-DEFAULT: 7 " 
 
        ::= 4  
        accRadiusEvntMutexAttribTrap TRAP-TYPE
        ENTERPRISE   accRadiusTraps 
        VARIABLES  { accRadiusTrapMsg,
                     accRadiusAuthConfigErrs ,
                      accTrapLogSeqNum}
        DESCRIPTION
		"Indicates that both the framed attributes and tunnel 
		attributes are present. It means RADIUS need to 
		configure both framed PPP session and tunnel session 
		which is not possible.
SEVERITY-DEFAULT: Warning 
EVENTTYPE-DEFAULT: 10 
ADDITIONAL-TEXT-VARIABLES: { accTrapLogSeqNum,accRadiusTrapMsg }
PCAUSE-DEFAULT: 7 " 
 
        ::= 5  
        accRadiusEvntReqTrap TRAP-TYPE
        ENTERPRISE   accRadiusTraps 
        VARIABLES  { accRadiusTrapMsg,
                     accRadiusAuthConfigErrs ,
                      accTrapLogSeqNum}
        DESCRIPTION
		"This trap indicates that there is a mismatch 
		between the PPP attributes and one in requested type.
SEVERITY-DEFAULT: Warning 
EVENTTYPE-DEFAULT: 10 
ADDITIONAL-TEXT-VARIABLES: { accTrapLogSeqNum,accRadiusTrapMsg }
PCAUSE-DEFAULT: 7 " 
 
        ::= 6  
        accRadiusEvntSPTrap TRAP-TYPE
        ENTERPRISE   accRadiusTraps 
        VARIABLES  { accRadiusTrapMsg,
                     accRadiusAuthConfigErrs ,
                      accTrapLogSeqNum}
        DESCRIPTION
		"This trap indicates that there is a incompatibility 
		between the Framed PPP service and the service profile.
SEVERITY-DEFAULT: Warning 
EVENTTYPE-DEFAULT: 10 
ADDITIONAL-TEXT-VARIABLES: { accTrapLogSeqNum,accRadiusTrapMsg }
PCAUSE-DEFAULT: 7 " 
 
        ::= 7  
        accRadiusEvntCfgTrap TRAP-TYPE
        ENTERPRISE   accRadiusTraps 
        VARIABLES  { accRadiusTrapMsg,
                     accRadiusAuthConfigErrs ,
                      accTrapLogSeqNum}
        DESCRIPTION
		"Proxy mode tunneling not enabled 
SEVERITY-DEFAULT: Warning 
EVENTTYPE-DEFAULT: 10 
ADDITIONAL-TEXT-VARIABLES: { accTrapLogSeqNum,accRadiusTrapMsg }
PCAUSE-DEFAULT: 7 " 
 
        ::= 8  
        accRadiusEvntAttribTrap TRAP-TYPE
        ENTERPRISE   accRadiusTraps 
        VARIABLES  { accRadiusTrapMsg,
                     accRadiusAuthConfigErrs ,
                      accTrapLogSeqNum}
        DESCRIPTION
		"Indicates that the kind of session is not valid.
SEVERITY-DEFAULT: Warning 
EVENTTYPE-DEFAULT: 10 
ADDITIONAL-TEXT-VARIABLES: { accTrapLogSeqNum,accRadiusTrapMsg }
PCAUSE-DEFAULT: 7 " 
 
        ::= 9  
        accRadiusRedundantReqTrap TRAP-TYPE
        ENTERPRISE   accRadiusTraps 
        VARIABLES  { accRadiusTrapMsg,
                     accRadiusAuthLastUser ,
                      accTrapLogSeqNum}
        DESCRIPTION
		"Indicates that the request is duplicate open-request; 
		and the session is already open.
SEVERITY-DEFAULT: Warning 
EVENTTYPE-DEFAULT: 10 
ADDITIONAL-TEXT-VARIABLES: { accTrapLogSeqNum,accRadiusTrapMsg }
PCAUSE-DEFAULT: 5 " 
 
        ::= 10  
        accRadiusBindApTrap TRAP-TYPE
        ENTERPRISE   accRadiusTraps 
        VARIABLES  { accRadiusTrapMsg,
                     accRadiusAuthLastUser ,
                      accTrapLogSeqNum}
        DESCRIPTION
		"Indicates that cant bind to access partition which has 
		been configured from the service profile of the user. 
		The service type is no longer checked and any service 
		profile with a configured access partition will cause 
		RADIUS to bind to the access partition; the trap 
		indicates that it may not be a physical port. 
SEVERITY-DEFAULT: Minor 
EVENTTYPE-DEFAULT: 2 
ADDITIONAL-TEXT-VARIABLES: { accTrapLogSeqNum,accRadiusTrapMsg }
PCAUSE-DEFAULT: 56 " 
 
        ::= 11  
        accRadiusAllocUsrSessionBlkTrap TRAP-TYPE
        ENTERPRISE   accRadiusTraps 
        VARIABLES  { accRadiusTrapMsg,
                     accRadiusAuthLastUser ,
                      accTrapLogSeqNum}
        DESCRIPTION
		"cannot allocate user session block due to 
		 memory shortage.
SEVERITY-DEFAULT: Major 
EVENTTYPE-DEFAULT: 10 
ADDITIONAL-TEXT-VARIABLES: { accTrapLogSeqNum,accRadiusTrapMsg }
PCAUSE-DEFAULT: 32 " 
 
        ::= 12
        accRadiusPktUnknwnServTrap TRAP-TYPE
        ENTERPRISE   accRadiusTraps 
        VARIABLES  { accRadiusTrapMsg ,
                      accTrapLogSeqNum}
        DESCRIPTION
                "Packet from unknown server - Addr %s, Port %d 
SEVERITY-DEFAULT: Warning 
EVENTTYPE-DEFAULT: 2 
ADDITIONAL-TEXT-VARIABLES: { accTrapLogSeqNum,accRadiusTrapMsg }
PCAUSE-DEFAULT: 5 " 
 
        ::= 13
        accRadiusUDPBindFaildTrap TRAP-TYPE
        ENTERPRISE   accRadiusTraps 
        VARIABLES  { accRadiusTrapMsg ,
                      accTrapLogSeqNum}
        DESCRIPTION
                "UDP bind failed on port %u 
SEVERITY-DEFAULT: Minor 
EVENTTYPE-DEFAULT: 2 
ADDITIONAL-TEXT-VARIABLES: { accTrapLogSeqNum,accRadiusTrapMsg }
PCAUSE-DEFAULT: 46 " 
 
        ::= 14
        accRadiusAccPartnBindTrap TRAP-TYPE
        ENTERPRISE   accRadiusTraps 
        VARIABLES  { accRadiusTrapMsg ,
                      accTrapLogSeqNum}
        DESCRIPTION
                "Can't bind to access partition 
SEVERITY-DEFAULT: Minor 
EVENTTYPE-DEFAULT: 10 
ADDITIONAL-TEXT-VARIABLES: { accTrapLogSeqNum,accRadiusTrapMsg }
PCAUSE-DEFAULT: 46 " 
 
        ::= 15
        accRadiusInvldLenAttrTrap TRAP-TYPE
        ENTERPRISE   accRadiusTraps 
        VARIABLES  { accRadiusTrapMsg ,
                      accTrapLogSeqNum}
        DESCRIPTION
                "Invalid length in access-accept attribute 
SEVERITY-DEFAULT: Minor 
EVENTTYPE-DEFAULT: 10 
ADDITIONAL-TEXT-VARIABLES: { accTrapLogSeqNum,accRadiusTrapMsg }
PCAUSE-DEFAULT: 253 " 
 
        ::= 16
        accRadiusInvldLenHdrTrap TRAP-TYPE
        ENTERPRISE   accRadiusTraps 
        VARIABLES  { accRadiusTrapMsg ,
                      accTrapLogSeqNum}
        DESCRIPTION
                "Invalid length in access-accept header 
SEVERITY-DEFAULT: Minor 
EVENTTYPE-DEFAULT: 10 
ADDITIONAL-TEXT-VARIABLES: { accTrapLogSeqNum,accRadiusTrapMsg }
PCAUSE-DEFAULT: 253 " 
 
        ::= 17
        accRadiusInvldAccChallPaktTrap TRAP-TYPE
        ENTERPRISE   accRadiusTraps 
        VARIABLES  { accRadiusTrapMsg ,
                      accTrapLogSeqNum}
        DESCRIPTION
                "Invalid access-challenge packet received 
SEVERITY-DEFAULT: Warning 
EVENTTYPE-DEFAULT: 2 
ADDITIONAL-TEXT-VARIABLES: { accTrapLogSeqNum,accRadiusTrapMsg }
PCAUSE-DEFAULT: 4 " 
 
        ::= 18
        accRadiusNoChalMsgTrap TRAP-TYPE
        ENTERPRISE   accRadiusTraps 
        VARIABLES  { accRadiusTrapMsg ,
                      accTrapLogSeqNum}
        DESCRIPTION
                "No challenge message in access-challenge packet 
SEVERITY-DEFAULT: Warning 
EVENTTYPE-DEFAULT: 2 
ADDITIONAL-TEXT-VARIABLES: { accTrapLogSeqNum,accRadiusTrapMsg }
PCAUSE-DEFAULT: 5 " 
 
        ::= 19
        accRadiusInvldAuthActResTrap TRAP-TYPE
        ENTERPRISE   accRadiusTraps 
        VARIABLES  { accRadiusTrapMsg ,
                      accTrapLogSeqNum}
        DESCRIPTION
                "Invalid authenticator in account-response 
SEVERITY-DEFAULT: Warning 
EVENTTYPE-DEFAULT: 2 
ADDITIONAL-TEXT-VARIABLES: { accTrapLogSeqNum,accRadiusTrapMsg }
PCAUSE-DEFAULT: 4 " 
 
        ::= 20
        accRadiusInvldAuthAccResTrap TRAP-TYPE
        ENTERPRISE   accRadiusTraps 
        VARIABLES  { accRadiusTrapMsg ,
                      accTrapLogSeqNum}
        DESCRIPTION
                "Invalid authenticator in access-response 
SEVERITY-DEFAULT: Warning 
EVENTTYPE-DEFAULT: 2 
ADDITIONAL-TEXT-VARIABLES: { accTrapLogSeqNum,accRadiusTrapMsg }
PCAUSE-DEFAULT: 4 " 
 
        ::= 21
END
