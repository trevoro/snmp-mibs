-- INTEL CONFIDENTIAL
-- Copyright 2006, 2007
-- Intel Corporation All Rights Reserved.
--
-- The source code contained or described herein and all documents related to
-- the source code ("Material") are owned by Intel Corporation or its
-- suppliers and licensors. Title to the Material remains with Intel
-- Corporation or its suppliers and licensors. The Material contains trade
-- secrets and proprietary and confidential information of Intel or its
-- suppliers and licensors. The Material is protected by worldwide copyright
-- and trade secret laws and treaty provisions. No part of the Material may be
-- used, copied, reproduced, modified, published, uploaded, posted,
-- transmitted, distributed, or disclosed in any way without Intel's prior
-- express written permission.
--
-- Unless otherwise expressly permitted by Intel in a separate license
-- agreement, use of the Material is subject to the copyright notices,
-- trademarks, warranty, use, and disclosure restrictions reflected on the
-- outside of the media, in the documents themselves, and in the "About" or
-- "Read Me" or similar file contained within this source code. Unless
-- otherwise expressly agreed by Intel in writing, you may not remove
-- or alter such notices in any way.
--

    INTELCORPORATION-MULTI-FLEX-SERVER-REG DEFINITIONS ::= BEGIN

        IMPORTS
	OBJECT-TYPE FROM RFC1155-SMI
            enterprises, MODULE-IDENTITY, OBJECT-IDENTITY, Integer32
                FROM SNMPv2-SMI

            DisplayString
                FROM SNMPv2-TC

            OBJECT-GROUP
                FROM SNMPv2-CONF;


            multiFlexServerRegModule MODULE-IDENTITY
                LAST-UPDATED "200710011820Z"        -- October 01, 2007 at 18:20 GMT
                ORGANIZATION
                    "Intel Corporation"
                CONTACT-INFO
                    "Brian Kurle
                    Intel Corporation
                    JF5-2-C3
                    Tel: 503-712-5032
                    E-Mail: brianx.j.kurle@intel.com"
                DESCRIPTION
                    "Registry module definitions for entire Multi-Flex
                    Server MIB system"
                REVISION "200710011820Z"        -- October 01, 2007 at 18:20 GMT
                DESCRIPTION
                    "Removed remaining references to OEMs"
                REVISION "200708211700Z"        -- August 21, 2007 at 17:00 GMT
                DESCRIPTION
                    "Renamed eventPolicyId to eventId"
                REVISION "200708161330Z"        -- August 16, 2007 at 13:30 GMT
                DESCRIPTION
                    "Reordered Revision to reverse chronological as some
                    browsers choke, cleaned up some other simple nit-picky
                    errors

                    Added eventPolicyId to the notification group"
                REVISION "200705301030Z"        -- May 30, 2007 at 10:30 GMT
                DESCRIPTION
                    "Moved components to { multiFlexServer 2 }
                    Added notificationInfo for bogus nodes used in event
                    notification"
                REVISION "200703061030Z"        -- March 06, 2007 at 10:30 GMT
                DESCRIPTION
                    "Dumped several nodes that really aren't relevant or
                    going to be used:
                        generic
                        profiles
                        requirements
                        (experiments has been moved)
                        conformance
                        compliance"
                REVISION "200702221700Z"        -- February 22, 2007 at 17:00 GMT
                DESCRIPTION
                    "Renamed MIB file and updated internal relevance to
                    formal product name Multi-Flex Server"
                REVISION "200611291530Z"        -- November 29, 2006 at 15:30 GMT
                DESCRIPTION
                    "Added regChassis & regControllers.   Renumbered
                    registry to put less likely 3rd party supplied
                    components toward the end.

                    Added three known new components to registry
                    (multiFlexServer1, esm1 and scm1 which should be
                    renamed later)."
                REVISION "200611011000Z"        -- November 01, 2006 at 10:00 GMT
                DESCRIPTION
                    "Made several changes:
                    old 'chassis' is now 'modularsystems'
                    removed 'typeOfchassis' (thus entire tree moved up)"
                REVISION "200610021200Z"        -- October 02, 2006 at 12:00 GMT
                DESCRIPTION
                    "Moved mib, conformance, groups, & compliance definitions here.
                    Heavily cleaned up module definitions."
                REVISION "200609281732Z"        -- September 28, 2006 at 17:32 GMT
                DESCRIPTION
                    "Removed code-name references and 'global prefixing.'
                    Changed smb to typeOfChassis."
                ::= { regModule 1 }

--
-- Node definitions
--

--
-- Path to our product
--
        intel               OBJECT IDENTIFIER ::= { enterprises 343 }
        products            OBJECT IDENTIFIER ::= { intel 2 }
        modularsystems      OBJECT IDENTIFIER ::= { products 19 }
        multiFlexServer     OBJECT IDENTIFIER ::= { modularsystems 1 }

--
-- Top level of nodes for our product.
--
        notifications OBJECT-IDENTITY
            STATUS current
            DESCRIPTION
                "All the Multi-Flex Server notifications will reside
                under this branch as specified in RFC2578 'Structure of
                Management Information Version 2 (SMIv2)' 8.5"
                                              ::= { multiFlexServer 0 } -- SNMPv1 compatible location of traps

        registry            OBJECT IDENTIFIER ::= { multiFlexServer 1 } -- Registry of modules and 3rd party components
        components          OBJECT IDENTIFIER ::= { multiFlexServer 2 } -- Definition of all components within (and including) the chassis.
        notificationInfo    OBJECT IDENTIFIER ::= { multiFlexServer 3 } -- Bogus nodes solely used for reference within NOTIFICATION-TYPEs


        regModule           OBJECT IDENTIFIER ::= { registry 1 } -- Where all MODULE-IDENTITY definitions are assigned
        regComponents       OBJECT IDENTIFIER ::= { registry 2 } -- OBJECT definitions of 3rd party components


-- Although the MIB will generically provide information, the type will point
-- back to an OID to reflect specifically determine the type of blade.
-- Those OIDs are contained in the following sub-tree.   They are not
-- management types, but merely tokens to the type.

        regChassis          OBJECT IDENTIFIER ::= { regComponents 1 } -- Our chassis types
        regSwitches         OBJECT IDENTIFIER ::= { regComponents 2 } -- 3rd party switch definitions
        regScms             OBJECT IDENTIFIER ::= { regComponents 3 } -- 3rd party storage controller definitions
        regBlades           OBJECT IDENTIFIER ::= { regComponents 4 } -- 3rd party blades definitions
        regPowerSupplies    OBJECT IDENTIFIER ::= { regComponents 5 }
        regFans             OBJECT IDENTIFIER ::= { regComponents 6 }

--
-- Chassis types
--
        multiFlexServer1 OBJECT-IDENTITY
            STATUS current
            DESCRIPTION
                "Multi-Flex Server rev1 chassis."
                                              ::= { regChassis 1 }


--
-- Switches we know about (so far)
--
        esm1 OBJECT-IDENTITY
            STATUS current
            DESCRIPTION
                "Switch"
                                              ::= { regSwitches 1 }


--
-- Scms we know about (so far)
--
        scm1 OBJECT-IDENTITY
            STATUS current
            DESCRIPTION
                "Storage Controller"
        ::= { regScms 1 }


--      root for items in Multi-Flex Server MIB module
        mib OBJECT IDENTIFIER ::= { components 2 }

--
-- MIB
-- SMIv2 definitions
--
--        conformance         OBJECT IDENTIFIER ::= { mib 1 }
        groups              OBJECT IDENTIFIER ::= { mib 2 } -- SMIv2 group definitions
--        compliance          OBJECT IDENTIFIER ::= { mib 3 }

--
-- Bogus notification nodes :(
--

        component OBJECT-TYPE
            SYNTAX DisplayString
            MAX-ACCESS read-only
            STATUS current
            DESCRIPTION
                "Name of device reporting the event"
            ::= { notificationInfo 1 }

        severity OBJECT-TYPE
            SYNTAX INTEGER {
                
                unknown(0),
                neutral(1),
                good(2),
                info(3),
                warning(4),
                critical(5)

            }
            MAX-ACCESS read-only
            STATUS current
            DESCRIPTION
                "Severity of the event being reported"
            ::= { notificationInfo 2 }
        
        eventType OBJECT-TYPE
            SYNTAX DisplayString
            MAX-ACCESS read-only
            STATUS current
            DESCRIPTION
                " ... "
            ::= { notificationInfo 3 }

        user OBJECT-TYPE
            SYNTAX DisplayString
            MAX-ACCESS read-only
            STATUS current
            DESCRIPTION
                " ... "
            ::= { notificationInfo 4 }

        instanceId OBJECT-TYPE
            SYNTAX DisplayString
            MAX-ACCESS read-only
            STATUS current
            DESCRIPTION
                " ... "
            ::= { notificationInfo 5 }

        detail OBJECT-TYPE
            SYNTAX DisplayString
            MAX-ACCESS read-only
            STATUS current
            DESCRIPTION
                " ... "
            ::= { notificationInfo 6 }

        eventId OBJECT-TYPE
            SYNTAX Integer32
            MAX-ACCESS read-only
            STATUS current
            DESCRIPTION
                " ... "
            ::= { notificationInfo 7 }

        chassisGroup OBJECT-GROUP
            OBJECTS {

                component,
                severity,
                eventType,
                user,
                instanceId,
                detail,
                eventId

            }
            STATUS current
            DESCRIPTION
                "Bogus Nodes (not really readable) for event notification"
            ::= { groups 1 }

    END
--  vim:ts=4:ai:nohls:nowrap:expandtab
