--	Quantum Bridge VT/VC Management Information Base
--	Version 1.0.0
--	July 7, 2000
--
--	Quantum Bridge Corporation
--	One High Street
--	North Andover, MA 01845
--	(978) 688-9100
--
----------------------------------------------------------------------------------------
--  12/13/2000   Made qbVTConfVTId(index) not-accessible object
--
--  10/31/2000  - Added loopback objects
--
--  10/14/2000 - Improved qbVTVCConnTable and
--		 qbVTVCCrossConnTable. Added new objects.
--
--  09/08/2000 - Added loopback objects
--
--  08/01/2000 - Merged VT and VC tables
--
--  07/29/2000 - Fixed some     typo
--
--  07/13/2000 - mvaysman    	Added VC tables
--				
--  07/06/2000 - mvaysman    	Original version
--
----------------------------------------------------------------------------------------
--
	QB-VT15-MIB DEFINITIONS ::= BEGIN
	IMPORTS 
    	NOTIFICATION-TYPE, MODULE-IDENTITY, OBJECT-TYPE, Gauge32, Counter32, Unsigned32, Integer32, TimeTicks
        	FROM SNMPv2-SMI
    	TEXTUAL-CONVENTION, TruthValue, TimeStamp, RowStatus, DisplayString
        	FROM SNMPv2-TC
    	MODULE-COMPLIANCE, OBJECT-GROUP
        	FROM SNMPv2-CONF
    	InterfaceIndex, InterfaceIndexOrZero, ifIndex
	    	FROM IF-MIB
    	qbMibs
        	FROM QUANTUMBRIDGE-REG
        AtmAddr, AtmConnKind, AtmConnCastType,
        AtmServiceCategory, AtmTrafficDescrParamIndex,
        AtmVpIdentifier, AtmVcIdentifier,
        AtmVorXAdminStatus, AtmVorXLastChange,
        AtmVorXOperStatus, atmNoClpNoScr
            FROM ATM-TC-MIB
	QbEnableStatus,QbPvcConnKind
		FROM QB-DWS-MIB
    	;

	qbVTVCMIB MODULE-IDENTITY
    	LAST-UPDATED "0012131255Z" -- December 13, 2000
    	ORGANIZATION "Quantum Bridge Communications, Inc."
    	CONTACT-INFO
        	"support@quantumbridge.com"
    	DESCRIPTION
        	"This module defines additional objects for the provisioning of
		VT1.5/VC12 links in Quantum Bridge devices."
    	::= { qbMibs 9 }

	-- Top-level organization of the MIB

	qbVTVCTables	    OBJECT IDENTIFIER ::=  { qbVTVCMIB 1 }
	qbVTVCNotifications  OBJECT IDENTIFIER ::= { qbVTVCMIB 2 }
	qbVTVCConformance    OBJECT IDENTIFIER ::= { qbVTVCMIB 3 }

	--
	-- Structure of MIB
	-- Quantum Bridge DWS Type Textual Convention
	--   

	QbVT15Sts1 ::= TEXTUAL-CONVENTION
	    STATUS          current
    		DESCRIPTION
		"The STS-1 number."
		SYNTAX          Unsigned32 (1..3)

	QbVT15VTGroup ::= TEXTUAL-CONVENTION
	    STATUS          current
    		DESCRIPTION
        		"The VT1.5 group number."
    		SYNTAX          Unsigned32 (1..7)

       QbVT15VTGroupId ::= TEXTUAL-CONVENTION
	    STATUS          current
    		DESCRIPTION
        		"The VT1.5 group number."
    		SYNTAX          Unsigned32 (1..4)


	QbVT15VTId ::= TEXTUAL-CONVENTION
	    STATUS          current
    		DESCRIPTION
        		"The VT Identifier number. The qbVT15VTId
			 is determined by using the following formula:
			 (sts-1) * 28 + (vtgrp-1) * 4 +  vtnum. 	       
			 sts-sonet path, vtgrp - sonet path group, 
			 vt - VT number."
    		SYNTAX          Unsigned32 (1..84)

	QbVC12Id ::= TEXTUAL-CONVENTION
	    STATUS          current
    		DESCRIPTION
        		"The VC Identifier number."
    		SYNTAX          Unsigned32 (1..63)

  -- **************************************************************************
  -- The configuration table that provisions VT connections at VT1.5
  -- Sonet signalling(STS-3) interfaces 
  -- ***************************************************************************

    qbVTVCConnTable	OBJECT-TYPE
        SYNTAX      SEQUENCE OF QbVTVCConnEntry
        MAX-ACCESS  not-accessible
        STATUS      current
        DESCRIPTION
            "The Quantum Bridge VT connection table contains a list of
	    VT1.5 connections that are provisioned at OAS SONET(STS-3)
	    and SDH(STM-1) interfaces between IOT(DS1/E1) ports and VTs/VCs,
	    ATM PVCs and VTs/VCs, VTs/VCs and VTs/VCs ports. The STS-3 interfaces 
	    are listed in the sonetMediumTable(RFC2558) as interfaces with the 'sonetMediumType'
	    object set to sonet(1) value. The STM-1 interfaces are listed in the
	    sonetMediumTable(RFC2558) as interfaces with the 'sonetMediumType'
	    object set to sdh(1). 
	    The table has 2 indexes of the first end-point: Sonet interface
	    index, vt/vc identifier.  	 	
	    Note: All connections between ATM ports and VTs/VCs are listed
	    in the atmVclTable."
    ::= { qbVTVCTables 1 }

    qbVTVCConnEntry OBJECT-TYPE
       SYNTAX      QbVTVCConnEntry
       MAX-ACCESS  not-accessible
       STATUS      current
       DESCRIPTION
            "An entry in the Quantum Bridge qbVTVCConnTable table."
       INDEX    { qbVTVCIfIndex, qbVTVCConnId }
       ::= { qbVTVCConnTable 1 }

    QbVTVCConnEntry ::=
       SEQUENCE {
		qbVTVCIfIndex		  InterfaceIndex,
		qbVTVCConnId		  INTEGER,
		qbVTVCConnIotAtmIfIndex	  InterfaceIndexOrZero,
		qbVTVCConnName            DisplayString,
		qbVTVCConnAdminStatus	  AtmVorXAdminStatus,
		qbVTVCConnOperStatus	  AtmVorXOperStatus,
		qbVTVCConnLastChange      AtmVorXLastChange,
		qbVTVCConnAtmVpi	  AtmVpIdentifier,
		qbVTVCConnAtmVci	  AtmVcIdentifier,
		qbVTVCConnKind	          QbPvcConnKind,
		qbVTVCCrossConnId	  INTEGER,
		qbVTVCConnRowStatus 	  RowStatus,
		qbVTVCConnLoopback        QbEnableStatus,
		qbVTVCConnLoopbackEndpt	  INTEGER
     }
   
     qbVTVCIfIndex  OBJECT-TYPE
	SYNTAX   InterfaceIndex 
        MAX-ACCESS  not-accessible
        STATUS	current
        DESCRIPTION
                 "The STS-3/SDH-1 signal interface." 
        ::= { qbVTVCConnEntry 1 }

    qbVTVCConnId OBJECT-TYPE
        SYNTAX      INTEGER (1..84)  
	MAX-ACCESS  not-accessible
	STATUS      current
	DESCRIPTION
		"The identifier of the specified VT (virtual tributary)
		or VC signal. The VT identifier is determined by using the
		following formula: (sts-1) * 28 + (vtgrp-1) * 4 +
		vtnum. sts-sonet path, vtgrp - sonet path group, vt
		- VT number.The VC identifier has ranges from 1 to 63."
	::= { qbVTVCConnEntry 2 }

    qbVTVCConnIotAtmIfIndex  OBJECT-TYPE
	SYNTAX   InterfaceIndexOrZero 
        MAX-ACCESS  read-create
        STATUS	current
        DESCRIPTION
                 "An IOT interface index of the atm layer interface
		 or DS1/E1 interface of the connection 
		 between  an ATM/IOT and a VT1.5/VC12 or VT1.5/VC12
		 and VT1.5/VC12. The connection type is indicated by
		 the qbVTVCConnKind object. If this object is set to
		 vt15ToAtm or vt15ToAtm the ATM layer interface is
		 specified. When the iotE1ToVt15, iotDs1ToVt15,iotE1ToVc12,
		 iotDs1ToVc12 values are set the IOT DS1/E1 interface
		 is specified. For a VT to VT connection this object
		 isn't needed."
        ::= { qbVTVCConnEntry 3 }

    qbVTVCConnName OBJECT-TYPE
        SYNTAX      DisplayString (SIZE(1..20))  
	MAX-ACCESS  read-create
	STATUS      current
	DESCRIPTION
		"The textual name of the VT1.5/VC12 connection as specified by
		a user. It provides a non-volatile handle for this
		PVC.The supplied name in the qbVTVCConnName is associated
                with the same connection for as long as that connection remains."
	::= { qbVTVCConnEntry 4 }

   qbVTVCConnAdminStatus OBJECT-TYPE
        SYNTAX      AtmVorXAdminStatus  
	MAX-ACCESS  read-create
	STATUS      current
	DESCRIPTION
		 "The desired administrative status of the connection
		 The up and down states indicate that the traffic
		 flow is enabled or disabled respectively across the
		 specified connection."
	::= { qbVTVCConnEntry 5 }

   qbVTVCConnOperStatus OBJECT-TYPE
        SYNTAX      AtmVorXOperStatus  
	MAX-ACCESS  read-only
	STATUS      current
	DESCRIPTION
		 "The current operational status of the connection."
	::= { qbVTVCConnEntry 6 }

  qbVTVCConnLastChange OBJECT-TYPE
        SYNTAX      AtmVorXLastChange  
	MAX-ACCESS  read-only
	STATUS      current
	DESCRIPTION
		"The value of sysUpTime at the time this connection
		entered its current operational state."
	::= { qbVTVCConnEntry 7 }
   
   qbVTVCConnAtmVpi  OBJECT-TYPE
    SYNTAX        AtmVpIdentifier
    MAX-ACCESS    read-create
    STATUS        current
    DESCRIPTION
        "The value of this object is equal to the VPI used
         by the ATM VCL mapped through this connection to a VT.
	 The value is irrelevant for a non-ATM  connection.
	 (i.e., qbVTVCConnKind isn't set vt15ToAtm or 
	 vc12ToAtm value)."
    ::= { qbVTVCConnEntry 8 }

  qbVTVCConnAtmVci   OBJECT-TYPE
    SYNTAX        AtmVcIdentifier
    MAX-ACCESS    read-create
    STATUS        current
    DESCRIPTION
	 "The value of this object is equal to the VCI used
         by the ATM VCL mapped through this connection to a VT.
	 The value is irrelevant if a non-ATM connection.
         (i.e., qbVTVCConnKind isn't set to vt15ToAtm or 
	 vc12ToAtm value)."
    ::= { qbVTVCConnEntry 9 }

 qbVTVCConnKind   OBJECT-TYPE
    SYNTAX        QbPvcConnKind 
    MAX-ACCESS    read-create
    STATUS        current
    DESCRIPTION
	 "The VT connection type. Two types of connection can be
	 provisioned on the VT/sonet port (IOT-VT and VT-ATM)"
    DEFVAL   { iotDs1ToVt15 }
    ::= { qbVTVCConnEntry 10 }

  qbVTVCCrossConnId OBJECT-TYPE
    SYNTAX        INTEGER (0..2147483647)
    MAX-ACCESS    read-only
    STATUS        current
    DESCRIPTION
	 "This object is instantiated only for a VT/VC 
          which is cross-connected to another VT/VC. Two entries
	  that have the same value belong to a single entry of 
	  qbVTVCCrossConnTable. The corresponding entry in qbVTVCCrossConnTable
	  can be found by sending getnext with qbVTVCIfIndex
	  qbVTVCConnId instances. The value is irrelevant for
	  a non-VTtpVT connection (i.e., qbVTVCConnKind isn't set to vt15Vt15
	  or  vt12Vt12 value)."
    ::= { qbVTVCConnEntry 11 }
   
   qbVTVCConnRowStatus OBJECT-TYPE
        SYNTAX      RowStatus  
	MAX-ACCESS  read-create
	STATUS      current
	DESCRIPTION
            "The status column for this IOT ENET interface.
	    This OBJECT can be set to:

		createAndGo(4)
            	destroy(6)

            The following values may be read:
            	active(1)

			This object may only be set to createAndGo(4).

			Setting this object to active(1) when its value
			is already active(1) is a no-op.
			
			Setting this object to createAndGo(4) causes the agent
			to attempt to create and commit a row based on
			the contents of the objects in the row.  If all necessary
			information is present in the row and the values are
			acceptable to the agent, the agent will change the
			status to active(1).  If any of the necessary objects
			are not available, the agent will reject the creation
			request."	
	::= { qbVTVCConnEntry 12 }

    qbVTVCConnLoopback OBJECT-TYPE
	SYNTAX      QbEnableStatus
	MAX-ACCESS  read-create
	STATUS      current
	DESCRIPTION
		"Activate a connection loopback for a PVC that has an
		endpoint on this VT.  
		This object, when read, returns one of the
		following results:
		enable(1):     Loopback is enabled on this VT
		disable(2):    Loopback is disbaled on this VT

		Setting this object to one of the acceptable values
		causes the following results depending on the
		qbVTVCConnLoopbackEndpt value:
		enable(1):     Enable loopback on this VT trib when
			       qbVTVCConnLoopbackEndpt is set to
			       'vtLoopback'. Enable loopback on IOT or
			       ATM port when qbVTVCConnLoopbackEndpt is set to  
			       nonVtloopback'. For VT to VT connection 
			       this object activates loopback on this VT.
		disable(2):    Disbale activated loopback. The
			       disabled endpoint is selected depending 
			       of the  qbVTVCConnLoopbackEndpt"			       
	DEFVAL  { disable }
    ::= { qbVTVCConnEntry   13 }

   qbVTVCConnLoopbackEndpt  OBJECT-TYPE
	SYNTAX      INTEGER {
		    vtLoopback(1),
		    nonVtLoopback(2)
	}
	MAX-ACCESS  read-create
	STATUS      current
	DESCRIPTION
		"Define an endpoint on which loopback is activated or
		disabled. The object works in conjunction with the qbVTVCConnLoopback."
	DEFVAL  { vtLoopback }
    ::= { qbVTVCConnEntry   14 }


  -- ***************************************************************************
  -- The configuration table that provisions VT/VC point-to-point cross-connections
  -- between two VT/VC endpoints of Sonet(STS-3), SDH(STS-1) interfaces  
  -- ***************************************************************************

    qbVTVCCrossConnTable	OBJECT-TYPE
        SYNTAX      SEQUENCE OF QbVTVCCrossConnEntry
        MAX-ACCESS  not-accessible
        STATUS      current
        DESCRIPTION
            "The Quantum Bridge VT cross-connection (VT to VT) table contains all 
             point-to-point cross-connections between various VTs that are provisoned
	     at OAS STS-3 Sonet interfaces.
	     The STS-3 interfaces are listed in the
	     sonetMediumTable(RFC2558) as interfaces with the 'sonetMediumType'
	     object set to sonet(1). The table is indexed by four
	     indexes: low interface interface index,low
	     vt identifiers, high interface index, and high vt
	     identifier. The terms low and high are chosen to
	     represent numerical ordering of two interfaces/vt within
	     VT cross-connect."
    ::= { qbVTVCTables 2 }

    qbVTVCCrossConnEntry        OBJECT-TYPE
       SYNTAX      QbVTVCCrossConnEntry
       MAX-ACCESS  not-accessible
       STATUS      current
       DESCRIPTION
            "An entry in the Quantum Bridge QbVTVCCrossConnTable."
       INDEX    { qbVTVCCrossConnIfIndexEndpt1, qbVTVCCrossConnVTIdEndpt1, 
		qbVTVCCrossConnIfIndexEndpt2, qbVTVCCrossConnVTIdEndpt2} 
       ::= { qbVTVCCrossConnTable 1 }

    QbVTVCCrossConnEntry ::=
       SEQUENCE {
		qbVTVCCrossConnIfIndexEndpt1    InterfaceIndex,
		qbVTVCCrossConnVTIdEndpt1	INTEGER,
		qbVTVCCrossConnIfIndexEndpt2    InterfaceIndex,	
		qbVTVCCrossConnVTIdEndpt2	INTEGER,
		qbVTVCCrossConnIndex		INTEGER,
		qbVTVCCrossConnName		DisplayString,
		qbVTVCCrossConnAdminStatus	AtmVorXAdminStatus,
		qbVTVCCrossConnOperStatus	AtmVorXOperStatus,
		qbVTVCCrossConnKind		QbPvcConnKind,	
		qbVTVCCrossConnRowStatus	RowStatus
     }
     
     qbVTVCCrossConnIfIndexEndpt1  OBJECT-TYPE
	SYNTAX   InterfaceIndex 
        MAX-ACCESS  not-accessible
        STATUS	current
        DESCRIPTION
                 "The STS-3/SDH-1 Sonet low interface index of the specified cross-connection." 
        ::= { qbVTVCCrossConnEntry 1 }

    qbVTVCCrossConnVTIdEndpt1 OBJECT-TYPE
        SYNTAX      INTEGER (1..84)  
	MAX-ACCESS  not-accessible
	STATUS      current
	DESCRIPTION
		"The low VT/VC identifier of the specified VT/VC group of the
		first cross-connect endpoint."
	::= { qbVTVCCrossConnEntry 2 }

    qbVTVCCrossConnIfIndexEndpt2  OBJECT-TYPE
	SYNTAX   InterfaceIndex 
        MAX-ACCESS  not-accessible
        STATUS	current
        DESCRIPTION
                 "The high STS-3 Sonet interface of the specified
		 cross-connection of the second cross-connect endpoint." 
        ::= { qbVTVCCrossConnEntry 3 }

    qbVTVCCrossConnVTIdEndpt2 OBJECT-TYPE
        SYNTAX      INTEGER (1..84)  
	MAX-ACCESS  not-accessible
	STATUS      current
	DESCRIPTION
		"The high VT/VC identifier of the specified VT group of the
		second cross-connect endpoint."
	::= { qbVTVCCrossConnEntry 4 }

   qbVTVCCrossConnIndex OBJECT-TYPE
        SYNTAX         INTEGER (1..2147483647)  
	MAX-ACCESS  read-create
	STATUS      current
	DESCRIPTION
		"A unique value to identify this VT to VT cross-connect.
		For each qbVTVCConnEntry associated with this cross-connect,  
		the agent reports this cross-connect index value
		in the qbVTVCCrossConnId attribute of
		the corresponding qbVTVCConnTable entries."
	::= { qbVTVCCrossConnEntry 5 }

    qbVTVCCrossConnName OBJECT-TYPE
        SYNTAX      DisplayString (SIZE(1..20))  
	MAX-ACCESS  read-create
	STATUS      current
	DESCRIPTION
		"The textual name of the VT1.5 cross-connection as specified by
		a user. It provides a non-volatile handle for this
		cross-connection. The supplied name in the qbVTVCCrossName is associated
                with the same cross-connection for as long as that cross-conection remains."
	::= { qbVTVCCrossConnEntry 6 }

   qbVTVCCrossConnAdminStatus OBJECT-TYPE
        SYNTAX      AtmVorXAdminStatus  
	MAX-ACCESS  read-create
	STATUS      current
	DESCRIPTION
		 "The desired administrative status of the specified cross-connection.
		 The up and down states indicate that the traffic
		 flow is enabled or disabled across this cross-connection."
	::= { qbVTVCCrossConnEntry 7 }  

   qbVTVCCrossConnOperStatus OBJECT-TYPE
        SYNTAX      AtmVorXOperStatus  
	MAX-ACCESS  read-only
	STATUS      current
	DESCRIPTION
		 "The current operational status of the connection."
	::= { qbVTVCCrossConnEntry 8 }

   qbVTVCCrossConnKind   OBJECT-TYPE
    SYNTAX        QbPvcConnKind 
    MAX-ACCESS    read-create
    STATUS        current
    DESCRIPTION
	 "The VT connection type. Two types of connection can be
	 provisioned on the VT-VT and VC-VC."
    DEFVAL   {vt15Vt15 }
    ::= {  qbVTVCCrossConnEntry 9 }
   
    qbVTVCCrossConnRowStatus OBJECT-TYPE
        SYNTAX      RowStatus  
	MAX-ACCESS  read-create
	STATUS      current
	DESCRIPTION
            "The status column for this IOT ENET interface.
	    This OBJECT can be set to:

		createAndGo(4)
            	destroy(6)

            The following values may be read:
            	active(1)

			This object may only be set to createAndGo(4).

			Setting this object to active(1) when its value
			is already active(1) is a no-op.
			
			Setting this object to createAndGo(4) causes the agent
			to attempt to create and commit a row based on
			the contents of the objects in the row.  If all necessary
			information is present in the row and the values are
			acceptable to the agent, the agent will change the
			status to active(1).  If any of the necessary objects
			are not available, the agent will reject the creation
			request.	

			Setting this object to destroy(6) will remove the corresponding
			entry in this table, and disable data traffic."
	::= { qbVTVCCrossConnEntry 10 }

  -- ***************************************************************************
  -- The configuration table to provision individual virtual tributaries 
  -- ***************************************************************************
    qbVTConfTable	OBJECT-TYPE
        SYNTAX      SEQUENCE OF QbVTConfEntry
        MAX-ACCESS  not-accessible
        STATUS      current
        DESCRIPTION
            "The Quantum Bridge VT configuration table contains
	    configuration parameters of tributaries at OAS VT155 
	    interfaces.
	    The STS-3 interfaces of D155VT cards that are listed in the
	    sonetMediumTable(RFC2558) as interfaces with the 'sonetMediumType'
	    object set to sonet(1). The table has two
	    indexes: Sonet interface index, and tributary identifier."
    ::= { qbVTVCTables 3 }

    qbVTConfEntry  OBJECT-TYPE
       SYNTAX      QbVTConfEntry
       MAX-ACCESS  not-accessible
       STATUS      current
       DESCRIPTION
            "An entry in the Quantum Bridge qbVTConfEntry. Every
	    entry containes settings of the tributary"
       INDEX    { qbVTConfIfIndex, qbVTConfVTId }
       ::= { qbVTConfTable 1 }

    QbVTConfEntry  ::=
       SEQUENCE {
		qbVTConfIfIndex    InterfaceIndex,
		qbVTConfVTId 	   QbVT15VTId,
		qbVTConfClockMode  INTEGER,
		qbVTConfAction	   INTEGER
     }
     
     qbVTConfIfIndex  OBJECT-TYPE
	SYNTAX   InterfaceIndex 
        MAX-ACCESS  not-accessible
        STATUS	current
        DESCRIPTION
                 "The STS-3/SDH-1 Sonet interface of the specified tributary." 
        ::= { qbVTConfEntry 1 }
  
     qbVTConfVTId  OBJECT-TYPE
        SYNTAX     QbVT15VTId  
	MAX-ACCESS  not-accessible
	STATUS      current
	DESCRIPTION
		"The identifier of the specified tributary."
	::= { qbVTConfEntry  2 }

    qbVTConfClockMode     OBJECT-TYPE
	SYNTAX        INTEGER {
                      srts(1),
                      adaptive(2)
                      }
	MAX-ACCESS    read-write
	STATUS        current
	DESCRIPTION
		"The object defines whether VT155 service clocking mode used for
		 AAL1 recovery. Applies only to D155VT interfaces that are configured
		for SONET format."
	DEFVAL { adaptive } 
    ::= { qbVTConfEntry  3 }

    qbVTConfAction  OBJECT-TYPE
        SYNTAX    INTEGER {
		  singleVTAction(1),
		  stsVTAction(2),
		  ifVTAction(3),
		  noop(4)
	}  
	MAX-ACCESS read-write
	STATUS      current
	DESCRIPTION
		"Indicates whether the clock mode is set for a single tributary 
		or group of tributaries.
		When set to 'singleVTAction(1)' a single selected
		tributary is set to a desired clock mode.
		When set to 'stsVTAction(2)' all
		tributaries that belongs to qbVTConfVTId's STS  are
		set to a desired clock mode. When set to 'ifVTAction(3)' all  
		qbVTConfIfIndex tributaries are set to a desired
		clock mode. For this mode the value of qbVTConfVTId
		is irrelevant. Thus any valid QbVT15VTId value can be
		used. 
		When the value is set to 'noop', no operation is performed.
		When read, this object always returns the value noop(4)."
	DEFVAL   { singleVTAction }	
      ::= { qbVTConfEntry  4 }

-- ****************************************************************
--  This table contains the VT/VC stats
-- **************************************************************** 

    qbVtVcStatsTable	OBJECT-TYPE
        SYNTAX      SEQUENCE OF QbVtVcStatsEntry
        MAX-ACCESS  not-accessible
        STATUS      current
        DESCRIPTION
            "This table contains the stats for each VT/VC with
            a connection established. One row in this table should
            exist for each VT/VC connection."
    ::= { qbVTVCTables 4 }

    qbVtVcStatsEntry OBJECT-TYPE
       SYNTAX      QbVtVcStatsEntry
       MAX-ACCESS  not-accessible
       STATUS      current
       DESCRIPTION
            "An entry in the Quantum Bridge qbVtVcStatsTable table."
       INDEX    { qbVtVcStatsIfIndex, qbVtVcStatsConnId }
       ::= { qbVtVcStatsTable 1 }

    QbVtVcStatsEntry ::=
       SEQUENCE {
		qbVtVcStatsIfIndex		InterfaceIndex,
		qbVtVcStatsConnId		INTEGER,
		qbVtVcStatsRxCells		Counter32,
		qbVtVcStatsTxCells		Counter32,
		qbVtVcStatsRxDroppedCells	Counter32,
		qbVtVcStatsTxConditionalCells	Counter32,
		qbVtVcStatsTxSuppressedCells	Counter32
     }
   
    qbVtVcStatsIfIndex  OBJECT-TYPE
		SYNTAX   InterfaceIndex 
        MAX-ACCESS  not-accessible
        STATUS	current
        DESCRIPTION
                 "The STS-3/SDH-1 signal interface." 
        ::= { qbVtVcStatsEntry 1 }

   qbVtVcStatsConnId OBJECT-TYPE
        SYNTAX      INTEGER (1..84)  
		MAX-ACCESS  not-accessible
		STATUS      current
		DESCRIPTION
		"The identifier of the specified VT (virtual tributary)
		or VC signal. The VT identifier is determined by using the
		following formula: (sts-1) * 28 + (vtgrp-1) * 4 +
		vtnum. sts-sonet path, vtgrp - sonet path group, vt
		- VT number.The VC identifier has ranges from 1 to 63."
	::= { qbVtVcStatsEntry 2 }

   qbVtVcStatsRxCells  OBJECT-TYPE
		SYNTAX   Counter32 
        MAX-ACCESS  read-only
        STATUS	current
        DESCRIPTION
                 "The number of received cells." 
        ::= { qbVtVcStatsEntry 3 }

   qbVtVcStatsTxCells  OBJECT-TYPE
		SYNTAX   Counter32 
        MAX-ACCESS  read-only
        STATUS	current
        DESCRIPTION
                 "The number of transmitted cells." 
        ::= { qbVtVcStatsEntry 4 }

   qbVtVcStatsRxDroppedCells  OBJECT-TYPE
		SYNTAX   Counter32 
        MAX-ACCESS  read-only
        STATUS	current
        DESCRIPTION
                 "The number of received cells that were dropped." 
        ::= { qbVtVcStatsEntry 5 }

   qbVtVcStatsTxConditionalCells  OBJECT-TYPE
		SYNTAX   Counter32 
        MAX-ACCESS  read-only
        STATUS	current
        DESCRIPTION
                 "The number of transmitted conditional cells." 
        ::= { qbVtVcStatsEntry 6 }	

   qbVtVcStatsTxSuppressedCells  OBJECT-TYPE
		SYNTAX   Counter32 
        MAX-ACCESS  read-only
        STATUS	current
        DESCRIPTION
                 "The number of transmitted supressed cells." 
        ::= { qbVtVcStatsEntry 7 }	

-- ****************************************************************
--  Notifications - defines a group of traps for use by this MIB.
--
-- ****************************************************************

   qbVTVCNotificationPrefix OBJECT IDENTIFIER ::= { qbVTVCNotifications 0 }

   qbVTVCConnOperStatusChange NOTIFICATION-TYPE
	OBJECTS       { qbVTVCConnOperStatus,
		        qbVTVCConnKind }
        STATUS        current
        DESCRIPTION
		 "A notification indicates that a VT15 connection
		 has chaged  the operations status. The
		 notification is originated for every connection
		 which is listed in the qbVTVCConnTable 
		 when its the  qbVTVCConnOperStatus
		 object changed state."
        ::= { qbVTVCNotificationPrefix 1 }

   qbVTVCCrossConnOperStatusChange NOTIFICATION-TYPE
	OBJECTS       { qbVTVCCrossConnOperStatus,
			qbVTVCCrossConnKind}
        STATUS        current
        DESCRIPTION
		 "A notification indicates that a VT15 cross-connection
		 has chaged the operations status. The
		 notification is originated for every connection
		 which is listed in the qbVT15CrossConnTable 
		 when its the  qbVTVCCrossConnOperStatus
		 object changed state."
        ::= { qbVTVCNotificationPrefix 2 }


-- ****************************************************************
-- Conformance Information
-- ****************************************************************

qbVTVCCompliances OBJECT IDENTIFIER ::= { qbVTVCConformance 1 }
qbVTVCGroups      OBJECT IDENTIFIER ::= { qbVTVCConformance 2 }

--
-- Compliance Statements
--

qbVTVCCompliance MODULE-COMPLIANCE
    STATUS      current
    DESCRIPTION
        "The compliance statement for all agents that support this
        MIB. A compliant agent implements all objects defined in this
        MIB."
    MODULE  -- this module
    MANDATORY-GROUPS {
        qbVTVCConnTable,
	qbVTVCCrossConnTable
    }
    ::= { qbVTVCCompliances 1 }

--
-- All Object Groups
--
    qbVTVCConnInfo OBJECT-GROUP
    OBJECTS {
	qbVTVCConnIotAtmIfIndex,
	qbVTVCConnName,
	qbVTVCConnAdminStatus,
	qbVTVCConnOperStatus,
	qbVTVCConnAtmVpi,
	qbVTVCConnAtmVci,
	qbVTVCConnKind,
	qbVTVCConnRowStatus
    }
    STATUS      current
    DESCRIPTION
        "The set of all accessible objects in this MIB."
    ::= { qbVTVCGroups  1 }

   qbVTVCCrossConnInfo OBJECT-GROUP
    OBJECTS {
	qbVTVCCrossConnName,
	qbVTVCCrossConnAdminStatus,
	qbVTVCCrossConnOperStatus,
	qbVTVCCrossConnRowStatus
    }
    STATUS      current
    DESCRIPTION
        "The set of all accessible objects in this MIB."
    ::= { qbVTVCGroups  2 }

END
