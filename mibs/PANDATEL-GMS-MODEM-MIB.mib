PANDATEL-GMS-MODEM-MIB DEFINITIONS ::= BEGIN

 -- This is the private mib group section for the GM-S modems.
 -- Because these modems must be installed in the PANDATEL modem rack
 -- the PANDATEL-MODEM-MIB also applies.

 -- Ver.1.05    Sep.13.1999

        IMPORTS
                enterprises
                        FROM RFC1155-SMI
                DisplayString
                        FROM RFC1213-MIB
                OBJECT-TYPE
                        FROM RFC-1212
                mdmSpecifics, device-id
                        FROM PANDATEL-MODEM-MIB;

-- ********************** THE MDM-GMS SUBTREE ******************************

-- the specific identifier is identical to the modem type integer
-- of the GM-S modem entries in the PANDATEL-MODEM-MIB mdmModemTable.

gms-modem      OBJECT IDENTIFIER ::= { device-id 204 }     -- chassis-mib

gms            OBJECT IDENTIFIER ::= { mdmSpecifics 204 }  -- this subtree

gmsModemTable OBJECT-TYPE
        SYNTAX  SEQUENCE OF GmsTableEntry
        ACCESS  not-accessible
        STATUS  mandatory
        DESCRIPTION
                "The table of all GM-S modems in this housing."
        ::= { gms 1 }

gmsTableEntry OBJECT-TYPE
        SYNTAX  GmsTableEntry
        ACCESS  not-accessible
        STATUS  mandatory
        DESCRIPTION
                "The index of the table."
        INDEX   { mdmRack, mdmModem, mdmPosition }
        ::= { gmsModemTable 1 }

GmsTableEntry ::= SEQUENCE {
        mdmRack
                INTEGER,
        mdmModem
                INTEGER,
        mdmPosition
                INTEGER,
        mdmModemName
                DisplayString,
        mdmDataEquipmentEmulation
                INTEGER,
        mdmModemProperty
                INTEGER,
        mdmHDSLUnit
                INTEGER,
        mdmClockSystem
                INTEGER,
        mdmClockSource
                INTEGER,
        mdmDataRate
                INTEGER
        }

mdmRack OBJECT-TYPE
        SYNTAX  INTEGER
        ACCESS  read-only
        STATUS  mandatory
        DESCRIPTION
                "The index of the rack where the modem is installed."
        ::= { gmsTableEntry 1 }

mdmModem OBJECT-TYPE
        SYNTAX  INTEGER
        ACCESS  read-only
        STATUS  mandatory
        DESCRIPTION
                "This variable displays the slot number where the
                 corresponding modem is installed in the rack."
        ::= { gmsTableEntry 2 }

mdmPosition OBJECT-TYPE
        SYNTAX  INTEGER {
                local       (1),
                remote      (2)
                }
        ACCESS  read-only
        STATUS  mandatory
        DESCRIPTION
                "This variable displays the location of the corresponding
                 modem: 'local' or 'remote'. The modem which is plugged into a
                 managed rack is 'local', the counterpart is 'remote'."
        ::= { gmsTableEntry 3 }

mdmModemName OBJECT-TYPE
        SYNTAX  DisplayString
        ACCESS  read-only
        STATUS  mandatory
        DESCRIPTION
                "A verbal name of this modem."
        ::= { gmsTableEntry 5 }

mdmDataEquipmentEmulation OBJECT-TYPE
        SYNTAX  INTEGER {
                other       (1),
                dte         (2),
                dce         (3),
                unknown     (99)
        }
        ACCESS  read-only
        STATUS  mandatory
        DESCRIPTION
                "Interface mode of the unit: DCE."
        ::= { gmsTableEntry 6 }

mdmModemProperty OBJECT-TYPE
        SYNTAX  INTEGER {
                other           (1),
                e1              (2),
                t1              (3),
                unknown         (99)
        }
        ACCESS  read-only
        STATUS  mandatory
        DESCRIPTION
                "Application type of HDSL link: E1 or T1."
        ::= { gmsTableEntry 7 }

mdmHDSLUnit OBJECT-TYPE
        SYNTAX  INTEGER {
                other       (1),
                ntu         (2),
                ltu         (3)
        }
        ACCESS  read-only
        STATUS  mandatory
        DESCRIPTION
                "HDSL unit type: Line Termination Unit (LTU) or
                 Network Termination Unit (LTU)"
        ::= { gmsTableEntry 10 }

mdmClockSystem OBJECT-TYPE
        SYNTAX  INTEGER {
                other       (1),
                dual        (2),
                single      (3)
        }
        ACCESS  read-write
        STATUS  mandatory
        DESCRIPTION
                "The clock system at the interface: 'single' or 'dual'."
        ::= { gmsTableEntry 23 }

mdmClockSource OBJECT-TYPE
        SYNTAX  INTEGER {
                other       (1),
                internal    (2),
                remote      (3),
                external    (4)
        }
        ACCESS  read-write
        STATUS  mandatory
        DESCRIPTION
                "The clock source at the interface: 'internal', 'remote'
                 or'external'."
        ::= { gmsTableEntry 24 }

mdmDataRate OBJECT-TYPE
        SYNTAX  INTEGER {
                other       (1)
        }
        ACCESS  read-write
        STATUS  mandatory
        DESCRIPTION
                "The data rate at the interface in bits per seconds. The
                 data rate at the remote counterpart changes simultaneously."
        ::= { gmsTableEntry 25 }

END
