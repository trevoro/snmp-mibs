PAIRGAIN-ATMTC-MIB

-- PairGain ATM TC Layer MIB Release 1.0(2)
-- Revision Date:  04/17/2000
--
-- Copyright 2000 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--
-- Revision History
--------------------------------------------------------------
-- Date     Ver     Programmer      Description
--------------------------------------------------------------
-- 03/17/00 1.0(1)  R. Wada 		Lifted TC portion from pgsdslcell.my file
-- 04/17/00 1.0(2)  R. Wada		    After MIB review.

DEFINITIONS ::= BEGIN

-- SECTION 1: Top Level Definitions

IMPORTS
    Counter32, MODULE-IDENTITY, OBJECT-TYPE, NOTIFICATION-TYPE
        FROM SNMPv2-SMI
    OBJECT-TYPE
        FROM RFC-1212
    pgAtmTcMIB
        FROM PAIRGAIN-COMMON-HD-MIB
    ifIndex
        FROM RFC1213-MIB
    DisplayString, RowStatus, TruthValue, TimeStamp
        FROM SNMPv2-TC;

-- Module Identity atmTc (required for SNMP v2)
pgatmTcMIB MODULE-IDENTITY
    LAST-UPDATED    "0003170000Z"
    ORGANIZATION    "PairGain Technologies Inc."
        CONTACT-INFO    "
                    14402 Franklin Avenue
                    Tustin, CA  92780
                    "
    DESCRIPTION "This module defines the ATM TC layer MIB "
    ::= {pgAtmTcMIB 1}

pgatmTcMibObjects        OBJECT IDENTIFIER ::= { pgatmTcMIB 1 }


   pgatmTcLayerTable  OBJECT-TYPE
        SYNTAX      SEQUENCE OF PgatmTcLayerEntry
        MAX-ACCESS  not-accessible
        STATUS      current
        DESCRIPTION
            "This table provides one row for each port.
             Each row contains the Physical Layer Parameters
             table for that port."
        ::= {pgatmTcMibObjects 1}


   pgatmTcLayerEntry       OBJECT-TYPE
                SYNTAX          PgatmTcLayerEntry
                MAX-ACCESS      not-accessible
                STATUS          current
                DESCRIPTION     "An entry in the pgatmTcLayerTable."
                INDEX           { ifIndex }
        ::= { pgatmTcLayerTable 1 }


  PgatmTcLayerEntry ::=    SEQUENCE {
		pgatmTcTxCellCount		Counter32,
		pgatmTcRxCellCount		Counter32,
		pgatmTcNonMatchCount  	Counter32,
		pgatmTcLOCDEventCount 	Counter32,
		pgatmTcCorrHECError   	Counter32,
		pgatmTcUnCorrHECError	Counter32,
		pgatmTcLayerMode        INTEGER,
		pgatmTcScramble   		INTEGER,
		pgatmTcClearStats		INTEGER,
		pgatmTcStatsLastCleared TimeStamp
        }

		        pgatmTcTxCellCount OBJECT-TYPE
                    SYNTAX      Counter32
                    MAX-ACCESS  read-only
                    STATUS      current
                    DESCRIPTION
                        "Total number of Transmitted cells"
                ::= { pgatmTcLayerEntry 1 }

                pgatmTcRxCellCount OBJECT-TYPE
                    SYNTAX      Counter32
                    MAX-ACCESS  read-only
                    STATUS      current
                    DESCRIPTION
                        "Total number of Received cells"
                ::= { pgatmTcLayerEntry 2 }

                pgatmTcNonMatchCount OBJECT-TYPE
                    SYNTAX      Counter32
                    MAX-ACCESS  read-only
                    STATUS      current
                    DESCRIPTION
                        "Total number Non-matching cells"
                ::= { pgatmTcLayerEntry 3 }

				pgatmTcLOCDEventCount OBJECT-TYPE
                    SYNTAX      Counter32
                    MAX-ACCESS  read-only
                    STATUS      current
                    DESCRIPTION
                        "Total number LOCD Events"
                ::= { pgatmTcLayerEntry 4 }

                pgatmTcCorrHECError OBJECT-TYPE
                    SYNTAX      Counter32
                    MAX-ACCESS  read-only
                    STATUS      current
                    DESCRIPTION
                        "Total number corrected HEC Errors"
                ::= { pgatmTcLayerEntry 5 }

                pgatmTcUnCorrHECError OBJECT-TYPE
                    SYNTAX      Counter32
                    MAX-ACCESS  read-only
                    STATUS      current
                    DESCRIPTION
                        "Total number un corrected HEC Errors"
                ::= { pgatmTcLayerEntry 6 }


                pgatmTcLayerMode OBJECT-TYPE
                    SYNTAX      INTEGER {
        		normal    (1),
        		loopback  (2)
        		}

                    MAX-ACCESS  read-write
                    STATUS      current
                    DESCRIPTION
                        "The state of the TC layer port
				normal means operating in normal mode
				loop   means operation in loopback mode"
                ::= { pgatmTcLayerEntry 7 }

                pgatmTcScramble OBJECT-TYPE
                    SYNTAX      INTEGER {
        		off       (0),
        		sss       (1),
				dss		  (2)
        		}

                    MAX-ACCESS  read-write
                    STATUS      current
                    DESCRIPTION
                        "
						off (1) - no cell scrambling.
						sss (2) - Self-Synchronizing Cell Scrambling (SSS)
						dss (3) - Distributed Sampler Header Scrambling (DSS)
						setting are on a per-port basis.
						"
                ::= { pgatmTcLayerEntry 8 }

				pgatmTcClearStats OBJECT-TYPE
					SYNTAX  INTEGER {
						clear(1)
					}
					MAX-ACCESS  read-write
					STATUS  current
					DESCRIPTION
						"Clear statistics counters to zero on this particular port."
					::= {  pgatmTcLayerEntry 9 }

				pgatmTcStatsLastCleared OBJECT-TYPE
        			SYNTAX  TimeStamp
        			MAX-ACCESS  read-only
        			STATUS  current
        			DESCRIPTION
            			"The value of MIB II's sysUpTime object at the
            			last time these statistics were cleared.
            			At power on, this value should contain 0.
            			"
        			::= { pgatmTcLayerEntry 10 }


END
