XEROX-GENERAL-MIB DEFINITIONS ::= BEGIN

-- Module: General MIB
-- Editor: Paul Gloger, Gary Padlipsky, Ira McDonald
-- File:   07gen.mib
-- Date:   14 December 1997 - Version 2.40.pub

IMPORTS
        MODULE-IDENTITY, OBJECT-IDENTITY,
        OBJECT-TYPE, Counter32, Integer32
                FROM SNMPv2-SMI                    -- RFC 1442/1902
        RowStatus, TruthValue, DisplayString,
        DateAndTime
                FROM SNMPv2-TC                     -- RFC 1443/1903
        MODULE-COMPLIANCE, OBJECT-GROUP
                FROM SNMPv2-CONF                   -- RFC 1444/1904
        hrDeviceIndex, InternationalDisplayString,
        ProductID
                FROM HOST-RESOURCES-MIB            -- RFC 1514
        CodedCharSet
                FROM Printer-MIB                   -- RFC 1759
        xeroxCommonMIB
                FROM XEROX-COMMON-MIB
        Cardinal32, CodedLanguage, CodedCountry,
        CodeIndexedStringIndex, Ordinal16, Ordinal32,
        XcmGenGroupSupport,
        XcmGenOptionValueSyntax,
        XcmGenReconfOptionState,
        XcmGenRowPersistence,
        XcmGenSNMPDomain,
        XcmGenSNMPVersion,
        XcmGenSNMPv2ErrorStatus,
        xcmGenZeroDotZero,
        XcmGlobalUniqueID
                FROM XEROX-GENERAL-TC;

xcmGeneralMIB MODULE-IDENTITY
    LAST-UPDATED "9712140000Z"
    ORGANIZATION "Xerox Corporation - XCMI Working Group"
    CONTACT-INFO "
                XCMI Editors
            E-Mail:     xcmieditors@cp10.es.xerox.com

    --
    --
            "
    DESCRIPTION "
        Version:    2.40.pub

        Xerox General MIB

        Copyright (C) 1997 Xerox Corporation. All Rights Reserved."
    ::= { xeroxCommonMIB 51 }

--
-- General Base Group (Mandatory)
--
-- Implementation of this group is mandatory for all systems.

xcmGenBase                  OBJECT IDENTIFIER ::= { xcmGeneralMIB 1 }

xcmGenBaseTable OBJECT-TYPE
    SYNTAX      SEQUENCE OF XcmGenBaseEntry
    MAX-ACCESS  not-accessible
    STATUS      current
    DESCRIPTION
        "A table of general counters and capabilities for ease of use
        of the XCMI General MIB on this host system.

        Usage:  The ONLY valid row in the 'xcmGenBaseTable'
        shall ALWAYS have an 'xcmGenBaseIndex' of one ('1')."
    ::= { xcmGenBase 2 }

xcmGenBaseEntry OBJECT-TYPE
    SYNTAX      XcmGenBaseEntry
    MAX-ACCESS  not-accessible
    STATUS      current
    DESCRIPTION
        "An entry of general counters and capabilities for ease of use
        of the XCMI General MIB on this host system.

        Usage:  The ONLY valid row in the 'xcmGenBaseTable'
        shall ALWAYS have an 'xcmGenBaseIndex' of one ('1')."
    INDEX       { xcmGenBaseIndex }
    ::= { xcmGenBaseTable 1 }

XcmGenBaseEntry ::= SEQUENCE {
        --  General MIB Info
        xcmGenBaseIndex                 Ordinal32,
        xcmGenBaseRowStatus             RowStatus,
        xcmGenBaseSystemHrDeviceIndex   Cardinal32,
        --  General MIB Capabilities Info
        xcmGenBaseGroupSupport          XcmGenGroupSupport,
        xcmGenBaseGroupCreateSupport    XcmGenGroupSupport,
        xcmGenBaseGroupUpdateSupport    XcmGenGroupSupport,
        xcmGenBaseClientDataMaxSupport  Cardinal32,
        xcmGenBaseOptionSyntaxSupport   Cardinal32,
        xcmGenBaseReconfStateSupport    Cardinal32,
        xcmGenBaseSNMPDomainSupport     Cardinal32,
        xcmGenBaseSNMPTrapSupport       TruthValue,
        xcmGenBaseSNMPVersionSupport    Cardinal32
    }

xcmGenBaseIndex OBJECT-TYPE
    SYNTAX      Ordinal32
    MAX-ACCESS  not-accessible
    STATUS      current
    DESCRIPTION
        "A unique value used by this host system to identify this
        conceptual row in the 'xcmGenBaseTable'.

        Usage:  The ONLY valid row in the 'xcmGenBaseTable'
        shall ALWAYS have an 'xcmGenBaseIndex' of one ('1')."
    ::= { xcmGenBaseEntry 1 }

xcmGenBaseRowStatus OBJECT-TYPE
    SYNTAX      RowStatus
    MAX-ACCESS  read-only
    STATUS      current
    DESCRIPTION
        "This object is used to display status of the ONLY valid
        conceptual row in the 'xcmGenBaseTable'.

        Usage:  'xcmGenBaseRowStatus' is 'read-only' because
        the ONLY valid conceptual row shall NOT be deleted."
    ::= { xcmGenBaseEntry 2 }

xcmGenBaseSystemHrDeviceIndex OBJECT-TYPE
    SYNTAX      Cardinal32
    MAX-ACCESS  read-only
    STATUS      current
    DESCRIPTION
        "The value of 'hrDeviceIndex' corresponding to the platform
        associated conceptual row in the 'hrDeviceTable' representing
        the CPU device (of type 'hrDeviceProcessor'), which currently
        supports the executing process/thread of this management agent."
    REFERENCE "
        See:    'hrDeviceIndex' in the Device group of the
                IETF Host Resources MIB (RFC 1514).
        See:    'xcmHrStoragePlatformDeviceIndex' in the Storage Ext
                group of the XCMI Host Resources Ext MIB."
    DEFVAL      { 0 }                   -- no system platform device
    ::= { xcmGenBaseEntry 3 }

xcmGenBaseGroupSupport OBJECT-TYPE
    SYNTAX      XcmGenGroupSupport
    MAX-ACCESS  read-only
    STATUS      current
    DESCRIPTION
        "The terse conformance statement of ALL mandatory, conditionally
        mandatory, and optional XCMI General MIB object groups which are
        supported by this management agent implementation (ie, version)
        on this host system, specified in a bit-mask.

        Usage:  Conforming management agents shall ALWAYS accurately
        report their support for the XCMI General MIB object groups."
    DEFVAL      { 0 }                   -- no mandatory groups
    ::= { xcmGenBaseEntry 4 }

xcmGenBaseGroupCreateSupport OBJECT-TYPE
    SYNTAX      XcmGenGroupSupport
    MAX-ACCESS  read-only
    STATUS      current
    DESCRIPTION
        "The terse conformance statement of ALL mandatory, conditionally
        mandatory, and optional XCMI General MIB object groups which are
        supported for dynamic row creation (via '...RowStatus')
        by this management agent implementation (ie, version)
        on this host system, specified in a bit-mask.

        Usage:  Conforming management agents shall ALWAYS accurately
        report their support for the XCMI General MIB object groups."
    DEFVAL      { 0 }                   -- no dynamic row create groups
    ::= { xcmGenBaseEntry 5 }

xcmGenBaseGroupUpdateSupport OBJECT-TYPE
    SYNTAX      XcmGenGroupSupport
    MAX-ACCESS  read-only
    STATUS      current
    DESCRIPTION
        "The terse conformance statement of ALL mandatory, conditionally
        mandatory, and optional XCMI General MIB object groups which are
        supported for existing row update (via SNMP Set-Request PDUs)
        by this management agent implementation (ie, version)
        on this host system, specified in a bit-mask.

        Usage:  Conforming management agents shall ALWAYS accurately
        report their support for the XCMI General MIB object groups."
    DEFVAL      { 0 }                   -- no existing row update groups
    ::= { xcmGenBaseEntry 6 }

xcmGenBaseClientDataMaxSupport OBJECT-TYPE
    SYNTAX      Cardinal32
    MAX-ACCESS  read-only
    STATUS      current
    DESCRIPTION "
        The maximum 'xcmGenClientDataLength' supported for ANY
        conceptual row in the 'xcmGenClientDataTable'.

        Usage:  Conforming implementations need NOT support maximum
        'xcmGenClientDataLength' greater than 1 octet."
    REFERENCE "
        See:    'xcmGenClientDataLength'"
    DEFVAL      { 1 }                   -- client data length support
    ::= { xcmGenBaseEntry 7 }

xcmGenBaseOptionSyntaxSupport OBJECT-TYPE
    SYNTAX      Cardinal32
    MAX-ACCESS  read-only
    STATUS      current
    DESCRIPTION "
        The 'xcmGenOptionValueSyntax' values supported for ANY
        conceptual row in the 'xcmGenOptionTable'.

        Usage:  Conforming management agents shall ALWAYS report their
        supported values as a 'bit-mask' formed via the bit-wise OR of
        '2**(n)', where (n) is each supported enumerated value in the
        in the 'XcmGenOptionValueSyntax' textual convention."
    REFERENCE "
        See:    'XcmGenOptionValueSyntax' in the XCMI General TC"
    DEFVAL      { 0 }                   -- no option syntax support
    ::= { xcmGenBaseEntry 8 }

xcmGenBaseReconfStateSupport OBJECT-TYPE
    SYNTAX      Cardinal32
    MAX-ACCESS  read-only
    STATUS      current
    DESCRIPTION "
        The 'xcmGenReconfOptionState' values supported for ANY
        conceptual row in the 'xcmGenReconfTable'.

        Usage:  Conforming management agents shall ALWAYS report their
        supported values as a 'bit-mask' formed via the bit-wise OR of
        '2**(n)', where (n) is each supported enumerated value in the
        in the 'XcmGenReconfOptionState' textual convention."
    REFERENCE "
        See:    'XcmGenReconfOptionState' in the XCMI General TC"
    DEFVAL      { 0 }                   -- no reconf state support
    ::= { xcmGenBaseEntry 9 }

xcmGenBaseSNMPDomainSupport OBJECT-TYPE
    SYNTAX      Cardinal32
    MAX-ACCESS  read-only
    STATUS      current
    DESCRIPTION "
        The 'xcmGenTrapClientSNMPDomain' values supported for ANY
        conceptual row in the 'xcmGenTrapClientTable'.

        Usage:  Conforming management agents shall ALWAYS report their
        supported values as a 'bit-mask' formed via the bit-wise OR of
        '2**(n)', where (n) is each supported enumerated value in the
        in the 'XcmGenSNMPDomain' textual convention."
    REFERENCE "
        See:    'XcmGenSNMPDomain' in the XCMI General TC"
--  DEFVAL intentionally omitted - agents shall report their support
    ::= { xcmGenBaseEntry 10 }

xcmGenBaseSNMPTrapSupport OBJECT-TYPE
    SYNTAX      TruthValue
    MAX-ACCESS  read-only
    STATUS      current
    DESCRIPTION "
        This object shall be 'true' if this management agent
        supports SNMP traps (in any SNMP domain and SNMP version)
        and MAY support the 'xcmGenTrapClientTable'.

        This object shall be 'false' if this management agent does NOT
        support SNMP traps (in any SNMP domain and SNMP version)
        and does NOT support the 'xcmGenTrapClientTable'."
    REFERENCE "
        See:    'xcmGenBaseGroupSupport' for 'xcmGenTrapClientTable'"
--  DEFVAL intentionally omitted - agents shall report their support
    ::= { xcmGenBaseEntry 11 }

xcmGenBaseSNMPVersionSupport OBJECT-TYPE
    SYNTAX      Cardinal32
    MAX-ACCESS  read-only
    STATUS      current
    DESCRIPTION "
        The 'xcmGenTrapClientSNMPVersion' values supported for ANY
        conceptual row in the 'xcmGenTrapClientTable'.

        Usage:  Conforming management agents shall ALWAYS report their
        supported values as a 'bit-mask' formed via the bit-wise OR of
        '2**(n)', where (n) is each supported enumerated value in the
        in the 'XcmGenSNMPVersion' textual convention."
    REFERENCE "
        See:    'XcmGenSNMPVersion' in the XCMI General TC"
--  DEFVAL intentionally omitted - agents shall report their support
    ::= { xcmGenBaseEntry 12 }

--
-- General Current Localization Group (Conditionally Mandatory)
--
-- This is a group to control the localization of static string objects
-- that use the InternationalDisplayString types in legacy and new MIBs.
--
-- Implementation of the xcmGenCurrentLocalization group is
-- conditionally mandatory:  Mandatory for all devices which
-- instrument MIB objects of type InternationalDisplayString or
-- implement the xcmGenLocalizationGroup.
--

xcmGenCurrentLocalization   OBJECT IDENTIFIER ::= { xcmGeneralMIB 3 }

xcmGenCurrentLocalizationTable OBJECT-TYPE
    SYNTAX      SEQUENCE OF XcmGenCurrentLocalizationEntry
    MAX-ACCESS  not-accessible
    STATUS      current
    DESCRIPTION "
        A table of general localization information per device.  It is
        put in a table so it can be per device using the hrDeviceIndex."
    ::= { xcmGenCurrentLocalization 1 }

xcmGenCurrentLocalizationEntry OBJECT-TYPE
    SYNTAX      XcmGenCurrentLocalizationEntry
    MAX-ACCESS  not-accessible
    STATUS      current
    DESCRIPTION "
        Contains the scalar objects that we want to be per device."
    INDEX       { hrDeviceIndex }
    ::= { xcmGenCurrentLocalizationTable 1 }

XcmGenCurrentLocalizationEntry ::= SEQUENCE {
        xcmGenCurrentLocalizationIndex  Ordinal16,
        xcmGenCurrLocalizationRowStatus RowStatus
    }

xcmGenCurrentLocalizationIndex OBJECT-TYPE
    SYNTAX      Ordinal16
    MAX-ACCESS  read-create
    STATUS      current
    DESCRIPTION "
        The value of the xcmGenLocalizationIndex corresponding to the
        current language, country, and character set which shall be
        used for all objects of type InternationalDisplayString in
        all legacy and future MIBs.

        Note the Printer MIB has a similar mechanism which controls only
        objects (of type OCTET STRING) which are in the Printer MIB."

    ::= { xcmGenCurrentLocalizationEntry 1 }

xcmGenCurrLocalizationRowStatus OBJECT-TYPE
    SYNTAX      RowStatus
    MAX-ACCESS  read-create
    STATUS      current
    DESCRIPTION "
        This object manages the row status of this conceptual row in
        the 'xcmGenCurrentLocalizationTable'.

        Usage:  Conforming implementations need NOT support dynamic row
        creation (via 'createAndGo(4)') nor dynamic row deletion (via
        'destroy(6)').

        Usage:  Conforming implementations may support a single, static
        conceptual row, but shall ALWAYS allocate that row with an
        'hrDeviceIndex' value of one ('1').

        Usage:  This row status shall ALWAYS be set, to 'active(1)' (for
        static rows) or 'createAndGo(4)' (for dynamic rows),
        in the same PDU which sets the
        current locale in 'xcmGenCurrentLocalizationIndex'
        (thus activating/allocating this conceptual row).

        Usage:  To explicitly release this conceptual row, a management
        station shall ALWAYS set 'xcmGenCurrLocalizationRowStatus' to
        'notInService(2)' (for static rows) or 'destroy(6)' (for dynamic
        rows)."
    ::= { xcmGenCurrentLocalizationEntry 2 }

--
-- General Localization Group (Conditionally Mandatory)
--
-- This is a group to control the localization of static string objects
-- that use 'InternationalDisplayString' types in legacy and new MIBs.
--
-- Implementation of the xcmGenLocalizationGroup group is
-- conditionally mandatory:  Mandatory for all which
-- instrument MIB objects of type 'InternationalDisplayString' or
-- implement the xcmGenCurrentLocalizationGroup.
--
-- Contains the localizations supported by this device.
--

xcmGenLocalization          OBJECT IDENTIFIER ::= { xcmGeneralMIB 4 }

xcmGenLocalizationTable OBJECT-TYPE
    SYNTAX      SEQUENCE OF XcmGenLocalizationEntry
    MAX-ACCESS  not-accessible
    STATUS      current
    DESCRIPTION "
        The available localizations in this device."
    ::= { xcmGenLocalization 1 }

xcmGenLocalizationEntry OBJECT-TYPE
    SYNTAX      XcmGenLocalizationEntry
    MAX-ACCESS  not-accessible
    STATUS      current
    DESCRIPTION "
        An entry exists in this table for each Localizaion, e.g. for 
        each combination of Language, Country (or Territory) and Coded 
        Character Set supported in some objects of 
        InternationalDisplayString type and for each device."
    INDEX       { hrDeviceIndex,
                  xcmGenLocalizationIndex }
    ::= { xcmGenLocalizationTable 1 }

XcmGenLocalizationEntry ::= SEQUENCE {
        xcmGenLocalizationIndex         Ordinal16,
        xcmGenLocalizationRowStatus     RowStatus,
        xcmGenLocalizationASCIIName     DisplayString,
        xcmGenLocalizationName          InternationalDisplayString,
        xcmGenLocalizationLanguage      CodedLanguage,
        xcmGenLocalizationCountry       CodedCountry,
        xcmGenLocalizationCharSet       CodedCharSet
    }

xcmGenLocalizationIndex OBJECT-TYPE
    SYNTAX      Ordinal16
    MAX-ACCESS  not-accessible
    STATUS      current
    DESCRIPTION "
        A unique value used by the device to identify this
        localization entry."
    ::= { xcmGenLocalizationEntry 1 }

xcmGenLocalizationRowStatus OBJECT-TYPE
    SYNTAX      RowStatus
    MAX-ACCESS  read-create
    STATUS      current
    DESCRIPTION "
        This object manages the row status of this conceptual row in
        the 'xcmGenLocalizationTable'."
    ::= { xcmGenLocalizationEntry 2 }

xcmGenLocalizationASCIIName OBJECT-TYPE
    SYNTAX      DisplayString (SIZE (0..255))
    MAX-ACCESS  read-create
    STATUS      current
    DESCRIPTION "
        The unlocalized human readable name in NVT ASCII of the
        localization with the language, followed by the country 
        (or territory), followed by the character set.

        Example: English US ASCII"
    DEFVAL     { ''H }
    ::= { xcmGenLocalizationEntry 3 }

xcmGenLocalizationName OBJECT-TYPE
    SYNTAX      InternationalDisplayString (SIZE (0..255))
    MAX-ACCESS  read-create
    STATUS      current
    DESCRIPTION "
        The localized human readable name of the localization with
        the language, followed by the country (or territory),
        followed by the character set. 

        Example: Japanese Japan Kanji (Represented with Kanji chars.)"
    DEFVAL     { ''H }                   -- no specified name
    ::= { xcmGenLocalizationEntry 4 }

xcmGenLocalizationLanguage OBJECT-TYPE
    SYNTAX      CodedLanguage
    MAX-ACCESS  read-create
    STATUS      current
    DESCRIPTION "
        A two character language abreviation from ISO 639:1988
        - Codes For the Representation of Names of Languages.
        Examples EN, GB, CA, FR, DE."
    DEFVAL     { ''H }                   -- no specified language
    ::= { xcmGenLocalizationEntry 5 }

xcmGenLocalizationCountry OBJECT-TYPE
    SYNTAX      CodedCountry
    MAX-ACCESS  read-create
    STATUS      current
    DESCRIPTION "
        A two character country or territory abbreviation from
        ISO 3166:1993 - Codes for the Representation of Names of
        Countries.
        Examples: US, FR, DE, ..."
    DEFVAL      { ''H }          -- no specified country or territory
    ::= { xcmGenLocalizationEntry 6 }

xcmGenLocalizationCharSet OBJECT-TYPE
    SYNTAX      CodedCharSet
    MAX-ACCESS  read-create
    STATUS      current
    DESCRIPTION "
        The coded character set used for this localization.
        The value is the enum for the coded character set registered
        with IANA.  See the CodedCharSet textual-convention in the
        Printer MIB (RFC 1759)."
    DEFVAL      { other }         -- no specified coded character set
    ::= { xcmGenLocalizationEntry 7 }

--
-- General Code Indexed String Group (Conditionally Mandatory)
--
-- This is a group to control the coded character set representation
-- of codeset indexed string objects that use the CodeIndexedStringIndex
-- types in new MIBs.
--
-- Implementation of the xcmGenIndexedStringGroup is
-- conditionally mandatory:  Mandatory for all systems which
-- instrument MIB objects of type CodeIndexedStringIndex or
-- implement the xcmGenCodedCharSetGroup.
--
-- Contains all the current codeset indexed strings for this device.
--

xcmGenCodeIndexedString     OBJECT IDENTIFIER ::= { xcmGeneralMIB 5 }

xcmGenCodeIndexedStringTable OBJECT-TYPE
    SYNTAX      SEQUENCE OF XcmGenCodeIndexedStringEntry
    MAX-ACCESS  not-accessible
    STATUS      current
    DESCRIPTION "
        The current codeset indexed strings for this device."
    ::= { xcmGenCodeIndexedString 1 }

xcmGenCodeIndexedStringEntry OBJECT-TYPE
    SYNTAX      XcmGenCodeIndexedStringEntry
    MAX-ACCESS  not-accessible
    STATUS      current
    DESCRIPTION "
        An entry exists in this table containing a code-indexed string
        in a particular coded character set.  There are separate sets of
        code-indexed strings for each device.

        If an agent supports multiple coded character representations
        of a codeset indexed string, including code conversion between,
        there will be a separate entry for each such coded
        representation.

        The xcmGenCodeIndexedStringCharSet selects which coded
        character representation is to be returned.  The value of
        xcmGenCodeIndexedStringCharSet is the coded character set enum
        registered with IANA. See the CodedCharSet textual-convention
        in the Printer MIB (RFC 1759)."
    INDEX       { hrDeviceIndex,
                  xcmGenCodeIndexedStringIndex,
                  xcmGenCodeIndexedStringCharSet }
    ::= { xcmGenCodeIndexedStringTable 1 }

XcmGenCodeIndexedStringEntry ::= SEQUENCE {
        xcmGenCodeIndexedStringIndex         CodeIndexedStringIndex,
        xcmGenCodeIndexedStringCharSet       CodedCharSet,  -- an index
        xcmGenCodeIndexedStringRowStat       RowStatus,
        xcmGenCodeIndexedStringData          OCTET STRING
    }

xcmGenCodeIndexedStringIndex OBJECT-TYPE
    SYNTAX      CodeIndexedStringIndex (1..2147483647)
    MAX-ACCESS  not-accessible
    STATUS      current
    DESCRIPTION "
        A unique value used by the device, along with the following
        xcmGenCodeIndexedStringCharSet, to identify this Coded String
        entry.

        A value of 0 is not valid for this object."
    ::= { xcmGenCodeIndexedStringEntry 1 }

xcmGenCodeIndexedStringCharSet OBJECT-TYPE
    SYNTAX      CodedCharSet
    MAX-ACCESS  not-accessible
    STATUS      current
    DESCRIPTION "
        The coded character set used for this code-indexed string.
        The value is the enum for the coded character set registered
        with IANA.  See the CodedCharSet textual-convention in the
        Printer MIB (RFC 1759)."
    ::= { xcmGenCodeIndexedStringEntry 2 }

xcmGenCodeIndexedStringRowStat OBJECT-TYPE
    SYNTAX      RowStatus
    MAX-ACCESS  read-create
    STATUS      current
    DESCRIPTION "
        This object manages the row status of this conceptual row in
        the 'xcmGenCodeIndexedStringTable'."
    ::= { xcmGenCodeIndexedStringEntry 3 }

xcmGenCodeIndexedStringData OBJECT-TYPE
    SYNTAX      OCTET STRING (SIZE (0..255))
    MAX-ACCESS  read-create
    STATUS      current
    DESCRIPTION "
        This is the actual code-indexed string data, in the coded 
        character set identified by xcmGenCodeIndexedStringCharSet."
    DEFVAL     { ''H }      -- no specified code-indexed string data
    ::= { xcmGenCodeIndexedStringEntry 4 }

-- General Coded Char Set Group (Conditionally Mandatory)
--
-- This is a group to control the coded character set representation
-- of code-indexed string objects that use the CodeIndexedStringIndex
-- types in new MIBs.
--
-- Implementation of the xcmGenCodedCharSetGroup group is
-- conditionally mandatory:  Mandatory for all systems which
-- instrument MIB objects of type CodeIndexedStringIndex or
-- implement the xcmGenIndexedStringGroup group.
--
-- Contains the coded character set identifications of the coded 
-- character sets supported by this device for representing code-indexed
-- strings.

xcmGenCodedCharSet          OBJECT IDENTIFIER ::= { xcmGeneralMIB 6 }

xcmGenCodedCharSetTable OBJECT-TYPE
    SYNTAX      SEQUENCE OF XcmGenCodedCharSetEntry
    MAX-ACCESS  not-accessible
    STATUS      current
    DESCRIPTION "
        The supported coded character sets for this device."
    ::= { xcmGenCodedCharSet 1 }

xcmGenCodedCharSetEntry OBJECT-TYPE
    SYNTAX      XcmGenCodedCharSetEntry
    MAX-ACCESS  not-accessible
    STATUS      current
    DESCRIPTION "
        An entry exists in this table for each coded character set
        supported in some objects of CodeIndexedStringIndex type for
        each device."
    INDEX       { hrDeviceIndex,
                  xcmGenCodedCharSetCharSet }
    ::= { xcmGenCodedCharSetTable 1 }

XcmGenCodedCharSetEntry ::= SEQUENCE {
        xcmGenCodedCharSetCharSet       CodedCharSet,
        xcmGenCodedCharSetRowStatus     RowStatus,
        xcmGenCodedCharSetASCIIName     DisplayString
    }

xcmGenCodedCharSetCharSet OBJECT-TYPE
    SYNTAX      CodedCharSet
    MAX-ACCESS  not-accessible
    STATUS      current
    DESCRIPTION "
        The supported coded character set enum identifier, used an index
        for this table.  The value is the enum for the coded character
        set registered with IANA."
    REFERENCE "
        See the CodedCharSet textual-convention in the Printer MIB."
    ::= { xcmGenCodedCharSetEntry 1 }

xcmGenCodedCharSetRowStatus OBJECT-TYPE
    SYNTAX      RowStatus
    MAX-ACCESS  read-create
    STATUS      current
    DESCRIPTION "
        This object manages the row status of this conceptual row in
        the 'xcmGenCodedCharSetTable'.

        Usage:  Conforming implementations need NOT support dynamic row
        creation (via 'createAndGo(4)') nor dynamic row deletion (via
        'destroy(6)')."
    ::= { xcmGenCodedCharSetEntry 2 }

xcmGenCodedCharSetASCIIName OBJECT-TYPE
    SYNTAX      DisplayString (SIZE (0..255))
    MAX-ACCESS  read-create
    STATUS      current
    DESCRIPTION "
        The unlocalized human readable name in ASCII of the
        coded character set.

        Example: 'ASCII'"
    DEFVAL     { ''H }                        -- no specified name
    ::= { xcmGenCodedCharSetEntry 3 }

--
-- General Fixed Localization Group (Conditionally Mandatory)
--
--  This is a group to control the localization of static string objects
--  that use the 'FixedLocaleDisplayString' type.
--
--  Implementation of the General Fixed Localization group is
--  conditionally mandatory:  Mandatory for all devices which
--  implement MIB objects of type 'FixedLocaleDisplayString' and ALSO
--  implement the xcmGenLocalizationGroup.
--

xcmGenFixedLocalization     OBJECT IDENTIFIER ::= { xcmGeneralMIB 7 }

xcmGenFixedLocalizationTable OBJECT-TYPE
    SYNTAX      SEQUENCE OF XcmGenFixedLocalizationEntry
    MAX-ACCESS  not-accessible
    STATUS      current
    DESCRIPTION "
        A table of fixed localization information per device.  It is
        put in a table so it can be per device using the hrDeviceIndex."
    REFERENCE "
        See:    'FixedLocaleDisplayString'"
    ::= { xcmGenFixedLocalization 1 }

xcmGenFixedLocalizationEntry OBJECT-TYPE
    SYNTAX      XcmGenFixedLocalizationEntry
    MAX-ACCESS  not-accessible
    STATUS      current
    DESCRIPTION "
        An entry of fixed localization information per device."
    REFERENCE "
        See:    'FixedLocaleDisplayString'"
    INDEX       { hrDeviceIndex }
    ::= { xcmGenFixedLocalizationTable 1 }

XcmGenFixedLocalizationEntry ::= SEQUENCE {
        xcmGenFixedLocalizationIndex    Ordinal16,
        xcmGenFixedLocalizationRowStat  RowStatus
    }

xcmGenFixedLocalizationIndex OBJECT-TYPE
    SYNTAX      Ordinal16
    MAX-ACCESS  read-create
    STATUS      current
    DESCRIPTION "
        The value of the xcmGenLocalizationIndex corresponding to the
        current language, country, and character set which shall be
        used for all objects of type 'FixedLocaleDisplayString' in all
        current and future MIBs."
    REFERENCE "
        See:    'FixedLocaleDisplayString'"
    ::= { xcmGenFixedLocalizationEntry 1 }

xcmGenFixedLocalizationRowStat OBJECT-TYPE
    SYNTAX      RowStatus
    MAX-ACCESS  read-create
    STATUS      current
    DESCRIPTION "
        This object manages the row status of this conceptual row in
        the 'xcmGenFixedLocalizationTable'.

        Usage:  Conforming implementations need NOT support dynamic row
        creation (via 'createAndGo(4)') nor dynamic row deletion (via
        'destroy(6)').

        Usage:  Conforming implementations may support a single, static
        conceptual row, but shall ALWAYS allocate that row with an
        'hrDeviceIndex' value of one ('1').

        Usage:  This row status shall ALWAYS be set, to 'active(1)' (for
        static rows) or 'createAndGo(4)' (for dynamic rows),
        in the same PDU which sets the
        fixed locale in 'xcmGenFixedLocalizationIndex'
        (thus activating/allocating this conceptual row).

        Usage:  To explicitly release this conceptual row, a management
        station shall ALWAYS set 'xcmGenFixedLocalizationRowStat' to
        'notInService(2)' (for static rows) or 'destroy(6)' (for dynamic
        rows)."
    ::= { xcmGenFixedLocalizationEntry 2 }

    --
    --
--
-- General Reconf Group (Conditionally Mandatory)
--
-- Implementation of this group is conditionally mandatory, ie,
-- mandatory for systems which support tree structured
-- atomic reconfiguration, and optional for all other systems.
--
-- Implementation of this group is conditionally mandatory,
-- however it shall ALWAYS be implemented by systems which
-- implement the 'xcmGenOptionGroup'.
--
-- Usage:  Systems which implement the 'xcmGenReconfGroup'
-- and 'xcmGenOptionGroup' shall ALWAYS also implement
-- the 'xcmGenLockGroup' (for advisory contention locks).

xcmGenReconf                OBJECT IDENTIFIER ::= { xcmGeneralMIB 9 }

--
--          General Reconf Simple Objects
--
--

xcmGenReconfSimple OBJECT-IDENTITY
    STATUS      current
    DESCRIPTION "
        This subtree is current.  Subordinate objects are leaf objects."
    ::= { xcmGenReconf 1 }

xcmGenReconfActivations OBJECT-TYPE
    SYNTAX      Counter32
    MAX-ACCESS  read-only
    STATUS      current
    DESCRIPTION "
        The count of SUCCESSFUL 'activations' of reconfiguration for
        this host system:  invoked by SUCCESSFUL writes to the
        'xcmGenReconfOptionState' reconfiguration invocation object of
        'activateFor[ImmediateChange|RebootChange|ImmediateReboot]';
        and followed by SUCCESSFUL completions of 'activation' (without
        errors reports in 'xcmGenReconfError[Index|Status]').

        Usage:  Although no default value ('DEFVAL' clause) is permitted
        (by IETF SMIv2) for this counter, conforming host systems shall
        ALWAYS zero this counter upon conceptual row creation."
    REFERENCE "
        See:    'xcmGenReconfOptionState'"
    ::= { xcmGenReconfSimple 1 }

--
--          General Reconf Table Objects
--

xcmGenReconfTable OBJECT-TYPE
    SYNTAX      SEQUENCE OF XcmGenReconfEntry
    MAX-ACCESS  not-accessible
    STATUS      current
    DESCRIPTION "
        A table containing information on a 'reconfiguration request',
        for use in atomic reconfiguration of this host system.

        Usage:  A conforming management station (or management agent)
        shall ALWAYS lock 'xcmGenReconfTable' and 'xcmGenOptionTable'
        before attempting to perform any 'reconfiguration request' on a
        host system (via the 'xcmGenLockTable')."
    ::= { xcmGenReconf 2 }

xcmGenReconfEntry OBJECT-TYPE
    SYNTAX      XcmGenReconfEntry
    MAX-ACCESS  not-accessible
    STATUS      current
    DESCRIPTION "
        An entry containing information on a 'reconfiguration request',
        for use in atomic reconfiguration of this host system.

        Usage:  The ONLY valid row in the 'xcmGenReconfTable' shall
        ALWAYS have an 'xcmGenReconfIndex' of one ('1')."
    INDEX       { hrDeviceIndex,
                  xcmGenReconfIndex }
    ::= { xcmGenReconfTable 1 }

XcmGenReconfEntry ::= SEQUENCE {
        --  General Reconf Info
        xcmGenReconfIndex               Ordinal32,
        xcmGenReconfRowStatus           RowStatus,
        xcmGenReconfOptionIndex         Cardinal32,
        xcmGenReconfOptionState         XcmGenReconfOptionState,
        xcmGenReconfErrorIndex          Cardinal32,
        xcmGenReconfErrorStatus         XcmGenSNMPv2ErrorStatus
    }

--
--          General Reconf Info
--

xcmGenReconfIndex OBJECT-TYPE
    SYNTAX      Ordinal32
    MAX-ACCESS  not-accessible
    STATUS      current
    DESCRIPTION "
        A unique value used by this host system to identify this
        conceptual row in the 'xcmGenReconfTable'.

        Usage:  The ONLY valid row in the 'xcmGenReconfTable' shall
        ALWAYS have an 'xcmGenReconfIndex' of one ('1')."
    REFERENCE "
        See:    System, Device, and Software Installed/Running groups
                in the IETF Host Resources MIB (RFC 1514).
        See:    Device Info, Device Mgmt, and Device Detail groups
                in the XCMI Host Resources Ext MIB."
    ::= { xcmGenReconfEntry 1 }

xcmGenReconfRowStatus OBJECT-TYPE
    SYNTAX      RowStatus
    MAX-ACCESS  read-create
    STATUS      current
    DESCRIPTION "
        This object manages the row status of this conceptual row in
        the 'xcmGenReconfTable'.

        Usage:  Conforming management agents shall ALWAYS support
        'active(1)' and should support 'notInService(2)' or 'destroy(6)'
        (to 'release' the 'reconfiguration request').

        Usage:  Conforming management agents need NOT support
        'createAndGo(4)', and should NOT support 'notReady(3)' or
        'createAndWait(5)'.

        Usage:  See section 3.4 'Secure Modes of Operation' and section
        3.5 'Secure SNMP Get/Set Requests' in XCMI Security TC, for
        details of secure modes of access to this row status object."
    REFERENCE "
        See:    'RowStatus' in IETF SNMPv2 TC (RFC 1443/1903).
        See:    'xcmHrDevMgmtCommandData' in XCMI HRX MIB and
                'xcmSecUserMgmtData' in XCMI Security MIB."
    ::= { xcmGenReconfEntry 2 }

xcmGenReconfOptionIndex OBJECT-TYPE
    SYNTAX      Cardinal32
    MAX-ACCESS  read-create
    STATUS      current
    DESCRIPTION "
        The value of 'xcmGenOptionIndex' corresponding to the first
        pending reconfiguration option (in 'xcmGenOptionTable'), or
        zero if there are no pending reconfiguration options for this
        host system.

        Usage:  This 'chain' represents pending reconfiguration
        options of this host system."
    REFERENCE "
        See:    'xcmGenReconfActiveOptionIndex'"
    DEFVAL      { 0 }                   -- no entries
    ::= { xcmGenReconfEntry 3 }

xcmGenReconfOptionState OBJECT-TYPE
    SYNTAX      XcmGenReconfOptionState
    MAX-ACCESS  read-create
    STATUS      current
    DESCRIPTION "
        The processing state of ALL pending reconfiguration options of
        this host system.

        A write to this object by an (authorized) management station
        invokes a request for validation (or activation) of ALL pending
        reconfiguration options of this host system.
        A read of this object returns 'idle', 'validateInProgress', or
        'activateInProgress' to report the processing state of the last
        'validate...' or 'activate...' request.
        It is mandatory that a conforming management agent ensure that,
        at system initialization, this object shall ALWAYS be set to a
        value of 'idle'.

        Usage:  See section 3.4 'Secure Modes of Operation' and section
        3.5 'Secure SNMP Get/Set Requests' in XCMI Security TC, for
        details of secure modes of access to this option state object."
    REFERENCE "
        See:    'xcmGenReconfError[Index|Status]'
        See:    'XcmGenReconfOptionState', in the companion XCMI
        CC TC, for details of 'validation' and 'activation' operations.
        See:    'xcmHrDevMgmtCommandData' in XCMI HRX MIB and
                'xcmSecUserMgmtData' in XCMI Security MIB."
    DEFVAL      { idle }                -- no reconfiguration processing
    ::= { xcmGenReconfEntry 4 }

xcmGenReconfErrorIndex OBJECT-TYPE
    SYNTAX      Cardinal32
    MAX-ACCESS  read-create
    STATUS      current
    DESCRIPTION "
        The value of 'xcmGenOptionIndex' corresponding to the first
        pending reconfiguration option (in 'xcmGenOptionTable') which
        was found to be 'in error' (during 'validate' or 'activate'
        reconfiguration processing for this host system), or zero
        if no error was found (eg, consistency, range, etc)."
    REFERENCE "
        See:    'xcmGenReconfErrorStatus'"
    DEFVAL      { 0 }                   -- no reconfiguration error
    ::= { xcmGenReconfEntry 5 }

xcmGenReconfErrorStatus OBJECT-TYPE
    SYNTAX      XcmGenSNMPv2ErrorStatus
    MAX-ACCESS  read-create
    STATUS      current
    DESCRIPTION "
        The reconfiguration error status corresponding to the first
        pending reconfiguration option (in 'xcmGenOptionTable') which
        was found to be 'in error' (during 'validate' or 'activate'
        reconfiguration processing for this host system), or 'noError'
        if no error was found (eg, consistency, range, etc)."
    REFERENCE "
        See:    'xcmGenReconfErrorIndex'"
    DEFVAL      { noError }             -- no reconfiguration error
    ::= { xcmGenReconfEntry 6 }

--
-- General Option Group (Conditionally Mandatory)
--
-- Implementation of this group is conditionally mandatory, ie,
-- mandatory for systems which support tree structured
-- atomic reconfiguration, and optional for all other systems.
--
-- Implementation of this group is conditionally mandatory,
-- however it shall ALWAYS be implemented by systems which
-- implement the 'xcmGenReconfGroup'.
--
-- Usage:  Systems which implement the 'xcmGenReconfGroup'
-- and 'xcmGenOptionGroup' shall ALWAYS also implement
-- the 'xcmGenLockGroup' (for advisory contention locks).

xcmGenOption                OBJECT IDENTIFIER ::= { xcmGeneralMIB 10 }

--
--          General Option Simple Objects
--
--          (for Option Operations ONLY in General MIB V2.32 and above)

xcmGenOptionSimple OBJECT-IDENTITY
    STATUS      current                 -- restricted use for operations
    DESCRIPTION "
        This arc shall ONLY be used to define Option Operations in
        the XCMI General MIB V2.32 and above - see General Base group."
    ::= { xcmGenOption 1 }

--
--          General Option Operations
--
--          Insert:     All 'family' options shall ALWAYS be 'added'
--                      to current single- or multi-valued options
--
--          Delete:     All 'family' options shall ALWAYS be 'removed'
--                      from current single- or multi-valued options
--
--          Replace:    All 'family' options shall ALWAYS 'replace'
--                      any current single- or multi-valued options
--
--          Note:       The 'replace' operation is the DEFAULT and need
--                      NOT be specified - it is defined for clarity

xcmGenOptionOperation
    OBJECT IDENTIFIER ::= { xcmGenOptionSimple 1 }
    -- integerTruthValue (shall ALWAYS be 'true')

xcmGenOptionOperationInsert
    OBJECT IDENTIFIER ::= { xcmGenOptionOperation 1 }
    -- integerTruthValue (shall ALWAYS be 'true')
xcmGenOptionOperationDelete
    OBJECT IDENTIFIER ::= { xcmGenOptionOperation 2 }
    -- integerTruthValue (shall ALWAYS be 'true')
xcmGenOptionOperationReplace
    OBJECT IDENTIFIER ::= { xcmGenOptionOperation 3 }
    -- integerTruthValue (shall ALWAYS be 'true')

--
--          General Option Table Objects
--

xcmGenOptionTable OBJECT-TYPE
    SYNTAX      SEQUENCE OF XcmGenOptionEntry
    MAX-ACCESS  not-accessible
    STATUS      current
    DESCRIPTION "
        A table containing information on reconfiguration options,
        for use in atomic reconfiguration of this host system.

        Usage:  A conforming management station (or management agent)
        shall ALWAYS lock 'xcmGenReconfTable' and 'xcmGenOptionTable'
        before attempting to perform any 'reconfiguration request' on a
        host system (via the 'xcmGenLockTable').

        Note:   The 'xcmGenOptionTable' is indexed by 'hrDeviceIndex',
        so the 'hrDeviceIndex' element of a columnar object instance ID
        (ie, fully specified object identifier) need NOT be specified in
        'xcmGenOptionTypeOID'.  To reconfigure objects indexed by
        several devices in 'hrDeviceTable' of the IETF Host Resources
        MIB (RFC 1514), a conforming management station shall ALWAYS use
        several rows in 'xcmGenReconfTable' and several trees of objects
        in 'xcmGenOptionTable' with appropriate 'hrDeviceIndex' values.
        To reconfigure objects which are actually NOT indexed by
        'hrDeviceIndex', it is RECOMMENDED that rows be used in
        'xcmGenOptionTable' which are indexed by 'hrDeviceIndex' for an
        'hrDeviceType' of 'hrDeviceUnknown'."
    ::= { xcmGenOption 2 }

xcmGenOptionEntry OBJECT-TYPE
    SYNTAX      XcmGenOptionEntry
    MAX-ACCESS  not-accessible
    STATUS      current
    DESCRIPTION "
        An entry containing information on a reconfiguration option,
        for use in atomic reconfiguration of this host system.

        Usage:  A conforming management station (or management agent)
        shall ALWAYS lock 'xcmGenReconfTable' and 'xcmGenOptionTable'
        before attempting to perform any 'reconfiguration request' on a
        host system (via the 'xcmGenLockTable')."
    INDEX       { hrDeviceIndex,
                  xcmGenOptionIndex }
    ::= { xcmGenOptionTable 1 }

XcmGenOptionEntry ::= SEQUENCE {
        --  General Option Info
        xcmGenOptionIndex               Ordinal32,
        xcmGenOptionRowStatus           RowStatus,
        xcmGenOptionTypeOID             OBJECT IDENTIFIER,
        xcmGenOptionValueSyntax         XcmGenOptionValueSyntax,
        xcmGenOptionValueInteger        Integer32,
        xcmGenOptionValueOID            OBJECT IDENTIFIER,
        xcmGenOptionValueString         OCTET STRING,
        xcmGenOptionValueLocalization   Cardinal32,
        xcmGenOptionValueCodedCharSet   CodedCharSet,
        --  General Option Common Cross References
        xcmGenOptionNextIndex           Cardinal32,
        xcmGenOptionPreviousIndex       Cardinal32,
        xcmGenOptionFamilyIndex         Cardinal32
    }

--
--          General Option Info
--

xcmGenOptionIndex OBJECT-TYPE
    SYNTAX      Ordinal32
    MAX-ACCESS  not-accessible
    STATUS      current
    DESCRIPTION "
        A unique value used by this host system to identify this
        conceptual row in the 'xcmGenOptionTable'."
    ::= { xcmGenOptionEntry 1 }

xcmGenOptionRowStatus OBJECT-TYPE
    SYNTAX      RowStatus
    MAX-ACCESS  read-create
    STATUS      current
    DESCRIPTION "
        This object manages the row status of this conceptual row in
        the 'xcmGenOptionTable'.

        Usage:  Conforming management agents shall ALWAYS support
        'active(1)' and 'createAndGo(4)'.

        Usage:  Conforming management agents should NOT support
        'notInService(2)', 'notReady(3)', 'createAndWait(5), or
        'destroy(6)'."
    ::= { xcmGenOptionEntry 2 }

xcmGenOptionTypeOID OBJECT-TYPE
    SYNTAX      OBJECT IDENTIFIER
    MAX-ACCESS  read-create
    STATUS      current
    DESCRIPTION "
        An unambiguous reconfiguration option type,
        used by system administrators and end users to identify
        this reconfiguration option.

        Usage:  Since this reconfiguration option type is specified
        as an object identifier, it may be taken from any IETF, Xerox,
        third- party, or product-specific MIB, or it may simply be any
        IETF SMIv2-style 'autonomous type'."
    DEFVAL      { xcmGenZeroDotZero }   -- no option type
    ::= { xcmGenOptionEntry 3 }

xcmGenOptionValueSyntax OBJECT-TYPE
    SYNTAX      XcmGenOptionValueSyntax
    MAX-ACCESS  read-create
    STATUS      current
    DESCRIPTION "
        A reconfiguration option value syntax,
        used by system administrators and end users to specify
        the correct value syntax for this reconfiguration option.

        Usage:  This reconfiguration option value syntax is used to
        select which of the following three objects shall be used to
        contain the value of this reconfiguration option."
    DEFVAL      { unknown }             -- unknown option value syntax
    ::= { xcmGenOptionEntry 4 }

xcmGenOptionValueInteger OBJECT-TYPE
    SYNTAX      Integer32
    MAX-ACCESS  read-create
    STATUS      current
    DESCRIPTION "
        A reconfiguration option value integer,
        used by system administrators and end users to specify
        the current value for a reconfiguration option
        with a base value syntax of 'INTEGER'.

        Note: This object has the type 'Integer32', rather than
        'INTEGER'.  This a work-around to compiler warnings which occur
        when 'INTEGER' is used without a range specification.  And if
        we had range qualified, it would have been identical to the
        SNMP 'Integer32' type.  In SNMPv2, only the 'Counter64 is an
        integer type wider 32 bits, and for backward compatibility we
        depricated the use of Counter64."
    REFERENCE "
        See:    'xcmGenOptionValueSyntax' and 'xcmGenOptionTypeOID'"
    DEFVAL      { 0 }                   -- no option value integer
    ::= { xcmGenOptionEntry 5 }

xcmGenOptionValueOID OBJECT-TYPE
    SYNTAX      OBJECT IDENTIFIER
    MAX-ACCESS  read-create
    STATUS      current
    DESCRIPTION "
        A reconfiguration option value OID (object identifier),
        used by system administrators and end users to specify
        the current value for a reconfiguration option
        with a base value syntax of 'OBJECT IDENTIFIER'."
    REFERENCE "
        See:    'xcmGenOptionValueSyntax' and 'xcmGenOptionTypeOID'"
    DEFVAL      { xcmGenZeroDotZero }   -- no option value OID
    ::= { xcmGenOptionEntry 6 }

xcmGenOptionValueString OBJECT-TYPE
    SYNTAX      OCTET STRING (SIZE (0..255))
    MAX-ACCESS  read-create
    STATUS      current
    DESCRIPTION "
        A reconfiguration option value string,
        used by system administrators and end users to specify
        the current value for a reconfiguration option
        with a base value syntax of 'OCTET STRING'."
    REFERENCE "
        See:    'xcmGenOptionValueSyntax' and 'xcmGenOptionTypeOID'"
    DEFVAL      { ''H }                 -- no option value string
    ::= { xcmGenOptionEntry 7 }

xcmGenOptionValueLocalization OBJECT-TYPE
    SYNTAX      Cardinal32
    MAX-ACCESS  read-create
    STATUS      current
    DESCRIPTION "
        A reconfiguration option value localization,
        used by system administrators and end users to specify
        the static localization for a reconfiguration option
        with a base value syntax of 'OCTET STRING'.

        Usage:  For a reconfiguration option string to which POSIX-style
        localization (territory, language, character set) is applicable,
        this object shall ALWAYS contain a suitable index value from
        'xcmGenLocalizationIndex' from the XCMI General MIB, or zero to
        indicate 'none'."
    REFERENCE "
        See:    'xcmGenOptionValueSyntax' and 'xcmGenOptionTypeOID'"
    DEFVAL      { 0 }                   -- no option value localization
    ::= { xcmGenOptionEntry 8 }

xcmGenOptionValueCodedCharSet OBJECT-TYPE
    SYNTAX      CodedCharSet
    MAX-ACCESS  read-create
    STATUS      current
    DESCRIPTION "
        A reconfiguration option value character set,
        used by system administrators and end users to specify
        the static character set for a reconfiguration option
        with a base value syntax of 'OCTET STRING'.

        Usage:  For a reconfiguration option string to which ONLY
        character set conversion (and NOT territory or language aspects
        of 'localization') is applicable, this object shall ALWAYS
        contain a suitable value or 'other(1)' to indicate 'none' or
        not currently standardized and enumerated in 'CodedCharSet'.
        The 'CodedCharSet' textual convention is defined in the IETF
        Printer MIB (RFC 1759)."
    REFERENCE "
        See:    'xcmGenOptionValueSyntax' and 'xcmGenOptionTypeOID'"
    DEFVAL      { other }               -- no option value character set
    ::= { xcmGenOptionEntry 9 }

--
--          General Option Common Cross References
--

xcmGenOptionNextIndex OBJECT-TYPE
    SYNTAX      Cardinal32
    MAX-ACCESS  read-create
    STATUS      current
    DESCRIPTION "
        The value of 'xcmGenOptionIndex' corresponding to the next
        'chained' conceptual row in the 'xcmGenOptionTable', or zero
        if this is the last associated conceptual row in a particular
        vertical 'chain' within a given set.

        Usage:  Generally, reconfiguration options (of similar or unlike
        type) are 'chained' vertically via '...[Next|Previous]Index'.
        But, in the case where particular communications options MUST
        be 'tightly coupled', they should be 'shelved' horizontally via
        '...[Family|Previous]Index' (eg, an IP address and an IP subnet
        mask)."
    DEFVAL      { 0 }                   -- no entry
    ::= { xcmGenOptionEntry 10 }

xcmGenOptionPreviousIndex OBJECT-TYPE
    SYNTAX      Cardinal32
    MAX-ACCESS  read-create
    STATUS      current
    DESCRIPTION "
        The value of 'xcmGenOptionIndex' corresponding to a previous
        associated conceptual row in the 'xcmGenOptionTable', or zero
        if this is the first associated conceptual row in a given set.

        Usage:  This object provides common 'backward' linkage for BOTH
        the 'xcmGenOptionNextIndex' and 'xcmGenOptionFamilyIndex'
        linkage objects.  A previous conceptual row MAY 'forward'
        reference this conceptual row via either '...NextIndex' or
        '...FamilyIndex' - ie, a given conceptual row MAY 'forward'
        reference EXACTLY zero, one, or two 'later' conceptual rows."
    DEFVAL      { 0 }                   -- no entry
    ::= { xcmGenOptionEntry 11 }

xcmGenOptionFamilyIndex OBJECT-TYPE
    SYNTAX      Cardinal32
    MAX-ACCESS  read-create
    STATUS      current
    DESCRIPTION "
        The value of 'xcmGenOptionIndex' corresponding to a next
        'family' conceptual row in the 'xcmGenOptionTable', or zero
        if this conceptual row has no associated 'family' members.

        Usage:  Generally, reconfiguration options (of similar or unlike
        type) are 'chained' vertically via '...[Next|Previous]Index'.
        But, in the case where particular reconfiguration options MUST
        be 'tightly coupled', they should be 'shelved' horizontally via
        '...FamilyIndex' (eg, an IP address and an IP subnet mask)."
    DEFVAL      { 0 }                   -- no entry
    ::= { xcmGenOptionEntry 12 }

--
-- General Client Data Group (Conditionally Mandatory)
--
-- Implementation of this group is conditionally mandatory, ie,
-- mandatory for systems which support 'client data' for remote
-- management stations, and optional for all other systems.
--
-- Usage:  Conforming implementations shall ALWAYS preserve active
-- 'client data' objects across management agent power cycles.
--

xcmGenClientData            OBJECT IDENTIFIER ::= { xcmGeneralMIB 11 }

--
--          General Client Data Simple Objects
--

xcmGenClientDataSimple OBJECT-IDENTITY
    STATUS      current
    DESCRIPTION "
        This subtree is current.  Subordinate objects are leaf objects."
    ::= { xcmGenClientData 1 }

xcmGenClientDataEntryCount OBJECT-TYPE
    SYNTAX      Counter32
    MAX-ACCESS  read-only
    STATUS      current
    DESCRIPTION "
        The current entry count (regardless of their current states) in
        the 'xcmGenClientDataTable' of this General MIB,
        on this host system."
    ::= { xcmGenClientDataSimple 1 }

xcmGenClientDataLastIndex OBJECT-TYPE
    SYNTAX      Cardinal32
    MAX-ACCESS  read-only
    STATUS      current
    DESCRIPTION "
        The last entry index (regardless of its current state) in
        the 'xcmGenClientDataTable' of this General MIB,
        on this host system.

        Usage:  This last entry index explicitly bounds the valid range
        of 'xcmGenClientDataIndex'."
    ::= { xcmGenClientDataSimple 2 }

--
--          General Client Data Table Objects
--

xcmGenClientDataTable OBJECT-TYPE
    SYNTAX      SEQUENCE OF XcmGenClientDataEntry
    MAX-ACCESS  not-accessible
    STATUS      current
    DESCRIPTION "
        A table containing 'client data' objects for use by conforming
        management stations/agents, particularly during installation
        of this host system.

        Usage:  To allocate 'client data' on managed host system,
        a conforming management station (or management agent) shall
        ALWAYS examine 'xcmGenClientDataLastIndex', to determine the
        appropriate value of 'xcmGenClientDataIndex' to use when
        creating a new conceptual row in the 'xcmGenClientDataTable'.

        Usage:  Throughout this specification, the term 'stable storage'
        refers to storage which is reliable over long durations (years)
        and is NOT destroyed by host system reboot (eg, battery-backed
        DRAM is 'stable storage' - while simple DRAM is NOT 'stable
        storage').  Examples of valid 'stable storage' include:  NVRAM,
        hard disk, EEPROM, etc.

        Usage:  Conforming implementations shall ALWAYS preserve active
        'client data' objects across management agent power cycles,
        and shall implement one of the following two methods:
        1)  The agent shall store 'client data' objects directly in
            'stable storage'; or
        2)  The agent shall automatically checkpoint all active 'client
            data' objects to 'stable storage' with reasonable frequency
            (either due to a write to some 'client data' object, or upon
            expiration of a product-specific timeout).

        Usage:  Conforming implementations may (optionally) support
        one of the following two 'checkpoint protocols':
        1)  A client sends a 'Set' of 'xcmGenClientDataRowStatus' to
            'active(1)', to request that a 'checkpoint' be performed;
        2a) An agent which supports 'rapid checkpoint',
            completes the checkpoint to 'stable storage', and
            sends a 'SetResponse' with 'noError(0)';
            <or>
        2b) An agent which supports 'delayed checkpoint',
            changes 'xcmGenClientDataRowStatus' to 'notInService(2)',
            sends a 'SetResponse' with 'noError(0)',
            completes the checkpoint to 'stable storage', and
            changes 'xcmGenClientDataRowStatus' back to 'active(1)'."
    ::= { xcmGenClientData 2 }

xcmGenClientDataEntry OBJECT-TYPE
    SYNTAX      XcmGenClientDataEntry
    MAX-ACCESS  not-accessible
    STATUS      current
    DESCRIPTION "
        An entry containing 'client data' objects for use by conforming
        management stations/agents, particularly during installation
        of this host system."
    INDEX       { xcmGenClientDataIndex }
    ::= { xcmGenClientDataTable 1 }

XcmGenClientDataEntry ::= SEQUENCE {
        --  General Client Data Info
        xcmGenClientDataIndex           Ordinal32,
        xcmGenClientDataRowStatus       RowStatus,
        xcmGenClientDataRequestDate     DateAndTime,
        xcmGenClientDataRequestID       XcmGlobalUniqueID,
        xcmGenClientDataProductID       ProductID,
        xcmGenClientDataLength          Cardinal32,
        xcmGenClientDataString          OCTET STRING
    }

--
--          General Client Data Info
--

xcmGenClientDataIndex OBJECT-TYPE
    SYNTAX      Ordinal32
    MAX-ACCESS  not-accessible
    STATUS      current
    DESCRIPTION "
        A unique value used by this host system to identify this
        conceptual row in the 'xcmGenClientDataTable'.

        Usage:  Conforming implementations which only support a single,
        statically allocated row, shall ALWAYS allocate that row with an
        'xcmGenClientDataIndex' value of one (1)."
    ::= { xcmGenClientDataEntry 1 }

xcmGenClientDataRowStatus OBJECT-TYPE
    SYNTAX      RowStatus
    MAX-ACCESS  read-create
    STATUS      current
    DESCRIPTION "
        This object manages the row status of this conceptual row in
        the 'xcmGenClientDataTable'.

        Usage:  Conforming implementations need NOT support dynamic row
        creation (via 'createAndGo(4)') nor dynamic row deletion (via
        'destroy(6)').

        Usage:  Conforming implementations may support a single, static
        conceptual row, but shall ALWAYS allocate that row with an
        'xcmGenClientDataIndex' value of one ('1').

        Usage:  This row status shall ALWAYS be set, to 'active(1)' (for
        static rows) or 'createAndGo(4)' (for dynamic rows),
        in the same PDU which sets the
        client data request ID in 'xcmGenClientDataRequestID',
        client data owner product ID in 'xcmGenClientDataProductID',
        and client data length in 'xcmGenClientDataLength'
        (thus activating/allocating this conceptual row).

        Usage:  To explicitly release this conceptual row, the client
        data owner shall ALWAYS set 'xcmGenClientDataRowStatus' to
        'notInService(2)' (for static rows) or 'destroy(6)' (for dynamic
        rows).

        Usage:  See section 3.4 'Secure Modes of Operation' and section
        3.5 'Secure SNMP Get/Set Requests' in XCMI Security TC, for
        details of secure modes of access to this row status object."
    REFERENCE "
        See:    'xcmGenClientDataRequestDate',
                'xcmGenClientDataRequestID',
                'xcmGenClientDataProductID',
                'xcmGenClientDataLength', and
                'xcmGenClientDataString'.
        See:    'RowStatus' in IETF SNMPv2 TC (RFC 1443/1903).
        See:    'xcmHrDevMgmtCommandData' in XCMI HRX MIB and
                'xcmSecUserMgmtData' in XCMI Security MIB."
    ::= { xcmGenClientDataEntry 2 }

xcmGenClientDataRequestDate OBJECT-TYPE
    SYNTAX      DateAndTime
    MAX-ACCESS  read-only
    STATUS      current
    DESCRIPTION "
        The client data request date which uniquely timestamps the
        creation of this conceptual row in the 'xcmGenClientDataTable'.

        Usage:  This request date shall ALWAYS be set (to a suitable
        value) by conforming management agents during creation of each
        conceptual row in the 'xcmGenClientDataTable'.

        Usage:  Conforming implementations which have a source of time,
        shall ALWAYS set a meaningful value in this object.  ONLY those
        implementations which do NOT have a source of time, shall return
        the following DEFVAL."
    REFERENCE "
        See:    'xcmGenClientDataRowStatus'"
    DEFVAL      { '0000000000000000'H } -- no client data request date
    ::= { xcmGenClientDataEntry 3 }

xcmGenClientDataRequestID OBJECT-TYPE
    SYNTAX      XcmGlobalUniqueID
    MAX-ACCESS  read-create
    STATUS      current
    DESCRIPTION "
        The client data owner request ID which uniquely identifies the
        creation of this conceptual row in the 'xcmGenClientDataTable'.

        Usage:  This request ID shall ALWAYS be set (to a suitable
        value) by the client data owner, in the same PDU which creates
        each conceptual row in the 'xcmGenClientDataTable'."
    REFERENCE "
        See:    'xcmGenClientDataRowStatus'"
    DEFVAL      { ''H }                 -- no client data request ID
    ::= { xcmGenClientDataEntry 4 }

xcmGenClientDataProductID OBJECT-TYPE
    SYNTAX      ProductID
    MAX-ACCESS  read-create
    STATUS      current
    DESCRIPTION "
        The client data owner product ID corresponding to the current
        'owner' of this client data.

        Usage:  This product ID shall ALWAYS be set (to a suitable
        value) by the client data owner, in the same PDU which creates
        each conceptual row in the 'xcmGenClientDataTable'."
    REFERENCE "
        See:    'xcmGenClientDataRowStatus'
        See:    'ProductID' in IETF Host Resources MIB (RFC 1514)."
    DEFVAL      { xcmGenZeroDotZero }   -- no client data product ID
    ::= { xcmGenClientDataEntry 5 }

xcmGenClientDataLength OBJECT-TYPE
    SYNTAX      Cardinal32
    MAX-ACCESS  read-create
    STATUS      current
    DESCRIPTION "
        The client data length requested/granted for this
        conceptual row in the 'xcmGenClientDataTable'.

        Usage:  Conforming implementations need NOT support maximum
        client data length greater than 1 octet.

        Usage:  This data length shall ALWAYS be set (to a suitable
        value) by the client data owner, in the same PDU which creates
        each conceptual row in the 'xcmGenClientDataTable'."
    REFERENCE "
        See:    'xcmGenClientDataRowStatus'"
    DEFVAL      { 0 }                   -- no client data length
    ::= { xcmGenClientDataEntry 6 }

xcmGenClientDataString OBJECT-TYPE
    SYNTAX      OCTET STRING (SIZE (0..255))
    MAX-ACCESS  read-create
    STATUS      current
    DESCRIPTION "
        The client data string currently set into this conceptual
        row in the 'xcmGenClientDataTable'.

        Usage:  Conforming implementations need NOT support maximum
        client data length greater than 1 octet.

        Usage:  This data string need NOT be set (to a suitable
        value) by the client data owner, in the same PDU which creates
        each conceptual row in the 'xcmGenClientDataTable'."
    REFERENCE "
        See:    'xcmGenClientDataRowStatus'"
    DEFVAL      { ''H }                 -- no client data string
    ::= { xcmGenClientDataEntry 7 }

-- Reserved (deleted arc)   OBJECT IDENTIFIER ::= { xcmGeneralMIB 12 }

-- General Trap Client Group (Conditionally Mandatory)
--
-- Implementation of this group is conditionally mandatory, ie,
-- mandatory for systems which implement SNMP trap support
-- and optional for all other systems.
--
-- Note:   Systems implementing the Trap Client group
-- shall ALWAYS implement the Trap View group.

xcmGenTrapClient            OBJECT IDENTIFIER ::= { xcmGeneralMIB 13 }

xcmGenTrapClientTable OBJECT-TYPE
    SYNTAX      SEQUENCE OF XcmGenTrapClientEntry
    MAX-ACCESS  not-accessible
    STATUS      current
    DESCRIPTION "
        A table of SNMP trap clients (management stations or proxies)
        registered for trap delivery from this host system.

        Usage:  SNMP version/transport independent trap registration."
    REFERENCE "
        See:    Party group in Historic SNMPv2 Party MIB (RFC 1447)."
    ::= { xcmGenTrapClient 2 }

xcmGenTrapClientEntry OBJECT-TYPE
    SYNTAX      XcmGenTrapClientEntry
    MAX-ACCESS  not-accessible
    STATUS      current
    DESCRIPTION "
        An entry for an SNMP trap client (management station or proxy)
        registered for trap delivery from this host system."
    INDEX       { xcmGenTrapClientSNMPDomain,
                  xcmGenTrapClientSNMPAddress }
    ::= { xcmGenTrapClientTable 1 }

XcmGenTrapClientEntry ::= SEQUENCE {
        --  Trap Client
        xcmGenTrapClientSNMPDomain      XcmGenSNMPDomain,
        xcmGenTrapClientSNMPAddress     OCTET STRING,
        xcmGenTrapClientRowStatus       RowStatus,
        xcmGenTrapClientIndex           Ordinal32,
        xcmGenTrapClientRowPersistence  XcmGenRowPersistence,
        xcmGenTrapClientSNMPVersion     XcmGenSNMPVersion
    }

xcmGenTrapClientSNMPDomain OBJECT-TYPE
    SYNTAX      XcmGenSNMPDomain
    MAX-ACCESS  not-accessible
    STATUS      current
    DESCRIPTION "
        This object is used to specify the transport domain (below
        SNMP) which shall be used by this management agent to deliver
        SNMP traps to the trap client (management station or proxy)."
    REFERENCE "
        See:    'XcmGenSNMPDomain' textual convention in the
                XCMI General TC.
        See:    'snmp...Domain' object identifiers in the
                IETF SNMPv2 Transport Mappings (RFC 1449/1906)."
    ::= { xcmGenTrapClientEntry 1 }

xcmGenTrapClientSNMPAddress OBJECT-TYPE
    SYNTAX      OCTET STRING (SIZE (0..255))
    MAX-ACCESS  not-accessible
    STATUS      current
    DESCRIPTION "
        This object is used to specify the transport address (below
        SNMP) which shall be used by this management agent to deliver
        SNMP traps to the trap client (management station or proxy).

        Usage:  This transport address usually consists of an underlying
        network layer address with a suffixed transport selector."
    REFERENCE "
        See:    'SnmpUDPAddress' (IP addr, UDP port - Internet),
                'SNMPOSIAddress' (len, NSAP addr, TSelector - OSI),
                'SNMPNBPAddress' (object, type, zone - AppleTalk), and
                'SNMPIPXAddress' (net no, MAC addr, socket - NetWare)
                textual conventions in the
                IETF SNMPv2 Transport Mappings (RFC 1449/1906).
        See:    'XcmSNMPNetbiosAddress' (MAC addr, port - NetBIOS)
                textual conventions in the
                XCMI Comms Config TC."
    ::= { xcmGenTrapClientEntry 2 }

xcmGenTrapClientRowStatus OBJECT-TYPE
    SYNTAX      RowStatus
    MAX-ACCESS  read-create
    STATUS      current
    DESCRIPTION "
        This object manages the row status of this conceptual row in
        the 'xcmGenTrapClientTable'.

        Usage:  Conforming management agents shall ALWAYS support
        'active(1)' and 'createAndGo(4)', and should also support
        'destroy(6)' (for 'release' of trap client entry).

        Usage:  Conforming management agents should NOT support
        'notInService(2)', 'notReady(3)', or 'createAndWait(5)'."
    ::= { xcmGenTrapClientEntry 3 }

xcmGenTrapClientIndex OBJECT-TYPE
    SYNTAX      Ordinal32
    MAX-ACCESS  read-only
    STATUS      current
    DESCRIPTION "
        A unique value ASSIGNED by this host system to identify this
        conceptual row in the 'xcmGenTrapClientTable'.

        This object is used to specify the unique client index which was
        chosen FOR the trap client registered in this conceptual row
        (management station or proxy) at row creation and which shall be
        used by the trap client to create any associated conceptual
        rows in the 'xcmGenTrapViewTable'.

        Usage:  Conforming management agents need NOT preserve the
        value of this object across power cycles for 'nonvolatile' rows
        in the 'xcmGenTrapClientTable', but shall ALWAYS preserve the
        configured associations with (any) subordinate rows in the
        'xcmGenTrapViewTable'."
    ::= { xcmGenTrapClientEntry 4 }

xcmGenTrapClientRowPersistence OBJECT-TYPE
    SYNTAX      XcmGenRowPersistence
    MAX-ACCESS  read-create
    STATUS      current
    DESCRIPTION "
        This object is used to specify the persistence of this
        conceptual row in the 'xcmGenTrapClientTable' (and associated
        conceptual rows in the 'xcmGenTrapViewTable').

        Usage:  Conforming management agents shall ALWAYS support
        'volatile' (lost across power cycles), but NEED NOT support any
        other levels of persistence."
    DEFVAL      { volatile }            -- lost across power cycles
    ::= { xcmGenTrapClientEntry 5 }

xcmGenTrapClientSNMPVersion OBJECT-TYPE
    SYNTAX      XcmGenSNMPVersion
    MAX-ACCESS  read-create
    STATUS      current
    DESCRIPTION "
        This object is used to specify the exact SNMP version which was
        chosen by the trap client registered in this conceptual row and
        which shall be used by this management agent to deliver traps
        to the trap client (management station or proxy)."
    DEFVAL      { snmpV1Community }     -- SNMPv1 Standard (RFC 1157)
    ::= { xcmGenTrapClientEntry 6 }

-- General Trap View Group (Conditionally Mandatory)
--
-- Implementation of this group is conditionally mandatory, ie,
-- mandatory for systems which implement SNMP trap support
-- and optional for all other systems.
--
-- Note:   Systems implementing the Trap View group
-- shall ALWAYS implement the Trap Client group.

xcmGenTrapView              OBJECT IDENTIFIER ::= { xcmGeneralMIB 14 }

xcmGenTrapViewTable OBJECT-TYPE
    SYNTAX      SEQUENCE OF XcmGenTrapViewEntry
    MAX-ACCESS  not-accessible
    STATUS      current
    DESCRIPTION "
        A table of SNMP trap object subtrees (ie, trap scopes)
        registered for trap delivery from this host system to the
        associated trap client (management station or proxy).

        Usage:  SNMP version/transport independent trap registration."
    REFERENCE "
        See:    View group in Historic SNMPv2 Party MIB (RFC 1447)."
    ::= { xcmGenTrapView 2 }

xcmGenTrapViewEntry OBJECT-TYPE
    SYNTAX      XcmGenTrapViewEntry
    MAX-ACCESS  not-accessible
    STATUS      current
    DESCRIPTION "
        An entry for an SNMP trap object subtree (ie, trap scope)
        registered for trap delivery from this host system to the
        associated trap client (management station or proxy)."
    INDEX       { xcmGenTrapClientIndex,
                  xcmGenTrapViewObjectSubtree }
    ::= { xcmGenTrapViewTable 1 }

XcmGenTrapViewEntry ::= SEQUENCE {
        --  Trap View (Scope)
        xcmGenTrapViewObjectSubtree    OBJECT IDENTIFIER,
        xcmGenTrapViewRowStatus        RowStatus
    }

xcmGenTrapViewObjectSubtree OBJECT-TYPE
    SYNTAX      OBJECT IDENTIFIER
    MAX-ACCESS  not-accessible
    STATUS      current
    DESCRIPTION "
        This object is used to specify the object subtree (within MIBs)
        which is 'in scope' for this trap view."
    ::= { xcmGenTrapViewEntry 1 }

xcmGenTrapViewRowStatus OBJECT-TYPE
    SYNTAX      RowStatus
    MAX-ACCESS  read-create
    STATUS      current
    DESCRIPTION "
        This object manages the row status of this conceptual row in
        the 'xcmGenTrapViewTable'.

        Usage:  Conforming management agents shall ALWAYS support
        'active(1)' and 'createAndGo(4)', and should also support
        'destroy(6)' (for 'release' of trap view entry).

        Usage:  Conforming management agents should NOT support
        'notInService(2)', 'notReady(3)', or 'createAndWait(5)'."
    ::= { xcmGenTrapViewEntry 2 }

--
--          General MIB Conformance Information
--
--          With Mandatory and Optional Conformance Groups

xcmGeneralMIBConformance
             OBJECT IDENTIFIER ::= { xcmGeneralMIB 2 }
xcmGeneralMIBGroups
             OBJECT IDENTIFIER ::= { xcmGeneralMIBConformance 2 }

--
--          Compliance Statements
--

xcmGeneralMIBCompliance MODULE-COMPLIANCE
    STATUS      current
    DESCRIPTION "
        The compliance statements for SNMP management agents that
        implement the General MIB."
    MODULE -- this module
    MANDATORY-GROUPS {
        xcmGenBaseGroup
    }

    GROUP       xcmGenCurrentLocalizationGroup
    DESCRIPTION "
        Implementation of this group is conditionally mandatory:
        Mandatory for all systems which instrument MIB objects of type
        InternationalDisplayString or implement the
        xcmGenLocalizationGroup group."

    GROUP       xcmGenLocalizationGroup
    DESCRIPTION "
        Implementation of this group is conditionally mandatory:
        Mandatory for all systems which instrument MIB objects of type
        InternationalDisplayString or implement the
        xcmGenCurrentLocalizationGroup group."

    GROUP       xcmGenCodeIndexedStringGroup
    DESCRIPTION "
        Implementation of this group is conditionally mandatory:
        Mandatory for all systems which instrument MIB objects of type
        CodeIndexedStringIndex or implement the
        xcmGenCodedCharSetGroup group."

    GROUP       xcmGenCodedCharSetGroup
    DESCRIPTION "
        Implementation of this group is conditionally mandatory:
        Mandatory for all systems which instrument MIB objects of type
        CodeIndexedStringIndex or implement the
        xcmGenCodeIndexedStringGroup group."

    GROUP       xcmGenFixedLocalizationGroup
    DESCRIPTION "
        Implementation of this group is optional for all systems,
        however it shall ALWAYS be implemented by systems which ALSO
        implement objects of type 'FixedLocaleDisplayString' and the
        'xcmGenLocalizationGroup'."

    --
    --

    GROUP       xcmGenReconfGroup
    DESCRIPTION "
        Implementation of this group is conditionally mandatory, ie,
        mandatory for systems which support tree structured
        atomic reconfiguration, and optional for all other systems.

        Implementation of this group is conditionally mandatory,
        however it shall ALWAYS be implemented by systems which
        implement the 'xcmGenOptionGroup'.

        Usage:  Systems which implement the 'xcmGenReconfGroup'
        and 'xcmGenOptionGroup' shall ALWAYS also implement
        the 'xcmGenLockGroup' (for advisory contention locks)."

    GROUP       xcmGenOptionGroup
    DESCRIPTION "
        Implementation of this group is conditionally mandatory, ie,
        mandatory for systems which support tree structured
        atomic reconfiguration, and optional for all other systems.
--
        Implementation of this group is conditionally mandatory,
        however it shall ALWAYS be implemented by systems which
        implement the 'xcmGenReconfGroup'.
--
        Usage:  Systems which implement the 'xcmGenReconfGroup'
        and 'xcmGenOptionGroup' shall ALWAYS also implement
        the 'xcmGenLockGroup' (for advisory contention locks)."

    GROUP       xcmGenClientDataGroup
    DESCRIPTION "
        Implementation of this group is conditionally mandatory, ie,
        mandatory for systems which support 'client data' for remote
        management stations, and optional for all other systems.

        Usage:  Conforming implementations shall ALWAYS preserve active
        'client data' objects across management agent power cycles."

    GROUP       xcmGenTrapClientGroup
    DESCRIPTION "
        Implementation of this group is conditionally mandatory, ie,
        mandatory for systems which implement SNMP trap support
        and optional for all other systems.

        Note:   Systems implementing the Trap Client group
        shall ALWAYS implement the Trap View group."

    GROUP       xcmGenTrapViewGroup
    DESCRIPTION "
        Implementation of this group is conditionally mandatory, ie,
        mandatory for systems which implement SNMP trap support
        and optional for all other systems.

        Note:   Systems implementing the Trap View group
        shall ALWAYS implement the Trap Client group."

    OBJECT      xcmGenCurrentLocalizationIndex 
    MIN-ACCESS  read-only
    DESCRIPTION "
        It is conformant to implement this object as read-only"

    OBJECT      xcmGenCurrLocalizationRowStatus
    SYNTAX      INTEGER { active(1) }   -- subset of RowStatus
    MIN-ACCESS  read-only
    DESCRIPTION "
        It is conformant to implement this object as read-only, and
        only one of the enumerated values for the 'RowStatus' textual
        convention need be supported, specifically:  active(1)."

    OBJECT      xcmGenLocalizationRowStatus
    SYNTAX      INTEGER { active(1) }   -- subset of RowStatus
    MIN-ACCESS  read-only
    DESCRIPTION "
        It is conformant to implement this object as read-only, and
        only one of the enumerated values for the 'RowStatus' textual
        convention need be supported, specifically:  active(1)."

    OBJECT      xcmGenLocalizationASCIIName 
    MIN-ACCESS  read-only
    DESCRIPTION "
        It is conformant to implement this object as read-only"

    OBJECT      xcmGenLocalizationName 
    MIN-ACCESS  read-only
    DESCRIPTION "
        It is conformant to implement this object as read-only"

    OBJECT      xcmGenLocalizationLanguage 
    MIN-ACCESS  read-only
    DESCRIPTION "
        It is conformant to implement this object as read-only"

    OBJECT      xcmGenLocalizationCountry 
    MIN-ACCESS  read-only
    DESCRIPTION "
        It is conformant to implement this object as read-only"

    OBJECT      xcmGenLocalizationCharSet 
    MIN-ACCESS  read-only
    DESCRIPTION "
        It is conformant to implement this object as read-only"

    OBJECT      xcmGenCodeIndexedStringRowStat
    SYNTAX      INTEGER { active(1) }   -- subset of RowStatus
    MIN-ACCESS  read-only
    DESCRIPTION "
        It is conformant to implement this object as read-only, and
        only one of the enumerated values for the 'RowStatus' textual
        convention need be supported, specifically:  active(1)."

    OBJECT      xcmGenCodeIndexedStringData 
    SYNTAX      OCTET STRING (SIZE (0..32))
    MIN-ACCESS  read-only
    DESCRIPTION "
        It is conformant to implement this object as read-only, and
        only 32 octets maximum string length need be supported."

    OBJECT      xcmGenCodedCharSetRowStatus
    SYNTAX      INTEGER { active(1) }   -- subset of RowStatus
    MIN-ACCESS  read-only
    DESCRIPTION "
        It is conformant to implement this object as read-only, and
        only one of the enumerated values for the 'RowStatus' textual
        convention need be supported, specifically:  active(1)."

    OBJECT      xcmGenCodedCharSetASCIIName 
    MIN-ACCESS  read-only
    DESCRIPTION "
        It is conformant to implement this object as read-only"

    OBJECT      xcmGenFixedLocalizationIndex 
    MIN-ACCESS  read-only
    DESCRIPTION "
        It is conformant to implement this object as read-only"

    OBJECT      xcmGenFixedLocalizationRowStat
    SYNTAX      INTEGER { active(1) }   -- subset of RowStatus
    MIN-ACCESS  read-only
    DESCRIPTION "
        It is conformant to implement this object as read-only, and
        only one of the enumerated values for the 'RowStatus' textual
        convention need be supported, specifically:  active(1)."

    --
    --

    OBJECT      xcmGenReconfRowStatus
    SYNTAX      INTEGER { active(1) }   -- subset of RowStatus
    MIN-ACCESS  read-write
    DESCRIPTION "
        It is conformant to implement this object as read-write, and
        only one of the enumerated values for the 'RowStatus' textual
        convention need be supported, specifically:  active(1)."

    OBJECT      xcmGenReconfOptionIndex
    MIN-ACCESS  read-write
    DESCRIPTION "
        It is conformant to implement this object as read-write"

    OBJECT      xcmGenReconfOptionState
    MIN-ACCESS  read-write
    DESCRIPTION "
        It is conformant to implement this object as read-write"

    OBJECT      xcmGenReconfErrorIndex
    MIN-ACCESS  read-write
    DESCRIPTION "
        It is conformant to implement this object as read-write"

    OBJECT      xcmGenReconfErrorStatus
    MIN-ACCESS  read-write
    DESCRIPTION "
        It is conformant to implement this object as read-write"

    OBJECT      xcmGenOptionRowStatus
    SYNTAX      INTEGER {               -- subset of RowStatus
        active(1),
--      notInService(2),
--      notReady(3),
        createAndGo(4)
--      createAndWait(5),
--      destroy(6)
        }
    MIN-ACCESS  read-write
    DESCRIPTION "
        It is conformant to implement this object as read-write, and
        those specified enumerated values for the 'RowStatus' textual
        convention need be supported."

    OBJECT      xcmGenOptionTypeOID
    MIN-ACCESS  read-write
    DESCRIPTION "
        It is conformant to implement this object as read-write"

    OBJECT      xcmGenOptionValueSyntax
    MIN-ACCESS  read-write
    DESCRIPTION "
        It is conformant to implement this object as read-write"

    OBJECT      xcmGenOptionValueInteger
    MIN-ACCESS  read-write
    DESCRIPTION "
        It is conformant to implement this object as read-write"

    OBJECT      xcmGenOptionValueOID
    MIN-ACCESS  read-write
    DESCRIPTION "
        It is conformant to implement this object as read-write"

    OBJECT      xcmGenOptionValueString
    SYNTAX      OCTET STRING (SIZE (0..32))
    MIN-ACCESS  read-write
    DESCRIPTION "
        It is conformant to implement this object as read-write, and
        only 32 octets maximum string length need be supported."

    OBJECT      xcmGenOptionValueLocalization
    MIN-ACCESS  read-write
    DESCRIPTION "
        It is conformant to implement this object as read-write"

    OBJECT      xcmGenOptionValueCodedCharSet
    MIN-ACCESS  read-write
    DESCRIPTION "
        It is conformant to implement this object as read-write"

    OBJECT      xcmGenOptionNextIndex
    MIN-ACCESS  read-write
    DESCRIPTION "
        It is conformant to implement this object as read-write"

    OBJECT      xcmGenOptionPreviousIndex
    MIN-ACCESS  read-write
    DESCRIPTION "
        It is conformant to implement this object as read-write"

    OBJECT      xcmGenOptionFamilyIndex
    MIN-ACCESS  read-write
    DESCRIPTION "
        It is conformant to implement this object as read-write"

    OBJECT      xcmGenClientDataRowStatus
    SYNTAX      INTEGER { active(1) }   -- subset of RowStatus
    MIN-ACCESS  read-only
    DESCRIPTION "
        It is conformant to implement this object as above, and only
        only one of the enumerated values for the 'RowStatus' textual
        convention need be supported, specifically:  active(1)."

    OBJECT      xcmGenClientDataLength
    SYNTAX      INTEGER (0..1)
    MIN-ACCESS  read-only
    DESCRIPTION "
        It is conformant to implement this object as above, and
        only 1 octet maximum client data length need be supported."

    OBJECT      xcmGenClientDataString
    SYNTAX      OCTET STRING (SIZE (0..1))
    DESCRIPTION "
        It is conformant to implement this object as above, and
        only 1 octet maximum client data length need be supported."

--  OBJECT      xcmGenTrapClientSNMPDomain
--  SYNTAX      INTEGER {
--  }
--  DESCRIPTION "
--      It is conformant to implement this object as above, and
--      no specific enumerated values for the 'XcmGenSNMPDomain'
--      textual convention need be supported."

--  OBJECT      xcmGenTrapClientSNMPAddress
--  SYNTAX      OCTET STRING (SIZE (0..32))
--  DESCRIPTION "
--      It is conformant to implement this object as above, and
--      only 32 octets maximunm string length need be supported."

    OBJECT      xcmGenTrapClientRowStatus
    SYNTAX      INTEGER {               -- subset of RowStatus
        active(1),
--      notInService(2),
--      notReady(3),
        createAndGo(4)
--      createAndWait(5),
--      destroy(6)
        }
    MIN-ACCESS  read-only
    DESCRIPTION "
        It is conformant to implement this object as read-only, and only
        those specified enumerated values for the 'RowStatus' textual
        convention need be supported."

    OBJECT      xcmGenTrapClientRowPersistence
    SYNTAX      INTEGER {
        other(1),
        unknown(2),
        volatile(3)                     -- lost across power cycles
--      nonvolatile(4),                    saved across power cycles
--      permanent(5),                      read-write, and no deletion
--      readonly(6)                        read-only, and no deletion
    }
    MIN-ACCESS  read-only
    DESCRIPTION "
        It is conformant to implement this object as read-only, and only
        those specified enumerated values for the 'XcmGenRowPersistence'
        textual convention need be supported."

    OBJECT      xcmGenTrapClientSNMPVersion
    SYNTAX      INTEGER {
        unknown(1),                     -- indeterminate
        other(2),                       -- some other version
        snmpV1Community(3)
--      snmpV1Party(4),
--      snmpV2Party(5),
--      snmpV2Community(6),
--      snmpV2Usec(7),
--      snmpV2Star(8),
--      snmpV2Secure(9)
    }
    MIN-ACCESS  read-only
    DESCRIPTION "
        It is conformant to implement this object as read-only, and only
        those specified enumerated values for the 'XcmGenSNMPVersion'
        textual convention need be supported."

    OBJECT      xcmGenTrapViewRowStatus
    SYNTAX      INTEGER {               -- subset of RowStatus
        active(1),
--      notInService(2),
--      notReady(3),
        createAndGo(4)
--      createAndWait(5),
--      destroy(6)
        }
    MIN-ACCESS  read-only
    DESCRIPTION "
        It is conformant to implement this object as read-only, and only
        those specified enumerated values for the 'RowStatus' textual
        convention need be supported."

    ::= { xcmGeneralMIBConformance 3 }

--
--          Conformance Groups
--

xcmGenBaseGroup OBJECT-GROUP
    OBJECTS {
        --  General MIB Info
        xcmGenBaseRowStatus,
        xcmGenBaseSystemHrDeviceIndex,
        --  General MIB Capabilities Info
        xcmGenBaseGroupSupport,
        xcmGenBaseGroupCreateSupport,
        xcmGenBaseGroupUpdateSupport,
        xcmGenBaseClientDataMaxSupport,
        xcmGenBaseOptionSyntaxSupport,
        xcmGenBaseReconfStateSupport,
        xcmGenBaseSNMPDomainSupport,
        xcmGenBaseSNMPTrapSupport,
        xcmGenBaseSNMPVersionSupport
    }
    STATUS      current
    DESCRIPTION "
        General Base Group (XCMI General MIB capabilities)"
    ::= { xcmGeneralMIBGroups 1 }

xcmGenCurrentLocalizationGroup OBJECT-GROUP
    OBJECTS { 
        xcmGenCurrentLocalizationIndex,
        xcmGenCurrLocalizationRowStatus
    }
    STATUS  current
    DESCRIPTION "
        General Current Localization Group (dynamic locales)"
    ::= { xcmGeneralMIBGroups 3 }

xcmGenLocalizationGroup OBJECT-GROUP
    OBJECTS {
        xcmGenLocalizationRowStatus,
        xcmGenLocalizationASCIIName,
        xcmGenLocalizationName,
        xcmGenLocalizationLanguage,
        xcmGenLocalizationCountry,
        xcmGenLocalizationCharSet
    }
    STATUS  current
    DESCRIPTION "
        General Localization Group (supported dynamic/static locales)"
    ::= { xcmGeneralMIBGroups 4 }

xcmGenCodeIndexedStringGroup OBJECT-GROUP
    OBJECTS { 
        xcmGenCodeIndexedStringRowStat,
        xcmGenCodeIndexedStringData
    }
    STATUS  current
    DESCRIPTION "
        General Coded String Group (code set conversions)"
    ::= { xcmGeneralMIBGroups 5 }

xcmGenCodedCharSetGroup OBJECT-GROUP
    OBJECTS {
        xcmGenCodedCharSetRowStatus,
        xcmGenCodedCharSetASCIIName
    }
    STATUS  current
    DESCRIPTION "
        General Coded Character Set Group (supported code sets)"
    ::= { xcmGeneralMIBGroups 6 }

xcmGenFixedLocalizationGroup OBJECT-GROUP
    OBJECTS {
        xcmGenFixedLocalizationIndex,
        xcmGenFixedLocalizationRowStat
    }
    STATUS      current
    DESCRIPTION "
        General Fixed Localization Group (static locales)"
    ::= { xcmGeneralMIBGroups 7 }

    --
    --

xcmGenReconfGroup OBJECT-GROUP
    OBJECTS {
        --  General Reconf Simple Objects
        xcmGenReconfActivations,
        --  General Reconf Info
        xcmGenReconfRowStatus,
        xcmGenReconfOptionIndex,
        xcmGenReconfOptionState,
        xcmGenReconfErrorIndex,
        xcmGenReconfErrorStatus
    }
    STATUS      current
    DESCRIPTION "
        General Reconf Group (reconfiguration requests)"
    ::= { xcmGeneralMIBGroups 9 }

xcmGenOptionGroup OBJECT-GROUP
    OBJECTS {
        --  General Option Info
        xcmGenOptionRowStatus,
        xcmGenOptionTypeOID,
        xcmGenOptionValueSyntax,
        xcmGenOptionValueInteger,
        xcmGenOptionValueOID,
        xcmGenOptionValueString,
        xcmGenOptionValueLocalization,
        xcmGenOptionValueCodedCharSet,
        --  General Option Common Cross References
        xcmGenOptionNextIndex,
        xcmGenOptionPreviousIndex,
        xcmGenOptionFamilyIndex
    }
    STATUS      current
    DESCRIPTION "
        General Option Group (reconfiguration options)"
    ::= { xcmGeneralMIBGroups 10 }

xcmGenClientDataGroup OBJECT-GROUP
    OBJECTS {
        --  General Client Data Simple Objects
        xcmGenClientDataEntryCount,
        xcmGenClientDataLastIndex,
        --  General Client Data Info
        xcmGenClientDataRowStatus,
        xcmGenClientDataRequestDate,
        xcmGenClientDataRequestID,
        xcmGenClientDataProductID,
        xcmGenClientDataLength,
        xcmGenClientDataString
    }
    STATUS      current
    DESCRIPTION "
        General Client Data Group (network device installs/upgrades)"
    ::= { xcmGeneralMIBGroups 11 }

--  ::= { xcmGeneralMIBGroups 12 } - Reserved (deleted arc)

xcmGenTrapClientGroup OBJECT-GROUP
    OBJECTS {
        xcmGenTrapClientRowStatus,
        xcmGenTrapClientIndex,
        xcmGenTrapClientRowPersistence,
        xcmGenTrapClientSNMPVersion
    }
    STATUS      current
    DESCRIPTION "
        General Trap Client Group (trap destination domains/addresses)"
    ::= { xcmGeneralMIBGroups 13 }

xcmGenTrapViewGroup OBJECT-GROUP
    OBJECTS {
        xcmGenTrapViewRowStatus
    }
    STATUS      current
    DESCRIPTION "
        General Trap View Group (trap requested object subtrees)"
    ::= { xcmGeneralMIBGroups 14 }

END
