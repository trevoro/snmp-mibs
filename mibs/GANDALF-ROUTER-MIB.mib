GANDALF-ROUTER-MIB

--                     Gandalf Data Limited
--                     130 Colonnade Rd. South,
--                     Nepean, Ontario,
--                     Canada, K2E 7M4
--                     (613) 723-6500

--                     Sept 22, 1994

--                     Version 1.2.2

--                     This document defines router OBJECTs in the
--                     Gandalf enterprise.

DEFINITIONS ::= BEGIN

IMPORTS
    enterprises, Counter, IpAddress, TimeTicks
       FROM RFC1155-SMI
    OBJECT-TYPE
       FROM RFC-1212
    TRAP-TYPE
       FROM RFC-1215
    ifIndex, DisplayString
       FROM RFC1213-MIB;

-- To manage the creation and deletion of conceptual rows the textual
-- convention 'RowStatus' from RFC 1443 is used and is defined as
-- follows:

   RowStatus ::= INTEGER
                 {
                 active(1),
                 notInService(2),
                 notReady(3),
                 createAndGo(4),
                 createAndWait(5),
                 destroy(6)
                 }

-- Objects whose syntax clause is of type RowStatus conform to the 
-- definitions and manager-agent interactions as described in 
-- 'draft-walbusser-v1rows-00.txt' dated October 19, 1993. This 
-- agents implementation will set all RowStatus objects to the 
-- 'notReady' state when the action on the RowStatus object is
-- 'createAndWait'. Objects in a active conceptual row can be modified 
-- without changing the RowStatus state however syntax and semantic 
-- rules may cause rejects (when in doubt set the RowStatus to 
-- 'notInService'). Setting any other object (other than the RowStatus 
-- object) to a legal value when the conceptual row does not exist 
-- will be accepted (the side effect on the RowStatus object when 
-- read will be 'notReady').

gandalf                     OBJECT IDENTIFIER ::= { enterprises 64 }
gandalf-router              OBJECT IDENTIFIER ::= { gandalf 11 }

--
--
-- Product MIB definitions in this document.

grGenerationX             OBJECT IDENTIFIER ::= { gandalf-router 1 }

-- Gandalf products that supprt the grGenerationX sub-tree also
-- support the following standardized MIBs:
--
--        RFC 1213 (MIB II, except egp)
--        RFC 1229 (Generic-Interfaces MIB, except ifExtnsTestTable)
--        RFC 1239 (Reassignment of Experimental MIBs to Standard MIBs)
--        RFC 1354 (IP Forwarding Table MIB)
--        RFC 1398 (Ethernet-like Interfaces MIB)
--        RFC 1471 (PPP LCP MIB)
--        RFC 1472 (PPP Security MIB)
--        RFC 1473 (PPP IPNCP MIB)
--        RFC 1474 (PPP BNCP MIB)
--        RFC 1493 (Bridge MIB)
--
-- depending on product functionality (ie: local vs. remote router). 
-- All read-write objects in the above MIBs are supported. Additional
-- MIB's may be supported other than those listed above.


--
--
-- groups under grGenerationX

grGeneral                 OBJECT IDENTIFIER ::= { grGenerationX 1 }
grPhysPortGroup           OBJECT IDENTIFIER ::= { grGenerationX 2 }
grLogicalGroup            OBJECT IDENTIFIER ::= { grGenerationX 3 }
grBridgeGroup             OBJECT IDENTIFIER ::= { grGenerationX 4 }
grIpxGroup                OBJECT IDENTIFIER ::= { grGenerationX 5 }
grIpGroup                 OBJECT IDENTIFIER ::= { grGenerationX 6 }
grSnmpGroup               OBJECT IDENTIFIER ::= { grGenerationX 7 }
grPppGroup                OBJECT IDENTIFIER ::= { grGenerationX 8 }

--
--
--
--        GENERAL PARAMETER GROUP OBJECTS
--        ===============================
--

    grSerNum OBJECT-TYPE
        SYNTAX  DisplayString (SIZE (1..16))
        ACCESS  read-only
        STATUS  mandatory
        DESCRIPTION
                "The serial number of this unit."
        ::= { grGeneral 1 }


    grSystemName OBJECT-TYPE
        SYNTAX  DisplayString (SIZE (1..48))
        ACCESS  read-write
        STATUS  mandatory
        DESCRIPTION
                "The name given to this router."
        ::= { grGeneral 2 }


    grSystemPasswd OBJECT-TYPE
        SYNTAX  DisplayString (SIZE (1..16))
        ACCESS  read-write
        STATUS  mandatory
        DESCRIPTION
                "The console password for direct or telnet console access."
        ::= { grGeneral 3 }


    grdBaseRev OBJECT-TYPE
        SYNTAX  DisplayString (SIZE (1..16))
        ACCESS  read-only
        STATUS  mandatory
        DESCRIPTION
                "Indicates revision of the configuration database."
        ::= { grGeneral 4 }


    grSoftwareRev OBJECT-TYPE
        SYNTAX DisplayString (SIZE (1..16))
        ACCESS read-only
        STATUS mandatory
        DESCRIPTION
            "This attribute provides the application (router) software
            revision number."
        ::= { grGeneral 5}

    grFirmwareRev OBJECT-TYPE
        SYNTAX DisplayString (SIZE (1..16))
        ACCESS read-only
        STATUS mandatory
        DESCRIPTION
            "This attribute provides the boot S/W revision number."
        ::= { grGeneral 6 }


    grReset OBJECT-TYPE
        SYNTAX  INTEGER {
                    hardReset(1)
                }
        ACCESS  read-write
        STATUS  mandatory
        DESCRIPTION
                "Resets the box. A read on this object will return a 
                zero value."
        ::= { grGeneral 7 }


    grDateAndTime OBJECT-TYPE
        SYNTAX  OCTET STRING (SIZE(11))
        ACCESS  read-write
        STATUS  mandatory
        DESCRIPTION
                "This object displays the current date and time in the 
                format as specified in RFC 1443 for the DateAndTime
                textual convention."
        ::= { grGeneral 8 }


    grSwitchPosition OBJECT-TYPE
        SYNTAX  INTEGER {
                    console(1),
                    wan(2)
                }
        ACCESS  read-only
        STATUS  mandatory
        DESCRIPTION
                "This object indicates the position of the Console/WAN
                switch position."
        ::= { grGeneral 9 }
--
--
--
--      PHYSICAL PORT GROUP OBJECTS
--      ===========================
--

    grPhysNameTable OBJECT-TYPE
        SYNTAX  SEQUENCE OF GrPhysNameEntry
        ACCESS  not-accessible
        STATUS  mandatory
        DESCRIPTION
                "A table containing assigned Ascii names to the
                physical ports"
        ::= { grPhysPortGroup 1 }


        grPhysNameEntry OBJECT-TYPE
            SYNTAX  GrPhysNameEntry
            ACCESS  not-accessible
            STATUS  mandatory
            DESCRIPTION
                    "Each entry of this table contains a name that has
                    been assigned by the router to this physical interface."
            INDEX   { ifIndex }
            ::= { grPhysNameTable 1 }


        GrPhysNameEntry ::=
            SEQUENCE {
                grPhysPortName
                   DisplayString
            }


        grPhysPortName OBJECT-TYPE
            SYNTAX  DisplayString (SIZE(1..16))
            ACCESS  read-only
            STATUS  mandatory
            DESCRIPTION
                    "This object indicates the Ascii name assigned by
                    the router to this physical port."
            ::= { grPhysNameEntry 1 }


    grPhysPortTable OBJECT-TYPE
        SYNTAX  SEQUENCE OF GrPhysPortEntry
        ACCESS  not-accessible
        STATUS  mandatory
        DESCRIPTION
                "A table containing information about physical WAN
                configuration information."
        ::= { grPhysPortGroup 2 }


        grPhysPortEntry OBJECT-TYPE
            SYNTAX  GrPhysPortEntry
            ACCESS  not-accessible
            STATUS  mandatory
            DESCRIPTION
                    "Each entry of this table contains information about
                    a specific physical WAN interface."
            INDEX   { ifIndex }
            ::= { grPhysPortTable 1 }


        GrPhysPortEntry ::=
            SEQUENCE {
                grPhysPortWanType
                   INTEGER,
                grPhysPortSignalling
                   INTEGER,
                grPhysPortSpeed
                   INTEGER,
                grPhysPortCallType
                   INTEGER,
                grPhysPortHoldOff
                   INTEGER,
                grPhysPortPool
                   DisplayString
            }


        grPhysPortWanType OBJECT-TYPE
            SYNTAX  INTEGER {
                        nonSwitched(1),
                        v25bis(2),
                        controlSignal(3)
                    }
            ACCESS  read-write
            STATUS  mandatory
            DESCRIPTION
                    "Determines the call setup/teardown 
                    signalling to the attached device."
            ::= { grPhysPortEntry 1 }


        grPhysPortSignalling OBJECT-TYPE
            SYNTAX  INTEGER {
                        rs232(1),
                        v11(2),
                        v35(3)
                    }
            ACCESS  read-only
            STATUS  mandatory
            DESCRIPTION
                    "This object indicates the type of physical 
                    interface signalling used to attached device."
            ::= { grPhysPortEntry 2 }


        grPhysPortSpeed OBJECT-TYPE
            SYNTAX  INTEGER
            ACCESS  read-write
            STATUS  mandatory
            DESCRIPTION
                    "This object indicates the speed of the physical
                    interface."
            ::= { grPhysPortEntry 3 }


        grPhysPortCallType OBJECT-TYPE
            SYNTAX  INTEGER {
                        originate(1),
                        answer(2),
                        both(3)
                    }
            ACCESS  read-write
            STATUS  mandatory
            DESCRIPTION
                    "This object indicates whether or not it will
                    originate calls only, accept calls only or both."
            ::= { grPhysPortEntry 4 }


        grPhysPortHoldOff OBJECT-TYPE
            SYNTAX  INTEGER (0..99)
            ACCESS  read-write
            STATUS  mandatory
            DESCRIPTION
                    "This object specifies the time required for the
                    port to remain idle before the next call can be
                    issued."
            ::= { grPhysPortEntry 5 }


        grPhysPortPool OBJECT-TYPE
            SYNTAX  DisplayString (SIZE(1..16))
            ACCESS  read-write
            STATUS  mandatory
            DESCRIPTION
                    "This object defines the resource pool that this
                    physical interface belongs to."
            ::= { grPhysPortEntry 6 }
--
--
--
--     Physical WAN Port Status Table.
--

    grPhysWanStatsTable OBJECT-TYPE
        SYNTAX  SEQUENCE OF GrPhysWanStatsEntry
        ACCESS  not-accessible
        STATUS  mandatory
        DESCRIPTION
                "A table containing information about physical WAN
                statistics."
        ::= { grPhysPortGroup 3 }


        grPhysWanStatsEntry OBJECT-TYPE
            SYNTAX  GrPhysWanStatsEntry
            ACCESS  not-accessible
            STATUS  mandatory
            DESCRIPTION
                    "Each entry of this table contains information about
                    a specific physical WAN interface. This table
                    represents additional information not provided in
                    the MIB II Interface table for WAN type interfaces."
            INDEX   { ifIndex }
            ::= { grPhysWanStatsTable 1 }


        GrPhysWanStatsEntry ::=
            SEQUENCE {
                grPhysWanStRxCrcErrs
                   Counter,
                grPhysWanStRxOverRunErrs
                   Counter,
                grPhysWanStTxUnderRunErrs
                   Counter,
                grPhysWanStRxAborts
                   Counter,
                grPhysWanStTxAborts
                   Counter,
                grPhysWanStRxOctetErrors
                   Counter,
                grPhysWanStTxOctetErrors
                   Counter,
                grPhysWanStLogicalIfIndex
                   OCTET STRING,
                grPhysWanStInCalls
                   Counter,
                grPhysWanStInFails
                   Counter,
                grPhysWanStInSecurityFails
                   Counter,
                grPhysWanStOutCalls
                   Counter,
                grPhysWanStOutFails
                   Counter,
                grPhysWanStOutSecurityFails
                   Counter
            }

        grPhysWanStRxCrcErrs OBJECT-TYPE
            SYNTAX  Counter
            ACCESS  read-only
            STATUS  mandatory
            DESCRIPTION
                    "The total number of frames that contained CRC errors."
            ::= { grPhysWanStatsEntry 1 }


        grPhysWanStRxOverRunErrs OBJECT-TYPE
            SYNTAX  Counter
            ACCESS  read-only
            STATUS  mandatory
            DESCRIPTION
                    "The total number of times that this interface has
                    encountered an overrun condition."
            ::= { grPhysWanStatsEntry 2 }


        grPhysWanStTxUnderRunErrs OBJECT-TYPE
            SYNTAX  Counter
            ACCESS  read-only
            STATUS  mandatory
            DESCRIPTION
                    "The total number of times that this interface has
                    encountered an underrun condition."
            ::= { grPhysWanStatsEntry 3 }


        grPhysWanStRxAborts OBJECT-TYPE
            SYNTAX  Counter
            ACCESS  read-only
            STATUS  mandatory
            DESCRIPTION
                    "The total number of received frames that were aborted."
            ::= { grPhysWanStatsEntry 4 }


        grPhysWanStTxAborts OBJECT-TYPE
            SYNTAX  Counter
            ACCESS  read-only
            STATUS  mandatory
            DESCRIPTION
                    "The total number of transmitted frames that were
                    aborted."
            ::= { grPhysWanStatsEntry 5 }


        grPhysWanStRxOctetErrors OBJECT-TYPE
            SYNTAX  Counter
            ACCESS  read-only
            STATUS  mandatory
            DESCRIPTION
                    "The total number of octets that were received that
                    were in error."
            ::= { grPhysWanStatsEntry 6 }


        grPhysWanStTxOctetErrors OBJECT-TYPE
            SYNTAX  Counter
            ACCESS  read-only
            STATUS  mandatory
            DESCRIPTION
                    "The total number of octets that were transmitted that
                    were in error."
            ::= { grPhysWanStatsEntry 7 }


        grPhysWanStLogicalIfIndex OBJECT-TYPE
            SYNTAX  OCTET STRING
            ACCESS  read-only
            STATUS  mandatory
            DESCRIPTION
                    "This object indicates the logical port indexes
                    (ifIndex) of all current calls if any exist. Each
                    octet in the string represents one ifIndex. If
                    the WAN port is idle (disconnected) then this
                    object will return a zero length string."
            ::= { grPhysWanStatsEntry 8 }


        grPhysWanStInCalls OBJECT-TYPE
            SYNTAX  Counter
            ACCESS  read-only
            STATUS  mandatory
            DESCRIPTION
                    "The total number of inbound call received by
                    this interface including those that failed."
            ::= { grPhysWanStatsEntry 9 }


        grPhysWanStInFails OBJECT-TYPE
            SYNTAX  Counter
            ACCESS  read-only
            STATUS  mandatory
            DESCRIPTION
                    "The total number of inbound calls that failed by
                    this interface excluding those that failed for 
                    security reasons."
            ::= { grPhysWanStatsEntry 10 }


        grPhysWanStInSecurityFails OBJECT-TYPE
            SYNTAX  Counter
            ACCESS  read-only
            STATUS  mandatory
            DESCRIPTION
                    "The total number of inbound calls that failed
                    because of authentication failures by this
                    interface."
            ::= { grPhysWanStatsEntry 11 }


        grPhysWanStOutCalls OBJECT-TYPE
            SYNTAX  Counter
            ACCESS  read-only
            STATUS  mandatory
            DESCRIPTION
                    "The total number of outbound calls attempted by
                    this interface including those that failed."
            ::= { grPhysWanStatsEntry 12 }


        grPhysWanStOutFails OBJECT-TYPE
            SYNTAX  Counter
            ACCESS  read-only
            STATUS  mandatory
            DESCRIPTION
                    "The total number of failed outbound call attempts
                    by this interface excluding those that failed for
                    security reasons."
            ::= { grPhysWanStatsEntry 13 }


        grPhysWanStOutSecurityFails OBJECT-TYPE
            SYNTAX  Counter
            ACCESS  read-only
            STATUS  mandatory
            DESCRIPTION
                    "The total number of outbound calls that failed due
                    to authentication failures by this interface."
            ::= { grPhysWanStatsEntry 14 }
--
--
--
--      LAN DESTINATION GROUP OBJECTS
--      =============================
--

    grLogicalTable OBJECT-TYPE
        SYNTAX  SEQUENCE OF GrLogicalEntry
        ACCESS  not-accessible
        STATUS  mandatory
        DESCRIPTION
                "A table containing information about logical LAN
                destinations."
        ::= { grLogicalGroup 1 }


        grLogicalEntry OBJECT-TYPE
            SYNTAX  GrLogicalEntry
            ACCESS  not-accessible
            STATUS  mandatory
            DESCRIPTION
                    "Each entry of this table contains information about
                    a specific logical interface to a local area network.
                    Each logical LAN can support routing or bridging
                    functions, these are considered virtual interfaces.
                    The logical LAN can be permanently attached to a
                    physical port (LAN or WAN) or it can float among
                    available physical resources (WAN's only)."
            INDEX   { ifIndex }
            ::= { grLogicalTable 1 }


        GrLogicalEntry ::=
            SEQUENCE {
                grLogicalDestName
                   DisplayString,
                grLogicalTimeEnabled
                   INTEGER,
                grLogicalTimeWindow
                   OCTET STRING,
                grLogicalType
                   INTEGER,
                grLogicalStatus
                   RowStatus
            }


        grLogicalDestName OBJECT-TYPE
            SYNTAX  DisplayString (SIZE (1..16))
            ACCESS  read-write
            STATUS  mandatory
            DESCRIPTION
                    "The Ascii string associated with this logical
                    destination LAN."
            ::= { grLogicalEntry 1 }


        grLogicalTimeEnabled OBJECT-TYPE
            SYNTAX  INTEGER {
                        enabled(1),
                        disabled(2)
                    }
            ACCESS  read-write
            STATUS  mandatory
            DESCRIPTION
                    "This object indicates whether or not this interface
                    is active only during certain periods as indicated
                    by grLogicalTimeWindow."
            ::= { grLogicalEntry 2 }


        grLogicalTimeWindow OBJECT-TYPE
            SYNTAX  OCTET STRING (SIZE(21))
            ACCESS  read-write
            STATUS  mandatory
            DESCRIPTION
                    "This object indicates the actual window that this
                    entry is to be active. Each day is represented by
                    three octets, starting with Monday. The most
                    significant bit of the first byte represents the
                    1st hour. The least significant bit of the third octet
                    represents the 24th hour in the day. The next three
                    octets represents the 24 hours of Tuesday etc thru
                    Sunday. This object has no meaning if grLogicalTimeEnabled
                    is disabled."
            ::= { grLogicalEntry 3 }


        grLogicalType OBJECT-TYPE
            SYNTAX  INTEGER {
                        local(1),
                        remote(2) 
                    }
            ACCESS  read-write
            STATUS  mandatory
            DESCRIPTION
                    "This object determines whether this network
                    interface is locally connected to a LAN or is
                    connected to a LAN via a WAN. If this object 
                    is set to local(1) then this interface is 
                    associated with one of the physical LAN interfaces 
                    via the ifIndex. If this object indicates remote(2) 
                    then this network is reachable through a wide area 
                    network (WAN) as described in grLogWanTable."
            ::= { grLogicalEntry 4 }


        grLogicalStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grLogicalEntry 5 }
--
--
--
--    The Logical WAN Table.
--

    grLogWanTable OBJECT-TYPE
        SYNTAX  SEQUENCE OF GrLogWanEntry
        ACCESS  not-accessible
        STATUS  mandatory
        DESCRIPTION
                "A table containing configuration parameters for
                wide area network connections to logical LAN destinations 
                that are accessible via serial interfaces. Each entry 
                is logically tied to a logical LAN destination entry 
                via ifIndex."
        ::= { grLogicalGroup 2 }


        grLogWanEntry OBJECT-TYPE
            SYNTAX  GrLogWanEntry
            ACCESS  not-accessible
            STATUS  mandatory
            DESCRIPTION
                    "Each entry of this table contains information about
                    a specific logical interface to a remotely connected
                    local area network. The instance of ifIndex used to
                    index into this table is the same instance value used
                    to index into the grLogicalTable."
            INDEX   { ifIndex }
            ::= { grLogWanTable 1 }


        GrLogWanEntry ::=
            SEQUENCE {
                grLogWanCmprsn
                   INTEGER,
                grLogWanThshldOvrflw
                   INTEGER,
                grLogWanThshld
                   INTEGER,
                grLogWanConnTimer
                   INTEGER,
                grLogWanDiscTimer
                   INTEGER,
                grLogWanSpoofing
                   INTEGER,
                grLogWanStatus
                   RowStatus
            }


        grLogWanCmprsn OBJECT-TYPE
            SYNTAX  INTEGER {
                        enabled(1),
                        disabled(2)
                    }
            ACCESS  read-write
            STATUS  mandatory
            DESCRIPTION
                    "This object indicates whether or not this interface
                    is to perform data compression."
            ::= { grLogWanEntry 1 }


        grLogWanThshldOvrflw OBJECT-TYPE
            SYNTAX  INTEGER {
                        enabled(1),
                        disabled(2)
                    }
            ACCESS  read-write
            STATUS  mandatory
            DESCRIPTION
                    "This object determines if this interface is to
                    attempt to bring up another link to the same
                    destination if the traffic over the primary link
                    exceeds a pre-determined threshold."
            ::= { grLogWanEntry 2 }


        grLogWanThshld OBJECT-TYPE
            SYNTAX  INTEGER (0..100)
            ACCESS  read-write
            STATUS  mandatory
            DESCRIPTION
                    "This object determines the transmit threshold which
                    when exceeded will cause an attempt to bring up another
                    path. The returned value of this object has no meaning
                    when threshold overflow is not enabled."
            ::= { grLogWanEntry 3 }


        grLogWanConnTimer OBJECT-TYPE
            SYNTAX  INTEGER (1..3600)
            ACCESS  read-write
            STATUS  mandatory
            DESCRIPTION
                    "When threshold overflow is enabled this object
                    determines the amount of time in seconds that
                    the average threshold must be exceeded before another 
                    link is established."
            ::= { grLogWanEntry 4 }


        grLogWanDiscTimer OBJECT-TYPE
            SYNTAX  INTEGER (1..3600)
            ACCESS  read-write
            STATUS  mandatory
            DESCRIPTION
                    "When threshold overflow is enabled this object
                    determines the amount of time in seconds that
                    the average threshold must be below before one of 
                    the multi-links is disconnected."
            ::= { grLogWanEntry 5 }


        grLogWanSpoofing OBJECT-TYPE
            SYNTAX  INTEGER {
                        enabled(1),
                        disabled(2)
                    }
            ACCESS  read-write
            STATUS  mandatory
            DESCRIPTION
                    "This object indicates whether or not spoofing will
                    occur on this link for routing information. If this
                    object is disabled then periodic routing updates
                    will be issued."
            ::= { grLogWanEntry 6 }


        grLogWanStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grLogWanEntry 7 }
--
--
--
--    The Logical WAN Port Binding table.
--

    grLogWanPortTable OBJECT-TYPE
        SYNTAX  SEQUENCE OF GrLogWanPortEntry
        ACCESS  not-accessible
        STATUS  mandatory
        DESCRIPTION
                "This configuration table identifies the characteristics
                of each potential transportation pipe to a remote
                site.  Each entry in this table is associated with an 
                entry in the grLogWanTable via its ifIndex. Multiple 
                entries can be associated with a single entry in the 
                grLogWanTable."
        ::= { grLogicalGroup 3 }


        grLogWanPortEntry OBJECT-TYPE
            SYNTAX  GrLogWanPortEntry
            ACCESS  not-accessible
            STATUS  mandatory
            DESCRIPTION
                    "Each entry of this table contains information about
                    a single WAN resource used by a logical interface to
                    a remote local area network. The instance of ifIndex
                    used to index into this table is the same instance
                    value used to index into the grLogicalTable. Multiple
                    entries in this table having the same ifIndex usually
                    indicates backup or multi-linking functionality."
            INDEX   { ifIndex, grLogWanPortIndex }
            ::= { grLogWanPortTable 1 }


        GrLogWanPortEntry ::=
            SEQUENCE {
                grLogWanPortIndex
                   INTEGER,
                grLogWanPortWanType
                   INTEGER,
                grLogWanPortPhysIfIndex
                   INTEGER,
                grLogWanPortPool
                   DisplayString,
                grLogWanPortRetry
                   INTEGER,
                grLogWanPortRetryPeriod
                   INTEGER,
                grLogWanPortPrepend
                   OCTET STRING,
                grLogWanPortDestAddr
                   DisplayString,
                grLogWanPortAdminStatus
                   INTEGER,
                grLogWanPortOperStatus
                   INTEGER,
                grLogWanPortStatus
                   RowStatus
            }


        grLogWanPortIndex OBJECT-TYPE
            SYNTAX  INTEGER
            ACCESS  read-only
            STATUS  mandatory
            DESCRIPTION
                    "Identifies the port index associated with this
                    entry."
            ::= { grLogWanPortEntry 1 }


        grLogWanPortWanType OBJECT-TYPE
            SYNTAX  INTEGER {
                        primary(1),
                        secondary(2)
                    }
            ACCESS  read-write
            STATUS  mandatory
            DESCRIPTION
                    "Indicates whether or not this link is to be used 
                    as a  primary or secondary (backup) link."
            ::= { grLogWanPortEntry 2 }


        grLogWanPortPhysIfIndex OBJECT-TYPE
            SYNTAX  INTEGER
            ACCESS  read-only
            STATUS  mandatory
            DESCRIPTION
                    "Identifies the physical port ifIndex that is in use
                    by this entry when the operational status is one of
                    connecting(1), connected(2) or disconnecting(3). 
                    Otherwise this object will contain a zero value."
            ::= { grLogWanPortEntry 3 }


        grLogWanPortPool OBJECT-TYPE
            SYNTAX  DisplayString (SIZE(1..16))
            ACCESS  read-write
            STATUS  mandatory
            DESCRIPTION
                    "The name of the resource pool that will be used
                    when attempting to allocate resources."
            ::= { grLogWanPortEntry 4 }


        grLogWanPortRetry OBJECT-TYPE
            SYNTAX  INTEGER (0..99)
            ACCESS  read-write
            STATUS  mandatory
            DESCRIPTION
                    "Determines the retry count for dial up WAN
                    circuits."
            ::= { grLogWanPortEntry 5 }


        grLogWanPortRetryPeriod OBJECT-TYPE
            SYNTAX  INTEGER (0..99)
            ACCESS  read-write
            STATUS  mandatory
            DESCRIPTION
                    "Determines the retry period in seconds for dial 
                    up WAN circuits."
            ::= { grLogWanPortEntry 6 }


        grLogWanPortPrepend OBJECT-TYPE
            SYNTAX  OCTET STRING (SIZE(3))
            ACCESS  read-write
            STATUS  mandatory
            DESCRIPTION
                    "Indicates in most cases an Ascii string that will
                    be prepended to the destination address."
            ::= { grLogWanPortEntry 7 }


        grLogWanPortDestAddr OBJECT-TYPE
            SYNTAX  DisplayString (SIZE (1..20))
            ACCESS  read-write
            STATUS  mandatory
            DESCRIPTION
                    "Indicates the destination address that this
                    interface will call (ie: phone number)."
            ::= { grLogWanPortEntry 8 }


        grLogWanPortAdminStatus OBJECT-TYPE
            SYNTAX  INTEGER {
                        up(1),
                        down(2)
                    }
            ACCESS  read-write
            STATUS  mandatory
            DESCRIPTION
                    "The current desired state of this sub-layer."
            ::= { grLogWanPortEntry 9 }


        grLogWanPortOperStatus OBJECT-TYPE
            SYNTAX  INTEGER {
                        connecting(1),
                        connected(2),
                        disconnecting(3),
                        disconnected(4),
                        retryExhausted(5)
                    }
            ACCESS  read-only
            STATUS  mandatory
            DESCRIPTION
                    "The current active state of this sub-layer."
            ::= { grLogWanPortEntry 10 }


        grLogWanPortStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grLogWanPortEntry 11 }
--
--
--
--    WAN Logical Port Status Table.
--

    grLogWanStatsTable OBJECT-TYPE
        SYNTAX  SEQUENCE OF GrLogWanStatsEntry
        ACCESS  not-accessible
        STATUS  mandatory
        DESCRIPTION
                "This table contains stats information for wide area
                connections to remote LAN's." 
        ::= { grLogicalGroup 4 }


        grLogWanStatsEntry OBJECT-TYPE
            SYNTAX  GrLogWanStatsEntry
            ACCESS  not-accessible
            STATUS  mandatory
            DESCRIPTION
                    "Each entry in this table contains specific
                    information about a single logical interface."
            INDEX   { ifIndex }
            ::= { grLogWanStatsTable 1 }


        GrLogWanStatsEntry ::=
            SEQUENCE {
               grLogWanStInUse
                  OCTET STRING,
               grLogWanStUncmpsdRxOctets
                  Counter,
               grLogWanStCmpsdRxOctets
                  Counter,
               grLogWanStUncmpsdTxOctets
                  Counter,
               grLogWanStCmpsdTxOctets
                  Counter,
               grLogWanStConnects
                  Counter,
               grLogWanStConnectFails
                  Counter
            }


        grLogWanStInUse OBJECT-TYPE
            SYNTAX  OCTET STRING
            ACCESS  read-only
            STATUS  mandatory
            DESCRIPTION
                    "This object indicates the physical WAN port(s) 
                    currently in use by this logical destination. The 
                    WAN port ifIndex(es) are represented in a string of 
                    octets of varying length (depending on the number of 
                    active connections) where each octet contains the 
                    ifIndex ifIndex of the physical port."
            ::= { grLogWanStatsEntry 1 }


        grLogWanStUncmpsdRxOctets OBJECT-TYPE
            SYNTAX  Counter
            ACCESS  read-only
            STATUS  mandatory
            DESCRIPTION
                    "The number of received octets after being decompressed."
            ::= { grLogWanStatsEntry 2 }


        grLogWanStCmpsdRxOctets OBJECT-TYPE
            SYNTAX  Counter
            ACCESS  read-only
            STATUS  mandatory
            DESCRIPTION
                    "The number of received compressed octets."
            ::= { grLogWanStatsEntry 3 }


        grLogWanStUncmpsdTxOctets OBJECT-TYPE
            SYNTAX  Counter
            ACCESS  read-only
            STATUS  mandatory
            DESCRIPTION
                    "The number of octets to be transmitted prior to being
                    compressed."
            ::= { grLogWanStatsEntry 4 }


        grLogWanStCmpsdTxOctets OBJECT-TYPE
            SYNTAX  Counter
            ACCESS  read-only
            STATUS  mandatory
            DESCRIPTION
                    "The number of transmitted compressed octets."
            ::= { grLogWanStatsEntry 5 }


        grLogWanStConnects OBJECT-TYPE
            SYNTAX  Counter
            ACCESS  read-only
            STATUS  mandatory
            DESCRIPTION
                    "The total number of times this interface has attempted
                    to establish a remote connection."
            ::= { grLogWanStatsEntry 6 }


        grLogWanStConnectFails OBJECT-TYPE
            SYNTAX  Counter
            ACCESS  read-only
            STATUS  mandatory
            DESCRIPTION
                    "The total number of times this interface has attempted
                    to establish a remote connection but failed."
            ::= { grLogWanStatsEntry 7 }
--
--
--
--    Virtual Port Statistics Table.
--

    grVirtualStatsTable OBJECT-TYPE
        SYNTAX  SEQUENCE OF GrVirtualStatsEntry
        ACCESS  not-accessible
        STATUS  mandatory
        DESCRIPTION
                "This table contains information with regards to
                virtual network interfaces."
        ::= { grLogicalGroup 5 }


        grVirtualStatsEntry OBJECT-TYPE
            SYNTAX  GrVirtualStatsEntry
            ACCESS  not-accessible
            STATUS  mandatory
            DESCRIPTION
                    "Each entry in this table contains specific
                    information about a single virtual network 
                    interface whether it be a IP or IPX port."
            INDEX   { grVSProtocolType, grVSNetAddr }
            ::= { grVirtualStatsTable 1 }


        GrVirtualStatsEntry ::=
            SEQUENCE {
               grVSProtocolType
                  INTEGER,
               grVSNetAddr
                  OCTET STRING,
               grVSIfIndex
                  INTEGER,
               grVSRxPkts
                  Counter,
               grVSTxPkts
                  Counter,
               grVSRxOctets
                  Counter,
               grVSTxOctets
                  Counter,
               grVSTTLDiscards
                  Counter,
               grVSRxFilteredPkts
                  Counter,
               grVSTxFilteredPkts
                  Counter
            }


        grVSProtocolType OBJECT-TYPE
            SYNTAX  INTEGER {
                        ip(1),
                        ipx(2)
                    }
            ACCESS  read-only
            STATUS  mandatory
            DESCRIPTION
                    "This object indicates what type of virtual port
                    this information pertains to. Virtual bridge port
                    stats can be obtained from RFC 1493 dot1dTpPortTable
                    as well as grBridgePortStatsTable."
            ::= { grVirtualStatsEntry 1 }


        grVSNetAddr OBJECT-TYPE
            SYNTAX  OCTET STRING
            ACCESS  read-only
            STATUS  mandatory
            DESCRIPTION
                    "The network address associated with this virtual
                    interface (either a IP or IPX network address)."
            ::= { grVirtualStatsEntry 2 }


        grVSIfIndex OBJECT-TYPE
            SYNTAX  INTEGER
            ACCESS  read-only
            STATUS  mandatory
            DESCRIPTION
                    "The network interface associated with this virtual
                    interface."
            ::= { grVirtualStatsEntry 3 }


        grVSRxPkts OBJECT-TYPE
            SYNTAX  Counter
            ACCESS  read-only
            STATUS  mandatory
            DESCRIPTION
                    "The total number of packets that this virtual
                    interface has received."
            ::= { grVirtualStatsEntry 4 }


        grVSTxPkts OBJECT-TYPE
            SYNTAX  Counter
            ACCESS  read-only
            STATUS  mandatory
            DESCRIPTION
                    "The total number of packets that this virtual
                    interface has transmitted."
            ::= { grVirtualStatsEntry 5 }


        grVSRxOctets OBJECT-TYPE
            SYNTAX  Counter
            ACCESS  read-only
            STATUS  mandatory
            DESCRIPTION
                    "The total number of octets that this virtual
                    interface has received."
            ::= { grVirtualStatsEntry 6 }


        grVSTxOctets OBJECT-TYPE
            SYNTAX  Counter
            ACCESS  read-only
            STATUS  mandatory
            DESCRIPTION
                    "The total number of octets that this virtual
                    interface has transmitted."
            ::= { grVirtualStatsEntry 7 }


        grVSTTLDiscards OBJECT-TYPE
            SYNTAX  Counter
            ACCESS  read-only
            STATUS  mandatory
            DESCRIPTION
                    "The total number of packets that this virtual
                    interface has discarded because their time to
                    live within the router has exceeded. The time
                    spent within the router is protocol specific."
            ::= { grVirtualStatsEntry 8 }


        grVSRxFilteredPkts OBJECT-TYPE
            SYNTAX  Counter
            ACCESS  read-only
            STATUS  mandatory
            DESCRIPTION
                    "The total number of received packets that this
                    virtual interface has filtered (as determined
                    by the receive and destination Access Rights)."
            ::= { grVirtualStatsEntry 9 }


        grVSTxFilteredPkts OBJECT-TYPE
            SYNTAX  Counter
            ACCESS  read-only
            STATUS  mandatory
            DESCRIPTION
                    "The total number of packets that were filtered
                    during the transmission process on this virtual
                    interface (as determined by the receive and 
                    destination Access Rights)."
            ::= { grVirtualStatsEntry 10 }
--
--
--
--          BRIDGE GROUP OBJECTS
--          ====================
--

    grBridgingState OBJECT-TYPE
        SYNTAX INTEGER {
                   enabled(1),
                   disabled(2)
               }
        ACCESS read-write
        STATUS mandatory
        DESCRIPTION
                "This object indicates the unit wide status for 802.1d
                bridging. Disabling this object overrides all interfaces 
                that have bridging enabled."
        ::= { grBridgeGroup 1 }


    grBrMaxTransitDelay OBJECT-TYPE
        SYNTAX INTEGER (100..3000)
        ACCESS read-write
        STATUS mandatory
        DESCRIPTION
                "Determines the maximum time in 1/100 of a second that a 
                bridged frame can be retained within the bridge before 
                being discarded."
        ::= { grBridgeGroup 2 }


    grBrFilterTestPackets OBJECT-TYPE
      SYNTAX INTEGER {
                 filter(1),
                 forward(2)
             }
      ACCESS read-write
      STATUS mandatory
      DESCRIPTION
              "This object indicates the current state of the ethernet
              test packets filter option."
      ::= { grBridgeGroup 3 }
--
--
--
--     The Bridge Protocol Filtering Table.
--

    grProtFilterType OBJECT-TYPE
        SYNTAX INTEGER {
                   filter(1),
                   forward(2)
               }
        ACCESS read-write
        STATUS mandatory
        DESCRIPTION
                "This object determines whether to forward or filter
                bridge packets that match an entry in the protocol filter
                table."
        ::= { grBridgeGroup 4 }


    grProtFilterTable OBJECT-TYPE
        SYNTAX  SEQUENCE OF GrProtFilterEntry
        ACCESS  not-accessible
        STATUS  mandatory
        DESCRIPTION
                "A table containing protocol filtering information
                configured into the bridge."
        ::= { grBridgeGroup 5 }


        grProtFilterEntry OBJECT-TYPE
            SYNTAX  GrProtFilterEntry
            ACCESS  not-accessible
            STATUS  mandatory
            DESCRIPTION
                    "Protocol filtering information configured into the
                    bridge. Each entry contains a protocol Id which
                    is used to filter/forward bridge packets based on the
                    packets protocol type (ie: DECNET, IP etc)."
            INDEX   { grProtFilterId }
            ::= { grProtFilterTable 1 }

        GrProtFilterEntry ::=
            SEQUENCE {
                grProtFilterId
                    INTEGER,
                grProtFilterStatus
                    RowStatus
            }


        grProtFilterId OBJECT-TYPE
            SYNTAX  INTEGER
            ACCESS  read-only
            STATUS  mandatory
            DESCRIPTION
                    "This attribute identifies the protocol type to
                    be filtered/forwarded."
            ::= { grProtFilterEntry 1 }


        grProtFilterStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grProtFilterEntry 2 }
--
--
--     The Bridge Protocol Priority Table.
--

    grProtPriorityTable OBJECT-TYPE
        SYNTAX  SEQUENCE OF GrProtPriorityEntry
        ACCESS  not-accessible
        STATUS  mandatory
        DESCRIPTION
                "A table containing protocol priority information
                configured into the bridge by (local or network)
                management specifying the priority in which frames
                will be transmitted on the wide area network links."
        ::= { grBridgeGroup 6 }


        grProtPriorityEntry OBJECT-TYPE
            SYNTAX  GrProtPriorityEntry
            ACCESS  not-accessible
            STATUS  mandatory
            DESCRIPTION
                    "Protocol priority information configured into the
                    bridge by (local or network) management."
            INDEX   { grProtPriorityId }
            ::= { grProtPriorityTable 1 }


        GrProtPriorityEntry ::=
            SEQUENCE {
                grProtPriorityId
                    INTEGER,
                grProtPriorityLevel
                    INTEGER,
                grProtPriorityStatus
                    RowStatus
            }


        grProtPriorityId OBJECT-TYPE
            SYNTAX  INTEGER
            ACCESS  read-only
            STATUS  mandatory
            DESCRIPTION
                    "This attribute identifies the protocol type to
                    be prioritized."
            ::= { grProtPriorityEntry 1 }


        grProtPriorityLevel OBJECT-TYPE
            SYNTAX INTEGER {
                       low(1),
                       medium(2),
                       high(3)
                   }
            ACCESS  read-write
            STATUS  mandatory
            DESCRIPTION
                    "The priority assigned to the associated Portocol ID."
            ::= { grProtPriorityEntry 2 }


        grProtPriorityStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grProtPriorityEntry 3 }
--
--
--
--                The Bridge Port configuration table.
--
--  To configure Spanning Tree on this port we use the
--  dot1dStpPortTable defined in RFC 1493. Note that ifIndex
--  is being used to index into the bridge port table. The value
--  for dot1dStpPort will have the same value as ifIndex to
--  identify the same bridge port. The following table is used 
--  to configure additional parameters on a per port basis that
--  are not available in RFC 1493.

    grBridgePortTable OBJECT-TYPE
        SYNTAX  SEQUENCE OF GrBridgePortEntry
        ACCESS  not-accessible
        STATUS  mandatory
        DESCRIPTION
                "This table defines additional bridging parameters
                (outside of those defined in RFC 1493) on bridging
                ports. The Bridge MIB (RFC 1493) is used  to configure
                all other bridge port parameters."
        ::= { grBridgeGroup 7 }


        grBridgePortEntry OBJECT-TYPE
            SYNTAX  GrBridgePortEntry
            ACCESS  not-accessible
            STATUS  mandatory
            DESCRIPTION
                    "Each entry in this table indicates the additional
                    parameters in use by the bridge port."
            INDEX   { ifIndex }
            ::= { grBridgePortTable 1 }


        GrBridgePortEntry ::=
            SEQUENCE {
                grBrPortStpBpduFilter
                   INTEGER,
                grBrPortAllowedToGoDef
                   OCTET STRING
            }


        grBrPortStpBpduFilter OBJECT-TYPE
            SYNTAX  INTEGER {
                        filter(1),
                        forward(2)
                    }
            ACCESS  read-write
            STATUS  mandatory
            DESCRIPTION
                    "This object determines if the Spanning Tree
                    BPDU's are filtered or forwarded. If set to
                    filter then this port will not send BPDU packets
                    and any received BPDU's will be discared before
                    reaching the Spanning Tree process."
            ::= { grBridgePortEntry 1 }


        grBrPortAllowedToGoDef OBJECT-TYPE
            SYNTAX  OCTET STRING
            ACCESS  read-write
            STATUS  mandatory
            DESCRIPTION
                    "The default set of ports to which frames destined
                    for this port have access. Each octet with the
                    value of this object specifies a set of eight ports,
                    with the first octet specifying port 1 through 8,
                    the second octet specifying ports 9 through 16, etc.
                    Within each octet, the most significant bit represents
                    the lowest numbered port, and the least significant
                    bit represents the highest numbered port. A bit value
                    of '1' indicates access allowed."
            ::= { grBridgePortEntry 2 }
--
--
--
--                The Bridge Port Status table.
--

    grBridgePortStatsTable OBJECT-TYPE
        SYNTAX  SEQUENCE OF GrBridgePortStatsEntry
        ACCESS  not-accessible
        STATUS  mandatory
        DESCRIPTION
                "This table contains bridge port statistics not
                available in the Bridge MIB."
        ::= { grBridgeGroup 8 }


        grBridgePortStatsEntry OBJECT-TYPE
            SYNTAX  GrBridgePortStatsEntry
            ACCESS  not-accessible
            STATUS  mandatory
            DESCRIPTION
                    "Each entry in this table contains bridge port
                    stats."
            INDEX   { ifIndex }
            ::= { grBridgePortStatsTable 1 }


        GrBridgePortStatsEntry ::=
            SEQUENCE {
                grBrPortStRxOctets
                   Counter,
                grBrPortStTxOctets
                   Counter,
                grBrPortStRxFilteredPkts
                   Counter,
                grBrPortStTxFilteredPkts
                   Counter
            }


        grBrPortStRxOctets OBJECT-TYPE
            SYNTAX  Counter
            ACCESS  read-only
            STATUS  mandatory
            DESCRIPTION
                    "This object indicates the number of received octets
                    on this bridge port."
            ::= { grBridgePortStatsEntry 1 }


        grBrPortStTxOctets OBJECT-TYPE
            SYNTAX  Counter
            ACCESS  read-only
            STATUS  mandatory
            DESCRIPTION
                    "This object indicates the number of transmitted
                    octets on this bridge port."
            ::= { grBridgePortStatsEntry 2 }


        grBrPortStRxFilteredPkts OBJECT-TYPE
            SYNTAX  Counter
            ACCESS  read-only
            STATUS  mandatory
            DESCRIPTION
                    "This object indicates the number of received bridge
                    packets that were filtered because of access rights
                    on the receive bridge port."
            ::= { grBridgePortStatsEntry 3 }


        grBrPortStTxFilteredPkts OBJECT-TYPE
            SYNTAX  Counter
            ACCESS  read-only
            STATUS  mandatory
            DESCRIPTION
                    "This object indicates the number of bridge packets 
                    that were filtered because of access rights on the 
                    output bridge port."
            ::= { grBridgePortStatsEntry 4 }
--
--
--
--     The Spanning Tree Unit Wide Group Parameters.
--

    grSpanningTreeStatus OBJECT-TYPE
        SYNTAX INTEGER {
                   enabled(1),
                   disabled(2)
               }
        ACCESS read-write
        STATUS mandatory
        DESCRIPTION
                "Indicates the unit wide status of 802.1d Spanning
                Tree."
        ::= { grBridgeGroup 9 }
--
--
--
--          IPX GROUP OBJECTS
--          =================
--
--
--  General box wide IPX configuration parameters.

    grIpxRoutingEnable OBJECT-TYPE
        SYNTAX  INTEGER {
                    enabled(1),
                    disabled(2)
                }
        ACCESS  read-write
        STATUS  mandatory
        DESCRIPTION
                "Configures the router to enable IPX routing on a unit
                wide basis."
        ::= { grIpxGroup 1 }


    grIpxPrimaryNet OBJECT-TYPE
        SYNTAX  OCTET STRING (SIZE(4))
        ACCESS  read-write
        STATUS  mandatory
        DESCRIPTION
                "Configure the router with the primary network
                number for IPXWAN."
        ::= { grIpxGroup 2 }


    grIpxRipEnable OBJECT-TYPE
        SYNTAX  INTEGER {
                    enabled(1),
                    disable(2)
                }
        ACCESS  read-write
        STATUS  mandatory
        DESCRIPTION
                "Configures the router to enable IPX RIP on a unit
                wide basis. Each logical port must still in turn
                have RIP enabled on a per port basis."
        ::= { grIpxGroup 3 }


    grIpxSapEnable OBJECT-TYPE
        SYNTAX  INTEGER {
                    enabled(1),
                    disable(2)
                }
        ACCESS  read-write
        STATUS  mandatory
        DESCRIPTION
                "Configures the router to enable IPX SAP on a unit
                wide basis. Each logical port must still in turn
                have SAP enabled on a per port basis."
        ::= { grIpxGroup 4 }
--
--
--
--     The IPX Access Restriction Table.
--

    grIpxAccessRestrictEnable OBJECT-TYPE
        SYNTAX  INTEGER {
                   enabled(1),
                   disabled(2)
                }
        ACCESS  read-write
        STATUS  mandatory
        DESCRIPTION
                "This object indicates if this router is using the 
                IPX Access Restriction table to filter out packets
                that are being routed."
        ::= { grIpxGroup 5 }


    grIpxAccessRestrictTable OBJECT-TYPE
        SYNTAX  SEQUENCE OF GrIpxAccessRestrictEntry
        ACCESS  not-accessible
        STATUS  mandatory
        DESCRIPTION
                "The IPX Access Restriction configuration table."
        ::= { grIpxGroup 6 }


        grIpxAccessRestrictEntry OBJECT-TYPE
            SYNTAX  GrIpxAccessRestrictEntry
            ACCESS  not-accessible
            STATUS  mandatory
            DESCRIPTION
                    "Contains information about a single IPX Access
                    filter."
            INDEX   { grIpxAccIndex }
            ::= { grIpxAccessRestrictTable 1 }


        GrIpxAccessRestrictEntry ::=
            SEQUENCE {
               grIpxAccIndex
                  INTEGER,
               grIpxAccName
                  DisplayString,
               grIpxAccType
                  INTEGER,
               grIpxAccSrcNet
                  OCTET STRING,
               grIpxAccSrcNode
                  OCTET STRING,
               grIpxAccSrcSocketFrom
                  INTEGER,
               grIpxAccSrcSocketTo
                  INTEGER,
               grIpxAccDstNet
                  OCTET STRING,
               grIpxAccDstNode
                  OCTET STRING,
               grIpxAccDstSocketFrom
                  INTEGER,
               grIpxAccDstSocketTo
                  INTEGER,
               grIpxAccStatus
                  RowStatus
            }


        grIpxAccIndex OBJECT-TYPE
            SYNTAX  INTEGER
            ACCESS  read-only
            STATUS  mandatory
            DESCRIPTION
                    "Identifies the unique entry in this table."
            ::= { grIpxAccessRestrictEntry 1 }


        grIpxAccName OBJECT-TYPE
            SYNTAX  DisplayString (SIZE(1..16))
            ACCESS  read-write
            STATUS  mandatory
            DESCRIPTION
                    "The name associated with this entry."
            ::= { grIpxAccessRestrictEntry 2 }


        grIpxAccType OBJECT-TYPE
            SYNTAX  INTEGER {
                       filter(1),
                       forward(2)
                    }
            ACCESS  read-write
            STATUS  mandatory
            DESCRIPTION
                    "This object indicates if the router is to filter
                     or forward IPX frames the match this access filter
                     entry."
            ::= { grIpxAccessRestrictEntry 3 }


        grIpxAccSrcNet OBJECT-TYPE
            SYNTAX  OCTET STRING (SIZE(4))
            ACCESS  read-write
            STATUS  mandatory
            DESCRIPTION
                    "Defines the source IPX Network id to match on."
            ::= { grIpxAccessRestrictEntry 4 }


        grIpxAccSrcNode OBJECT-TYPE
            SYNTAX  OCTET STRING (SIZE(6))
            ACCESS  read-write
            STATUS  mandatory
            DESCRIPTION
                    "Defines the source IPX host id to apply when
                    determining a match."
            ::= { grIpxAccessRestrictEntry 5 }


        grIpxAccSrcSocketFrom OBJECT-TYPE
            SYNTAX  INTEGER (0..65535)
            ACCESS  read-write
            STATUS  mandatory
            DESCRIPTION
                    "Defines the FROM range of source sockets to filter/
                    forward."
            ::= { grIpxAccessRestrictEntry 6 }


        grIpxAccSrcSocketTo OBJECT-TYPE
            SYNTAX  INTEGER (0..65535)
            ACCESS  read-write
            STATUS  mandatory
            DESCRIPTION
                    "Defines the TO range of source sockets to filter/
                    forward."
            ::= { grIpxAccessRestrictEntry 7 }


        grIpxAccDstNet OBJECT-TYPE
            SYNTAX  OCTET STRING (SIZE(4))
            ACCESS  read-write
            STATUS  mandatory
            DESCRIPTION
                    "Defines the destination IPX Network id to match on."
            ::= { grIpxAccessRestrictEntry 8 }


        grIpxAccDstNode OBJECT-TYPE
            SYNTAX  OCTET STRING (SIZE(6))
            ACCESS  read-write
            STATUS  mandatory
            DESCRIPTION
                    "Defines the destination IPX host id to apply when
                    determining a match."
            ::= { grIpxAccessRestrictEntry 9 }


        grIpxAccDstSocketFrom OBJECT-TYPE
            SYNTAX  INTEGER (0..65535)
            ACCESS  read-write
            STATUS  mandatory
            DESCRIPTION
                    "Defines the FROM range of destination sockets to
                    filter/forward."
            ::= { grIpxAccessRestrictEntry 10 }


        grIpxAccDstSocketTo OBJECT-TYPE
            SYNTAX  INTEGER (0..65535)
            ACCESS  read-write
            STATUS  mandatory
            DESCRIPTION
                    "Defines the TO range of destination sockets to
                    filter/forward."
            ::= { grIpxAccessRestrictEntry 11 }


        grIpxAccStatus OBJECT-TYPE
            SYNTAX  RowStatus
            ACCESS  read-write
            STATUS  mandatory
            DESCRIPTION
                    "The current status of this entry."
            REFERENCE
                    "Textual Conventions for Version 2 of the
                    Simple Network Management Protocol (RFC 1443)."

            ::= { grIpxAccessRestrictEntry 12 }
--
--
--
--     The IPX Dynamic RIP Table.
--

    grIpxRouteTable OBJECT-TYPE
        SYNTAX  SEQUENCE OF GrIpxRouteEntry
        ACCESS  not-accessible
        STATUS  mandatory
        DESCRIPTION
                "This table contains the static and learned IPX RIP 
                information."
        ::= { grIpxGroup 7 }


        grIpxRouteEntry OBJECT-TYPE
            SYNTAX  GrIpxRouteEntry
            ACCESS  not-accessible
            STATUS  mandatory
            DESCRIPTION
                    "Each entry in this table contains specific
                    information about a single learned or static IPX 
                    RIP route."
            INDEX   { grIpxRouteDest,
                      grIpxRouteType,
                      grIpxRouteNextHopNet,
                      grIpxRouteNextHopNode }
            ::= { grIpxRouteTable 1 }


        GrIpxRouteEntry ::=
            SEQUENCE {
                grIpxRouteDest
                    OCTET STRING,
                grIpxRouteType
                    INTEGER,
                grIpxRouteHops
                    INTEGER,
                grIpxRouteDelay
                    INTEGER,
                grIpxRouteAge
                    TimeTicks,
                grIpxRouteNextHopNet
                    OCTET STRING,
                grIpxRouteNextHopNode
                    OCTET STRING,
                grIpxRouteIfIndex
                    INTEGER,
                grIpxRouteStatus
                    RowStatus
            }


        grIpxRouteDest OBJECT-TYPE
            SYNTAX  OCTET STRING (SIZE(4))
            ACCESS  read-only
            STATUS  mandatory
            DESCRIPTION
                    "This object indicates the destination network that
                    this entries information pertains to."
            ::= { grIpxRouteEntry 1 }


        grIpxRouteType OBJECT-TYPE
            SYNTAX  INTEGER {
                        learned(1),
                        static(2),
			local(3)
                    }
            ACCESS  read-only
            STATUS  mandatory
            DESCRIPTION
                    "This object displays the type of route this entry
                    is (ie: dynamically learned via RIP, static etc)."
            ::= { grIpxRouteEntry 2 }


        grIpxRouteHops OBJECT-TYPE
            SYNTAX  INTEGER
            ACCESS  read-write
            STATUS  mandatory
            DESCRIPTION
                    "This object indicates the number of routers that
                    must be passed through to reach the destination
                    network associated with this entry."
            ::= { grIpxRouteEntry 3 }


        grIpxRouteDelay OBJECT-TYPE
            SYNTAX  INTEGER
            ACCESS  read-write
            STATUS  mandatory
            DESCRIPTION
                    "This object indicates the amount of time in ticks
                    that a packet takes to reach the destination network 
                    associated with this entry. Each tick represents
                    appx. 55 milliseconds."
            ::= { grIpxRouteEntry 4 }


        grIpxRouteAge OBJECT-TYPE
            SYNTAX  TimeTicks
            ACCESS  read-only
            STATUS  mandatory
            DESCRIPTION
                    "This object indicates the age of this entry since
                    the last RIP update in one hundreths of a second."
            ::= { grIpxRouteEntry 5 }


        grIpxRouteNextHopNet OBJECT-TYPE
            SYNTAX  OCTET STRING (SIZE(4))
            ACCESS  read-only
            STATUS  mandatory
            DESCRIPTION
                    "This object indicates the network portion of the
                    next IPX router that IPX packets will be sent to in
                    order to reach the destination network associated
                    with this entry."
            ::= { grIpxRouteEntry 6 }


        grIpxRouteNextHopNode OBJECT-TYPE
            SYNTAX  OCTET STRING (SIZE(6))
            ACCESS  read-only
            STATUS  mandatory
            DESCRIPTION
                    "This object indicates the address portion of the next
                    IPX router that IPX packets will be sent to in order
                    to reach the destination network associated with this
                    entry."
            ::= { grIpxRouteEntry 7 }


        grIpxRouteIfIndex OBJECT-TYPE
            SYNTAX  INTEGER
            ACCESS  read-only
            STATUS  mandatory
            DESCRIPTION
                    "This object indicates the logical port/interface
                    (ifIndex) that this route was learned on."
            ::= { grIpxRouteEntry 8 }


        grIpxRouteStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpxRouteEntry 9 }
--
--
--
--      The IPX Dynamic SAP Table.
--

    grIpxServerTable OBJECT-TYPE
        SYNTAX  SEQUENCE OF GrIpxServerEntry
        ACCESS  not-accessible
        STATUS  mandatory
        DESCRIPTION
                "This table contains the learned and static IPX SAP 
                information."
        ::= { grIpxGroup 8 }


        grIpxServerEntry OBJECT-TYPE
            SYNTAX  GrIpxServerEntry
            ACCESS  not-accessible
            STATUS  mandatory
            DESCRIPTION
                    "Each entry in this table contains specific
                    information about a single learned or static IPX SAP
                    server."
            INDEX   { grIpxServerType,
                      grIpxServerSapType,
                      grIpxServerName }
            ::= { grIpxServerTable 1 }


        GrIpxServerEntry ::=
            SEQUENCE {
                grIpxServerType
                    INTEGER,
                grIpxServerSapType
                    INTEGER,
                grIpxServerName
                    DisplayString,
                grIpxServerAge
                    TimeTicks,
                grIpxServerNet
                    OCTET STRING,
                grIpxServerNode
                    OCTET STRING,
                grIpxServerSocket
                    INTEGER,
                grIpxServerStatus
                    RowStatus
            }


        grIpxServerType OBJECT-TYPE
            SYNTAX  INTEGER
            ACCESS  read-only
            STATUS  mandatory
            DESCRIPTION
                    "The IPX server type."
            ::= { grIpxServerEntry 1 }


        grIpxServerSapType OBJECT-TYPE
            SYNTAX  INTEGER {
                        learned(1),
                        static(2)
                    }
            ACCESS  read-only
            STATUS  mandatory
            DESCRIPTION
                    "This object displays how this type of entry was
                    learned (ie: dynamically learned via RIP, static etc)."
            ::= { grIpxServerEntry 2 }


        grIpxServerName OBJECT-TYPE
            SYNTAX  DisplayString (SIZE (1..48))
            ACCESS  read-only
            STATUS  mandatory
            DESCRIPTION
                    "The IPX server name."
            ::= { grIpxServerEntry 3 }


        grIpxServerAge OBJECT-TYPE
            SYNTAX  TimeTicks
            ACCESS  read-only
            STATUS  mandatory
            DESCRIPTION
                    "The age in one hundreths of a second since this
                    router last heard from this server."
            ::= { grIpxServerEntry 4 }


        grIpxServerNet OBJECT-TYPE
            SYNTAX  OCTET STRING (SIZE(4))
            ACCESS  read-write
            STATUS  mandatory
            DESCRIPTION
                    "This object contains the address of the network
                    on which the server resides."
            ::= { grIpxServerEntry 5 }


        grIpxServerNode OBJECT-TYPE
            SYNTAX  OCTET STRING (SIZE(6))
            ACCESS  read-write
            STATUS  mandatory
            DESCRIPTION
                    "This object contains the address of the node on
                    which the server resides."
            ::= { grIpxServerEntry 6 }


        grIpxServerSocket OBJECT-TYPE
            SYNTAX  INTEGER
            ACCESS  read-write
            STATUS  mandatory
            DESCRIPTION
                    "This object contains the socket number on which
                    the server will receive service requests."
            ::= { grIpxServerEntry 7 }


        grIpxServerStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpxServerEntry 8 }
--
--
--
--    IPX Node Counters.
--
--  These stats represent the IPX stats on a unit wide basis.

    grIpxInReceives OBJECT-TYPE
        SYNTAX  Counter
        ACCESS  read-only
        STATUS  mandatory
        DESCRIPTION
                "This object reports the total number of IPX
                received packets including errored packets that this
                unit has processed."
        ::= { grIpxGroup 9 }


    grIpxInHdrErrors OBJECT-TYPE
        SYNTAX  Counter
        ACCESS  read-only
        STATUS  mandatory
        DESCRIPTION
                "The number of input datagrams discarded due to errors
                in their IPX headers, including bad checksums, transport
                control exceeded etc."
        ::= { grIpxGroup 10 }


    grIpxForwDatagrams OBJECT-TYPE
        SYNTAX  Counter
        ACCESS  read-only
        STATUS  mandatory
        DESCRIPTION
                "The number of input datagrams for which this entity
                was not their final IPX destination, as a result of
                which an attempt was made to find a route to forward
                them to that final destination."
        ::= { grIpxGroup 11 }


    grIpxInUnknownSockets OBJECT-TYPE
        SYNTAX  Counter
        ACCESS  read-only
        STATUS  mandatory
        DESCRIPTION
                "The number of locally-addressed datagrams received
                successfully but discarded because of an unknown or
                unsupported socket."
        ::= { grIpxGroup 12 }


    grIpxInDiscards OBJECT-TYPE
        SYNTAX  Counter
        ACCESS  read-only
        STATUS  mandatory
        DESCRIPTION
                "The number of input IPX datagrams for which no
                problems were encountered to prevent their continued
                processing, but were discarded."
        ::= { grIpxGroup 13 }


    grIpxInDelivers OBJECT-TYPE
        SYNTAX  Counter
        ACCESS  read-only
        STATUS  mandatory
        DESCRIPTION
                "The total number of input datagrams successfully
                delivered to IPX user-protocols (including RIP and
                SAP)."
        ::= { grIpxGroup 14 }


    grIpxOutRequests OBJECT-TYPE
        SYNTAX  Counter
        ACCESS  read-only
        STATUS  mandatory
        DESCRIPTION
                "The total number of IPX datagrams which local IPX
                user-protocols (including RIP and SAP) supplied to IPX
                in requests for transmission. This does not include any
                datagrams counted in grIpxForwDatagrams."
        ::= { grIpxGroup 15 }


    grIpxOutDiscards OBJECT-TYPE
        SYNTAX  Counter
        ACCESS  read-only
        STATUS  mandatory
        DESCRIPTION
                "The number of output IPX datagrams for which no problem
                was encountered to prevent their transmission to their
                destination, but which were discarded (ie: due to no
                resources)."
        ::= { grIpxGroup 16 }


    grIpxOutNoRoutes OBJECT-TYPE
        SYNTAX  Counter
        ACCESS  read-only
        STATUS  mandatory
        DESCRIPTION
                "The number of IPX datagrams discarded because no route
                could be found to transmit them to their destination.
                Note that this counter includes any packets counted in
                grIpxForwDatagrams which meet this `no-route' criterion."
        ::= { grIpxGroup 17 }
--
--
--    The IPX Logical Port Configuration Table
--

    grIpxLogicalTable OBJECT-TYPE
        SYNTAX  SEQUENCE OF GrIpxLogicalEntry
        ACCESS  not-accessible
        STATUS  mandatory
        DESCRIPTION
                "A table containing information about logical IPX LAN
                destinations."
        ::= { grIpxGroup 18 }


        grIpxLogicalEntry OBJECT-TYPE
            SYNTAX  GrIpxLogicalEntry
            ACCESS  not-accessible
            STATUS  mandatory
            DESCRIPTION
                    "Each entry of this table contains information about
                    a specific IPX logical interface to a local area 
                    network. Each logical LAN can support routing or 
                    bridging functions, these are considered virtual 
                    interfaces."
            INDEX   { ifIndex }
            ::= { grIpxLogicalTable 1 }


        GrIpxLogicalEntry ::=
            SEQUENCE {
                grIpxLAccessDef
                   INTEGER,
                grIpxLRestrictions
                   OCTET STRING,
                grIpxLTransport
                   INTEGER,
                grIpxLStatus
                   RowStatus
            }


        grIpxLAccessDef OBJECT-TYPE
            SYNTAX  INTEGER {
                        filter(1),
                        forward(2)
                    }
            ACCESS  read-write
            STATUS  mandatory
            DESCRIPTION
                    "This object indicates what the default access right
                    will apply to IPX packets that do not match any of the
                    IPX Access Restrictions."
            ::= { grIpxLogicalEntry 1 }


        grIpxLRestrictions OBJECT-TYPE
            SYNTAX  OCTET STRING
            ACCESS  read-write
            STATUS  mandatory
            DESCRIPTION
                    "This object specifies the access filter/forward
                    requirements for this logical destination for IPX
                    packets. Each octet represents an entry (index) in
                    the grIpxAccessRestrictTable."
            ::= { grIpxLogicalEntry 2 }


        grIpxLTransport OBJECT-TYPE
            SYNTAX  INTEGER {
                        ipxcp(1),
                        bncp(2)
                    }
            ACCESS  read-write
            STATUS  mandatory
            DESCRIPTION
                    "This object indicates the transport NCP to use within
                    a PPP connection when the IPX network is remote."
            ::= { grIpxLogicalEntry 3 }


        grIpxLStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpxLogicalEntry 4 }
--
--
--
--     IPX Virtual Port Configuration Group.
--

    grIpxVirtualTable OBJECT-TYPE
        SYNTAX  SEQUENCE OF GrIpxVirtualEntry
        ACCESS  not-accessible
        STATUS  mandatory
        DESCRIPTION
                "This table is used to display and configure IPX 
                virtual port information. Each logical LAN destination 
                may have one or more IPX virtuals."
        ::= { grIpxGroup 19 }


        grIpxVirtualEntry OBJECT-TYPE
            SYNTAX  GrIpxVirtualEntry
            ACCESS  not-accessible
            STATUS  mandatory
            DESCRIPTION
                    "Each entry in this table contains configuration
                    information specific to a single IPX interface."
            INDEX   { grIpxVNetAddr }
            ::= { grIpxVirtualTable 1 }


        GrIpxVirtualEntry ::=
            SEQUENCE {
                grIpxVNetAddr
                    OCTET STRING,
                grIpxVNetEncap
                    INTEGER,
                grIpxVRipEnable
                    INTEGER,
                grIpxVRipMetric
                    INTEGER,
                grIpxVRipTxPeriod
                    INTEGER,
                grIpxVRipAgeTimer
                    INTEGER,
                grIpxVSapEnable
                    INTEGER,
                grIpxVSapTxPeriod
                    INTEGER,
                grIpxVSapAgeTimer
                    INTEGER,
                grIpxVWdogSpoof
                    INTEGER,
                grIpxVIfIndex
                    INTEGER,
                grIpxVStatus
                    RowStatus
            }


        grIpxVNetAddr OBJECT-TYPE
            SYNTAX  OCTET STRING (SIZE(4))
            ACCESS  read-only
            STATUS  mandatory
            DESCRIPTION
                    "Determines the network number this interface is
                    attached to."
            ::= { grIpxVirtualEntry 1 }


        grIpxVNetEncap OBJECT-TYPE
            SYNTAX  INTEGER {
                        ether2(1),
                        raw(2),
                        llc(3),
                        snap(4)
                    }
            ACCESS  read-write
            STATUS  mandatory
            DESCRIPTION
                    "The protocol encapsulation used on LAN's. Only
                    applies when the LAN destination is associated with
                    a physical LAN interface."
            ::= { grIpxVirtualEntry 2 }


        grIpxVRipEnable OBJECT-TYPE
            SYNTAX  INTEGER {
                        enabled(1),
                        disabled(2)
                    }
            ACCESS  read-write
            STATUS  mandatory
            DESCRIPTION
                    "Enables IPX RIP on this interface."
            ::= { grIpxVirtualEntry 3 }


        grIpxVRipMetric OBJECT-TYPE
            SYNTAX  INTEGER (1..16)
            ACCESS  read-write
            STATUS  mandatory
            DESCRIPTION
                    "This object determines the metric or cost that
                    will be added to the metric on learned routes from
                    this interface or on routes broadcast out this
                    interface. The default is 1."
            ::= { grIpxVirtualEntry 4 }


        grIpxVRipTxPeriod OBJECT-TYPE
            SYNTAX  INTEGER
            ACCESS  read-write
            STATUS  mandatory
            DESCRIPTION
                    "The RIP update period in seconds."
            ::= { grIpxVirtualEntry 5 }


        grIpxVRipAgeTimer OBJECT-TYPE
            SYNTAX  INTEGER
            ACCESS  read-write
            STATUS  mandatory
            DESCRIPTION
                    "The amount of time in seconds before this interface 
                    will age out a learned RIP entry."
            ::= { grIpxVirtualEntry 6 }


        grIpxVSapEnable OBJECT-TYPE
            SYNTAX  INTEGER {
                        enabled(1),
                        disabled(2)
                    }
            ACCESS  read-write
            STATUS  mandatory
            DESCRIPTION
                    "Enables IPX SAP on this interface."
            ::= { grIpxVirtualEntry 7 }


        grIpxVSapTxPeriod OBJECT-TYPE
            SYNTAX  INTEGER
            ACCESS  read-write
            STATUS  mandatory
            DESCRIPTION
                    "The RIP update period in seconds."
            ::= { grIpxVirtualEntry 8 }


        grIpxVSapAgeTimer OBJECT-TYPE
            SYNTAX  INTEGER
            ACCESS  read-write
            STATUS  mandatory
            DESCRIPTION
                    "The amount of time in seconds before this interfaces 
                    will age out a learned SAP entry."
            ::= { grIpxVirtualEntry 9 }


        grIpxVWdogSpoof OBJECT-TYPE
            SYNTAX  INTEGER {
                        enabled(1),
                        disabled(2)
                    }
            ACCESS  read-write
            STATUS  mandatory
            DESCRIPTION
                    "Enables or disables watchdog spoofing on this IPX
                    interface. Only applies to LAN destinations when
                    connected to physical LAN interfaces."
            ::= { grIpxVirtualEntry 10 }


        grIpxVIfIndex OBJECT-TYPE
            SYNTAX  INTEGER
            ACCESS  read-write
            STATUS  mandatory
            DESCRIPTION
                    "The interface on which this network is available 
                    through."
            ::= { grIpxVirtualEntry 11 }


        grIpxVStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpxVirtualEntry 12 }
--
--
--
--     IPX Virtual RIP Statistics.
--

    grIpxVRipTable OBJECT-TYPE
        SYNTAX  SEQUENCE OF GrIpxVRipEntry
        ACCESS  not-accessible
        STATUS  mandatory
        DESCRIPTION
                "This table contains IPX RIP statistics per IPX interface."
        ::= { grIpxGroup 20 }


        grIpxVRipEntry OBJECT-TYPE
            SYNTAX  GrIpxVRipEntry
            ACCESS  not-accessible
            STATUS  mandatory
            DESCRIPTION
                    "Each entry in this table contains specific information 
                    on RIP statistics for a single IPX interface."
            INDEX   { grIpxVNetAddr }
            ::= { grIpxVRipTable 1 }


        GrIpxVRipEntry ::=
            SEQUENCE {
               grIpxVRipRtePkts
                  Counter,
               grIpxVRipHopCntExcs
                  Counter,
               grIpxVRipNetbHopCntExcs
                  Counter,
               grIpxVRipNoNetAddRcvs
                  Counter,
               grIpxVRipRxGenQs
                  Counter,
               grIpxVRipRxNearQs
                  Counter,
               grIpxVRipRxGenRs
                  Counter,
               grIpxVRipRxNearRs
                  Counter,
               grIpxVRipTxGenQs
                  Counter,
               grIpxVRipTxNearQs
                  Counter,
               grIpxVRipTxGenRs
                  Counter,
               grIpxVRipTxNearRs
                  Counter,
               grIpxVRipRxUnknGenQs
                  Counter,
               grIpxVRipRxUnknNearQs
                  Counter,
               grIpxVRipRxUnknGenRs
                  Counter,
               grIpxVRipRxUnknNearRs
                  Counter,
               grIpxVRipAgedOuts
                  Counter,
               grIpxVRipPeriodics
                  Counter,
               grIpxVRipUpdates
                  Counter,
               grIpxVRipWrongNets
                  Counter,
               grIpxVRipBadInfos
                  Counter
            }


        grIpxVRipRtePkts OBJECT-TYPE
            SYNTAX  Counter
            ACCESS  read-only
            STATUS  mandatory
            DESCRIPTION
                    "The total number of packets that this interface
                    has routed excluding RIP and SAP packets."
            ::= { grIpxVRipEntry 1 }


        grIpxVRipHopCntExcs OBJECT-TYPE
            SYNTAX  Counter
            ACCESS  read-only
            STATUS  mandatory
            DESCRIPTION
                    "The total number of received IPX packets (excluding
		    netbios IPX packets) that were discarded because
		    the hop count (16 hops) was exceeded."
            ::= { grIpxVRipEntry 2 }


        grIpxVRipNetbHopCntExcs OBJECT-TYPE
            SYNTAX  Counter
            ACCESS  read-only
            STATUS  mandatory
            DESCRIPTION
                    "The total number of received netbios IPX packets
		    that were discarded because the hop count (8 hops)
                    was exceeded."
            ::= { grIpxVRipEntry 3 }


        grIpxVRipNoNetAddRcvs OBJECT-TYPE
            SYNTAX  Counter
            ACCESS  read-only
            STATUS  mandatory
            DESCRIPTION
                    "The total number of received RIP packets which
                    contained no network address."
            ::= { grIpxVRipEntry 4 }


        grIpxVRipRxGenQs OBJECT-TYPE
            SYNTAX  Counter
            ACCESS  read-only
            STATUS  mandatory
            DESCRIPTION
                    "The total number of received general queries."
            ::= { grIpxVRipEntry 5 }


        grIpxVRipRxNearQs OBJECT-TYPE
            SYNTAX  Counter
            ACCESS  read-only
            STATUS  mandatory
            DESCRIPTION
                    "The total number of received near queries."
            ::= { grIpxVRipEntry 6 }


        grIpxVRipRxGenRs OBJECT-TYPE
            SYNTAX  Counter
            ACCESS  read-only
            STATUS  mandatory
            DESCRIPTION
                    "The total number of received general responses."
            ::= { grIpxVRipEntry 7 }


        grIpxVRipRxNearRs OBJECT-TYPE
            SYNTAX  Counter
            ACCESS  read-only
            STATUS  mandatory
            DESCRIPTION
                    "The total number of received near responses."
            ::= { grIpxVRipEntry 8 }


        grIpxVRipTxGenQs OBJECT-TYPE
            SYNTAX  Counter
            ACCESS  read-only
            STATUS  mandatory
            DESCRIPTION
                    "The total number of transmitted general queries."
            ::= { grIpxVRipEntry 9 }


        grIpxVRipTxNearQs OBJECT-TYPE
            SYNTAX  Counter
            ACCESS  read-only
            STATUS  mandatory
            DESCRIPTION
                    "The total number of transmitted near queries."
            ::= { grIpxVRipEntry 10 }


        grIpxVRipTxGenRs OBJECT-TYPE
            SYNTAX  Counter
            ACCESS  read-only
            STATUS  mandatory
            DESCRIPTION
                    "The total number of transmitted general responses."
            ::= { grIpxVRipEntry 11 }


        grIpxVRipTxNearRs OBJECT-TYPE
            SYNTAX  Counter
            ACCESS  read-only
            STATUS  mandatory
            DESCRIPTION
                    "The total number of transmitted near responses."
            ::= { grIpxVRipEntry 12 }


        grIpxVRipRxUnknGenQs OBJECT-TYPE
            SYNTAX  Counter
            ACCESS  read-only
            STATUS  mandatory
            DESCRIPTION
                    "The total number of received unknown general queries."
            ::= { grIpxVRipEntry 13 }


        grIpxVRipRxUnknNearQs OBJECT-TYPE
            SYNTAX  Counter
            ACCESS  read-only
            STATUS  mandatory
            DESCRIPTION
                    "The total number of received unknown near queries."
            ::= { grIpxVRipEntry 14 }


        grIpxVRipRxUnknGenRs OBJECT-TYPE
            SYNTAX  Counter
            ACCESS  read-only
            STATUS  mandatory
            DESCRIPTION
                    "The total number of received unknown general responses."
            ::= { grIpxVRipEntry 15 }


        grIpxVRipRxUnknNearRs OBJECT-TYPE
            SYNTAX  Counter
            ACCESS  read-only
            STATUS  mandatory
            DESCRIPTION
                    "The total number of received unknown near responses."
            ::= { grIpxVRipEntry 16 }


        grIpxVRipAgedOuts OBJECT-TYPE
            SYNTAX  Counter
            ACCESS  read-only
            STATUS  mandatory
            DESCRIPTION
                    "The total number of route entries that have aged out."
            ::= { grIpxVRipEntry 17 }


        grIpxVRipPeriodics OBJECT-TYPE
            SYNTAX  Counter
            ACCESS  read-only
            STATUS  mandatory
            DESCRIPTION
                    "The total number of RIP periodics broadcasted."
            ::= { grIpxVRipEntry 18 }


        grIpxVRipUpdates OBJECT-TYPE
            SYNTAX  Counter
            ACCESS  read-only
            STATUS  mandatory
            DESCRIPTION
                    "The total number of RIP updates issued."
            ::= { grIpxVRipEntry 19 }


        grIpxVRipWrongNets OBJECT-TYPE
            SYNTAX  Counter
            ACCESS  read-only
            STATUS  mandatory
            DESCRIPTION
                    "The total number of received RIP packets with 
                    an incorrect network address."
            ::= { grIpxVRipEntry 20 }


        grIpxVRipBadInfos OBJECT-TYPE
            SYNTAX  Counter
            ACCESS  read-only
            STATUS  mandatory
            DESCRIPTION
                    "The total number of received RIP packets with
                    bad information."
            ::= { grIpxVRipEntry 21 }
--
--
--
--      IPX Virtual SAP Statistics.
--

    grIpxVSapTable OBJECT-TYPE
        SYNTAX  SEQUENCE OF GrIpxVSapEntry
        ACCESS  not-accessible
        STATUS  mandatory
        DESCRIPTION
                "This table contains SAP statistics for each IPX virtual 
                interface."
        ::= { grIpxGroup 21 }


        grIpxVSapEntry OBJECT-TYPE
            SYNTAX  GrIpxVSapEntry
            ACCESS  not-accessible
            STATUS  mandatory
            DESCRIPTION
                    "Each entry in this table contains specific information 
                    on SAP statistics for a single IPX interface."
            INDEX   { grIpxVNetAddr }
            ::= { grIpxVSapTable 1 }


        GrIpxVSapEntry ::=
            SEQUENCE {
               grIpxVSapRxGenQs
                  Counter,
               grIpxVSapRxNearQs
                  Counter,
               grIpxVSapRxGenRs
                  Counter,
               grIpxVSapRxNearRs
                  Counter,
               grIpxVSapTxGenQs
                  Counter,
               grIpxVSapTxNearQs
                  Counter,
               grIpxVSapTxGenRs
                  Counter,
               grIpxVSapTxNearRs
                  Counter,
               grIpxVSapRxUnknGenQs
                  Counter,
               grIpxVSapRxUnknNearQs
                  Counter,
               grIpxVSapRxUnknGenRs
                  Counter,
               grIpxVSapRxUnknNearRs
                  Counter,
               grIpxVSapAgedOuts
                  Counter,
               grIpxVSapPeriodics
                  Counter,
               grIpxVSapUpdates
                  Counter,
               grIpxVSapWrongNets
                  Counter,
               grIpxVSapBadInfos
                  Counter
            }


        grIpxVSapRxGenQs OBJECT-TYPE
            SYNTAX  Counter
            ACCESS  read-only
            STATUS  mandatory
            DESCRIPTION
                    "The total number of received general queries."
            ::= { grIpxVSapEntry 1 }


        grIpxVSapRxNearQs OBJECT-TYPE
            SYNTAX  Counter
            ACCESS  read-only
            STATUS  mandatory
            DESCRIPTION
                    "The total number of received near queries."
            ::= { grIpxVSapEntry 2 }


        grIpxVSapRxGenRs OBJECT-TYPE
            SYNTAX  Counter
            ACCESS  read-only
            STATUS  mandatory
            DESCRIPTION
                    "The total number of received general responses."
            ::= { grIpxVSapEntry 3 }


        grIpxVSapRxNearRs OBJECT-TYPE
            SYNTAX  Counter
            ACCESS  read-only
            STATUS  mandatory
            DESCRIPTION
                    "The total number of received near responses."
            ::= { grIpxVSapEntry 4 }


        grIpxVSapTxGenQs OBJECT-TYPE
            SYNTAX  Counter
            ACCESS  read-only
            STATUS  mandatory
            DESCRIPTION
                    "The total number of transmitted general queries."
            ::= { grIpxVSapEntry 5 }


        grIpxVSapTxNearQs OBJECT-TYPE
            SYNTAX  Counter
            ACCESS  read-only
            STATUS  mandatory
            DESCRIPTION
                    "The total number of transmitted near queries."
            ::= { grIpxVSapEntry 6 }


        grIpxVSapTxGenRs OBJECT-TYPE
            SYNTAX  Counter
            ACCESS  read-only
            STATUS  mandatory
            DESCRIPTION
                    "The total number of transmitted general responses."
            ::= { grIpxVSapEntry 7 }


        grIpxVSapTxNearRs OBJECT-TYPE
            SYNTAX  Counter
            ACCESS  read-only
            STATUS  mandatory
            DESCRIPTION
                    "The total number of transmitted near responses."
            ::= { grIpxVSapEntry 8 }


        grIpxVSapRxUnknGenQs OBJECT-TYPE
            SYNTAX  Counter
            ACCESS  read-only
            STATUS  mandatory
            DESCRIPTION
                    "The total number of received unknown general queries."
            ::= { grIpxVSapEntry 9 }


        grIpxVSapRxUnknNearQs OBJECT-TYPE
            SYNTAX  Counter
            ACCESS  read-only
            STATUS  mandatory
            DESCRIPTION
                    "The total number of received unknown near queries."
            ::= { grIpxVSapEntry 10 }


        grIpxVSapRxUnknGenRs OBJECT-TYPE
            SYNTAX  Counter
            ACCESS  read-only
            STATUS  mandatory
            DESCRIPTION
                    "The total number of received unknown general responses."
            ::= { grIpxVSapEntry 11 }


        grIpxVSapRxUnknNearRs OBJECT-TYPE
            SYNTAX  Counter
            ACCESS  read-only
            STATUS  mandatory
            DESCRIPTION
                    "The total number of received unknown near responses."
            ::= { grIpxVSapEntry 12 }


        grIpxVSapAgedOuts OBJECT-TYPE
            SYNTAX  Counter
            ACCESS  read-only
            STATUS  mandatory
            DESCRIPTION
                    "The total number of server entries that have aged out."
            ::= { grIpxVSapEntry 13 }


        grIpxVSapPeriodics OBJECT-TYPE
            SYNTAX  Counter
            ACCESS  read-only
            STATUS  mandatory
            DESCRIPTION
                    "The total number of SAP periodics broadcasted."
            ::= { grIpxVSapEntry 14 }


        grIpxVSapUpdates OBJECT-TYPE
            SYNTAX  Counter
            ACCESS  read-only
            STATUS  mandatory
            DESCRIPTION
                    "The total number of SAP updates issued."
            ::= { grIpxVSapEntry 15 }


        grIpxVSapWrongNets OBJECT-TYPE
            SYNTAX  Counter
            ACCESS  read-only
            STATUS  mandatory
            DESCRIPTION
                    "The total number of received SAP packets with
                    an incorrect network address."
            ::= { grIpxVSapEntry 16 }


        grIpxVSapBadInfos OBJECT-TYPE
            SYNTAX  Counter
            ACCESS  read-only
            STATUS  mandatory
            DESCRIPTION
                    "The total number of received SAP packets with
                    bad information."
            ::= { grIpxVSapEntry 17 }
--
--
--
--        IP GROUP OBJECTS
--        ================
--

    grIpRipEnable OBJECT-TYPE
        SYNTAX  INTEGER {
                   enabled(1),
                   disabled(2)
                }
        ACCESS  read-write
        STATUS  mandatory
        DESCRIPTION
                "Configures the router to enable IP RIP on a unit
                wide basis. Each logical port must still in turn
                have RIP enabled on a per port basis."
        ::= { grIpGroup 1 }


    grIpArpCacheAge OBJECT-TYPE
        SYNTAX  INTEGER (1..1200)
        ACCESS  read-write
        STATUS  mandatory
        DESCRIPTION
                "This object determines the elapsed time in seconds
                that a ARP binding will remain in the ARP cache before
                it is timed out if the entry has not been referenced."
        ::= { grIpGroup 2 }


    grIpProxyArp OBJECT-TYPE
        SYNTAX  INTEGER {
                   enabled(1),
                   disabled(2)
                }
        ACCESS  read-write
        STATUS  mandatory
        DESCRIPTION
                "Configures the router for proxy ARP on all LAN
                interfaces."
        ::= { grIpGroup 3 }
--
--
--
--      The Trusted Gateway Table.
--

    grIpTrustedGatewayEnable OBJECT-TYPE
        SYNTAX  INTEGER {
                   enabled(1),
                   disabled(2)
                }
        ACCESS  read-write
        STATUS  mandatory
        DESCRIPTION
                "This object indicates if this router is using
                the Trusted Gateway Table to accept dynamically
                learned routes."
        ::= { grIpGroup 4 }


    grIpTrustedGatewayTable OBJECT-TYPE
        SYNTAX  SEQUENCE OF GrIpTrustedGatewayEntry
        ACCESS  not-accessible
        STATUS  mandatory
        DESCRIPTION
                "This table is used to display and configure the trusted
                gateways that IP RIP will accept routing updates from."
        ::= { grIpGroup 5 }


        grIpTrustedGatewayEntry OBJECT-TYPE
            SYNTAX  GrIpTrustedGatewayEntry
            ACCESS  not-accessible
            STATUS  mandatory
            DESCRIPTION
                    "Each entry in this table contains information on a 
                    trusted gateway."
            INDEX   { grIpGatewayAddr }
            ::= { grIpTrustedGatewayTable 1 }


        GrIpTrustedGatewayEntry ::=
            SEQUENCE {
               grIpGatewayAddr
                  IpAddress,
               grIpGatewayName
                  DisplayString,
               grIpGatewayStatus
                  RowStatus
            }


        grIpGatewayAddr OBJECT-TYPE
            SYNTAX  IpAddress
            ACCESS  read-only
            STATUS  mandatory
            DESCRIPTION
                    "The IP address of the trusted gateway."
            ::= { grIpTrustedGatewayEntry 1 }


        grIpGatewayName OBJECT-TYPE
            SYNTAX  DisplayString (SIZE (1..16))
            ACCESS  read-write
            STATUS  mandatory
            DESCRIPTION
                    "This object indicates the associated name of
                    the trusted gateway."
            ::= { grIpTrustedGatewayEntry 2 }


        grIpGatewayStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpTrustedGatewayEntry 3 }
--
--
--
--      The IP Access Restriction Table.
--

    grIpAccessRestrictEnable OBJECT-TYPE
        SYNTAX  INTEGER {
                   enabled(1),
                   disabled(2)
                }
        ACCESS  read-write
        STATUS  mandatory
        DESCRIPTION
                "This object indicates if the IP Access Restriction table 
                is being used to filter/forward packets."
        ::= { grIpGroup 6 }


    grIpAccessRestrictTable OBJECT-TYPE
        SYNTAX  SEQUENCE OF GrIpAccessRestrictEntry
        ACCESS  not-accessible
        STATUS  mandatory
        DESCRIPTION
                "The IP Access Restriction configuration table."
        ::= { grIpGroup 7 }


        grIpAccessRestrictEntry OBJECT-TYPE
            SYNTAX  GrIpAccessRestrictEntry
            ACCESS  not-accessible
            STATUS  mandatory
            DESCRIPTION
                    "Contains information about a single IP Access
                    filter."
            INDEX   { grIpAccIndex }
            ::= { grIpAccessRestrictTable 1 }


        GrIpAccessRestrictEntry ::=
            SEQUENCE {
               grIpAccIndex
                  INTEGER,
               grIpAccName
                  DisplayString,
               grIpAccType
                  INTEGER,
               grIpAccSrcNet
                  IpAddress,
               grIpAccSrcMask
                  IpAddress,
               grIpAccDstNet
                  IpAddress,
               grIpAccDstMask
                  IpAddress,
               grIpAccProtocolFrom
                  INTEGER,
               grIpAccProtocolTo
                  INTEGER,
               grIpAccPortFrom
                  INTEGER,
               grIpAccPortTo
                  INTEGER,
               grIpAccStatus
                  RowStatus
            }


        grIpAccIndex OBJECT-TYPE
            SYNTAX  INTEGER
            ACCESS  read-only
            STATUS  mandatory
            DESCRIPTION
                    "Identifies the unique entry in this table."
            ::= { grIpAccessRestrictEntry 1 }


        grIpAccName OBJECT-TYPE
            SYNTAX  DisplayString (SIZE(1..16))
            ACCESS  read-write
            STATUS  mandatory
            DESCRIPTION
                    "The name associated with this entry."
            ::= { grIpAccessRestrictEntry 2 }


        grIpAccType OBJECT-TYPE
            SYNTAX  INTEGER {
                       filter(1),
                       forward(2)
                    }
            ACCESS  read-write
            STATUS  mandatory
            DESCRIPTION
                    "This object indicates what action should be taken 
                    when a match on this entry has occurred."
            ::= { grIpAccessRestrictEntry 3 }


        grIpAccSrcNet OBJECT-TYPE
            SYNTAX  IpAddress
            ACCESS  read-write
            STATUS  mandatory
            DESCRIPTION
                    "Defines the source IP address to match on."
            ::= { grIpAccessRestrictEntry 4 }


        grIpAccSrcMask OBJECT-TYPE
            SYNTAX  IpAddress
            ACCESS  read-write
            STATUS  mandatory
            DESCRIPTION
                    "Defines the source IP address mask to apply when
                    determing a match."
            ::= { grIpAccessRestrictEntry 5 }


        grIpAccDstNet OBJECT-TYPE
            SYNTAX  IpAddress
            ACCESS  read-write
            STATUS  mandatory
            DESCRIPTION
                    "Defines the destination IP address to match on."
            ::= { grIpAccessRestrictEntry 6 }


        grIpAccDstMask OBJECT-TYPE
            SYNTAX  IpAddress
            ACCESS  read-write
            STATUS  mandatory
            DESCRIPTION
                    "Defines the destination IP address mask to apply when
                    determing a match."
            ::= { grIpAccessRestrictEntry 7 }


        grIpAccProtocolFrom OBJECT-TYPE
            SYNTAX  INTEGER (0..255)
            ACCESS  read-write
            STATUS  mandatory
            DESCRIPTION
                    "Defines the FROM portion of the protocol ID range."
            ::= { grIpAccessRestrictEntry 8 }


        grIpAccProtocolTo OBJECT-TYPE
            SYNTAX  INTEGER (0..255)
            ACCESS  read-write
            STATUS  mandatory
            DESCRIPTION
                    "Defines the TO portion of the protocol ID range."
            ::= { grIpAccessRestrictEntry 9 }


        grIpAccPortFrom OBJECT-TYPE
            SYNTAX  INTEGER (0..65535)
            ACCESS  read-write
            STATUS  mandatory
            DESCRIPTION
                    "Defines the FROM portion of the port number range."
            ::= { grIpAccessRestrictEntry 10 }


        grIpAccPortTo OBJECT-TYPE
            SYNTAX  INTEGER (0..65535)
            ACCESS  read-write
            STATUS  mandatory
            DESCRIPTION
                    "Defines the TO portion of the port number range."
            ::= { grIpAccessRestrictEntry 11 }


        grIpAccStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpAccessRestrictEntry 12 }
--
--
--      The IP Logical Port Configuration Table
--

    grIpLogicalTable OBJECT-TYPE
        SYNTAX  SEQUENCE OF GrIpLogicalEntry
        ACCESS  not-accessible
        STATUS  mandatory
        DESCRIPTION
                "A table containing information about logical IP LAN
                destinations."
        ::= { grIpGroup 8 }


        grIpLogicalEntry OBJECT-TYPE
            SYNTAX  GrIpLogicalEntry
            ACCESS  not-accessible
            STATUS  mandatory
            DESCRIPTION
                    "Each entry of this table contains information about
                    a specific logical interface to a local area network.
                    Each logical LAN can support routing or bridging
                    functions, these are considered virtual interfaces."
            INDEX   { ifIndex }
            ::= { grIpLogicalTable 1 }


        GrIpLogicalEntry ::=
            SEQUENCE {
                grIpLAccessDef
                   INTEGER,
                grIpLRestrictions
                   OCTET STRING,
                grIpLTransport
                   INTEGER,
                grIpLStatus
                   RowStatus
            }


        grIpLAccessDef OBJECT-TYPE
            SYNTAX  INTEGER {
                        filter(1),
                        forward(2)
                    }
            ACCESS  read-write
            STATUS  mandatory
            DESCRIPTION
                    "This object indicates what the default access rights
                    will apply to IP packets that do not match any of the
                    access restrictions."
            ::= { grIpLogicalEntry 1 }


        grIpLRestrictions OBJECT-TYPE
            SYNTAX  OCTET STRING
            ACCESS  read-write
            STATUS  mandatory
            DESCRIPTION
                    "This object specifies the access filter/forward
                    restrictions for this logical destination for IP
                    packets. Each octet represents an entry (grIpAccIndex)
                    in the grIpAccessRestrictTable."
            ::= { grIpLogicalEntry 2 }


        grIpLTransport OBJECT-TYPE
            SYNTAX  INTEGER {
                        ipcp(1),
                        bncp(2)
                    }
            ACCESS  read-write
            STATUS  mandatory
            DESCRIPTION
                    "This object indicates the transport NCP to use within
                    a PPP connection."
            ::= { grIpLogicalEntry 3 }


        grIpLStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpLogicalEntry 4 }
--
--
--
--     The IP Virtual Port Configuration Table.
--

    grIpVirtualTable OBJECT-TYPE
        SYNTAX  SEQUENCE OF GrIpVirtualEntry
        ACCESS  not-accessible
        STATUS  mandatory
        DESCRIPTION
                "This table is used to display and configure IP virtual 
                port information. Each logical LAN destination may have 
                one or more IP virtuals."
        ::= { grIpGroup 9 }


        grIpVirtualEntry OBJECT-TYPE
            SYNTAX  GrIpVirtualEntry
            ACCESS  not-accessible
            STATUS  mandatory
            DESCRIPTION
                    "Each entry in this table contains configuration
                    information specific to a single IP interface."
            INDEX   { grIpVNetAddr }
            ::= { grIpVirtualTable 1 }


        GrIpVirtualEntry ::=
            SEQUENCE {
                grIpVNetAddr
                    IpAddress,
                grIpVNetMask
                    IpAddress,
                grIpVNetEncap
                    INTEGER,
                grIpVBcastAddr
                    INTEGER,
                grIpVRipTx
                    INTEGER,
                grIpVSendDefaultRoute
                   INTEGER,
                grIpVSendStaticRoutes
                   INTEGER,
                grIpVRipRx
                    INTEGER,
                grIpVRipMetric
                    INTEGER,
                grIpVOverrideDefaultRoute
                   INTEGER,
                grIpVIfIndex
                   INTEGER,
                grIpVStatus
                   RowStatus
            }


        grIpVNetAddr OBJECT-TYPE
            SYNTAX  IpAddress
            ACCESS  read-only
            STATUS  mandatory
            DESCRIPTION
                    "The IP address that uniquely identifies this entry."
            ::= { grIpVirtualEntry 1 }


        grIpVNetMask OBJECT-TYPE
            SYNTAX  IpAddress
            ACCESS  read-write
            STATUS  mandatory
            DESCRIPTION
                    "The subnet mask assigned to this entry."
            ::= { grIpVirtualEntry 2 }


        grIpVNetEncap OBJECT-TYPE
            SYNTAX  INTEGER {
                        ether2(1),
                        snap(2)
                    }
            ACCESS  read-write
            STATUS  mandatory
            DESCRIPTION
                    "The encapsulation method used on all IP frames 
                    transmitted out this interface."
            ::= { grIpVirtualEntry 3 }


        grIpVBcastAddr OBJECT-TYPE
            SYNTAX  INTEGER {
                        allOnes(1),
                        allZeros(2)
                    }
            ACCESS  read-write
            STATUS  mandatory
            DESCRIPTION
                    "The value of the least-significant bit in the
                    IP broadcast address used for sending datagrams on
                    the interface associated with the IP address of this 
                    entry. For example, when the Internet standard 
                    all-ones broadcast address is used, the value will 
                    be 1. This value applies to both the subnet and 
                    network broadcasts addresses used by the entity on 
                    this interface."
            ::= { grIpVirtualEntry 4 }


        grIpVRipTx OBJECT-TYPE
            SYNTAX  INTEGER {
                        enabled(1),
                        disabled(2)
                    }
            ACCESS  read-write
            STATUS  mandatory
            DESCRIPTION
                    "Enables or disables the sending of RIP information
                    for this IP interface."
            ::= { grIpVirtualEntry 5 }


        grIpVSendDefaultRoute OBJECT-TYPE
            SYNTAX  INTEGER {
                        enabled(1),
                        disabled(2)
                    }
            ACCESS  read-write
            STATUS  mandatory
            DESCRIPTION
                    "Enables or disables the sending of default routes
                    via RIP on this interface."
            ::= { grIpVirtualEntry 6 }


        grIpVSendStaticRoutes OBJECT-TYPE
            SYNTAX  INTEGER {
                        enabled(1),
                        disabled(2)
                    }
            ACCESS  read-write
            STATUS  mandatory
            DESCRIPTION
                    "Enables or disables the sending of static routes
                    via RIP over this interface."
            ::= { grIpVirtualEntry 7 }


        grIpVRipRx OBJECT-TYPE
            SYNTAX  INTEGER {
                        enabled(1),
                        disabled(2)
                    }
            ACCESS  read-write
            STATUS  mandatory
            DESCRIPTION
                    "Determines whether or not RIP will ignore or update
                    its routing tables for this interface when a RIP
                    packet is received."
            ::= { grIpVirtualEntry 8 }


        grIpVRipMetric OBJECT-TYPE
            SYNTAX  INTEGER (1..16)
            ACCESS  read-write
            STATUS  mandatory
            DESCRIPTION
                    "This object determines the metric or cost that
                    will be added to the metric on learned routes from
                    this interface or on routes broadcast out this
                    interface. The default is 1."
            ::= { grIpVirtualEntry 9 }


        grIpVOverrideDefaultRoute OBJECT-TYPE
            SYNTAX  INTEGER {
                        enabled(1),
                        disabled(2)
                    }
            ACCESS  read-write
            STATUS  mandatory
            DESCRIPTION
                    "Determines if RIP will override the statically
                    configured default route if a better learned
                    route is found."
            ::= { grIpVirtualEntry 10 }


        grIpVIfIndex OBJECT-TYPE
            SYNTAX INTEGER
            ACCESS  read-write
            STATUS  mandatory
            DESCRIPTION
                    "The interface that this virtual is associated
                    with."
            ::= { grIpVirtualEntry 11 }


        grIpVStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grIpVirtualEntry 12 }
--
--
--
--      The IP Virtual Port RIP Table.
--

    grIpVRipTable OBJECT-TYPE
        SYNTAX  SEQUENCE OF GrIpVRipEntry
        ACCESS  not-accessible
        STATUS  mandatory
        DESCRIPTION
                "This table contains RIP statistics per IP virtual 
                interfaces."
        ::= { grIpGroup 10 }


        grIpVRipEntry OBJECT-TYPE
            SYNTAX  GrIpVRipEntry
            ACCESS  not-accessible
            STATUS  mandatory
            DESCRIPTION
                    "Each entry in this table contains RIP statistics
                    specific to a single IP interface."
            INDEX   { grIpVNetAddr }
            ::= { grIpVRipTable 1 }


        GrIpVRipEntry ::=
            SEQUENCE {
                grIpVRipRxPkts
                    Counter,
                grIpVRipRxBadPkts
                    Counter,
                grIpVRipRxBadRtes
                    Counter,
                grIpVRipTxUpdates
                    Counter
            }


        grIpVRipRxPkts OBJECT-TYPE
            SYNTAX  Counter
            ACCESS  read-only
            STATUS  mandatory
            DESCRIPTION
                    "This object indicates the number of RIP packets
                    regardless of RIP type received on this virtual port."
            ::= { grIpVRipEntry 1 }


        grIpVRipRxBadPkts OBJECT-TYPE
            SYNTAX  Counter
            ACCESS  read-only
            STATUS  mandatory
            DESCRIPTION
                    "This object indicates the number of received packets
                    that contained incorrect header/packet definition
                    (ie: unsupported version(0), non-zero must be zero
                    fields)."
            ::= { grIpVRipEntry 2 }


        grIpVRipRxBadRtes OBJECT-TYPE
            SYNTAX  Counter
            ACCESS  read-only
            STATUS  mandatory
            DESCRIPTION
                    "This object indicates the number of received packet
                    entries that contained bad route information (ie:
                    unsupported family(AF_INET), bad metric or a
                    bad network address."
            ::= { grIpVRipEntry 3 }


        grIpVRipTxUpdates OBJECT-TYPE
            SYNTAX  Counter
            ACCESS  read-only
            STATUS  mandatory
            DESCRIPTION
                    "The number of updates sent on this interface."
            ::= { grIpVRipEntry 4 }
--
--
--
--         SNMP GROUP OBJECTS
--         ==================
--

    grSnmpNetworkSet OBJECT-TYPE
        SYNTAX  INTEGER {
                    enabled(1),
                    disabled(2)
                }
        ACCESS  read-write
        STATUS  mandatory
        DESCRIPTION
                "This object indicates whether SNMP network sets are
                allowed. If not then only local sets from the console
                are permitted."
        ::= { grSnmpGroup 1 }

    grSnmpCommunityTable OBJECT-TYPE
        SYNTAX  SEQUENCE OF GrSnmpCommunityEntry
        ACCESS  not-accessible
        STATUS  mandatory
        DESCRIPTION
                "This table describes the SNMP management communities
                supported by this SNMP agent."
        ::= { grSnmpGroup 2 }


        grSnmpCommunityEntry OBJECT-TYPE
            SYNTAX  GrSnmpCommunityEntry
            ACCESS  not-accessible
            STATUS  mandatory
            DESCRIPTION
                    "Each entry in this table describes the attributes
                    of each SNMP community supported by this SNMP agent."
            INDEX  { grCommunityIndex }
            ::= { grSnmpCommunityTable 1 }


        GrSnmpCommunityEntry ::=
            SEQUENCE {
                grCommunityIndex
                    INTEGER,
                grCommunityName
                    DisplayString,
                grCommunityType
                    INTEGER,
                grCommunityPriv
                    INTEGER,
                grCommunityTrapGeneration
                    INTEGER,
                grCommunityTrapPort
                    INTEGER,
                grCommunityStatus
                    RowStatus
            }


        grCommunityIndex OBJECT-TYPE
            SYNTAX  INTEGER
            ACCESS  read-only
            STATUS  mandatory
            DESCRIPTION
                    "The index that identifies this community."
            ::= { grSnmpCommunityEntry 1 }

	
        grCommunityName OBJECT-TYPE
            SYNTAX  DisplayString (SIZE (1..16))
            ACCESS  read-write
            STATUS  mandatory
            DESCRIPTION
                    "The name of a Community that will be allowed access 
                    by the SNMP agent."
            ::= { grSnmpCommunityEntry 2 }


        grCommunityType OBJECT-TYPE
            SYNTAX  INTEGER {
                        public(1),
                        restricted(2)
            }
            ACCESS  read-write
            STATUS  mandatory
            DESCRIPTION
                    "This object defines whether this community provides
                    public or restricted access. Restricted access requires
                    that all SNMP requests to this agent must have a IP
                    address listed in the grSnmpCommMemberTable associated
                    with this community."
            ::= { grSnmpCommunityEntry 3 }


        grCommunityPriv OBJECT-TYPE
            SYNTAX  INTEGER {
                        none(1),
                        readonly(2),
                        readwrite(3)
                    }
            ACCESS  read-write
            STATUS  mandatory
            DESCRIPTION
                    "The access priviledge associated with this community."
            ::= { grSnmpCommunityEntry 4 }


        grCommunityTrapGeneration OBJECT-TYPE
            SYNTAX  INTEGER {
                        none(1),
                        all(2)
                    }
            ACCESS  read-write
            STATUS  mandatory
            DESCRIPTION
                    "This object indicates whether or not trap events
                    are issued to the IP addresses listed for this 
                    community."
            ::= { grSnmpCommunityEntry 5 }


        grCommunityTrapPort OBJECT-TYPE
            SYNTAX  INTEGER
            ACCESS  read-write
            STATUS  mandatory
            DESCRIPTION
                    "The remote UDP port number that traps will be sent
                    to (default port 162 is used)."
            ::= { grSnmpCommunityEntry 6 }


        grCommunityStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grSnmpCommunityEntry 7 }
--
--
--
--
--     The SNMP Community Members Table
--

    grSnmpCommMemberTable OBJECT-TYPE
        SYNTAX  SEQUENCE OF GrSnmpCommMemberEntry
        ACCESS  not-accessible
        STATUS  mandatory
        DESCRIPTION
                "This table describes the SNMP management community
                members supported by this SNMP agent."
        ::= { grSnmpGroup 3 }


        grSnmpCommMemberEntry OBJECT-TYPE
            SYNTAX  GrSnmpCommMemberEntry
            ACCESS  not-accessible
            STATUS  mandatory
            DESCRIPTION
                    "Each entry in this table is a management stations
                    address."
            INDEX  { grCommunityIndex,
                     grCommMemberIpAddr }
            ::= { grSnmpCommMemberTable 1 }


        GrSnmpCommMemberEntry ::=
            SEQUENCE {
                grCommMemberIpAddr
                    IpAddress,
                grCommMemberStatus
                    RowStatus
            }


        grCommMemberIpAddr OBJECT-TYPE
            SYNTAX  IpAddress
            ACCESS  read-only
            STATUS  mandatory
            DESCRIPTION
                    "The IP Address of a manager associated with this
                    Community that will be supported by the SNMP agent."
            ::= { grSnmpCommMemberEntry 1 }


        grCommMemberStatus OBJECT-TYPE
            SYNTAX  RowStatus
            ACCESS  read-write
            STATUS  mandatory
            DESCRIPTION
                    "The current status of this entry."
            REFERENCE
                    "Textual Conventions for Version 2 of the
                    Simple Network Management Protocol (RFC 1443)."
            ::= { grSnmpCommMemberEntry 2 }
--^L
--
--
--          PPP GROUP OBJECTS
--          =================
--

    grPppLinkStatusTable   OBJECT-TYPE
        SYNTAX    SEQUENCE OF GrPppLinkStatusEntry
        ACCESS    not-accessible
        STATUS    mandatory
        DESCRIPTION
                "A table containing PPP-link specific variables
                for this PPP implementation. An extension table to
                pppLinkStatusTable in RFC 1471."
        ::= { grPppGroup 1 }
 
        grPppLinkStatusEntry   OBJECT-TYPE
            SYNTAX    GrPppLinkStatusEntry
            ACCESS    not-accessible
            STATUS    mandatory
            DESCRIPTION
                    "Management information about a particular PPP
                    Link."
            INDEX   { ifIndex }
            ::= { grPppLinkStatusTable 1 }
 
        GrPppLinkStatusEntry ::= 
            SEQUENCE {
                grPppLinkStatusMultilink
                   INTEGER,
                grPppLinkStatusLapB
                   INTEGER
            }


        grPppLinkStatusMultilink OBJECT-TYPE
            SYNTAX  INTEGER {
                        enabled(1),
                        disabled(2)
                    }
            ACCESS  read-only
            STATUS  mandatory
            DESCRIPTION
                    "Indicates whether PPP multi-link operation is in
                    effect on this link. The value of this object is 
                    meaningful only when the link has reached the open
                    state (ifOperStatus is up)."
            ::= { grPppLinkStatusEntry 1 }
 
 
        grPppLinkStatusLapB OBJECT-TYPE
            SYNTAX  INTEGER {
                        enabled(1),
                        disabled(2)
                    }
            ACCESS  read-only
            STATUS  mandatory
            DESCRIPTION
                    "Indicates whether lapb is being used at the link 
                    layer on this link. The value of this object is 
                    meaningful only when the link has reached the open
                    state (ifOperStatus is up)."
            ::= { grPppLinkStatusEntry 2 }

--
--
--
--     IPX NCP Table Objects
--

    grPppIpxTable   OBJECT-TYPE
        SYNTAX    SEQUENCE OF GrPppIpxEntry
        ACCESS    not-accessible
        STATUS    mandatory
        DESCRIPTION
                "A table containing IPXCP parameters for the
                local PPP entity."
        ::= { grPppGroup 2 }
 
        grPppIpxEntry   OBJECT-TYPE
            SYNTAX    GrPppIpxEntry
            ACCESS    not-accessible
            STATUS    mandatory
            DESCRIPTION
                    "IPXCP status information for a particular PPP
                    link."
            INDEX   { ifIndex }
            ::= { grPppIpxTable 1 }
 
        GrPppIpxEntry ::=
            SEQUENCE {
                grPppIpxAdminStatus
                   INTEGER,
                grPppIpxOperStatus
                   INTEGER
            }
 
 
        grPppIpxAdminStatus OBJECT-TYPE
            SYNTAX  INTEGER {
                        open(1),
                        close(2)
                    }
            ACCESS  read-write
            STATUS  mandatory
            DESCRIPTION
                    "The immediate desired status of the IPX network
                    protocol. Setting this object to open will
                    inject an administrative open event into the IPX
                    network protocol's finite state machine.
                    Setting this object to close will inject an
                    administrative close event into the IPX network
                    protocol's finite state machine."
            ::= { grPppIpxEntry 1 }


        grPppIpxOperStatus OBJECT-TYPE
            SYNTAX  INTEGER {
                        opened(1),
                        not-opened(2)
                    }
            ACCESS  read-only
            STATUS  mandatory
            DESCRIPTION
                    "The operational status of the IPX network
                    protocol. If the value of this object is up
                    then the finite state machine for the IPX
                    network protocol has reached the Opened state."
            ::= { grPppIpxEntry 2 }

--
--  
--
--
--       Trap Definitions
--
--   All the following traps will contain the snmpTrapDescription
--   object which provides a textual description of the trap.

    grNewIpDefaultGateway TRAP-TYPE
        ENTERPRISE  gandalf
        DESCRIPTION
                "The grNewIpDefaultGateway trap indicates that the
                router has learned of a new default gateway (0.0.0.0).
                This will cause the router to start forwarding all IP 
                traffic whose destination networks are not in the 
                routing tables to this default gateway/router."
        ::= 1200


    grIpStaticRouteOverride TRAP-TYPE
        ENTERPRISE  gandalf
        DESCRIPTION
                "The grIpStaticRouteOverride trap is generated by the
                router whenever a statically configured IP route has 
                been overridden by a dynamically learned route (the 
                dynamic route has better metrics)."
        ::= 1201
 
 
    grIpxStaticRouteOverride TRAP-TYPE
        ENTERPRISE  gandalf
        DESCRIPTION
                "The grIpStaticRouteOverride trap is generated by the
                router whenever a statically configured IPX route has 
                been overridden by a dynamically learned route (the 
                dynamic route has better metrics)."
        ::= 1202
 
 
    grPppLqmFailed TRAP-TYPE
        ENTERPRISE  gandalf
        DESCRIPTION
                "The grPppLqmFailed trap indicates that a PPP link is
                suffering from a loss of link quality. Normally this
                will cause retransmission and/or traffic errors which 
                may prove the link to be unusable. The ifIndex will be
                provided in the variable bindings for this trap type."
        ::= 1203
 
 
    grWanRetryThreshold TRAP-TYPE
        ENTERPRISE  gandalf
        DESCRIPTION
                "The grWanRetryThreshold trap is generated by the 
                router whenever the maximum number of retries have
                been exhausted when attempting to contact a remote
                site on a specific serial interface. The ifIndex will
                provided in the variable bindings for this trap type."
        ::= 1204
 
END
