OWNEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, RowStatus
			FROM SNMPv2-TC
		ownExt
			FROM APENT-MIB;

--OWNEXT MIB

    apOwnExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  Web Host Owner information"
      ::= { ownExt 1}

apOwnTable OBJECT-TYPE
	SYNTAX          SEQUENCE OF APOwnEntry
	MAX-ACCESS      not-accessible
	STATUS          current
	DESCRIPTION
		"A list of information for the specified owner."
	::= { ownExt 2 }

apOwnEntry OBJECT-TYPE
	SYNTAX          APOwnEntry
	MAX-ACCESS      not-accessible
	STATUS          current
	DESCRIPTION
		"A group of information to uniquely identify an owner providing 
		Web host service."
	INDEX   { apOwnName }
	--DEFAULT apjam-group apOwnerRowInst, apOwnName
	--DEFAULT apjam-popup-def apOwnerRowInst, Properties, local
	--DEFAULT apjam-popup-def apOwnerRowInst, Statistics, chart OwnerChartGroup
	--DEFAULT apjam-popup-def apOwnerRowInst, Delete, special, apOwnStatus
	--DEFAULT apjam-wizard	Owner Wizard, 1, images/arrowlogo.gif, "Owners are the basis for hosting a website."
	--DEFAULT apjam-wizard	Owner Wizard, 2, images/arrowlogo.gif, ""
	--DEFAULT apjam-chart-group OwnerChartGroup, com.arrowpoint.auto.charts.ownHitsChart, apOwnerRowInst
	::= { apOwnTable 1 }

APOwnEntry ::= SEQUENCE {
		apOwnName                 	   DisplayString,
		apOwnIndex               	   Integer32,
		apOwnMaxFlowPipeBwdth          Integer32,
		apOwnFlowPipeBurstTolerance    Integer32,
		apOwnMaxPrioritizedFlows       Integer32,
	    apOwnBillingInfo	           DisplayString,
		apOwnAddress                   DisplayString,
		apOwnEmailAddress              DisplayString,
		apOwnFlowPipeBwdthAlloc        Integer32,
		apOwnFlowPipeActiveFlows       Integer32,
		apOwnFlowPipeTotalFlows        Integer32,
		apOwnFlowPipeTotalMisses       Integer32,
		apOwnQosBwdthAlloc             Integer32,
		apOwnBEBwdthAlloc			 Integer32,
		apOwnHits                    Integer32,
		apOwnRedirects               Integer32,
		apOwnDrops                   Integer32,
		apOwnRejNoServices           Integer32,
		apOwnRejServOverload         Integer32,
		apOwnSpoofs                  Integer32,
		apOwnNats                    Integer32,
		apOwnByteCount               Integer32,
		apOwnFrameCount              Integer32,
		apOwnDNSPolicy               INTEGER,
	 	apOwnStatus 				   RowStatus,
		apOwnCaseSensitive           INTEGER,
		apOwnDNSBalance               INTEGER
}

apOwnName OBJECT-TYPE
	SYNTAX          DisplayString (SIZE(1..31))
	MAX-ACCESS      read-create
	STATUS          current
	DESCRIPTION     
			"The name of the owner providing Web hosting service."
	--DEFAULT ap-display-name	Name
	--DEFAULT apjam-popup-ref apOwnerRowInst, Properties
	--DEFAULT ap-create-requires Yes
	--DEFAULT apjam-noedit-dlg	True
	--DEFAULT apjam-wizard-field	1, normal
	::= {apOwnEntry 1}

apOwnIndex OBJECT-TYPE
	SYNTAX          Integer32
	MAX-ACCESS      read-only
	STATUS  		current
	DESCRIPTION     
		"The unique index for each owner providing Web hosting service."
	::= {apOwnEntry 2}

apOwnMaxFlowPipeBwdth OBJECT-TYPE
	SYNTAX          Integer32 ( 0..100000 )
	MAX-ACCESS      read-create
	STATUS  		current
	DESCRIPTION     
		"The Max Flow pipe Bandwidth allowed for this owner used by all non guaranteed service flows."
	DEFVAL { 0 }
	--DEFAULT ap-display-name	Max Flowpipe Bandwidth
	::= {apOwnEntry 3}

apOwnFlowPipeBurstTolerance  OBJECT-TYPE
	SYNTAX          Integer32 (0..1000)
	MAX-ACCESS      read-create
	STATUS  		current
	DESCRIPTION     
		"The Burst Tolerance percentage configured for this owner's prioritized Bandwidth."
	DEFVAL { 0 }
	--DEFAULT ap-display-name	Flowpipe Burst Tolerance
	::= {apOwnEntry 4}

apOwnMaxPrioritizedFlows OBJECT-TYPE
	SYNTAX          Integer32 (0..100000)
	MAX-ACCESS      read-create
	STATUS  		current
	DESCRIPTION     
		"The Maximum number of prioritized flows allowed for this owner."
	DEFVAL { 0 }
	--DEFAULT ap-display-name	Max Prioritized Flows
	::= {apOwnEntry 5}


apOwnBillingInfo OBJECT-TYPE
	SYNTAX          DisplayString (SIZE(0..128))
	MAX-ACCESS      read-create
	STATUS          current
	DESCRIPTION     
			"The billing information of the owner providing Web hosting service."
	--DEFAULT ap-display-name	Billing Information
	--DEFAULT apjam-popup-ref apOwnerRowInst, Properties
	--DEFAULT apjam-wizard-field	2, normal
	::= {apOwnEntry 6}

apOwnAddress OBJECT-TYPE
	SYNTAX          DisplayString (SIZE(0..128))
	MAX-ACCESS      read-create
	STATUS          current
	DESCRIPTION     
			"The address of the owner providing Web hosting service."
	--DEFAULT ap-display-name	Address
	--DEFAULT apjam-popup-ref apOwnerRowInst, Properties
	--DEFAULT apjam-wizard-field	2, normal
	::= {apOwnEntry 7}

apOwnEmailAddress OBJECT-TYPE
	SYNTAX          DisplayString (SIZE(0..64 ))
	MAX-ACCESS      read-create
	STATUS          current
	DESCRIPTION     
			"The email address of the owner providing Web hosting service."
	--DEFAULT ap-display-name	Email Address
	--DEFAULT apjam-popup-ref apOwnerRowInst, Properties
	--DEFAULT apjam-wizard-field	2, normal
	::= {apOwnEntry 8}

apOwnFlowPipeBwdthAlloc		OBJECT-TYPE
			SYNTAX          Integer32  (0.. 100000)
			MAX-ACCESS      read-only
			STATUS  		current
	DESCRIPTION     
		"The statistics of allocated Flow Pipe Bandwidth for this owner."
	DEFVAL { 0 }
	--DEFAULT ap-display-name	Current Flowpipe Bandwidth
	--DEFAULT apjam-popup-ref apOwnerRowInst, Statistics
	::= {apOwnEntry 9}
		
apOwnFlowPipeActiveFlows		OBJECT-TYPE
			SYNTAX          Integer32  (0.. 100000)
			MAX-ACCESS      read-only
			STATUS  		current
	DESCRIPTION     
		"The statistics of Number of active Flow Pipe flows for this owner."
	DEFVAL { 0 }
	--DEFAULT ap-display-name	Active Flow Count
	::= {apOwnEntry 10}

apOwnFlowPipeTotalFlows		OBJECT-TYPE
			SYNTAX          Integer32  (0.. 100000)
			MAX-ACCESS      read-only
			STATUS  		current
	DESCRIPTION     
		"The statistics of total number of  Flow Pipe flows for this owner."
	DEFVAL { 0 }
	--DEFAULT ap-display-name	Total Flows
	::= {apOwnEntry 11}

apOwnFlowPipeTotalMisses		OBJECT-TYPE
			SYNTAX          Integer32  (0.. 100000)
			MAX-ACCESS      read-only
			STATUS  		current
	DESCRIPTION     
		"The statistics total number of missed flow pipe flows for this owner."
	DEFVAL { 0 }
	--DEFAULT ap-display-name	Flowpipe Misses
	::= {apOwnEntry 12}

apOwnQosBwdthAlloc		OBJECT-TYPE
			SYNTAX          Integer32  (0.. 100000)
			MAX-ACCESS      read-only
			STATUS  		current
	DESCRIPTION     
		"The statistics of allocated Guaranteed Bandwidth for this owner for all QoS classes defined by this owner."
	DEFVAL { 0 }
	--DEFAULT ap-display-name	Current QOS Bandwidth
	--DEFAULT apjam-popup-ref apOwnerRowInst, Statistics
	::= {apOwnEntry 13 }

apOwnBEBwdthAlloc		OBJECT-TYPE
			SYNTAX          Integer32  (0.. 100000)
			MAX-ACCESS      read-only
			STATUS  		current
	DESCRIPTION     
		"The statistics of allocated Best Effort Bandwidth for this owner."
	DEFVAL { 0 }
	--DEFAULT ap-display-name	Current BestEffort Bandwidth
	::= {apOwnEntry 14 }


apOwnHits OBJECT-TYPE
	SYNTAX          Integer32
	MAX-ACCESS      read-only
	STATUS  		current
	DESCRIPTION     
		"Total number of hits for this owner."
	DEFVAL { 0 }
	--DEFAULT ap-display-name	Hits
	--DEFAULT apjam-popup-ref apOwnerRowInst, Statistics
	--DEFAULT apjam-chart-def ownHitsChart, pie, apOwnerRowInst, "Hit Information for Owner"
	--DEFAULT apjam-chart-item ownHitsChart, get, green
	::= {apOwnEntry 15}

apOwnRedirects OBJECT-TYPE
	SYNTAX          Integer32
	MAX-ACCESS      read-only
	STATUS  		current
	DESCRIPTION     
		"Total number of redirects for this owner."
	DEFVAL { 0 }
	--DEFAULT ap-display-name	Redirects
	--DEFAULT apjam-popup-ref apOwnerRowInst, Statistics
	--DEFAULT apjam-chart-item ownHitsChart, get, blue
	::= {apOwnEntry 16}

apOwnDrops OBJECT-TYPE
	SYNTAX          Integer32
	MAX-ACCESS      read-only
	STATUS  		current
	DESCRIPTION     
		"Total number of dropped requests for this owner."
	DEFVAL { 0 }
	--DEFAULT ap-display-name	Drops
	--DEFAULT apjam-popup-ref apOwnerRowInst, Statistics
	--DEFAULT apjam-chart-item ownHitsChart, get, orange
	::= {apOwnEntry 17}

apOwnRejNoServices OBJECT-TYPE
	SYNTAX          Integer32
	MAX-ACCESS      read-only
	STATUS  		current
	DESCRIPTION     
		"Total number of rejects due to no service available for this owner."
	DEFVAL { 0 }
	--DEFAULT ap-display-name	Reject No Services
	--DEFAULT apjam-popup-ref apOwnerRowInst, Statistics
	--DEFAULT apjam-chart-item ownHitsChart, get, red
	::= {apOwnEntry 18}

apOwnRejServOverload OBJECT-TYPE
	SYNTAX          Integer32
	MAX-ACCESS      read-only
	STATUS  		current
	DESCRIPTION     
		"Total number of rejects due to no service overloaded for this owner."
	DEFVAL { 0 }
	--DEFAULT ap-display-name	Reject Services Overload
	--DEFAULT apjam-popup-ref apOwnerRowInst, Statistics
	--DEFAULT apjam-chart-item ownHitsChart, get, yellow
	::= {apOwnEntry 19}

apOwnSpoofs OBJECT-TYPE
	SYNTAX          Integer32
	MAX-ACCESS      read-only
	STATUS  		current
	DESCRIPTION     
		"Total number of spoofed requests for this owner."
	DEFVAL { 0 }
	--DEFAULT ap-display-name	Spoof Flows
	--DEFAULT apjam-popup-ref apOwnerRowInst, Statistics
	::= {apOwnEntry 20}

apOwnNats OBJECT-TYPE
	SYNTAX          Integer32
	MAX-ACCESS      read-only
	STATUS  		current
	DESCRIPTION     
		"Total number of requests that required network address translation for this owner."
	DEFVAL { 0 }
	--DEFAULT ap-display-name	Nat Flows
	--DEFAULT apjam-popup-ref apOwnerRowInst, Statistics
	::= {apOwnEntry 21}

apOwnByteCount OBJECT-TYPE
	SYNTAX          Integer32
	MAX-ACCESS      read-only
	STATUS  		current
	DESCRIPTION     
		"Total number of bytes moved by this owner."
	DEFVAL { 0 }
	--DEFAULT ap-display-name	Bytes
	--DEFAULT apjam-popup-ref apOwnerRowInst, Statistics
	::= {apOwnEntry 22}

apOwnFrameCount OBJECT-TYPE
	SYNTAX          Integer32
	MAX-ACCESS      read-only
	STATUS  		current
	DESCRIPTION     
		"Total number of frames moved by this owner."
	DEFVAL { 0 }
	--DEFAULT ap-display-name	Frames
	--DEFAULT apjam-popup-ref apOwnerRowInst, Statistics
	::= {apOwnEntry 23}

apOwnDNSPolicy  OBJECT-TYPE
	SYNTAX          INTEGER {
							none(0),
							accept(1),
							push(2),
							both(3)
							}
	MAX-ACCESS      read-create
	STATUS  		current
	DESCRIPTION     
		"The IP Protocol the of the content providing service."
	DEFVAL { none }
	::= {apOwnEntry 24}


apOwnStatus OBJECT-TYPE
	SYNTAX          RowStatus
	MAX-ACCESS      read-create
	STATUS          current
	DESCRIPTION      
		"Status entry for this row."
	::= {apOwnEntry 25}

apOwnCaseSensitive  OBJECT-TYPE
	SYNTAX  INTEGER {
					insensitive(0),
					sensitive(1)
 					}
	MAX-ACCESS      read-create
	STATUS 			current
	DESCRIPTION     
		"Controls whether this owner's rules use case sensitive or case insensitive matching."
	DEFVAL { insensitive }
	--DEFAULT ap-display-name	Case Sensitivity
	--DEFAULT apjam-popup-ref apCntInst, Properties
	--DEFAULT apjam-wizard-field	2, normal
	::= {apOwnEntry  26}


apOwnDNSBalance OBJECT-TYPE
	SYNTAX          INTEGER {
							preferlocal(1),
							roundrobin(2),
							leastloaded(3)
							}
	MAX-ACCESS      read-create
	STATUS  		current
	DESCRIPTION     
		"The default DNS distribution algorithm to use for this owner's content rules."
	DEFVAL { roundrobin }
	::= {apOwnEntry  27}
END
