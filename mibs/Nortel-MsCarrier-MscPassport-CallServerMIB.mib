Nortel-MsCarrier-MscPassport-CallServerMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      Unsigned32
   FROM Nortel-MsCarrier-MscPassport-StandardTextualConventionsMIB

      NonReplicated,
      WildcardedDigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     CallServer Enterprise MIB."

callServerMIB OBJECT IDENTIFIER ::= { mscPassportMIBs 41 }










-- CallRouter
-- This component performs the call routing function. It is a database 
-- containing prefix-DNAs. Unlike the DNAs under the 
-- NumberingPlanIndicator component which are only local DNAs, 
-- the DNAs under this component can refer to local DNAs and DNAs 
-- resident on other Passport modules. This component represents a 
-- database that is used to translate a DNA in a call setup packet into a 
-- ModuleId or a RoutingId so that the call setup packet can be routed 
-- to the correct Passport module within the subnet or to the correct 
-- Passport subnet. This call router can only be used for a Passport 
-- only network. This call router only provides service when there is 
-- no CSRM attached to the Passport subnet. If a CSRM is connected 
-- to the subnet, the CSRM will provide the call routing service.

mscCR OBJECT IDENTIFIER ::= { mscComponents 42 }



mscCRRowStatusTable OBJECT-TYPE
   SYNTAX     SEQUENCE OF MscCRRowStatusEntry
   ACCESS     not-accessible
   STATUS     mandatory
   DESCRIPTION
     "This entry controls the addition and deletion of 
      mscCR components."
::= { mscCR 1 }

mscCRRowStatusEntry OBJECT-TYPE
   SYNTAX     MscCRRowStatusEntry
   ACCESS     not-accessible
   STATUS     mandatory
   DESCRIPTION
     "A single entry in the table represents a single 
      mscCR component."
   INDEX {
      mscCRIndex }
::= { mscCRRowStatusTable 1 }

MscCRRowStatusEntry ::= SEQUENCE {
   mscCRRowStatus
      RowStatus,
   mscCRComponentName
      DisplayString,
   mscCRStorageType
      StorageType,
   mscCRIndex
      NonReplicated }

mscCRRowStatus OBJECT-TYPE
   SYNTAX     RowStatus 
   ACCESS     read-write
   STATUS     mandatory
   DESCRIPTION
     "This variable is used as the basis for SNMP naming of
      mscCR components.
      These components can be added and deleted."
::= { mscCRRowStatusEntry 1 }

mscCRComponentName OBJECT-TYPE
   SYNTAX     DisplayString 
   ACCESS     read-only
   STATUS     mandatory
   DESCRIPTION
     "This variable provides the component's string name for
      use with the ASCII Console Interface"
::= { mscCRRowStatusEntry 2 }

mscCRStorageType OBJECT-TYPE
   SYNTAX     StorageType 
   ACCESS     read-only
   STATUS     mandatory
   DESCRIPTION
     "This variable represents the storage type value for the
      mscCR tables."
::= { mscCRRowStatusEntry 4 }

mscCRIndex OBJECT-TYPE
   SYNTAX     NonReplicated 
   ACCESS     not-accessible
   STATUS     mandatory
   DESCRIPTION
     "This variable represents the index for the mscCR tables."
::= { mscCRRowStatusEntry 10 }


-- CallRouter NumberingPlanId/<x121,e164> 
-- This component collects all the prefix DNAs provisioned for a 
-- particular numbering plan indicator. There are two numbering plans 
-- allowed, E.164 and X.121.

mscCRNpi OBJECT IDENTIFIER ::= { mscCR 2 }



mscCRNpiRowStatusTable OBJECT-TYPE
   SYNTAX     SEQUENCE OF MscCRNpiRowStatusEntry
   ACCESS     not-accessible
   STATUS     mandatory
   DESCRIPTION
     "This entry controls the addition and deletion of 
      mscCRNpi components."
::= { mscCRNpi 1 }

mscCRNpiRowStatusEntry OBJECT-TYPE
   SYNTAX     MscCRNpiRowStatusEntry
   ACCESS     not-accessible
   STATUS     mandatory
   DESCRIPTION
     "A single entry in the table represents a single 
      mscCRNpi component."
   INDEX {
      mscCRIndex,
      mscCRNpiIndex }
::= { mscCRNpiRowStatusTable 1 }

MscCRNpiRowStatusEntry ::= SEQUENCE {
   mscCRNpiRowStatus
      RowStatus,
   mscCRNpiComponentName
      DisplayString,
   mscCRNpiStorageType
      StorageType,
   mscCRNpiIndex
      INTEGER }

mscCRNpiRowStatus OBJECT-TYPE
   SYNTAX     RowStatus 
   ACCESS     read-write
   STATUS     mandatory
   DESCRIPTION
     "This variable is used as the basis for SNMP naming of
      mscCRNpi components.
      These components can be added and deleted."
::= { mscCRNpiRowStatusEntry 1 }

mscCRNpiComponentName OBJECT-TYPE
   SYNTAX     DisplayString 
   ACCESS     read-only
   STATUS     mandatory
   DESCRIPTION
     "This variable provides the component's string name for
      use with the ASCII Console Interface"
::= { mscCRNpiRowStatusEntry 2 }

mscCRNpiStorageType OBJECT-TYPE
   SYNTAX     StorageType 
   ACCESS     read-only
   STATUS     mandatory
   DESCRIPTION
     "This variable represents the storage type value for the
      mscCRNpi tables."
::= { mscCRNpiRowStatusEntry 4 }

mscCRNpiIndex OBJECT-TYPE
   SYNTAX     INTEGER  {
                 x121(0),
                 e164(1) }
   ACCESS     not-accessible
   STATUS     mandatory
   DESCRIPTION
     "This variable represents the index for the mscCRNpi tables."
::= { mscCRNpiRowStatusEntry 10 }

mscCRNpiStatsTable OBJECT-TYPE
   SYNTAX     SEQUENCE OF MscCRNpiStatsEntry
   ACCESS     not-accessible
   STATUS     mandatory
   DESCRIPTION
     "This group of attributes contains the statistics kept for a particular 
      numbering plan indicator."
::= { mscCRNpi 10 }

mscCRNpiStatsEntry OBJECT-TYPE
   SYNTAX     MscCRNpiStatsEntry
   ACCESS     not-accessible
   STATUS     mandatory
   DESCRIPTION
     "An entry in the mscCRNpiStatsTable."
   INDEX {
      mscCRIndex,
      mscCRNpiIndex }
::= { mscCRNpiStatsTable 1 }

MscCRNpiStatsEntry ::= SEQUENCE {
   mscCRNpiTotalDnas
      Unsigned32,
   mscCRNpiCallsRouted
      Counter32,
   mscCRNpiCallsFailed
      Counter32 }

mscCRNpiTotalDnas OBJECT-TYPE
   SYNTAX     Unsigned32 (0..4294967295)
   ACCESS     read-only
   STATUS     mandatory
   DESCRIPTION
     "This attribute contains the total number of prefix-DNAs 
      provisioned."
   DEFVAL     { 0 }
::= { mscCRNpiStatsEntry 1 }

mscCRNpiCallsRouted OBJECT-TYPE
   SYNTAX     Counter32 
   ACCESS     read-only
   STATUS     mandatory
   DESCRIPTION
     "This attribute contains the total number of call setup packets routed. 
      When the counter reaches the maximum, it wraps back to zero."
::= { mscCRNpiStatsEntry 2 }

mscCRNpiCallsFailed OBJECT-TYPE
   SYNTAX     Counter32 
   ACCESS     read-only
   STATUS     mandatory
   DESCRIPTION
     "This attribute contains the total number of call setup packets that 
      failed to route. This could be caused by the MID or RID being 
      unreachable or by the DNA failing to translate to a MID or RID. 
      Check the prefix-DNA provisioning data and the DNAs associated 
      to the endpoints of the connection. When the counter reaches the 
      maximum, it wraps back to zero."
::= { mscCRNpiStatsEntry 3 }


-- Cr Npi/<x121,e164> Dna/<BCD(1..15, WILDCARDED)>
-- This subcomponent represents a prefix-DNA in the numbering plan. 
-- The instance value must be 1 to 15 digits each of value 0 through 9 
-- or wildcard.Wild digits may be used so that the digit position 
-- specified by the wild digit is ignored when making a routing 
-- decision. This will reduce the number of prefix-DNAs needed to 
-- properly route the calls. The wild digit is represented by "?". 
-- Wildcarding inconsistencies can not exist. If a prefix-DNA already 
-- exists in the database with a specific digit in position 3, new prefix-
-- DNAs may not be added with a wildcard in position 3. Similarly, if 
-- the prefix-DNA already exists with a wildcard in a particular 
-- position, a similar prefix-DNA cannot be added with a specific digit 
-- in the same position.

mscCRNpiDna OBJECT IDENTIFIER ::= { mscCRNpi 2 }



mscCRNpiDnaRowStatusTable OBJECT-TYPE
   SYNTAX     SEQUENCE OF MscCRNpiDnaRowStatusEntry
   ACCESS     not-accessible
   STATUS     mandatory
   DESCRIPTION
     "This entry controls the addition and deletion of 
      mscCRNpiDna components."
::= { mscCRNpiDna 1 }

mscCRNpiDnaRowStatusEntry OBJECT-TYPE
   SYNTAX     MscCRNpiDnaRowStatusEntry
   ACCESS     not-accessible
   STATUS     mandatory
   DESCRIPTION
     "A single entry in the table represents a single 
      mscCRNpiDna component."
   INDEX {
      mscCRIndex,
      mscCRNpiIndex,
      mscCRNpiDnaIndex }
::= { mscCRNpiDnaRowStatusTable 1 }

MscCRNpiDnaRowStatusEntry ::= SEQUENCE {
   mscCRNpiDnaRowStatus
      RowStatus,
   mscCRNpiDnaComponentName
      DisplayString,
   mscCRNpiDnaStorageType
      StorageType,
   mscCRNpiDnaIndex
      WildcardedDigitString }

mscCRNpiDnaRowStatus OBJECT-TYPE
   SYNTAX     RowStatus 
   ACCESS     read-write
   STATUS     mandatory
   DESCRIPTION
     "This variable is used as the basis for SNMP naming of
      mscCRNpiDna components.
      These components can be added and deleted."
::= { mscCRNpiDnaRowStatusEntry 1 }

mscCRNpiDnaComponentName OBJECT-TYPE
   SYNTAX     DisplayString 
   ACCESS     read-only
   STATUS     mandatory
   DESCRIPTION
     "This variable provides the component's string name for
      use with the ASCII Console Interface"
::= { mscCRNpiDnaRowStatusEntry 2 }

mscCRNpiDnaStorageType OBJECT-TYPE
   SYNTAX     StorageType 
   ACCESS     read-only
   STATUS     mandatory
   DESCRIPTION
     "This variable represents the storage type value for the
      mscCRNpiDna tables."
::= { mscCRNpiDnaRowStatusEntry 4 }

mscCRNpiDnaIndex OBJECT-TYPE
   SYNTAX     WildcardedDigitString (SIZE (1..15))
   ACCESS     not-accessible
   STATUS     mandatory
   DESCRIPTION
     "This variable represents the index for the mscCRNpiDna tables."
::= { mscCRNpiDnaRowStatusEntry 10 }

mscCRNpiDnaProvTable OBJECT-TYPE
   SYNTAX     SEQUENCE OF MscCRNpiDnaProvEntry
   ACCESS     not-accessible
   STATUS     mandatory
   DESCRIPTION
     "This group of attributes represents what the prefix-DNA maps to."
::= { mscCRNpiDna 10 }

mscCRNpiDnaProvEntry OBJECT-TYPE
   SYNTAX     MscCRNpiDnaProvEntry
   ACCESS     not-accessible
   STATUS     mandatory
   DESCRIPTION
     "An entry in the mscCRNpiDnaProvTable."
   INDEX {
      mscCRIndex,
      mscCRNpiIndex,
      mscCRNpiDnaIndex }
::= { mscCRNpiDnaProvTable 1 }

MscCRNpiDnaProvEntry ::= SEQUENCE {
   mscCRNpiDnaRoutingId
      Unsigned32,
   mscCRNpiDnaModuleId
      Unsigned32 }

mscCRNpiDnaRoutingId OBJECT-TYPE
   SYNTAX     Unsigned32 (0..126)
   ACCESS     read-write
   STATUS     mandatory
   DESCRIPTION
     "This attribute identifies the routingId that the prefix-DNA maps to. 
      If the value is set to zero, then the routingId is not used. Note that at 
      least one and only one of the attributes in this group must be set to a 
      non-zero value."
   DEFVAL     { 0 }
::= { mscCRNpiDnaProvEntry 1 }

mscCRNpiDnaModuleId OBJECT-TYPE
   SYNTAX     Unsigned32 (0..1909)
   ACCESS     read-write
   STATUS     mandatory
   DESCRIPTION
     "This attribute contains the module identifier value that the DNA 
      maps to. If the value is set to zero, then the moduleId is not used. 
      Note that at least one and only one of the attributes in this group 
      must be set to a non-zero value."
   DEFVAL     { 0 }
::= { mscCRNpiDnaProvEntry 2 }




-- 
-- Version and Compliance statements
-- 



-- Object-Group Statement:
-- A list of all current accessible leaf objects.

-- OBJECTS { mscCRNpiDnaModuleId,
--           mscCRStorageType,
--           mscCRRowStatus,
--           mscCRNpiCallsRouted,
--           mscCRNpiDnaComponentName,
--           mscCRNpiCallsFailed,
--           mscCRNpiTotalDnas,
--           mscCRNpiDnaRowStatus,
--           mscCRNpiComponentName,
--           mscCRNpiDnaStorageType,
--           mscCRNpiDnaRoutingId,
--           mscCRComponentName,
--           mscCRNpiStorageType,
--           mscCRNpiRowStatus }
-- STATUS  mandatory
-- DESCRIPTION
--   "A list of all current accessible leaf objects."

callServerGroup OBJECT IDENTIFIER ::= { callServerMIB 1 }
callServerGroupCA OBJECT IDENTIFIER ::= { callServerGroup 1 }
callServerGroupCA02 OBJECT IDENTIFIER ::= { callServerGroupCA 3 }
callServerGroupCA02A OBJECT IDENTIFIER ::= { callServerGroupCA02 2 }



-- Agent-Capabilities Statement:

-- PRODUCT-RELEASE "MscPassport Release 1.2 CallServer."
-- STATUS          mandatory
-- DESCRIPTION     "Carrier Passport CallServer MIB: MIB Version CA02A,
--                  Software Version CA02S9C."
-- SUPPORTS        Nortel-MsCarrier-MscPassport-CallServerMIB
--    INCLUDES     { callServerGroupCA02A }

callServerCapabilities OBJECT IDENTIFIER ::= { callServerMIB 3 }
callServerCapabilitiesCA OBJECT IDENTIFIER ::= { callServerCapabilities 1 }
callServerCapabilitiesCA02 OBJECT IDENTIFIER ::= { callServerCapabilitiesCA 3 }
callServerCapabilitiesCA02A OBJECT IDENTIFIER ::= { callServerCapabilitiesCA02 2 }





END
