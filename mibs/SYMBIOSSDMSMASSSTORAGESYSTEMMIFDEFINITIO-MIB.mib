-- MIB generated by miftomib version 1.0a

SYMBIOSSDMSMASSSTORAGESYSTEMMIFDEFINITIO-MIB DEFINITIONS ::= BEGIN

-- This file is the Symbios Logic Mass Storage MIF

IMPORTS
    OBJECT-TYPE
    FROM RFC-1212
    Counter, enterprises
    FROM RFC1155-SMI
    DisplayString
    FROM RFC1213-MIB;

DmiCounter			::= Counter
DmiInteger			::= INTEGER
DmiInteger64X		::= INTEGER (-18446744073709551615..18446744073709551615)
DmiDisplaystring	::= DisplayString
DmiDateX			::= OCTET STRING (SIZE (28))
DmiComponentIndex	::= INTEGER

symbios                	OBJECT IDENTIFIER ::= {enterprises 1123}
cosprings             	OBJECT IDENTIFIER ::= {symbios 3}
scsitype		OBJECT IDENTIFIER ::= {cosprings 1}
type8xx			OBJECT IDENTIFIER ::= {scsitype 2}
id			OBJECT IDENTIFIER ::= {type8xx 1}
dmtfGroups          	OBJECT IDENTIFIER ::= {id 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
This group is required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this component."
	::= {eComponentid 1}

a1Product OBJECT-TYPE
	SYNTAX		DmiDisplaystring
	ACCESS		read-only
	STATUS		mandatory
	DESCRIPTION	"Product name for this component."
	::= {eComponentid 2}

a1Version OBJECT-TYPE
	SYNTAX		DmiDisplaystring
	ACCESS		read-only
	STATUS		mandatory
	DESCRIPTION	"Version number of this component."
	::= {eComponentid 3}

a1SerialNumber OBJECT-TYPE
	SYNTAX		DmiDisplaystring
	ACCESS		read-only
	STATUS		mandatory
	DESCRIPTION	"Serial number for this component"
	::= {eComponentid 4}

a1Installation OBJECT-TYPE
	SYNTAX		DmiDateX
	ACCESS		read-only
	STATUS		mandatory
	DESCRIPTION	"The installation date and time of this component. The Service
Layer assigns this value, the manufacturer should leave it blank."
	::= {eComponentid 5}

a1Verify OBJECT-TYPE
	SYNTAX		INTEGER {
		vAnErrorOccurredCheckStatusCode         	(0),
		vThisComponentDoesNotExist              	(1),
		vTheVerifyIsNotSupported                	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SSoftwareComponentInformation ::= SEQUENCE {
	a2MajorVersion                          	DmiDisplaystring,
	a2MinorVersion                          	DmiDisplaystring,
	a2Revision                              	DmiDisplaystring,
	a2Build                                 	DmiDisplaystring,
	a2TargetOperatingSystem                 	DmiInteger,
	a2LanguageEdition                       	DmiDisplaystring,
	a2IdentificationCode                    	DmiDisplaystring,
	a2InstallableState                      	DmiInteger,
	a2ExecutableState                       	DmiInteger
}

tSoftwareComponentInformation OBJECT-TYPE
	SYNTAX		SEQUENCE OF SSoftwareComponentInformation
	ACCESS		not-accessible
	STATUS		mandatory
	DESCRIPTION	"Contains additional identifying information about this software
component."
	::= {dmtfGroups 2}

eSoftwareComponentInformation OBJECT-TYPE
	SYNTAX		SSoftwareComponentInformation
	ACCESS		not-accessible
	STATUS		mandatory
	DESCRIPTION	""
	INDEX		{DmiComponentIndex}
	::= {tSoftwareComponentInformation 1}

a2MajorVersion OBJECT-TYPE
	SYNTAX		DmiDisplaystring
	ACCESS		read-only
	STATUS		mandatory
	DESCRIPTION	"Major version of this software component."
	::= {eSoftwareComponentInformation 1}

a2MinorVersion OBJECT-TYPE
	SYNTAX		DmiDisplaystring
	ACCESS		read-only
	STATUS		mandatory
	DESCRIPTION	"Minor version of this software component."
	::= {eSoftwareComponentInformation 2}

a2Revision OBJECT-TYPE
	SYNTAX		DmiDisplaystring
	ACCESS		read-only
	STATUS		mandatory
	DESCRIPTION	"Revision of this software component."
	::= {eSoftwareComponentInformation 3}

a2Build OBJECT-TYPE
	SYNTAX		DmiDisplaystring
	ACCESS		read-only
	STATUS		mandatory
	DESCRIPTION	"Manufacturer's internal identifier for this compilation."
	::= {eSoftwareComponentInformation 4}

a2TargetOperatingSystem OBJECT-TYPE
	SYNTAX		INTEGER {
		vOther                                  	(0),
		vDos                                    	(1),
		vMacos                                  	(2),
		vOs2                                    	(3),
		vUnix                                   	(4),
		vWin16                                  	(5),
		vWin32                                  	(6),
		vOpenvms                                	(7),
		vNetware                                	(8),
		vWin9x                                  	(9),
		vWinnt                                  	(10)
	}
	ACCESS		read-only
	STATUS		mandatory
	DESCRIPTION	"The operating system for which this software component is
intended."
	::= {eSoftwareComponentInformation 5}

a2LanguageEdition OBJECT-TYPE
	SYNTAX		DmiDisplaystring
	ACCESS		read-only
	STATUS		mandatory
	DESCRIPTION	"This identifies the language edition of this component."
	::= {eSoftwareComponentInformation 6}

a2IdentificationCode OBJECT-TYPE
	SYNTAX		DmiDisplaystring
	ACCESS		read-only
	STATUS		mandatory
	DESCRIPTION	"Stock Keeping Unit (SKU) or Part Number for this software
component."
	::= {eSoftwareComponentInformation 7}

a2InstallableState OBJECT-TYPE
	SYNTAX		INTEGER {
		vUnknown                                	(1),
		vInstallable                            	(2),
		vNotInstallable                         	(3)
	}
	ACCESS		read-only
	STATUS		mandatory
	DESCRIPTION	"Specifies whether this component describes a software product
installed for the purpose of further distribution."
	::= {eSoftwareComponentInformation 8}

a2ExecutableState OBJECT-TYPE
	SYNTAX		INTEGER {
		vUnknown                                	(1),
		vExecutable                             	(2),
		vNotExecutable                          	(3)
	}
	ACCESS		read-only
	STATUS		mandatory
	DESCRIPTION	"Specifies whether this component describes a software product
which is executable."
	::= {eSoftwareComponentInformation 9}

SComponentid1 ::= SEQUENCE {
	a3FileName                              	DmiDisplaystring,
	a3FileSize                              	DmiInteger,
	a3FileDateAndTime                       	DmiDateX,
	a3FileChecksum                          	DmiInteger,
	a3FileCrc1                              	DmiInteger,
	a3FileCrc2                              	DmiInteger,
	a3FileLocation                          	DmiInteger
}

tComponentid1 OBJECT-TYPE
	SYNTAX		SEQUENCE OF SComponentid1
	ACCESS		not-accessible
	STATUS		mandatory
	DESCRIPTION	"The Software Signature Group contains information that can
be used to detect this software component."
	::= {dmtfGroups 3}

eComponentid1 OBJECT-TYPE
	SYNTAX		SComponentid1
	ACCESS		not-accessible
	STATUS		mandatory
	DESCRIPTION	""
	INDEX		{DmiComponentIndex, a3FileName, a3FileLocation}
	::= {tComponentid1 1}

a3FileName OBJECT-TYPE
	SYNTAX		DmiDisplaystring
	ACCESS		read-only
	STATUS		mandatory
	DESCRIPTION	"The name of a file that can be examined to detect this software
component."
	::= {eComponentid1 1}

a3FileSize OBJECT-TYPE
	SYNTAX		DmiInteger
	ACCESS		read-only
	STATUS		mandatory
	DESCRIPTION	"The size in bytes of a file that can be examined to detect
this software component."
	::= {eComponentid1 2}

a3FileDateAndTime OBJECT-TYPE
	SYNTAX		DmiDateX
	ACCESS		read-only
	STATUS		mandatory
	DESCRIPTION	"The date and time of a file that can be examined to detect
this software component."
	::= {eComponentid1 3}

a3FileChecksum OBJECT-TYPE
	SYNTAX		DmiInteger
	ACCESS		read-only
	STATUS		mandatory
	DESCRIPTION	"The checksum of the first 32 bytes of this file."
	::= {eComponentid1 4}

a3FileCrc1 OBJECT-TYPE
	SYNTAX		DmiInteger
	ACCESS		read-only
	STATUS		mandatory
	DESCRIPTION	"The 16-bit CRC (ITU-T) on the middle 512k of this file."
	::= {eComponentid1 5}

a3FileCrc2 OBJECT-TYPE
	SYNTAX		DmiInteger
	ACCESS		read-only
	STATUS		mandatory
	DESCRIPTION	"The 16-bit CRC (ITU-T) on the middle 512k of this file with
a modulo-3 offset relative to the beginning of the file."
	::= {eComponentid1 6}

a3FileLocation OBJECT-TYPE
	SYNTAX		DmiInteger
	ACCESS		read-only
	STATUS		mandatory
	DESCRIPTION	"The location of this file, as an index into the location
table."
	::= {eComponentid1 7}

SFieldReplaceableUnit ::= SEQUENCE {
	a4FruIndex                              	DmiInteger,
	a4DeviceGroupIndex                      	DmiInteger,
	a4Description                           	DmiDisplaystring,
	a4Manufacturer                          	DmiDisplaystring,
	a4Model                                 	DmiDisplaystring,
	a4PartNumber                            	DmiDisplaystring,
	a4FruSerialNumber                       	DmiDisplaystring,
	a4RevisionLevel                         	DmiDisplaystring,
	a4WarrantyStartDate                     	DmiDateX,
	a4WarrantyDuration                      	DmiInteger,
	a4SupportPhoneNumber                    	DmiDisplaystring
}

tFieldReplaceableUnit OBJECT-TYPE
	SYNTAX		SEQUENCE OF SFieldReplaceableUnit
	ACCESS		not-accessible
	STATUS		mandatory
	DESCRIPTION	"A Field Replaceable Unit (FRU), is defined as a hardware
component which is designed to be separately removable for replacement or
repair. For the purposes of this definition, a motherboard and a fixed hard
disk are FRUs, whereas a fixed hard disk platter or a chip fixed in place
on the motherboard are not FRUs since they are not designed to be separately
removable. Each instance within the FRU table should contain the device group
and instance data for the associated hardware component."
	::= {dmtfGroups 4}

eFieldReplaceableUnit OBJECT-TYPE
	SYNTAX		SFieldReplaceableUnit
	ACCESS		not-accessible
	STATUS		mandatory
	DESCRIPTION	""
	INDEX		{DmiComponentIndex, a4FruIndex}
	::= {tFieldReplaceableUnit 1}

a4FruIndex OBJECT-TYPE
	SYNTAX		DmiInteger
	ACCESS		read-only
	STATUS		mandatory
	DESCRIPTION	"The index into the Field Replaceable Unit table."
	::= {eFieldReplaceableUnit 1}

a4DeviceGroupIndex OBJECT-TYPE
	SYNTAX		DmiInteger
	ACCESS		read-only
	STATUS		mandatory
	DESCRIPTION	"The group ID of the group referencing this Field Replaceable
Unit instance."
	::= {eFieldReplaceableUnit 2}

a4Description OBJECT-TYPE
	SYNTAX		DmiDisplaystring
	ACCESS		read-only
	STATUS		mandatory
	DESCRIPTION	"A clear description of this Field Replaceable Unit."
	::= {eFieldReplaceableUnit 3}

a4Manufacturer OBJECT-TYPE
	SYNTAX		DmiDisplaystring
	ACCESS		read-only
	STATUS		mandatory
	DESCRIPTION	"The name of the company manufacturing or providing this Field
Replaceable Unit."
	::= {eFieldReplaceableUnit 4}

a4Model OBJECT-TYPE
	SYNTAX		DmiDisplaystring
	ACCESS		read-only
	STATUS		mandatory
	DESCRIPTION	"The manufacturer's model number for this Field Replaceable
Unit."
	::= {eFieldReplaceableUnit 5}

a4PartNumber OBJECT-TYPE
	SYNTAX		DmiDisplaystring
	ACCESS		read-only
	STATUS		mandatory
	DESCRIPTION	"A part number by which a replacement part can be ordered
for this Field Replaceable Unit."
	::= {eFieldReplaceableUnit 6}

a4FruSerialNumber OBJECT-TYPE
	SYNTAX		DmiDisplaystring
	ACCESS		read-only
	STATUS		mandatory
	DESCRIPTION	"The manufacturer's serial number for this Field Replaceable
Unit."
	::= {eFieldReplaceableUnit 7}

a4RevisionLevel OBJECT-TYPE
	SYNTAX		DmiDisplaystring
	ACCESS		read-only
	STATUS		mandatory
	DESCRIPTION	"The revision level of this Field Replaceable Unit."
	::= {eFieldReplaceableUnit 8}

a4WarrantyStartDate OBJECT-TYPE
	SYNTAX		DmiDateX
	ACCESS		read-only
	STATUS		mandatory
	DESCRIPTION	"The start date of the service warranty for this Field Replaceabl
 Unit."
	::= {eFieldReplaceableUnit 9}

a4WarrantyDuration OBJECT-TYPE
	SYNTAX		DmiInteger
	ACCESS		read-only
	STATUS		mandatory
	DESCRIPTION	"The total duration of this Field Replaceable Unit warranty
in months."
	::= {eFieldReplaceableUnit 10}

a4SupportPhoneNumber OBJECT-TYPE
	SYNTAX		DmiDisplaystring
	ACCESS		read-only
	STATUS		mandatory
	DESCRIPTION	"The phone number(s) for support for this Field Replaceable
Unit."
	::= {eFieldReplaceableUnit 11}

SStorageDevices ::= SEQUENCE {
	a5StorageDeviceIndex                    	DmiInteger,
	a5Type                                  	DmiInteger,
	a5TypeDescription                       	DmiDisplaystring,
	a5WorldwideIdentifierType               	DmiInteger,
	a5WorldwideIdentifier                   	DmiDisplaystring,
	a5Sub-identifier                        	DmiDisplaystring,
	a5MediaDataBlockSize                    	DmiInteger,
	a5FormattedMediaCapacity                	DmiInteger64X,
	a5RemovableDevice                       	DmiInteger,
	a5DeviceLoaded                          	DmiInteger,
	a5RemovableMedia                        	DmiInteger,
	a5MediaLoaded                           	DmiInteger,
	a5Compression                           	DmiInteger,
	a5Encryption                            	DmiInteger,
	a5FruGroupIndex                         	DmiInteger,
	a5OperationalGroupIndex                 	DmiInteger
}

tStorageDevices OBJECT-TYPE
	SYNTAX		SEQUENCE OF SStorageDevices
	ACCESS		not-accessible
	STATUS		mandatory
	DESCRIPTION	"This group defines the mass storage devices in this system."
	::= {dmtfGroups 5}

eStorageDevices OBJECT-TYPE
	SYNTAX		SStorageDevices
	ACCESS		not-accessible
	STATUS		mandatory
	DESCRIPTION	""
	INDEX		{DmiComponentIndex, a5StorageDeviceIndex}
	::= {tStorageDevices 1}

a5StorageDeviceIndex OBJECT-TYPE
	SYNTAX		DmiInteger
	ACCESS		read-only
	STATUS		mandatory
	DESCRIPTION	"An index into the storage device table."
	::= {eStorageDevices 1}

a5Type OBJECT-TYPE
	SYNTAX		INTEGER {
		vOther                                  	(1),
		vUnknown                                	(2),
		vRigidDiskDrive                         	(3),
		vCartridgeRigidDiskDrive                	(4),
		vFlexibleDisketteDrive                  	(5),
		vCompactDiskDrive                       	(6),
		vOpticalWrite-onceread-manyWormDrive    	(7),
		vMagneto-opticalDrive                   	(8),
		vTapeDrive                              	(9),
		vMediaChanger                           	(10)
	}
	ACCESS		read-only
	STATUS		mandatory
	DESCRIPTION	"The type of this mass storage device.  If 'Other' is used,
then the Type Description attribute shall be used."
	::= {eStorageDevices 2}

a5TypeDescription OBJECT-TYPE
	SYNTAX		DmiDisplaystring
	ACCESS		read-only
	STATUS		mandatory
	DESCRIPTION	"A longer description of the storage device.  For example:
 3.5 inch flexible diskette drive using diskettes with a maximum capacity
of 1.44MB.  If 'Other' was specified above, then this field shall be used.
 Otherwise, the contents of this optional field shall not contradict the
Storage Device Type specified above."
	::= {eStorageDevices 3}

a5WorldwideIdentifierType OBJECT-TYPE
	SYNTAX		INTEGER {
		vOther                                  	(1),
		vUnknown                                	(2),
		vNone                                   	(3),
		vVendorIdProductIdSerialNumber          	(4),
		vIeeeExtendedUniqueIdentifier64-bit     	(5),
		vFc-ph64-bitName-identifier             	(6),
		vBinary                                 	(7),
		vUnicode                                	(8),
		vLanMacAddress                          	(9),
		vWanAccessAddress                       	(10)
	}
	ACCESS		read-only
	STATUS		mandatory
	DESCRIPTION	"The type of identifier displayed by the Worldwide Identifier
attribute."
	::= {eStorageDevices 4}

a5WorldwideIdentifier OBJECT-TYPE
	SYNTAX		DmiDisplaystring
	ACCESS		read-only
	STATUS		mandatory
	DESCRIPTION	"The Worldwide identifier for this device."
	::= {eStorageDevices 5}

a5Sub-identifier OBJECT-TYPE
	SYNTAX		DmiDisplaystring
	ACCESS		read-only
	STATUS		mandatory
	DESCRIPTION	"The sub-identifier for this storage device (e.g., the device's
SCSI logical unit number)."
	::= {eStorageDevices 6}

a5MediaDataBlockSize OBJECT-TYPE
	SYNTAX		DmiInteger
	ACCESS		read-only
	STATUS		mandatory
	DESCRIPTION	"The size in bytes of the data blocks used on the storage
media.  If the media block size is unknown or not consistent across the media,
then this value shall be zero."
	::= {eStorageDevices 7}

a5FormattedMediaCapacity OBJECT-TYPE
	SYNTAX		DmiInteger64X
	ACCESS		read-only
	STATUS		mandatory
	DESCRIPTION	"The total size in bytes of this storage media after it has
been formatted."
	::= {eStorageDevices 8}

a5RemovableDevice OBJECT-TYPE
	SYNTAX		INTEGER {
		vFalse                                  	(0),
		vTrue                                   	(1),
		vUnknown                                	(2)
	}
	ACCESS		read-only
	STATUS		mandatory
	DESCRIPTION	"If true, then this storage device is removable (e.g.:  PCMCIA
device)."
	::= {eStorageDevices 9}

a5DeviceLoaded OBJECT-TYPE
	SYNTAX		INTEGER {
		vFalse                                  	(0),
		vTrue                                   	(1),
		vUnknown                                	(2)
	}
	ACCESS		read-only
	STATUS		mandatory
	DESCRIPTION	"If true, then the storage device is loaded.  If the device
is not removable, then this value shall be 'TRUE'."
	::= {eStorageDevices 10}

a5RemovableMedia OBJECT-TYPE
	SYNTAX		INTEGER {
		vFalse                                  	(0),
		vTrue                                   	(1),
		vUnknown                                	(2)
	}
	ACCESS		read-only
	STATUS		mandatory
	DESCRIPTION	"If true, then the media in this storage device is removable."
	::= {eStorageDevices 11}

a5MediaLoaded OBJECT-TYPE
	SYNTAX		INTEGER {
		vFalse                                  	(0),
		vTrue                                   	(1),
		vUnknown                                	(2)
	}
	ACCESS		read-only
	STATUS		mandatory
	DESCRIPTION	"If true, the media in this storage device is loaded.  If
the media is not removable, then this value shall be 'TRUE' "
	::= {eStorageDevices 12}

a5Compression OBJECT-TYPE
	SYNTAX		INTEGER {
		vFalse                                  	(0),
		vTrue                                   	(1),
		vUnknown                                	(2)
	}
	ACCESS		read-only
	STATUS		mandatory
	DESCRIPTION	"If true, the storage device supports compression."
	::= {eStorageDevices 13}

a5Encryption OBJECT-TYPE
	SYNTAX		INTEGER {
		vFalse                                  	(0),
		vTrue                                   	(1),
		vUnknown                                	(2)
	}
	ACCESS		read-only
	STATUS		mandatory
	DESCRIPTION	"If true, the storage device supports encryption."
	::= {eStorageDevices 14}

a5FruGroupIndex OBJECT-TYPE
	SYNTAX		DmiInteger
	ACCESS		read-only
	STATUS		mandatory
	DESCRIPTION	"If this is a Field Replaceable Unit or if it is part of another
FRU,  this provides an index into the FRU table for this device; 'value =
-1' indicates that the group is not a FRU."
	::= {eStorageDevices 15}

a5OperationalGroupIndex OBJECT-TYPE
	SYNTAX		DmiInteger
	ACCESS		read-only
	STATUS		mandatory
	DESCRIPTION	"The index into the Operational State table for this device."
	::= {eStorageDevices 16}

SStorageDevicesEvents ::= SEQUENCE {
	a6StorageDevicesEventType               	DmiInteger,
	a6EventSeverity                         	DmiInteger,
	a6EventIsStateBased                     	DmiInteger,
	a6EventStateKey                         	DmiInteger,
	a6AssociatedGroup                       	DmiDisplaystring,
	a6EventSystem                           	DmiInteger,
	a6EventSubsystem                        	DmiInteger
}

tStorageDevicesEvents OBJECT-TYPE
	SYNTAX		SEQUENCE OF SStorageDevicesEvents
	ACCESS		not-accessible
	STATUS		mandatory
	DESCRIPTION	"Storage Devices events."
	::= {dmtfGroups 6}

eStorageDevicesEvents OBJECT-TYPE
	SYNTAX		SStorageDevicesEvents
	ACCESS		not-accessible
	STATUS		mandatory
	DESCRIPTION	""
	INDEX		{DmiComponentIndex, a6AssociatedGroup}
	::= {tStorageDevicesEvents 1}

a6StorageDevicesEventType OBJECT-TYPE
	SYNTAX		INTEGER {
		vRebuildInProgress                      	(1),
		vStorageDeviceReadying                  	(2),
		vStorageDeviceError                     	(3),
		vSelf-monitoringWarning                 	(4)
	}
	ACCESS		read-only
	STATUS		mandatory
	DESCRIPTION	"The type of Storage Devices event that has occurred."
	::= {eStorageDevicesEvents 1}

a6EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eStorageDevicesEvents 2}

a6EventIsStateBased OBJECT-TYPE
	SYNTAX		INTEGER {
		vFalse                                  	(0),
		vTrue                                   	(1)
	}
	ACCESS		read-only
	STATUS		mandatory
	DESCRIPTION	"The value of this attribute determined whether the Event
 being reported is a state-based Event or not.  If the value of this attribute
is TRUE then the Event is state-based.  Else the Event is not state-based"
	::= {eStorageDevicesEvents 3}

a6EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eStorageDevicesEvents 4}

a6AssociatedGroup OBJECT-TYPE
	SYNTAX		DmiDisplaystring
	ACCESS		read-only
	STATUS		mandatory
	DESCRIPTION	"The"
	::= {eStorageDevicesEvents 5}

a6EventSystem OBJECT-TYPE
	SYNTAX		INTEGER {
		vOther                                  	(1),
		vUnknown                                	(2)
	}
	ACCESS		read-only
	STATUS		mandatory
	DESCRIPTION	"The major functional aspect of the product causing the fault."
	::= {eStorageDevicesEvents 6}

a6EventSubsystem OBJECT-TYPE
	SYNTAX		INTEGER {
		vOther                                  	(1),
		vUnknown                                	(2)
	}
	ACCESS		read-only
	STATUS		mandatory
	DESCRIPTION	"The minor functional aspect of the product causing the fault."
	::= {eStorageDevicesEvents 7}

SStorageController ::= SEQUENCE {
	a7ControllerIndex                       	DmiInteger,
	a7Identification                        	DmiDisplaystring,
	a7WorldwideIdentifierType               	DmiInteger,
	a7WorldwideIdentifier                   	DmiDisplaystring,
	a7ProtectionManagement                  	DmiInteger,
	a7BusMaster                             	DmiInteger,
	a7SecondsSinceLastPower-up              	DmiInteger,
	a7FruGroupIndex                         	DmiInteger,
	a7OperationalGroupIndex                 	DmiInteger
}

tStorageController OBJECT-TYPE
	SYNTAX		SEQUENCE OF SStorageController
	ACCESS		not-accessible
	STATUS		mandatory
	DESCRIPTION	"This group defines the storage controller in this system."
	::= {dmtfGroups 7}

eStorageController OBJECT-TYPE
	SYNTAX		SStorageController
	ACCESS		not-accessible
	STATUS		mandatory
	DESCRIPTION	""
	INDEX		{DmiComponentIndex, a7ControllerIndex}
	::= {tStorageController 1}

a7ControllerIndex OBJECT-TYPE
	SYNTAX		DmiInteger
	ACCESS		read-only
	STATUS		mandatory
	DESCRIPTION	"An index into the Storage Controller table."
	::= {eStorageController 1}

a7Identification OBJECT-TYPE
	SYNTAX		DmiDisplaystring
	ACCESS		read-only
	STATUS		mandatory
	DESCRIPTION	"e.g. Name, brand and hardware revision level of the storage
controller."
	::= {eStorageController 2}

a7WorldwideIdentifierType OBJECT-TYPE
	SYNTAX		INTEGER {
		vOther                                  	(1),
		vUnknown                                	(2),
		vNone                                   	(3),
		vVendorIdProductIdSerialNumber          	(4),
		vIeeeExtendedUniqueIdentifier64-bit     	(5),
		vFc-ph64-bitName-identifier             	(6),
		vBinary                                 	(7),
		vUnicode                                	(8),
		vLanMacAddress                          	(9),
		vWanAccessAddress                       	(10)
	}
	ACCESS		read-only
	STATUS		mandatory
	DESCRIPTION	"The type of identifier displayed by the Worldwide Identifier
attribute."
	::= {eStorageController 3}

a7WorldwideIdentifier OBJECT-TYPE
	SYNTAX		DmiDisplaystring
	ACCESS		read-only
	STATUS		mandatory
	DESCRIPTION	"The Worldwide identifier for this controller."
	::= {eStorageController 4}

a7ProtectionManagement OBJECT-TYPE
	SYNTAX		INTEGER {
		vOther                                  	(1),
		vUnknown                                	(2),
		vUnprotected                            	(3),
		vProtected                              	(4),
		vProtectedThroughScsi-3ControllerCommand	(5),
		vProtectedThroughScsi-3ControllerComman1	(6)
	}
	ACCESS		read-only
	STATUS		mandatory
	DESCRIPTION	"Indicates whether or not the controller provides redundancy
or protection against device failures."
	::= {eStorageController 5}

a7BusMaster OBJECT-TYPE
	SYNTAX		INTEGER {
		vFalse                                  	(0),
		vTrue                                   	(1),
		vUnknown                                	(2)
	}
	ACCESS		read-only
	STATUS		mandatory
	DESCRIPTION	"If true, then this storage controller is the bus master."
	::= {eStorageController 6}

a7SecondsSinceLastPower-up OBJECT-TYPE
	SYNTAX		DmiInteger
	ACCESS		read-only
	STATUS		mandatory
	DESCRIPTION	"The number of seconds that have passed since this controller
was last powered on."
	::= {eStorageController 7}

a7FruGroupIndex OBJECT-TYPE
	SYNTAX		DmiInteger
	ACCESS		read-only
	STATUS		mandatory
	DESCRIPTION	"If this is a Field Replaceable Unit or if it is part of another
FRU, this provides an index into the FRU table; 'value = -1' indicates that
the group is not a FRU."
	::= {eStorageController 8}

a7OperationalGroupIndex OBJECT-TYPE
	SYNTAX		DmiInteger
	ACCESS		read-only
	STATUS		mandatory
	DESCRIPTION	"The index into the Operational State table for this device."
	::= {eStorageController 9}

SStorageControllerEvents ::= SEQUENCE {
	a8StorageControllerEventType            	DmiInteger,
	a8EventSeverity                         	DmiInteger,
	a8EventIsStateBased                     	DmiInteger,
	a8EventStateKey                         	DmiInteger,
	a8AssociatedGroup                       	DmiDisplaystring,
	a8EventSystem                           	DmiInteger,
	a8EventSubsystem                        	DmiInteger
}

tStorageControllerEvents OBJECT-TYPE
	SYNTAX		SEQUENCE OF SStorageControllerEvents
	ACCESS		not-accessible
	STATUS		mandatory
	DESCRIPTION	"Storage Controller events."
	::= {dmtfGroups 8}

eStorageControllerEvents OBJECT-TYPE
	SYNTAX		SStorageControllerEvents
	ACCESS		not-accessible
	STATUS		mandatory
	DESCRIPTION	""
	INDEX		{DmiComponentIndex, a8AssociatedGroup}
	::= {tStorageControllerEvents 1}

a8StorageControllerEventType OBJECT-TYPE
	SYNTAX		INTEGER {
		vStorageControllerError                 	(1),
		vSelf-monitoringWarning1                	(2)
	}
	ACCESS		read-only
	STATUS		mandatory
	DESCRIPTION	"The type of Storage Controller event that has occurred."
	::= {eStorageControllerEvents 1}

a8EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eStorageControllerEvents 2}

a8EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eStorageControllerEvents 3}

a8EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eStorageControllerEvents 4}

a8AssociatedGroup OBJECT-TYPE
	SYNTAX		DmiDisplaystring
	ACCESS		read-only
	STATUS		mandatory
	DESCRIPTION	"The"
	::= {eStorageControllerEvents 5}

a8EventSystem OBJECT-TYPE
	SYNTAX		INTEGER {
		vOther                                  	(1),
		vUnknown                                	(2)
	}
	ACCESS		read-only
	STATUS		mandatory
	DESCRIPTION	"The major functional aspect of the product causing the fault."
	::= {eStorageControllerEvents 6}

a8EventSubsystem OBJECT-TYPE
	SYNTAX		INTEGER {
		vOther                                  	(1),
		vUnknown                                	(2)
	}
	ACCESS		read-only
	STATUS		mandatory
	DESCRIPTION	"The minor functional aspect of the product causing the fault."
	::= {eStorageControllerEvents 7}

SBusPort ::= SEQUENCE {
	a9BusPortIndex                          	DmiInteger,
	a9Protocol                              	DmiInteger,
	a9ProtocolDescription                   	DmiDisplaystring,
	a9SignalCharacteristics                 	DmiInteger,
	a9WorldwideIdentifierType               	DmiInteger,
	a9WorldwideIdentifier                   	DmiDisplaystring,
	a9AddressDescriptor                     	DmiDisplaystring,
	a9Isochronous                           	DmiInteger,
	a9MaximumWidth                          	DmiInteger,
	a9MaximumTransferRate                   	DmiInteger,
	a9MaximumNumberOfAttachments            	DmiInteger,
	a9ConnectorType                         	DmiInteger,
	a9ConnectorTypeDescription              	DmiDisplaystring,
	a9ConnectorGender                       	DmiInteger,
	a9OperationalGroupIndex                 	DmiInteger,
	a9MassStorageStatisticsGroupIndex       	DmiInteger
}

tBusPort OBJECT-TYPE
	SYNTAX		SEQUENCE OF SBusPort
	ACCESS		not-accessible
	STATUS		mandatory
	DESCRIPTION	"This global table has one entry for each of the Bus Ports
in this Component."
	::= {dmtfGroups 9}

eBusPort OBJECT-TYPE
	SYNTAX		SBusPort
	ACCESS		not-accessible
	STATUS		mandatory
	DESCRIPTION	""
	INDEX		{DmiComponentIndex, a9BusPortIndex}
	::= {tBusPort 1}

a9BusPortIndex OBJECT-TYPE
	SYNTAX		DmiInteger
	ACCESS		read-only
	STATUS		mandatory
	DESCRIPTION	"An index into the Bus Port table."
	::= {eBusPort 1}

a9Protocol OBJECT-TYPE
	SYNTAX		INTEGER {
		vOther                                  	(1),
		vUnknown                                	(2),
		vEisa                                   	(3),
		vIsa                                    	(4),
		vPci                                    	(5),
		vAtaatapi                               	(6),
		vFlexibleDiskette                       	(7),
		v1496                                   	(8),
		vScsiParallelInterface                  	(9),
		vScsiFibreChannelProtocol               	(10),
		vScsiSerialBusProtocol                  	(11),
		vScsiSerialBusProtocol-21394            	(12),
		vScsiSerialStorageArchitecture          	(13),
		vVesa                                   	(14),
		vPcmcia                                 	(15),
		vUniversalSerialBus                     	(16),
		vParallelPort                           	(17),
		vEscon                                  	(18),
		vDiagnostic                             	(19),
		vI2c                                    	(20),
		vPower                                  	(21),
		vHippi                                  	(22),
		vMultibus                               	(23),
		vVme                                    	(24),
		vIpi                                    	(25),
		vIeee-488                               	(26),
		vRs232                                  	(27),
		vIeee802310base5                        	(28),
		vIeee802310base2                        	(29),
		vIeee80231base5                         	(30),
		vIeee802310broad36                      	(31),
		vIeee8023100basevg                      	(32),
		vIeee8025Token-ring                     	(33),
		vAnsiX3t95Fddi                          	(34),
		vMca                                    	(35)
	}
	ACCESS		read-only
	STATUS		mandatory
	DESCRIPTION	"The protocol describing the electrical characteristic of
the Bus Port.  If 'Other' is used, then the Protocol Description attribute
shall be used."
	::= {eBusPort 2}

a9ProtocolDescription OBJECT-TYPE
	SYNTAX		DmiDisplaystring
	ACCESS		read-only
	STATUS		mandatory
	DESCRIPTION	"Additional description of the protocol described above. 
If 'Other' was specified above, then this field shall be used.  Otherwise,
the contents of this optional field shall not contradict the Protocol specified
above."
	::= {eBusPort 3}

a9SignalCharacteristics OBJECT-TYPE
	SYNTAX		INTEGER {
		vOther                                  	(1),
		vUnknown                                	(2),
		vSingleEnded                            	(3),
		vDifferential                           	(4),
		vLowVoltageDifferential                 	(5),
		vOptical                                	(6)
	}
	ACCESS		read-only
	STATUS		mandatory
	DESCRIPTION	"The signal characteristics of the Bus Port being described."
	::= {eBusPort 4}

a9WorldwideIdentifierType OBJECT-TYPE
	SYNTAX		INTEGER {
		vOther                                  	(1),
		vUnknown                                	(2),
		vNone                                   	(3),
		vVendorIdProductIdSerialNumber          	(4),
		vIeeeExtendedUniqueIdentifier64-bit     	(5),
		vFc-ph64-bitName-identifier             	(6),
		vBinary                                 	(7),
		vUnicode                                	(8),
		vLanMacAddress                          	(9),
		vWanAccessAddress                       	(10)
	}
	ACCESS		read-only
	STATUS		mandatory
	DESCRIPTION	"The type of identifier displayed by the Worldwide Identifier
attribute."
	::= {eBusPort 5}

a9WorldwideIdentifier OBJECT-TYPE
	SYNTAX		DmiDisplaystring
	ACCESS		read-only
	STATUS		mandatory
	DESCRIPTION	"The Worldwide identifier for this bus port."
	::= {eBusPort 6}

a9AddressDescriptor OBJECT-TYPE
	SYNTAX		DmiDisplaystring
	ACCESS		read-only
	STATUS		mandatory
	DESCRIPTION	"The address descriptor of this bus port.  For example, the
SCSI address of this port."
	::= {eBusPort 7}

a9Isochronous OBJECT-TYPE
	SYNTAX		INTEGER {
		vFalse                                  	(0),
		vTrue                                   	(1)
	}
	ACCESS		read-only
	STATUS		mandatory
	DESCRIPTION	"Indicates whether or not this bus port supports isochronous
transfers."
	::= {eBusPort 8}

a9MaximumWidth OBJECT-TYPE
	SYNTAX		DmiInteger
	ACCESS		read-only
	STATUS		mandatory
	DESCRIPTION	"The maximum width, in bits, of this Bus Port's data path.
 A value of 1 should be used for serial."
	::= {eBusPort 9}

a9MaximumTransferRate OBJECT-TYPE
	SYNTAX		DmiInteger
	ACCESS		read-only
	STATUS		mandatory
	DESCRIPTION	"The theoretical maximum transfer rate, in millions of bytes
per second, that this Bus Port is capable of achieving under ideal conditions.
 A value of zero should be used if the transfer rate is less than 1 million
bytes per second.  A value of 0x80000000 should be used if the transfer rate
is unknown."
	::= {eBusPort 10}

a9MaximumNumberOfAttachments OBJECT-TYPE
	SYNTAX		DmiInteger
	ACCESS		read-only
	STATUS		mandatory
	DESCRIPTION	"The maximum number of directly addressable entities supported
by this bus port's protocol.  A value of zero should be used if the number
of attachments is unknown."
	::= {eBusPort 11}

a9ConnectorType OBJECT-TYPE
	SYNTAX		INTEGER {
		vOther                                  	(1),
		vUnknown                                	(2),
		vNone                                   	(3),
		vScsiAHigh-densityShielded50Pins        	(4),
		vScsiAHigh-densityUnshielded50Pins      	(5),
		vScsiALow-densityShielded50Pins         	(6),
		vScsiALow-densityUnshielded50Pins       	(7),
		vScsiPHigh-densityShielded68Pins        	(8),
		vScsiPHigh-densityUnshielded68Pins      	(9),
		vScsiSca-i80Pins                        	(10),
		vScsiSca-ii80Pins                       	(11),
		vScsiFibreChannelDb9Copper              	(12),
		vScsiFibreChannelFibre                  	(13),
		vScsiFibreChannelSca-ii40Pins           	(14),
		vScsiFibreChannelSca-ii20Pins           	(15),
		vScsiFibreChannelBnc                    	(16),
		vAta3-12Inch40Pins                      	(17),
		vAta2-12Inch44Pins                      	(18),
		vSerial9Pin                             	(19),
		vSerial25Pin                            	(20),
		vRs23225Pin                             	(21),
		vRs422                                  	(22),
		vIeee-488                               	(23),
		vAui                                    	(24),
		vUptCategory3                           	(25),
		vUptCategory4                           	(26),
		vUptCategory5                           	(27),
		vBnc                                    	(28),
		vStpRj11                                	(29),
		vStpRj45                                	(30),
		vStpDb9                                 	(31),
		vFiberMic                               	(32),
		vAppleAui                               	(33),
		vPciSlot                                	(34),
		vIsaSlot                                	(35),
		vEisaSlot                               	(36),
		vVesaSlot                               	(37),
		vPcmciaSlot                             	(38),
		vPcCardSlot                             	(39),
		vFloppyDiskette5-14Inch                 	(40),
		vFloppyDiskette3-12Inch                 	(41),
		vHssdc6Pins                             	(42),
		vGbicSocket                             	(43)
	}
	ACCESS		read-only
	STATUS		mandatory
	DESCRIPTION	"Describes how options (cards, devices, etc.) physically connect
to this bus port.  If 'Other' is used, then the Connector Type Description
attribute shall be used."
	::= {eBusPort 12}

a9ConnectorTypeDescription OBJECT-TYPE
	SYNTAX		DmiDisplaystring
	ACCESS		read-only
	STATUS		mandatory
	DESCRIPTION	"An additional text description of the type of connector describe
above.  If 'Other' was specified above, then this field shall be used.  Otherwis
, the contents of this optional field shall not contradict the connector
specified above."
	::= {eBusPort 13}

a9ConnectorGender OBJECT-TYPE
	SYNTAX		INTEGER {
		vOther                                  	(1),
		vUnknown                                	(2),
		vFemale                                 	(3),
		vMale                                   	(4)
	}
	ACCESS		read-only
	STATUS		mandatory
	DESCRIPTION	"Indicates the gender of the connector described above."
	::= {eBusPort 14}

a9OperationalGroupIndex OBJECT-TYPE
	SYNTAX		DmiInteger
	ACCESS		read-only
	STATUS		mandatory
	DESCRIPTION	"The index into the Operational State table for this bus port."
	::= {eBusPort 15}

a9MassStorageStatisticsGroupIndex OBJECT-TYPE
	SYNTAX		DmiInteger
	ACCESS		read-only
	STATUS		mandatory
	DESCRIPTION	"The index into the Mass Storage Statistics table for this
bus port."
	::= {eBusPort 16}

SBusPortEvents ::= SEQUENCE {
	a10BusPortEventType                     	DmiInteger,
	a10EventSeverity                        	DmiInteger,
	a10EventIsStateBased                    	DmiInteger,
	a10EventStateKey                        	DmiInteger,
	a10AssociatedGroup                      	DmiDisplaystring,
	a10EventSystem                          	DmiInteger,
	a10EventSubsystem                       	DmiInteger
}

tBusPortEvents OBJECT-TYPE
	SYNTAX		SEQUENCE OF SBusPortEvents
	ACCESS		not-accessible
	STATUS		mandatory
	DESCRIPTION	"Bus Port events."
	::= {dmtfGroups 10}

eBusPortEvents OBJECT-TYPE
	SYNTAX		SBusPortEvents
	ACCESS		not-accessible
	STATUS		mandatory
	DESCRIPTION	""
	INDEX		{DmiComponentIndex, a10AssociatedGroup}
	::= {tBusPortEvents 1}

a10BusPortEventType OBJECT-TYPE
	SYNTAX		INTEGER {
		vBusPortError                           	(1)
	}
	ACCESS		read-only
	STATUS		mandatory
	DESCRIPTION	"The type of Bus Port event that has occurred."
	::= {eBusPortEvents 1}

a10EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eBusPortEvents 2}

a10EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eBusPortEvents 3}

a10EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eBusPortEvents 4}

a10AssociatedGroup OBJECT-TYPE
	SYNTAX		DmiDisplaystring
	ACCESS		read-only
	STATUS		mandatory
	DESCRIPTION	"The"
	::= {eBusPortEvents 5}

a10EventSystem OBJECT-TYPE
	SYNTAX		INTEGER {
		vOther                                  	(1),
		vUnknown                                	(2)
	}
	ACCESS		read-only
	STATUS		mandatory
	DESCRIPTION	"The major functional aspect of the product causing the fault."
	::= {eBusPortEvents 6}

a10EventSubsystem OBJECT-TYPE
	SYNTAX		INTEGER {
		vOther                                  	(1),
		vUnknown                                	(2)
	}
	ACCESS		read-only
	STATUS		mandatory
	DESCRIPTION	"The minor functional aspect of the product causing the fault."
	::= {eBusPortEvents 7}

SMassStorageAssociation ::= SEQUENCE {
	a11AssociationIndex                     	DmiInteger,
	a11Type                                 	DmiInteger,
	a11Object1Type                          	DmiInteger,
	a11Object1Index                         	DmiInteger,
	a11Object2Type                          	DmiInteger,
	a11Object2Index                         	DmiInteger
}

tMassStorageAssociation OBJECT-TYPE
	SYNTAX		SEQUENCE OF SMassStorageAssociation
	ACCESS		not-accessible
	STATUS		mandatory
	DESCRIPTION	"Mass storage associations define the relationships between
the various components of the Storage Subsystem."
	::= {dmtfGroups 11}

eMassStorageAssociation OBJECT-TYPE
	SYNTAX		SMassStorageAssociation
	ACCESS		not-accessible
	STATUS		mandatory
	DESCRIPTION	""
	INDEX		{DmiComponentIndex, a11AssociationIndex}
	::= {tMassStorageAssociation 1}

a11AssociationIndex OBJECT-TYPE
	SYNTAX		DmiInteger
	ACCESS		read-only
	STATUS		mandatory
	DESCRIPTION	"An index into the Association table."
	::= {eMassStorageAssociation 1}

a11Type OBJECT-TYPE
	SYNTAX		INTEGER {
		vPhysicalOrganization                   	(0),
		vLogicalOrganization                    	(1),
		vLogicalToPhysicalOrganization          	(2),
		vRedundancyOrganization                 	(3),
		vSpareOrganization                      	(4),
		vCacheOrganization                      	(5),
		vSoftwareOrganization                   	(6)
	}
	ACCESS		read-only
	STATUS		mandatory
	DESCRIPTION	"This field specifies the type of the association."
	::= {eMassStorageAssociation 2}

a11Object1Type OBJECT-TYPE
	SYNTAX		INTEGER {
		vStorageController                      	(0),
		vStorageDevice                          	(1),
		vBusPort                                	(2),
		vVolumeSet                              	(3),
		vProtectedSpaceExtent                   	(4),
		vAggregateProtectedSpaceExtent          	(5),
		vPhysicalExtent                         	(6),
		vAggregatePhysicalExtent                	(7),
		vRedundancyGroup                        	(8),
		vCache                                  	(9),
		vSoftwareComponent                      	(10),
		vSoftwareSignature                      	(11)
	}
	ACCESS		read-only
	STATUS		mandatory
	DESCRIPTION	"This field specifies the type of the object referred to by
object 1 index.  Therefore, combined with the object 1 index a complete referenc
 is made to a specific object."
	::= {eMassStorageAssociation 3}

a11Object1Index OBJECT-TYPE
	SYNTAX		DmiInteger
	ACCESS		read-only
	STATUS		mandatory
	DESCRIPTION	"An index into the table identified by the object 1 type."
	::= {eMassStorageAssociation 4}

a11Object2Type OBJECT-TYPE
	SYNTAX		INTEGER {
		vStorageController                      	(0),
		vStorageDevice                          	(1),
		vBusPort                                	(2),
		vVolumeSet                              	(3),
		vProtectedSpaceExtent                   	(4),
		vAggregateProtectedSpaceExtent          	(5),
		vPhysicalExtent                         	(6),
		vAggregatePhysicalExtent                	(7),
		vRedundancyGroup                        	(8),
		vCache                                  	(9),
		vSoftwareComponent                      	(10),
		vSoftwareSignature                      	(11)
	}
	ACCESS		read-only
	STATUS		mandatory
	DESCRIPTION	"This field specifies the type of the object referred to by
object 2 index.  Therefore, combined with the object 2 index a complete referenc
 is made to a specific object."
	::= {eMassStorageAssociation 5}

a11Object2Index OBJECT-TYPE
	SYNTAX		DmiInteger
	ACCESS		read-only
	STATUS		mandatory
	DESCRIPTION	"An index into the table identified by the Object 2 type."
	::= {eMassStorageAssociation 6}

SMassStorageAssociationEvents ::= SEQUENCE {
	a12MassStorageAssociationEventType      	DmiInteger,
	a12EventSeverity                        	DmiInteger,
	a12EventIsStateBased                    	DmiInteger,
	a12EventStateKey                        	DmiInteger,
	a12AssociatedGroup                      	DmiDisplaystring,
	a12EventSystem                          	DmiInteger,
	a12EventSubsystem                       	DmiInteger
}

tMassStorageAssociationEvents OBJECT-TYPE
	SYNTAX		SEQUENCE OF SMassStorageAssociationEvents
	ACCESS		not-accessible
	STATUS		mandatory
	DESCRIPTION	"Mass Storage Association events."
	::= {dmtfGroups 12}

eMassStorageAssociationEvents OBJECT-TYPE
	SYNTAX		SMassStorageAssociationEvents
	ACCESS		not-accessible
	STATUS		mandatory
	DESCRIPTION	""
	INDEX		{DmiComponentIndex, a12AssociatedGroup}
	::= {tMassStorageAssociationEvents 1}

a12MassStorageAssociationEventType OBJECT-TYPE
	SYNTAX		INTEGER {
		vPhysicalOrganization                   	(0),
		vLogicalOrganization                    	(1),
		vLogicalToPhysicalOrganization          	(2),
		vRedundancyOrganization                 	(3),
		vSpareOrganization                      	(4),
		vCacheOrganization                      	(5),
		vSoftwareOrganization                   	(6)
	}
	ACCESS		read-only
	STATUS		mandatory
	DESCRIPTION	"The type of Mass storage association where a change has occurred
"
	::= {eMassStorageAssociationEvents 1}

a12EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eMassStorageAssociationEvents 2}

a12EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eMassStorageAssociationEvents 3}

a12EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eMassStorageAssociationEvents 4}

a12AssociatedGroup OBJECT-TYPE
	SYNTAX		DmiDisplaystring
	ACCESS		read-only
	STATUS		mandatory
	DESCRIPTION	"The"
	::= {eMassStorageAssociationEvents 5}

a12EventSystem OBJECT-TYPE
	SYNTAX		INTEGER {
		vStorageController                      	(0),
		vStorageDevice                          	(1),
		vBusPort                                	(2),
		vVolumeSet                              	(3),
		vProtectedSpaceExtent                   	(4),
		vAggregateProtectedSpaceExtent          	(5),
		vPhysicalExtent                         	(6),
		vAggregatePhysicalExtent                	(7),
		vRedundancyGroup                        	(8),
		vCache                                  	(9),
		vSoftwareComponent                      	(10),
		vSoftwareSignature                      	(11)
	}
	ACCESS		read-only
	STATUS		mandatory
	DESCRIPTION	"The mass storage association object type which is causing
a change."
	::= {eMassStorageAssociationEvents 6}

a12EventSubsystem OBJECT-TYPE
	SYNTAX		INTEGER {
		vOther                                  	(1),
		vUnknown                                	(2)
	}
	ACCESS		read-only
	STATUS		mandatory
	DESCRIPTION	"The minor functional aspect of the product causing the fault."
	::= {eMassStorageAssociationEvents 7}

SBusPortAssociation ::= SEQUENCE {
	a13BusPortAssociationIndex              	DmiInteger,
	a13NegotiatedSpeed                      	DmiInteger,
	a13NegotiatedWidth                      	DmiInteger
}

tBusPortAssociation OBJECT-TYPE
	SYNTAX		SEQUENCE OF SBusPortAssociation
	ACCESS		not-accessible
	STATUS		mandatory
	DESCRIPTION	"Bus Port Association "
	::= {dmtfGroups 13}

eBusPortAssociation OBJECT-TYPE
	SYNTAX		SBusPortAssociation
	ACCESS		not-accessible
	STATUS		mandatory
	DESCRIPTION	""
	INDEX		{DmiComponentIndex, a13BusPortAssociationIndex}
	::= {tBusPortAssociation 1}

a13BusPortAssociationIndex OBJECT-TYPE
	SYNTAX		DmiInteger
	ACCESS		read-only
	STATUS		mandatory
	DESCRIPTION	"An index into the Bus Port Association table.  This index
is the same as the index in the Association group that defines the bus port
association."
	::= {eBusPortAssociation 1}

a13NegotiatedSpeed OBJECT-TYPE
	SYNTAX		DmiInteger
	ACCESS		read-only
	STATUS		mandatory
	DESCRIPTION	"The maximum burst transfer rate, in millions of bytes, which
was negotiated between the two associated bus ports."
	::= {eBusPortAssociation 2}

a13NegotiatedWidth OBJECT-TYPE
	SYNTAX		DmiInteger
	ACCESS		read-only
	STATUS		mandatory
	DESCRIPTION	"The width, in bits, of the bus ports data path which was
negotiated between the two associated bus ports."
	::= {eBusPortAssociation 3}

SOperationalState ::= SEQUENCE {
	a14OperationalStateInstanceIndex        	DmiInteger,
	a14DeviceGroupIndex                     	DmiInteger,
	a14OperationalStatus                    	DmiInteger,
	a14UsageState                           	DmiInteger,
	a14AvailabilityStatus                   	DmiInteger,
	a14AdministrativeState                  	DmiInteger,
	a14FatalErrorCount                      	DmiCounter,
	a14MajorErrorCount                      	DmiCounter,
	a14WarningErrorCount                    	DmiCounter,
	a14CurrentErrorStatus                   	DmiInteger,
	a14DevicePredictedFailureStatus         	DmiInteger
}

tOperationalState OBJECT-TYPE
	SYNTAX		SEQUENCE OF SOperationalState
	ACCESS		not-accessible
	STATUS		mandatory
	DESCRIPTION	"This group provides the operational state, usage, and availabili
y status, and administrative state indicators for specific Device Group instance
."
	::= {dmtfGroups 14}

eOperationalState OBJECT-TYPE
	SYNTAX		SOperationalState
	ACCESS		not-accessible
	STATUS		mandatory
	DESCRIPTION	""
	INDEX		{DmiComponentIndex, a14OperationalStateInstanceIndex}
	::= {tOperationalState 1}

a14OperationalStateInstanceIndex OBJECT-TYPE
	SYNTAX		DmiInteger
	ACCESS		read-only
	STATUS		mandatory
	DESCRIPTION	"The Index into the Operational State table."
	::= {eOperationalState 1}

a14DeviceGroupIndex OBJECT-TYPE
	SYNTAX		DmiInteger
	ACCESS		read-only
	STATUS		mandatory
	DESCRIPTION	"The group ID of the group referencing this instance."
	::= {eOperationalState 2}

a14OperationalStatus OBJECT-TYPE
	SYNTAX		INTEGER {
		vOther                                  	(1),
		vUnknown                                	(2),
		vEnabled                                	(3),
		vDisabled                               	(4),
		vNotApplicable                          	(5)
	}
	ACCESS		read-only
	STATUS		mandatory
	DESCRIPTION	"The operational status of the Device Group instance."
	::= {eOperationalState 3}

a14UsageState OBJECT-TYPE
	SYNTAX		INTEGER {
		vOther                                  	(1),
		vUnknown                                	(2),
		vIdle                                   	(3),
		vActive                                 	(4),
		vBusy                                   	(5),
		vNotApplicable                          	(6)
	}
	ACCESS		read-only
	STATUS		mandatory
	DESCRIPTION	"The usage state of the Device Group instance."
	::= {eOperationalState 4}

a14AvailabilityStatus OBJECT-TYPE
	SYNTAX		INTEGER {
		vOther                                  	(1),
		vUnknown                                	(2),
		vRunning                                	(3),
		vWarning                                	(4),
		vInTest                                 	(5),
		vNotApplicable                          	(6),
		vPowerOff                               	(7),
		vOffLine                                	(8),
		vOffDuty                                	(9),
		vDegraded                               	(10),
		vNotInstalled                           	(11),
		vInstallError                           	(12),
		vPowerSave                              	(13)
	}
	ACCESS		read-only
	STATUS		mandatory
	DESCRIPTION	"The availability status of the Device Group instance."
	::= {eOperationalState 5}

a14AdministrativeState OBJECT-TYPE
	SYNTAX		INTEGER {
		vOther                                  	(1),
		vUnknown                                	(2),
		vLocked                                 	(3),
		vUnlocked                               	(4),
		vNotApplicable                          	(5),
		vShuttingDown                           	(6)
	}
	ACCESS		read-only
	STATUS		mandatory
	DESCRIPTION	"The administrative state of the Device Group instance."
	::= {eOperationalState 6}

a14FatalErrorCount OBJECT-TYPE
	SYNTAX		DmiCounter
	ACCESS		read-only
	STATUS		mandatory
	DESCRIPTION	"The accumulated Fatal or Non-recoverable error count for
this Device Group instance."
	::= {eOperationalState 7}

a14MajorErrorCount OBJECT-TYPE
	SYNTAX		DmiCounter
	ACCESS		read-only
	STATUS		mandatory
	DESCRIPTION	"The accumulated Major or Critical error count for this Device
Group instance."
	::= {eOperationalState 8}

a14WarningErrorCount OBJECT-TYPE
	SYNTAX		DmiCounter
	ACCESS		read-only
	STATUS		mandatory
	DESCRIPTION	"The accumulated Warning or Non-Critical error count for this
Device Group instance."
	::= {eOperationalState 9}

a14CurrentErrorStatus OBJECT-TYPE
	SYNTAX		INTEGER {
		vOther                                  	(1),
		vUnknown                                	(2),
		vOk                                     	(3),
		vNon-critical1                          	(4),
		vCritical                               	(5),
		vNon-recoverable1                       	(6)
	}
	ACCESS		read-only
	STATUS		mandatory
	DESCRIPTION	"This attribute presents the current error status for this
Device Group instance. The most critical error status in effect should be
presented. I.e. if a part of the Device Group instance is 'Critical', while
other status is 'Non-critical' then the status 'Critical' should be reported."
	::= {eOperationalState 10}

a14DevicePredictedFailureStatus OBJECT-TYPE
	SYNTAX		INTEGER {
		vOther                                  	(1),
		vUnknown                                	(2),
		vNotSupportedByThisDevice               	(3),
		vNoFailurePredictedByTheDevice          	(4),
		vDeviceFailurePredictedByTheDevice      	(5),
		vMediaFailurePredictedByTheDevice       	(6)
	}
	ACCESS		read-only
	STATUS		mandatory
	DESCRIPTION	"Enumeration describing the current Device Predicted Failure
Status (e.g.: the S.M.A.R.T. status of the device)."
	::= {eOperationalState 11}

SSymi2omassstoragesystem ::= SEQUENCE {
	a15SymDeviceIndex                       	DmiInteger,
	a15SymDeviceIndex2                       	DmiInteger,
	a15SmartReportingCapability             	DmiInteger,
	a15SmartPollingPeriod                   	DmiInteger
}

tSymi2omassstoragesystem OBJECT-TYPE
	SYNTAX		SEQUENCE OF SSymi2omassstoragesystem
	ACCESS		not-accessible
	STATUS		mandatory
	DESCRIPTION	"This group is the Symbios Vendor unique group. "
	::= {dmtfGroups 15}

eSymi2omassstoragesystem OBJECT-TYPE
	SYNTAX		SSymi2omassstoragesystem
	ACCESS		not-accessible
	STATUS		mandatory
	DESCRIPTION	""
	INDEX		{DmiComponentIndex, a15SymDeviceIndex}
	::= {tSymi2omassstoragesystem 1}

a15SymDeviceIndex OBJECT-TYPE
	SYNTAX		DmiInteger
	ACCESS		read-only
	STATUS		mandatory
	DESCRIPTION	"An index into the Symbios Vendor Unique Device info table."
	::= {eSymi2omassstoragesystem 1}

a15SymDeviceIndex2 OBJECT-TYPE
	SYNTAX		DmiInteger
	ACCESS		read-only
	STATUS		mandatory
	DESCRIPTION	"An Symbios Vendor Unique Flag."
	::= {eSymi2omassstoragesystem 2}

a15SmartReportingCapability OBJECT-TYPE
	SYNTAX		INTEGER {
		vDisabled                               	(0),
		vEnabled                                	(1),
		vUnknown                                	(2),
		vNotSupported                           	(3)
	}
	ACCESS		read-write
	STATUS		mandatory
	DESCRIPTION	"A flag indicating the state of a Devices's SMART reporting
capability."
	::= {eSymi2omassstoragesystem 3}

a15SmartPollingPeriod OBJECT-TYPE
	SYNTAX		DmiInteger
	ACCESS		read-write
	STATUS		mandatory
	DESCRIPTION	"Number of minutes to wait between polling a device for its
S.M.A.R.T. status."
	::= {eSymi2omassstoragesystem 4}

SMiftomib ::= SEQUENCE {
	a99MibName                              	DmiDisplaystring,
	a99MibOid                               	DmiDisplaystring,
	a99DisableTrap                          	DmiInteger
}

tMiftomib OBJECT-TYPE
	SYNTAX		SEQUENCE OF SMiftomib
	ACCESS		not-accessible
	STATUS		mandatory
	DESCRIPTION	"This group defines attributes required for DMI to SNMP translati
n."
	::= {dmtfGroups 99}

eMiftomib OBJECT-TYPE
	SYNTAX		SMiftomib
	ACCESS		not-accessible
	STATUS		mandatory
	DESCRIPTION	""
	INDEX		{DmiComponentIndex}
	::= {tMiftomib 1}

a99MibName OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB OID that corresponds to this MIF"
	::= {eMiftomib 2}

a99DisableTrap OBJECT-TYPE
	SYNTAX		DmiInteger
	ACCESS		read-write
	STATUS		mandatory
	DESCRIPTION	"This attribute can be changed to disable sending oftraps
from this component"
	::= {eMiftomib 3}

END
