APPEXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress
			FROM SNMPv2-SMI
		RowStatus, DisplayString
			FROM SNMPv2-TC
		appExt
			FROM APENT-MIB;


    apAppMib MODULE-IDENTITY
	   LAST-UPDATED "9802052000Z" -- Thur March 5 20:00:00 EST 1997
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for App"
      ::= { appExt 1}




apAppSessionTable OBJECT-TYPE
	SYNTAX      SEQUENCE OF ApAppSessionEntry
	MAX-ACCESS  not-accessible
	STATUS      current
	DESCRIPTION
		"A table of App Sessions."
	::= {appExt 2}

apAppSessionEntry OBJECT-TYPE
	SYNTAX      ApAppSessionEntry
	MAX-ACCESS  not-accessible
	STATUS      current
	DESCRIPTION
	       "ArrowPoint App table extensions"
	INDEX  {apAppIpAddr}
	::= {apAppSessionTable 1}

ApAppSessionEntry ::=
	SEQUENCE {
	       apAppIpAddr               IpAddress,
	       apAppAuthType             INTEGER,
	       apAppEncryptType          INTEGER,
	       apAppKalFreq              INTEGER,
	       apAppSecret               DisplayString,
	       apAppPktsTx               INTEGER,
	       apAppPktsRx               INTEGER,
	       apAppSessionState         INTEGER,
	       apAppRcmdEnable           INTEGER,
	       apAppSessionStatus        RowStatus
		 }

apAppIpAddr OBJECT-TYPE
	SYNTAX      IpAddress
	MAX-ACCESS  read-only
	STATUS      current
	DESCRIPTION
	       "The Interface IP Address of Peer"
	::= {apAppSessionEntry 1}

apAppAuthType OBJECT-TYPE
	SYNTAX      INTEGER {
						authNone(0),
						authChallenge(1)
			    }
	MAX-ACCESS  read-create
	STATUS      current
	DESCRIPTION
	       "The type of Authentication performed on Peer"
	::= {apAppSessionEntry 2}

apAppEncryptType OBJECT-TYPE
	SYNTAX      INTEGER {
						encryptNone(0),
						encryptMd5hash(1)
			    }
	MAX-ACCESS  read-create
	STATUS      current
	DESCRIPTION
	       "The type of Encryption performed with Peer"
	::= {apAppSessionEntry 3}

apAppKalFreq OBJECT-TYPE
	SYNTAX      INTEGER    ( 14..900 )
	MAX-ACCESS  read-create
	STATUS      current
	DESCRIPTION
	       "Keep alive timer interval (seconds). Default is 14 sec."
	DEFVAL {14}
	::= {apAppSessionEntry 4}

apAppSecret OBJECT-TYPE
	SYNTAX          DisplayString (SIZE(0..32))
	MAX-ACCESS      read-create
	STATUS                  current
	DESCRIPTION     
		"The secret authentication and encryption"
	::= {apAppSessionEntry 5}

apAppPktsTx OBJECT-TYPE
	SYNTAX      INTEGER
	MAX-ACCESS  read-only
	STATUS      current
	DESCRIPTION
	       "Count of the number of APP packets transmitted."
	::= {apAppSessionEntry 6}

apAppPktsRx OBJECT-TYPE
	SYNTAX      INTEGER
	MAX-ACCESS  read-only
	STATUS      current
	DESCRIPTION
	       "Count of the number of APP packets received."
	::= {apAppSessionEntry 7}

apAppSessionState OBJECT-TYPE
	SYNTAX      INTEGER {
						stopped(0),
						init(1),
						opened(2),
						auth(3),
						up(4),
						down(5)
			    }
	MAX-ACCESS  read-only
	STATUS      current
	DESCRIPTION
	       "The current State of the Session"
	::= {apAppSessionEntry 8}

apAppRcmdEnable OBJECT-TYPE
	SYNTAX      INTEGER {
						rcmdEnable(0),
						rcmdDisable(1)
			    }
	MAX-ACCESS  read-create
	STATUS      current
	DESCRIPTION
	       "Determines if remote CLI cmds are permitted on this Peer"
	::= {apAppSessionEntry 9}

apAppSessionStatus OBJECT-TYPE
	SYNTAX      RowStatus
	MAX-ACCESS  read-create
	STATUS      current
	DESCRIPTION
	       "Status entry for this row"
	::= {apAppSessionEntry 10}



apAppEnable OBJECT-TYPE
	SYNTAX      INTEGER {
                             disable(0),
                             enable(1)
                            }
	MAX-ACCESS  read-write
	STATUS      current
	DESCRIPTION
	       "Parameter to enable or disable App functionality."
	DEFVAL {disable}
	::= {appExt 3}

apAppPortNumber OBJECT-TYPE
	SYNTAX      INTEGER    ( 1..65535 )
	MAX-ACCESS  read-write
	STATUS      current
	DESCRIPTION
	       "The Port Number for the APP Protocol"
	DEFVAL {5001}
	::= {appExt 4}

apAppMaxFrameSize OBJECT-TYPE
	SYNTAX      INTEGER    ( 10240..65535 )
	MAX-ACCESS  read-write
	STATUS      current
	DESCRIPTION
	       "The maximum frame size allowed by the APP Protocol"
	DEFVAL {10240}
	::= {appExt 5}
END
