PICTURETEL-VCS-CONFIG-MIB DEFINITIONS ::= BEGIN

IMPORTS
	MODULE-IDENTITY, OBJECT-TYPE, OBJECT-IDENTITY
FROM SNMPv2-SMI
	TruthValue, TimeStamp, DisplayString
FROM SNMPv2-TC
	ptConfiguration
FROM PICTURETEL-VCS-MIB;

pictureTelVCSConfigurationModule MODULE-IDENTITY
	LAST-UPDATED "0101030000Z"
	ORGANIZATION "PictureTel Corporation"
	CONTACT-INFO
		"
		Postal:	PictureTel Corporation
				100 Minuteman Drive
				Andover, MA 01810-1031
				USA"
	DESCRIPTION
		"Final version of the PictureTel Configuration MIB"
	REVISION	"0101030000Z"
	DESCRIPTION
		"Rev 0.0.05
		3 Jan 2001 12:00  
		Latest version of MIB module PICTURETEL-VCS-CONFIG-MIB"

 ::= { ptConfiguration 1 }


--
-- Configuration placeholders
--

ptBasicConfig           OBJECT-IDENTITY
	STATUS          current
	DESCRIPTION     "Subtree for basic system configuration"
	::= { pictureTelVCSConfigurationModule 1 }


ptAdvancedConfig             OBJECT-IDENTITY
	STATUS          current
	DESCRIPTION     "Subtree for advanced system configuration"
	::= { pictureTelVCSConfigurationModule 2 }


--
--  Basic System configuration
--

ptConfSysName OBJECT-TYPE
	SYNTAX	DisplayString
	MAX-ACCESS	read-only
	STATUS	current
	DESCRIPTION
		"An administratively assigned name for the videoconferencing 
		system. If the name is unknown, the value contained in this 
		object is the zero-length string.  This value is the same as 
		the system name defined in the system software."
	REFERENCE
		"This object contains a value identical to that of the MIB-II 
		sysName object"
	::= { ptBasicConfig 1 }

ptConfSysDescription OBJECT-TYPE
	SYNTAX	DisplayString
	MAX-ACCESS	read-write
	STATUS	current
	DESCRIPTION
		"A textual description of the entity.  This value
		should include the full name and version
		identification of the system's hardware type,
		software operating-system, and networking
		software.  It is mandatory that this only contain
		printable ASCII characters."
	::= { ptBasicConfig 2 }

ptConfSysContact OBJECT-TYPE
	SYNTAX	DisplayString
	MAX-ACCESS	read-write
	STATUS	current
	DESCRIPTION
		"The textual identification of the on-site support staff
		responsible for the videoconferencing system installation.  If
		no contact information is known, the value contained in this
		object is the zero-length string."
	REFERENCE
		"This object contains a value identical to that of the MIB-II 
		sysContact object"
	::= { ptBasicConfig 3 }

ptConfSysOID OBJECT-TYPE
	SYNTAX	OBJECT IDENTIFIER
	MAX-ACCESS	read-only
	STATUS	current
	DESCRIPTION
		"The product identifier for the videoconferencing system.  The 
		value of this managed object is an Object Value Assignment 
		(OVA), residing within the registration subtree of the
		vendor's enterprise name space.  This object is useful in 
		verifying the model and version of the vendor's service."
	REFERENCE
		"This object contains a value identical to that of the MIB-II 
		sysObjectID object"
	::= { ptBasicConfig 4 }

ptConfSysUpTime OBJECT-TYPE
	SYNTAX  TimeStamp
	MAX-ACCESS  read-only
	STATUS  current
	DESCRIPTION
		"The time (in hundredths of a second) since the network
		 management portion of the system was last re-initialized"
	::= { ptBasicConfig 5 }

ptConfSysLocation OBJECT-TYPE
	SYNTAX	DisplayString
	MAX-ACCESS	read-write
	STATUS	current
	DESCRIPTION
		"The physical location of the videoconferencing system (e.g., 
		`Main conference room - 3rd floor').  If the location is unknown,
		the value contained in this object is the zero-length string."
	REFERENCE
		"This object contains a value identical to that of the MIB-II 
		sysLocation object"
	::= { ptBasicConfig 6 }


ptConfSysNotificationMode OBJECT-TYPE
	SYNTAX	TruthValue
	MAX-ACCESS	read-write
	STATUS	current
	DESCRIPTION
		"If the value of this object is true(1), then the notifications 
		are enabled"
	::= { ptBasicConfig 7 }


END
