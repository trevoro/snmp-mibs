-- ZyXEL Communications Corporation
-- Private Enterprise MIB definition 
  
-- This file describes the ZyXEL Communications Corporation Enterprise MIB.
-- It contains ZyXEL products OIDs, and common managed objects.

-- $Log: ZYXEL-MULTICAST-MIB.mib $
-- Revision 1.3  2012/09/19 07:42:34  Kevin
-- if it's leaf node, revise the vender name from zyxel to zy
-- Revision 1.2  2012/07/05 06:23:47  Kevin
-- 1. upgrade from SNMP to SNMPv2 
-- 2. clean warning
-- Revision 1.1  2012/05/30 07:50:20  Kevin
-- Initial revision

ZYXEL-MULTICAST-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt
    	FROM ZYXEL-ES-SMI;

	zyxelMulticast MODULE-IDENTITY
	LAST-UPDATED	"201207010000Z"    
	ORGANIZATION "Enterprise Solution ZyXEL"     
	CONTACT-INFO
		""	   
	DESCRIPTION
		"The subtree for multicast"
	::= { esMgmt 54 }
	
	zyxelMulticastSetup     OBJECT IDENTIFIER ::= { zyxelMulticast 1 }

	
  
-- *******************************************************************
-- *
-- * zyxelMulticastSetup
-- *
-- *******************************************************************
       
-- zyxelMulticastUnknownMulticastFrameForwarding
        zyMulticastUnknownMulticastFrameForwarding OBJECT-TYPE
        SYNTAX  INTEGER {
         	flooding(1),
         	drop(2)
        }
        MAX-ACCESS  read-write
        STATUS  current
        DESCRIPTION
			"Specify the action to perform when the switch receives an unknown multicast frame. Unknown multicast 
			frames are addressed to multicast groups for which the Switch has not recorded any group members. 
			Select Drop to discard the frame(s). Select Flooding to send the frame(s) to all ports of the same 
			domain."
        ::= { zyxelMulticastSetup 1 }

-- zyxelMulticastReservedMulticastFrameForwarding
        zyMulticastReservedMulticastFrameForwarding OBJECT-TYPE
        SYNTAX  INTEGER {
         	flooding(1),
         	drop(2)
        }
        MAX-ACCESS  read-write
        STATUS  current
        DESCRIPTION
			"The IP address range of 224.0.0.0 to 224.0.0.255 are reserved for multicasting on the local 
			network only. For example, 224.0.0.1 is for all hosts on a local network segment and 224.0.0.9 is 
			used to send RIP routing information to all RIP v2 routers on the same network segment. A multicast 
			router will not forward a packet with the destination IP address within this range to other networks. 
			See the IANA web site for more information. 
			The layer-2 multicast MAC addresses are also included in this group. 
			Specify the action to perform when the Switch receives a frame with a reserved multicast address. 
			Select Drop to discard the frame(s). Select Flooding to send the frame(s) to all ports of the same domain. "
        ::= { zyxelMulticastSetup 2 }  

 

END
