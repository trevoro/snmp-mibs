-- 3COM MDM MIB 
-- MIB File Generated on 26-Jan-1999 at 18:21:57

MDM-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

mdm OBJECT IDENTIFIER ::= { nas 6 }

mdmID OBJECT IDENTIFIER ::= { mdm 1 }

mdmIDTable OBJECT-TYPE
SYNTAX SEQUENCE OF MdmIDEntry
ACCESS not-accessible
STATUS mandatory
DESCRIPTION
"A list of modem ID entries."
::= { mdmID 1 }

mdmIDEntry OBJECT-TYPE
SYNTAX MdmIDEntry
ACCESS not-accessible
STATUS mandatory
DESCRIPTION
"An Identification table entry, containing objects which 
define the identity and capabilities of a modem."
INDEX { mdmIDIndex }
::= { mdmIDTable 1 }

MdmIDEntry ::=
SEQUENCE {
mdmIDIndex
    INTEGER,
mdmIDModel
    INTEGER,
mdmIDCountry
    INTEGER,
mdmIDHardwareSerNum
    DisplayString,
mdmIDHardwareRev
    DisplayString,
mdmIDSupervisorSwRev
    DisplayString,
mdmIDDataPumpSwRev
    DisplayString,
mdmIDIoProcessorSwRev
    DisplayString,
mdmIDSupervisorDate
    DisplayString
}

mdmIDIndex OBJECT-TYPE
SYNTAX INTEGER
ACCESS read-only
STATUS mandatory
DESCRIPTION
"A unique value for each modem configured in the system 
based on the values in the entity table in the USR 
extensions to the chassis mib."
::= { mdmIDEntry 1 }

mdmIDModel OBJECT-TYPE
SYNTAX INTEGER{
  unknown(1),
  v32bisDualStandard(2),
  hst(3),
  v32bis(4),
  v32terboDualStandard(11),
  v32terbo(12),
  v32terboFax(13),
  v34DualStandard(14),
  v34(15),
  v34Fax(16),
  v34FaxISDN(30),
  x2(31),
  hdm24Channel(32),
  hdm30Channel(33),
  cdma(39)
}
ACCESS read-only
STATUS mandatory
DESCRIPTION
"Defines the model (ie. V.23, HST, etc.) of the modem 
represented by this row in the table."
::= { mdmIDEntry 2 }

mdmIDCountry OBJECT-TYPE
SYNTAX INTEGER{
  unknown(1),
  northamerica(2),
  japan(3),
  finland(4),
  sweden(5),
  uk(6),
  norway(7),
  switzerland(8),
  netherlands(9),
  southAfrica(10),
  italy(11),
  newZealand(12),
  czech(13),
  belgium(14),
  denmark(15),
  australia(16),
  france(17),
  germany(18),
  ccitt(19),
  austria(20),
  ireland(21),
  spain(22),
  portugal(23),
  malaysia(24)
}
ACCESS read-only
STATUS mandatory
DESCRIPTION
"This object identifies the country or countries that this 
modem is designed for use in."
::= { mdmIDEntry 3 }

mdmIDHardwareSerNum OBJECT-TYPE
SYNTAX DisplayString (SIZE(0..16))
ACCESS read-only
STATUS mandatory
DESCRIPTION
"The modem's hardware serial number as stored in EEPROM."
::= { mdmIDEntry 4 }

mdmIDHardwareRev OBJECT-TYPE
SYNTAX DisplayString (SIZE(0..11))
ACCESS read-only
STATUS mandatory
DESCRIPTION
"The hardware revision of the modem as stored in the modem's 
EEPROM."
::= { mdmIDEntry 5 }

mdmIDSupervisorSwRev OBJECT-TYPE
SYNTAX DisplayString (SIZE(0..11))
ACCESS read-only
STATUS mandatory
DESCRIPTION
"The revision of the software being executed by the modem's 
supervisor processor."
::= { mdmIDEntry 6 }

mdmIDDataPumpSwRev OBJECT-TYPE
SYNTAX DisplayString (SIZE(0..11))
ACCESS read-only
STATUS mandatory
DESCRIPTION
"The revision of software being executed by the modem's data 
pump processor."
::= { mdmIDEntry 7 }

mdmIDIoProcessorSwRev OBJECT-TYPE
SYNTAX DisplayString (SIZE(0..11))
ACCESS read-only
STATUS mandatory
DESCRIPTION
"The revison of software being executed by the modem's IO 
Control Processor."
::= { mdmIDEntry 8 }

mdmIDSupervisorDate OBJECT-TYPE
SYNTAX DisplayString (SIZE(0..8))
ACCESS read-only
STATUS mandatory
DESCRIPTION
"The supervisor build date."
::= { mdmIDEntry 9 }

-- The modem Line Interface Group

mdmLi OBJECT IDENTIFIER ::= { mdm 2 }

mdmLiTable OBJECT-TYPE
SYNTAX SEQUENCE OF MdmLiEntry
ACCESS not-accessible
STATUS mandatory
DESCRIPTION
"A list of configurable Line Interface objects for a modem.  
The number of table entries is given by modemNumber."
::= { mdmLi 1 }

mdmLiEntry OBJECT-TYPE
SYNTAX MdmLiEntry
ACCESS not-accessible
STATUS mandatory
DESCRIPTION
"Objects which define the line interface characteristics for 
a particualar modem."
INDEX { mdmLiIndex }
::= { mdmLiTable 1 }

MdmLiEntry ::=
SEQUENCE {
mdmLiIndex
    INTEGER,
mdmLiDialPause
    INTEGER,
mdmLiCarrierRecDelay
    INTEGER,
mdmLiCarrierLoss
    INTEGER,
mdmLiToneDialTiming
    INTEGER,
mdmLiDteRxDataDelay
    INTEGER,
mdmLiTransmiter
    INTEGER,
mdmLiDialMode
    INTEGER,
mdmLiGuardTone
    INTEGER,
mdmLiLeasedLine
    INTEGER,
mdmLiLeasedLineRestDelay
    INTEGER,
mdmLiPulseMakeBreak
    INTEGER,
mdmLiAnswerTone
    INTEGER,
mdmLiRemoteEscGuardTime
    INTEGER,
mdmLiRemoteEscChar
    INTEGER,
mdmLiRemAccessLimit
    INTEGER,
mdmLiRemPassword0
    DisplayString,
mdmLiRemPassword1
    DisplayString,
mdmLiTransmitLevel
    INTEGER,
mdmLiSrc
    INTEGER
}

mdmLiIndex OBJECT-TYPE
SYNTAX INTEGER
ACCESS read-only
STATUS mandatory
DESCRIPTION
"Index into the Line Interface table.  This index is the 
value from the chassis mib entity relation table that is 
applicable for a particular modem."
::= { mdmLiEntry 1 }

mdmLiDialPause OBJECT-TYPE
SYNTAX INTEGER (0..255)
ACCESS read-write
STATUS mandatory
DESCRIPTION
"Duration in seconds for the pause(') option in the dial 
command and the pause between command re-executions(> and 
A>) Default = 2.  Equates to the modem's S8 register."
::= { mdmLiEntry 2 }

mdmLiCarrierRecDelay OBJECT-TYPE
SYNTAX INTEGER (0..255)
ACCESS read-write
STATUS mandatory
DESCRIPTION
"Duration in 10ths of a second that the remote modem's 
carrier signal must be present before recognition.  Ignored 
at speeds above 2400. Equates to the modem's S9 register.  
Default=6."
::= { mdmLiEntry 3 }

mdmLiCarrierLoss OBJECT-TYPE
SYNTAX INTEGER (0..255)
ACCESS read-write
STATUS mandatory
DESCRIPTION
"Duration in 10ths of a second the modem waits after loss of 
carrier before hanging up.  This allows the modem to 
distinguish between a momentary lapse in line quality and a 
true disconnect.  When equal to 255 the modem will remain 
off hook until DTR drops or an ATH command is recieved.  
Equates to the modem's S10 register.  Default=7."
::= { mdmLiEntry 4 }

mdmLiToneDialTiming OBJECT-TYPE
SYNTAX INTEGER (0..255)
ACCESS read-write
STATUS mandatory
DESCRIPTION
"Duration and spacing in milliseconds of dialed Touch Tones. 
 Equates to the modem's S10 register.  Default=70."
::= { mdmLiEntry 5 }

mdmLiDteRxDataDelay OBJECT-TYPE
SYNTAX INTEGER (0..255)
ACCESS read-write
STATUS mandatory
DESCRIPTION
"Duration in 10ths of a second that the modem inserts a RX 
transmission delay between CD and the first recieved 
character.  Intended for custom applications and not 
recomended for general usage.  Equates to the modem's S35 
register.  Default=0."
::= { mdmLiEntry 6 }

mdmLiTransmiter OBJECT-TYPE
SYNTAX INTEGER{
  disable(1),
  enable(2)
}
ACCESS read-write
STATUS mandatory
DESCRIPTION
"Enables the modem to transmit data.  Corresponds to the 
modem 'C' register.  Default=2."
::= { mdmLiEntry 7 }

mdmLiDialMode OBJECT-TYPE
SYNTAX INTEGER{
  pulse(1),
  tone(2)
}
ACCESS read-write
STATUS mandatory
DESCRIPTION
"Determines whether the modem uses pulse or tone for dialing 
when initiating outgoing calls.   Equates to the P and T 
registers in the modem.  Default=0."

::= { mdmLiEntry 8 }

mdmLiGuardTone OBJECT-TYPE
SYNTAX INTEGER{
  none(1),
  european550(2),
  uk1800(3)
}
ACCESS read-write
STATUS mandatory
DESCRIPTION
"This object is required for modems answering calls that 
originate from sites outside of North America.  The modem's 
must be operating in either 1200 or 2400 bps and be using 
the V.32 answer sequence.  This object defines what guard 
tone is used for answering calls.  This object equates to 
the &G register in US Robotics modems.  Default=none."
::= { mdmLiEntry 9 }

mdmLiLeasedLine OBJECT-TYPE
SYNTAX INTEGER{
  disable(1),
  enable(2),
  cellularHSTMode(3)
}
ACCESS read-write
STATUS mandatory
DESCRIPTION
"Enables modem to operate in leased line mode.  When enabled 
the local an remote modems make a continuous connection 
without dialing.  Should the connection be broken the 
modem's will attempt to automaticly reestablish it(see 
mdmCcLeasedLineRest).  Equates to the modem's &L register 
Default = disabled."
::= { mdmLiEntry 10 }

mdmLiLeasedLineRestDelay OBJECT-TYPE
SYNTAX INTEGER (0..255)
ACCESS read-write
STATUS mandatory
DESCRIPTION
"Sets the duration, in seconds, of the delay between when 
the modem senses loss of carrier and when it attempts to 
reestablish a leased line connection.  The default setting 
of 15 should be appropriate for most installations."
::= { mdmLiEntry 11 }

mdmLiPulseMakeBreak OBJECT-TYPE
SYNTAX INTEGER{
  northAmerica(1),
  britishCommonwealth(2)
}
ACCESS read-write
STATUS mandatory
DESCRIPTION
"Determines the ratio of off hook to on hook interval for 
Pulse dialing.  Equates to the modem's &P register.  
Default=North America."
::= { mdmLiEntry 12 }

mdmLiAnswerTone OBJECT-TYPE
SYNTAX INTEGER{
  enable(1),
  disable(2)
}
ACCESS read-write
STATUS mandatory
DESCRIPTION
"Disables the 2100 Hz Answer tone allowing V.42 modems to 
connect more quickly and/or eliminating problems with older 
2400-bps modems that do not recognise this tone. Equates to 
the modem's S27.3 register. Default=Enabled."
::= { mdmLiEntry 13 }

mdmLiRemoteEscGuardTime OBJECT-TYPE
SYNTAX INTEGER (0..255)
ACCESS read-write
STATUS mandatory
DESCRIPTION
"Sets the duration in 20 millisecond increments of the guard 
time that the modem requires preceding and following the 
remote escape sequence.
The default is 200 or 4 seconds."
::= { mdmLiEntry 14 }

mdmLiRemoteEscChar OBJECT-TYPE
SYNTAX INTEGER (0..255)
ACCESS read-write
STATUS mandatory
DESCRIPTION
"Specifies the decimal value of the character used in the 
remote access escape code for entering online command mode 
on this modem from the remote site.  Default = 126(~)."
::= { mdmLiEntry 15 }

mdmLiRemAccessLimit OBJECT-TYPE
SYNTAX INTEGER (0..255)
ACCESS read-write
STATUS mandatory
DESCRIPTION
"Determines the number of attempts to enter remote online 
command mode that are allowed for any one connection.  The 
default is 0 which disables the remote access functon."
::= { mdmLiEntry 16 }

mdmLiRemPassword0 OBJECT-TYPE
SYNTAX DisplayString (SIZE(0..8))
ACCESS read-write
STATUS mandatory
DESCRIPTION
"The password that allows a dial-in user to gain view only 
access to this modems parameters.  A maximum of 8 
characters is allowed."
::= { mdmLiEntry 17 }

mdmLiRemPassword1 OBJECT-TYPE
SYNTAX DisplayString (SIZE(0..8))
ACCESS read-write
STATUS mandatory
DESCRIPTION
"The password used by a dial-in user to gain read-write 
access to this modems configuration.  Maximum length is 8 
characters."
::= { mdmLiEntry 18 }

mdmLiTransmitLevel OBJECT-TYPE
SYNTAX INTEGER (0..20)
ACCESS read-write
STATUS mandatory
DESCRIPTION
"Specifies the signal level of the modem transmitter in 
negative db."
::= { mdmLiEntry 19 }

mdmLiSrc OBJECT-TYPE
SYNTAX INTEGER{
  nic(1),
  t1Tdm(2),
  priTdm(3)
}
ACCESS read-write
STATUS optional
DESCRIPTION
"Specifies either NIC or TDM as the source for the line 
interface."
::= { mdmLiEntry 20 }

-- The modem Data Compression group

mdmDc OBJECT IDENTIFIER ::= { mdm 3 }

mdmDcTable OBJECT-TYPE
SYNTAX SEQUENCE OF MdmDcEntry
ACCESS not-accessible
STATUS mandatory
DESCRIPTION
"A table of configurable objects that define the operation 
of Data Compression in the modem."
::= { mdmDc 1 }

mdmDcEntry OBJECT-TYPE
SYNTAX MdmDcEntry
ACCESS not-accessible
STATUS mandatory
DESCRIPTION
"Objects which define Data Compression operation for a 
modem."
INDEX { mdmDcIndex }
::= { mdmDcTable 1 }

MdmDcEntry ::=
SEQUENCE {
mdmDcIndex
    INTEGER,
mdmDcDataCompression
    INTEGER
}

mdmDcIndex OBJECT-TYPE
SYNTAX INTEGER
ACCESS read-only
STATUS mandatory
DESCRIPTION
"The index into the Data Compression table.  This object 
contains the unique value for this modem as defined in the 
chassis mib entity relation table."
::= { mdmDcEntry 1 }

mdmDcDataCompression OBJECT-TYPE
SYNTAX INTEGER{
  none(1),
  autoEnable(2),
  enable(3),
  mnpWoCompression(4)
}
ACCESS read-write
STATUS mandatory
DESCRIPTION
"Determines when and how data compression is enabled.   
Corresponds to the &K register in USR modems."
::= { mdmDcEntry 2 }

-- The modem Test Function Group

mdmTf OBJECT IDENTIFIER ::= { mdm 4 }

mdmTfTable OBJECT-TYPE
SYNTAX SEQUENCE OF MdmTfEntry
ACCESS not-accessible
STATUS mandatory
DESCRIPTION
"Table of test functions for modems.  There is a table entry 
for each modem the quantity of which is specified by 
modemNumber."
::= { mdmTf 1 }

mdmTfEntry OBJECT-TYPE
SYNTAX MdmTfEntry
ACCESS not-accessible
STATUS mandatory
DESCRIPTION
"Objects used to request thet the modem perform certain 
diagnostic tests."
INDEX { mdmTfIndex }
::= { mdmTfTable 1 }

MdmTfEntry ::=
SEQUENCE {
mdmTfIndex
    INTEGER,
mdmTfTest
    INTEGER,
mdmTfTestTime
    INTEGER,
mdmTfV54
    INTEGER,
mdmTfV54Errors
    INTEGER,
mdmTfATG
    OCTET STRING,
mdmTfDialInToneTest
    INTEGER,
mdmTfToneTestCallRef
    OCTET STRING
}

mdmTfIndex OBJECT-TYPE
SYNTAX INTEGER
ACCESS read-only
STATUS mandatory
DESCRIPTION
"A unique value used to identify this modem the value of 
which is determined by the entity table in the chassis mib 
and used as a method to index into the test function table."
::= { mdmTfEntry 1 }

mdmTfTest OBJECT-TYPE
SYNTAX INTEGER (0..255)
ACCESS read-write
STATUS mandatory
DESCRIPTION
"Equates to modem's S16 register."
::= { mdmTfEntry 2 }

mdmTfTestTime OBJECT-TYPE
SYNTAX INTEGER (0..255)
ACCESS read-write
STATUS mandatory
DESCRIPTION
"Duration in seconds that the tests specified by 
mdmTfTestControl are to execute.  Default=0(indefinate)."
::= { mdmTfEntry 3 }

mdmTfV54 OBJECT-TYPE
SYNTAX INTEGER (0..255)
ACCESS read-write
STATUS mandatory
DESCRIPTION
"Corresponds to modem's &T register and provides tests 
specified by V.54.  Default=normal."
::= { mdmTfEntry 4 }

mdmTfV54Errors OBJECT-TYPE
SYNTAX INTEGER
ACCESS read-only
STATUS mandatory
DESCRIPTION
"The number of errors occurring during the last V54 loopback 
test."
::= { mdmTfEntry 5 }

mdmTfATG OBJECT-TYPE
SYNTAX OCTET STRING (SIZE(0..32))
ACCESS read-only
STATUS mandatory
DESCRIPTION
"ATG data from the modem"
::= { mdmTfEntry 6 }

mdmTfDialInToneTest OBJECT-TYPE
SYNTAX INTEGER{
  disable(1),
  enable(2)
}
ACCESS read-write
STATUS mandatory
DESCRIPTION
"This object is used to enable Dial in Tone Tests."
::= { mdmTfEntry 7 }

mdmTfToneTestCallRef OBJECT-TYPE
SYNTAX OCTET STRING (SIZE(0..53))
ACCESS read-only
STATUS mandatory
DESCRIPTION
"This object is used to send the call reference info with 
the tone test."

::= { mdmTfEntry 8 }

mdmTfToneTable OBJECT-TYPE
SYNTAX SEQUENCE OF MdmTfToneEntry
ACCESS not-accessible
STATUS optional
DESCRIPTION
"Table for modem tone tests"
::= { mdmTf 2 }

mdmTfToneEntry OBJECT-TYPE
SYNTAX MdmTfToneEntry
ACCESS not-accessible
STATUS optional
DESCRIPTION
"Objects for modem tone tests"
INDEX { mdmTfToneIndex }
::= { mdmTfToneTable 1 }

MdmTfToneEntry ::=
SEQUENCE {
mdmTfToneIndex
    INTEGER,
mdmTfTxFreq
    INTEGER,
mdmTfTxAmpl
    INTEGER,
mdmTfRxFreq
    INTEGER,
mdmTfRxAmpl
    INTEGER
}

mdmTfToneIndex OBJECT-TYPE
SYNTAX INTEGER
ACCESS read-only
STATUS optional
DESCRIPTION
"A value used to ID this modem"
::= { mdmTfToneEntry 1 }

mdmTfTxFreq OBJECT-TYPE
SYNTAX INTEGER (300..4000)
ACCESS read-write
STATUS optional
DESCRIPTION
"Modem tone test TX frequency"
::= { mdmTfToneEntry 2 }

mdmTfTxAmpl OBJECT-TYPE
SYNTAX INTEGER (-40..0)
ACCESS read-write
STATUS optional
DESCRIPTION
"Modem tone test TX amplitude"
::= { mdmTfToneEntry 3 }

mdmTfRxFreq OBJECT-TYPE
SYNTAX INTEGER (0..5000)
ACCESS read-only
STATUS optional
DESCRIPTION
"Modem tone test RX frequency"
::= { mdmTfToneEntry 4 }

mdmTfRxAmpl OBJECT-TYPE
SYNTAX INTEGER
ACCESS read-only
STATUS optional
DESCRIPTION
"Modem tone test RX amplitude"
::= { mdmTfToneEntry 5 }

mdmTfRspndrTable OBJECT-TYPE
SYNTAX SEQUENCE OF MdmTfRspndrEntry
ACCESS not-accessible
STATUS optional
DESCRIPTION
"Table for 105/102 responder test results."
::= { mdmTf 3 }

mdmTfRspndrEntry OBJECT-TYPE
SYNTAX MdmTfRspndrEntry
ACCESS not-accessible
STATUS optional
DESCRIPTION
"Objects containing the 105/102 responder test result dB 
levels and test status values."
INDEX { mdmTfRspndrIndex }
::= { mdmTfRspndrTable 1 }

MdmTfRspndrEntry ::=
SEQUENCE {
mdmTfRspndrIndex
    INTEGER,
mdmTf404FarNearLvl
    INTEGER,
mdmTf404NearFarLvl
    INTEGER,
mdmTf1004FarNearLvl
    INTEGER,
mdmTf1004NearFarLvl
    INTEGER,
mdmTf2804FarNearLvl
    INTEGER,
mdmTf2804NearFarLvl
    INTEGER,
mdmTfCmsgFarNearLvl
    INTEGER,
mdmTfCmsgNearFarLvl
    INTEGER,
mdmTfCnotchFarNearLvl
    INTEGER,
mdmTfCnotchNearFarLvl
    INTEGER,
mdmtTfSigNoiseFarNearLvl
    INTEGER,
mdmtTfSigNoiseNearFarLvl
    INTEGER,
mdmTf404FarNearSts
    INTEGER,
mdmTf404NearFarSts
    INTEGER,
mdmTf1004FarNearSts
    INTEGER,
mdmTf1004NearFarSts
    INTEGER,
mdmTf2804FarNearSts
    INTEGER,
mdmTf2804NearFarSts
    INTEGER,
mdmTfCmsgFarNearSts
    INTEGER,
mdmTfCmsgNearFarSts
    INTEGER,
mdmTfCnotchFarNearSts
    INTEGER,
mdmTfCnotchNearFarSts
    INTEGER,
mdmTfSigNoiseFarNearSts
    INTEGER,
mdmTfSigNoiseNearFarSts
    INTEGER,
mdmTf0dB1004FarNearLvl
    INTEGER,
mdmTf0dB1004NearFarLvl
    INTEGER,
mdmTf0dB1004FarNearSts
    INTEGER,
mdmTf0dB1004NearFarSts
    INTEGER
}

mdmTfRspndrIndex OBJECT-TYPE
SYNTAX INTEGER
ACCESS read-only
STATUS optional
DESCRIPTION
"A value used to ID this modem."
::= { mdmTfRspndrEntry 1 }

mdmTf404FarNearLvl OBJECT-TYPE
SYNTAX INTEGER
ACCESS read-only
STATUS optional
DESCRIPTION
"404 Hz tone at -16 dB loss test level. Far to near. Level 
in 0.1 dB resolution."
::= { mdmTfRspndrEntry 2 }

mdmTf404NearFarLvl OBJECT-TYPE
SYNTAX INTEGER
ACCESS read-only
STATUS optional
DESCRIPTION
"404 Hz tone at -16 dB loss test level. Near to far. Level 
in 0.1 dB resolution."
::= { mdmTfRspndrEntry 3 }

mdmTf1004FarNearLvl OBJECT-TYPE
SYNTAX INTEGER
ACCESS read-only
STATUS optional
DESCRIPTION
"1004 Hz tone at -16 dB loss test level. Far to near. Level 
in 0.1 dB resolution."
::= { mdmTfRspndrEntry 4 }

mdmTf1004NearFarLvl OBJECT-TYPE
SYNTAX INTEGER
ACCESS read-only
STATUS optional
DESCRIPTION
"1004 Hz tone at -16 dB loss test level. Near to far. Level 
in 0.1 dB resolution."
::= { mdmTfRspndrEntry 5 }

mdmTf2804FarNearLvl OBJECT-TYPE
SYNTAX INTEGER
ACCESS read-only
STATUS optional
DESCRIPTION
"2804 Hz tone at -16 dB loss test level. Far to near. Level 
in 0.1 dB resolution."
::= { mdmTfRspndrEntry 6 }

mdmTf2804NearFarLvl OBJECT-TYPE
SYNTAX INTEGER
ACCESS read-only
STATUS optional
DESCRIPTION
"2804 Hz tone at -16 dB loss test level. Near to far. Level 
in 0.1 dB resolution."
::= { mdmTfRspndrEntry 7 }

mdmTfCmsgFarNearLvl OBJECT-TYPE
SYNTAX INTEGER
ACCESS read-only
STATUS optional
DESCRIPTION
"C-message test level. Far to near. Level in 0.1 dB 
resolution."
::= { mdmTfRspndrEntry 8 }

mdmTfCmsgNearFarLvl OBJECT-TYPE
SYNTAX INTEGER
ACCESS read-only
STATUS optional
DESCRIPTION
"C-message test level. Near to far. Level in 0.1 dB 
resolution."
::= { mdmTfRspndrEntry 9 }

mdmTfCnotchFarNearLvl OBJECT-TYPE
SYNTAX INTEGER
ACCESS read-only
STATUS optional
DESCRIPTION
"C-notch test level. Far to near. Level in 0.1 dB 
resolution."
::= { mdmTfRspndrEntry 10 }

mdmTfCnotchNearFarLvl OBJECT-TYPE
SYNTAX INTEGER
ACCESS read-only
STATUS optional
DESCRIPTION
"C-notch test level. Near to far. Level in 0.1 dB 
resolution."
::= { mdmTfRspndrEntry 11 }

mdmtTfSigNoiseFarNearLvl OBJECT-TYPE
SYNTAX INTEGER
ACCESS read-only
STATUS optional
DESCRIPTION
"Signal to noise ratio level. Far to near. Level in 0.1 dB 
resolution."
::= { mdmTfRspndrEntry 12 }

mdmtTfSigNoiseNearFarLvl OBJECT-TYPE
SYNTAX INTEGER
ACCESS read-only
STATUS optional
DESCRIPTION
"Signal to noise ratio level. Near to far. Level in 0.1 dB 
resolution."
::= { mdmTfRspndrEntry 13 }

mdmTf404FarNearSts OBJECT-TYPE
SYNTAX INTEGER{
  noTest(1),
  success(2),
  noResponder(3),
  unsupported(4),
  timeOut(5),
  noToneDetected(6)
}
ACCESS read-only
STATUS optional
DESCRIPTION
"404 Hz tone at -16 dB loss test status. Far to near. 

Default=noTest(1)."
::= { mdmTfRspndrEntry 14 }

mdmTf404NearFarSts OBJECT-TYPE
SYNTAX INTEGER{
  noTest(1),
  success(2),
  noResponder(3),
  unsupported(4),
  timeOut(5),
  noToneDetected(6)
}
ACCESS read-only
STATUS optional
DESCRIPTION
"404 Hz tone at -16 db loss test status. Near to far. 

Default=noTest(1)."
::= { mdmTfRspndrEntry 15 }

mdmTf1004FarNearSts OBJECT-TYPE
SYNTAX INTEGER{
  noTest(1),
  success(2),
  noResponder(3),
  unsupported(4),
  timeOut(5),
  noToneDetected(6)
}
ACCESS read-only
STATUS optional
DESCRIPTION
"1004 Hz tone at -16 dB loss test status. Far to near. 

Default=noTest(1)."
::= { mdmTfRspndrEntry 16 }

mdmTf1004NearFarSts OBJECT-TYPE
SYNTAX INTEGER{
  noTest(1),
  success(2),
  noResponder(3),
  unsupported(4),
  timeOut(5),
  noToneDetected(6)
}
ACCESS read-only
STATUS optional
DESCRIPTION
"1004 Hz tone at -16 dB loss test status. Near to far. 

Default=noTest(1)."
::= { mdmTfRspndrEntry 17 }

mdmTf2804FarNearSts OBJECT-TYPE
SYNTAX INTEGER{
  noTest(1),
  success(2),
  noResponder(3),
  unsupported(4),
  timeOut(5),
  noToneDetected(6)
}
ACCESS read-only
STATUS optional
DESCRIPTION
"2804 Hz tone at -16 dB loss test status. Far to near. 

Default=noTest(1)."
::= { mdmTfRspndrEntry 18 }

mdmTf2804NearFarSts OBJECT-TYPE
SYNTAX INTEGER{
  noTest(1),
  success(2),
  noResponder(3),
  unsupported(4),
  timeOut(5),
  noToneDetected(6)
}
ACCESS read-only
STATUS optional
DESCRIPTION
"2804 Hz tone at -16 dB loss test status. Near to far. 

Default=noTest(1)."
::= { mdmTfRspndrEntry 19 }

mdmTfCmsgFarNearSts OBJECT-TYPE
SYNTAX INTEGER{
  noTest(1),
  success(2),
  noResponder(3),
  unsupported(4),
  timeOut(5),
  noToneDetected(6)
}
ACCESS read-only
STATUS optional
DESCRIPTION
"C-message test status. Far to near. 
Default=noTest(1)."
::= { mdmTfRspndrEntry 20 }

mdmTfCmsgNearFarSts OBJECT-TYPE
SYNTAX INTEGER{
  noTest(1),
  success(2),
  noResponder(3),
  unsupported(4),
  timeOut(5),
  noToneDetected(6)
}
ACCESS read-only
STATUS optional
DESCRIPTION
"C-message test status. Near to far. 
Default=noTest(1)."
::= { mdmTfRspndrEntry 21 }

mdmTfCnotchFarNearSts OBJECT-TYPE
SYNTAX INTEGER{
  noTest(1),
  success(2),
  noResponder(3),
  unsupported(4),
  timeOut(5),
  noToneDetected(6)
}
ACCESS read-only
STATUS optional
DESCRIPTION
"C-notch test status. Far to near. 
Default=noTest(1)."
::= { mdmTfRspndrEntry 22 }

mdmTfCnotchNearFarSts OBJECT-TYPE
SYNTAX INTEGER{
  noTest(1),
  success(2),
  noResponder(3),
  unsupported(4),
  timeOut(5),
  noToneDetected(6)
}
ACCESS read-only
STATUS optional
DESCRIPTION
"C-notch test status. Near to far. 
Default=noTest(1)."
::= { mdmTfRspndrEntry 23 }

mdmTfSigNoiseFarNearSts OBJECT-TYPE
SYNTAX INTEGER{
  noTest(1),
  success(2),
  noResponder(3),
  unsupported(4),
  timeOut(5),
  noToneDetected(6)
}
ACCESS read-only
STATUS optional
DESCRIPTION
"Signal to noise ratio status. Far to near. 

Default=noTest(1)."
::= { mdmTfRspndrEntry 24 }

mdmTfSigNoiseNearFarSts OBJECT-TYPE
SYNTAX INTEGER{
  noTest(1),
  success(2),
  noResponder(3),
  unsupported(4),
  timeOut(5),
  noToneDetected(6)
}
ACCESS read-only
STATUS optional
DESCRIPTION
"Signal to noise ratio status. Near to far. 

Default=noTest(1)."
::= { mdmTfRspndrEntry 25 }

mdmTf0dB1004FarNearLvl OBJECT-TYPE
SYNTAX INTEGER
ACCESS read-only
STATUS optional
DESCRIPTION
"1004 Hz tone at 0 db loss test level. Far to near. Level in 
0.1 dB resolution." 
::= { mdmTfRspndrEntry 26 }

mdmTf0dB1004NearFarLvl OBJECT-TYPE
SYNTAX INTEGER
ACCESS read-only
STATUS optional
DESCRIPTION
"1004 Hz tone at 0 db loss test level. Near to far. Level in 
0.1 dB resolution." 
::= { mdmTfRspndrEntry 27 }

mdmTf0dB1004FarNearSts OBJECT-TYPE
SYNTAX INTEGER{
  noTest(1),
  success(2),
  noResponder(3),
  unsupported(4),
  timeOut(5),
  noToneDetected(6)
}
ACCESS read-only
STATUS optional
DESCRIPTION
"1004 Hz tone at 0 db loss test status. Far to 
near.
Default=noTest(1)." 
::= { mdmTfRspndrEntry 28 }

mdmTf0dB1004NearFarSts OBJECT-TYPE
SYNTAX INTEGER{
  noTest(1),
  success(2),
  noResponder(3),
  unsupported(4),
  timeOut(5),
  noToneDetected(6)
}
ACCESS read-only
STATUS optional
DESCRIPTION
"1004 Hz tone at 0 db loss test status. Near to 
Far.
Default=noTest(1)." 
::= { mdmTfRspndrEntry 29 }

-- The modem DTE Interface group

mdmDi OBJECT IDENTIFIER ::= { mdm 5 }

mdmDiTable OBJECT-TYPE
SYNTAX SEQUENCE OF MdmDiEntry
ACCESS not-accessible
STATUS mandatory
DESCRIPTION
"Table of DTE interface objects.  The number of table 
entries is specified by modemNumber."
::= { mdmDi 1 }

mdmDiEntry OBJECT-TYPE
SYNTAX MdmDiEntry
ACCESS not-accessible
STATUS mandatory
DESCRIPTION
"Objects that define the DTE interface for a modem."
INDEX { mdmDiIndex }
::= { mdmDiTable 1 }

MdmDiEntry ::=
SEQUENCE {
mdmDiIndex
    INTEGER,
mdmDiEscCodeGuardTime
    INTEGER,
mdmDiLocalEscChar
    INTEGER,
mdmDiCarriageRetChar
    INTEGER,
mdmDiLineFeedChar
    INTEGER,
mdmDiBackspaceChar
    INTEGER,
mdmDiDelAsBackspace
    INTEGER,
mdmDiResetOnDtrEna
    INTEGER,
mdmDiResultCodePauseDis
    INTEGER,
mdmDiInterbridgeEna
    INTEGER,
mdmDiBreakLen
    INTEGER,
mdmDiXonChar
    INTEGER,
mdmDiXoffChar
    INTEGER,
mdmDiDsrPulseTime
    INTEGER,
mdmDiRtsCtsDelay
    INTEGER,
mdmDiHiSpeedResCodeEna
    INTEGER,
mdmDiCmdLocalEchoEna
    INTEGER,
mdmDiDataModeEchoEna
    INTEGER,
mdmDiDteDataRateMode
    INTEGER,
mdmDiCdOverride
    INTEGER,
mdmDiDtrOverride
    INTEGER,
mdmDiDsrOverride
    INTEGER,
mdmDiEiaLineStatus
    INTEGER,
mdmDiTransmitFlowCntl
    INTEGER,
mdmDiSoftwareRxFlowCntl
    INTEGER,
mdmDiHardwareRxFlowCntl
    INTEGER,
mdmDiBreakHandling
    INTEGER,
mdmDiDteNvramLock
    INTEGER,
mdmDiSerialFormat
    INTEGER,
mdmDiDefaultDteDataRate
    INTEGER,
mdmDiRemAccessMsg
    INTEGER,
mdmDiV25DteDataRate
    INTEGER,
mdmDiSrc
    INTEGER,
mdmDiSlot
    INTEGER,
mdmDiBusyClock
    INTEGER,
mdmDiAtString
    DisplayString,
mdmDiDtrRecognitionTime
    INTEGER
}

mdmDiIndex OBJECT-TYPE
SYNTAX INTEGER
ACCESS read-only
STATUS mandatory
DESCRIPTION
"The index for the DTE interface table contains the unique 
value associated with this modem as defined in the chassis 
mib entity table."
::= { mdmDiEntry 1 }

mdmDiEscCodeGuardTime OBJECT-TYPE
SYNTAX INTEGER (0..255)
ACCESS read-write
STATUS mandatory
DESCRIPTION
"Duration in 50ths of a second of idle time that must 
precede and follow the modem's command mode escape code.  
Default=50."
::= { mdmDiEntry 2 }

mdmDiLocalEscChar OBJECT-TYPE
SYNTAX INTEGER (0..255)
ACCESS read-write
STATUS mandatory
DESCRIPTION
"Decimal equivalent of the character that is used to escape 
to on-line command mode.  Values between 128 and 255 
disable the escape code.  Default=43(+)."
::= { mdmDiEntry 3 }

mdmDiCarriageRetChar OBJECT-TYPE
SYNTAX INTEGER (0..255)
ACCESS read-write
STATUS mandatory
DESCRIPTION
"Specifies the decimal equivalent of the carriage return 
character.  Default=13."
::= { mdmDiEntry 4 }

mdmDiLineFeedChar OBJECT-TYPE
SYNTAX INTEGER (0..255)
ACCESS read-write
STATUS mandatory
DESCRIPTION
"Specifies the decimal equivalent of the line feed 
character.  Default=10."
::= { mdmDiEntry 5 }

mdmDiBackspaceChar OBJECT-TYPE
SYNTAX INTEGER (0..255)
ACCESS read-write
STATUS mandatory
DESCRIPTION
"Specifies the decimal equivalent of the backspace 
character.  Default=8."
::= { mdmDiEntry 6 }

mdmDiDelAsBackspace OBJECT-TYPE
SYNTAX INTEGER{
  delete(1),
  backspace(2)
}
ACCESS read-write
STATUS mandatory
DESCRIPTION
"Defines functionality of the delete key.  Acts either to 
delete the character the cursor is currently on or acts the 
same as the backspace key.  Default=delete."
::= { mdmDiEntry 7 }

mdmDiResetOnDtrEna OBJECT-TYPE
SYNTAX INTEGER{
  disable(1),
  enable(2)
}
ACCESS read-write
STATUS mandatory
DESCRIPTION
"When enabled, this option will cause the modem to restart 
when the DTR control signal drops.  Default=disabled."
::= { mdmDiEntry 8 }

mdmDiResultCodePauseDis OBJECT-TYPE
SYNTAX INTEGER{
  enable(1),
  disable(2)
}
ACCESS read-write
STATUS mandatory
DESCRIPTION
"When enabled, the modem pauses 250ms before transmission of 
any result code.  Default=enable."
::= { mdmDiEntry 9 }

mdmDiInterbridgeEna OBJECT-TYPE
SYNTAX INTEGER{
  disable(1),
  enable(2)
}
ACCESS read-write
STATUS mandatory
DESCRIPTION
"When enabled, the modem operates in a mode that is 
compatible with an 'Appletalk InterBridge Network'.  
Default=disabled."
::= { mdmDiEntry 10 }

mdmDiBreakLen OBJECT-TYPE
SYNTAX INTEGER (0..255)
ACCESS read-write
STATUS mandatory
DESCRIPTION
"Defines the duration of break characters that are sent to 
the DTE in ARQ mode.  Defined in 10ms increments.  
Default=10(100ms)."
::= { mdmDiEntry 11 }

mdmDiXonChar OBJECT-TYPE
SYNTAX INTEGER (0..255)
ACCESS read-write
STATUS mandatory
DESCRIPTION
"Defines the decimal equivalent of the Xon character.  This 
character will be used when software flow control is 
enabled.  Default=17."
::= { mdmDiEntry 12 }

mdmDiXoffChar OBJECT-TYPE
SYNTAX INTEGER (0..255)
ACCESS read-write
STATUS mandatory
DESCRIPTION
"Defines the decimal equivalent of the xoff character.  This 
character will be used when software flow control is 
enabled.  Default=19."
::= { mdmDiEntry 13 }

mdmDiDsrPulseTime OBJECT-TYPE
SYNTAX INTEGER (0..150)
ACCESS read-write
STATUS mandatory
DESCRIPTION
"Duration in 20 millisecond increments that the DSR signal 
is pulsed when the modem is configured for pulsed DSR mode. 
 Default=150."
::= { mdmDiEntry 14 }

mdmDiRtsCtsDelay OBJECT-TYPE
SYNTAX INTEGER (0..255)
ACCESS read-write
STATUS mandatory
DESCRIPTION
"Duration in 10 millisecond increments that the modem delays 
setting CTS after detecting the presence of RTS.  
Default=1."
::= { mdmDiEntry 15 }

mdmDiHiSpeedResCodeEna OBJECT-TYPE
SYNTAX INTEGER{
  enable(1),
  disable(2)
}
ACCESS read-write
STATUS mandatory
DESCRIPTION
"Determines if connection establishment result codes above 
9600 are sent to the DTE.  Default=enable."
::= { mdmDiEntry 16 }

mdmDiCmdLocalEchoEna OBJECT-TYPE
SYNTAX INTEGER{
  disable(1),
  enable(2)
}
ACCESS read-write
STATUS mandatory
DESCRIPTION
"Defines whether or not the characters transmitted by the 
DTE are echoed back when in command mode.  
Default=disabled."
::= { mdmDiEntry 17 }

mdmDiDataModeEchoEna OBJECT-TYPE
SYNTAX INTEGER{
  enable(1),
  disable(2)
}
ACCESS read-write
STATUS mandatory
DESCRIPTION
"Defines whether or not the DTE's transmitted data is echoed 
back durring a connection(half duplex).  Default=disabled."
::= { mdmDiEntry 18 }

mdmDiDteDataRateMode OBJECT-TYPE
SYNTAX INTEGER{
  followsLinkRate(1),
  fixed(2),
  arqFixedNonArqFollows(3)
}
ACCESS read-write
STATUS mandatory
DESCRIPTION
"Defines how the modem determines the DTE data rate.  When 
set to the default, follows link rate, the modem switches 
the DTE speed to match the link rate.  When set to fixed, 
the DTE speed remains at the default DTE data rate or the 
rate of the last AT command.  When set to ARQ fixed-Non ARQ 
follows the dte speed remains fixed for ARQ calls and 
follows the link rate for non ARQ calls."
::= { mdmDiEntry 19 }

mdmDiCdOverride OBJECT-TYPE
SYNTAX INTEGER{
  enable(1),
  disable(2)
}
ACCESS read-write
STATUS mandatory
DESCRIPTION
"Defines the operation of the CD(Carrier Detect) signal.  
When overridden the CD signal is always asserted.  
Default=normal."
::= { mdmDiEntry 20 }

mdmDiDtrOverride OBJECT-TYPE
SYNTAX INTEGER{
  enable(1),
  disable(2)
}
ACCESS read-write
STATUS mandatory
DESCRIPTION
"Defines operation with regard to DTR.  When overridden the 
DTR signal is always assumed to be present.  
Default=normal."
::= { mdmDiEntry 21 }

mdmDiDsrOverride OBJECT-TYPE
SYNTAX INTEGER{
  dsrOveridden(1),
  modemControled(2),
  pulsedCtsFollowsCd(3),
  pulsed(4),
  dsrEqualsCd(5),
  normalCtsFollowsCd(6)
}
ACCESS read-write
STATUS mandatory
DESCRIPTION
"Determines the functionality of the modem's DSR signal.  
Default=Override."
::= { mdmDiEntry 22 }

mdmDiEiaLineStatus OBJECT-TYPE
SYNTAX INTEGER (0..255)
ACCESS read-only
STATUS mandatory
DESCRIPTION
"Provides a mechanism for the console to determine the 
current state of the DTE's EIA signals."
::= { mdmDiEntry 23 }

mdmDiTransmitFlowCntl OBJECT-TYPE
SYNTAX INTEGER{
  none(1),
  hardware(2),
  software(3),
  hardwareAndSoftware(4)
}
ACCESS read-write
STATUS mandatory
DESCRIPTION
"Determines if transmit flow control is enabled and if so 
whether it is hardware or software.  Default=none."
::= { mdmDiEntry 24 }

mdmDiSoftwareRxFlowCntl OBJECT-TYPE
SYNTAX INTEGER{
  none(1),
  xonXoffLocalRemote(2),
  xonXoffLocal(3),
  hpHostMode(4),
  hpTerminalMode(5),
  localIncommingXonXoff(6)
}
ACCESS read-write
STATUS mandatory
DESCRIPTION
"Determines if receive software flow control is enabled as 
well as what type.  Default=none."
::= { mdmDiEntry 25 }

mdmDiHardwareRxFlowCntl OBJECT-TYPE
SYNTAX INTEGER{
  rtsCtsDelayed(1),
  rtsIgnored(2),
  dataOnRtsHigh(3)
}
ACCESS read-write
STATUS mandatory
DESCRIPTION
"Determines if receive hardware flow control is enabled as 
well as how it is implemented.  Default=RTS ignored."
::= { mdmDiEntry 26 }

mdmDiBreakHandling OBJECT-TYPE
SYNTAX INTEGER{
  destructiveNotSent(1),
  destructiveExpedited(2),
  nondestructiveExpedited(3),
  nondestructiveNotSent(4)
}
ACCESS read-write
STATUS mandatory
DESCRIPTION
"Defines the method used to handle received breaks.  When 
defined as destructive the modem's transmit data buffer is 
flushed.  When defined as expidited, the break preceeds any 
pending data in the transmit buffer. 
Default=Destructive,Expidited."
::= { mdmDiEntry 27 }

mdmDiDteNvramLock OBJECT-TYPE
SYNTAX INTEGER{
  disable(1),
  enable(2)
}
ACCESS read-write
STATUS mandatory
DESCRIPTION
"When locked, prohibits the DTE user from changing any of 
the NVRAM settings in the modem.  Default=unlocked."
::= { mdmDiEntry 28 }

mdmDiSerialFormat OBJECT-TYPE
SYNTAX INTEGER{
  bit8NoParity(1),
  bit7EvenParity(2),
  bit7OddParity(3),
  bit7MarkParity(4)
}
ACCESS read-write
STATUS mandatory
DESCRIPTION
"Defines the data bits and parity of the modem's DTE.  Used 
in situations where the attached DTE is unable to send AT 
commands to initialize the DTE format.  Default=8 bit no 
parity."
::= { mdmDiEntry 29 }

mdmDiDefaultDteDataRate OBJECT-TYPE
SYNTAX INTEGER{
  bps110(1),
  bps300(2),
  bps600(3),
  bps1200(4),
  bps2400(5),
  bps4800(6),
  bps9600(8),
  bps19K(12),
  bps38K(13),
  unknown(16),
  bps57K(17),
  bps115K(22)
}
ACCESS read-write
STATUS mandatory
DESCRIPTION
"Defines the data rate of the DTE.  Useful in those cases 
where the DTE is incapable of sending an AT command to 
initialize the data rate and a fixed data rate is required. 
 Default=9600."
::= { mdmDiEntry 30 }

mdmDiRemAccessMsg OBJECT-TYPE
SYNTAX INTEGER{
  enable(1),
  disable(2)
}
ACCESS read-write
STATUS mandatory
DESCRIPTION
"Specifies if the modem is to send the 'Modem Unavailable' 
message to the DTE when the DTE attempts to send data to a 
modem that is curently in command mode with a remote DTE.  
Default = enabled."
::= { mdmDiEntry 31 }

mdmDiV25DteDataRate OBJECT-TYPE
SYNTAX INTEGER{
  bps1200(1),
  bps2400(2),
  bps4800(3),
  bps7200(4),
  bps9600(5),
  bps12K(6),
  bps14K(7),
  bps16K(8),
  bps19K(9),
  bps21K(10),
  bps24K(11),
  bps26K(12),
  bps28K(13)
}
ACCESS read-write
STATUS optional
DESCRIPTION
"Defines the DTE Data Rates supported for V25 bis."
::= { mdmDiEntry 32 }

mdmDiSrc OBJECT-TYPE
SYNTAX INTEGER{
  nic(1),
  packetBus(2)
}
ACCESS read-write
STATUS optional
DESCRIPTION
"Specifies either NIC or Packet Bus as the source for the 
DTE interface."
::= { mdmDiEntry 33 }

mdmDiSlot OBJECT-TYPE
SYNTAX INTEGER (1..16)
ACCESS read-write
STATUS optional
DESCRIPTION
"Specifies the slot address as the DTE interface  source 
when mdmdiSrc is configured for Packet Bus."
::= { mdmDiEntry 34 }

mdmDiBusyClock OBJECT-TYPE
SYNTAX INTEGER{
  extClock1(1),
  busyOut(2)
}
ACCESS read-write
STATUS optional
DESCRIPTION
"specifies whether the modem will support either the current 
transmit clock or a new busy out."
::= { mdmDiEntry 35 }

mdmDiAtString OBJECT-TYPE
SYNTAX DisplayString (SIZE(0..41))
ACCESS read-write
STATUS mandatory
DESCRIPTION
"Provides an interface for issuing an AT command to the 
modem. Not implemented as a command so as to allow the 
object to be saved to NVRAM and subsequently configured 
during power-up."

::= { mdmDiEntry 36 }

mdmDiDtrRecognitionTime OBJECT-TYPE
SYNTAX INTEGER (0..255)
ACCESS read-write
STATUS mandatory
DESCRIPTION
"S25 register tells the modem how quickly to react when DTR 
transitions from off to on. Default is 20. Increments are 
in 10 ms."
::= { mdmDiEntry 37 }

-- The modem Signal Converter group

mdmSc OBJECT IDENTIFIER ::= { mdm 6 }

mdmScTable OBJECT-TYPE
SYNTAX SEQUENCE OF MdmScEntry
ACCESS not-accessible
STATUS mandatory
DESCRIPTION
"Table of configurable objects which determine the operation 
of the Signal Converter.  The quantity of entries in this 
table is defined by modemNumber."
::= { mdmSc 1 }

mdmScEntry OBJECT-TYPE
SYNTAX MdmScEntry
ACCESS not-accessible
STATUS mandatory
DESCRIPTION
"Objects that define the operation of the modem's Signal 
Converter."
INDEX { mdmScIndex }
::= { mdmScTable 1 }

MdmScEntry ::=
SEQUENCE {
mdmScIndex
    INTEGER,
mdmScLinkRateSelect
    INTEGER,
mdmScNonArqBufSize
    INTEGER,
mdmScNonMnpDataCapture
    INTEGER,
mdmScSyncTimingSource
    INTEGER,
mdmScHstMod
    INTEGER,
mdmScHiFreqEq
    INTEGER,
mdmScBackChanRate
    INTEGER,
mdmScV21Mod
    INTEGER,
mdmScV32UnencodedMod
    INTEGER,
mdmScV32Mod
    INTEGER,
mdmScBell208
    INTEGER,
mdmScV32Bis
    INTEGER,
mdmScV32BisEnhance
    INTEGER,
mdmScV32QuickRetrain
    INTEGER,
mdmScV23
    INTEGER,
mdmScHiSpeedModulation
    INTEGER,
mdmScFallback
    INTEGER,
mdmScV32TerboModeEnable
    INTEGER,
mdmScV34ModeEnable
    INTEGER,
mdmScVFCSymRate2400
    INTEGER,
mdmScVFCSymRate2743
    INTEGER,
mdmScVFCSymRate2800
    INTEGER,
mdmScVFCSymRate3000
    INTEGER,
mdmScVFCSymRate3200
    INTEGER,
mdmScVFCSymRate3429
    INTEGER,
mdmScVFC8S2DMapping
    INTEGER,
mdmScVFC16S4DMapping
    INTEGER,
mdmScVFC32S2DMapping
    INTEGER,
mdmScVFC64S4DMapping
    INTEGER,
mdmScVFCNonLinearCoding
    INTEGER,
mdmScVFCTxLevelDeviation
    INTEGER,
mdmScVFCPreEmphasis
    INTEGER,
mdmScVFCPreCoding
    INTEGER,
mdmScVFCShaping
    INTEGER,
mdmScVFCModeEnable
    INTEGER,
mdmScV8
    INTEGER,
mdmSCV8CallIndicator
    INTEGER,
mdmScV34pModeEnable
    INTEGER,
mdmSc300
    INTEGER,
mdmSc1200
    INTEGER,
mdmSc2400
    INTEGER,
mdmScHighSpeed
    INTEGER,
mdmScSelectiveReject
    INTEGER,
mdmScPhExclusionDel
    INTEGER,
mdmScLinkRateAmpU
    INTEGER,
mdmScLowerSpeedMin
    INTEGER,
mdmScLowerSpeedMax
    INTEGER,
mdmScX2Client
    INTEGER,
mdmScX2Server
    INTEGER,
mdmScX2Symmetric
    INTEGER,
mdmScX2HighPowerConst
    INTEGER,
mdmScPiafs
    INTEGER,
mdmScPiafsV42bis
    INTEGER,
mdmScTxPwrLvl
    INTEGER,
mdmScTxPwrLvlApplied
    INTEGER,
mdmScX2Version2
    INTEGER,
mdmScV34Fallback
    INTEGER,
mdmScV90Analogue
    INTEGER,
mdmScV90Digital
    INTEGER,
mdmScV90AllDigital
    INTEGER
}

mdmScIndex OBJECT-TYPE
SYNTAX INTEGER
ACCESS read-only
STATUS mandatory
DESCRIPTION
"The unique value found in the chassis mib entity relation 
table that references this modem."
::= { mdmScEntry 1 }

mdmScLinkRateSelect OBJECT-TYPE
SYNTAX INTEGER{
  variable(1),
  bps300(2),
  bps1200(3),
  bps2400(4),
  bps4800(5),
  bps7200(6),
  bps9600(7),
  bps12000(8),
  bps14400(9),
  bps16800(10),
  bps19200(11),
  bps21600(12),
  bps24000(13),
  bps26400(14),
  bps28800(15),
  bps31200(16),
  bps33600(17),
  bps33333(18),
  bps37333(19),
  bps41333(20),
  bps42666(21),
  bps44000(22),
  bps45333(23),
  bps46666(24),
  bps48000(25),
  bps49333(26),
  bps50666(27),
  bps52000(28),
  bps53333(29),
  bps54666(30),
  bps56000(31),
  bps57333(32),
  bps64000(33),
  bps28000(34),
  bps29333(35),
  bps30666(36),
  bps32000(37),
  bps34666(38),
  bps36000(39),
  bps38666(40),
  bps40000(41),
  bps58666(42),
  bps60000(43),
  bps61333(44),
  bps62666(45)
}
ACCESS read-write
STATUS mandatory
DESCRIPTION
"Determines if the link will run at a fixed or variable data 
rate.  Default=variable."
::= { mdmScEntry 2 }

mdmScNonArqBufSize OBJECT-TYPE
SYNTAX INTEGER{
  bytes1500(1),
  bytes128(2)
}
ACCESS read-write
STATUS mandatory
DESCRIPTION
" Sets the sizer of the transmit buffer for non-ARQ mode 
operation to either 128 bytes or 1.5K.  The smaller size is 
for low speed interactive applications, the large size is 
for file transfer.  Default=128."
::= { mdmScEntry 3 }

mdmScNonMnpDataCapture OBJECT-TYPE
SYNTAX INTEGER{
  disable(1),
  enable(2)
}
ACCESS read-write
STATUS mandatory
DESCRIPTION
"Causes received characters to be buffered when the modem is 
attempting to negotiate an MNP call and the remote modem is 
not.  Default=disabled."
::= { mdmScEntry 4 }

mdmScSyncTimingSource OBJECT-TYPE
SYNTAX INTEGER{
  internal(1),
  external(2),
  rxLinkClock(3)
}
ACCESS read-write
STATUS mandatory
DESCRIPTION
"Specifies the clock source when operating in synchronous 
mode.  Default=internal."
::= { mdmScEntry 5 }

mdmScHstMod OBJECT-TYPE
SYNTAX INTEGER{
  enable(1),
  disable(2)
}
ACCESS read-write
STATUS mandatory
DESCRIPTION
"May be used to disable HST operation on USRobotics Dual 
Standard modems.  Default=enable."
::= { mdmScEntry 6 }

mdmScHiFreqEq OBJECT-TYPE
SYNTAX INTEGER{
  enable(1),
  disable(2)
}
ACCESS read-write
STATUS mandatory
DESCRIPTION
"Allows modem's high frequency equalization to be disabled 
if it causes problems on shorter lines.  Default=enabled."
::= { mdmScEntry 7 }

mdmScBackChanRate OBJECT-TYPE
SYNTAX INTEGER{
  bps450(1),
  bps300(2)
}
ACCESS read-write
STATUS mandatory
DESCRIPTION
"Specifies the lower speed used in the asymetrical (HST) 
mode of operation.  The 300 bps setting is provided for 
compatibility with early HST modems.  Default=450."
::= { mdmScEntry 8 }

mdmScV21Mod OBJECT-TYPE
SYNTAX INTEGER{
  disable(1),
  enable(2)
}
ACCESS read-write
STATUS mandatory
DESCRIPTION
"When enabled, the modem will answer both bell 103 and V.21 
calls but originates only V.21 calls.  Default=disabled."
::= { mdmScEntry 9 }

mdmScV32UnencodedMod OBJECT-TYPE
SYNTAX INTEGER{
  disable(1),
  enable(2)
}
ACCESS read-write
STATUS mandatory
DESCRIPTION
"Allows unencoded modulation in V.32 mode.  Although part of 
the CCITT V.32 recomendation it is rarely used.  
Default=disabled."
::= { mdmScEntry 10 }

mdmScV32Mod OBJECT-TYPE
SYNTAX INTEGER{
  enable(1),
  disable(2)
}
ACCESS read-write
STATUS mandatory
DESCRIPTION
"Allows V.32 modulation to be disabled on USRobotics Dual 
Standard modems.  Default=enabled."
::= { mdmScEntry 11 }

mdmScBell208 OBJECT-TYPE
SYNTAX INTEGER{
  disable(1),
  enable(2)
}
ACCESS read-write
STATUS mandatory
DESCRIPTION
"Allows modems that support Bell 208 modulation to include 
Bell 208 as part of the negotiation sequence.  Default=Bell 
208 disabled."
::= { mdmScEntry 12 }

mdmScV32Bis OBJECT-TYPE
SYNTAX INTEGER{
  enable(1),
  disable(2)
}
ACCESS read-write
STATUS mandatory
DESCRIPTION
"Allows V.32 bis modulation to be disabled.  On USRobotics 
Dual Standard modems this may be useful in troublshooting 
HST operation.  Default=V.32 bis enabled."
::= { mdmScEntry 13 }

mdmScV32BisEnhance OBJECT-TYPE
SYNTAX INTEGER{
  enable(1),
  disable(2)
}
ACCESS read-write
STATUS mandatory
DESCRIPTION
"Allows USRobotics V.32 Enahnced mode to be disabled for 
purposes of troubleshooting  Default=enabled."
::= { mdmScEntry 14 }

mdmScV32QuickRetrain OBJECT-TYPE
SYNTAX INTEGER{
  enable(1),
  disable(2)
}
ACCESS read-write
STATUS mandatory
DESCRIPTION
"Allows the faster retrains that occur with USR's enhanced 
V.32 mode to be disabled for troubleshooting purposes.  
Default=enabled."
::= { mdmScEntry 15 }

mdmScV23 OBJECT-TYPE
SYNTAX INTEGER{
  disable(1),
  enable(2)
}
ACCESS read-write
STATUS mandatory
DESCRIPTION
"Allows the modem to negotiate a V.23 connection(used in 
U.K.) after failing to negotiate a higher rate.  
Default=disabled."
::= { mdmScEntry 16 }

mdmScHiSpeedModulation OBJECT-TYPE
SYNTAX INTEGER{
  v32(1),
  hst(2),
  bell208(3)
}
ACCESS read-write
STATUS mandatory
DESCRIPTION
"Defines the handshaking options used in negotiation of high 
speed calls.  Default=CCITT V.32 "
::= { mdmScEntry 17 }

mdmScFallback OBJECT-TYPE
SYNTAX INTEGER{
  enable(1),
  disable(2)
}
ACCESS read-write
STATUS mandatory
DESCRIPTION
"Defines whether or not the modem will be allowed to change 
protocols 
it detects a significant change in the line 
characteristics.  If the modem is unable to maintain 
transmission with the current modulation technique it would 
fall back to a lower speed and if the line then improved it 
would upshift to a higher speed.   Default=enabled."
::= { mdmScEntry 18 }

mdmScV32TerboModeEnable OBJECT-TYPE
SYNTAX INTEGER{
  disable(1),
  enable(2)
}
ACCESS read-write
STATUS mandatory
DESCRIPTION
"Allows the V32 Terbo mode to be disabled/enabled."
::= { mdmScEntry 19 }

mdmScV34ModeEnable OBJECT-TYPE
SYNTAX INTEGER{
  disable(1),
  enable(2)
}
ACCESS read-write
STATUS mandatory
DESCRIPTION
"Allows V34 mode to be disabled/enabled."
::= { mdmScEntry 20 }

mdmScVFCSymRate2400 OBJECT-TYPE
SYNTAX INTEGER{
  enable(1),
  disable(2)
}
ACCESS read-write
STATUS mandatory
DESCRIPTION
"Allows the 2400 symbol rate to be disabled/enabled on V.FC 
modems."
::= { mdmScEntry 21 }

mdmScVFCSymRate2743 OBJECT-TYPE
SYNTAX INTEGER{
  enable(1),
  disable(2)
}
ACCESS read-write
STATUS mandatory
DESCRIPTION
"Allows the 2743 symbol rate to be disabled/enabled on V.FC 
modems."
::= { mdmScEntry 22 }

mdmScVFCSymRate2800 OBJECT-TYPE
SYNTAX INTEGER{
  enable(1),
  disable(2)
}
ACCESS read-write
STATUS mandatory
DESCRIPTION
"Allows the 2800 symbol rate to be disabled/enabled on V.FC 
modems."
::= { mdmScEntry 23 }

mdmScVFCSymRate3000 OBJECT-TYPE
SYNTAX INTEGER{
  enable(1),
  disable(2)
}
ACCESS read-write
STATUS mandatory
DESCRIPTION
"Allows the 3000 symbol rate to be disabled/enabled on V.FC 
modems."
::= { mdmScEntry 24 }

mdmScVFCSymRate3200 OBJECT-TYPE
SYNTAX INTEGER{
  enable(1),
  disable(2)
}
ACCESS read-write
STATUS mandatory
DESCRIPTION
"Allows the 3200 symbol rate to be disabled/enabled on V.FC 
modems."
::= { mdmScEntry 25 }

mdmScVFCSymRate3429 OBJECT-TYPE
SYNTAX INTEGER{
  enable(1),
  disable(2)
}
ACCESS read-write
STATUS mandatory
DESCRIPTION
"Allows the 3429 symbol rate to be disabled/enabled on V.FC 
modems."
::= { mdmScEntry 26 }

mdmScVFC8S2DMapping OBJECT-TYPE
SYNTAX INTEGER{
  enable(1),
  disable(2)
}
ACCESS read-write
STATUS mandatory
DESCRIPTION
"Allows the 8S-2D mapping to be disabled/enabled on V.FC 
modems."
::= { mdmScEntry 27 }

mdmScVFC16S4DMapping OBJECT-TYPE
SYNTAX INTEGER{
  enable(1),
  disable(2)
}
ACCESS read-write
STATUS mandatory
DESCRIPTION
"Allows the 16S-4D mapping to be disabled/enabled on V.FC 
modems."
::= { mdmScEntry 28 }

mdmScVFC32S2DMapping OBJECT-TYPE
SYNTAX INTEGER{
  enable(1),
  disable(2)
}
ACCESS read-write
STATUS mandatory
DESCRIPTION
"Allows the 32S-2D mapping to be disabled/enabled on V.FC 
modems."
::= { mdmScEntry 29 }

mdmScVFC64S4DMapping OBJECT-TYPE
SYNTAX INTEGER{
  enable(1),
  disable(2)
}
ACCESS read-write
STATUS mandatory
DESCRIPTION
"Allows the 64S-4D mapping to be disabled/enabled on V.FC 
modems."
::= { mdmScEntry 30 }

mdmScVFCNonLinearCoding OBJECT-TYPE
SYNTAX INTEGER{
  enable(1),
  disable(2)
}
ACCESS read-write
STATUS mandatory
DESCRIPTION
"Allows the non-linear coding to be disabled/enabled on V.FC 
modems."
::= { mdmScEntry 31 }

mdmScVFCTxLevelDeviation OBJECT-TYPE
SYNTAX INTEGER{
  enable(1),
  disable(2)
}
ACCESS read-write
STATUS mandatory
DESCRIPTION
"Allows the TX level deviation to be disabled/enabled on 
V.FC modems."
::= { mdmScEntry 32 }

mdmScVFCPreEmphasis OBJECT-TYPE
SYNTAX INTEGER{
  enable(1),
  disable(2)
}
ACCESS read-write
STATUS mandatory
DESCRIPTION
"Allows the pre-emphasis to be disabled/enabled on V.FC 
modems."
::= { mdmScEntry 33 }

mdmScVFCPreCoding OBJECT-TYPE
SYNTAX INTEGER{
  enable(1),
  disable(2)
}
ACCESS read-write
STATUS mandatory
DESCRIPTION
"Allows the precoding to be disabled/enabled on V.FC 
modems."
::= { mdmScEntry 34 }

mdmScVFCShaping OBJECT-TYPE
SYNTAX INTEGER{
  enable(1),
  disable(2)
}
ACCESS read-write
STATUS mandatory
DESCRIPTION
"Allows the shaping to be disabled/enabled on V.FC modems."
::= { mdmScEntry 35 }

mdmScVFCModeEnable OBJECT-TYPE
SYNTAX INTEGER{
  enable(1),
  disable(2)
}
ACCESS read-write
STATUS mandatory
DESCRIPTION
"Allows to disable/enable V.FC mode in order to troubleshoot 
a connection."
::= { mdmScEntry 36 }

mdmScV8 OBJECT-TYPE
SYNTAX INTEGER{
  enable(1),
  disable(2)
}
ACCESS read-write
STATUS mandatory
DESCRIPTION
"Allow V8 mode to be disabled/enabled"
::= { mdmScEntry 37 }

mdmSCV8CallIndicator OBJECT-TYPE
SYNTAX INTEGER{
  enable(1),
  disable(2)
}
ACCESS read-write
STATUS mandatory
DESCRIPTION
"Allow V.8. call indicater to be disabled/enabled."
::= { mdmScEntry 38 }

mdmScV34pModeEnable OBJECT-TYPE
SYNTAX INTEGER{
  enable(1),
  disable(2)
}
ACCESS read-write
STATUS mandatory
DESCRIPTION
"Allows V34 plus modulation mode to be disabled. 
(default=0/enabled)"
::= { mdmScEntry 39 }

mdmSc300 OBJECT-TYPE
SYNTAX INTEGER{
  disable(1),
  enable(2)
}
ACCESS read-write
STATUS mandatory
DESCRIPTION
"Restrict 300 baud negotiations. Register S48.0 Default is 
disable (0) restriction."
 
::= { mdmScEntry 40 }

mdmSc1200 OBJECT-TYPE
SYNTAX INTEGER{
  disable(1),
  enable(2)
}
ACCESS read-write
STATUS mandatory
DESCRIPTION
"Restrict 1200 baud negotiations. Register S48.1 Default is 
disable (0) restriction."
 
::= { mdmScEntry 41 }

mdmSc2400 OBJECT-TYPE
SYNTAX INTEGER{
  disable(1),
  enable(2)
}
ACCESS read-write
STATUS mandatory
DESCRIPTION
"Restrict 2400 baud negotiations. Register S48.2 Default is 
disable (0) restriction."
 
::= { mdmScEntry 42 }

mdmScHighSpeed OBJECT-TYPE
SYNTAX INTEGER{
  disable(1),
  enable(2)
}
ACCESS read-write
STATUS mandatory
DESCRIPTION
"Restrict highspeed baud negotiations. Register S48.3 
Default is disable (0) restriction."
 
::= { mdmScEntry 43 }

mdmScSelectiveReject OBJECT-TYPE
SYNTAX INTEGER{
  enable(1),
  disable(2)
}
ACCESS read-write
STATUS mandatory
DESCRIPTION
"Selective Reject register S51.6 is a function of the 
V.42/LAPM protocol. The default is enable (1)"
::= { mdmScEntry 44 }

mdmScPhExclusionDel OBJECT-TYPE
SYNTAX INTEGER{
  disable(1),
  enable(2)
}
ACCESS read-write
STATUS mandatory
DESCRIPTION
"Enable/disable phone extension delay S51.7. Default is 
enable "
::= { mdmScEntry 45 }

mdmScLinkRateAmpU OBJECT-TYPE
SYNTAX INTEGER{
  variable(1),
  bps300(2),
  bps1200(3),
  bps2400(4),
  bps4800(5),
  bps7200(6),
  bps9600(7),
  bps12000(8),
  bps14400(9),
  bps16800(10),
  bps19200(11),
  bps21600(12),
  bps24000(13),
  bps26400(14),
  bps28800(15),
  bps31200(16),
  bps33600(17),
  bps33333(18),
  bps37333(19),
  bps41333(20),
  bps42666(21),
  bps44000(22),
  bps45333(23),
  bps46666(24),
  bps48000(25),
  bps49333(26),
  bps50666(27),
  bps52000(28),
  bps53333(29),
  bps54666(30),
  bps56000(31),
  bps57333(32),
  bps64000(33),
  bps28000(34),
  bps29333(35),
  bps30666(36),
  bps32000(37),
  bps34666(38),
  bps36000(39),
  bps38666(40),
  bps40000(41),
  bps58666(42),
  bps60000(43),
  bps61333(44),
  bps62666(45)
}
ACCESS read-write
STATUS mandatory
DESCRIPTION
"Minimum high-speed direction link speed Default=variable."
::= { mdmScEntry 46 }

mdmScLowerSpeedMin OBJECT-TYPE
SYNTAX INTEGER{
  variable(1),
  bps300(2),
  bps1200(3),
  bps2400(4),
  bps4800(5),
  bps7200(6),
  bps9600(7),
  bps12000(8),
  bps14400(9),
  bps16800(10),
  bps19200(11),
  bps21600(12),
  bps24000(13),
  bps26400(14),
  bps28800(15),
  bps31200(16),
  bps33600(17),
  bps33333(18),
  bps37333(19),
  bps41333(20),
  bps42666(21),
  bps44000(22),
  bps45333(23),
  bps46666(24),
  bps48000(25),
  bps49333(26),
  bps50666(27),
  bps52000(28),
  bps53333(29),
  bps54666(30),
  bps56000(31),
  bps57333(32),
  bps64000(33),
  bps28000(34),
  bps29333(35),
  bps30666(36),
  bps32000(37),
  bps34666(38),
  bps36000(39),
  bps38666(40),
  bps40000(41),
  bps58666(42),
  bps60000(43),
  bps61333(44),
  bps62666(45)
}
ACCESS read-write
STATUS mandatory
DESCRIPTION
"Lower speed direction minimum Default=1."
::= { mdmScEntry 47 }

mdmScLowerSpeedMax OBJECT-TYPE
SYNTAX INTEGER{
  variable(1),
  bps300(2),
  bps1200(3),
  bps2400(4),
  bps4800(5),
  bps7200(6),
  bps9600(7),
  bps12000(8),
  bps14400(9),
  bps16800(10),
  bps19200(11),
  bps21600(12),
  bps24000(13),
  bps26400(14),
  bps28800(15),
  bps31200(16),
  bps33600(17),
  bps33333(18),
  bps37333(19),
  bps41333(20),
  bps42666(21),
  bps44000(22),
  bps45333(23),
  bps46666(24),
  bps48000(25),
  bps49333(26),
  bps50666(27),
  bps52000(28),
  bps53333(29),
  bps54666(30),
  bps56000(31),
  bps57333(32),
  bps64000(33),
  bps28000(34),
  bps29333(35),
  bps30666(36),
  bps32000(37),
  bps34666(38),
  bps36000(39),
  bps38666(40),
  bps40000(41),
  bps58666(42),
  bps60000(43),
  bps61333(44),
  bps62666(45)
}
ACCESS read-write
STATUS mandatory
DESCRIPTION
"Lower speed direction maximum  Default=1."
::= { mdmScEntry 48 }

mdmScX2Client OBJECT-TYPE
SYNTAX INTEGER{
  enabled(1),
  disabled(2)
}
ACCESS read-write
STATUS mandatory
DESCRIPTION
"X2 Client Mode Disable Default=enabled."
::= { mdmScEntry 49 }

mdmScX2Server OBJECT-TYPE
SYNTAX INTEGER{
  enabled(1),
  disabled(2)
}
ACCESS read-write
STATUS mandatory
DESCRIPTION
"X2 Server Mode Disable Default=enabled."
::= { mdmScEntry 50 }

mdmScX2Symmetric OBJECT-TYPE
SYNTAX INTEGER{
  enabled(1),
  disabled(2)
}
ACCESS read-write
STATUS mandatory
DESCRIPTION
"X2 Symmetric Mode Disable Default=enable."
::= { mdmScEntry 51 }

mdmScX2HighPowerConst OBJECT-TYPE
SYNTAX INTEGER{
  disable(1),
  enable(2)
}
ACCESS read-write
STATUS mandatory
DESCRIPTION
"This object is used to enable/disable the X2 high-power 
constellation. This object is only valid in countries, 
where it is legal. It corresponds to S Register 76.7 
Default = Disable(1)." 
::= { mdmScEntry 52 }

mdmScPiafs OBJECT-TYPE
SYNTAX INTEGER{
  enable(1),
  disable(2)
}
ACCESS read-write
STATUS mandatory
DESCRIPTION
"This object is used to enable/disable PIAFS protocol. It 
corresponds to S Register 72.4 Default = enable(1)."
::= { mdmScEntry 53 }

mdmScPiafsV42bis OBJECT-TYPE
SYNTAX INTEGER{
  enable(1),
  disable(2)
}
ACCESS read-write
STATUS mandatory
DESCRIPTION
"This object is used to enable/disable PIAFS V42bis 
compression protocol. It corresponds to S Register 72.5. 
Default = enable(1)." 
::= { mdmScEntry 54 }

mdmScTxPwrLvl OBJECT-TYPE
SYNTAX INTEGER (0..31)
ACCESS read-write
STATUS mandatory
DESCRIPTION
"This object configures the power level. It applies to 
S-register S82."
::= { mdmScEntry 55 }

mdmScTxPwrLvlApplied OBJECT-TYPE
SYNTAX INTEGER{
  inputToFarEndOfCodec(1),
  outputOfTheServerModem(2)
}
ACCESS read-write
STATUS mandatory
DESCRIPTION
"This object configures where the power level is applied. It 
applies to S-register S81.0."
::= { mdmScEntry 56 }

mdmScX2Version2 OBJECT-TYPE
SYNTAX INTEGER{
  enabled(1),
  disabled(2)
}
ACCESS read-write
STATUS mandatory
DESCRIPTION
"This object is the x2 Version 2 Modulation. It applies to 
S-register S81.1 "
::= { mdmScEntry 57 }

mdmScV34Fallback OBJECT-TYPE
SYNTAX INTEGER{
  enabled(1),
  disabled(2)
}
ACCESS read-write
STATUS mandatory
DESCRIPTION
"This object is the x2 fallback to v34. It applies to 
S-register S76.3 "
::= { mdmScEntry 58 }

mdmScV90Analogue OBJECT-TYPE
SYNTAX INTEGER{
  enabled(1),
  disabled(2)
}
ACCESS read-write
STATUS mandatory
DESCRIPTION
"This object controls the enable/disable of the V.90 client 
modulation.Default=Enable(1)."
::= { mdmScEntry 59 }

mdmScV90Digital OBJECT-TYPE
SYNTAX INTEGER{
  enabled(1),
  disabled(2)
}
ACCESS read-write
STATUS mandatory
DESCRIPTION
"This object controls the enable/disable of the V.90 server 
modulation.Default=Enable(1)."
::= { mdmScEntry 60 }

mdmScV90AllDigital OBJECT-TYPE
SYNTAX INTEGER{
  enabled(1),
  disabled(2)
}
ACCESS read-write
STATUS mandatory
DESCRIPTION
"This object controls the enable/disable of the V.90 
symmetric modulation. Default=Enable(1)."
::= { mdmScEntry 61 }

-- The modem Call Control group

mdmCc OBJECT IDENTIFIER ::= { mdm 7 }

mdmCcTable OBJECT-TYPE
SYNTAX SEQUENCE OF MdmCcEntry
ACCESS not-accessible
STATUS mandatory
DESCRIPTION
"A table containing the call control parameters for each 
modem in the chassis."
::= { mdmCc 1 }

mdmCcEntry OBJECT-TYPE
SYNTAX MdmCcEntry
ACCESS not-accessible
STATUS mandatory
DESCRIPTION
"Call control parameters for a modem.  These define the 
sequence of operation related to how a call is negotiated."
INDEX { mdmCcIndex }
::= { mdmCcTable 1 }

MdmCcEntry ::=
SEQUENCE {
mdmCcIndex
    INTEGER,
mdmCcDialDelay
    INTEGER,
mdmCcWaitForCarrier
    INTEGER,
mdmCcInactivityTimer
    INTEGER,
mdmCcAutoDialOnDtrEna
    INTEGER,
mdmCcAutoDialOnPwrUpEna
    INTEGER,
mdmCcGhostPortLockEna
    INTEGER,
mdmCcQuietResultCodes
    INTEGER,
mdmCcResponseMode
    INTEGER,
mdmCcResultCodeOptions
    INTEGER,
mdmCcArqResultCodeMode
    INTEGER,
mdmCcEscCodeRsp
    INTEGER,
mdmCcAtRecognition
    INTEGER,
mdmCcMgmtSysMsgDis
    INTEGER,
mdmCcV32ToneDuration
    INTEGER,
mdmCcAutoAnswer
    INTEGER,
mdmCcAnswerInOrigMode
    INTEGER,
mdmCcArqBufWait
    INTEGER,
mdmCcPhoneString0
    DisplayString,
mdmCcPhoneString1
    DisplayString,
mdmCcPhoneString2
    DisplayString,
mdmCcPhoneString3
    DisplayString,
mdmCcErrorCntlMode
    INTEGER,
mdmCcMiMic
    INTEGER,
mdmCcMnpWith1200
    INTEGER,
mdmCcMnpWith2400
    INTEGER,
mdmCcMnpWithV32
    INTEGER,
mdmCcMnpTimeout
    INTEGER,
mdmCcV21V23FallBackTimer
    INTEGER,
mdmCcAddnlAnswToneDur
    INTEGER,
mdmCcBillingDelayPeriod
    INTEGER,
mdmCcCarrierAccessCode1
    DisplayString,
mdmCcCarrierAccessCode2
    DisplayString,
mdmCcCarrierAccessCode3
    DisplayString,
mdmCcCallingInitStr1
    DisplayString,
mdmCcCallingInitStr2
    DisplayString,
mdmCcCallingInitStr3
    DisplayString,
mdmCcCallingInitStr4
    DisplayString,
mdmCcDataFaxMode
    INTEGER,
mdmCcT1CallSetupProc
    INTEGER,
mdmCcT1DialToneType
    INTEGER,
mdmCcT1KpStMfTones
    INTEGER,
mdmCcT1CallInitStrUse
    INTEGER,
mdmCcT1CallInitStrBase
    INTEGER,
mdmCcIntBlackListDis
    INTEGER,
mdmCcOffHookRestrict
    INTEGER,
mdmCcT1DialInAniDig
    INTEGER,
mdmCcT1DialInDnisDig
    INTEGER,
mdmCcNoPbNoConnEna
    INTEGER,
mdmCcIdleDiscPatt
    INTEGER,
mdmCcMnp10
    INTEGER,
mdmCcMnp10Ec
    INTEGER,
mdmCcAtzPbHandling
    INTEGER,
mdmCcDefltPRISlot
    INTEGER,
mdmCcExtDTMFToneSupport
    INTEGER,
mdmCcDataOverVoice
    INTEGER,
mdmCc2100AnswerTone
    INTEGER,
mdmCcEnableV120v42Bis
    INTEGER,
mdmCcHdlcLicIe
    INTEGER,
mdmCcDtmfTerminationTone
    INTEGER,
mdmCcAfaxMaxRateSrvOpt20
    INTEGER,
mdmCcAfaxMaxRateSrvOpt21
    INTEGER
}

mdmCcIndex OBJECT-TYPE
SYNTAX INTEGER
ACCESS read-only
STATUS mandatory
DESCRIPTION
"The index which uniquely identifies the modem to which this 
entry is applicable.  The value corresponds to the value of 
the index to the entity table in the chassis MIB that 
corresponds to the same modem."
::= { mdmCcEntry 1 }

mdmCcDialDelay OBJECT-TYPE
SYNTAX INTEGER (0..255)
ACCESS read-write
STATUS mandatory
DESCRIPTION
"Defines the number of seconds the modem waits between going 
off hook and begining to dial.  Ignored when result code 
options 2,4,6,or 7 are active.  Default=2."
::= { mdmCcEntry 2 }

mdmCcWaitForCarrier OBJECT-TYPE
SYNTAX INTEGER (0..255)
ACCESS read-write
STATUS mandatory
DESCRIPTION
"Defines the number of seconds the modem will wait for a 
carrier signal after dialing.  Default=60."
::= { mdmCcEntry 3 }

mdmCcInactivityTimer OBJECT-TYPE
SYNTAX INTEGER (0..255)
ACCESS read-write
STATUS mandatory
DESCRIPTION
"Sets the duration (in seconds) that the modem will maintain 
a connection when there is no activity on the phone line.  
The feature is disabled when set to 0.  Default=0."
::= { mdmCcEntry 4 }

mdmCcAutoDialOnDtrEna OBJECT-TYPE
SYNTAX INTEGER{
  disable(1),
  enable(2)
}
ACCESS read-write
STATUS mandatory
DESCRIPTION
"When enabled the modem will dial the number present in 
mdmCCPhoneString0 when the DTR signal transitions from low 
to high.  Default=disable(1)."
::= { mdmCcEntry 5 }

mdmCcAutoDialOnPwrUpEna OBJECT-TYPE
SYNTAX INTEGER{
  disable(1),
  enable(2)
}
ACCESS read-write
STATUS mandatory
DESCRIPTION
"When enabled, the modem will dial the number present in 
mdmCcPhoneString0 on power up or after a reset.  
Default=disable(1)."
::= { mdmCcEntry 6 }

mdmCcGhostPortLockEna OBJECT-TYPE
SYNTAX INTEGER{
  disable(1),
  enable(2)
}
ACCESS read-write
STATUS mandatory
DESCRIPTION
"When enabled, the modem requires that DTR go low before it 
will accept another call.  The modem also implements a Fast 
Connect mode where CD is asserted before the link 
negotiation is complete.  Default=disable(1)."
::= { mdmCcEntry 7 }

mdmCcQuietResultCodes OBJECT-TYPE
SYNTAX INTEGER{
  displayResult(1),
  noResult(2),
  originateOnly(3)
}
ACCESS read-write
STATUS mandatory
DESCRIPTION
"Determines whether or not the modem transmits result codes 
to the DTE.  Default=noResult(2)."
::= { mdmCcEntry 8 }

mdmCcResponseMode OBJECT-TYPE
SYNTAX INTEGER{
  numeric(1),
  verbal(2)
}
ACCESS read-write
STATUS mandatory
DESCRIPTION
"Determines whether the modem transmits result codes in the 
verbal or numeric mode.  Default=verbal(2)."
::= { mdmCcEntry 9 }

mdmCcResultCodeOptions OBJECT-TYPE
SYNTAX INTEGER (0..7)
ACCESS read-write
STATUS mandatory
DESCRIPTION
"Defines one of eight result code subsets and also defines 
indirectly how the modem reacts to dial tone etc.  Equates 
to the modem's X register Default=1."
::= { mdmCcEntry 10 }

mdmCcArqResultCodeMode OBJECT-TYPE
SYNTAX INTEGER{
  arqResultsDisabled(1),
  arqResultsEnabled(2),
  includeHstV32(3),
  includeProtocol(4)
}
ACCESS read-write
STATUS mandatory
DESCRIPTION
"Defines whether or not the ARQ result codes are sent to the 
DTE on connection(if result codes are enabled).  
Default=arqResultsEnabled(2)."
::= { mdmCcEntry 11 }

mdmCcEscCodeRsp OBJECT-TYPE
SYNTAX INTEGER{
  goOnHook(1),
  enterCommandMode(2),
  ignoreEscCode(3)
}
ACCESS read-write
STATUS mandatory
DESCRIPTION
"Defines the action of the modem in response to the escape 
code(+++).  The default value is determined by the state of 
Dip switch 2-3 on power up."
::= { mdmCcEntry 12 }

mdmCcAtRecognition OBJECT-TYPE
SYNTAX INTEGER{
  ignore(1),
  queryOnly(2),
  enableAll(3)
}
ACCESS read-write
STATUS mandatory
DESCRIPTION
"Determines which, if any, AT commands the modem will 
recognize or accept from the DTE.  Default=ignore(1)."
::= { mdmCcEntry 13 }

mdmCcMgmtSysMsgDis OBJECT-TYPE
SYNTAX INTEGER{
  enable(1),
  disable(2)
}
ACCESS read-write
STATUS mandatory
DESCRIPTION
"Determines if the modem is to send special result codes, 
triggered by user conflicts with the management system, to 
the DTE.  Default=enable(1)."
::= { mdmCcEntry 14 }

mdmCcV32ToneDuration OBJECT-TYPE
SYNTAX INTEGER (0..255)
ACCESS read-write
STATUS mandatory
DESCRIPTION
"Specifies the duration (in 10ths of a second) that the 
modem transmits the 3000/600 Hz answer tones for V.32 
handshaking.  A setting of 0 eliminates these tones and 
will result in faster connect times for V.21 and V.23 
calls.  Default=8."
::= { mdmCcEntry 15 }

mdmCcAutoAnswer OBJECT-TYPE
SYNTAX INTEGER (0..255)
ACCESS read-write
STATUS mandatory
DESCRIPTION
"Determines the number of rings that the modem will answer 
calls on.  When set to 0 the modem can only originate 
calls.  Default=1."
::= { mdmCcEntry 17 }

mdmCcAnswerInOrigMode OBJECT-TYPE
SYNTAX INTEGER{
  disable(1),
  enable(2)
}
ACCESS read-write
STATUS mandatory
DESCRIPTION
"When enabled the modem will answer calls using the sequence 
normaly used by the originating modem.  Default=disable(1)."
::= { mdmCcEntry 18 }

mdmCcArqBufWait OBJECT-TYPE
SYNTAX INTEGER (0..255)
ACCESS read-write
STATUS mandatory
DESCRIPTION
"Sets the duration (in seconds) that the modem waits on an 
ARQ call before clearing the transmit buffer and dropping 
carrier after DTR drops.  This is to allow time for the 
remote modem to acknowledge receipt of all transmitted 
data.  Default=0."
::= { mdmCcEntry 19 }

mdmCcPhoneString0 OBJECT-TYPE
SYNTAX DisplayString (SIZE(0..36))
ACCESS read-write
STATUS mandatory
DESCRIPTION
"Phone number stored in modem's non volitile memory.  Useful 
in providing quick access to frequently called numbers.  In 
addition mdmCcPhoneString0 is used for the dial on power up 
and dial on DTR options."
::= { mdmCcEntry 20 }

mdmCcPhoneString1 OBJECT-TYPE
SYNTAX DisplayString (SIZE(0..36))
ACCESS read-write
STATUS mandatory
DESCRIPTION
"Phone number stored in the modem's non volitile memory, 
useful for providing quick access to frequently called 
numbers."
::= { mdmCcEntry 21 }

mdmCcPhoneString2 OBJECT-TYPE
SYNTAX DisplayString (SIZE(0..36))
ACCESS read-write
STATUS mandatory
DESCRIPTION
"Phone number stored in the modem's non volitile memory, 
useful in providing quick access to frequently called 
numbers."
::= { mdmCcEntry 22 }

mdmCcPhoneString3 OBJECT-TYPE
SYNTAX DisplayString (SIZE(0..36))
ACCESS read-write
STATUS mandatory
DESCRIPTION
"Phone number stored in the modem's non volitile memory, 
useful in providing quick access to frequently called 
numbers."

::= { mdmCcEntry 23 }

mdmCcErrorCntlMode OBJECT-TYPE
SYNTAX INTEGER{
  none(1),
  syncMode(2),
  normalArq(3),
  arqOnly(4),
  v25bisChar(5),
  v25bisBit(6)
}
ACCESS read-write
STATUS mandatory
DESCRIPTION
"Defines if the modem is operating in synchronous or 
asynchronous mode and how it responds relative to 
negotiation of error control on asynchronous connections.  
When set to the default, normalArq(3), the modem attempts 
to connect with error control but if unable to negotiate it 
connects anyway.  When set to none(1), async connections do 
not attempt to use error control.  When set to arqOnly(4), 
the modem will hang up if unable to negotiate error contol. 
 When set to syncMode(2), the modem will not connect 
asynchronously."
::= { mdmCcEntry 24 }

mdmCcMiMic OBJECT-TYPE
SYNTAX INTEGER{
  disable(1),
  enable(2)
}
ACCESS read-write
STATUS mandatory
DESCRIPTION
"Specifies whether the modem will recognize MI/MIC closure 
as the mechanism for detecting incomming calls.  
Default=disable(1)."
::= { mdmCcEntry 25 }

mdmCcMnpWith1200 OBJECT-TYPE
SYNTAX INTEGER{
  enable(1),
  disable(2)
}
ACCESS read-write
STATUS mandatory
DESCRIPTION
"Determines if the modem will include MNP/V42 negotiation on 
1200 bps connections.  Default=enable(1)."
::= { mdmCcEntry 26 }

mdmCcMnpWith2400 OBJECT-TYPE
SYNTAX INTEGER{
  enable(1),
  disable(2)
}
ACCESS read-write
STATUS mandatory
DESCRIPTION
"Determines if the modem will include MNP/V43 negotiation on 
2400 bps calls.  default=enable(1)."
::= { mdmCcEntry 27 }

mdmCcMnpWithV32 OBJECT-TYPE
SYNTAX INTEGER{
  enable(1),
  disable(2)
}
ACCESS read-write
STATUS mandatory
DESCRIPTION
"Determines if the modem will include MNP/V42 negotiation on 
V.32 connections.  Default=enable(1)."
::= { mdmCcEntry 28 }

mdmCcMnpTimeout OBJECT-TYPE
SYNTAX INTEGER (0..14)
ACCESS read-write
STATUS mandatory
DESCRIPTION
"Specifies the MNP/V42 link request timeout for negotiation 
of 1200 and 2400 bps calls.  Default=5."
::= { mdmCcEntry 29 }

mdmCcV21V23FallBackTimer OBJECT-TYPE
SYNTAX INTEGER (0..255)
ACCESS read-write
STATUS mandatory
DESCRIPTION
"V21/V23 fallback timer, 1/10 sec. NVRAM S Register S29. 
Default=20"
::= { mdmCcEntry 30 }

mdmCcAddnlAnswToneDur OBJECT-TYPE
SYNTAX INTEGER (0..255)
ACCESS read-write
STATUS optional
DESCRIPTION
"Additional answer tone duration, 1/10 sec.  NVRAM S 
Register S49. Default=16."
::= { mdmCcEntry 31 }

mdmCcBillingDelayPeriod OBJECT-TYPE
SYNTAX INTEGER (0..255)
ACCESS read-write
STATUS optional
DESCRIPTION
"Billing Delay Period.  1/50 sec. NVRAM S Register S50.  
Default=100."
::= { mdmCcEntry 32 }

mdmCcCarrierAccessCode1 OBJECT-TYPE
SYNTAX DisplayString (SIZE(0..10))
ACCESS read-write
STATUS optional
DESCRIPTION
"The DNIS Carrier Access Code (CAC) Number.  This is a 
string which contains a number from 1 to 10 digits (e.g. 
9501755). This is the 1st of 3 CACs."
::= { mdmCcEntry 33 }

mdmCcCarrierAccessCode2 OBJECT-TYPE
SYNTAX DisplayString (SIZE(0..10))
ACCESS read-write
STATUS optional
DESCRIPTION
"The DNIS Carrier Access Code (CAC) Number.  This is a 
string which contains a number from 1 to 10 digits.  This 
is the 2nd of 3 CACs."
::= { mdmCcEntry 34 }

mdmCcCarrierAccessCode3 OBJECT-TYPE
SYNTAX DisplayString (SIZE(0..10))
ACCESS read-write
STATUS optional
DESCRIPTION
"The DNIS Carrier Access Code (CAC) Number.  This is a 
string which contains a number from 1 to 10 digits. This is 
the 3rd of 3 CACs."
::= { mdmCcEntry 35 }

mdmCcCallingInitStr1 OBJECT-TYPE
SYNTAX DisplayString (SIZE(0..40))
ACCESS read-write
STATUS optional
DESCRIPTION
"This is the Carrier Access Code (CAC) initialization 
string.  This string is a configuration string of 1 to 30 
characters (e.g. &F, &F&B1&R1, etc.)  This string does NOT 
include the AT attention prefix. This is the 1st of 4 CAC 
init strings."
::= { mdmCcEntry 36 }

mdmCcCallingInitStr2 OBJECT-TYPE
SYNTAX DisplayString (SIZE(0..40))
ACCESS read-write
STATUS optional
DESCRIPTION
"This is the Carrier Access Code (CAC) initialization 
string.  This string is 1 to 30 characters. It does NOT 
include the AT attention prefix. It is the 2nd of 4 CAC 
init strings."
::= { mdmCcEntry 37 }

mdmCcCallingInitStr3 OBJECT-TYPE
SYNTAX DisplayString (SIZE(0..40))
ACCESS read-write
STATUS optional
DESCRIPTION
"This is the Carrier Access Code (CAC) initialization 
string.  This is a string of 1 to 30 characters.  It does 
NOT include the AT attention prefix.  This is the 3rd of 4 
CAC init strings."
::= { mdmCcEntry 38 }

mdmCcCallingInitStr4 OBJECT-TYPE
SYNTAX DisplayString (SIZE(0..40))
ACCESS read-write
STATUS optional
DESCRIPTION
"This is the Carrier Access Code (CAC) initialization 
string.  This is a string of 1 to 30 characters.  It does 
NOT include the AT attention prefix.  This is the 4th of 4 
CAC init strings."
::= { mdmCcEntry 39 }

mdmCcDataFaxMode OBJECT-TYPE
SYNTAX INTEGER{
  dataMode(1),
  faxClass1Mode(2),
  dataFaxClass1Mode(3),
  faxClass2Mode(4),
  dataFaxClass2Mode(5)
}
ACCESS read-write
STATUS mandatory
DESCRIPTION
"Gives the current Data/FAX mode of the modem."
::= { mdmCcEntry 40 }

mdmCcT1CallSetupProc OBJECT-TYPE
SYNTAX INTEGER{
  normalSetup(1),
  noSetup(2)
}
ACCESS read-write
STATUS optional
DESCRIPTION
"Determines T1 call setup procedures used.  Choices are 
'normal' or 'none'.  None assumes a dedicated (leased) DS0 
assigned to the modem.
Default=normalSetup(1)."
::= { mdmCcEntry 41 }

mdmCcT1DialToneType OBJECT-TYPE
SYNTAX INTEGER{
  mfTones(1),
  dtmfTones(2)
}
ACCESS read-write
STATUS optional
DESCRIPTION
"Determines if MF or DTMF tones are used for T1 signaling. 
Default = mfTones(1)."
::= { mdmCcEntry 42 }

mdmCcT1KpStMfTones OBJECT-TYPE
SYNTAX INTEGER{
  enable(1),
  disable(2)
}
ACCESS read-write
STATUS optional
DESCRIPTION
"Determines the usage of KP and ST MF tone encapsulation of 
the dial sequence.
Default=enable(1)."
::= { mdmCcEntry 43 }

mdmCcT1CallInitStrUse OBJECT-TYPE
SYNTAX INTEGER{
  enable(1),
  disable(2)
}
ACCESS read-write
STATUS optional
DESCRIPTION
"Determines if calling init strings are used or 
not.
Default=enable(1)."
::= { mdmCcEntry 44 }

mdmCcT1CallInitStrBase OBJECT-TYPE
SYNTAX INTEGER{
  dnisBase(1),
  aniBase(2)
}
ACCESS read-write
STATUS optional
DESCRIPTION
"Determines if the calling init strings are based upon DNIS 
or ANI.
Default=dnisBase(1)."
::= { mdmCcEntry 45 }

mdmCcIntBlackListDis OBJECT-TYPE
SYNTAX INTEGER{
  enable(1),
  disable(2)
}
ACCESS read-write
STATUS mandatory
DESCRIPTION
"Disable BlackList restriction in the international modems. 
Default=0 (enable)  s40.1 reg "

::= { mdmCcEntry 46 }

mdmCcOffHookRestrict OBJECT-TYPE
SYNTAX INTEGER{
  enable(1),
  disable(2)
}
ACCESS read-write
STATUS mandatory
DESCRIPTION
"Disable off-hook restriction in the international modems. 
Default=0 (enable)  S40.2 reg"
::= { mdmCcEntry 47 }

mdmCcT1DialInAniDig OBJECT-TYPE
SYNTAX INTEGER (0..12)
ACCESS read-write
STATUS optional
DESCRIPTION
"Sets the number of ANI digits allowed in incoming calls. 
Default = 0."
::= { mdmCcEntry 48 }

mdmCcT1DialInDnisDig OBJECT-TYPE
SYNTAX INTEGER (0..12)
ACCESS read-write
STATUS optional
DESCRIPTION
"Sets the number of DNIS/DID digits allowed in incoming 
calls. Default = 0."
::= { mdmCcEntry 49 }

mdmCcNoPbNoConnEna OBJECT-TYPE
SYNTAX INTEGER{
  disable(1),
  enable(2)
}
ACCESS read-write
STATUS optional
DESCRIPTION
"Sets if to answer a call when there is no Packet Bus link. 
Normal is the Default =0"
::= { mdmCcEntry 50 }

mdmCcIdleDiscPatt OBJECT-TYPE
SYNTAX INTEGER (0..255)
ACCESS read-write
STATUS optional
DESCRIPTION
"Idle disconnect pattern sent to the T1 NAC. Normal values: 
USA = 1, international = 84.  Default = 1.  Configure the 
T1 identically.  Consult the help screen, user manual or US 
Robotics before changing.  Modem register S71."
::= { mdmCcEntry 51 }

mdmCcMnp10 OBJECT-TYPE
SYNTAX INTEGER{
  disable(1),
  enable(2)
}
ACCESS read-write
STATUS optional
DESCRIPTION
"S61.4 register disable/enable MNP10 originate mode."
::= { mdmCcEntry 52 }

mdmCcMnp10Ec OBJECT-TYPE
SYNTAX INTEGER{
  disable(1),
  enable(2)
}
ACCESS read-write
STATUS optional
DESCRIPTION
"S61.5 register disable/enable MNP10EC originate mode."
::= { mdmCcEntry 53 }

mdmCcAtzPbHandling OBJECT-TYPE
SYNTAX INTEGER{
  normalAtz(1),
  atzPbIgnored(2),
  atzPbNvram(3)
}
ACCESS read-write
STATUS optional
DESCRIPTION
"ATZ handling over Packet Bus. S72 REG"
::= { mdmCcEntry 54 }

mdmCcDefltPRISlot OBJECT-TYPE
SYNTAX INTEGER (1..5)
ACCESS read-write
STATUS mandatory
DESCRIPTION
"Default dialout PRI slot.  Default = 1"
::= { mdmCcEntry 55 }

mdmCcExtDTMFToneSupport OBJECT-TYPE
SYNTAX INTEGER{
  disable(1),
  enable(2)
}
ACCESS read-write
STATUS mandatory
DESCRIPTION
"Enable/Disable DTMF extended support.  Default = disable"
::= { mdmCcEntry 56 }

mdmCcDataOverVoice OBJECT-TYPE
SYNTAX INTEGER{
  disable(1),
  enable(2)
}
ACCESS read-write
STATUS mandatory
DESCRIPTION
"Data Over Voice support originate S68.1."
::= { mdmCcEntry 57 }

mdmCc2100AnswerTone OBJECT-TYPE
SYNTAX INTEGER{
  disable(1),
  enable(2)
}
ACCESS read-write
STATUS mandatory
DESCRIPTION
"Data Over Voice support answer S68.2."
::= { mdmCcEntry 58 }

mdmCcEnableV120v42Bis OBJECT-TYPE
SYNTAX INTEGER{
  disable(1),
  enable(2)
}
ACCESS read-write
STATUS mandatory
DESCRIPTION
"V.42bis Compression over V.120. S67.4"
::= { mdmCcEntry 59 }

mdmCcHdlcLicIe OBJECT-TYPE
SYNTAX INTEGER{
  disable(1),
  enable(2)
}
ACCESS read-write
STATUS mandatory
DESCRIPTION
"This object is to Enable\Disable LIC IE message for HDLC 
protocols. S Register S68.3"
::= { mdmCcEntry 60 }

mdmCcDtmfTerminationTone OBJECT-TYPE
SYNTAX INTEGER (0..16)
ACCESS read-write
STATUS mandatory
DESCRIPTION
"This object is to set the DTMF Termination Tone."
::= { mdmCcEntry 61 }

mdmCcAfaxMaxRateSrvOpt20 OBJECT-TYPE
SYNTAX INTEGER{
  bps2400(1),
  bps4800(2),
  bps7200(3),
  bps9600(4),
  bps12000(5),
  bps14400(6)
}
ACCESS read-write
STATUS mandatory
DESCRIPTION
"This object is used to limit the maximum rate for an Analog 
Fax Connection. Service option 20. Upper nibble of the S94 
register."
::= { mdmCcEntry 62 }

mdmCcAfaxMaxRateSrvOpt21 OBJECT-TYPE
SYNTAX INTEGER{
  bps2400(1),
  bps4800(2),
  bps7200(3),
  bps9600(4),
  bps12000(5),
  bps14400(6)
}
ACCESS read-write
STATUS mandatory
DESCRIPTION
"This object is used to limit the maximum rate for an Analog 
Fax Connection. Service option 21.  Lower nibble of S94 
register."
::= { mdmCcEntry 63 }

-- The modem Error Correction group

mdmEc OBJECT IDENTIFIER ::= { mdm 8 }

mdmEcTable OBJECT-TYPE
SYNTAX SEQUENCE OF MdmEcEntry
ACCESS not-accessible
STATUS mandatory
DESCRIPTION
"A table of Error Control Parameters for each modem in this 
system, the quantity of entries is given by modemNumber."
::= { mdmEc 1 }

mdmEcEntry OBJECT-TYPE
SYNTAX MdmEcEntry
ACCESS not-accessible
STATUS mandatory
DESCRIPTION
"Configurable objects which define the modems error control 
operation."
INDEX { mdmEcIndex }
::= { mdmEcTable 1 }

MdmEcEntry ::=
SEQUENCE {
mdmEcIndex
    INTEGER,
mdmEcMnp3Dis
    INTEGER,
mdmEcMnp4Dis
    INTEGER,
mdmEcMnpUnusual
    INTEGER,
mdmEcV42MnpHandshake
    INTEGER
}

mdmEcIndex OBJECT-TYPE
SYNTAX INTEGER
ACCESS read-only
STATUS mandatory
DESCRIPTION
"This object contains the unique value assigned to this 
modem in the chassis mib entity relation table and is used 
as the mechanism for correctly indexing into this table."
::= { mdmEcEntry 1 }

mdmEcMnp3Dis OBJECT-TYPE
SYNTAX INTEGER{
  enable(1),
  disable(2)
}
ACCESS read-write
STATUS mandatory
DESCRIPTION
"Determines if the modem will negotiate for MNP level 3 
error correction.  Default=enable."
::= { mdmEcEntry 2 }

mdmEcMnp4Dis OBJECT-TYPE
SYNTAX INTEGER{
  enable(1),
  disable(2)
}
ACCESS read-write
STATUS mandatory
DESCRIPTION
"Determines if the modem will negotiate for MNP level 4 
error correction.  Default=enable."
::= { mdmEcEntry 3 }

mdmEcMnpUnusual OBJECT-TYPE
SYNTAX INTEGER{
  disable(1),
  enable(2)
}
ACCESS read-write
STATUS mandatory
DESCRIPTION
"Determines if the modem will attempt to negotiate for MNP 
operation used in some early 2400bps modems.  
Default=disable."
::= { mdmEcEntry 4 }

mdmEcV42MnpHandshake OBJECT-TYPE
SYNTAX INTEGER{
  enableAll(1),
  enableV42disableMnp(2),
  disablev42enablemnp(3),
  disableDetectionPhase(4)
}
ACCESS read-write
STATUS mandatory
DESCRIPTION
"Determines what types of error correction the modem will 
attempt to negotiate.  When configured for the default, 
full V.42 and MNP, the modem first tries to connect with 
V42 error control and then with MNP error control.  When 
set to disable either V42 or MNP the modem will only 
attempt to negotiate the enabled protocol.  When set to 
disable the V42 detect phase, it is not included in the 
handshaking process.  This allows for faster connections 
between V42 modems."
::= { mdmEcEntry 5 }

-- The modem Call Statistics group

mdmCs OBJECT IDENTIFIER ::= { mdm 9 }

mdmCsTable OBJECT-TYPE
SYNTAX SEQUENCE OF MdmCsEntry
ACCESS not-accessible
STATUS mandatory
DESCRIPTION
"A table of modem status and call statistic parameters for 
each modem in the chassis."
::= { mdmCs 1 }

mdmCsEntry OBJECT-TYPE
SYNTAX MdmCsEntry
ACCESS not-accessible
STATUS mandatory
DESCRIPTION
"Objects that define the modem status and statistics 
specific to a the current connection when the modem is on 
line or to the last connection when the modem is idle."
INDEX { mdmCsIndex }
::= { mdmCsTable 1 }

MdmCsEntry ::=
SEQUENCE {
mdmCsIndex
    INTEGER,
mdmCsStatus
    INTEGER,
mdmCsLastNumberDialedOut
    DisplayString,
mdmCsLastNumberDialedIn
    DisplayString,
mdmCsLastCallingPartyNum
    DisplayString,
mdmCsOriginateAnswer
    INTEGER,
mdmCsRings
    INTEGER,
mdmCsDisconnectReason
    INTEGER,
mdmCsConnectFailReason
    INTEGER,
mdmCsInitialTxLinkRate
    INTEGER,
mdmCsInitialRxLinkRate
    INTEGER,
mdmCsFinalTxLinkRate
    INTEGER,
mdmCsFinalRxLinkRate
    INTEGER,
mdmCsModulationType
    INTEGER,
mdmCsSyncAsyncModeUsed
    INTEGER,
mdmCsErrorControlType
    INTEGER,
mdmCsCompressionType
    INTEGER,
mdmCsEqualizationType
    INTEGER,
mdmCsFallbackEnabled
    INTEGER,
mdmCsCharsSent
    INTEGER,
mdmCsCharsReceived
    INTEGER,
mdmCsOctetsSent
    INTEGER,
mdmCsOctetsReceived
    INTEGER,
mdmCsBlocksSent
    INTEGER,
mdmCsBlocksReceived
    INTEGER,
mdmCsBlocksResent
    INTEGER,
mdmCsRetrainsRequested
    INTEGER,
mdmCsRetrainsGranted
    INTEGER,
mdmCsLineReversalQty
    INTEGER,
mdmCsCharsLost
    INTEGER,
mdmCsBackChannelRate
    INTEGER,
mdmCsBlerQty
    INTEGER,
mdmCsLinkTimeoutQty
    INTEGER,
mdmCsFallbackQty
    INTEGER,
mdmCsUpshiftQty
    INTEGER,
mdmCsLinkNakQty
    INTEGER,
mdmCsGainHitCount
    INTEGER,
mdmCsSecurityUserName
    DisplayString,
mdmCsCallDuration
    DisplayString,
mdmCsCallRefNum
    INTEGER,
mdmCsPriCardSlot
    INTEGER,
mdmCsTDMTimeSlot
    INTEGER,
mdmCsPriCardSpanLine
    INTEGER,
mdmCsBChannelUsed
    INTEGER,
mdmCsQCarrFreqTx
    INTEGER,
mdmCsQCarrFreqRx
    INTEGER,
mdmCsQSymRateTx
    INTEGER,
mdmCsQSymRateRx
    INTEGER,
mdmCsQTrellisTx
    INTEGER,
mdmCsQTrellisRx
    INTEGER,
mdmCsQNonLinCdTx
    INTEGER,
mdmCsQNonLinCdRx
    INTEGER,
mdmCsQPrecodingTx
    INTEGER,
mdmCsQPrecodingRx
    INTEGER,
mdmCsQShapingTx
    INTEGER,
mdmCsQShapingRx
    INTEGER,
mdmCsQPreemphTx
    INTEGER,
mdmCsQPreemphRx
    INTEGER,
mdmCsQRxLevel
    INTEGER,
mdmCsQTxLevel
    INTEGER,
mdmCsQSNR
    INTEGER,
mdmCsQNearEcho
    INTEGER,
mdmCsQFarEcho
    INTEGER,
mdmCsQRndTripDly
    INTEGER,
mdmCsQPacketSizeCurr
    INTEGER,
mdmCsQPacketSizeLow
    INTEGER,
mdmCsQPacketSizeHigh
    INTEGER,
mdmCsQCellTxLevelCurr
    INTEGER,
mdmCsQCellTxLevelLow
    INTEGER,
mdmCsQCellTxLevelHigh
    INTEGER,
mdmCsQSNRLevelCurr
    INTEGER,
mdmCsQSNRLevelLow
    INTEGER,
mdmCsQSNRLevelHigh
    INTEGER,
mdmCsQCellularProt
    INTEGER,
mdmCsFreqProbeData
    OCTET STRING,
mdmCsLevelProbeData
    OCTET STRING,
mdmCsQTimingOffset
    INTEGER,
mdmCsQCarrierOffset
    INTEGER,
mdmCsQCoding
    INTEGER,
mdmCsTrainingInfo
    OCTET STRING,
mdmCsX2signature
    OCTET STRING,
mdmCsX2Status
    INTEGER,
mdmCsCallType
    INTEGER,
mdmCsCallStartTime
    INTEGER,
mdmCsCallEndTime
    INTEGER,
mdmCsDigitalPadAttenuated
    INTEGER,
mdmCsInitModulationType
    INTEGER,
mdmCsRxMinSpeed
    INTEGER,
mdmCsRxMaxSpeed
    INTEGER,
mdmCsTxMinSpeed
    INTEGER,
mdmCsTxMaxSpeed
    INTEGER,
mdmCsCollectedDTMFDigits
    OCTET STRING
}

mdmCsIndex OBJECT-TYPE
SYNTAX INTEGER
ACCESS read-only
STATUS mandatory
DESCRIPTION
"The index value which uniquely identifies the modem to 
which this entry is applicable.  The value corresponds to 
the index of the same modem in the entity table of the 
chassis MIB."
::= { mdmCsEntry 1 }

mdmCsStatus OBJECT-TYPE
SYNTAX INTEGER{
  idle(1),
  offHook(2),
  dialing(3),
  ringing(4),
  ringRcvd(5),
  linkNegotiation(6),
  onlineOriginate(7),
  onlineAnswer(8),
  localCommandMode(9),
  remoteCommandMode(10),
  lineBusiedOut(11),
  toneTest(12),
  responderTest105(13),
  responderTest102(14),
  failed(33),
  testingRom(49),
  testingRam(50),
  testingNvram(51),
  analogLoopback(52),
  localDigitalLoopback(53),
  remoteDigitalLoopback(54),
  selfTest(55),
  phoneTest(56),
  nonManagedDevice(57),
  slotEmpty(58),
  modemDisabled(59),
  notResponding(60),
  nonManagableDevice(61),
  miuFailed(62)
}
ACCESS read-only
STATUS mandatory
DESCRIPTION
"Current status of a modem including presence(idle), 
availability(disabled), and call progress states."
::= { mdmCsEntry 2 }

mdmCsLastNumberDialedOut OBJECT-TYPE
SYNTAX DisplayString (SIZE(0..40))
ACCESS read-only
STATUS mandatory
DESCRIPTION
"An ASCII string which represents the last phone number 
dialed by the modem."
::= { mdmCsEntry 3 }

mdmCsLastNumberDialedIn OBJECT-TYPE
SYNTAX DisplayString (SIZE(0..40))
ACCESS read-only
STATUS mandatory
DESCRIPTION
"An ASCII string representing the last number dialed in(if 
known).  This is the 950-xxx (DNIS) number."
::= { mdmCsEntry 4 }

mdmCsLastCallingPartyNum OBJECT-TYPE
SYNTAX DisplayString (SIZE(0..40))
ACCESS read-only
STATUS mandatory
DESCRIPTION
"An ASCII string representing the current or last party that 
called this modem.  Only known in ANI applications."
::= { mdmCsEntry 5 }

mdmCsOriginateAnswer OBJECT-TYPE
SYNTAX INTEGER{
  originateInOriginate(1),
  originateInAnswer(2),
  answerInOriginate(3),
  answerInAnswer(4)
}
ACCESS read-only
STATUS mandatory
DESCRIPTION
"Defines whether the last or current call was originated or 
answered."
::= { mdmCsEntry 6 }

mdmCsRings OBJECT-TYPE
SYNTAX INTEGER
ACCESS read-only
STATUS mandatory
DESCRIPTION
"Defines the quantity of rings detected before the DTE 
answered with DTR on the last incomming call."
::= { mdmCsEntry 7 }

mdmCsDisconnectReason OBJECT-TYPE
SYNTAX INTEGER{
  dtrDrop(1),
  escapeSequence(2),
  athCommand(3),
  carrierLoss(4),
  inactivityTimout(5),
  mnpIncompatible(6),
  undefined(7),
  remotePassword(8),
  linkPassword(9),
  retransmitLimit(10),
  linkDisconnectMsgReceived(11),
  noLoopCurrent(12),
  invalidSpeed(13),
  unableToRetrain(14),
  managementCommand(15),
  noDialTone(16),
  keyAbort(17),
  lineBusy(18),
  noAnswer(19),
  voice(20),
  noAnswerTone(21),
  noCarrier(22),
  undetermined(23),
  v42SabmeTimeout(24),
  v42BreakTimeout(25),
  v42DisconnectCmd(26),
  v42IdExchangeFail(27),
  v42BadSetup(28),
  v42InvalidCodeWord(29),
  v42StringToLong(30),
  v42InvalidCommand(31),
  none(32),
  v32Cleardown(33),
  dialSecurity(34),
  remoteAccessDenied(35),
  loopLoss(36),
  ds0Teardown(37),
  promptNotEnabled(38),
  noPromptingInSync(39),
  nonArqMode(40),
  modeIncompatible(41),
  noPromptInNonARQ(42),
  dialBackLink(43),
  linkAbort(44),
  autopassFailed(45),
  pbGenericError(46),
  pbLinkErrTxPreAck(47),
  pbLinkErrTxTardyACK(48),
  pbTransmitBusTimeout(49),
  pbReceiveBusTimeout(50),
  pbLinkErrTxTAL(51),
  pbLinkErrRxTAL(52),
  pbTransmitMasterTimeout(53),
  pbClockMissing(54),
  pbReceivedLsWhileLinkUp(55),
  pbOutOfSequenceFrame(56),
  pbBadFrame(57),
  pbAckWaitTimeout(58),
  pbReceivedAckSequenceErr(59),
  pbReceiveOvrflwRNRFailed(60),
  pbReceiveMsgBufOvrflw(61),
  rcvdGatewayDiscCmd(62),
  tokenPassingTimeout(63),
  dspInterruptTimeout(64),
  mnpProtocolViolation(65),
  class2FaxHangupCmd(66),
  hstSpeedSwitchTimeout(67),
  tooManyUnacked(68),
  timerExpired(69),
  t1Glare(70),
  priDialoutRqTimeout(71),
  abortAnlgDstOvrIsdn(72),
  normalUserCallClear(73),
  normalUnspecified(74),
  bearerIncompatibility(75),
  protocolErrorEvent(76),
  abnormalDisconnect(77),
  invalidCauseValue(78),
  resourceUnavailable(79),
  remotHungUpDuringTraining(80),
  trainingTimeout(81),
  incomingModemNotAvailable(82),
  incomingInvalidBearerCap(83),
  incomingInvalidChannelID(84),
  incomingInvalidProgInd(85),
  incomingInvalidCallingPty(86),
  incomingInvalidCalledPty(87),
  incomingCallBlock(88),
  incomingLoopStNoRingOff(89),
  outgoingTelcoDisconnect(90),
  outgoingEMWinkTimeout(91),
  outgoingEMWinkTooShort(92),
  outgoingNoChannelAvail(93),
  dspReboot(94),
  noDSPRespToKA(95),
  noDSPRespToDisc(96),
  dspTailPtrInvalid(97),
  dspHeadPtrInvalid(98),
  dataProcessingGenericErr(99),
  timeslotUnavailable(100),
  gmtTimeNotSet(101),
  chasAwarenessNotAvailable(102),
  r2InvalidChannelDirection(103),
  r2ChannelBlockedByNetwork(104),
  r2Glare(105),
  r2OutgoingCallBlocked(106),
  r2DNISNotFound(107),
  r2SigCauseCongestion(108),
  r2SigCauseUnallocNumber(109),
  r2DSPFatalError(110),
  callBlacklisted(111)
}
ACCESS read-only
STATUS mandatory
DESCRIPTION
"Defines the reason that the last call was terminated."
::= { mdmCsEntry 8 }

mdmCsConnectFailReason OBJECT-TYPE
SYNTAX INTEGER{
  dtrDrop(1),
  escapeSequence(2),
  athCommand(3),
  carrierLoss(4),
  inactivityTimout(5),
  mnpIncompatible(6),
  undefined(7),
  remotePassword(8),
  linkPassword(9),
  retransmitLimit(10),
  linkDisconnectMsgReceived(11),
  noLoopCurrent(12),
  invalidSpeed(13),
  unableToRetrain(14),
  managementCommand(15),
  noDialTone(16),
  keyAbort(17),
  lineBusy(18),
  noAnswer(19),
  voice(20),
  noAnswerTone(21),
  noCarrier(22),
  undetermined(23),
  v42SabmeTimeout(24),
  v42BreakTimeout(25),
  v42DisconnectCmd(26),
  v42IdExchangeFail(27),
  v42BadSetup(28),
  v42InvalidCodeWord(29),
  v42StringToLong(30),
  v42InvalidCommand(31),
  none(32),
  v32Cleardown(33),
  dialSecurity(34),
  remoteAccessDenied(35),
  loopLoss(36),
  ds0Teardown(37),
  promptNotEnabled(38),
  noPromptingInSync(39),
  nonArqMode(40),
  modeIncompatible(41),
  noPromptInNonARQ(42),
  dialBackLink(43),
  linkAbort(44),
  autopassFailed(45),
  pbGenericError(46),
  pbLinkErrTxPreAck(47),
  pbLinkErrTxTardyACK(48),
  pbTransmitBusTimeout(49),
  pbReceiveBusTimeout(50),
  pbLinkErrTxTAL(51),
  pbLinkErrRxTAL(52),
  pbTransmitMasterTimeout(53),
  pbClockMissing(54),
  pbReceivedLsWhileLinkUp(55),
  pbOutOfSequenceFrame(56),
  pbBadFrame(57),
  pbAckWaitTimeout(58),
  pbReceivedAckSequenceErr(59),
  pbReceiveOvrflwRNRFailed(60),
  pbReceiveMsgBufOvrflw(61),
  rcvdGatewayDiscCmd(62),
  tokenPassingTimeout(63),
  dspInterruptTimeout(64),
  mnpProtocolViolation(65),
  class2FaxHangupCmd(66),
  hstSpeedSwitchTimeout(67),
  tooManyUnacked(68),
  timerExpired(69),
  t1Glare(70),
  priDialoutRqTimeout(71),
  abortAnlgDstOvrIsdn(72),
  normalUserCallClear(73),
  normalUnspecified(74),
  bearerIncompatibility(75),
  protocolErrorEvent(76),
  abnormalDisconnect(77),
  invalidCauseValue(78),
  resourceUnavailable(79),
  remotHungUpDuringTraining(80),
  trainingTimeout(81),
  incomingModemNotAvailable(82),
  incomingInvalidBearerCap(83),
  incomingInvalidChannelID(84),
  incomingInvalidProgInd(85),
  incomingInvalidCallingPty(86),
  incomingInvalidCalledPty(87),
  incomingCallBlock(88),
  incomingLoopStNoRingOff(89),
  outgoingTelcoDisconnect(90),
  outgoingEMWinkTimeout(91),
  outgoingEMWinkTooShort(92),
  outgoingNoChannelAvail(93),
  dspReboot(94),
  noDSPRespToKA(95),
  noDSPRespToDisc(96),
  dspTailPtrInvalid(97),
  dspHeadPtrInvalid(98),
  dataProcessingGenericErr(99),
  timeslotUnavailable(100),
  gmtTimeNotSet(101),
  chasAwarenessNotAvailable(102),
  r2InvalidChannelDirection(103),
  r2ChannelBlockedByNetwork(104),
  r2Glare(105),
  r2OutgoingCallBlocked(106),
  r2DNISNotFound(107),
  r2SigCauseCongestion(108),
  r2SigCauseUnallocNumber(109),
  r2DSPFatalError(110),
  callBlacklisted(111)
}
ACCESS read-only
STATUS mandatory
DESCRIPTION
"Defines the reason for failure if indeed the last call 
attempt failed."
::= { mdmCsEntry 9 }

mdmCsInitialTxLinkRate OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"The transmit speed at which the modem initialy connected on 
it's last or current call."
::= { mdmCsEntry 10 }

mdmCsInitialRxLinkRate OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"The receive speed at which the modem initialy connected on 
it's previous or current call."
::= { mdmCsEntry 11 }

mdmCsFinalTxLinkRate OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"The current transmit link rate of a connection, or the last 
link rate of the last connection."
::= { mdmCsEntry 12 }

mdmCsFinalRxLinkRate OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"The current receive link rate of a connection, or the last 
link rate of the last connection."
::= { mdmCsEntry 13 }

mdmCsModulationType OBJECT-TYPE
SYNTAX INTEGER{
  usRoboticsHST(1),
  ccittV32(2),
  ccittV22bis(3),
  bell103(4),
  ccittV21(5),
  bell212(6),
  ccittV32bis(7),
  ccittV23(8),
  noConnection(9),
  bell208b(10),
  v21FaxClass1(11),
  v27FaxClass1(12),
  v29FaxClass1(13),
  v17FaxClass1(14),
  v21FaxClass2(15),
  v27FaxClass2(16),
  v29FaxClass2(17),
  v17FaxClass2(18),
  v32Terbo(19),
  v34(20),
  vFC(21),
  v34plus(22),
  x2server(23),
  v110(24),
  v120(25),
  x75(26),
  asyncSyncPPP(27),
  clearChannel(28),
  x2client(29),
  x2symmetric(30),
  piafs(31),
  x2version2(32),
  v90Analogue(33),
  v90Digital(34),
  v90AllDigital(35)
}
ACCESS read-only
STATUS mandatory
DESCRIPTION
"Specifies the current/final modulation type of the current 
or last call.  The value can be different from the object 
mdmCsInitModulationType only for X2/V.90 calls."
::= { mdmCsEntry 14 }

mdmCsSyncAsyncModeUsed OBJECT-TYPE
SYNTAX INTEGER{
  asynchronous(1),
  synchronous(2)
}
ACCESS read-only
STATUS mandatory
DESCRIPTION
"Defines whether the current or last call was synchronous or 
asynchronous."
::= { mdmCsEntry 15 }

mdmCsErrorControlType OBJECT-TYPE
SYNTAX INTEGER{
  none(1),
  mnpLevel3(2),
  mnpLevel4(3),
  ccittV42(4),
  usRoboticsHST(5),
  synchronousNone(6),
  mnpLevel2(7),
  mnp10(8),
  v42Etc(9),
  mnp10Ec(10),
  lapmEc(11),
  v42Etc2(12),
  ccittV42SREJ(13),
  piafs(14),
  v120(15),
  x75(16)
}
ACCESS read-only
STATUS mandatory
DESCRIPTION
"Specifies the Error control settings in the current or last 
call. (short form)"
::= { mdmCsEntry 16 }

mdmCsCompressionType OBJECT-TYPE
SYNTAX INTEGER{
  none(1),
  ccittV42bis(2),
  mnpLevel5(3)
}
ACCESS read-only
STATUS mandatory
DESCRIPTION
"Specifies the data compression used in the current or last 
call. (short format)"
::= { mdmCsEntry 17 }

mdmCsEqualizationType OBJECT-TYPE
SYNTAX INTEGER{
  long(1),
  short(2)
}
ACCESS read-only
STATUS mandatory
DESCRIPTION
"Specifies the equalization used in the current or last 
call."
::= { mdmCsEntry 18 }

mdmCsFallbackEnabled OBJECT-TYPE
SYNTAX INTEGER{
  disable(1),
  enable(2)
}
ACCESS read-only
STATUS mandatory
DESCRIPTION
"Specifies whether line speed fallbacks were negotiated on 
the current or previous call."
::= { mdmCsEntry 19 }

mdmCsCharsSent OBJECT-TYPE
SYNTAX INTEGER
ACCESS read-only
STATUS mandatory
DESCRIPTION
"Specifies the number of characters sent on the current or 
previous call."
::= { mdmCsEntry 20 }

mdmCsCharsReceived OBJECT-TYPE
SYNTAX INTEGER
ACCESS read-only
STATUS mandatory
DESCRIPTION
"Specifies the number of characters received in the current 
or previous call."
::= { mdmCsEntry 21 }

mdmCsOctetsSent OBJECT-TYPE
SYNTAX INTEGER
ACCESS read-only
STATUS mandatory
DESCRIPTION
"Specifies the number of octets sent in the current or 
previous call."
::= { mdmCsEntry 22 }

mdmCsOctetsReceived OBJECT-TYPE
SYNTAX INTEGER
ACCESS read-only
STATUS mandatory
DESCRIPTION
"Specifies the number of octets received in the current or 
previous call."
::= { mdmCsEntry 23 }

mdmCsBlocksSent OBJECT-TYPE
SYNTAX INTEGER
ACCESS read-only
STATUS mandatory
DESCRIPTION
"Specifies the number of blocks sent in the current or 
previous call."
::= { mdmCsEntry 24 }

mdmCsBlocksReceived OBJECT-TYPE
SYNTAX INTEGER
ACCESS read-only
STATUS mandatory
DESCRIPTION
"Specifies the number of blocks received in the current or 
previous call."
::= { mdmCsEntry 25 }

mdmCsBlocksResent OBJECT-TYPE
SYNTAX INTEGER
ACCESS read-only
STATUS mandatory
DESCRIPTION
"Specifies the number of blocks the modem has had to 
retransmit due to block errors or timeouts in the current 
or previous call."
::= { mdmCsEntry 26 }

mdmCsRetrainsRequested OBJECT-TYPE
SYNTAX INTEGER
ACCESS read-only
STATUS mandatory
DESCRIPTION
"Specifies the number of retrains requested in the current 
or previous call."
::= { mdmCsEntry 27 }

mdmCsRetrainsGranted OBJECT-TYPE
SYNTAX INTEGER
ACCESS read-only
STATUS mandatory
DESCRIPTION
"Specifies the number of retrains granted in the current or 
previous call."
::= { mdmCsEntry 28 }

mdmCsLineReversalQty OBJECT-TYPE
SYNTAX INTEGER
ACCESS read-only
STATUS mandatory
DESCRIPTION
"Specifies the number of times the HST high and low speeds 
directions have been reversed in the current or previous 
call."
::= { mdmCsEntry 29 }

mdmCsCharsLost OBJECT-TYPE
SYNTAX INTEGER
ACCESS read-only
STATUS mandatory
DESCRIPTION
"Specifies the number of characters lost on the current or 
previous call.  Not meaningful on synchronous calls."
::= { mdmCsEntry 30 }

mdmCsBackChannelRate OBJECT-TYPE
SYNTAX INTEGER{
  bps450(1),
  bps300(2),
  none(3)
}
ACCESS read-only
STATUS mandatory
DESCRIPTION
"Specifies the negotiated HST back channel speed on the 
current or previous call."
::= { mdmCsEntry 31 }

mdmCsBlerQty OBJECT-TYPE
SYNTAX INTEGER
ACCESS read-only
STATUS mandatory
DESCRIPTION
"Specifies the number of block errors received on the link 
in the current or last call."
::= { mdmCsEntry 32 }

mdmCsLinkTimeoutQty OBJECT-TYPE
SYNTAX INTEGER
ACCESS read-only
STATUS mandatory
DESCRIPTION
"Specifies the number of link protocol timeouts on the 
current or previous call."
::= { mdmCsEntry 33 }

mdmCsFallbackQty OBJECT-TYPE
SYNTAX INTEGER
ACCESS read-only
STATUS mandatory
DESCRIPTION
"Specifies the quantity of link speed fallbacks that occured 
on the current or previous call."
::= { mdmCsEntry 34 }

mdmCsUpshiftQty OBJECT-TYPE
SYNTAX INTEGER
ACCESS read-only
STATUS mandatory
DESCRIPTION
"Specifies the number of link speed upshifts have occured in 
the current or previous call."
::= { mdmCsEntry 35 }

mdmCsLinkNakQty OBJECT-TYPE
SYNTAX INTEGER
ACCESS read-only
STATUS mandatory
DESCRIPTION
"Specifies the quantity of negative acknowledgements sent in 
response to errored blocks received on the link in the 
current or previous call."
::= { mdmCsEntry 36 }

mdmCsGainHitCount OBJECT-TYPE
SYNTAX INTEGER
ACCESS read-only
STATUS mandatory
DESCRIPTION
"The modem calculates the gain that is required to adjust 
the received signal to the ideal level.  This defines the 
number of times that the gain was recalculated durring the 
current or previous call."
::= { mdmCsEntry 37 }

mdmCsSecurityUserName OBJECT-TYPE
SYNTAX DisplayString (SIZE(0..8))
ACCESS read-only
STATUS mandatory
DESCRIPTION
"The last dial security user that initiated the Call. This 
object is not saved to  NVRAM."

::= { mdmCsEntry 38 }

mdmCsCallDuration OBJECT-TYPE
SYNTAX DisplayString (SIZE(0..10))
ACCESS read-only
STATUS mandatory
DESCRIPTION
"This is the length of the call in hh:mm:ss format. The 
maximum value reported will be 9999:59:59."
::= { mdmCsEntry 39 }

mdmCsCallRefNum OBJECT-TYPE
SYNTAX INTEGER
ACCESS read-only
STATUS mandatory
DESCRIPTION
"Call Reference Number"
::= { mdmCsEntry 40 }

mdmCsPriCardSlot OBJECT-TYPE
SYNTAX INTEGER
ACCESS read-only
STATUS mandatory
DESCRIPTION
"Primary Card Slot"
::= { mdmCsEntry 41 }

mdmCsTDMTimeSlot OBJECT-TYPE
SYNTAX INTEGER
ACCESS read-only
STATUS mandatory
DESCRIPTION
"Time Division Multipexing Time Slot"
::= { mdmCsEntry 42 }

mdmCsPriCardSpanLine OBJECT-TYPE
SYNTAX INTEGER
ACCESS read-only
STATUS mandatory
DESCRIPTION
"Primary Card Span Line"
::= { mdmCsEntry 43 }

mdmCsBChannelUsed OBJECT-TYPE
SYNTAX INTEGER
ACCESS read-only
STATUS mandatory
DESCRIPTION
"B Channel Used"
::= { mdmCsEntry 44 }

mdmCsQCarrFreqTx OBJECT-TYPE
SYNTAX INTEGER (0..65535)
ACCESS read-only
STATUS mandatory
DESCRIPTION
"Transmit carrier value (Hz)."
::= { mdmCsEntry 45 }

mdmCsQCarrFreqRx OBJECT-TYPE
SYNTAX INTEGER (0..65535)
ACCESS read-only
STATUS mandatory
DESCRIPTION
"Receive carrier value (Hz)."
::= { mdmCsEntry 46 }

mdmCsQSymRateTx OBJECT-TYPE
SYNTAX INTEGER (0..65535)
ACCESS read-only
STATUS mandatory
DESCRIPTION
"Transmit symbol rate."
::= { mdmCsEntry 47 }

mdmCsQSymRateRx OBJECT-TYPE
SYNTAX INTEGER (0..65535)
ACCESS read-only
STATUS mandatory
DESCRIPTION
"Receive symbol rate."
::= { mdmCsEntry 48 }

mdmCsQTrellisTx OBJECT-TYPE
SYNTAX INTEGER{
  trellis8S-2D(1),
  trellis16S-4D(2),
  trellis32S-2D(3),
  trellis64S-4D(4)
}
ACCESS read-only
STATUS mandatory
DESCRIPTION
"Transmit Trellis coding."
::= { mdmCsEntry 49 }

mdmCsQTrellisRx OBJECT-TYPE
SYNTAX INTEGER{
  trellis8S-2D(1),
  trellis16S-4D(2),
  trellis32S-2D(3),
  trellis64S-4D(4)
}
ACCESS read-only
STATUS mandatory
DESCRIPTION
"Receive Trellis coding."
::= { mdmCsEntry 50 }

mdmCsQNonLinCdTx OBJECT-TYPE
SYNTAX INTEGER{
  off(1),
  on(2)
}
ACCESS read-only
STATUS mandatory
DESCRIPTION
"Status of transmit non-linear coding."
::= { mdmCsEntry 51 }

mdmCsQNonLinCdRx OBJECT-TYPE
SYNTAX INTEGER{
  off(1),
  on(2)
}
ACCESS read-only
STATUS mandatory
DESCRIPTION
"Status of receive non-linear coding."
::= { mdmCsEntry 52 }

mdmCsQPrecodingTx OBJECT-TYPE
SYNTAX INTEGER{
  off(1),
  on(2)
}
ACCESS read-only
STATUS mandatory
DESCRIPTION
"Status of transmit precoding."
::= { mdmCsEntry 53 }

mdmCsQPrecodingRx OBJECT-TYPE
SYNTAX INTEGER{
  off(1),
  on(2)
}
ACCESS read-only
STATUS mandatory
DESCRIPTION
"Status of receive precoding."
::= { mdmCsEntry 54 }

mdmCsQShapingTx OBJECT-TYPE
SYNTAX INTEGER{
  off(1),
  on(2)
}
ACCESS read-only
STATUS mandatory
DESCRIPTION
"Status of transmit shaping."
::= { mdmCsEntry 55 }

mdmCsQShapingRx OBJECT-TYPE
SYNTAX INTEGER{
  off(1),
  on(2)
}
ACCESS read-only
STATUS mandatory
DESCRIPTION
"Status of receive shaping."
::= { mdmCsEntry 56 }

mdmCsQPreemphTx OBJECT-TYPE
SYNTAX INTEGER (0..65535)
ACCESS read-only
STATUS mandatory
DESCRIPTION
"Transmit pre-emphasis (-dBm)."
::= { mdmCsEntry 57 }

mdmCsQPreemphRx OBJECT-TYPE
SYNTAX INTEGER (0..65535)
ACCESS read-only
STATUS mandatory
DESCRIPTION
"Receive pre-emphasis (-dBm)."
::= { mdmCsEntry 58 }

mdmCsQRxLevel OBJECT-TYPE
SYNTAX INTEGER
ACCESS read-only
STATUS mandatory
DESCRIPTION
"Receive level (X 10) (-dBm)."
::= { mdmCsEntry 59 }

mdmCsQTxLevel OBJECT-TYPE
SYNTAX INTEGER
ACCESS read-only
STATUS mandatory
DESCRIPTION
"Transmit level (X 10) (-dBm)."
::= { mdmCsEntry 60 }

mdmCsQSNR OBJECT-TYPE
SYNTAX INTEGER
ACCESS read-only
STATUS mandatory
DESCRIPTION
"Signal to noise (x 10) (dB)."
::= { mdmCsEntry 61 }

mdmCsQNearEcho OBJECT-TYPE
SYNTAX INTEGER
ACCESS read-only
STATUS mandatory
DESCRIPTION
"Near echo (x 10) (dB)."
::= { mdmCsEntry 62 }

mdmCsQFarEcho OBJECT-TYPE
SYNTAX INTEGER
ACCESS read-only
STATUS mandatory
DESCRIPTION
"Far echo (x 10) (dB)."
::= { mdmCsEntry 63 }

mdmCsQRndTripDly OBJECT-TYPE
SYNTAX INTEGER (0..65535)
ACCESS read-only
STATUS mandatory
DESCRIPTION
"Round trip delay (msec)."
::= { mdmCsEntry 64 }

mdmCsQPacketSizeCurr OBJECT-TYPE
SYNTAX INTEGER (0..65535)
ACCESS read-only
STATUS mandatory
DESCRIPTION
"Current packet size (bytes)."
::= { mdmCsEntry 65 }

mdmCsQPacketSizeLow OBJECT-TYPE
SYNTAX INTEGER (0..65535)
ACCESS read-only
STATUS mandatory
DESCRIPTION
"Min. packet size (bytes)."
::= { mdmCsEntry 66 }

mdmCsQPacketSizeHigh OBJECT-TYPE
SYNTAX INTEGER (0..65535)
ACCESS read-only
STATUS mandatory
DESCRIPTION
"Max. packet size (bytes)."
::= { mdmCsEntry 67 }

mdmCsQCellTxLevelCurr OBJECT-TYPE
SYNTAX INTEGER
ACCESS read-only
STATUS mandatory
DESCRIPTION
"Current Tx level cellular (x 10)(-dBm)."
::= { mdmCsEntry 68 }

mdmCsQCellTxLevelLow OBJECT-TYPE
SYNTAX INTEGER
ACCESS read-only
STATUS mandatory
DESCRIPTION
"Min. Tx level cellular (x 10)(-dBm)."
::= { mdmCsEntry 69 }

mdmCsQCellTxLevelHigh OBJECT-TYPE
SYNTAX INTEGER
ACCESS read-only
STATUS mandatory
DESCRIPTION
"Max. Tx level cellular (x 10)(-dBm)."
::= { mdmCsEntry 70 }

mdmCsQSNRLevelCurr OBJECT-TYPE
SYNTAX INTEGER
ACCESS read-only
STATUS mandatory
DESCRIPTION
"Current SNR level cellular (x 10) (-dBm)."
::= { mdmCsEntry 71 }

mdmCsQSNRLevelLow OBJECT-TYPE
SYNTAX INTEGER
ACCESS read-only
STATUS mandatory
DESCRIPTION
"Min. SNR level cellular (x 10) (-dBm)."
::= { mdmCsEntry 72 }

mdmCsQSNRLevelHigh OBJECT-TYPE
SYNTAX INTEGER
ACCESS read-only
STATUS mandatory
DESCRIPTION
"Max. SNR level cellular (x 10) (-dBm)."
::= { mdmCsEntry 73 }

mdmCsQCellularProt OBJECT-TYPE
SYNTAX INTEGER{
  none(1),
  mnp10(2),
  mnp10ec(3),
  v42etc(4)
}
ACCESS read-only
STATUS mandatory
DESCRIPTION
"Current cellular protocol."
::= { mdmCsEntry 74 }

mdmCsFreqProbeData OBJECT-TYPE
SYNTAX OCTET STRING (SIZE(0..60))
ACCESS read-only
STATUS mandatory
DESCRIPTION
"Probe frequency."
::= { mdmCsEntry 75 }

mdmCsLevelProbeData OBJECT-TYPE
SYNTAX OCTET STRING (SIZE(0..30))
ACCESS read-only
STATUS mandatory
DESCRIPTION
"Probe level."
::= { mdmCsEntry 76 }

mdmCsQTimingOffset OBJECT-TYPE
SYNTAX INTEGER (0..65535)
ACCESS read-only
STATUS mandatory
DESCRIPTION
"Timing Offset in parts per million."
::= { mdmCsEntry 77 }

mdmCsQCarrierOffset OBJECT-TYPE
SYNTAX INTEGER (0..65535)
ACCESS read-only
STATUS mandatory
DESCRIPTION
"Carrier Offset in Hertz."
::= { mdmCsEntry 78 }

mdmCsQCoding OBJECT-TYPE
SYNTAX INTEGER{
  mulaw(1),
  alaw(2)
}
ACCESS read-only
STATUS mandatory
DESCRIPTION
"PCM Coding mu/A law Default=mulaw."
::= { mdmCsEntry 80 }

mdmCsTrainingInfo OBJECT-TYPE
SYNTAX OCTET STRING (SIZE(0..255))
ACCESS read-only
STATUS mandatory
DESCRIPTION
"Training Information"
::= { mdmCsEntry 81 }

mdmCsX2signature OBJECT-TYPE
SYNTAX OCTET STRING (SIZE(0..255))
ACCESS read-only
STATUS mandatory
DESCRIPTION
"X2 diagnostics information from modem in hex."
::= { mdmCsEntry 82 }

mdmCsX2Status OBJECT-TYPE
SYNTAX INTEGER{
  x2v90NotOperational(1),
  x2Operational(2),
  v8DisabledLocal(3),
  x2DisabledLocal(4),
  baud3200DisabledLocal(5),
  speedLimitedLocal(6),
  v8notDetectedFromRemote(7),
  x2notDetectedFromRemote(8),
  incompatibleX2Versions(9),
  incompatibleX2Modes(10),
  baud3200DisabledRemote(11),
  excessiveHFAttenuation(12),
  channelNoSymbolRate(13),
  exitBeforeX2Connect(14),
  v90Operational(15),
  x2v90Operational(16),
  v90DisabledLocal(17),
  x2v90DisabledLocal(18),
  v90SymRatesDisabledLcl(19),
  v90NotDetectedFrmRemote(20),
  x2v90NotDetectedFrmRmt(21),
  incompatibleV90Versions(22),
  incompatibleV90Modes(23),
  v90IncompactibleSymRate(24)
}
ACCESS read-only
STATUS mandatory
DESCRIPTION
"x2 status of modem."
::= { mdmCsEntry 83 }

mdmCsCallType OBJECT-TYPE
SYNTAX INTEGER{
  analogCall(1),
  chT1WinkStart(2),
  chT1ImmediateStart(3),
  chT1LoopStart(4),
  chT1GroundStart(5),
  chT1PRICall(6)
}
ACCESS read-only
STATUS mandatory
DESCRIPTION
"Call type information."
::= { mdmCsEntry 84 }

mdmCsCallStartTime OBJECT-TYPE
SYNTAX INTEGER
ACCESS read-only
STATUS mandatory
DESCRIPTION
"Call started time in GMT format."
::= { mdmCsEntry 85 }

mdmCsCallEndTime OBJECT-TYPE
SYNTAX INTEGER
ACCESS read-only
STATUS mandatory
DESCRIPTION
"Call Ended time in GMT format."
::= { mdmCsEntry 86 }

mdmCsDigitalPadAttenuated OBJECT-TYPE
SYNTAX INTEGER (0..255)
ACCESS read-only
STATUS mandatory
DESCRIPTION
"Attenuation of the digital pad in tenths of DB."
::= { mdmCsEntry 87 }

mdmCsInitModulationType OBJECT-TYPE
SYNTAX INTEGER{
  usRoboticsHST(1),
  ccittV32(2),
  ccittV22bis(3),
  bell103(4),
  ccittV21(5),
  bell212(6),
  ccittV32bis(7),
  ccittV23(8),
  noConnection(9),
  bell208b(10),
  v21FaxClass1(11),
  v27FaxClass1(12),
  v29FaxClass1(13),
  v17FaxClass1(14),
  v21FaxClass2(15),
  v27FaxClass2(16),
  v29FaxClass2(17),
  v17FaxClass2(18),
  v32Terbo(19),
  v34(20),
  vFC(21),
  v34plus(22),
  x2server(23),
  v110(24),
  v120(25),
  x75(26),
  asyncSyncPPP(27),
  clearChannel(28),
  x2client(29),
  x2symmetric(30),
  piafs(31),
  x2version2(32),
  v90Analogue(33),
  v90Digital(34),
  v90AllDigital(35)
}
ACCESS read-only
STATUS mandatory
DESCRIPTION
"Specifies the modulation type of the current or last call.  
The value can be different from the object 
mdmCsModulationType only for X2/V.90 calls."
::= { mdmCsEntry 88 }

mdmCsRxMinSpeed OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"Current/Last Session MIN Rx Speed."
::= { mdmCsEntry 89 }

mdmCsRxMaxSpeed OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"Current/Last Session MAX Rx Speed."
::= { mdmCsEntry 90 }

mdmCsTxMinSpeed OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"Current/Last Session MIN Tx Speed."
::= { mdmCsEntry 91 }

mdmCsTxMaxSpeed OBJECT-TYPE
SYNTAX INTEGER{
  bps110(1),
  bps300(2),
  bps600(3),
  bps1200(4),
  bps2400(5),
  bps4800(6),
  bps7200(7),
  bps9600(8),
  bps12K(9),
  bps14K(10),
  bps16K(11),
  bps19K(12),
  bps38K(13),
  bps75(14),
  bps450(15),
  unknown(16),
  bps57K(17),
  bps21K(18),
  bps24K(19),
  bps26K(20),
  bps28K(21),
  bps31K(23),
  bps33K(24),
  bps25333(25),
  bps26666(26),
  bps28000(27),
  bps29333(28),
  bps30666(29),
  bps32000(30),
  bps33333(31),
  bps34666(32),
  bps36000(33),
  bps37333(34),
  bps38666(35),
  bps40000(36),
  bps41333(37),
  bps42666(38),
  bps44000(39),
  bps45333(40),
  bps46666(41),
  bps48000(42),
  bps49333(43),
  bps50666(44),
  bps52000(45),
  bps53333(46),
  bps54666(47),
  bps56000(48),
  bps57333(49),
  bps58666(50),
  bps60000(51),
  bps61333(52),
  bps62666(53),
  bps64000(54)
}
ACCESS read-only
STATUS mandatory
DESCRIPTION
"Current/Last Session MAX Tx Speed."
::= { mdmCsEntry 92 }

mdmCsCollectedDTMFDigits OBJECT-TYPE
SYNTAX OCTET STRING (SIZE(0..64))
ACCESS read-only
STATUS mandatory
DESCRIPTION
"This object is an ASCII array of the DTMF digits collected 
from the client."
::= { mdmCsEntry 93 }

-- The modem Event group

mdmEv OBJECT IDENTIFIER ::= { mdm 10 }

mdmEvTable OBJECT-TYPE
SYNTAX SEQUENCE OF MdmEvEntry
ACCESS not-accessible
STATUS mandatory
DESCRIPTION
"A list of modem events."
::= { mdmEv 1 }

mdmEvEntry OBJECT-TYPE
SYNTAX MdmEvEntry
ACCESS not-accessible
STATUS mandatory
DESCRIPTION
"Modem events that can be managed."
INDEX { mdmEvIndex }
::= { mdmEvTable 1 }

MdmEvEntry ::=
SEQUENCE {
mdmEvIndex
    INTEGER,
mdmEvWatchdogTimouts
    Counter,
mdmEvDteIdleTimouts
    Counter,
mdmEvInConnectEstabs
    Counter,
mdmEvOutConnectEstabs
    Counter,
mdmEvInConnectTerms
    Counter,
mdmEvOutConnectTerms
    Counter,
mdmEvConnectAttemptFails
    Counter,
mdmEvConnectTimouts
    Counter,
mdmEvMgmtBusFailures
    Counter,
mdmEvResetByDtes
    Counter,
mdmEvDtrFalses
    Counter,
mdmEvDtrTrues
    Counter,
mdmEvNoTones
    Counter,
mdmEvNoLoops
    Counter,
mdmEvBlers
    Counter,
mdmEvFallBacks
    Counter,
mdmEvInConnectTime
    Counter,
mdmEvInTotalBytesRx
    Counter,
mdmEvInTotalBytesTx
    Counter,
mdmEvOutConnectTime
    Counter,
mdmEvOutTotalBytesRx
    Counter,
mdmEvOutTotalBytesTx
    Counter,
mdmEvInConnAttemptFails
    Counter,
mdmEvOutConnAttemptFails
    Counter
}

mdmEvIndex OBJECT-TYPE
SYNTAX INTEGER
ACCESS read-only
STATUS mandatory
DESCRIPTION
"Index into event table."
::= { mdmEvEntry 1 }

mdmEvWatchdogTimouts OBJECT-TYPE
SYNTAX Counter
ACCESS read-only
STATUS mandatory
DESCRIPTION
"Quantity of times that a watchdog timeout has been detected 
for this modem."
::= { mdmEvEntry 2 }

mdmEvDteIdleTimouts OBJECT-TYPE
SYNTAX Counter
ACCESS read-only
STATUS mandatory
DESCRIPTION
"The number of times that the modem has had no DTE activity 
for the time specified by mdmEtDteIdleThresh."
::= { mdmEvEntry 3 }

mdmEvInConnectEstabs OBJECT-TYPE
SYNTAX Counter
ACCESS read-only
STATUS mandatory
DESCRIPTION
"The number of times that the modem has reported a incomming 
connection established event."
::= { mdmEvEntry 4 }

mdmEvOutConnectEstabs OBJECT-TYPE
SYNTAX Counter
ACCESS read-only
STATUS mandatory
DESCRIPTION
"The number of times that the modem has reported an outgoing 
connection established event."
::= { mdmEvEntry 5 }

mdmEvInConnectTerms OBJECT-TYPE
SYNTAX Counter
ACCESS read-only
STATUS mandatory
DESCRIPTION
"The number of times the modem has reported an incomming 
connection terminated event."
::= { mdmEvEntry 6 }

mdmEvOutConnectTerms OBJECT-TYPE
SYNTAX Counter
ACCESS read-only
STATUS mandatory
DESCRIPTION
"The number of times the modem has reported an outgoing 
connection termination event."
::= { mdmEvEntry 7 }

mdmEvConnectAttemptFails OBJECT-TYPE
SYNTAX Counter
ACCESS read-only
STATUS mandatory
DESCRIPTION
"The number of times the modem has reported a connect 
attempt failure event.  This does not include those connect 
attempt failures that are reported due to no dial tone and 
no loop current."
::= { mdmEvEntry 8 }

mdmEvConnectTimouts OBJECT-TYPE
SYNTAX Counter
ACCESS read-only
STATUS mandatory
DESCRIPTION
"The number of times that the NMC has detected a call that 
has has a duration in excess of the threshold defined in 
mdmEtConnectThresh."

::= { mdmEvEntry 9 }

mdmEvMgmtBusFailures OBJECT-TYPE
SYNTAX Counter
ACCESS read-only
STATUS mandatory
DESCRIPTION
"The number of times the NMC has been unable to get a 
response from the modem to requests on the management bus."
::= { mdmEvEntry 10 }

mdmEvResetByDtes OBJECT-TYPE
SYNTAX Counter
ACCESS read-only
STATUS mandatory
DESCRIPTION
"The number of times that the modem has been reset by the 
DTE via the ATZ command or by DTR drop."
::= { mdmEvEntry 11 }

mdmEvDtrFalses OBJECT-TYPE
SYNTAX Counter
ACCESS read-only
STATUS mandatory
DESCRIPTION
"The number of times the modem has reported DTR False 
events.  The DTR false event timeout is based on 
mdmEtDtrFalseThresh."
::= { mdmEvEntry 12 }

mdmEvDtrTrues OBJECT-TYPE
SYNTAX Counter
ACCESS read-only
STATUS mandatory
DESCRIPTION
"The number of times the modem has reported DTR True events. 
 The modem reports these events to the NMC based on the 
value of mdmEtDtrTrueTresh."
::= { mdmEvEntry 13 }

mdmEvNoTones OBJECT-TYPE
SYNTAX Counter
ACCESS read-only
STATUS mandatory
DESCRIPTION
"The number of times the modem reported no tones."
::= { mdmEvEntry 14 }

mdmEvNoLoops OBJECT-TYPE
SYNTAX Counter
ACCESS read-only
STATUS mandatory
DESCRIPTION
"The number of times the modem reported no loop current 
events."
::= { mdmEvEntry 15 }

mdmEvBlers OBJECT-TYPE
SYNTAX Counter
ACCESS read-only
STATUS mandatory
DESCRIPTION
"The number of times the modem reported BLERs."
::= { mdmEvEntry 16 }

mdmEvFallBacks OBJECT-TYPE
SYNTAX Counter
ACCESS read-only
STATUS mandatory
DESCRIPTION
"The number of times the modem reported fall backs."
::= { mdmEvEntry 17 }

mdmEvInConnectTime OBJECT-TYPE
SYNTAX Counter
ACCESS read-only
STATUS mandatory
DESCRIPTION
"Cumulative counter for inbound call connect time."
::= { mdmEvEntry 18 }

mdmEvInTotalBytesRx OBJECT-TYPE
SYNTAX Counter
ACCESS read-only
STATUS mandatory
DESCRIPTION
"Cumulative counter for number of bytes received on inbound 
calls."
::= { mdmEvEntry 19 }

mdmEvInTotalBytesTx OBJECT-TYPE
SYNTAX Counter
ACCESS read-only
STATUS mandatory
DESCRIPTION
"Cumulative counter for number of bytes transmitted on 
inbound calls."
::= { mdmEvEntry 20 }

mdmEvOutConnectTime OBJECT-TYPE
SYNTAX Counter
ACCESS read-only
STATUS mandatory
DESCRIPTION
"Cumulative counter for outbound call connect time."
::= { mdmEvEntry 21 }

mdmEvOutTotalBytesRx OBJECT-TYPE
SYNTAX Counter
ACCESS read-only
STATUS mandatory
DESCRIPTION
"Cumulative counter for number of bytes received on outbound 
calls."
::= { mdmEvEntry 22 }

mdmEvOutTotalBytesTx OBJECT-TYPE
SYNTAX Counter
ACCESS read-only
STATUS mandatory
DESCRIPTION
"Cumulative counter for number of bytes transmitted on 
outbound calls."
::= { mdmEvEntry 23 }

mdmEvInConnAttemptFails OBJECT-TYPE
SYNTAX Counter
ACCESS read-only
STATUS mandatory
DESCRIPTION
"The number of times the modem has reported a inbound 
connect attempt failure event. This does not include those 
connect attempt failues that are reported due to no dial 
time and no loop current."
::= { mdmEvEntry 24 }

mdmEvOutConnAttemptFails OBJECT-TYPE
SYNTAX Counter
ACCESS read-only
STATUS mandatory
DESCRIPTION
"The number of times the modem has reported a outbound 
connect attempt failure event. This does not include those 
connect attempt failures that are reported due to no dial 
tone and no loop current."
::= { mdmEvEntry 25 }

-- The modem Event Threshold group

mdmEt OBJECT IDENTIFIER ::= { mdm 11 }

mdmEtTable OBJECT-TYPE
SYNTAX SEQUENCE OF MdmEtEntry
ACCESS not-accessible
STATUS mandatory
DESCRIPTION
"Table of event thresholds used for setting up the modem to 
report events that can in turn be monitored by RMON."
::= { mdmEt 1 }

mdmEtEntry OBJECT-TYPE
SYNTAX MdmEtEntry
ACCESS not-accessible
STATUS mandatory
DESCRIPTION
"Event Thresholds that are used by the modem and the NMC to 
qualify certain events."
INDEX { mdmEtIndex }
::= { mdmEtTable 1 }

MdmEtEntry ::=
SEQUENCE {
mdmEtIndex
    INTEGER,
mdmEtDteIdleThresh
    INTEGER,
mdmEtDtrFalseThresh
    INTEGER,
mdmEtDtrTrueThresh
    INTEGER,
mdmEtConnTimeLimit
    INTEGER,
mdmEtBlerThresh
    INTEGER,
mdmEtFallbackThresh
    INTEGER
}

mdmEtIndex OBJECT-TYPE
SYNTAX INTEGER
ACCESS read-only
STATUS mandatory
DESCRIPTION
"Index into table used to identify the the specific modem, 
contians the unique value from the chassis mib entity 
table."
::= { mdmEtEntry 1 }

mdmEtDteIdleThresh OBJECT-TYPE
SYNTAX INTEGER (0..255)
ACCESS read-write
STATUS mandatory
DESCRIPTION
"Defines the length of time for the modem to wait before 
reporting a 'DTE transmit data idle' event.  (There must be 
no activity on the DTE transmit line for the specified 
quantity of minutes."
::= { mdmEtEntry 2 }

mdmEtDtrFalseThresh OBJECT-TYPE
SYNTAX INTEGER (0..255)
ACCESS read-write
STATUS mandatory
DESCRIPTION
"Defines the quantity of seconds that will be used by the 
modem to qualify a 'DTR False' event."
::= { mdmEtEntry 3 }

mdmEtDtrTrueThresh OBJECT-TYPE
SYNTAX INTEGER (0..255)
ACCESS read-write
STATUS mandatory
DESCRIPTION
"Defines the quantity of seconds that the modem will use to 
qualify a 'DTR True' event."
::= { mdmEtEntry 4 }

mdmEtConnTimeLimit OBJECT-TYPE
SYNTAX INTEGER (0..255)
ACCESS read-write
STATUS mandatory
DESCRIPTION
"Defines the number of minutes that a call may be connected 
before triggering the 'connect timer limit' event.  A value 
of zero for this limit means that no event is to be 
detected (ie. no time limit)."
::= { mdmEtEntry 5 }

mdmEtBlerThresh OBJECT-TYPE
SYNTAX INTEGER (0..255)
ACCESS read-write
STATUS mandatory
DESCRIPTION
"Defines the number of BLERs that will be used to qualify 
the 'BLER count at threshold' event for a given call."
::= { mdmEtEntry 6 }

mdmEtFallbackThresh OBJECT-TYPE
SYNTAX INTEGER (0..255)
ACCESS read-write
STATUS mandatory
DESCRIPTION
"Defines the number of fallbacks at which the 'fallback 
count at threshold' event will be generated for a given 
call."
::= { mdmEtEntry 7 }

-- The modem Command group

mdmCd OBJECT IDENTIFIER ::= { mdm 12 }

mdmCdTable OBJECT-TYPE
SYNTAX SEQUENCE OF MdmCdEntry
ACCESS not-accessible
STATUS mandatory
DESCRIPTION
"The command table contains an entry for each modem 
installed in a chassis.  It provides a means for processing 
actions requested by the management console.  The mechanism 
used is to set the command and get the result which will 
indicate the success of the request."
::= { mdmCd 1 }

mdmCdEntry OBJECT-TYPE
SYNTAX MdmCdEntry
ACCESS not-accessible
STATUS mandatory
DESCRIPTION
"Objects that are used to request that certain actions be 
taken by the modem itself or that the NMC take certain 
actions for the modem."
INDEX { mdmCdIndex }
::= { mdmCdTable 1 }

MdmCdEntry ::=
SEQUENCE {
mdmCdIndex
    INTEGER,
mdmCdMgtStationId
    OCTET STRING,
mdmCdReqId
    INTEGER,
mdmCdFunction
    INTEGER,
mdmCdForce
    INTEGER,
mdmCdParam
    OCTET STRING,
mdmCdResult
    INTEGER,
mdmCdCode
    INTEGER
}

mdmCdIndex OBJECT-TYPE
SYNTAX INTEGER
ACCESS read-only
STATUS mandatory
DESCRIPTION
"The index value which uniquely identifies the modem to 
which this entry is applicable.  The value corresponds to 
the index of the corresponding modem in the entity table of 
the chassis MIB."
::= { mdmCdEntry 1 }

mdmCdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with uchasCmdReqId and 
uchasCmdResult to detect interference from other MSs."
::= { mdmCdEntry 2 }

mdmCdReqId OBJECT-TYPE
SYNTAX INTEGER
ACCESS read-write
STATUS mandatory
DESCRIPTION
"This object contains the value of the request-id field in 
the SNMP PDU which invoked the most recent command or test 
on this modem.  If the request-id is unknown or undefined, 
this object contains the value zero."
::= { mdmCdEntry 3 }

mdmCdFunction OBJECT-TYPE
SYNTAX INTEGER{
  noCommand(1),
  softwareReset(2),
  storeToNvram(3),
  restoreFromDflt(4),
  restoreFromNvram(5),
  offHook(6),
  onHook(7),
  sndTone(8),
  rcvTone(9),
  endTest(10),
  rspndrTest105(11),
  rspndrTest102(12),
  lclAnlgLpbk(13),
  lclDgtlLpbk(14),
  rmtDgtlLpbk(15),
  selfTest(16),
  testRam(17),
  testRom(18),
  testNVRAM(19),
  v54LclAnlgLpbk(20),
  v54RmtDgtlLpbk(21),
  idlePhoneLine(22),
  loadHwFlowDflt(23),
  loadSwFlowDflt(24),
  loadMnp10CllulrDflt(25),
  loadV42CllulrMblDflt(26),
  loadV42CllulrFxdDflt(27),
  hardBusyAtDisable(33),
  softBusyAtDisable(34),
  restoreLineAt(35)
}
ACCESS read-write
STATUS mandatory
DESCRIPTION
"This object contains a value that describes the command 
that is being invoked."
::= { mdmCdEntry 4 }

mdmCdForce OBJECT-TYPE
SYNTAX INTEGER{
  force(1),
  noForce(2)
}
ACCESS read-write
STATUS mandatory
DESCRIPTION
"In certain cases the modem may be in 
a state where certain 
commands could adversely affect connectiuons.  In such 
cases, a command request with this object not present or 
set to noForce will result in a warning.  If the operator 
elects to ignore such warnings, this object can be set to 
force in a subsequent request to cause the command to be 
carried out regardless of the potetialy hazzerdous effect."
::= { mdmCdEntry 5 }

mdmCdParam OBJECT-TYPE
SYNTAX OCTET STRING (SIZE(0..24))
ACCESS read-write
STATUS mandatory
DESCRIPTION
"This object can contain parameters that are specific to the 
particualar command being issued."
::= { mdmCdEntry 6 }

mdmCdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1)  if no 
commands have been requested since last reset."
::= { mdmCdEntry 7 }

mdmCdCode OBJECT-TYPE
SYNTAX INTEGER{
  noError(1),
  unable(2),
  unrecognizedCommand(6),
  slotEmpty(8),
  noResponse(12),
  notConnected(13),
  connected(14),
  onLine(17),
  unsupportedCommand(20),
  deviceDisabled(22),
  deviceInTestMode(24),
  testFailed(25),
  deviceInSecurityMode(31),
  noRTS(51),
  noDTR(52),
  wrongLoopbackSpeed(53),
  noLoopbackInARQ(54),
  pendingSoftwareDownload(73),
  invalidFrequency(89),
  noLoopCurrent(90),
  noDialTone(91),
  noLineDetected(92)
}
ACCESS read-only
STATUS mandatory
DESCRIPTION
"The value of this object 
indicates a further description 
of what went wrong when a command fails." 
::= { mdmCdEntry 8 }

mdmTe OBJECT IDENTIFIER ::= { mdm 13 }

mdmTeTable OBJECT-TYPE
SYNTAX SEQUENCE OF MdmTeEntry
ACCESS not-accessible
STATUS mandatory
DESCRIPTION
"A table containing an enable for each trap that a modem 
entity is capable of generating.  Some of these events 
occur often and traps may flood the network if care is not 
taken to avoid such conditions.  These traps should be 
enabled sparingly. (usually only when debugging a problem 
on a particular modem)"
::= { mdmTe 1 }

mdmTeEntry OBJECT-TYPE
SYNTAX MdmTeEntry
ACCESS not-accessible
STATUS mandatory
DESCRIPTION
"There is one modem trap enable row for each modem entity in 
the NAS chassis."
INDEX { mdmTeIndex }
::= { mdmTeTable 1 }

MdmTeEntry ::=
SEQUENCE {
mdmTeIndex
    INTEGER,
mdmTeInConnEstablished
    INTEGER,
mdmTeOutConnEstablished
    INTEGER,
mdmTeInConnTerminated
    INTEGER,
mdmTeOutConnTerminated
    INTEGER,
mdmTeConnAttemptFailure
    INTEGER,
mdmTeConnLimitExpired
    INTEGER,
mdmTeDteXmitDataIdle
    INTEGER,
mdmTeDtrTrue
    INTEGER,
mdmTeDtrFalse
    INTEGER,
mdmTeBlerCountAtThresh
    INTEGER,
mdmTeFallbkCountAtThresh
    INTEGER,
mdmTeNoDialTone
    INTEGER,
mdmTeNoLoopCurrent
    INTEGER,
mdmTeResetByDTE
    INTEGER,
mdmTeDialOutCallDur
    INTEGER,
mdmTeDialInCallDur
    INTEGER,
mdmTePbActive
    INTEGER,
mdmTePbLost
    INTEGER,
mdmTeDteRingNoAns
    INTEGER,
mdmTePbClockLossEvent
    INTEGER,
mdmTePbClockRestoreEvent
    INTEGER,
mdmTeInConnAttemptFail
    INTEGER,
mdmTeOutConnAttemptFail
    INTEGER,
mdmTe105ResponderTest
    INTEGER
}

mdmTeIndex OBJECT-TYPE
SYNTAX INTEGER
ACCESS read-only
STATUS mandatory
DESCRIPTION
"A unique index which identifies the modem for which these 
trap enables pertain.  The index to the trap enable table 
matches the index of the corresponding modem in the entity 
table in the chassis MIB."
::= { mdmTeEntry 1 }

mdmTeInConnEstablished OBJECT-TYPE
SYNTAX INTEGER{
  enableTrap(1),
  disableAll(2),
  enableLog(3),
  enableAll(4)
}
ACCESS read-write
STATUS mandatory
DESCRIPTION
"Enables generation of an SNMP trap upon detection of an 
incoming connection establishment on the specified modem."
::= { mdmTeEntry 2 }

mdmTeOutConnEstablished OBJECT-TYPE
SYNTAX INTEGER{
  enableTrap(1),
  disableAll(2),
  enableLog(3),
  enableAll(4)
}
ACCESS read-write
STATUS mandatory
DESCRIPTION
"Enables generation of an SNMP trap upon detection of an 
outgoing connection establishment on the specified modem."
::= { mdmTeEntry 3 }

mdmTeInConnTerminated OBJECT-TYPE
SYNTAX INTEGER{
  enableTrap(1),
  disableAll(2),
  enableLog(3),
  enableAll(4)
}
ACCESS read-write
STATUS mandatory
DESCRIPTION
"Enables generation of an SNMP trap upon detection of an 
incoming connection termination on the specified modem."
::= { mdmTeEntry 4 }

mdmTeOutConnTerminated OBJECT-TYPE
SYNTAX INTEGER{
  enableTrap(1),
  disableAll(2),
  enableLog(3),
  enableAll(4)
}
ACCESS read-write
STATUS mandatory
DESCRIPTION
"Enables generation of an SNMP trap upon detection of an 
outgoing connection terminated on the specified modem."
::= { mdmTeEntry 5 }

mdmTeConnAttemptFailure OBJECT-TYPE
SYNTAX INTEGER{
  enableTrap(1),
  disableAll(2),
  enableLog(3),
  enableAll(4)
}
ACCESS read-write
STATUS mandatory
DESCRIPTION
"Enables generation of an SNMP trap upon detection of a 
connection attemp failure on the specified modem."
::= { mdmTeEntry 6 }

mdmTeConnLimitExpired OBJECT-TYPE
SYNTAX INTEGER{
  enableTrap(1),
  disableAll(2),
  enableLog(3),
  enableAll(4)
}
ACCESS read-write
STATUS mandatory
DESCRIPTION
"Enables generation of an SNMP trap upon detection of the 
expiration of the connection time limit on the specified 
modem."
::= { mdmTeEntry 7 }

mdmTeDteXmitDataIdle OBJECT-TYPE
SYNTAX INTEGER{
  enableTrap(1),
  disableAll(2),
  enableLog(3),
  enableAll(4)
}
ACCESS read-write
STATUS mandatory
DESCRIPTION
"Enables generation of an SNMP trap upon detection of DTE 
transmit data idle on the specified modem."
::= { mdmTeEntry 8 }

mdmTeDtrTrue OBJECT-TYPE
SYNTAX INTEGER{
  enableTrap(1),
  disableAll(2),
  enableLog(3),
  enableAll(4)
}
ACCESS read-write
STATUS mandatory
DESCRIPTION
"Enables generation of an SNMP trap upon detection of DTR 
going true on the specified modem."
::= { mdmTeEntry 9 }

mdmTeDtrFalse OBJECT-TYPE
SYNTAX INTEGER{
  enableTrap(1),
  disableAll(2),
  enableLog(3),
  enableAll(4)
}
ACCESS read-write
STATUS mandatory
DESCRIPTION
"Enables generation of an SNMP trap upon detection of DTR 
going false on the specified modem."
::= { mdmTeEntry 10 }

mdmTeBlerCountAtThresh OBJECT-TYPE
SYNTAX INTEGER{
  enableTrap(1),
  disableAll(2),
  enableLog(3),
  enableAll(4)
}
ACCESS read-write
STATUS mandatory
DESCRIPTION
"Enables generation of an SNMP trap upon detection of the 
BLER count at the specified threshold on the specified 
modem."
::= { mdmTeEntry 11 }

mdmTeFallbkCountAtThresh OBJECT-TYPE
SYNTAX INTEGER{
  enableTrap(1),
  disableAll(2),
  enableLog(3),
  enableAll(4)
}
ACCESS read-write
STATUS mandatory
DESCRIPTION
"Enables generation of an SNMP trap upon detection of the 
fallback count at the specified threshold on the specified 
modem."
::= { mdmTeEntry 12 }

mdmTeNoDialTone OBJECT-TYPE
SYNTAX INTEGER{
  enableTrap(1),
  disableAll(2),
  enableLog(3),
  enableAll(4)
}
ACCESS read-write
STATUS mandatory
DESCRIPTION
"Enables generation of an SNMP trap upon detection of no 
dial tone on the specified modem."
::= { mdmTeEntry 13 }

mdmTeNoLoopCurrent OBJECT-TYPE
SYNTAX INTEGER{
  enableTrap(1),
  disableAll(2),
  enableLog(3),
  enableAll(4)
}
ACCESS read-write
STATUS mandatory
DESCRIPTION
"Enables generation of an SNMP trap upon detection of no 
loop current on the specified modem."
::= { mdmTeEntry 14 }

mdmTeResetByDTE OBJECT-TYPE
SYNTAX INTEGER{
  enableTrap(1),
  disableAll(2),
  enableLog(3),
  enableAll(4)
}
ACCESS read-write
STATUS mandatory
DESCRIPTION
"Enables generation of an SNMP trap upon detection of reset 
by DTE on the specified modem."
::= { mdmTeEntry 15 }

mdmTeDialOutCallDur OBJECT-TYPE
SYNTAX INTEGER{
  enableTrap(1),
  disableAll(2),
  enableLog(3),
  enableAll(4)
}
ACCESS read-write
STATUS mandatory
DESCRIPTION
"Enables the dial out (from the NMC) call duration trap. 
Default = disable(2)."
::= { mdmTeEntry 16 }

mdmTeDialInCallDur OBJECT-TYPE
SYNTAX INTEGER{
  enableTrap(1),
  disableAll(2),
  enableLog(3),
  enableAll(4)
}
ACCESS read-write
STATUS mandatory
DESCRIPTION
"Enables the dial in (to the NMC) call duration trap. 
Default = disable(2)."
::= { mdmTeEntry 17 }

mdmTePbActive OBJECT-TYPE
SYNTAX INTEGER{
  enableTrap(1),
  disableAll(2),
  enableLog(3),
  enableAll(4)
}
ACCESS read-write
STATUS optional
DESCRIPTION
"Enables the Packet Bus Active. Default = disable(2)."
::= { mdmTeEntry 18 }

mdmTePbLost OBJECT-TYPE
SYNTAX INTEGER{
  enableTrap(1),
  disableAll(2),
  enableLog(3),
  enableAll(4)
}
ACCESS read-write
STATUS optional
DESCRIPTION
"Enables the Packet Bus Lost trap. Default = disable(2)."
::= { mdmTeEntry 19 }

mdmTeDteRingNoAns OBJECT-TYPE
SYNTAX INTEGER{
  enableTrap(1),
  disableAll(2),
  enableLog(3),
  enableAll(4)
}
ACCESS read-write
STATUS optional
DESCRIPTION
"Enables the Dte Ring No Answer trap. Default = disable(2)."
::= { mdmTeEntry 20 }

mdmTePbClockLossEvent OBJECT-TYPE
SYNTAX INTEGER{
  enableTrap(1),
  disableAll(2),
  enableLog(3),
  enableAll(4)
}
ACCESS read-write
STATUS mandatory
DESCRIPTION
"This object is used to disable the ability for a NAC to 
report when the packet bus clock has been lost.  Default = 
disableAll(2)."
::= { mdmTeEntry 21 }

mdmTePbClockRestoreEvent OBJECT-TYPE
SYNTAX INTEGER{
  enableTrap(1),
  disableAll(2),
  enableLog(3),
  enableAll(4)
}
ACCESS read-write
STATUS mandatory
DESCRIPTION
"This object is used to disable the ability for a NAC to 
report when the packet bus clock has been restored.  
Default = disableAll(2)."
::= { mdmTeEntry 22 }

mdmTeInConnAttemptFail OBJECT-TYPE
SYNTAX INTEGER{
  enableTrap(1),
  disableAll(2),
  enableLog(3),
  enableAll(4)
}
ACCESS read-write
STATUS mandatory
DESCRIPTION
"Enables generation of a SNMP trap upon detection of an 
inbound connection attempt failure on the specified modem."
::= { mdmTeEntry 23 }

mdmTeOutConnAttemptFail OBJECT-TYPE
SYNTAX INTEGER{
  enableTrap(1),
  disableAll(2),
  enableLog(3),
  enableAll(4)
}
ACCESS read-write
STATUS mandatory
DESCRIPTION
"Enables generation of a SNMP trap upon detection of an 
outbound connection attempt failure on the specified modem."
::= { mdmTeEntry 24 }

mdmTe105ResponderTest OBJECT-TYPE
SYNTAX INTEGER{
  enableTrap(1),
  disableAll(2),
  enableLog(3),
  enableAll(4)
}
ACCESS read-write
STATUS mandatory
DESCRIPTION
"Enables generation of a SNMP trap upon detection of a 105 
responder test on the specified modem."
::= { mdmTeEntry 25 }

-- The modem Link Security group.

mdmLs OBJECT IDENTIFIER ::= { mdm 14 }

mdmLsTable OBJECT-TYPE
SYNTAX SEQUENCE OF MdmLsTableEntry
ACCESS not-accessible
STATUS mandatory
DESCRIPTION
"A table defining all the Link Security parameters for each 
modem in the chassis."
::= { mdmLs 1 }

mdmLsTableEntry OBJECT-TYPE
SYNTAX MdmLsTableEntry
ACCESS not-accessible
STATUS mandatory
DESCRIPTION
"Link Security parameters for a modem. These define the link 
level security operations which take place when a call is 
negotiated."
INDEX { mdmLsIndex }
::= { mdmLsTable 1 }

MdmLsTableEntry ::=
SEQUENCE {
mdmLsIndex
    INTEGER,
mdmLsSecurityEnable
    INTEGER,
mdmLsFallbackPromptEnable
    INTEGER,
mdmLsForcePromptEnable
    INTEGER,
mdmLsLocAccPasswdEnable
    INTEGER,
mdmLsDialBackEnable
    INTEGER,
mdmLsAutoPassPasswd
    DisplayString,
mdmLsLocalAccessPasswd
    DisplayString,
mdmLsAccountPasswd
    DisplayString
}

mdmLsIndex OBJECT-TYPE
SYNTAX INTEGER
ACCESS read-only
STATUS mandatory
DESCRIPTION
"The index which uniquely identifies the modem to which this 
entry is applicable. The value corresponds to the value of 
the index to the entity table in the chassis MIB that 
corresponds to the same modem."
::= { mdmLsTableEntry 1 }

mdmLsSecurityEnable OBJECT-TYPE
SYNTAX INTEGER{
  disable(1),
  enable(2)
}
ACCESS read-write
STATUS mandatory
DESCRIPTION
"Allows to disable/enable the dial security feature for the 
modem."
::= { mdmLsTableEntry 2 }

mdmLsFallbackPromptEnable OBJECT-TYPE
SYNTAX INTEGER{
  disable(1),
  enable(2)
}
ACCESS read-write
STATUS mandatory
DESCRIPTION
"Disables/enables the prompting by the called modem when the 
auto pass password supplied by the caller fails or if no 
password is supplied at all."
::= { mdmLsTableEntry 3 }

mdmLsForcePromptEnable OBJECT-TYPE
SYNTAX INTEGER{
  disable(1),
  enable(2)
}
ACCESS read-write
STATUS mandatory
DESCRIPTION
"If this is enabled, the modem will prompt the remote user 
for a password regardless of the success of the modem to 
negotiate the auto pass password."
::= { mdmLsTableEntry 4 }

mdmLsLocAccPasswdEnable OBJECT-TYPE
SYNTAX INTEGER{
  disable(1),
  enable(2)
}
ACCESS read-write
STATUS mandatory
DESCRIPTION
"Disables/enables the Local Access Password feature used to 
establish security check when accessing any security 
setting."
::= { mdmLsTableEntry 5 }

mdmLsDialBackEnable OBJECT-TYPE
SYNTAX INTEGER{
  disable(1),
  enable(2)
}
ACCESS read-write
STATUS mandatory
DESCRIPTION
"If this is set to enable the modem, after successful 
password validation, will disconnect and dial out to the 
originating modem."
::= { mdmLsTableEntry 6 }

mdmLsAutoPassPasswd OBJECT-TYPE
SYNTAX DisplayString (SIZE(0..8))
ACCESS read-write
STATUS mandatory
DESCRIPTION
"Contains the Auto Pass Password used for establishing Link 
security during call negotiation."
::= { mdmLsTableEntry 7 }

mdmLsLocalAccessPasswd OBJECT-TYPE
SYNTAX DisplayString (SIZE(0..8))
ACCESS read-write
STATUS mandatory
DESCRIPTION
"Contains the Local Access password used when accessing any 
security setting and when Local Access password feature is 
enabled."
::= { mdmLsTableEntry 8 }

mdmLsAccountPasswd OBJECT-TYPE
SYNTAX DisplayString (SIZE(0..8))
ACCESS read-write
STATUS mandatory
DESCRIPTION
"Contains the fall back password which must be entered if 
auto pass password is not satisfied."
::= { mdmLsTableEntry 9 }

-- The Modem Hub Security Group

mdmHs OBJECT IDENTIFIER ::= { mdm 15 }

mdmHsTable OBJECT-TYPE
SYNTAX SEQUENCE OF MdmHsEntry
ACCESS not-accessible
STATUS optional
DESCRIPTION
"A table containing the Hub security parameters accessible 
in the modem."
::= { mdmHs 1 }

mdmHsEntry OBJECT-TYPE
SYNTAX MdmHsEntry
ACCESS not-accessible
STATUS optional
DESCRIPTION
"There is one entry in this table for each modem entity 
found in the chassis mib entity table."
INDEX { mdmHsIndex }
::= { mdmHsTable 1 }

MdmHsEntry ::=
SEQUENCE {
mdmHsIndex
    INTEGER,
mdmHsDialInEnable
    INTEGER,
mdmHsDialOutEnable
    INTEGER,
mdmHsDtrDcdDelay
    INTEGER,
mdmHsDtrDsrDelay
    INTEGER
}

mdmHsIndex OBJECT-TYPE
SYNTAX INTEGER
ACCESS read-only
STATUS optional
DESCRIPTION
"An index that uniquely identifies the modem to which this 
row in the Hub Security table pertains.  The value of this 
index matches the value of the index for the corresonding 
entity in the entity table of the Chassis MIB."
::= { mdmHsEntry 1 }

mdmHsDialInEnable OBJECT-TYPE
SYNTAX INTEGER{
  disable(1),
  allowNoNMC(2),
  refuseNoNMC(3),
  busyOutNoNMC(4)
}
ACCESS read-write
STATUS optional
DESCRIPTION
"Allows the modem to be configured for dial-in security. 
Enabling this effectively disables the modem's built-in 
Link security operation.  The default for this object is 
disabled."
::= { mdmHsEntry 2 }

mdmHsDialOutEnable OBJECT-TYPE
SYNTAX INTEGER{
  disable(1),
  refuseNoNMC(2),
  allowNoNMC(3)
}
ACCESS read-write
STATUS optional
DESCRIPTION
"Allows modems to be configured for dial-out security.  
Enabling this effectively disables the modem's built-in 
link security operation.  The default value for this object 
is disabled."
::= { mdmHsEntry 3 }

mdmHsDtrDcdDelay OBJECT-TYPE
SYNTAX INTEGER (0..255)
ACCESS read-write
STATUS optional
DESCRIPTION
"Allows configuration of the time delay (in 100ths of a 
second) between reciept of DTR and assertion of DCD when 
the user on an incomming security call has successfully 
compleated the security dialog.  This object only applies 
to modems using an RS232 like interface."
::= { mdmHsEntry 4 }

mdmHsDtrDsrDelay OBJECT-TYPE
SYNTAX INTEGER (0..255)
ACCESS read-write
STATUS optional
DESCRIPTION
"Allows configuration of the delay (in 100ths of a second) 
between detection of DTR and assertion of DSR when an 
incomming security call has completed security negotiation 
successfully."
::= { mdmHsEntry 5 }

mdmAutoResponse OBJECT IDENTIFIER ::= { mdm 16 }

mdmArTable OBJECT-TYPE
SYNTAX SEQUENCE OF MdmArEntry
ACCESS not-accessible
STATUS optional
DESCRIPTION
"Table of auto response scripts for each modem in the 
chassis. The number of table entries is specified by 
modemNumber."
::= { mdmAutoResponse 1 }

mdmArEntry OBJECT-TYPE
SYNTAX MdmArEntry
ACCESS not-accessible
STATUS optional
DESCRIPTION
"List of configurable auto response scripts."
INDEX { mdmArIndex }
::= { mdmArTable 1 }

MdmArEntry ::=
SEQUENCE {
mdmArIndex
    INTEGER,
mdmArIncomConnectEstab
    OCTET STRING,
mdmArOutgoConnectEstab
    OCTET STRING,
mdmArIncomConnectTerm
    OCTET STRING,
mdmArOutgoConnectTerm
    OCTET STRING,
mdmArConnectAttemptFail
    OCTET STRING,
mdmArConnectTimeExpire
    OCTET STRING,
mdmArResetByDte
    OCTET STRING,
mdmArDteXmitIdle
    OCTET STRING,
mdmArBlersAtThresh
    OCTET STRING,
mdmArFbacksAtThresh
    OCTET STRING,
mdmArDialOutLoginFail
    OCTET STRING,
mdmArDialOutRestrNum
    OCTET STRING,
mdmArDialInLoginFail
    OCTET STRING,
mdmArDialBackRestrNum
    OCTET STRING,
mdmArDialBackRestModem
    OCTET STRING,
mdmArLoginAttemptsExceed
    OCTET STRING,
mdmArUserBlacklisted
    OCTET STRING,
mdmArAttmpLoginByBlistUsr
    OCTET STRING,
mdmArRspAttemptLimExceed
    OCTET STRING,
mdmArWatchdog
    OCTET STRING,
mdmArMgtBusFailure
    OCTET STRING,
mdmArDtrTrue
    OCTET STRING,
mdmArDtrFalse
    OCTET STRING,
mdmArMdmRingNoAnswer
    OCTET STRING,
mdmArDteRingNoAnswer
    OCTET STRING,
mdmArNoDialTone
    OCTET STRING,
mdmArNoLoopCurrent
    OCTET STRING,
mdmArTimer1
    OCTET STRING,
mdmArTimer2
    OCTET STRING,
mdmArTimer3
    OCTET STRING,
mdmArTimer4
    OCTET STRING,
mdmArPacketBusActive
    OCTET STRING,
mdmArPacketBusLost
    OCTET STRING
}

mdmArIndex OBJECT-TYPE
SYNTAX INTEGER
ACCESS read-only
STATUS optional
DESCRIPTION
"Index in to the auto response table. This index contains 
the unique value associated with the modem as defined in 
the chassis mib entity table."
::= { mdmArEntry 1 }

mdmArIncomConnectEstab OBJECT-TYPE
SYNTAX OCTET STRING (SIZE(0..40))
ACCESS read-write
STATUS optional
DESCRIPTION
"This script is triggered when a Total Control WAN HUB modem 
establishes a connection with a remote modem. The remote 
modem is the caller."
::= { mdmArEntry 2 }

mdmArOutgoConnectEstab OBJECT-TYPE
SYNTAX OCTET STRING (SIZE(0..40))
ACCESS read-write
STATUS optional
DESCRIPTION
"This script is triggered when a Total Control WAN HUB modem 
establishes a connection with a remote modem. The Total 
Control WAN HUB modem is the caller."
::= { mdmArEntry 3 }

mdmArIncomConnectTerm OBJECT-TYPE
SYNTAX OCTET STRING (SIZE(0..40))
ACCESS read-write
STATUS optional
DESCRIPTION
"This script is triggered after a remote modem has called a 
Total Control WAN HUB modem, but the connection between 
them terminated for some reason."
::= { mdmArEntry 4 }

mdmArOutgoConnectTerm OBJECT-TYPE
SYNTAX OCTET STRING (SIZE(0..40))
ACCESS read-write
STATUS optional
DESCRIPTION
"This script is triggered after a Total Control WAN HUB 
modem called a remote modem, but the connection between 
them terminated for some reason."
::= { mdmArEntry 5 }

mdmArConnectAttemptFail OBJECT-TYPE
SYNTAX OCTET STRING (SIZE(0..40))
ACCESS read-write
STATUS optional
DESCRIPTION
"This script is triggered when a Total Control WAN HUB modem 
fails to connect with a remote modem for an incoming or an 
outgoing call."
::= { mdmArEntry 6 }

mdmArConnectTimeExpire OBJECT-TYPE
SYNTAX OCTET STRING (SIZE(0..40))
ACCESS read-write
STATUS optional
DESCRIPTION
"This script is triggered when a connection duration exceeds 
the user defined connection time limit."
::= { mdmArEntry 7 }

mdmArResetByDte OBJECT-TYPE
SYNTAX OCTET STRING (SIZE(0..40))
ACCESS read-write
STATUS optional
DESCRIPTION
"This script is triggered when a modem has been reset by a 
DTE."
::= { mdmArEntry 8 }

mdmArDteXmitIdle OBJECT-TYPE
SYNTAX OCTET STRING (SIZE(0..40))
ACCESS read-write
STATUS optional
DESCRIPTION
"This script is triggered when a modem's DTE remains idle 
for specified amount of minutes that is defined by a user."
::= { mdmArEntry 9 }

mdmArBlersAtThresh OBJECT-TYPE
SYNTAX OCTET STRING (SIZE(0..40))
ACCESS read-write
STATUS optional
DESCRIPTION
"This script is triggered when a Total Control WAN HUB modem 
receives a certain amount of block errors. This amount can 
be configured by a user."
::= { mdmArEntry 10 }

mdmArFbacksAtThresh OBJECT-TYPE
SYNTAX OCTET STRING (SIZE(0..40))
ACCESS read-write
STATUS optional
DESCRIPTION
"This script is triggered when a Total Control WAN HUB modem 
reaches a certain amount of fall backs within a single 
session. This amount can be configured by a user."
::= { mdmArEntry 11 }

mdmArDialOutLoginFail OBJECT-TYPE
SYNTAX OCTET STRING (SIZE(0..40))
ACCESS read-write
STATUS optional
DESCRIPTION
"This script is triggered when a user, who is attempting to 
dial out from a Total Control WAN HUB modem that supports 
dial security, enters an invalid response to a prompt."
::= { mdmArEntry 12 }

mdmArDialOutRestrNum OBJECT-TYPE
SYNTAX OCTET STRING (SIZE(0..40))
ACCESS read-write
STATUS optional
DESCRIPTION
"This script is triggered when a user, who is attempting to 
dial out from a Total Control WAN HUB modem that supports 
dial security, uses a restricted number."

::= { mdmArEntry 13 }

mdmArDialInLoginFail OBJECT-TYPE
SYNTAX OCTET STRING (SIZE(0..40))
ACCESS read-write
STATUS optional
DESCRIPTION
"This script is triggered when a user, who is attempting to 
dial in from a remote modem in to a Total Control WAN HUB 
modem that supports dial security, enters an invalid 
response to a prompt."
::= { mdmArEntry 14 }

mdmArDialBackRestrNum OBJECT-TYPE
SYNTAX OCTET STRING (SIZE(0..40))
ACCESS read-write
STATUS optional
DESCRIPTION
"This script is triggered when a user, who is attempting to 
dial in from a remote modem in to a Total Control WAN HUB 
modem that supports dial security, requests the Total 
Control WAN HUB modem to dial back to a restricted number."
::= { mdmArEntry 15 }

mdmArDialBackRestModem OBJECT-TYPE
SYNTAX OCTET STRING (SIZE(0..40))
ACCESS read-write
STATUS optional
DESCRIPTION
"This script is triggered when a user, who is attempting to 
dial in from a remote modem in to a Total Control WAN HUB 
modem that supports dial security, requests the Total 
Control WAN HUB modem to dial back using a restricted Total 
Control WAN HUB modem."
::= { mdmArEntry 16 }

mdmArLoginAttemptsExceed OBJECT-TYPE
SYNTAX OCTET STRING (SIZE(0..40))
ACCESS read-write
STATUS optional
DESCRIPTION
"This script is triggered when a user, who is dialing in to 
or out of the Total Control WAN HUB modem, exceeds the 
number of correct user name/password response attempts."
::= { mdmArEntry 17 }

mdmArUserBlacklisted OBJECT-TYPE
SYNTAX OCTET STRING (SIZE(0..40))
ACCESS read-write
STATUS optional
DESCRIPTION
"This script is triggered when a user, who is dialing in to 
or out of the Total Control WAN HUB modem, exceeds the 
number of password prompt retries. At this point the user 
becomes black listed."
::= { mdmArEntry 18 }

mdmArAttmpLoginByBlistUsr OBJECT-TYPE
SYNTAX OCTET STRING (SIZE(0..40))
ACCESS read-write
STATUS optional
DESCRIPTION
"This script is triggered when a user, who has been black 
listed, is trying to dial in to or out of a Total Control 
WAN HUB modem."
::= { mdmArEntry 19 }

mdmArRspAttemptLimExceed OBJECT-TYPE
SYNTAX OCTET STRING (SIZE(0..40))
ACCESS read-write
STATUS optional
DESCRIPTION
"This script is triggered when a user, who is dialing in to 
or out of a Total Control WAN HUB modem, exceeds the number 
of security prompt retries during a single dial security 
session."
::= { mdmArEntry 20 }

mdmArWatchdog OBJECT-TYPE
SYNTAX OCTET STRING (SIZE(0..40))
ACCESS read-write
STATUS optional
DESCRIPTION
"This script is triggered when a software failure has 
occurred on a modem."
::= { mdmArEntry 21 }

mdmArMgtBusFailure OBJECT-TYPE
SYNTAX OCTET STRING (SIZE(0..40))
ACCESS read-write
STATUS optional
DESCRIPTION
"This script is triggered when a contact with a modem, via 
the management bus, has been lost."
::= { mdmArEntry 22 }

mdmArDtrTrue OBJECT-TYPE
SYNTAX OCTET STRING (SIZE(0..40))
ACCESS read-write
STATUS optional
DESCRIPTION
"This script is triggered when a modem's DTE transitions it 
DTR line from low to high and holds it high for the 
specified number of seconds. This amount is user 
configurable."
::= { mdmArEntry 23 }

mdmArDtrFalse OBJECT-TYPE
SYNTAX OCTET STRING (SIZE(0..40))
ACCESS read-write
STATUS optional
DESCRIPTION
"This script is triggered when a modem's DTE transitions it 
DTR line from high to low and holds it low for the 
specified number of seconds. This amount is user 
configurable."
::= { mdmArEntry 24 }

mdmArMdmRingNoAnswer OBJECT-TYPE
SYNTAX OCTET STRING (SIZE(0..40))
ACCESS read-write
STATUS optional
DESCRIPTION
"This script is triggered when a Total Control WAN HUB 
modem, configured for auto answer, fails to answer an 
incoming call within a specified number of rings. This 
amount is user configurable."
::= { mdmArEntry 25 }

mdmArDteRingNoAnswer OBJECT-TYPE
SYNTAX OCTET STRING (SIZE(0..40))
ACCESS read-write
STATUS optional
DESCRIPTION
"This script is triggered when a DTE fials to raise DTR in 
response to an incoming call for a specified amount of 
rings. This amount is user configurable."
::= { mdmArEntry 26 }

mdmArNoDialTone OBJECT-TYPE
SYNTAX OCTET STRING (SIZE(0..40))
ACCESS read-write
STATUS optional
DESCRIPTION
"This script is triggered when a Total Control WAN HUB modem 
goes off hook, but detects an inadequate dial tone level on 
an analog phone line."
::= { mdmArEntry 27 }

mdmArNoLoopCurrent OBJECT-TYPE
SYNTAX OCTET STRING (SIZE(0..40))
ACCESS read-write
STATUS optional
DESCRIPTION
"This script is triggered when a Total Control WAN HUB modem 
goes off hook, but it does not detect the presence of loop 
current on an analog phone line."
::= { mdmArEntry 28 }

mdmArTimer1 OBJECT-TYPE
SYNTAX OCTET STRING (SIZE(0..40))
ACCESS read-write
STATUS optional
DESCRIPTION
"This script is triggered when the first general purpose 
timer expires."
::= { mdmArEntry 29 }

mdmArTimer2 OBJECT-TYPE
SYNTAX OCTET STRING (SIZE(0..40))
ACCESS read-write
STATUS optional
DESCRIPTION
"This script is triggered when the second general purpose 
timer expires."
::= { mdmArEntry 30 }

mdmArTimer3 OBJECT-TYPE
SYNTAX OCTET STRING (SIZE(0..40))
ACCESS read-write
STATUS optional
DESCRIPTION
"This script is triggered when the third general purpose 
timer expires."
::= { mdmArEntry 31 }

mdmArTimer4 OBJECT-TYPE
SYNTAX OCTET STRING (SIZE(0..40))
ACCESS read-write
STATUS optional
DESCRIPTION
"This script is triggered when the fourth general purpose 
timer expires."
::= { mdmArEntry 32 }

mdmArPacketBusActive OBJECT-TYPE
SYNTAX OCTET STRING (SIZE(0..40))
ACCESS read-write
STATUS optional
DESCRIPTION
"This script is triggered when a packet bus active event is 
detected by the modem."
::= { mdmArEntry 33 }

mdmArPacketBusLost OBJECT-TYPE
SYNTAX OCTET STRING (SIZE(0..40))
ACCESS read-write
STATUS optional
DESCRIPTION
"This script is triggered when a packet bus lost event is 
detected by the modem."
::= { mdmArEntry 34 }

-- The modem Cellular Support group

mdmCe OBJECT IDENTIFIER ::= { mdm 17 }

mdmCeTable OBJECT-TYPE
SYNTAX SEQUENCE OF MdmCeEntry
ACCESS not-accessible
STATUS mandatory
DESCRIPTION
"A list of configurable Cellular Support object for a modem. 
 The number of table entries is given by modemNumber."  
::= { mdmCe 1 }

mdmCeEntry OBJECT-TYPE
SYNTAX MdmCeEntry
ACCESS not-accessible
STATUS mandatory
DESCRIPTION
"Objects which define the Cellular characteristics for a 
particular modem."
INDEX { mdmCeIndex }
::= { mdmCeTable 1 }

MdmCeEntry ::=
SEQUENCE {
mdmCeIndex
    INTEGER,
mdmCeMnp10Dis
    INTEGER,
mdmCeMnpxDis
    INTEGER,
mdmCeComp
    INTEGER,
mdmCeOperDis
    INTEGER,
mdmCeLinkSpeed
    INTEGER,
mdmCeShortFormRules
    INTEGER,
mdmCeDceBitraLim
    INTEGER,
mdmCeDceTxLev
    INTEGER,
mdmCeV42EtcDis
    INTEGER,
mdmCeV42CellSite
    INTEGER,
mdmCeV42EtcCallToneDis
    INTEGER,
mdmCeV42EtcTxLevConDis
    INTEGER,
mdmCeDceStartRate
    INTEGER,
mdmCeV42DceTxDemDis
    INTEGER,
mdmCeMnp10FallbackDis
    INTEGER,
mdmCeMnp10FallforDis
    INTEGER,
mdmCeDbNoEtcDis
    INTEGER,
mdmCeMnpxDetPhEna
    INTEGER
}

mdmCeIndex OBJECT-TYPE
SYNTAX INTEGER
ACCESS read-only
STATUS mandatory
DESCRIPTION
"This index value which uniquely identifies the modem to 
which this entry is applicable.  The value corresponds to 
the index of the corresponding modem in the entity table of 
the chassis MIB."
::= { mdmCeEntry 1 }

mdmCeMnp10Dis OBJECT-TYPE
SYNTAX INTEGER{
  disable(1),
  enable(2)
}
ACCESS read-write
STATUS mandatory
DESCRIPTION
"This object is bit 0 of S-register 60.  It disable/enables 
MNP10 negotiation mostly used with cellular operations. 
(defualt=0)"
::= { mdmCeEntry 2 }

mdmCeMnpxDis OBJECT-TYPE
SYNTAX INTEGER{
  disable(1),
  enable(2)
}
ACCESS read-write
STATUS mandatory
DESCRIPTION
"This object is bit 1 of S-register 60.  It will 
enable/disable the MNP extended services to be active 
during negotiation.  This will mean that MNP10 will use 
V.42 to negotiate. (defualt=0)"
::= { mdmCeEntry 3 }

mdmCeComp OBJECT-TYPE
SYNTAX INTEGER{
  mnp5(1),
  v42bis(2)
}
ACCESS read-write
STATUS mandatory
DESCRIPTION
"This object is bit 2 of S-register 60.  It selects which 
compression type will be negotiated if allowed by other 
modem settings. (default =0>"
::= { mdmCeEntry 4 }

mdmCeOperDis OBJECT-TYPE
SYNTAX INTEGER{
  disable(1),
  enable(2)
}
ACCESS read-write
STATUS mandatory
DESCRIPTION
"This object is bit 3 of S-register 60.  It announces that 
at least one end of the link will be across a cellular 
network.  Therefore, the Dyncamic Transmit Algorithm will 
be active. (default=0)"
::= { mdmCeEntry 5 }

mdmCeLinkSpeed OBJECT-TYPE
SYNTAX INTEGER{
  linkAtHighSpeed(1),
  linkAt1200BpsV22(2)
}
ACCESS read-write
STATUS mandatory
DESCRIPTION
"This object is bit 4 of register 60 tells the modem which 
speed to establish the link at. (default=0)"
::= { mdmCeEntry 6 }

mdmCeShortFormRules OBJECT-TYPE
SYNTAX INTEGER{
  disable(1),
  form1CodeWords512(2),
  form2CodeWords1024(3),
  form3CodeWords2048(4)
}
ACCESS read-write
STATUS mandatory
DESCRIPTION
"This object is the S-register 61.  It takes a value from 0 
to 3 and regulates the V.42bis Short Form Negotiation 
rules.  The short form assumes that the maximum string 
length is always 32 octets and that the direction of 
compression is always bi-directional. (default=0)"
::= { mdmCeEntry 7 }

mdmCeDceBitraLim OBJECT-TYPE
SYNTAX INTEGER{
  maxDceRate(1),
  bps4800(2),
  bps7200(3),
  bps9600(4),
  bps12000(5),
  bps14400(6)
}
ACCESS read-write
STATUS mandatory
DESCRIPTION
"This object is the S-register 64.  It limits DCE bitrates 
to values equal to or below the chosen setting. (default=0)"
::= { mdmCeEntry 8 }

mdmCeDceTxLev OBJECT-TYPE
SYNTAX INTEGER{
  modemContrlTxLev(1),
  dBm10(2),
  dBm11(3),
  dBm12(4),
  dBm13(5),
  dBm14(6),
  dBm15(7),
  dBm16(8),
  dBm17(9),
  dBm18(10),
  dBm19(11),
  dBm20(12),
  dBm21(13),
  dBm22(14),
  dBm23(15),
  dBm24(16),
  dBm25(17)
}
ACCESS read-write
STATUS mandatory
DESCRIPTION
"This object is S-register 65.  It selects DCE TX level to 
use during cellular operations. (default=0)"
::= { mdmCeEntry 9 }

mdmCeV42EtcDis OBJECT-TYPE
SYNTAX INTEGER{
  disable(1),
  enable(2)
}
ACCESS read-write
STATUS mandatory
DESCRIPTION
"This object is the bit 0 of S-register 66.  It 
enables/disables ETC. (default=0)"
::= { mdmCeEntry 10 }

mdmCeV42CellSite OBJECT-TYPE
SYNTAX INTEGER{
  fixedSite(1),
  mobileSite(2)
}
ACCESS read-write
STATUS mandatory
DESCRIPTION
"This object is the bit 1 of S-register 66.  It selects 
fixed or mobile site operations. (default=0)"
::= { mdmCeEntry 11 }

mdmCeV42EtcCallToneDis OBJECT-TYPE
SYNTAX INTEGER{
  disable(1),
  enable(2)
}
ACCESS read-write
STATUS mandatory
DESCRIPTION
"This object is the bit 2 of S-register 66.  It 
enables/disables ETC calling tone. (default=0)"
::= { mdmCeEntry 12 }

mdmCeV42EtcTxLevConDis OBJECT-TYPE
SYNTAX INTEGER{
  disable(1),
  enable(2)
}
ACCESS read-write
STATUS mandatory
DESCRIPTION
"This object is the bit 3 of S-register 66.  It 
enables/disables forced ETC TX level control. (default=0)"
::= { mdmCeEntry 13 }

mdmCeDceStartRate OBJECT-TYPE
SYNTAX INTEGER{
  auto(1),
  bps4800(2),
  bps9600(3)
}
ACCESS read-write
STATUS mandatory
DESCRIPTION
"This object is the bits 4 and 5 of S-register 66.  It sets 
the DCE startup rate. (default=0)"
::= { mdmCeEntry 14 }

mdmCeV42DceTxDemDis OBJECT-TYPE
SYNTAX INTEGER{
  disable(1),
  enable(2)
}
ACCESS read-write
STATUS mandatory
DESCRIPTION
"This object is the bit 6 of S-register 66.  It 
enables/disables DCE TX De-emphasis. (default=0)"
::= { mdmCeEntry 15 }

mdmCeMnp10FallbackDis OBJECT-TYPE
SYNTAX INTEGER{
  disable(1),
  enable(2)
}
ACCESS read-write
STATUS mandatory
DESCRIPTION
"This object is the bit 5 of S-register 60.  It 
enables/disables MNP10 fallback. (default=0)"
::= { mdmCeEntry 16 }

mdmCeMnp10FallforDis OBJECT-TYPE
SYNTAX INTEGER{
  disable(1),
  enable(2)
}
ACCESS read-write
STATUS mandatory
DESCRIPTION
"This object is the bit 6 of S-register 60.  It 
enables/disables MNP10 fallforward. (default=0)"
::= { mdmCeEntry 17 }

mdmCeDbNoEtcDis OBJECT-TYPE
SYNTAX INTEGER{
  disable(1),
  enable(2)
}
ACCESS read-write
STATUS mandatory
DESCRIPTION
"This object is the bit 7 of S-register 66.  It 
enables/disables non-ETC originate mode.  
(default=0/disable)"
::= { mdmCeEntry 18 }

mdmCeMnpxDetPhEna OBJECT-TYPE
SYNTAX INTEGER{
  enable(1),
  disable(2)
}
ACCESS read-write
STATUS mandatory
DESCRIPTION
"This object is the bit 7 of S-register 60.  It 
enables/disables the MNPX detection phase during connection 
establishment. (default=0/enable)."
::= { mdmCeEntry 19 }

mdmSts OBJECT IDENTIFIER ::= { mdm 18 }

mdmStsTable OBJECT-TYPE
SYNTAX SEQUENCE OF MdmStsEntry
ACCESS not-accessible
STATUS mandatory
DESCRIPTION
"A table containing configuration information for each NAC 
in the NAS chassis that supports packet bus datagrams."
::= { mdmSts 1 }

mdmStsEntry OBJECT-TYPE
SYNTAX MdmStsEntry
ACCESS not-accessible
STATUS mandatory
DESCRIPTION
"There is one configuration row for each modem entity."
INDEX { mdmStsIndex }
::= { mdmStsTable 1 }

MdmStsEntry ::=
SEQUENCE {
mdmStsIndex
    INTEGER,
mdmStsPbClock
    INTEGER
}

mdmStsIndex OBJECT-TYPE
SYNTAX INTEGER
ACCESS read-only
STATUS mandatory
DESCRIPTION
"A unique value for each card in the chassis.  The value of 
this object matches the value of the index of the 
corresponding card's entry in the entity table of the 
chassis MIB."
::= { mdmStsEntry 1 }

mdmStsPbClock OBJECT-TYPE
SYNTAX INTEGER{
  notSupported(1),
  clockMaster(2),
  clockSlave(3),
  noClockPresent(4)
}
ACCESS read-only
STATUS mandatory
DESCRIPTION
"This object defines the current status of the packet bus 
clock."
::= { mdmStsEntry 2 }

mdmMa OBJECT IDENTIFIER ::= { mdm 19 }

mdmMaTable OBJECT-TYPE
SYNTAX SEQUENCE OF MdmMaEntry
ACCESS not-accessible
STATUS mandatory
DESCRIPTION
"A Mapping table entry, containing objects which define the 
card level configuration each modem is mapped to and the 
unique change indicator."
::= { mdmMa 1 }

mdmMaEntry OBJECT-TYPE
SYNTAX MdmMaEntry
ACCESS not-accessible
STATUS mandatory
DESCRIPTION
"Objects which define the Mapping and Status for a 
particular modem."
INDEX { mdmMaIndex }
::= { mdmMaTable 1 }

MdmMaEntry ::=
SEQUENCE {
mdmMaIndex
    INTEGER,
mdmMaChangeIndicator
    INTEGER,
mdmMaChannelConfig
    INTEGER
}

mdmMaIndex OBJECT-TYPE
SYNTAX INTEGER
ACCESS read-only
STATUS mandatory
DESCRIPTION
"This index value which uniquely identifies the modem to 
which this entry is applicable. The value corresponds to 
the index of the corresponding modem in the entity table of 
the chassis MIB."
::= { mdmMaEntry 1 }

mdmMaChangeIndicator OBJECT-TYPE
SYNTAX INTEGER{
  notSupported(1),
  cfgChanged(2),
  cfgUnchanged(3)
}
ACCESS read-only
STATUS mandatory
DESCRIPTION
"A value of changed indicates that the card level 
configuration for a specific channel on a HDM is not the 
one in use on that channel."
::= { mdmMaEntry 2 }

mdmMaChannelConfig OBJECT-TYPE
SYNTAX INTEGER{
  group1(1),
  group2(2),
  group3(3),
  group4(4)
}
ACCESS read-write
STATUS mandatory
DESCRIPTION
"Values of group(1), group(2), group(3), group(4) represent 
the HDM card level configuration of 1..4 used by this 
channel." 
::= { mdmMaEntry 3 }

END
