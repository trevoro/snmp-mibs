USR-IP-ROUTING-MIB DEFINITIONS ::= BEGIN
    IMPORTS
        OBJECT-TYPE, MODULE-IDENTITY, 
        Integer32, Counter32, IpAddress
                FROM SNMPv2-SMI
        DisplayString
                FROM SNMPv2-TC
        common, UsrNetLogicalId, UsrConfigStatus
                FROM USR-DEFINITIONS-MIB;
usrIpRouting MODULE-IDENTITY
         LAST-UPDATED "200205051245Z"
         ORGANIZATION "CommWorks Corporation, a 3Com Company"
         CONTACT-INFO "Customer Support"
         DESCRIPTION
                 "The commWorks enterprise defined MIB objects
                  for IP routing process."
--       REVISION "200205051245Z"
--       DESCRIPTION "Converted to SNMPv2"
         ::= { common 19 }
-- Begin IP routing object definitions here...
usrIpRouterId    OBJECT-TYPE
    SYNTAX    IpAddress
    MAX-ACCESS    read-write
    STATUS        current
    DESCRIPTION
        "the router id is usually the ip address of one of the router's
         lan interface ip address.  this variable can only be set when
         usrIpAdminStatus is set to disabled."
::= {usrIpRouting 1}
usrIpAdminStatus    OBJECT-TYPE
    SYNTAX    INTEGER {
            enabled(1),
            disabled(2)
        }
    MAX-ACCESS    read-write
    STATUS        current
    DESCRIPTION
        "this variable is used to enable or disable the ip routing instance."
        --CONFIGURABLE
::= {usrIpRouting 2}
usrIpStaticProtoStatus    OBJECT-TYPE
    SYNTAX    INTEGER {
            enable(1),
            disable(2)
        }
    MAX-ACCESS    read-write
    STATUS        current
    DESCRIPTION
        "this variable is used to enable or disable static remote routes"
::= {usrIpRouting 3}
usrIpASNumber    OBJECT-TYPE
    SYNTAX    Integer32 (1..65535)
    MAX-ACCESS    read-write
    STATUS        current
    DESCRIPTION
        "this is the autonomous system number used by egp, which can only be 
         modified when usrIpAdminStatus is set to disabled."
::= {usrIpRouting 4}
usrIpRtabMaxAdmin    OBJECT-TYPE
    SYNTAX        Integer32 (30..65535)
    MAX-ACCESS        read-write
    STATUS            current
    DESCRIPTION
        "the max admin route table entries for next set.  this is put in by
         rci for lightstream atm.  it is not used by lanlinker or netserver."
::= {usrIpRouting 5}
usrIpRtabMax    OBJECT-TYPE
    SYNTAX    Integer32 (30..20000)
    MAX-ACCESS    read-only
    STATUS        current
    DESCRIPTION
        "this displays the maximum routing table size, this
         value can no longer be modified. The max size of the
         routing table is determined at compilation time, 
         based on the DFLT_RTH_CNT. DFLT_RTH_CNT is currently 
         set to 3880."
::= {usrIpRouting 6}
usrIpNHEntryMax    OBJECT-TYPE
    SYNTAX        Integer32 (256..65535)
    MAX-ACCESS        read-write
    STATUS            current
    DESCRIPTION
        "this defines the maximum next hop entries, which can only be 
         modified when usrIpAdminStatus is set to disabled.  the default
         is 512"
::= {usrIpRouting 7}
usrIpRtEntryCount    OBJECT-TYPE
    SYNTAX        Counter32
    MAX-ACCESS        read-only
    STATUS            current
    DESCRIPTION
        "this keeps the number of route entries."
::= {usrIpRouting 8}
usrIpGenStat    OBJECT-TYPE
    SYNTAX    INTEGER {
            create(1),
            delete(2)
        }
    MAX-ACCESS    read-write
    STATUS        current
    DESCRIPTION
        "this variable denotes the existence of the ip routing instance,
         which can also be used to delete the routing instance."
::= {usrIpRouting 9}
usrIpRipGenStat    OBJECT-TYPE
    SYNTAX        INTEGER {
                enabled(1),
                disabled(2)
            }
    MAX-ACCESS        read-write
    STATUS            current
    DESCRIPTION
        "this mib variable is used to enable or disable the ip rip instance
         at the ip routing instance level.  it is a no op if ip rip instance
         is not yet created.
         the rip instance, i.e. usrIpRipAdminStatus, may still remain
         disabled, if it is either not created or it was disabled at ip rip
         instance level.  to fully enable the rip instance, one has to make
         sure that ip rip instance is already created and enabled on both
         levels."
::= {usrIpRouting 10}
usrIpRipAdminStatus    OBJECT-TYPE
    SYNTAX        INTEGER {
                create(1),
                delete(2)
        }
    MAX-ACCESS        read-write
    STATUS            current
    DESCRIPTION
        "this variable is used to create or delete the ip rip instance."
::= {usrIpRouting 11}
usrIpRipFlags    OBJECT-TYPE
    SYNTAX    Integer32
    MAX-ACCESS    read-write
    STATUS        current
    DESCRIPTION
        "Several Flags  are supported by this mib object,
         only RIP_FLAG_RFC1058_METRICS, RIP_FLAG_SEND_REQUEST are
         accessible.
         The only allowable values for setting are as follows:-
         24 (0x18) - SEND_REQUEST & METRICS
         8         - METRICS
         16 (0x10) - SEND_REQUEST
         0         - NONE
         Note:- when setting these values a GET will not
         necessarily return the value SET: it will
         return the SET value plus the bitmask(s)
         for inaccessible flags.
         The default flags are 0x1A (decimal 26) reflecting,
         RIP_FLAG_JITTER_UPDATE     :=    0x00000002 (default)    
         RIP_FLAG_RFC1058_METRICS   :=    0x00000008 (default)
         RIP_FLAG_SEND_REQUEST      :=    0x00000010 (default) "
::= {usrIpRouting 12}
usrIpIfbTable    OBJECT-TYPE
    SYNTAX    SEQUENCE OF UsrIpIfbEntry
    MAX-ACCESS    not-accessible
    STATUS        current
    DESCRIPTION
        "rci uses interface block to describe the system's network interface
         which is similar to pilgrim portal."
::= {usrIpRouting 13}
usrIpIfbEntry    OBJECT-TYPE
    SYNTAX    UsrIpIfbEntry
    MAX-ACCESS    not-accessible
    STATUS        current
    DESCRIPTION
        "an entry for one ip interface block."
    INDEX {usrIpIfbEntAddr, usrIpIfbEntIfIndex}
::= {usrIpIfbTable 1}
UsrIpIfbEntry ::= SEQUENCE {
    usrIpIfbEntAddr         IpAddress,
    usrIpIfbEntIfIndex        UsrNetLogicalId,
    usrIpIfbEntIfHandle        Integer32,
    usrIpIfbEntNetMask        IpAddress,
    usrIpIfbEntOnesBc        Integer32,
    usrIpIfbEntZerosBc        Integer32,
    usrIpIfbEntReasmMaxSize    Integer32,
    usrIpIfbEntType            INTEGER,
    usrIpIfbEntNbrAddr        IpAddress,
    usrIpIfbEntAdminStatus    INTEGER,
    usrIpIfbEntStat            INTEGER,
    usrIpIfbEntPortDown        INTEGER
}
usrIpIfbEntAddr    OBJECT-TYPE
    SYNTAX        IpAddress
    MAX-ACCESS        read-only
    STATUS            current
    DESCRIPTION
        "ip network interface address, i.e. host address"
::= {usrIpIfbEntry 1}
usrIpIfbEntIfIndex    OBJECT-TYPE
    SYNTAX        UsrNetLogicalId
    MAX-ACCESS        read-only
    STATUS            current
    DESCRIPTION
        "the logical identifier of the ip network."
::={usrIpIfbEntry 2}
usrIpIfbEntIfHandle    OBJECT-TYPE
    SYNTAX        Integer32
    MAX-ACCESS        read-only
    STATUS            current
    DESCRIPTION
        "don't know yet"
::= {usrIpIfbEntry 3}
usrIpIfbEntNetMask    OBJECT-TYPE
    SYNTAX        IpAddress
    MAX-ACCESS        read-only
    STATUS            current
    DESCRIPTION
        "the subnet mask associated w/ the ip address of this entry."
::= {usrIpIfbEntry 4}
usrIpIfbEntOnesBc    OBJECT-TYPE
    SYNTAX        Integer32 (0..1)
    MAX-ACCESS        read-only
    STATUS            current
    DESCRIPTION
        "the value of the least-significant bit in the ip broadcast address
         used for sending datagrams on the (logical) interface associated w/
         the ip address of this entry."
::= {usrIpIfbEntry 5}
usrIpIfbEntZerosBc    OBJECT-TYPE
    SYNTAX        Integer32 (0..1)
    MAX-ACCESS        not-accessible
    STATUS            current
    DESCRIPTION
        "the value of the least-significant bit in the ip broadcast address
         used for sending datagrams on the (logical) interface associated w/
         the ip address of this entry."
::= {usrIpIfbEntry 6}
usrIpIfbEntReasmMaxSize    OBJECT-TYPE
    SYNTAX            Integer32 (0..65535)
    MAX-ACCESS            read-only
    STATUS                current
    DESCRIPTION
        "the size of the largest ip datagram which this entity can re-assemble
         from incoming ip fragmented datagrams received on this interface.
         it is usually equivalent to the mtu of the interface."
::= {usrIpIfbEntry 7}
usrIpIfbEntType    OBJECT-TYPE
    SYNTAX        INTEGER {
                broadcast(1),
                non-broadcast(2),
                point-to-point(3)
            }
    MAX-ACCESS        read-only
    STATUS            current
    DESCRIPTION
        "this denotes the ip network (logical) type."
::= {usrIpIfbEntry 8}
usrIpIfbEntNbrAddr    OBJECT-TYPE
    SYNTAX        IpAddress
    MAX-ACCESS        read-write
    STATUS            current
    DESCRIPTION
        "this may be needed for point to point connection."
::= {usrIpIfbEntry 9}
usrIpIfbEntAdminStatus    OBJECT-TYPE
    SYNTAX            INTEGER {
                    enabled(1),
                    disabled(2)
                }
    MAX-ACCESS            read-write
    STATUS                current
    DESCRIPTION
        "this variable is used to enable or disable this interface block"
::= {usrIpIfbEntry 10}
usrIpIfbEntStat    OBJECT-TYPE
    SYNTAX        INTEGER {
                create(1),
                delete(2)
            }
    MAX-ACCESS        read-write
    STATUS        obsolete
    DESCRIPTION
        "this variable is used to create or delete an interface block."
::= {usrIpIfbEntry 11}
usrIpIfbEntPortDown    OBJECT-TYPE
    SYNTAX        INTEGER {
                active(1),
                inactive(2)
            }
    MAX-ACCESS        read-write
    STATUS        obsolete
    DESCRIPTION
        "this variable is used to indicate the state of the hardware."
::= {usrIpIfbEntry 12}
usrIpRipGenAdminStat    OBJECT-TYPE
    SYNTAX            INTEGER {
                    enabled(1),
                    disabled(2)
                }
    MAX-ACCESS            read-write
    STATUS                current
    DESCRIPTION
        "this variable is used to disable or enable the ip rip instance at
         the rip instance level."
        --CONFIGURABLE
::= {usrIpRouting 14}
usrIpRipGenIntfCnt    OBJECT-TYPE
    SYNTAX        Integer32
    MAX-ACCESS        read-only
    STATUS            current
    DESCRIPTION
        "this variable shows the number of the ip rip interfaces."
::= {usrIpRouting 15}
usrIpRipGenNbrCnt    OBJECT-TYPE
    SYNTAX        Integer32
    MAX-ACCESS        read-only
    STATUS            current
    DESCRIPTION
        "this variable shows the number of the rip neighbours."
::= {usrIpRouting 16}
usrIpRipGenJitter    OBJECT-TYPE
    SYNTAX        INTEGER {
                enabled(1),
                disabled(2)
            }
    MAX-ACCESS        read-write
    STATUS            current
    DESCRIPTION
        "this variable is used to enable or disable the rip packet
         jitter feature."
::= {usrIpRouting 17}
usrIpRipIfTable    OBJECT-TYPE
    SYNTAX        SEQUENCE OF UsrIpRipIfEntry
    MAX-ACCESS        not-accessible
    STATUS            current
    DESCRIPTION
        "rci uses interface block to describe the system's network interface
         which is similar to pilgrim portal."
::= {usrIpRouting 18}
usrIpRipIfEntry    OBJECT-TYPE
    SYNTAX        UsrIpRipIfEntry
    MAX-ACCESS        not-accessible
    STATUS            current
    DESCRIPTION
        "an entry of rip interface block."
    INDEX {usrIpRipIfEntAddr, usrIpRipIfEntAddrLessIf}
::= {usrIpRipIfTable 1}
UsrIpRipIfEntry ::= SEQUENCE {
    usrIpRipIfEntAddr            IpAddress,
    usrIpRipIfEntAddrLessIf        Integer32,
    usrIpRipIfVersion            INTEGER,
    usrIpRipIfType                INTEGER,
    usrIpRipIfAdminStat            INTEGER,
    usrIpRipIfMetric            Integer32,
    usrIpRipIfSendDefault        INTEGER,
    usrIpRipIfAcceptDefault        INTEGER,
    usrIpRipIfSubnetsOnly        INTEGER,
    usrIpRipIfSilent            INTEGER,
    usrIpRipIfSplitHorizon        INTEGER,
    usrIpRipIfPoison            INTEGER,
    usrIpRipIfFlash                INTEGER,
    usrIpRipIfDfltRouteMetric    Integer32,
    usrIpRipIfPortDown            INTEGER,
    usrIpRipIfStat                INTEGER,
    usrIpRip2IfStatRcvBadPackets Integer32,
    usrIpRip2IfStatRcvBadRoutes     Integer32,
    usrIpRip2IfStatSendUpdates     Integer32
}
usrIpRipIfEntAddr    OBJECT-TYPE
    SYNTAX        IpAddress
    MAX-ACCESS        read-only
    STATUS            current
    DESCRIPTION
        "the interface ip address."
::= {usrIpRipIfEntry 1}
usrIpRipIfEntAddrLessIf    OBJECT-TYPE
    SYNTAX            Integer32
    MAX-ACCESS            read-only
    STATUS                current
    DESCRIPTION
        "this column is used when the interface ip address is not specified.
         in general, it is equal to network id."
::= {usrIpRipIfEntry 2}
usrIpRipIfVersion    OBJECT-TYPE
    SYNTAX        INTEGER {
                ripv1(1),
                ripv2(2)
            }
    MAX-ACCESS        read-write
    STATUS            current
    DESCRIPTION
        "this variable tells what version of rip this interface is running."
::= {usrIpRipIfEntry 3}
usrIpRipIfType    OBJECT-TYPE
    SYNTAX    INTEGER {
            broadcast(1),
            non-broadcast(2),
            point-to-point(3)
        }
    MAX-ACCESS    read-write
    STATUS        current
    DESCRIPTION
        "this variable shows the interface type, i.e. broadcast,
         non-broadcast, point-to-point and undefined."
::= {usrIpRipIfEntry 4}
usrIpRipIfAdminStat    OBJECT-TYPE
    SYNTAX        INTEGER {
                enabled(1),
                disabled(2)
            }
    MAX-ACCESS        read-write
    STATUS            current
    DESCRIPTION
        "this variable shows whether the rip is enabled for this interface."
::= {usrIpRipIfEntry 5}
usrIpRipIfMetric    OBJECT-TYPE
    SYNTAX        Integer32 (1..16)
    MAX-ACCESS        read-write
    STATUS            current
    DESCRIPTION
        "this variable is to define the metric for this interface."
::= {usrIpRipIfEntry 6}
usrIpRipIfSendDefault    OBJECT-TYPE
    SYNTAX            INTEGER {
                    enabled(1),
                    disabled(2)
                }
    MAX-ACCESS            read-write
    STATUS                current
    DESCRIPTION
        "this variable is to enable advertising the default route."
::= {usrIpRipIfEntry 7}
usrIpRipIfAcceptDefault    OBJECT-TYPE
    SYNTAX            INTEGER {
                    enabled(1),
                    disabled(2)
                }
    MAX-ACCESS            read-write
    STATUS                current
    DESCRIPTION
        "this variable is to enable accepting the default route."
::= {usrIpRipIfEntry 8}
usrIpRipIfSubnetsOnly    OBJECT-TYPE
    SYNTAX            INTEGER {
                    enabled(1),
                    disabled(2)
                }
    MAX-ACCESS            read-write
    STATUS                current
    DESCRIPTION
        "this variable is to enable this interface to advertise
         only subnet routes only."
::= {usrIpRipIfEntry 9}
usrIpRipIfSilent    OBJECT-TYPE
    SYNTAX        INTEGER {
                enabled(1),
                disabled(2)
            }
    MAX-ACCESS        read-write
    STATUS            current
    DESCRIPTION
        "this variable is to enable listen-only feature for this interface."
::= {usrIpRipIfEntry 10}
usrIpRipIfSplitHorizon    OBJECT-TYPE
    SYNTAX            INTEGER {
                    enabled(1),
                    disabled(2)
                }
    MAX-ACCESS            read-write
    STATUS                current
    DESCRIPTION
        "this variable is to enable split horizon."
::= {usrIpRipIfEntry 11}
usrIpRipIfPoison    OBJECT-TYPE
    SYNTAX        INTEGER {
                enabled(1),
                disabled(2)
            }
    MAX-ACCESS        read-write
    STATUS            current
    DESCRIPTION
        "this variable is to enable poison reverse."
::= {usrIpRipIfEntry 12}
usrIpRipIfFlash    OBJECT-TYPE
    SYNTAX        INTEGER {
                enabled(1),
                disabled(2)
            }
    MAX-ACCESS        read-write
    STATUS            current
    DESCRIPTION
        "this variable is to enable sending flash update."
::= {usrIpRipIfEntry 13}
usrIpRipIfDfltRouteMetric    OBJECT-TYPE
    SYNTAX                Integer32 (1..16)
    MAX-ACCESS                read-write
    STATUS                    current
    DESCRIPTION
        "this variable specifies the metric of the default route."
::= {usrIpRipIfEntry 14}
usrIpRipIfPortDown    OBJECT-TYPE
    SYNTAX        INTEGER {
                down(1),
                up(2)
            }
    MAX-ACCESS        read-only
    STATUS            current
    DESCRIPTION
        "this variable denotes the status of the physical port."
::= {usrIpRipIfEntry 15}
usrIpRipIfStat    OBJECT-TYPE
    SYNTAX    INTEGER {
            create(1),
            delete(2)
        }
    MAX-ACCESS    read-write
    STATUS        current
    DESCRIPTION
        "this variable is to delete the rip interface."
::= {usrIpRipIfEntry 16}
usrIpRip2IfStatRcvBadPackets    OBJECT-TYPE
    SYNTAX                Integer32
    MAX-ACCESS                read-only
    STATUS                    current
    DESCRIPTION
        "ripv2 received bad packet counter."
::= {usrIpRipIfEntry 17}
usrIpRip2IfStatRcvBadRoutes    OBJECT-TYPE
    SYNTAX                Integer32
    MAX-ACCESS                read-only
    STATUS                    current
    DESCRIPTION
        "ripv2 received bad route counter."
::= {usrIpRipIfEntry 18}
usrIpRip2IfStatSendUpdates    OBJECT-TYPE
    SYNTAX                Integer32
    MAX-ACCESS                read-only
    STATUS                    current
    DESCRIPTION
        "ripv2 sent update packet counter."
::= {usrIpRipIfEntry 19}
usrIpRip2IfConfTable    OBJECT-TYPE
    SYNTAX            SEQUENCE OF UsrIpRip2IfConfEntry
    MAX-ACCESS            not-accessible
    STATUS                current
    DESCRIPTION
        "table for ripv2 specific interface configuration information"
::= {usrIpRouting 19}
usrIpRip2IfConfEntry    OBJECT-TYPE
    SYNTAX            UsrIpRip2IfConfEntry
    MAX-ACCESS            not-accessible
    STATUS                current
    DESCRIPTION
        "an entry of ripv2 interface configuration table."
    INDEX {rip2IfConfAddress, rip2IfConfIndex}
::= {usrIpRip2IfConfTable 1}
UsrIpRip2IfConfEntry ::= SEQUENCE {
    rip2IfConfAddress            IpAddress,
    rip2IfConfIndex                Integer32,
    rip2IfConfDomain            Integer32,
    rip2IfConfAuthType            INTEGER,
    rip2IfConfAuthKey            OCTET STRING,
    rip2IfConfSend                INTEGER,
    rip2IfConfReceive            INTEGER,
    rip2IfConfDefaultMetric        Integer32,
    rip2IfConfStatus            INTEGER,
    rip2IfConfSrcAddress        Integer32
}
rip2IfConfAddress    OBJECT-TYPE
    SYNTAX        IpAddress
    MAX-ACCESS        read-only
    STATUS            current
    DESCRIPTION
        "the network interface address."
::= {usrIpRip2IfConfEntry 1}
rip2IfConfIndex    OBJECT-TYPE
    SYNTAX        Integer32
    MAX-ACCESS        read-only
    STATUS            current
    DESCRIPTION
        "the network id."
::= {usrIpRip2IfConfEntry 2}
rip2IfConfDomain    OBJECT-TYPE
    SYNTAX        Integer32
    MAX-ACCESS        not-accessible
    STATUS        obsolete
    DESCRIPTION
        "this thing is obsolete."
::= {usrIpRip2IfConfEntry 3}
rip2IfConfAuthType    OBJECT-TYPE
    SYNTAX        INTEGER {
                none(1),
                simple(2),
                md5(3)
            }
    MAX-ACCESS        read-write
    STATUS            current
    DESCRIPTION
        "this variable specifies the authentication type.  md5 is not 
         supported in this version yet."
::= {usrIpRip2IfConfEntry 4}
rip2IfConfAuthKey    OBJECT-TYPE
    SYNTAX        OCTET STRING (SIZE(16))
    MAX-ACCESS        read-write
    STATUS            current
    DESCRIPTION
        "the authentication key is defined here."
::= {usrIpRip2IfConfEntry 5}
rip2IfConfSend        OBJECT-TYPE
    SYNTAX        INTEGER {
                none(1),
                version1(2),
                compatible(3),
                version2(4)
            }
    MAX-ACCESS        read-write
    STATUS            current
    DESCRIPTION
        "this variable defines the send policy."
::= {usrIpRip2IfConfEntry 6}
rip2IfConfReceive    OBJECT-TYPE
    SYNTAX        INTEGER {
                version1(1),
                version2(2),
                both(3),
                none(4)
            }
    MAX-ACCESS        read-write
    STATUS            current
    DESCRIPTION
        "this variable defines the receive policy."
::= {usrIpRip2IfConfEntry 7}
rip2IfConfDefaultMetric    OBJECT-TYPE
    SYNTAX        Integer32
    MAX-ACCESS        read-write
    STATUS            current
    DESCRIPTION
        "this variable defines the default metric of this network interface."
::= {usrIpRip2IfConfEntry 8}
rip2IfConfStatus    OBJECT-TYPE
    SYNTAX        INTEGER {
                enabled(1),
                disabled(2)
            }
    MAX-ACCESS        read-write
    STATUS            current
    DESCRIPTION
        ""
::= {usrIpRip2IfConfEntry 9}
rip2IfConfSrcAddress    OBJECT-TYPE
    SYNTAX            Integer32
    MAX-ACCESS            read-only
    STATUS                current
    DESCRIPTION
        ""
::= {usrIpRip2IfConfEntry 10}
usrIpDelRouteAll OBJECT-TYPE
    SYNTAX  Integer32
    MAX-ACCESS  read-write
    STATUS      current
    DESCRIPTION
        "This object is used to clear the whole routing table
         - setting this object with ANY value will do this."
::= { usrIpRouting 20 }
usrIPRterBaseCfgFileName OBJECT-TYPE
    SYNTAX   DisplayString 
    MAX-ACCESS   read-write
    STATUS       current
    DESCRIPTION 
        "The name of a ConfigFile to read/write
         permanent database records. If the value of this
         object is an empty string, then the SLIP process
         uses the default name `@file://SlipFile.cfg'."
::= { usrIpRouting 21 } 
usrIPRterBaseCFMSaveStatus OBJECT-TYPE
    SYNTAX  UsrConfigStatus
    MAX-ACCESS  read-write
    STATUS      current
    DESCRIPTION
        "Setting the value of this object to `save'
         causes the values of the SLIP Base Group
         entries to be written out to the current SLIP
         config file. While the new config file is being
         written, the SLIP process will set the value
         of this flag set to `saving''. Any attempts to set
         the value while it is  not `normal' (i.e. the file
         is currently being written to the config file)
         while result in a badValue error being returned.
         Setting the value to `normal' will result in no
         action."
::= { usrIpRouting 22 }
-- ------------------------------------------------------------
          -- the USR IP Routing Table Head Structure
usrIpRTH OBJECT-TYPE
    SYNTAX  SEQUENCE OF UsrIpRTHEntry
    MAX-ACCESS  not-accessible
    STATUS      current
    DESCRIPTION
        "This entity's IP Routing table."
::= { usrIpRouting 23 }
usrIpRTHEntry OBJECT-TYPE
    SYNTAX  UsrIpRTHEntry
    MAX-ACCESS  not-accessible
    STATUS      current
    DESCRIPTION
        "A route to a particular destination.
         These routes are learned or written from
         the forwarder and so these objects are
         not accessible for SET via CLI or SNMP.
         The only PDU type implemented is GETNEXT."
    INDEX   { usrIpRTHDest, usrIpRTHMask, usrIpRTHNhId }
::= { usrIpRTH 1 }
          UsrIpRTHEntry ::=
              SEQUENCE {
                  usrIpRTHDest      IpAddress,
                  usrIpRTHMask      IpAddress,
                  usrIpRTHProto     INTEGER,
                  usrIpRTHMetric    Integer32,
                  usrIpRTHClass     Integer32,
                  usrIpRTHFwdFlags  Integer32,
                  usrIpRTHAge       Integer32,
                  usrIpRTHNhId      Integer32,
                  usrIpRTHNextHop   IpAddress,
                  usrIpRTHIfIndex   Integer32
              }
usrIpRTHDest OBJECT-TYPE
    SYNTAX  IpAddress
    MAX-ACCESS  read-write
    STATUS      current
    DESCRIPTION
            "The destination IP address of this route.  An
            entry with a value of 0.0.0.0 is considered a
            default route.  Multiple routes to a single
            destination can appear in the table, but access to
            such multiple entries is dependent on the table-
            access mechanisms defined by the network
            management protocol in use."
   --CONFIGURABLE
::= { usrIpRTHEntry 1 }
usrIpRTHMask OBJECT-TYPE
    SYNTAX  IpAddress
    MAX-ACCESS  read-write
    STATUS      current
    DESCRIPTION
            "Indicate the mask to be logical-ANDed with the
            destination address before being compared to the
            value in the ipRTHDest field.  For those systems
            that do not support arbitrary subnet masks, an
            agent constructs the value of the ipRTHMask by
            determining whether the value of the correspondent
            ipRTHDest field belong to a class-A, B, or C
            network, and then using one of:
                 mask           network
                 255.0.0.0      class-A
                 255.255.0.0    class-B
                 255.255.255.0  class-C
            If the value of the ipRTHDest is 0.0.0.0 (a
            default route), then the mask value is also
            0.0.0.0.  It should be noted that all IP routing
            subsystems implicitly use this mechanism."
    --CONFIGURABLE
::= { usrIpRTHEntry 2 }
usrIpRTHProto OBJECT-TYPE
    SYNTAX  INTEGER {
                other(0),       -- none of the following
                local(1),       -- static local
                remote(2),      -- static remote
                special(3),     -- static special
                                -- the remaining values are
                                -- all gateway routing
                                -- protocols
                ospf(4),        -- OSPF
                ospfExt(5),     -- OSPF External
                ospfDisc3(6),   -- OSPF discard routes
                ospfDisc7(7),   -- OSPF discard routes
                rip(8),         -- RIP
                ripDisc(9),     -- RIP discard routes
                egp(10),        -- EGP
                bgpExt(11),     -- BGP External
                bgpInt(12),     -- BGP Internal
                bgpAggrDisc(13),-- BGP Aggregate
                redistrib(14)   -- Server redistribution
                      }
    MAX-ACCESS  read-only
    STATUS      current
    DESCRIPTION
            "The routing mechanism via which this route was
            learned.  Inclusion of values for gateway routing
            protocols is not intended to imply that hosts
            should support those protocols."
::= { usrIpRTHEntry 3 }
usrIpRTHMetric OBJECT-TYPE
    SYNTAX  Integer32
    MAX-ACCESS  read-write
    STATUS      current
    DESCRIPTION
            "The primary routing metric for this route.  The
            semantics of this metric are determined by the
            routing-protocol specified in the route's
            ipRTHProto value.  If this metric is not used,
            its value should be set to -1."
    --CONFIGURABLE
::= { usrIpRTHEntry 4 }
usrIpRTHClass OBJECT-TYPE
    SYNTAX  Integer32
    MAX-ACCESS  read-write
    STATUS      current
    DESCRIPTION
            "The forward class is preference class associated
            with this route.  There are 3 classes; the lower
            the class the more preferred the route.  
            Local routes are in Class 0.  These are the 
            most preferred routes.
            OSPF Internal routes are also in Class 0.  OSPF
            internal routes are less preferred than Local
            Routes.
            OSPF External routes are Class 1 or Class 2.
            Static configured and RIP routes are Class 1.
            BGP and EGP routes are Class 2."
::= { usrIpRTHEntry 5 }
usrIpRTHFwdFlags OBJECT-TYPE
    SYNTAX  Integer32
    MAX-ACCESS  read-write
    STATUS      current
    DESCRIPTION
            "Forward flags are hints to the forwarding engine
            as to what to do with the incoming packet."
::= { usrIpRTHEntry 6 }
usrIpRTHAge OBJECT-TYPE
    SYNTAX  Integer32
    MAX-ACCESS  read-write
    STATUS      current
    DESCRIPTION
            "The number of seconds since this route was last
            updated or otherwise determined to be correct.
            Note that no semantics of `too old' can be implied
            except through knowledge of the routing protocol
            by which the route was learned."
::= { usrIpRTHEntry 7 }
usrIpRTHNhId OBJECT-TYPE
    SYNTAX  Integer32
    MAX-ACCESS  read-write
    STATUS      current
    DESCRIPTION
            "The index into the globally defined Next Hop
             Block."
::= { usrIpRTHEntry 8 }
usrIpRTHNextHop OBJECT-TYPE
    SYNTAX  IpAddress
    MAX-ACCESS  read-write
    STATUS      current
    DESCRIPTION
            "The IP address of the next hop of this route.
            (In the case of a route bound to an interface
            which is realized via a broadcast media, the value
            of this field is the agent's IP address on that
            interface.)"
    --CONFIGURABLE
::= { usrIpRTHEntry 9 }
usrIpRTHIfIndex OBJECT-TYPE
    SYNTAX  Integer32
    MAX-ACCESS  read-write
    STATUS      current
    DESCRIPTION
            "The index value which uniquely identifies the
            local interface through which the next hop of this
            route should be reached.  The interface identified
            by a particular value of this index is the same
            interface as identified by the same value of
            ifIndex."
::= { usrIpRTHEntry 10 }
-- ------------------------------------------------------------
-- the USR IP Routing Table Entry Structure
usrIpRTE OBJECT-TYPE
    SYNTAX  SEQUENCE OF UsrIpRTEEntry
    MAX-ACCESS  not-accessible
    STATUS      current
    DESCRIPTION
            "This entity's IP Routing table."
::= { usrIpRouting 24 }
usrIpRTEEntry OBJECT-TYPE
    SYNTAX  UsrIpRTEEntry
    MAX-ACCESS  not-accessible
    STATUS      current
    DESCRIPTION
            "A route to a particular destination.
             These routes are learned or written from
             the forwarder and so these objects are
             not accessible for SET via CLI or SNMP.
             The only PDU type implemented is GETNEXT."
    INDEX   { usrIpRTEDest, usrIpRTEMask, usrIpRTEPref,
              usrIpRTEMetric, usrIpRTEProto, usrIpRTENhId }
::= { usrIpRTE 1 }
    UsrIpRTEEntry ::=
              SEQUENCE {
                  usrIpRTEDest      IpAddress,
                  usrIpRTEMask      IpAddress,
                  usrIpRTEProto     INTEGER,
                  usrIpRTEMetric    Integer32,
                  usrIpRTEAge       Integer32,
                  usrIpRTEFwdFlags  Integer32,
                  usrIpRTEPref      Integer32,
                  usrIpRTENhId      Integer32,
                  usrIpRTENextHop   IpAddress,
                  usrIpRTEIfIndex   Integer32
              }
usrIpRTEDest OBJECT-TYPE
    SYNTAX  IpAddress
    MAX-ACCESS  read-write
    STATUS      current
    DESCRIPTION
            "The destination IP address of this route.  An
            entry with a value of 0.0.0.0 is considered a
            default route.  Multiple routes to a single
            destination can appear in the table, but access to
            such multiple entries is dependent on the table-
            access mechanisms defined by the network
            management protocol in use."
    --CONFIGURABLE
::= { usrIpRTEEntry 1 }
usrIpRTEMask OBJECT-TYPE
    SYNTAX  IpAddress
    MAX-ACCESS  read-write
    STATUS      current
    DESCRIPTION
            "Indicate the mask to be logical-ANDed with the
            destination address before being compared to the
            value in the ipRTEDest field.  For those systems
            that do not support arbitrary subnet masks, an
            agent constructs the value of the ipRTEMask by
            determining whether the value of the correspondent
            ipRTEDest field belong to a class-A, B, or C
            network, and then using one of:
                 mask           network
                 255.0.0.0      class-A
                 255.255.0.0    class-B
                 255.255.255.0  class-C
            If the value of the ipRTEDest is 0.0.0.0 (a
            default route), then the mask value is also
            0.0.0.0.  It should be noted that all IP routing
            subsystems implicitly use this mechanism."
    --CONFIGURABLE
::= { usrIpRTEEntry 2 }
usrIpRTEProto OBJECT-TYPE
    SYNTAX  INTEGER {
                other(0),       -- none of the following
                local(1),       -- static local
                remote(2),      -- static remote
                special(3),     -- static special
                                -- the remaining values are
                                -- all gateway routing
                                -- protocols
                ospf(4),        -- OSPF
                ospfExt(5),     -- OSPF External
                ospfDisc3(6),   -- OSPF discard routes
                ospfDisc7(7),   -- OSPF discard routes
                rip(8),         -- RIP
                ripDisc(9),     -- RIP discard routes
                egp(10),        -- EGP
                bgpExt(11),     -- BGP External
                bgpInt(12),     -- BGP Internal
                bgpAggrDisc(13),-- BGP Aggregate
                redistrib(14)   -- Server redistribution
            }
    MAX-ACCESS  read-only
    STATUS      current
    DESCRIPTION
            "The routing mechanism via which this route was
            learned.  Inclusion of values for gateway routing
            protocols is not intended to imply that hosts
            should support those protocols."
::= { usrIpRTEEntry 3 }
usrIpRTEMetric OBJECT-TYPE
    SYNTAX  Integer32
    MAX-ACCESS  read-write
    STATUS      current
    DESCRIPTION
            "The primary routing metric for this route.  The
            semantics of this metric are determined by the
            routing-protocol specified in the route's
            ipRTEProto value.  If this metric is not used,
            its value should be set to -1."
    --CONFIGURABLE
::= { usrIpRTEEntry 4 }
usrIpRTEAge OBJECT-TYPE
    SYNTAX  Integer32
    MAX-ACCESS  read-write
    STATUS      current
    DESCRIPTION
            "The number of seconds since this route was last
            updated or otherwise determined to be correct.
            Note that no semantics of `too old' can be implied
            except through knowledge of the routing protocol
            by which the route was learned."
::= { usrIpRTEEntry 5 }
usrIpRTEFwdFlags OBJECT-TYPE
    SYNTAX  Integer32
    MAX-ACCESS  read-write
    STATUS      current
    DESCRIPTION
            "Forward flags are hints to the forwarding engine
            as to what to do with the incoming packet."
::= { usrIpRTEEntry 6 }
usrIpRTEPref OBJECT-TYPE
    SYNTAX  Integer32
    MAX-ACCESS  read-write
    STATUS      current
    DESCRIPTION
            "The preference associated with this route after
            it has been added to the routing table."
::= { usrIpRTEEntry 7 }
usrIpRTENhId OBJECT-TYPE
    SYNTAX  Integer32
    MAX-ACCESS  read-write
    STATUS      current
    DESCRIPTION
            "The index into the globally defined Next Hop
             Block."
::= { usrIpRTEEntry 8 }
usrIpRTENextHop OBJECT-TYPE
    SYNTAX  IpAddress
    MAX-ACCESS  read-write
    STATUS      current
    DESCRIPTION
            "The IP address of the next hop of this route.
            (In the case of a route bound to an interface
            which is realized via a broadcast media, the value
            of this field is the agent's IP address on that
            interface.)"
    --CONFIGURABLE
::= { usrIpRTEEntry 9 }
usrIpRTEIfIndex OBJECT-TYPE
    SYNTAX  Integer32
    MAX-ACCESS  read-write
    STATUS      current
    DESCRIPTION
            "The index value which uniquely identifies the
            local interface through which the next hop of this
            route should be reached.  The interface identified
            by a particular value of this index is the same
            interface as identified by the same value of
            ifIndex."
::= { usrIpRTEEntry 10 }
usrIpRipRXPacketCount    OBJECT-TYPE
    SYNTAX    Integer32
      MAX-ACCESS    read-only
      STATUS        current
      DESCRIPTION
              "Number of IP RIP packets received."
::= {usrIpRouting 26}
usrIpRipTXPacketCount    OBJECT-TYPE
    SYNTAX    Integer32
      MAX-ACCESS    read-only
      STATUS        current
      DESCRIPTION
              "Number of IP RIP packets transmitted."
::= {usrIpRouting 27}
usrIpRipIncorrectPacketCount    OBJECT-TYPE
    SYNTAX    Integer32
      MAX-ACCESS    read-only
      STATUS        current
      DESCRIPTION
              "Number of incorrect IP RIP packets received."
::= {usrIpRouting 28}
-- ------------------------------------------------------------
END     -- End of USR-IP-ROUTING-MIB DEFINITIONS
--
--	usr_ip_cfg.mib
--
--
-- Author:         Jim Halpin
--
