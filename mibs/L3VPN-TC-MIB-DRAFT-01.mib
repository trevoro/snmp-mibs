-- extracted from draft-ietf-l3vpn-tc-mib-01.txt
-- at Thu Feb  5 06:16:36 2004

L3VPN-TC-MIB-DRAFT-01 DEFINITIONS ::= BEGIN

IMPORTS
   MODULE-IDENTITY, experimental
      FROM SNMPv2-SMI

    TEXTUAL-CONVENTION  
      FROM SNMPv2-TC;

l3vpnTcMIB MODULE-IDENTITY
   LAST-UPDATED "200402031200Z"  -- 03 February 2004 12:00:00 GMT
   ORGANIZATION "Layer 3 Virtual Private Networks
                 (l3vpn) Working Group."
   CONTACT-INFO
          "   Benson Schliesser
              bensons@savvis.net

              Thomas D. Nadeau
              tnadeau@cisco.com

              Comments and discussion to l3vpn@ietf.org"

   DESCRIPTION
        "This MIB contains TCs for L3VPN."

  -- Revision history.
   REVISION "200402031200Z"  -- 03 February 2004 12:00:00 GMT
   DESCRIPTION
      "Updated from PPVPN to L3VPN, and to reflect new MIB
       naming convention."

   REVISION "200211031200Z"  -- 03 November 2002 12:00:00 GMT
   DESCRIPTION
      "Refreshed for IETF web page."

   REVISION "200202281200Z"  -- 28 February 2002 12:00:00 GMT
   DESCRIPTION
      "Initial draft version."

   ::= { experimental 1 } -- to be assigned by IANA

-- definition of textual conventions

VPNId ::= TEXTUAL-CONVENTION
    STATUS current
    DESCRIPTION
        "The purpose of a VPN-ID is to identify a VPN.
         The global VPN Identifier format is:
         3 octet VPN Authority, Organizationally Unique Identifier
         followed by
         4 octet VPN index identifying VPN according to OUI"
    REFERENCE
        "RFC 2685, Fox & Gleeson, 'Virtual Private
         Networks Identifier', September 1999."
    SYNTAX    OCTET STRING (SIZE (0..7))

END

-- 
--    Copyright (C) The Internet Society (2001). All Rights
--    Reserved.
-- 
--    This document and translations of it may be copied and
--    furnished to others, and derivative works that comment on
--    or otherwise explain it or assist in its implementation
--    may be prepared, copied, published and distributed, in
--    whole or in part, without restriction of any kind,
--    provided that the above copyright notice and this
--    paragraph are included on all such copies and derivative
--    works.  However, this document itself may not be modified
--    in any way, such as by removing the copyright notice or
--    references to the Internet Society or other Internet
--    organizations, except as needed for the purpose of
--    developing Internet standards in which case the
--    procedures for copyrights defined in the Internet
--    Standards process must be followed, or as required to
--    translate it into languages other than English.
--    The limited permissions granted above are perpetual and
--    will not be revoked by the Internet Society or its
--    successors or assigns. This document and the information
--    contained herein is provided on an "AS IS" basis and THE
--    INTERNET SOCIETY AND THE INTERNET ENGINEERING TASK FORCE
--    DISCLAIMS ALL WARRANTIES, EXPRESS OR IMPLIED, INCLUDING
--    BUT NOT LIMITED TO ANY WARRANTY THAT THE USE OF THE
--    INFORMATION HEREIN WILL NOT INFRINGE ANY RIGHTS OR ANY
--    IMPLIED WARRANTIES OF MERCHANTABILITY OR FITNESS FOR A
--    PARTICULAR PURPOSE.
-- 
-- 
-- 8.0 Intellectual Property Considerations
-- 
--    The IETF takes no position regarding the validity or scope of any
--    intellectual property or other rights that might be claimed to per-
--    tain to the implementation or use of the technology described in this
--    document or the extent to which any license under such rights might
--    or might not be available; neither does it represent that it has made
--    any effort to identify any such rights.  Information on the IETF's
--    procedures with respect to rights in standards-track and standards-
--    related documentation can be found in BCP-11.  Copies of claims of
--    rights made available for publication and any assurances of licenses
--    to be made available, or the result of an attempt made to obtain a
--    general license or permission for the use of such proprietary rights
--    by implementers or users of this specification can be obtained from
--    the IETF Secretariat.
-- 
--    The IETF invites any interested party to bring to its attention any
--    copyrights, patents or patent applications, or other proprietary
--    rights which may cover technology that may be required to practice
--    this standard.  Please address the information to the IETF Executive
--    Director.
