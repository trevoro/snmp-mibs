ENETEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE,Integer32
			FROM SNMPv2-SMI
		DisplayString
			FROM SNMPv2-TC
		enetExt
			FROM APENT-MIB;

--ENETEXT MIB

    apEnetExtMib MODULE-IDENTITY
	   LAST-UPDATED "9707202000Z" -- Wed July 20 20:00:00 EST 1997
	   ORGANIZATION "ArrowPoint Communications Inc."
	   CONTACT-INFO
	   "                Steven Colby
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  ethernet physical layer management"
      ::= { enetExt 1}

apEnetPhyTable OBJECT-TYPE
	SYNTAX          SEQUENCE OF APENETPhyEntry
	MAX-ACCESS      not-accessible
	STATUS          current
	DESCRIPTION
		""
	::= { enetExt 2 }

apEnetPhyEntry OBJECT-TYPE
	SYNTAX          APENETPhyEntry
	MAX-ACCESS      not-accessible
	STATUS          current
	DESCRIPTION
		""
	INDEX   { apEnetPhyIfIndex }
	::= { apEnetPhyTable 1 }

APENETPhyEntry ::= SEQUENCE {
		apEnetPhyIfIndex       Integer32,
		apEnetPhyConfig        INTEGER,
		apEnetPhyConfigActual  INTEGER,
        apEnetDescr            DisplayString
}

apEnetPhyIfIndex OBJECT-TYPE
	SYNTAX          Integer32
    MAX-ACCESS      read-only
	STATUS          current
	DESCRIPTION     
			"The ifIndex associated with this physical ethernet interface"
	::= { apEnetPhyEntry 1}

apEnetPhyConfig OBJECT-TYPE
	SYNTAX			INTEGER {
							ten-half-duplex(0),
							ten-full-duplex(1),
							hundred-half-duplex(2),
							hundred-full-duplex(3),
							auto-negotiate(4),
							disabled(5),
							hundred-full-duplex-loopback(6),
              giga-full-duplex-no-pause(7),
              giga-full-duplex-asym-pause(8),
              giga-full-duplex-sym-pause(9),
              giga-full-duplex-sym-asym-pause(10),
              giga-full-duplex-loopback(11)
              }
	MAX-ACCESS		read-write
	STATUS			current
	DESCRIPTION
		"The duplex of the physical ethernet interface to configure"
	::= { apEnetPhyEntry 2 }

apEnetPhyConfigActual OBJECT-TYPE
	SYNTAX			INTEGER {
							ten-half-duplex(0),
							ten-full-duplex(1),
							hundred-half-duplex(2),
							hundred-full-duplex(3),
              giga-full-duplex-no-pause(4),
              giga-full-duplex-asym-pause(5),
              giga-full-duplex-sym-pause(6),
              giga-full-duplex-sym-asym-pause(7)
							}
	MAX-ACCESS		read-only
	STATUS			current
	DESCRIPTION
		"The actual duplex of the physical ethernet interface"
	::= { apEnetPhyEntry 3 }

apEnetDescr OBJECT-TYPE
	SYNTAX			DisplayString(SIZE(0..255))
	MAX-ACCESS		read-write
	STATUS			current
	DESCRIPTION
		"A textual string containing information about the interface."
	::= { apEnetPhyEntry 4 }

END
