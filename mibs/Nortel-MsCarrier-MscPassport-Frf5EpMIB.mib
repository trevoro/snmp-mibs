Nortel-MsCarrier-MscPassport-Frf5EpMIB
DEFINITIONS ::= BEGIN



IMPORTS

      OBJECT-TYPE
   FROM RFC-1212

      mscPassportMIBs
   FROM Nortel-MsCarrier-MscPassport-UsefulDefinitionsMIB

      Counter32,
      RowPointer,
      DisplayString,
      StorageType,
      RowStatus,
      Integer32,
      Unsigned32
   FROM Nortel-MsCarrier-MscPassport-StandardTextualConventionsMIB

      AsciiString,
      NonReplicated,
      HexString,
      IntegerSequence
   FROM Nortel-MsCarrier-MscPassport-TextualConventionsMIB

      mscMcsMgrIndex,
      mscMcsMgr
   FROM Nortel-MsCarrier-MscPassport-McsMgrMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Frf5Ep Enterprise MIB."

frf5EpMIB OBJECT IDENTIFIER ::= { mscPassportMIBs 121 }










-- McsMgr Frf5EndPointGroup/n
-- The Frf5EpG component contains FRF.5 End Points that share a 
-- common destination NSAP address, and a list of address prefixes.

mscMcsMgrFrf5EpG OBJECT IDENTIFIER ::= { mscMcsMgr 14 }



mscMcsMgrFrf5EpGRowStatusTable OBJECT-TYPE
   SYNTAX     SEQUENCE OF MscMcsMgrFrf5EpGRowStatusEntry
   ACCESS     not-accessible
   STATUS     mandatory
   DESCRIPTION
     "This entry controls the addition and deletion of 
      mscMcsMgrFrf5EpG components."
::= { mscMcsMgrFrf5EpG 1 }

mscMcsMgrFrf5EpGRowStatusEntry OBJECT-TYPE
   SYNTAX     MscMcsMgrFrf5EpGRowStatusEntry
   ACCESS     not-accessible
   STATUS     mandatory
   DESCRIPTION
     "A single entry in the table represents a single 
      mscMcsMgrFrf5EpG component."
   INDEX {
      mscMcsMgrIndex,
      mscMcsMgrFrf5EpGIndex }
::= { mscMcsMgrFrf5EpGRowStatusTable 1 }

MscMcsMgrFrf5EpGRowStatusEntry ::= SEQUENCE {
   mscMcsMgrFrf5EpGRowStatus
      RowStatus,
   mscMcsMgrFrf5EpGComponentName
      DisplayString,
   mscMcsMgrFrf5EpGStorageType
      StorageType,
   mscMcsMgrFrf5EpGIndex
      Integer32 }

mscMcsMgrFrf5EpGRowStatus OBJECT-TYPE
   SYNTAX     RowStatus 
   ACCESS     read-write
   STATUS     mandatory
   DESCRIPTION
     "This variable is used as the basis for SNMP naming of
      mscMcsMgrFrf5EpG components.
      These components can be added and deleted."
::= { mscMcsMgrFrf5EpGRowStatusEntry 1 }

mscMcsMgrFrf5EpGComponentName OBJECT-TYPE
   SYNTAX     DisplayString 
   ACCESS     read-only
   STATUS     mandatory
   DESCRIPTION
     "This variable provides the component's string name for
      use with the ASCII Console Interface"
::= { mscMcsMgrFrf5EpGRowStatusEntry 2 }

mscMcsMgrFrf5EpGStorageType OBJECT-TYPE
   SYNTAX     StorageType 
   ACCESS     read-only
   STATUS     mandatory
   DESCRIPTION
     "This variable represents the storage type value for the
      mscMcsMgrFrf5EpG tables."
::= { mscMcsMgrFrf5EpGRowStatusEntry 4 }

mscMcsMgrFrf5EpGIndex OBJECT-TYPE
   SYNTAX     Integer32 (1..8191)
   ACCESS     not-accessible
   STATUS     mandatory
   DESCRIPTION
     "This variable represents the index for the mscMcsMgrFrf5EpG tables."
::= { mscMcsMgrFrf5EpGRowStatusEntry 10 }


-- McsMgr Frf5EpG/n Address
-- This component contains the destination NSAP address used by all 
-- FRF.5 End Points provisioned under an Frf5EpG. The Address also 
-- provides the list of address prefixes directed to the end points under 
-- this group.

mscMcsMgrFrf5EpGAddr OBJECT IDENTIFIER ::= { mscMcsMgrFrf5EpG 2 }



mscMcsMgrFrf5EpGAddrRowStatusTable OBJECT-TYPE
   SYNTAX     SEQUENCE OF MscMcsMgrFrf5EpGAddrRowStatusEntry
   ACCESS     not-accessible
   STATUS     mandatory
   DESCRIPTION
     "This entry controls the addition and deletion of 
      mscMcsMgrFrf5EpGAddr components."
::= { mscMcsMgrFrf5EpGAddr 1 }

mscMcsMgrFrf5EpGAddrRowStatusEntry OBJECT-TYPE
   SYNTAX     MscMcsMgrFrf5EpGAddrRowStatusEntry
   ACCESS     not-accessible
   STATUS     mandatory
   DESCRIPTION
     "A single entry in the table represents a single 
      mscMcsMgrFrf5EpGAddr component."
   INDEX {
      mscMcsMgrIndex,
      mscMcsMgrFrf5EpGIndex,
      mscMcsMgrFrf5EpGAddrIndex }
::= { mscMcsMgrFrf5EpGAddrRowStatusTable 1 }

MscMcsMgrFrf5EpGAddrRowStatusEntry ::= SEQUENCE {
   mscMcsMgrFrf5EpGAddrRowStatus
      RowStatus,
   mscMcsMgrFrf5EpGAddrComponentName
      DisplayString,
   mscMcsMgrFrf5EpGAddrStorageType
      StorageType,
   mscMcsMgrFrf5EpGAddrIndex
      NonReplicated }

mscMcsMgrFrf5EpGAddrRowStatus OBJECT-TYPE
   SYNTAX     RowStatus 
   ACCESS     read-only
   STATUS     mandatory
   DESCRIPTION
     "This variable is used as the basis for SNMP naming of
      mscMcsMgrFrf5EpGAddr components.
      These components cannot be added nor deleted."
::= { mscMcsMgrFrf5EpGAddrRowStatusEntry 1 }

mscMcsMgrFrf5EpGAddrComponentName OBJECT-TYPE
   SYNTAX     DisplayString 
   ACCESS     read-only
   STATUS     mandatory
   DESCRIPTION
     "This variable provides the component's string name for
      use with the ASCII Console Interface"
::= { mscMcsMgrFrf5EpGAddrRowStatusEntry 2 }

mscMcsMgrFrf5EpGAddrStorageType OBJECT-TYPE
   SYNTAX     StorageType 
   ACCESS     read-only
   STATUS     mandatory
   DESCRIPTION
     "This variable represents the storage type value for the
      mscMcsMgrFrf5EpGAddr tables."
::= { mscMcsMgrFrf5EpGAddrRowStatusEntry 4 }

mscMcsMgrFrf5EpGAddrIndex OBJECT-TYPE
   SYNTAX     NonReplicated 
   ACCESS     not-accessible
   STATUS     mandatory
   DESCRIPTION
     "This variable represents the index for the mscMcsMgrFrf5EpGAddr tables."
::= { mscMcsMgrFrf5EpGAddrRowStatusEntry 10 }

mscMcsMgrFrf5EpGAddrProvTable OBJECT-TYPE
   SYNTAX     SEQUENCE OF MscMcsMgrFrf5EpGAddrProvEntry
   ACCESS     not-accessible
   STATUS     mandatory
   DESCRIPTION
     "This group contains the provisionable attributes of the Address 
      component."
::= { mscMcsMgrFrf5EpGAddr 10 }

mscMcsMgrFrf5EpGAddrProvEntry OBJECT-TYPE
   SYNTAX     MscMcsMgrFrf5EpGAddrProvEntry
   ACCESS     not-accessible
   STATUS     mandatory
   DESCRIPTION
     "An entry in the mscMcsMgrFrf5EpGAddrProvTable."
   INDEX {
      mscMcsMgrIndex,
      mscMcsMgrFrf5EpGIndex,
      mscMcsMgrFrf5EpGAddrIndex }
::= { mscMcsMgrFrf5EpGAddrProvTable 1 }

MscMcsMgrFrf5EpGAddrProvEntry ::= SEQUENCE {
   mscMcsMgrFrf5EpGAddrRemoteAddress
      AsciiString,
   mscMcsMgrFrf5EpGAddrCommentText
      AsciiString }

mscMcsMgrFrf5EpGAddrRemoteAddress OBJECT-TYPE
   SYNTAX     AsciiString (SIZE (0..44))
   ACCESS     read-write
   STATUS     mandatory
   DESCRIPTION
     "This attribute specifies the ATM End System Address (AESA) in 
      the ISO NSAP format that is used by each EndPoint under this 
      Frf5EpG to establish a VCC. For example, NSAP ATM address 
      '45000006138292323F000000000020480D002900'."
::= { mscMcsMgrFrf5EpGAddrProvEntry 1 }

mscMcsMgrFrf5EpGAddrCommentText OBJECT-TYPE
   SYNTAX     AsciiString (SIZE (0..750))
   ACCESS     read-write
   STATUS     mandatory
   DESCRIPTION
     "This optional attribute contains additional textual information to be 
      added by the network operator."
   DEFVAL     { ''H }  -- ""
::= { mscMcsMgrFrf5EpGAddrProvEntry 2 }

mscMcsMgrFrf5EpGAddrAddrPreTable OBJECT-TYPE
   SYNTAX     SEQUENCE OF MscMcsMgrFrf5EpGAddrAddrPreEntry
   ACCESS     not-accessible
   STATUS     mandatory
   DESCRIPTION
     "This attribute specifies the list of prefixes directed to the EndPoints 
      under this Frf5EndPointGroup. The individual end point is selected 
      for each subconnection on the basis of its 
      supportedTransferPriorities.
      For example, E.164 prefix 'e.613722', X.121 prefix 'x.302'."
::= { mscMcsMgrFrf5EpGAddr 362 }

mscMcsMgrFrf5EpGAddrAddrPreEntry OBJECT-TYPE
   SYNTAX     MscMcsMgrFrf5EpGAddrAddrPreEntry
   ACCESS     not-accessible
   STATUS     mandatory
   DESCRIPTION
     "An entry in the mscMcsMgrFrf5EpGAddrAddrPreTable."
   INDEX {
      mscMcsMgrIndex,
      mscMcsMgrFrf5EpGIndex,
      mscMcsMgrFrf5EpGAddrIndex,
      mscMcsMgrFrf5EpGAddrAddrPreValue }
::= { mscMcsMgrFrf5EpGAddrAddrPreTable 1 }

MscMcsMgrFrf5EpGAddrAddrPreEntry ::= SEQUENCE {
   mscMcsMgrFrf5EpGAddrAddrPreValue
      AsciiString,
   mscMcsMgrFrf5EpGAddrAddrPreRowStatus
      RowStatus }

mscMcsMgrFrf5EpGAddrAddrPreValue OBJECT-TYPE
   SYNTAX     AsciiString (SIZE (3..17))
   ACCESS     read-write
   STATUS     mandatory
   DESCRIPTION
     "This variable represents both the value and the index for the
      mscMcsMgrFrf5EpGAddrAddrPreTable."
::= { mscMcsMgrFrf5EpGAddrAddrPreEntry 1 }

mscMcsMgrFrf5EpGAddrAddrPreRowStatus OBJECT-TYPE
   SYNTAX     RowStatus 
   ACCESS     write-only
   STATUS     mandatory
   DESCRIPTION
     "This variable is used to control the addition and deletion 
      of individual values of the mscMcsMgrFrf5EpGAddrAddrPreTable."
::= { mscMcsMgrFrf5EpGAddrAddrPreEntry 2 }


-- McsMgr Frf5EpG/n EndPoint/n
-- The EndPoint component represents a single ATM VCC that can 
-- multiplex multiple Frame Relay DLCIs.

mscMcsMgrFrf5EpGEp OBJECT IDENTIFIER ::= { mscMcsMgrFrf5EpG 3 }



mscMcsMgrFrf5EpGEpRowStatusTable OBJECT-TYPE
   SYNTAX     SEQUENCE OF MscMcsMgrFrf5EpGEpRowStatusEntry
   ACCESS     not-accessible
   STATUS     mandatory
   DESCRIPTION
     "This entry controls the addition and deletion of 
      mscMcsMgrFrf5EpGEp components."
::= { mscMcsMgrFrf5EpGEp 1 }

mscMcsMgrFrf5EpGEpRowStatusEntry OBJECT-TYPE
   SYNTAX     MscMcsMgrFrf5EpGEpRowStatusEntry
   ACCESS     not-accessible
   STATUS     mandatory
   DESCRIPTION
     "A single entry in the table represents a single 
      mscMcsMgrFrf5EpGEp component."
   INDEX {
      mscMcsMgrIndex,
      mscMcsMgrFrf5EpGIndex,
      mscMcsMgrFrf5EpGEpIndex }
::= { mscMcsMgrFrf5EpGEpRowStatusTable 1 }

MscMcsMgrFrf5EpGEpRowStatusEntry ::= SEQUENCE {
   mscMcsMgrFrf5EpGEpRowStatus
      RowStatus,
   mscMcsMgrFrf5EpGEpComponentName
      DisplayString,
   mscMcsMgrFrf5EpGEpStorageType
      StorageType,
   mscMcsMgrFrf5EpGEpIndex
      Integer32 }

mscMcsMgrFrf5EpGEpRowStatus OBJECT-TYPE
   SYNTAX     RowStatus 
   ACCESS     read-write
   STATUS     mandatory
   DESCRIPTION
     "This variable is used as the basis for SNMP naming of
      mscMcsMgrFrf5EpGEp components.
      These components can be added and deleted."
::= { mscMcsMgrFrf5EpGEpRowStatusEntry 1 }

mscMcsMgrFrf5EpGEpComponentName OBJECT-TYPE
   SYNTAX     DisplayString 
   ACCESS     read-only
   STATUS     mandatory
   DESCRIPTION
     "This variable provides the component's string name for
      use with the ASCII Console Interface"
::= { mscMcsMgrFrf5EpGEpRowStatusEntry 2 }

mscMcsMgrFrf5EpGEpStorageType OBJECT-TYPE
   SYNTAX     StorageType 
   ACCESS     read-only
   STATUS     mandatory
   DESCRIPTION
     "This variable represents the storage type value for the
      mscMcsMgrFrf5EpGEp tables."
::= { mscMcsMgrFrf5EpGEpRowStatusEntry 4 }

mscMcsMgrFrf5EpGEpIndex OBJECT-TYPE
   SYNTAX     Integer32 (0..15)
   ACCESS     not-accessible
   STATUS     mandatory
   DESCRIPTION
     "This variable represents the index for the mscMcsMgrFrf5EpGEp tables."
::= { mscMcsMgrFrf5EpGEpRowStatusEntry 10 }

mscMcsMgrFrf5EpGEpStateTable OBJECT-TYPE
   SYNTAX     SEQUENCE OF MscMcsMgrFrf5EpGEpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscMcsMgrFrf5EpGEp 10 }

mscMcsMgrFrf5EpGEpStateEntry OBJECT-TYPE
   SYNTAX     MscMcsMgrFrf5EpGEpStateEntry
   ACCESS     not-accessible
   STATUS     mandatory
   DESCRIPTION
     "An entry in the mscMcsMgrFrf5EpGEpStateTable."
   INDEX {
      mscMcsMgrIndex,
      mscMcsMgrFrf5EpGIndex,
      mscMcsMgrFrf5EpGEpIndex }
::= { mscMcsMgrFrf5EpGEpStateTable 1 }

MscMcsMgrFrf5EpGEpStateEntry ::= SEQUENCE {
   mscMcsMgrFrf5EpGEpAdminState
      INTEGER,
   mscMcsMgrFrf5EpGEpOperationalState
      INTEGER,
   mscMcsMgrFrf5EpGEpUsageState
      INTEGER,
   mscMcsMgrFrf5EpGEpAvailabilityStatus
      OCTET STRING,
   mscMcsMgrFrf5EpGEpProceduralStatus
      OCTET STRING,
   mscMcsMgrFrf5EpGEpControlStatus
      OCTET STRING,
   mscMcsMgrFrf5EpGEpAlarmStatus
      OCTET STRING,
   mscMcsMgrFrf5EpGEpStandbyStatus
      INTEGER,
   mscMcsMgrFrf5EpGEpUnknownStatus
      INTEGER }

mscMcsMgrFrf5EpGEpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscMcsMgrFrf5EpGEpStateEntry 1 }

mscMcsMgrFrf5EpGEpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscMcsMgrFrf5EpGEpStateEntry 2 }

mscMcsMgrFrf5EpGEpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscMcsMgrFrf5EpGEpStateEntry 3 }

mscMcsMgrFrf5EpGEpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscMcsMgrFrf5EpGEpStateEntry 4 }

mscMcsMgrFrf5EpGEpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscMcsMgrFrf5EpGEpStateEntry 5 }

mscMcsMgrFrf5EpGEpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscMcsMgrFrf5EpGEpStateEntry 6 }

mscMcsMgrFrf5EpGEpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscMcsMgrFrf5EpGEpStateEntry 7 }

mscMcsMgrFrf5EpGEpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscMcsMgrFrf5EpGEpStateEntry 8 }

mscMcsMgrFrf5EpGEpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscMcsMgrFrf5EpGEpStateEntry 9 }

mscMcsMgrFrf5EpGEpOperTable OBJECT-TYPE
   SYNTAX     SEQUENCE OF MscMcsMgrFrf5EpGEpOperEntry
   ACCESS     not-accessible
   STATUS     mandatory
   DESCRIPTION
     "This group contains the operational attributes for the FRF.5 ATM 
      connection."
::= { mscMcsMgrFrf5EpGEp 11 }

mscMcsMgrFrf5EpGEpOperEntry OBJECT-TYPE
   SYNTAX     MscMcsMgrFrf5EpGEpOperEntry
   ACCESS     not-accessible
   STATUS     mandatory
   DESCRIPTION
     "An entry in the mscMcsMgrFrf5EpGEpOperTable."
   INDEX {
      mscMcsMgrIndex,
      mscMcsMgrFrf5EpGIndex,
      mscMcsMgrFrf5EpGEpIndex }
::= { mscMcsMgrFrf5EpGEpOperTable 1 }

MscMcsMgrFrf5EpGEpOperEntry ::= SEQUENCE {
   mscMcsMgrFrf5EpGEpLastVccClearCause
      Unsigned32,
   mscMcsMgrFrf5EpGEpConnectionTransferPriority
      Unsigned32,
   mscMcsMgrFrf5EpGEpServiceCategory
      INTEGER,
   mscMcsMgrFrf5EpGEpPeakCellRate01
      Unsigned32,
   mscMcsMgrFrf5EpGEpSustainedCellRate0
      Unsigned32,
   mscMcsMgrFrf5EpGEpSustainedCellRate01
      Unsigned32,
   mscMcsMgrFrf5EpGEpMaximumBurstSize0
      Unsigned32,
   mscMcsMgrFrf5EpGEpMaximumBurstSize01
      Unsigned32,
   mscMcsMgrFrf5EpGEpAvgFrameSize
      Unsigned32,
   mscMcsMgrFrf5EpGEpTrafficParmConversionPolicy
      INTEGER,
   mscMcsMgrFrf5EpGEpType
      INTEGER,
   mscMcsMgrFrf5EpGEpLastVccCauseDiag
      HexString }

mscMcsMgrFrf5EpGEpLastVccClearCause OBJECT-TYPE
   SYNTAX     Unsigned32 (0..255)
   ACCESS     read-only
   STATUS     mandatory
   DESCRIPTION
     "This attribute indicates the clear cause value of the last SPVC 
      release message received on the FRF.5 end point Vcc pipe."
::= { mscMcsMgrFrf5EpGEpOperEntry 4 }

mscMcsMgrFrf5EpGEpConnectionTransferPriority OBJECT-TYPE
   SYNTAX     Unsigned32 (0..15)
   ACCESS     read-only
   STATUS     mandatory
   DESCRIPTION
     "This attribute indicates the transfer priority used to establish the 
      ATM connection and to multiplex the Frame Relay DLCIs."
::= { mscMcsMgrFrf5EpGEpOperEntry 5 }

mscMcsMgrFrf5EpGEpServiceCategory OBJECT-TYPE
   SYNTAX     INTEGER  {
                 ubr(0),
                 cbr(1),
                 rtVbr(2),
                 nrtVbr(3) }
   ACCESS     read-only
   STATUS     mandatory
   DESCRIPTION
     "This attribute indicates the ATM service category that is used for 
      this connection."
::= { mscMcsMgrFrf5EpGEpOperEntry 6 }

mscMcsMgrFrf5EpGEpPeakCellRate01 OBJECT-TYPE
   SYNTAX     Unsigned32 (0..4294967295)
   ACCESS     read-only
   STATUS     mandatory
   DESCRIPTION
     "This attribute indicates the Peak Cell Rate (PCR) of the FRF.5 ATM 
      VCC for all cells (with CLP=0 and CLP=1).
      The pcr01 is derived from the End Point traffic parameters using the 
      conversion policy of the connectionTransferPriority. The 
      conversion policy is defined under the ModuleData 
      FrameRelayService AtmNetworking TransferPriority/n component."
::= { mscMcsMgrFrf5EpGEpOperEntry 8 }

mscMcsMgrFrf5EpGEpSustainedCellRate0 OBJECT-TYPE
   SYNTAX     Unsigned32 (0..4294967295)
   ACCESS     read-only
   STATUS     mandatory
   DESCRIPTION
     "This attribute indicates the Sustained Cell Rate (SCR) of the FRF.5 
      ATM VCC for high priority cells (with CLP=0).
      The scr0 is derived from the End Point traffic parameters using the 
      conversion policy of the connectionTransferPriority. The 
      conversion policy is defined under the ModuleData 
      FrameRelayService AtmNetworking TransferPriority/n component."
::= { mscMcsMgrFrf5EpGEpOperEntry 9 }

mscMcsMgrFrf5EpGEpSustainedCellRate01 OBJECT-TYPE
   SYNTAX     Unsigned32 (0..4294967295)
   ACCESS     read-only
   STATUS     mandatory
   DESCRIPTION
     "This attribute indicates the Sustained Cell Rate (SCR) of the FRF.5 
      ATM VCC for all cells (with CLP=0 and CLP=1).
      The scr01 is derived from the End Point traffic parameters using the 
      conversion policy of the connectionTransferPriority. The 
      conversion policy is defined under the ModuleData 
      FrameRelayService AtmNetworking TransferPriority/n component."
::= { mscMcsMgrFrf5EpGEpOperEntry 10 }

mscMcsMgrFrf5EpGEpMaximumBurstSize0 OBJECT-TYPE
   SYNTAX     Unsigned32 (0..4294967295)
   ACCESS     read-only
   STATUS     mandatory
   DESCRIPTION
     "This attribute indicates the Maximum Burst Size (MBS) of the 
      FRF.5 ATM VCC for high priority cells (with CLP=0).
      The mbs0 is derived from the End Point traffic parameters using the 
      conversion policy of the connectionTransferPriority. The 
      conversion policy is defined under the ModuleData 
      FrameRelayService AtmNetworking TransferPriority/n component."
::= { mscMcsMgrFrf5EpGEpOperEntry 11 }

mscMcsMgrFrf5EpGEpMaximumBurstSize01 OBJECT-TYPE
   SYNTAX     Unsigned32 (0..4294967295)
   ACCESS     read-only
   STATUS     mandatory
   DESCRIPTION
     "This attribute indicates the Maximum Burst Size (MBS) of the 
      FRF.5 ATM VCC for all cells (with CLP=0 and CLP=1).
      The mbs01 is derived from the End Point traffic parameters using 
      the conversion policy of the connectionTransferPriority. The 
      conversion policy is defined under the ModuleData 
      FrameRelayService AtmNetworking TransferPriority/n component."
::= { mscMcsMgrFrf5EpGEpOperEntry 12 }

mscMcsMgrFrf5EpGEpAvgFrameSize OBJECT-TYPE
   SYNTAX     Unsigned32 (1..8187)
   ACCESS     read-only
   STATUS     mandatory
   DESCRIPTION
     "This attribute indicates the average frame size that is used in the 
      traffic parameter conversion policy calculations for this end point."
   DEFVAL     { 128 }
::= { mscMcsMgrFrf5EpGEpOperEntry 13 }

mscMcsMgrFrf5EpGEpTrafficParmConversionPolicy OBJECT-TYPE
   SYNTAX     INTEGER  {
                 n3(3),
                 n4(4),
                 n5(5),
                 n6(6) }
   ACCESS     read-only
   STATUS     mandatory
   DESCRIPTION
     "This attribute indicates the traffic parameter conversion policy used 
      to specify the equivalent ATM bandwidth rate at this end point.
      
      Policy 3 characterizes the traffic in the following way:
      - ATM traffic descriptor type 6 is selected
      - PCR0+1 is based on the AR
      - SCR0+1 is based on the CIR and EIR
      - MBS0+1 is based on Bc,Be,CIR,EIR and AR
      - Takes into account that the instananeous rate of the frame relay 
      stream can burst above CIR and up tp the AR.
      
      Policy 4 characterizes the traffic in the following way:
      - ATM traffic descriptor type 7 or 8 is selected. Type 7 is chosen 
      when non-conforming cells are to be discarded and type 8 when 
      non-conforming cells are tagged by UPC traffic policer.
      - PCR0+1 is based on the AR
      - SCR0 is based on the CIR
      - MBS0 is based on Bc,CIR and AR
      - There is no direct characterization of EIR. The allowed EIR can be 
      derived using the difference between the AR and CIR.
      
      Policy 5 characterizes the traffic in the following way:
      - ATM traffic descriptor type 7 or 8 is selected . Type 7 is chosen 
      when non-conforming cells are to be discarded and type 8 when 
      non-conforming cells are tagged by UPC traffic policer
      - PCR0+1 is based on CIR and EIR
      - SCR0 is based on the CIR
      - MBS0 is based on the Bc,CIR and AR
      - The maximum PCR is no longer based on AR but based on the 
      CIR and EIR.
      
      Policy 6 characterizes the traffic in the following way:
      - ATM traffic descriptor type 3 is selected
      - PCR0+1 is based only on CIR."
::= { mscMcsMgrFrf5EpGEpOperEntry 14 }

mscMcsMgrFrf5EpGEpType OBJECT-TYPE
   SYNTAX     INTEGER  {
                 master(0),
                 slave(1) }
   ACCESS     read-only
   STATUS     mandatory
   DESCRIPTION
     "This attribute indicates the FRF.5 End Point type. If the value is 
      master, this End Point is responsible for initiating the call to set up 
      the FRF.5 ATM VCC. If the value is slave, this End Point receives 
      call setup requests from the remote end."
::= { mscMcsMgrFrf5EpGEpOperEntry 15 }

mscMcsMgrFrf5EpGEpLastVccCauseDiag OBJECT-TYPE
   SYNTAX     HexString (SIZE (1..8))
   ACCESS     read-only
   STATUS     mandatory
   DESCRIPTION
     "This attribute indicates the diagnostic value of the last SPVC release 
      message received on the FRF.5 end point Vcc pipe."
::= { mscMcsMgrFrf5EpGEpOperEntry 20 }


-- DsMgr Frf5EpG/n Ep/m LocalManagementInterface
-- This component defines the parameters for implementing the Frame 
-- Relay Forum FRF.5 Local Management Interface protocol.

mscMcsMgrFrf5EpGEpLmi OBJECT IDENTIFIER ::= { mscMcsMgrFrf5EpGEp 2 }



mscMcsMgrFrf5EpGEpLmiRowStatusTable OBJECT-TYPE
   SYNTAX     SEQUENCE OF MscMcsMgrFrf5EpGEpLmiRowStatusEntry
   ACCESS     not-accessible
   STATUS     mandatory
   DESCRIPTION
     "This entry controls the addition and deletion of 
      mscMcsMgrFrf5EpGEpLmi components."
::= { mscMcsMgrFrf5EpGEpLmi 1 }

mscMcsMgrFrf5EpGEpLmiRowStatusEntry OBJECT-TYPE
   SYNTAX     MscMcsMgrFrf5EpGEpLmiRowStatusEntry
   ACCESS     not-accessible
   STATUS     mandatory
   DESCRIPTION
     "A single entry in the table represents a single 
      mscMcsMgrFrf5EpGEpLmi component."
   INDEX {
      mscMcsMgrIndex,
      mscMcsMgrFrf5EpGIndex,
      mscMcsMgrFrf5EpGEpIndex,
      mscMcsMgrFrf5EpGEpLmiIndex }
::= { mscMcsMgrFrf5EpGEpLmiRowStatusTable 1 }

MscMcsMgrFrf5EpGEpLmiRowStatusEntry ::= SEQUENCE {
   mscMcsMgrFrf5EpGEpLmiRowStatus
      RowStatus,
   mscMcsMgrFrf5EpGEpLmiComponentName
      DisplayString,
   mscMcsMgrFrf5EpGEpLmiStorageType
      StorageType,
   mscMcsMgrFrf5EpGEpLmiIndex
      NonReplicated }

mscMcsMgrFrf5EpGEpLmiRowStatus OBJECT-TYPE
   SYNTAX     RowStatus 
   ACCESS     read-write
   STATUS     mandatory
   DESCRIPTION
     "This variable is used as the basis for SNMP naming of
      mscMcsMgrFrf5EpGEpLmi components.
      These components can be added and deleted."
::= { mscMcsMgrFrf5EpGEpLmiRowStatusEntry 1 }

mscMcsMgrFrf5EpGEpLmiComponentName OBJECT-TYPE
   SYNTAX     DisplayString 
   ACCESS     read-only
   STATUS     mandatory
   DESCRIPTION
     "This variable provides the component's string name for
      use with the ASCII Console Interface"
::= { mscMcsMgrFrf5EpGEpLmiRowStatusEntry 2 }

mscMcsMgrFrf5EpGEpLmiStorageType OBJECT-TYPE
   SYNTAX     StorageType 
   ACCESS     read-only
   STATUS     mandatory
   DESCRIPTION
     "This variable represents the storage type value for the
      mscMcsMgrFrf5EpGEpLmi tables."
::= { mscMcsMgrFrf5EpGEpLmiRowStatusEntry 4 }

mscMcsMgrFrf5EpGEpLmiIndex OBJECT-TYPE
   SYNTAX     NonReplicated 
   ACCESS     not-accessible
   STATUS     mandatory
   DESCRIPTION
     "This variable represents the index for the mscMcsMgrFrf5EpGEpLmi tables."
::= { mscMcsMgrFrf5EpGEpLmiRowStatusEntry 10 }

mscMcsMgrFrf5EpGEpLmiParmsTable OBJECT-TYPE
   SYNTAX     SEQUENCE OF MscMcsMgrFrf5EpGEpLmiParmsEntry
   ACCESS     not-accessible
   STATUS     mandatory
   DESCRIPTION
     "This group contains the provisionable attributes of the Local 
      Management Interface component."
::= { mscMcsMgrFrf5EpGEpLmi 10 }

mscMcsMgrFrf5EpGEpLmiParmsEntry OBJECT-TYPE
   SYNTAX     MscMcsMgrFrf5EpGEpLmiParmsEntry
   ACCESS     not-accessible
   STATUS     mandatory
   DESCRIPTION
     "An entry in the mscMcsMgrFrf5EpGEpLmiParmsTable."
   INDEX {
      mscMcsMgrIndex,
      mscMcsMgrFrf5EpGIndex,
      mscMcsMgrFrf5EpGEpIndex,
      mscMcsMgrFrf5EpGEpLmiIndex }
::= { mscMcsMgrFrf5EpGEpLmiParmsTable 1 }

MscMcsMgrFrf5EpGEpLmiParmsEntry ::= SEQUENCE {
   mscMcsMgrFrf5EpGEpLmiProcedures
      INTEGER,
   mscMcsMgrFrf5EpGEpLmiAsyncStatusReport
      INTEGER,
   mscMcsMgrFrf5EpGEpLmiErrorEventThreshold
      Unsigned32,
   mscMcsMgrFrf5EpGEpLmiEventCount
      Unsigned32,
   mscMcsMgrFrf5EpGEpLmiCheckPointTimer
      Unsigned32,
   mscMcsMgrFrf5EpGEpLmiSide
      INTEGER }

mscMcsMgrFrf5EpGEpLmiProcedures OBJECT-TYPE
   SYNTAX     INTEGER  {
                 none(0),
                 ansi(2),
                 ccitt(3) }
   ACCESS     read-write
   STATUS     mandatory
   DESCRIPTION
     "This attribute selects the procedures to be used for the Local 
      Management Interface. The following are the supported procedures:
      
      none: no Local Management Interface procedures are running on 
      the ATM VCC. This accomodates remote interworking functions 
      which do not implement LMI procedures. In this case, the 
      remaining attributes of this group will be ignored.
      
      ccitt: Local Management Interface procedures from the CCITT 
      specification are supported. Dlci/0 is used for the LMI protocol, to 
      comply with FRF.5. 
      
      ansi: Local Management Interface procedures from the ANSI 
      specification are supported. DLCI 0 is used for the LMI protocol."
   DEFVAL     { ccitt }
::= { mscMcsMgrFrf5EpGEpLmiParmsEntry 1 }

mscMcsMgrFrf5EpGEpLmiAsyncStatusReport OBJECT-TYPE
   SYNTAX     INTEGER  {
                 off(0),
                 on(1) }
   ACCESS     read-write
   STATUS     mandatory
   DESCRIPTION
     "This attribute selects the use of asynchronous PVC status report 
      procedures as specified in the CCITT specification (ITU-T Q.933, 
      Annex A), and the ANSI specification Annex D."
   DEFVAL     { on }
::= { mscMcsMgrFrf5EpGEpLmiParmsEntry 2 }

mscMcsMgrFrf5EpGEpLmiErrorEventThreshold OBJECT-TYPE
   SYNTAX     Unsigned32 (1..10)
   ACCESS     read-write
   STATUS     mandatory
   DESCRIPTION
     "For the network side procedure, an event is defined as follows: (1) 
      receipt of a STATUS ENQUIRY message, or (2) expiration of timer 
      T392. An error event is (1) nonreceipt of STATUS ENQUIRY in 
      T392 seconds; (2) invalid format of an LMI message; (3) invalid 
      receive sequence number.
      For the user side procedure, an event is defined as a polling cycle or 
      a status enquiry and status report exchange. An error event is (1) 
      non-receipt of a STATUS within the polling cycle, or (2) invalid 
      format of an LMI message, or (3) invalid sequence number.
      
      This attribute specifies the number of error events which, if they 
      occur within eventCount events, will cause a protocol error 
      condition. The condition is cleared after eventCount sequential 
      correct events occur.
      
      It must be less than or equal to eventCount (n393)."
   DEFVAL     { 3 }
::= { mscMcsMgrFrf5EpGEpLmiParmsEntry 3 }

mscMcsMgrFrf5EpGEpLmiEventCount OBJECT-TYPE
   SYNTAX     Unsigned32 (1..10)
   ACCESS     read-write
   STATUS     mandatory
   DESCRIPTION
     "This attribute specifies the number of contiguous events within 
      which no more than eventErrorThreshold error events are allowed.
      
      It must be greater than or equal to errorEventThreshold (n392)."
   DEFVAL     { 4 }
::= { mscMcsMgrFrf5EpGEpLmiParmsEntry 4 }

mscMcsMgrFrf5EpGEpLmiCheckPointTimer OBJECT-TYPE
   SYNTAX     Unsigned32 (5..255)
   ACCESS     read-write
   STATUS     mandatory
   DESCRIPTION
     "This attribute selects the time (in seconds) within which a STATUS 
      ENQUIRY message is expected. It must be greater than 
      linkVerificationTimer (t391)."
   DEFVAL     { 200 }
::= { mscMcsMgrFrf5EpGEpLmiParmsEntry 5 }

mscMcsMgrFrf5EpGEpLmiSide OBJECT-TYPE
   SYNTAX     INTEGER  {
                 network(0),
                 user(1),
                 both(2) }
   ACCESS     read-write
   STATUS     mandatory
   DESCRIPTION
     "This attribute selects the user side procedure (DTE), or the network 
      side procedure (DCE), or both the user side and the network side 
      procedures of the LMI. 
      
      This attribute can be set to user, network or both."
   DEFVAL     { both }
::= { mscMcsMgrFrf5EpGEpLmiParmsEntry 8 }

mscMcsMgrFrf5EpGEpLmiNniParmsTable OBJECT-TYPE
   SYNTAX     SEQUENCE OF MscMcsMgrFrf5EpGEpLmiNniParmsEntry
   ACCESS     not-accessible
   STATUS     mandatory
   DESCRIPTION
     "This group contains the provisionable attributes of the FRF.5 LMI 
      procedures which are unique to NNI."
::= { mscMcsMgrFrf5EpGEpLmi 11 }

mscMcsMgrFrf5EpGEpLmiNniParmsEntry OBJECT-TYPE
   SYNTAX     MscMcsMgrFrf5EpGEpLmiNniParmsEntry
   ACCESS     not-accessible
   STATUS     mandatory
   DESCRIPTION
     "An entry in the mscMcsMgrFrf5EpGEpLmiNniParmsTable."
   INDEX {
      mscMcsMgrIndex,
      mscMcsMgrFrf5EpGIndex,
      mscMcsMgrFrf5EpGEpIndex,
      mscMcsMgrFrf5EpGEpLmiIndex }
::= { mscMcsMgrFrf5EpGEpLmiNniParmsTable 1 }

MscMcsMgrFrf5EpGEpLmiNniParmsEntry ::= SEQUENCE {
   mscMcsMgrFrf5EpGEpLmiFullStatusPollingCycles
      Unsigned32,
   mscMcsMgrFrf5EpGEpLmiLinkVerificationTimer
      Unsigned32 }

mscMcsMgrFrf5EpGEpLmiFullStatusPollingCycles OBJECT-TYPE
   SYNTAX     Unsigned32 (1..255)
   ACCESS     read-write
   STATUS     mandatory
   DESCRIPTION
     "This attribute specifies how frequently the FRF.5 LMI initiates a 
      Status Enquiry for a full PVC status report. A polling cycle is a 
      Status Enquiry and Status Report exchange."
   DEFVAL     { 1 }
::= { mscMcsMgrFrf5EpGEpLmiNniParmsEntry 1 }

mscMcsMgrFrf5EpGEpLmiLinkVerificationTimer OBJECT-TYPE
   SYNTAX     Unsigned32 (5..255)
   ACCESS     read-write
   STATUS     mandatory
   DESCRIPTION
     "This attribute specifies how frequently the FRF.5 LMI initiates a 
      Status Enquiry for link integrity verification. It must be less than 
      checkPointTimer (t392)."
   DEFVAL     { 180 }
::= { mscMcsMgrFrf5EpGEpLmiNniParmsEntry 2 }

mscMcsMgrFrf5EpGEpLmiStateTable OBJECT-TYPE
   SYNTAX     SEQUENCE OF MscMcsMgrFrf5EpGEpLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscMcsMgrFrf5EpGEpLmi 12 }

mscMcsMgrFrf5EpGEpLmiStateEntry OBJECT-TYPE
   SYNTAX     MscMcsMgrFrf5EpGEpLmiStateEntry
   ACCESS     not-accessible
   STATUS     mandatory
   DESCRIPTION
     "An entry in the mscMcsMgrFrf5EpGEpLmiStateTable."
   INDEX {
      mscMcsMgrIndex,
      mscMcsMgrFrf5EpGIndex,
      mscMcsMgrFrf5EpGEpIndex,
      mscMcsMgrFrf5EpGEpLmiIndex }
::= { mscMcsMgrFrf5EpGEpLmiStateTable 1 }

MscMcsMgrFrf5EpGEpLmiStateEntry ::= SEQUENCE {
   mscMcsMgrFrf5EpGEpLmiAdminState
      INTEGER,
   mscMcsMgrFrf5EpGEpLmiOperationalState
      INTEGER,
   mscMcsMgrFrf5EpGEpLmiUsageState
      INTEGER }

mscMcsMgrFrf5EpGEpLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscMcsMgrFrf5EpGEpLmiStateEntry 1 }

mscMcsMgrFrf5EpGEpLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscMcsMgrFrf5EpGEpLmiStateEntry 2 }

mscMcsMgrFrf5EpGEpLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscMcsMgrFrf5EpGEpLmiStateEntry 3 }

mscMcsMgrFrf5EpGEpLmiPsiTable OBJECT-TYPE
   SYNTAX     SEQUENCE OF MscMcsMgrFrf5EpGEpLmiPsiEntry
   ACCESS     not-accessible
   STATUS     mandatory
   DESCRIPTION
     "This group provides the protocol status of the Local Management 
      Interface."
::= { mscMcsMgrFrf5EpGEpLmi 13 }

mscMcsMgrFrf5EpGEpLmiPsiEntry OBJECT-TYPE
   SYNTAX     MscMcsMgrFrf5EpGEpLmiPsiEntry
   ACCESS     not-accessible
   STATUS     mandatory
   DESCRIPTION
     "An entry in the mscMcsMgrFrf5EpGEpLmiPsiTable."
   INDEX {
      mscMcsMgrIndex,
      mscMcsMgrFrf5EpGIndex,
      mscMcsMgrFrf5EpGEpIndex,
      mscMcsMgrFrf5EpGEpLmiIndex }
::= { mscMcsMgrFrf5EpGEpLmiPsiTable 1 }

MscMcsMgrFrf5EpGEpLmiPsiEntry ::= SEQUENCE {
   mscMcsMgrFrf5EpGEpLmiProtocolStatus
      INTEGER }

mscMcsMgrFrf5EpGEpLmiProtocolStatus OBJECT-TYPE
   SYNTAX     INTEGER  {
                 errorCondition(0),
                 normalCondition(1) }
   ACCESS     read-only
   STATUS     mandatory
   DESCRIPTION
     "This attribute indicates whether the LMI is in an error condition or 
      whether the protocol is behaving normally. This attribute will be set 
      to errorCondition after enough LMI errors have been detected to 
      warrant a change in condition. This occurs when n392 of the last 
      n393 events are in error.
      The error condition is lifted when a sufficient number of 
      consecutive events has occurred without error. This occurs when 
      n393 consecutive good events take place.
      The consequence of an error condition is that all DLCIs on this 
      interface will become inactive in both directions."
   DEFVAL     { normalCondition }
::= { mscMcsMgrFrf5EpGEpLmiPsiEntry 1 }

mscMcsMgrFrf5EpGEpLmiStatsTable OBJECT-TYPE
   SYNTAX     SEQUENCE OF MscMcsMgrFrf5EpGEpLmiStatsEntry
   ACCESS     not-accessible
   STATUS     mandatory
   DESCRIPTION
     "This group contains the operational statistics for the FRF.5 NNI 
      Local Management Interface."
::= { mscMcsMgrFrf5EpGEpLmi 14 }

mscMcsMgrFrf5EpGEpLmiStatsEntry OBJECT-TYPE
   SYNTAX     MscMcsMgrFrf5EpGEpLmiStatsEntry
   ACCESS     not-accessible
   STATUS     mandatory
   DESCRIPTION
     "An entry in the mscMcsMgrFrf5EpGEpLmiStatsTable."
   INDEX {
      mscMcsMgrIndex,
      mscMcsMgrFrf5EpGIndex,
      mscMcsMgrFrf5EpGEpIndex,
      mscMcsMgrFrf5EpGEpLmiIndex }
::= { mscMcsMgrFrf5EpGEpLmiStatsTable 1 }

MscMcsMgrFrf5EpGEpLmiStatsEntry ::= SEQUENCE {
   mscMcsMgrFrf5EpGEpLmiKeepAliveStatusToInterface
      Counter32,
   mscMcsMgrFrf5EpGEpLmiFullStatusToInterface
      Counter32,
   mscMcsMgrFrf5EpGEpLmiKeepAliveStatusEnqFromInterface
      Counter32,
   mscMcsMgrFrf5EpGEpLmiFullStatusEnqFromInterface
      Counter32,
   mscMcsMgrFrf5EpGEpLmiNetworkSideEventHistory
      AsciiString,
   mscMcsMgrFrf5EpGEpLmiUserSideEventHistory
      AsciiString,
   mscMcsMgrFrf5EpGEpLmiProtocolErrors
      Counter32,
   mscMcsMgrFrf5EpGEpLmiUnexpectedIes
      Counter32,
   mscMcsMgrFrf5EpGEpLmiSequenceErrors
      Counter32,
   mscMcsMgrFrf5EpGEpLmiStatusSequenceErrors
      Counter32,
   mscMcsMgrFrf5EpGEpLmiUnexpectedReports
      Counter32,
   mscMcsMgrFrf5EpGEpLmiPollingVerifTimeouts
      Counter32,
   mscMcsMgrFrf5EpGEpLmiNoStatusReportCount
      Counter32,
   mscMcsMgrFrf5EpGEpLmiKeepAliveEnqToIf
      Counter32,
   mscMcsMgrFrf5EpGEpLmiFullStatusEnqToIf
      Counter32 }

mscMcsMgrFrf5EpGEpLmiKeepAliveStatusToInterface OBJECT-TYPE
   SYNTAX     Counter32 
   ACCESS     read-only
   STATUS     mandatory
   DESCRIPTION
     "This attribute counts the Local Management Interface keep alive 
      status messages sent to the ATM VCC in response to a status 
      enquiry for keep alive status. When the maximum count is reached 
      it wraps to zero."
::= { mscMcsMgrFrf5EpGEpLmiStatsEntry 1 }

mscMcsMgrFrf5EpGEpLmiFullStatusToInterface OBJECT-TYPE
   SYNTAX     Counter32 
   ACCESS     read-only
   STATUS     mandatory
   DESCRIPTION
     "This attribute counts the Local Management Interface full status 
      messages sent to the ATM VCC in response to a status enquiry for 
      keep alive or full status. When the maximum count is reached it 
      wraps to zero."
::= { mscMcsMgrFrf5EpGEpLmiStatsEntry 2 }

mscMcsMgrFrf5EpGEpLmiKeepAliveStatusEnqFromInterface OBJECT-TYPE
   SYNTAX     Counter32 
   ACCESS     read-only
   STATUS     mandatory
   DESCRIPTION
     "This attribute counts the Local Management Interface valid keep 
      alive status enquiry messages received from the ATM VCC. When 
      the maximum count is reached it wraps to zero."
::= { mscMcsMgrFrf5EpGEpLmiStatsEntry 3 }

mscMcsMgrFrf5EpGEpLmiFullStatusEnqFromInterface OBJECT-TYPE
   SYNTAX     Counter32 
   ACCESS     read-only
   STATUS     mandatory
   DESCRIPTION
     "This attribute counts the Local Management Interface valid full 
      status enquiry messages received from the ATM VCC. When the 
      maximum count is reached it wraps to zero."
::= { mscMcsMgrFrf5EpGEpLmiStatsEntry 4 }

mscMcsMgrFrf5EpGEpLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The left most 
      event is the most recent to occur. The provisioned eventCount 
      dictates the maximum number of events displayed. A good event is 
      triggered by receipt of a valid status enquiry message. An error 
      event is either a T392 timer expiry or receipt of a status enquiry 
      with an incorrect sequence number."
::= { mscMcsMgrFrf5EpGEpLmiStatsEntry 5 }

mscMcsMgrFrf5EpGEpLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The left most 
      event is the most recent to occur. The provisioned eventCount 
      dictates the maximum number of events displayed. A good event is 
      triggered by receipt of a valid status message. An error event is 
      either a T391 timer expiry or receipt of a status message with an 
      incorrect sequence number."
::= { mscMcsMgrFrf5EpGEpLmiStatsEntry 6 }

mscMcsMgrFrf5EpGEpLmiProtocolErrors OBJECT-TYPE
   SYNTAX     Counter32 
   ACCESS     read-only
   STATUS     mandatory
   DESCRIPTION
     "This attribute counts the number of Local Management Interface 
      protocol errors. It is the sum of the sequence (sequenceErrors and 
      statusSequenceErrors) and timeout (pollingVerifTimeouts and 
      noStatusReportCount) errors. When the maximum count is reached 
      it wraps to zero."
::= { mscMcsMgrFrf5EpGEpLmiStatsEntry 7 }

mscMcsMgrFrf5EpGEpLmiUnexpectedIes OBJECT-TYPE
   SYNTAX     Counter32 
   ACCESS     read-only
   STATUS     mandatory
   DESCRIPTION
     "This attribute counts the number of Local Managament Interface 
      frames received with an Information Element identifier that is 
      unknown or unexpected. An unexpected Information Element is not 
      a protocol error. When the maximum count is reached, this counter 
      wraps to zero."
::= { mscMcsMgrFrf5EpGEpLmiStatsEntry 8 }

mscMcsMgrFrf5EpGEpLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is reached the counter wraps to zero."
::= { mscMcsMgrFrf5EpGEpLmiStatsEntry 9 }

mscMcsMgrFrf5EpGEpLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is reached the 
      counter wraps to zero."
::= { mscMcsMgrFrf5EpGEpLmiStatsEntry 10 }

mscMcsMgrFrf5EpGEpLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is reached the counter wraps to zero."
::= { mscMcsMgrFrf5EpGEpLmiStatsEntry 11 }

mscMcsMgrFrf5EpGEpLmiPollingVerifTimeouts OBJECT-TYPE
   SYNTAX     Counter32 
   ACCESS     read-only
   STATUS     mandatory
   DESCRIPTION
     "This attribute counts the checkPointTimer (T392) expiries occurring 
      on the Local Management Interface. When the maximum count is 
      reached the counter wraps to zero."
::= { mscMcsMgrFrf5EpGEpLmiStatsEntry 12 }

mscMcsMgrFrf5EpGEpLmiNoStatusReportCount OBJECT-TYPE
   SYNTAX     Counter32 
   ACCESS     read-only
   STATUS     mandatory
   DESCRIPTION
     "This attribute counts the number of times when no status report or 
      an invalid status report comes from the external network. This 
      attribute is incremented:
      i) after a status enquiry is sent out and the T391 timer expires 
      without having a status report received.
      ii) if an invalid status report is received.
      
      When the maximum count is reached it wraps to zero."
::= { mscMcsMgrFrf5EpGEpLmiStatsEntry 13 }

mscMcsMgrFrf5EpGEpLmiKeepAliveEnqToIf OBJECT-TYPE
   SYNTAX     Counter32 
   ACCESS     read-only
   STATUS     mandatory
   DESCRIPTION
     "This attribute counts the number of Local Management Interface 
      keep alive enquiry status messages sent to the external user device 
      for keep alive status. When the maximum count is reached it wraps 
      to zero."
::= { mscMcsMgrFrf5EpGEpLmiStatsEntry 14 }

mscMcsMgrFrf5EpGEpLmiFullStatusEnqToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { mscMcsMgrFrf5EpGEpLmiStatsEntry 15 }


-- McsMgr Frf5EpG/n Ep/n EndPointDescriptor
-- This component describes the ATM SPVC which supports the 
-- FRF.5 connection.

mscMcsMgrFrf5EpGEpEpd OBJECT IDENTIFIER ::= { mscMcsMgrFrf5EpGEp 3 }



mscMcsMgrFrf5EpGEpEpdRowStatusTable OBJECT-TYPE
   SYNTAX     SEQUENCE OF MscMcsMgrFrf5EpGEpEpdRowStatusEntry
   ACCESS     not-accessible
   STATUS     mandatory
   DESCRIPTION
     "This entry controls the addition and deletion of 
      mscMcsMgrFrf5EpGEpEpd components."
::= { mscMcsMgrFrf5EpGEpEpd 1 }

mscMcsMgrFrf5EpGEpEpdRowStatusEntry OBJECT-TYPE
   SYNTAX     MscMcsMgrFrf5EpGEpEpdRowStatusEntry
   ACCESS     not-accessible
   STATUS     mandatory
   DESCRIPTION
     "A single entry in the table represents a single 
      mscMcsMgrFrf5EpGEpEpd component."
   INDEX {
      mscMcsMgrIndex,
      mscMcsMgrFrf5EpGIndex,
      mscMcsMgrFrf5EpGEpIndex,
      mscMcsMgrFrf5EpGEpEpdIndex }
::= { mscMcsMgrFrf5EpGEpEpdRowStatusTable 1 }

MscMcsMgrFrf5EpGEpEpdRowStatusEntry ::= SEQUENCE {
   mscMcsMgrFrf5EpGEpEpdRowStatus
      RowStatus,
   mscMcsMgrFrf5EpGEpEpdComponentName
      DisplayString,
   mscMcsMgrFrf5EpGEpEpdStorageType
      StorageType,
   mscMcsMgrFrf5EpGEpEpdIndex
      NonReplicated }

mscMcsMgrFrf5EpGEpEpdRowStatus OBJECT-TYPE
   SYNTAX     RowStatus 
   ACCESS     read-only
   STATUS     mandatory
   DESCRIPTION
     "This variable is used as the basis for SNMP naming of
      mscMcsMgrFrf5EpGEpEpd components.
      These components cannot be added nor deleted."
::= { mscMcsMgrFrf5EpGEpEpdRowStatusEntry 1 }

mscMcsMgrFrf5EpGEpEpdComponentName OBJECT-TYPE
   SYNTAX     DisplayString 
   ACCESS     read-only
   STATUS     mandatory
   DESCRIPTION
     "This variable provides the component's string name for
      use with the ASCII Console Interface"
::= { mscMcsMgrFrf5EpGEpEpdRowStatusEntry 2 }

mscMcsMgrFrf5EpGEpEpdStorageType OBJECT-TYPE
   SYNTAX     StorageType 
   ACCESS     read-only
   STATUS     mandatory
   DESCRIPTION
     "This variable represents the storage type value for the
      mscMcsMgrFrf5EpGEpEpd tables."
::= { mscMcsMgrFrf5EpGEpEpdRowStatusEntry 4 }

mscMcsMgrFrf5EpGEpEpdIndex OBJECT-TYPE
   SYNTAX     NonReplicated 
   ACCESS     not-accessible
   STATUS     mandatory
   DESCRIPTION
     "This variable represents the index for the mscMcsMgrFrf5EpGEpEpd tables."
::= { mscMcsMgrFrf5EpGEpEpdRowStatusEntry 10 }

mscMcsMgrFrf5EpGEpEpdProvTable OBJECT-TYPE
   SYNTAX     SEQUENCE OF MscMcsMgrFrf5EpGEpEpdProvEntry
   ACCESS     not-accessible
   STATUS     mandatory
   DESCRIPTION
     "This group contains the provisionable attributes of the FRF.5 End 
      Point."
::= { mscMcsMgrFrf5EpGEpEpd 10 }

mscMcsMgrFrf5EpGEpEpdProvEntry OBJECT-TYPE
   SYNTAX     MscMcsMgrFrf5EpGEpEpdProvEntry
   ACCESS     not-accessible
   STATUS     mandatory
   DESCRIPTION
     "An entry in the mscMcsMgrFrf5EpGEpEpdProvTable."
   INDEX {
      mscMcsMgrIndex,
      mscMcsMgrFrf5EpGIndex,
      mscMcsMgrFrf5EpGEpIndex,
      mscMcsMgrFrf5EpGEpEpdIndex }
::= { mscMcsMgrFrf5EpGEpEpdProvTable 1 }

MscMcsMgrFrf5EpGEpEpdProvEntry ::= SEQUENCE {
   mscMcsMgrFrf5EpGEpEpdRemoteConnectionIdentifier
      IntegerSequence,
   mscMcsMgrFrf5EpGEpEpdConnectionTransferPriority
      Unsigned32,
   mscMcsMgrFrf5EpGEpEpdCommittedInformationRate
      Unsigned32,
   mscMcsMgrFrf5EpGEpEpdExcessInformationRate
      Unsigned32,
   mscMcsMgrFrf5EpGEpEpdCommittedBurstSize
      Unsigned32,
   mscMcsMgrFrf5EpGEpEpdType
      INTEGER,
   mscMcsMgrFrf5EpGEpEpdAccessRate
      Unsigned32,
   mscMcsMgrFrf5EpGEpEpdExcessBurstSize
      Unsigned32 }

mscMcsMgrFrf5EpGEpEpdRemoteConnectionIdentifier OBJECT-TYPE
   SYNTAX     IntegerSequence (SIZE (3..9))
   ACCESS     read-write
   STATUS     mandatory
   DESCRIPTION
     "This attribute specifies the remote connection identifier. It either 
      represents the VPI.VCI logical channel number assignment of a 
      remote ATM interface, or the Endpoint.Frf5EndPointGroup 
      instances of a remote Passport FRF.5 EndPoint."
::= { mscMcsMgrFrf5EpGEpEpdProvEntry 3 }

mscMcsMgrFrf5EpGEpEpdConnectionTransferPriority OBJECT-TYPE
   SYNTAX     Unsigned32 (0..15)
   ACCESS     read-write
   STATUS     mandatory
   DESCRIPTION
     "This attribute specifies the transfer priority used to establish the 
      ATM connection. The EndPoint references the ModuleData 
      FrameRelayService AtmNetworking TransferPriority/n component 
      to determine the ATM service category to be used by the 
      connection.
      This attribute is also used to determine which EndPoint within an 
      Frf5EndPointGroup is to multiplex a particular FrAtm Dlci.
      DESCRIPTION"
::= { mscMcsMgrFrf5EpGEpEpdProvEntry 4 }

mscMcsMgrFrf5EpGEpEpdCommittedInformationRate OBJECT-TYPE
   SYNTAX     Unsigned32 (0..50000000)
   ACCESS     read-write
   STATUS     mandatory
   DESCRIPTION
     "This attribute specifies the committed information rate (CIR), and 
      represents the rate at which the network FRF.5 ATM VCC agrees to 
      transfer information under normal conditions. A conservative CIR 
      value would be the sum of the CIRs of all the individual FrAtm 
      Dlcis multiplexed by the VCC.
      The cir is converted into ATM service parameters according to the 
      conversion policy specified by the connectionTransferPriority 
      attribute. The conversion policy is defined under the ModuleData 
      FrameRelayService AtmNetworking TransferPriority/n component."
   DEFVAL     { 64000 }
::= { mscMcsMgrFrf5EpGEpEpdProvEntry 5 }

mscMcsMgrFrf5EpGEpEpdExcessInformationRate OBJECT-TYPE
   SYNTAX     Unsigned32 (0..50000000)
   ACCESS     read-write
   STATUS     mandatory
   DESCRIPTION
     "This attribute specifies the excess information rate (EIR), and 
      represents the rate at which the network FRF.5 ATM VCC attempts 
      to transfer information. A conservative EIR value would be the sum 
      of the EIRs of all the individual FrAtm Dlcis multiplexed by the 
      VCC.
      The eir is converted into ATM service parameters according to the 
      conversion policy specified by the connectionTransferPriority 
      attribute. The conversion policy is defined under the ModuleData 
      FrameRelayService AtmNetworking TransferPriority/n component."
   DEFVAL     { 0 }
::= { mscMcsMgrFrf5EpGEpEpdProvEntry 6 }

mscMcsMgrFrf5EpGEpEpdCommittedBurstSize OBJECT-TYPE
   SYNTAX     Unsigned32 (0..50000000)
   ACCESS     read-write
   STATUS     mandatory
   DESCRIPTION
     "This attribute specifies the committed burst size (Bc), and represents 
      the amount of data that the network FRF.5 ATM VCC agrees to 
      transfer under normal conditions. A conservative Bc value would be 
      the sum of the Bcs of all the individual FrAtm Dlcis multiplexed by 
      the VCC.
      The bc is converted into ATM service parameters according to the 
      conversion policy specified by the connectionTransferPriority 
      attribute. The conversion policy is defined under the ModuleData 
      FrameRelayService AtmNetworking TransferPriority/n component."
   DEFVAL     { 16000 }
::= { mscMcsMgrFrf5EpGEpEpdProvEntry 7 }

mscMcsMgrFrf5EpGEpEpdType OBJECT-TYPE
   SYNTAX     INTEGER  {
                 master(0),
                 slave(1) }
   ACCESS     read-write
   STATUS     mandatory
   DESCRIPTION
     "This attribute specifies the FRF.5 End Point type. If the value is 
      provisioned as master, this End Point is responsible for initiating 
      the SPVC call to set up the FRF.5 ATM VCC. If the value is 
      provisioned as slave, this End Point receives call setup requests 
      from a master remote end."
   DEFVAL     { master }
::= { mscMcsMgrFrf5EpGEpEpdProvEntry 8 }

mscMcsMgrFrf5EpGEpEpdAccessRate OBJECT-TYPE
   SYNTAX     Unsigned32 (0..50000000)
   ACCESS     read-write
   STATUS     mandatory
   DESCRIPTION
     "This attribute represents the access rate of the FRF.5 EndPoint. A 
      conservative value would be the sum of the access rates of all the 
      FrAtms' that have DLCIs multiplexed by the VCC. The access rate 
      is converted into ATM service parameters when conversion policies 
      3, 4 and 5 are used. For policy 6, this attribute is ignored."
   DEFVAL     { 1536000 }
::= { mscMcsMgrFrf5EpGEpEpdProvEntry 9 }

mscMcsMgrFrf5EpGEpEpdExcessBurstSize OBJECT-TYPE
   SYNTAX     Unsigned32 (0..50000000)
   ACCESS     read-write
   STATUS     mandatory
   DESCRIPTION
     "This attribute specifies the excess burst size (Be), and represents the 
      amount of uncommitted data that the network FRF.5 ATM VCC 
      agrees to transfer under normal conditions. A conservative Be value 
      would be the sum of the Bes of all the individual FrAtm Dlcis 
      multiplexed by the VCC.
      The be is converted into ATM service parameters according to the 
      conversion policy specified by the connectionTransferPriority 
      attribute. The conversion policy is defined under the ModuleData 
      FrameRelayService AtmNetworking TransferPriority/n component."
   DEFVAL     { 0 }
::= { mscMcsMgrFrf5EpGEpEpdProvEntry 10 }

mscMcsMgrFrf5EpGEpEpdCidDataTable OBJECT-TYPE
   SYNTAX     SEQUENCE OF MscMcsMgrFrf5EpGEpEpdCidDataEntry
   ACCESS     not-accessible
   STATUS     mandatory
   DESCRIPTION
     "This group contains the attribute for a component's Customer 
      Identifier (CID). Refer to the attribute description for a detailed 
      explanation of CIDs."
::= { mscMcsMgrFrf5EpGEpEpd 11 }

mscMcsMgrFrf5EpGEpEpdCidDataEntry OBJECT-TYPE
   SYNTAX     MscMcsMgrFrf5EpGEpEpdCidDataEntry
   ACCESS     not-accessible
   STATUS     mandatory
   DESCRIPTION
     "An entry in the mscMcsMgrFrf5EpGEpEpdCidDataTable."
   INDEX {
      mscMcsMgrIndex,
      mscMcsMgrFrf5EpGIndex,
      mscMcsMgrFrf5EpGEpIndex,
      mscMcsMgrFrf5EpGEpEpdIndex }
::= { mscMcsMgrFrf5EpGEpEpdCidDataTable 1 }

MscMcsMgrFrf5EpGEpEpdCidDataEntry ::= SEQUENCE {
   mscMcsMgrFrf5EpGEpEpdCustomerIdentifier
      Unsigned32 }

mscMcsMgrFrf5EpGEpEpdCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscMcsMgrFrf5EpGEpEpdCidDataEntry 1 }

-- 
-- *** THIS SUBTREE CURRENTLY NOT IMPLEMENTED ***
-- 

-- McsMgr Frf5EpGrp/n Ep/n DataLinkConnectionIdentifier/n
-- This component represents a logical connection multiplexed inside 
-- the FRF.5 ATM VCC.

mscMcsMgrFrf5EpGEpDlci OBJECT IDENTIFIER ::= { mscMcsMgrFrf5EpGEp 4 }



mscMcsMgrFrf5EpGEpDlciRowStatusTable OBJECT-TYPE
   SYNTAX     SEQUENCE OF MscMcsMgrFrf5EpGEpDlciRowStatusEntry
   ACCESS     not-accessible
   STATUS     mandatory
   DESCRIPTION
     "*** THIS TABLE CURRENTLY NOT IMPLEMENTED ***

      This entry controls the addition and deletion of 
      mscMcsMgrFrf5EpGEpDlci components."
::= { mscMcsMgrFrf5EpGEpDlci 1 }

mscMcsMgrFrf5EpGEpDlciRowStatusEntry OBJECT-TYPE
   SYNTAX     MscMcsMgrFrf5EpGEpDlciRowStatusEntry
   ACCESS     not-accessible
   STATUS     mandatory
   DESCRIPTION
     "A single entry in the table represents a single 
      mscMcsMgrFrf5EpGEpDlci component."
   INDEX {
      mscMcsMgrIndex,
      mscMcsMgrFrf5EpGIndex,
      mscMcsMgrFrf5EpGEpIndex,
      mscMcsMgrFrf5EpGEpDlciIndex }
::= { mscMcsMgrFrf5EpGEpDlciRowStatusTable 1 }

MscMcsMgrFrf5EpGEpDlciRowStatusEntry ::= SEQUENCE {
   mscMcsMgrFrf5EpGEpDlciRowStatus
      RowStatus,
   mscMcsMgrFrf5EpGEpDlciComponentName
      DisplayString,
   mscMcsMgrFrf5EpGEpDlciStorageType
      StorageType,
   mscMcsMgrFrf5EpGEpDlciIndex
      Integer32 }

mscMcsMgrFrf5EpGEpDlciRowStatus OBJECT-TYPE
   SYNTAX     RowStatus 
   ACCESS     read-only
   STATUS     mandatory
   DESCRIPTION
     "This variable is used as the basis for SNMP naming of
      mscMcsMgrFrf5EpGEpDlci components.
      These components cannot be added nor deleted."
::= { mscMcsMgrFrf5EpGEpDlciRowStatusEntry 1 }

mscMcsMgrFrf5EpGEpDlciComponentName OBJECT-TYPE
   SYNTAX     DisplayString 
   ACCESS     read-only
   STATUS     mandatory
   DESCRIPTION
     "This variable provides the component's string name for
      use with the ASCII Console Interface"
::= { mscMcsMgrFrf5EpGEpDlciRowStatusEntry 2 }

mscMcsMgrFrf5EpGEpDlciStorageType OBJECT-TYPE
   SYNTAX     StorageType 
   ACCESS     read-only
   STATUS     mandatory
   DESCRIPTION
     "This variable represents the storage type value for the
      mscMcsMgrFrf5EpGEpDlci tables."
::= { mscMcsMgrFrf5EpGEpDlciRowStatusEntry 4 }

mscMcsMgrFrf5EpGEpDlciIndex OBJECT-TYPE
   SYNTAX     Integer32 (16..1007 | 1022)
   ACCESS     not-accessible
   STATUS     mandatory
   DESCRIPTION
     "This variable represents the index for the mscMcsMgrFrf5EpGEpDlci tables."
::= { mscMcsMgrFrf5EpGEpDlciRowStatusEntry 10 }

mscMcsMgrFrf5EpGEpDlciOperTable OBJECT-TYPE
   SYNTAX     SEQUENCE OF MscMcsMgrFrf5EpGEpDlciOperEntry
   ACCESS     not-accessible
   STATUS     mandatory
   DESCRIPTION
     "*** THIS TABLE CURRENTLY NOT IMPLEMENTED ***

      This group contains the operational attributes for the FRF.5 DLCI."
::= { mscMcsMgrFrf5EpGEpDlci 10 }

mscMcsMgrFrf5EpGEpDlciOperEntry OBJECT-TYPE
   SYNTAX     MscMcsMgrFrf5EpGEpDlciOperEntry
   ACCESS     not-accessible
   STATUS     mandatory
   DESCRIPTION
     "An entry in the mscMcsMgrFrf5EpGEpDlciOperTable."
   INDEX {
      mscMcsMgrIndex,
      mscMcsMgrFrf5EpGIndex,
      mscMcsMgrFrf5EpGEpIndex,
      mscMcsMgrFrf5EpGEpDlciIndex }
::= { mscMcsMgrFrf5EpGEpDlciOperTable 1 }

MscMcsMgrFrf5EpGEpDlciOperEntry ::= SEQUENCE {
   mscMcsMgrFrf5EpGEpDlciABitStatusToIf
      INTEGER,
   mscMcsMgrFrf5EpGEpDlciABitReasonToIf
      INTEGER,
   mscMcsMgrFrf5EpGEpDlciABitStatusFromIf
      INTEGER,
   mscMcsMgrFrf5EpGEpDlciABitReasonFromIf
      INTEGER,
   mscMcsMgrFrf5EpGEpDlciAccessConnectionComponent
      AsciiString }

mscMcsMgrFrf5EpGEpDlciABitStatusToIf OBJECT-TYPE
   SYNTAX     INTEGER  {
                 inactive(0),
                 active(1) }
   ACCESS     read-only
   STATUS     mandatory
   DESCRIPTION
     "This attribute indicates the most recent A-bit status sent to the ATM 
      VCC. If the value is inactive, the reason for the LMI failure is given 
      by the aBitReasonToNetwork."
   DEFVAL     { inactive }
::= { mscMcsMgrFrf5EpGEpDlciOperEntry 1 }

mscMcsMgrFrf5EpGEpDlciABitReasonToIf OBJECT-TYPE
   SYNTAX     INTEGER  {
                 notApplicable(0),
                 remoteUserSignaled(1),
                 localLmiError(2),
                 remoteLmiError(3),
                 localLinkDown(4),
                 remoteLinkDown(5),
                 pvcDown(6) }
   ACCESS     read-only
   STATUS     mandatory
   DESCRIPTION
     "This attribute indicates the reason for the latest inactive A-bit status 
      sent to the ATM VCC.
      The value is notApplicable when the aBitStatusToNetwork is active.
      The value is remoteUserSignaled if the FrAtm originating the A-Bit 
      status has detected that the virtual circuit is down at the remote 
      network through the LMI protocol. The FrAtm must be running 
      network site LMI protocol for this A-Bit status reason to be sent.
      The value is localLmiError if the LMI protocol is down at this Ep.
      The value is remoteLmiError if the LMI protocol is down at the 
      FrAtm originating this A-Bit status reason.
      The value is localLinkDown if the physical interface is disabled at 
      this Ep.
      The value is pvcDown if no A-Bit status has been sent to this Ep 
      (i.e., no A-Bit status has been relayed from the FrAtm).
      The value is remoteLinkDown if the physical interface is disabled 
      at the FrAtm originating this A-Bit status reason."
   DEFVAL     { notApplicable }
::= { mscMcsMgrFrf5EpGEpDlciOperEntry 2 }

mscMcsMgrFrf5EpGEpDlciABitStatusFromIf OBJECT-TYPE
   SYNTAX     INTEGER  {
                 inactive(0),
                 active(1) }
   ACCESS     read-only
   STATUS     mandatory
   DESCRIPTION
     "This attribute indicates the most recent A-bit status received from 
      the ATM VCC. If the value is inactive, the reason for the LMI 
      failure is given by the aBitReasonFromNetwork."
   DEFVAL     { inactive }
::= { mscMcsMgrFrf5EpGEpDlciOperEntry 3 }

mscMcsMgrFrf5EpGEpDlciABitReasonFromIf OBJECT-TYPE
   SYNTAX     INTEGER  {
                 notApplicable(0),
                 remoteUserSignalled(1),
                 localLmiError(2),
                 localLinkDown(4),
                 missingFromLmiReport(7) }
   ACCESS     read-only
   STATUS     mandatory
   DESCRIPTION
     "This attributes indicates the reason for the latest inactive A-bit 
      status received from the ATM VCC.
      The value is notApplicable when the aBitStatusFromNetwork is 
      active.
      The value is remoteUserSignaled if the remote FRF.5 End Point 
      originating the A-Bit status has detected that the virtual circuit is 
      down at the remote network through the LMI protocol. The remote 
      FRF.5 End Point must be running network site LMI protocol for this 
      A-Bit status reason to be sent.
      The value is localLmiError if the LMI protocol is down at this Ep.
      The value is localLinkDown if the physical interface is disabled at 
      this Ep.
      The value is missingFromLmiReport if the remote FRF.5 End Point 
      did not provide a reason along with the inactive A-Bit status."
   DEFVAL     { notApplicable }
::= { mscMcsMgrFrf5EpGEpDlciOperEntry 4 }

mscMcsMgrFrf5EpGEpDlciAccessConnectionComponent OBJECT-TYPE
   SYNTAX     AsciiString (SIZE (0..23))
   ACCESS     read-only
   STATUS     mandatory
   DESCRIPTION
     "This attribute identifies the FrAtm Dlci to which this Dlci 
      component is bound."
::= { mscMcsMgrFrf5EpGEpDlciOperEntry 5 }


-- An AtmConnection component is created for each ATM connection 
-- established by an application. It shows where the data traffic for this 
-- connection is directed.

mscMcsMgrFrf5EpGEpAtmCon OBJECT IDENTIFIER ::= { mscMcsMgrFrf5EpGEp 5 }



mscMcsMgrFrf5EpGEpAtmConRowStatusTable OBJECT-TYPE
   SYNTAX     SEQUENCE OF MscMcsMgrFrf5EpGEpAtmConRowStatusEntry
   ACCESS     not-accessible
   STATUS     mandatory
   DESCRIPTION
     "This entry controls the addition and deletion of 
      mscMcsMgrFrf5EpGEpAtmCon components."
::= { mscMcsMgrFrf5EpGEpAtmCon 1 }

mscMcsMgrFrf5EpGEpAtmConRowStatusEntry OBJECT-TYPE
   SYNTAX     MscMcsMgrFrf5EpGEpAtmConRowStatusEntry
   ACCESS     not-accessible
   STATUS     mandatory
   DESCRIPTION
     "A single entry in the table represents a single 
      mscMcsMgrFrf5EpGEpAtmCon component."
   INDEX {
      mscMcsMgrIndex,
      mscMcsMgrFrf5EpGIndex,
      mscMcsMgrFrf5EpGEpIndex,
      mscMcsMgrFrf5EpGEpAtmConIndex }
::= { mscMcsMgrFrf5EpGEpAtmConRowStatusTable 1 }

MscMcsMgrFrf5EpGEpAtmConRowStatusEntry ::= SEQUENCE {
   mscMcsMgrFrf5EpGEpAtmConRowStatus
      RowStatus,
   mscMcsMgrFrf5EpGEpAtmConComponentName
      DisplayString,
   mscMcsMgrFrf5EpGEpAtmConStorageType
      StorageType,
   mscMcsMgrFrf5EpGEpAtmConIndex
      NonReplicated }

mscMcsMgrFrf5EpGEpAtmConRowStatus OBJECT-TYPE
   SYNTAX     RowStatus 
   ACCESS     read-only
   STATUS     mandatory
   DESCRIPTION
     "This variable is used as the basis for SNMP naming of
      mscMcsMgrFrf5EpGEpAtmCon components.
      These components cannot be added nor deleted."
::= { mscMcsMgrFrf5EpGEpAtmConRowStatusEntry 1 }

mscMcsMgrFrf5EpGEpAtmConComponentName OBJECT-TYPE
   SYNTAX     DisplayString 
   ACCESS     read-only
   STATUS     mandatory
   DESCRIPTION
     "This variable provides the component's string name for
      use with the ASCII Console Interface"
::= { mscMcsMgrFrf5EpGEpAtmConRowStatusEntry 2 }

mscMcsMgrFrf5EpGEpAtmConStorageType OBJECT-TYPE
   SYNTAX     StorageType 
   ACCESS     read-only
   STATUS     mandatory
   DESCRIPTION
     "This variable represents the storage type value for the
      mscMcsMgrFrf5EpGEpAtmCon tables."
::= { mscMcsMgrFrf5EpGEpAtmConRowStatusEntry 4 }

mscMcsMgrFrf5EpGEpAtmConIndex OBJECT-TYPE
   SYNTAX     NonReplicated 
   ACCESS     not-accessible
   STATUS     mandatory
   DESCRIPTION
     "This variable represents the index for the mscMcsMgrFrf5EpGEpAtmCon tables."
::= { mscMcsMgrFrf5EpGEpAtmConRowStatusEntry 10 }

mscMcsMgrFrf5EpGEpAtmConOperTable OBJECT-TYPE
   SYNTAX     SEQUENCE OF MscMcsMgrFrf5EpGEpAtmConOperEntry
   ACCESS     not-accessible
   STATUS     mandatory
   DESCRIPTION
     "This attribute group contains the operational attributes for the 
      NapAtmConnection component."
::= { mscMcsMgrFrf5EpGEpAtmCon 10 }

mscMcsMgrFrf5EpGEpAtmConOperEntry OBJECT-TYPE
   SYNTAX     MscMcsMgrFrf5EpGEpAtmConOperEntry
   ACCESS     not-accessible
   STATUS     mandatory
   DESCRIPTION
     "An entry in the mscMcsMgrFrf5EpGEpAtmConOperTable."
   INDEX {
      mscMcsMgrIndex,
      mscMcsMgrFrf5EpGIndex,
      mscMcsMgrFrf5EpGEpIndex,
      mscMcsMgrFrf5EpGEpAtmConIndex }
::= { mscMcsMgrFrf5EpGEpAtmConOperTable 1 }

MscMcsMgrFrf5EpGEpAtmConOperEntry ::= SEQUENCE {
   mscMcsMgrFrf5EpGEpAtmConNextHop
      RowPointer }

mscMcsMgrFrf5EpGEpAtmConNextHop OBJECT-TYPE
   SYNTAX     RowPointer 
   ACCESS     read-only
   STATUS     mandatory
   DESCRIPTION
     "This attribute shows the component name of the AtmIf Vcc Ep or 
      AtmCon component to which this switched connection is 
      established."
::= { mscMcsMgrFrf5EpGEpAtmConOperEntry 1 }




-- 
-- Version and Compliance statements
-- 



-- Object-Group Statement:
-- A list of all current accessible leaf objects.

-- OBJECTS { mscMcsMgrFrf5EpGEpLmiPollingVerifTimeouts,
--           mscMcsMgrFrf5EpGEpProceduralStatus,
--           mscMcsMgrFrf5EpGEpStandbyStatus,
--           mscMcsMgrFrf5EpGEpAvgFrameSize,
--           mscMcsMgrFrf5EpGEpLmiRowStatus,
--           mscMcsMgrFrf5EpGEpLmiSequenceErrors,
--           mscMcsMgrFrf5EpGAddrRowStatus,
--           mscMcsMgrFrf5EpGRowStatus,
--           mscMcsMgrFrf5EpGEpUsageState,
--           mscMcsMgrFrf5EpGEpMaximumBurstSize01,
--           mscMcsMgrFrf5EpGEpServiceCategory,
--           mscMcsMgrFrf5EpGEpComponentName,
--           mscMcsMgrFrf5EpGEpLmiStorageType,
--           mscMcsMgrFrf5EpGEpDlciRowStatus,
--           mscMcsMgrFrf5EpGEpLmiUnexpectedReports,
--           mscMcsMgrFrf5EpGEpLastVccClearCause,
--           mscMcsMgrFrf5EpGEpEpdExcessBurstSize,
--           mscMcsMgrFrf5EpGEpLmiUsageState,
--           mscMcsMgrFrf5EpGEpLmiStatusSequenceErrors,
--           mscMcsMgrFrf5EpGEpLmiKeepAliveStatusToInterface,
--           mscMcsMgrFrf5EpGEpLmiLinkVerificationTimer,
--           mscMcsMgrFrf5EpGAddrComponentName,
--           mscMcsMgrFrf5EpGEpOperationalState,
--           mscMcsMgrFrf5EpGEpDlciABitReasonFromIf,
--           mscMcsMgrFrf5EpGEpLmiProtocolStatus,
--           mscMcsMgrFrf5EpGEpSustainedCellRate01,
--           mscMcsMgrFrf5EpGEpLmiAdminState,
--           mscMcsMgrFrf5EpGEpLmiProtocolErrors,
--           mscMcsMgrFrf5EpGEpLastVccCauseDiag,
--           mscMcsMgrFrf5EpGEpRowStatus,
--           mscMcsMgrFrf5EpGEpConnectionTransferPriority,
--           mscMcsMgrFrf5EpGEpLmiFullStatusEnqToIf,
--           mscMcsMgrFrf5EpGEpLmiFullStatusPollingCycles,
--           mscMcsMgrFrf5EpGEpLmiEventCount,
--           mscMcsMgrFrf5EpGEpDlciABitStatusToIf,
--           mscMcsMgrFrf5EpGEpEpdAccessRate,
--           mscMcsMgrFrf5EpGStorageType,
--           mscMcsMgrFrf5EpGEpLmiCheckPointTimer,
--           mscMcsMgrFrf5EpGEpEpdStorageType,
--           mscMcsMgrFrf5EpGEpAtmConNextHop,
--           mscMcsMgrFrf5EpGEpLmiUserSideEventHistory,
--           mscMcsMgrFrf5EpGEpAvailabilityStatus,
--           mscMcsMgrFrf5EpGEpPeakCellRate01,
--           mscMcsMgrFrf5EpGEpDlciStorageType,
--           mscMcsMgrFrf5EpGAddrRemoteAddress,
--           mscMcsMgrFrf5EpGAddrAddrPreValue,
--           mscMcsMgrFrf5EpGEpLmiSide,
--           mscMcsMgrFrf5EpGEpAlarmStatus,
--           mscMcsMgrFrf5EpGEpLmiComponentName,
--           mscMcsMgrFrf5EpGEpLmiErrorEventThreshold,
--           mscMcsMgrFrf5EpGEpLmiNetworkSideEventHistory,
--           mscMcsMgrFrf5EpGEpEpdCommittedBurstSize,
--           mscMcsMgrFrf5EpGEpLmiFullStatusEnqFromInterface,
--           mscMcsMgrFrf5EpGEpUnknownStatus,
--           mscMcsMgrFrf5EpGEpMaximumBurstSize0,
--           mscMcsMgrFrf5EpGAddrCommentText,
--           mscMcsMgrFrf5EpGEpAtmConComponentName,
--           mscMcsMgrFrf5EpGEpLmiKeepAliveEnqToIf,
--           mscMcsMgrFrf5EpGEpDlciABitStatusFromIf,
--           mscMcsMgrFrf5EpGEpStorageType,
--           mscMcsMgrFrf5EpGEpDlciABitReasonToIf,
--           mscMcsMgrFrf5EpGEpLmiOperationalState,
--           mscMcsMgrFrf5EpGComponentName,
--           mscMcsMgrFrf5EpGEpEpdComponentName,
--           mscMcsMgrFrf5EpGEpEpdType,
--           mscMcsMgrFrf5EpGEpEpdRowStatus,
--           mscMcsMgrFrf5EpGEpTrafficParmConversionPolicy,
--           mscMcsMgrFrf5EpGEpAtmConRowStatus,
--           mscMcsMgrFrf5EpGAddrAddrPreRowStatus,
--           mscMcsMgrFrf5EpGEpEpdCustomerIdentifier,
--           mscMcsMgrFrf5EpGEpEpdRemoteConnectionIdentifier,
--           mscMcsMgrFrf5EpGAddrStorageType,
--           mscMcsMgrFrf5EpGEpType,
--           mscMcsMgrFrf5EpGEpSustainedCellRate0,
--           mscMcsMgrFrf5EpGEpEpdCommittedInformationRate,
--           mscMcsMgrFrf5EpGEpDlciAccessConnectionComponent,
--           mscMcsMgrFrf5EpGEpLmiAsyncStatusReport,
--           mscMcsMgrFrf5EpGEpLmiKeepAliveStatusEnqFromInterface,
--           mscMcsMgrFrf5EpGEpAdminState,
--           mscMcsMgrFrf5EpGEpLmiUnexpectedIes,
--           mscMcsMgrFrf5EpGEpLmiProcedures,
--           mscMcsMgrFrf5EpGEpDlciComponentName,
--           mscMcsMgrFrf5EpGEpEpdConnectionTransferPriority,
--           mscMcsMgrFrf5EpGEpLmiNoStatusReportCount,
--           mscMcsMgrFrf5EpGEpLmiFullStatusToInterface,
--           mscMcsMgrFrf5EpGEpEpdExcessInformationRate,
--           mscMcsMgrFrf5EpGEpControlStatus,
--           mscMcsMgrFrf5EpGEpAtmConStorageType }
-- STATUS  mandatory
-- DESCRIPTION
--   "A list of all current accessible leaf objects."

frf5EpGroup OBJECT IDENTIFIER ::= { frf5EpMIB 1 }
frf5EpGroupCA OBJECT IDENTIFIER ::= { frf5EpGroup 1 }
frf5EpGroupCA02 OBJECT IDENTIFIER ::= { frf5EpGroupCA 3 }
frf5EpGroupCA02A OBJECT IDENTIFIER ::= { frf5EpGroupCA02 2 }



-- Agent-Capabilities Statement:

-- PRODUCT-RELEASE "MscPassport Release 1.2 Frf5Ep."
-- STATUS          mandatory
-- DESCRIPTION     "Carrier Passport Frf5Ep MIB: MIB Version CA02A,
--                  Software Version CA02S9C."
-- SUPPORTS        Nortel-MsCarrier-MscPassport-Frf5EpMIB
--    INCLUDES     { frf5EpGroupCA02A }

frf5EpCapabilities OBJECT IDENTIFIER ::= { frf5EpMIB 3 }
frf5EpCapabilitiesCA OBJECT IDENTIFIER ::= { frf5EpCapabilities 1 }
frf5EpCapabilitiesCA02 OBJECT IDENTIFIER ::= { frf5EpCapabilitiesCA 3 }
frf5EpCapabilitiesCA02A OBJECT IDENTIFIER ::= { frf5EpCapabilitiesCA02 2 }





END
