-------------------------------------------------------------------------------
-- file: NncAAL5.mib
--
-- description:
--      This file contains the SNMP definitions for Newbridge ATM
--      AAL5 configuration and statistics.
--
-- %%history-start%%
-- 1999.05.26 dylans 31A1284: atm.van2 trib merge 
-- 1999.06.23 dylans P.284729: Updated after review 
-- %%history-end%%
--
-- Copyright 1998 Newbridge Networks Corporation.  All Rights Reserved
-------------------------------------------------------------------------------
NNCAAL5-MIB DEFINITIONS ::= BEGIN
 
  IMPORTS
    MODULE-IDENTITY, OBJECT-TYPE, Counter32    FROM SNMPv2-SMI
    TEXTUAL-CONVENTION                         FROM SNMPv2-TC
    MODULE-COMPLIANCE, OBJECT-GROUP            FROM SNMPv2-CONF
    ifIndex                                    FROM IF-MIB
    atmVclVpi, atmVclVci                       FROM ATM-MIB
    nncExtensions                              FROM NNCGNI0001-SMI;

nncAAL5 MODULE-IDENTITY
  LAST-UPDATED    "9906101200Z"
  ORGANIZATION    "Newbridge Networks Corporation"
  CONTACT-INFO
                  "Newbridge Networks Corporation
                   Postal: 600 March Road
                   Kanata, Ontario
                   Canada K2K 2E6
 
                   Phone:  +1 613 591 3600
                   Fax:    +1 613 591 3680"
 
  DESCRIPTION     "This module contains definitions for monitoring and 
                   configuring AAL5 information on Newbridge ATM cards."
 
  ::= { nncExtensions 71 }
 

  nncAAL5Objects            OBJECT IDENTIFIER ::= { nncAAL5 1}
  nncAAL5Traps              OBJECT IDENTIFIER ::= { nncAAL5 2} 
  nncAAL5Groups             OBJECT IDENTIFIER ::= { nncAAL5 3}
  nncAAL5Compliances        OBJECT IDENTIFIER ::= { nncAAL5 4}

  nncAAL5Configuration      OBJECT IDENTIFIER ::= { nncAAL5Objects 1}
  nncAAL5Statistics         OBJECT IDENTIFIER ::= { nncAAL5Objects 2}

-------------------------------------------------------------------------------
-- AAL5 Statistics Table
-------------------------------------------------------------------------------
 
nncAAL5StatisticsTable    OBJECT-TYPE
    SYNTAX        SEQUENCE OF NncAAL5StatisticsEntry
    MAX-ACCESS    not-accessible
    STATUS        current
    DESCRIPTION
        "The nncAAL5StatisticsTable contains AAL5 Statistics on a per
         connection basis."
    ::= { nncAAL5Statistics 1 }
 
nncAAL5StatisticsEntry    OBJECT-TYPE
    SYNTAX        NncAAL5StatisticsEntry
    MAX-ACCESS    not-accessible
    STATUS        current
    DESCRIPTION
        "An entry in the nncAAL5StatisticsTable."
    INDEX  { ifIndex, atmVclVpi, atmVclVci }
    ::= { nncAAL5StatisticsTable 1 }
 
NncAAL5StatisticsEntry ::= SEQUENCE  {
    nncAAL5RxPDUs                            Counter32,
    nncAAL5TxPDUs                            Counter32,
    nncAAL5Crc32PDUErrors                    Counter32,
    nncAAL5InvalidFormatPDU                  Counter32,
    nncAAL5OversizedSDU                      Counter32,
    nncAAL5InvalidFields                     Counter32,
    nncAAL5ReassemblyTimerExpirations        Counter32
    }

nncAAL5RxPDUs         OBJECT-TYPE
    SYNTAX        Counter32
    MAX-ACCESS    read-only
    STATUS        current
    DESCRIPTION
        "This count gives the number of AAL5 PDUs received."
    ::= { nncAAL5StatisticsEntry 1 }

nncAAL5TxPDUs         OBJECT-TYPE
    SYNTAX        Counter32
    MAX-ACCESS    read-only
    STATUS        current
    DESCRIPTION
        "This count gives the number of AAL5 PDUs transmitted."
    ::= { nncAAL5StatisticsEntry 2 }

nncAAL5Crc32PDUErrors         OBJECT-TYPE
    SYNTAX        Counter32
    MAX-ACCESS    read-only
    STATUS        current
    DESCRIPTION
        "This count gives the number of AAL5 CRC-32 errors in the cell
         payload."
    ::= { nncAAL5StatisticsEntry 3 }

nncAAL5InvalidFormatPDU       OBJECT-TYPE
    SYNTAX        Counter32
    MAX-ACCESS    read-only
    STATUS        current
    DESCRIPTION
        "This count gives the number of all AAL5 invalid format PDU errors."
    ::= { nncAAL5StatisticsEntry 4 }

nncAAL5OversizedSDU           OBJECT-TYPE
    SYNTAX        Counter32
    MAX-ACCESS    read-only
    STATUS        current
    DESCRIPTION
        "This count gives the number of reassembled SDUs which were larger
         than the allowed size for the application."
    ::= { nncAAL5StatisticsEntry 5 }

nncAAL5InvalidFields          OBJECT-TYPE
    SYNTAX        Counter32
    MAX-ACCESS    read-only
    STATUS        current
    DESCRIPTION
        "This count gives the sum of three simple counts: Invalid Format PDU,
         Oversized SDU, and Length Violation."
    ::= { nncAAL5StatisticsEntry 6 }

nncAAL5ReassemblyTimerExpirations  OBJECT-TYPE
    SYNTAX        Counter32
    MAX-ACCESS    read-only
    STATUS        current
    DESCRIPTION
        "This count gives the number of reassembly timer expirations."
    ::= { nncAAL5StatisticsEntry 7 }

 
-------------------------------------------------------------------------------
-- Conformance Group Definitions
-------------------------------------------------------------------------------
 
nncAAL5BasicStatisticsGroup        OBJECT-GROUP
  OBJECTS {
    nncAAL5RxPDUs,
    nncAAL5TxPDUs,
    nncAAL5Crc32PDUErrors,
    nncAAL5InvalidFormatPDU,
    nncAAL5OversizedSDU,
    nncAAL5InvalidFields,
    nncAAL5ReassemblyTimerExpirations
  }
  STATUS          current
  DESCRIPTION     "Collection of objects providing raw AAL5 stats."
  ::= { nncAAL5Groups 1 }


-------------------------------------------------------------------------------
-- Compliance Statements (mandatory)
-------------------------------------------------------------------------------
nncAAL5Compliance    MODULE-COMPLIANCE
  STATUS          current
  DESCRIPTION     "The compliance statement for Newbridge SNMP."
  MODULE
    MANDATORY-GROUPS {
      nncAAL5BasicStatisticsGroup
    }
  ::= { nncAAL5Compliances 1 }
 
 
-------------------------------------------------------------------------------
--      Review Minutes
-------------------------------------------------------------------------------
END -- DEFINITION OF NNCAAL5-MIB
