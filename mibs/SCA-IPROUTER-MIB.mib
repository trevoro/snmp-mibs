SCA-IPROUTER-MIB DEFINITIONS ::= BEGIN

-- Copyright (C) 1997 Intel Corporation. All rights reserved.
--
-- IP router MIB, 97-03-14
--
-- This MIB defines the management information for a system functioning
-- as an IP router.
--
-- Change History:
-- 97-03-14 Initial version

    IMPORTS
      Counter, IpAddress FROM RFC1155-SMI
      scanet             FROM SCANET-MIB
      OBJECT-TYPE        FROM RFC-1212;


    iprouter             OBJECT IDENTIFIER ::= { scanet 42 }

--********************** IP configuration ***********************************

    conf                 OBJECT IDENTIFIER ::= { iprouter 1 }

--********************** IP Interface configuration *************************

    confIfTable OBJECT-TYPE
    SYNTAX SEQUENCE OF ConfIfEntry
    ACCESS not-accessible
    STATUS mandatory
    DESCRIPTION "The table contains configuration information for each
                 IP link."
    ::= { conf 1 }

    confIfEntry OBJECT-TYPE
    SYNTAX ConfIfEntry
    ACCESS not-accessible
    STATUS mandatory
    DESCRIPTION "Configuration information for the IP link."
    INDEX { confIfIndex }
    ::= { confIfTable 1 }

    ConfIfEntry ::=
    SEQUENCE {
      confIfIndex
        INTEGER,
      confIfAddrAndMask1
        OCTET STRING (SIZE (8)),
      confIfAddrAndMask2
        OCTET STRING (SIZE (8)),
      confIfAddrAndMask3
        OCTET STRING (SIZE (8)),
      confIfAddrAndMask4
        OCTET STRING (SIZE (8)),
      confIfRouteProto
        INTEGER,
      confIfTrigRip
        INTEGER,
      confIfRipMetric
        INTEGER,
      confIfRip2AuthType
        INTEGER,
      confIfRip2AuthKey
        OCTET STRING (SIZE (0..16)),
      confIfBootpReqForw
        INTEGER,
      confIfProxyArp
        INTEGER,
      confIfFiltering
        INTEGER,
      confIfRxDefAction
        INTEGER,
      confIfTxDefAction
        INTEGER,
      confIfRxDefLogging
        INTEGER,
      confIfTxDefLogging
        INTEGER,
      confIfCreateObj
        OCTET STRING (SIZE (59)),
      confIfDeleteObj
        INTEGER
    }

    confIfIndex OBJECT-TYPE
    SYNTAX INTEGER
    ACCESS read-only
    STATUS mandatory
    DESCRIPTION "The ifIndex of the IP link."
    ::= { confIfEntry 1 }

    confIfAddrAndMask1 OBJECT-TYPE
    SYNTAX OCTET STRING (SIZE (8))
    ACCESS read-write
    STATUS mandatory
    DESCRIPTION "The primary IP Address and Mask of the IP link.
                 The format of the octet string is:
                 4 bytes : IP Address.
                 4 bytes : Subnet Mask.
                 A string of all zeros is used for unnumbered links."
    ::= { confIfEntry 2 }

    confIfAddrAndMask2 OBJECT-TYPE
    SYNTAX OCTET STRING (SIZE (8))
    ACCESS read-write
    STATUS mandatory
    DESCRIPTION "The second IP Address and Mask of the IP link.
                 The format of the octet string is:
                 4 bytes : IP Address.
                 4 bytes : Subnet Mask."
    ::= { confIfEntry 3 }

    confIfAddrAndMask3 OBJECT-TYPE
    SYNTAX OCTET STRING (SIZE (8))
    ACCESS read-write
    STATUS mandatory
    DESCRIPTION "The third IP Address and Mask of the IP link.
                 The format of the octet string is:
                 4 bytes : IP Address.
                 4 bytes : Subnet Mask."
    ::= { confIfEntry 4 }

    confIfAddrAndMask4 OBJECT-TYPE
    SYNTAX OCTET STRING (SIZE (8))
    ACCESS read-write
    STATUS mandatory
    DESCRIPTION "The fourth IP Address and Mask of the IP link.
                 The format of the octet string is:
                 4 bytes : IP Address.
                 4 bytes : Subnet Mask."
    ::= { confIfEntry 5 }

    confIfRouteProto OBJECT-TYPE
    SYNTAX INTEGER {
      none (1),
      rip-1 (2),
      rip-2 (3)
    }
    ACCESS read-write
    STATUS mandatory
    DESCRIPTION "The Routing Protocol used on the link."
    ::= { confIfEntry 6 }

    confIfTrigRip OBJECT-TYPE
    SYNTAX INTEGER {
      disabled (1),
      enabled (2)
    }
    ACCESS read-write
    STATUS mandatory
    DESCRIPTION "Indicates whether Triggered RIP is used on the link."
    ::= { confIfEntry 7 }

    confIfRipMetric OBJECT-TYPE
    SYNTAX INTEGER (1..15)
    ACCESS read-write
    STATUS mandatory
    DESCRIPTION "The RIP metric used on the link."
    ::= { confIfEntry 8 }

    confIfRip2AuthType OBJECT-TYPE
    SYNTAX INTEGER {
      none (1),
      simple-password (2)
    }
    ACCESS read-write
    STATUS mandatory
    DESCRIPTION "The RIP-2 Authentication type used on the link."
    ::= { confIfEntry 9 }

    confIfRip2AuthKey OBJECT-TYPE
    SYNTAX OCTET STRING (SIZE (0..16))
    ACCESS read-write
    STATUS mandatory
    DESCRIPTION "The authentication key used in RIP-2."
    ::= { confIfEntry 10 }

    confIfBootpReqForw OBJECT-TYPE
    SYNTAX INTEGER {
      disabled (1),
      enabled (2)
    }
    ACCESS read-write
    STATUS mandatory
    DESCRIPTION "Indicates whether BOOTP requests are forwarded on the link"
    ::= { confIfEntry 11 }

    confIfProxyArp OBJECT-TYPE
    SYNTAX INTEGER {
      disabled (1),
      enabled (2)
    }
    ACCESS read-write
    STATUS mandatory
    DESCRIPTION "Indicates whether Proxy Arp is used on the link."
    ::= { confIfEntry 12 }

    confIfFiltering OBJECT-TYPE
    SYNTAX INTEGER {
      disabled (1),
      enabled (2)
    }
    ACCESS read-write
    STATUS mandatory
    DESCRIPTION "Indicates whether IP filtering is used on the link."
    ::= { confIfEntry 13 }

    confIfRxDefAction OBJECT-TYPE
    SYNTAX INTEGER {
      discard (1),
      pass (2)
    }
    ACCESS read-write
    STATUS mandatory
    DESCRIPTION "Indicates whether packets not matching any of the Rx
                 filters on the link must be passed or discarded."
    ::= { confIfEntry 14 }

    confIfTxDefAction OBJECT-TYPE
    SYNTAX INTEGER {
      discard (1),
      pass (2)
    }
    ACCESS read-write
    STATUS mandatory
    DESCRIPTION "Indicates whether packets not matching any of the Tx
                 filters on the link must be passed or discarded."
    ::= { confIfEntry 15 }

    confIfRxDefLogging OBJECT-TYPE
    SYNTAX INTEGER {
      disabled (1),
      enabled (2)
    }
    ACCESS read-write
    STATUS mandatory
    DESCRIPTION "Indicates whether packets not matching any of the Rx
                 filters must be logged."
    ::= { confIfEntry 16 }

    confIfTxDefLogging OBJECT-TYPE
    SYNTAX INTEGER {
      disabled (1),
      enabled (2)
    }
    ACCESS read-write
    STATUS mandatory
    DESCRIPTION "Indicates whether packets not matching any of the Tx
                 filters must be logged."
    ::= { confIfEntry 17 }

    confIfCreateObj OBJECT-TYPE
    SYNTAX OCTET STRING (SIZE (59))
    ACCESS read-write
    STATUS mandatory
    DESCRIPTION "Create a non existing table entry. If the entry already exist,
                 genError is returned.
                 Binary format:
                 4 bytes : confIfAddr1
                 4 bytes : confIfMask1
                 4 bytes : confIfAddr2
                 4 bytes : confIfMask2
                 4 bytes : confIfAddr3
                 4 bytes : confIfMask3
                 4 bytes : confIfAddr4
                 4 bytes : confIfMask4
                 1 bytes : confIfRouteProto
                 1 bytes : confIfTrigRip
                 1 bytes : confIfRipMetric
                 1 bytes : confIfRip2AuthType
                16 bytes : confIfRip2AuthKey
                 1 bytes : confIfBootpReqForw
                 1 bytes : confIfProxyArp
                 1 bytes : confIfFiltering
                 1 bytes : confIfRxDefAction
                 1 bytes : confIfTxDefAction
                 1 bytes : confIfRxDefLogging
                 1 bytes : confIfTxDefLogging
                 "
    ::= { confIfEntry 18 }

    confIfDeleteObj OBJECT-TYPE
    SYNTAX INTEGER {
      delete (1)
    }
    ACCESS read-write
    STATUS mandatory
    DESCRIPTION "Delete an existing table entry"
    ::= { confIfEntry 19 }


--********************** IP filter configuration ****************************

    filterTable OBJECT-TYPE
    SYNTAX SEQUENCE OF FilterEntry
    ACCESS not-accessible
    STATUS mandatory
    DESCRIPTION "The table contains IP filter configuration information."
    ::= { conf 2 }

    filterEntry OBJECT-TYPE
    SYNTAX FilterEntry
    ACCESS not-accessible
    STATUS mandatory
    DESCRIPTION "Configuration information for the IP filter."
    INDEX { filterIfIndex, filterDirIndex, filterIndex }
    ::= { filterTable 1 }

    FilterEntry ::=
    SEQUENCE {
      filterIfIndex
        INTEGER,
      filterDirIndex
        INTEGER,
      filterIndex
        INTEGER,
      filterAction
        INTEGER,
      filterLogging
        INTEGER,
      filterProtocol
        INTEGER,
      filterProtocolValue
        INTEGER,
      filterTcpFlags
        INTEGER,
      filterSrcAddrType
        INTEGER,
      filterSrcAddr
        IpAddress,
      filterSrcMask
        IpAddress,
      filterDestAddrType
        INTEGER,
      filterDestAddr
        IpAddress,
      filterDestMask
        IpAddress,
      filterSrcPort
        INTEGER,
      filterSrcPortValue
        INTEGER,
      filterSrcPortOper
        INTEGER,
      filterDestPort
        INTEGER,
      filterDestPortValue
        INTEGER,
      filterDestPortOper
        INTEGER,
      filterHits
        INTEGER
    }

    filterIfIndex OBJECT-TYPE
    SYNTAX INTEGER
    ACCESS read-only
    STATUS mandatory
    DESCRIPTION "The ifIndex of the IP link on which the filter is used."
    ::= { filterEntry 1 }

    filterDirIndex OBJECT-TYPE
    SYNTAX INTEGER {
      rx (1),
      tx (2)
    }
    ACCESS read-only
    STATUS mandatory
    DESCRIPTION "Indicates whether the filter is an Rx or Tx filter."
    ::= { filterEntry 2 }

    filterIndex OBJECT-TYPE
    SYNTAX INTEGER
    ACCESS read-only
    STATUS mandatory
    DESCRIPTION "Index in the Rx or Tx filter list for the link."
    ::= { filterEntry 3 }

    filterAction OBJECT-TYPE
    SYNTAX INTEGER {
      discard (1),
      pass (2),
      disabled (3)
    }
    ACCESS read-write
    STATUS mandatory
    DESCRIPTION "The action to be taken when a packet matches the filter.
                 Disabled filters are ignored."
    ::= { filterEntry 4 }

    filterLogging OBJECT-TYPE
    SYNTAX INTEGER {
      disabled (1),
      enabled (2)
    }
    ACCESS read-write
    STATUS mandatory
    DESCRIPTION "Indicates whether packets matching the filter must be logged."
    ::= { filterEntry 5 }

    filterProtocol OBJECT-TYPE
    SYNTAX INTEGER {
      all (1),
      other (2),
      icmp (3),
      tcp (4),
      udp (5)
    }
    ACCESS read-write
    STATUS mandatory
    DESCRIPTION "Indicates whether the filter matches all protocols, a user
                 defined protocol or a known protocol."
    ::= { filterEntry 6 }

    filterProtocolValue OBJECT-TYPE
    SYNTAX INTEGER (0..255)
    ACCESS read-write
    STATUS mandatory
    DESCRIPTION "The protocol field in the IP header of the packet."
    ::= { filterEntry 7 }

    filterTcpFlags OBJECT-TYPE
    SYNTAX INTEGER {
      all (1),
      ack (2)
    }
    ACCESS read-write
    STATUS mandatory
    DESCRIPTION "Indicates whether the filter matches all TCP packets or
                 only TCP packets with the ACK flag set. When the ACK flag is
                 set, the packet belongs to an established TCP connection."
    ::= { filterEntry 8 }

    filterSrcAddrType OBJECT-TYPE
    SYNTAX INTEGER {
      all (1),
      network (2),
      host (3)
    }
    ACCESS read-write
    STATUS mandatory
    DESCRIPTION "Indicates whether the filter matches all source addresses,
                 addresses on a specific network or a specific host address."
    ::= { filterEntry 9 }

    filterSrcAddr OBJECT-TYPE
    SYNTAX IpAddress
    ACCESS read-write
    STATUS mandatory
    DESCRIPTION "Indicates the network or host address which the source
                 address must match."
    ::= { filterEntry 10 }

    filterSrcMask OBJECT-TYPE
    SYNTAX IpAddress
    ACCESS read-write
    STATUS mandatory
    DESCRIPTION "The subnet mask of the network which the source address
                 must match."
    ::= { filterEntry 11 }

    filterSrcPort OBJECT-TYPE
    SYNTAX INTEGER {
      all (1),
      other (2),
      ftp-data (20),
      ftp-control (21),
      telnet (23),
      smtp (25),
      dns (53),
      bootp-server (67),
      bootp-client (68),
      tftp (69),
      gopher (70),
      www (80),
      snmp (161),
      snmp-trap(162),
      rip (520),
      nfs (2049)
    }
    ACCESS read-write
    STATUS mandatory
    DESCRIPTION "Indicates whether the filter matches all or a specific
                 UDP/TCP source port."
    ::= { filterEntry 12 }

    filterSrcPortValue OBJECT-TYPE
    SYNTAX INTEGER (0..65535)
    ACCESS read-write
    STATUS mandatory
    DESCRIPTION "The UDP/TCP source port of the filter."
    ::= { filterEntry 13 }

    filterSrcPortOper OBJECT-TYPE
    SYNTAX INTEGER {
      equal-to (1),
      not-equal-to (2),
      greater-than (3),
      less-than (4)
    }
    ACCESS read-write
    STATUS mandatory
    DESCRIPTION "The source port operator indicates whether UDP/TCP source
                 port values equal to, not equal to, greater than or less
                 than the filter source port match the filter."
    ::= { filterEntry 14 }

    filterDestAddrType OBJECT-TYPE
    SYNTAX INTEGER {
      all (1),
      network (2),
      host (3)
    }
    ACCESS read-write
    STATUS mandatory
    DESCRIPTION "Indicates whether the filter matches all destination
                 addresses, addresses on a specific network or a specific
                 host address."
    ::= { filterEntry 15 }

    filterDestAddr OBJECT-TYPE
    SYNTAX IpAddress
    ACCESS read-write
    STATUS mandatory
    DESCRIPTION "Indicates the network or host address which the destination
                 address must match."
    ::= { filterEntry 16 }

    filterDestMask OBJECT-TYPE
    SYNTAX IpAddress
    ACCESS read-write
    STATUS mandatory
    DESCRIPTION "The subnet mask of the network which the destination
               address must match."
    ::= { filterEntry 17 }

    filterDestPort OBJECT-TYPE
    SYNTAX INTEGER {
      all (1),
      other (2),
      ftp-data (20),
      ftp-control (21),
      telnet (23),
      smtp (25),
      dns (53),
      bootp-server (67),
      bootp-client (68),
      tftp (69),
      gopher (70),
      www (80),
      snmp (161),
      snmp-trap(162),
      rip (520),
      nfs (2049)
    }
    ACCESS read-write
    STATUS mandatory
    DESCRIPTION "Indicates whether the filter matches all or a specific
                 UDP/TCP destination port."
    ::= { filterEntry 18 }

    filterDestPortValue OBJECT-TYPE
    SYNTAX INTEGER (0..65535)
    ACCESS read-write
    STATUS mandatory
    DESCRIPTION "The UDP/TCP destination port of the filter."
    ::= { filterEntry 19 }

    filterDestPortOper OBJECT-TYPE
    SYNTAX INTEGER {
      equal-to (1),
      not-equal-to (2),
      greater-than (3),
      less-than (4)
    }
    ACCESS read-write
    STATUS mandatory
    DESCRIPTION "The destination port operator indicates whether UDP/TCP
                 destination port values equal to, not equal to, greater than
                 or less than the filter destination port match the filter."
    ::= { filterEntry 20 }

    filterHits OBJECT-TYPE
    SYNTAX Counter
    ACCESS read-only
    STATUS mandatory
    DESCRIPTION "The number of packets matching the filter."
    ::= { filterEntry 21 }

--********************** IP NAT configuration *******************************

    natTable OBJECT-TYPE
    SYNTAX SEQUENCE OF NatEntry
    ACCESS not-accessible
    STATUS mandatory
    DESCRIPTION "The table contains NAT information."
    ::= { conf 3 }

    natEntry OBJECT-TYPE
    SYNTAX NatEntry
    ACCESS not-accessible
    STATUS mandatory
    DESCRIPTION "Information for the NAT entry."
    INDEX { natIfIndex, natIndex }
    ::= { natTable 1 }

    NatEntry ::=
    SEQUENCE {
      natIfIndex
        INTEGER,
      natIndex
        INTEGER,
      natIntAddr
        IpAddress,
      natIntMask
        IpAddress,
      natExtAddr
        IpAddress,
      natExtMask
        IpAddress,
      natType
        INTEGER,
      natAuto
        INTEGER,
      natTime
        INTEGER
    }

    natIfIndex OBJECT-TYPE
    SYNTAX INTEGER
    ACCESS read-only
    STATUS mandatory
    DESCRIPTION "The ifIndex of the IP link on which the NAT entry
                 is used."
    ::= { natEntry 1 }

    natIndex OBJECT-TYPE
    SYNTAX INTEGER
    ACCESS read-only
    STATUS mandatory
    DESCRIPTION "Internal NAT index."
    ::= { natEntry 2 }

    natIntAddr OBJECT-TYPE
    SYNTAX IpAddress
    ACCESS read-write
    STATUS mandatory
    DESCRIPTION "The Internal IP Address of the NAT entry."
    ::= { natEntry 3 }

    natIntMask OBJECT-TYPE
    SYNTAX IpAddress
    ACCESS read-write
    STATUS mandatory
    DESCRIPTION "The Internal Mask of the NAT entry."
    ::= { natEntry 4 }

    natExtAddr OBJECT-TYPE
    SYNTAX IpAddress
    ACCESS read-write
    STATUS mandatory
    DESCRIPTION "The External IP Address of the NAT entry."
    ::= { natEntry 5 }

    natExtMask OBJECT-TYPE
    SYNTAX IpAddress
    ACCESS read-write
    STATUS mandatory
    DESCRIPTION "The External Mask of the NAT entry."
    ::= { natEntry 6 }

    natType OBJECT-TYPE
    SYNTAX INTEGER {
      static (1),
      dynamic (2)
    }
    ACCESS read-write
    STATUS mandatory
    DESCRIPTION "Indicates whether the NAT entry is static or dynamic."
    ::= { natEntry 7 }

    natAuto OBJECT-TYPE
    SYNTAX INTEGER {
      yes (1),
      no (2)
    }
    ACCESS read-only
    STATUS mandatory
    DESCRIPTION "Indicates whether the NAT entry has been automatically
                 inserted."
    ::= { natEntry 8 }

    natTime OBJECT-TYPE
    SYNTAX INTEGER
    ACCESS read-only
    STATUS mandatory
    DESCRIPTION "The time left for dynamic NAT entries."
    ::= { natEntry 9 }


--********************** IP Static Route configuration *********************

    statRoutTable OBJECT-TYPE
    SYNTAX SEQUENCE OF StatRoutEntry
    ACCESS not-accessible
    STATUS mandatory
    DESCRIPTION "The table contains static route information."
    ::= { conf 4 }

    statRoutEntry OBJECT-TYPE
    SYNTAX StatRoutEntry
    ACCESS not-accessible
    STATUS mandatory
    DESCRIPTION "Information for the static route entry."
    INDEX { statRoutIfIndex, statRoutNetwork }
    ::= { statRoutTable 1 }

    StatRoutEntry ::=
    SEQUENCE {
      statRoutIfIndex
        INTEGER,
      statRoutNetwork
        IpAddress,
      statRoutMask
        IpAddress,
      statRoutNextHop
        IpAddress,
      statRoutMetric
        INTEGER,
      statRoutCreateObj
        OCTET STRING (SIZE (12)),
      statRoutDeleteObj
        INTEGER
    }

    statRoutIfIndex OBJECT-TYPE
    SYNTAX INTEGER
    ACCESS read-write
    STATUS mandatory
    DESCRIPTION "The ifIndex of the IP link on which the static route is used."
    ::= { statRoutEntry 1 }

    statRoutNetwork OBJECT-TYPE
    SYNTAX IpAddress
    ACCESS read-write
    STATUS mandatory
    DESCRIPTION "IP address of network."
    ::= { statRoutEntry 2 }

    statRoutMask OBJECT-TYPE
    SYNTAX IpAddress
    ACCESS read-write
    STATUS mandatory
    DESCRIPTION "Subnet mask of network"
    ::= { statRoutEntry 3 }

    statRoutNextHop OBJECT-TYPE
    SYNTAX IpAddress
    ACCESS read-write
    STATUS mandatory
    DESCRIPTION "Next hop router (LAN only)"
    ::= { statRoutEntry 4 }

    statRoutMetric OBJECT-TYPE
    SYNTAX INTEGER
    ACCESS read-write
    STATUS mandatory
    DESCRIPTION "Metric to network"
    ::= { statRoutEntry 5 }

    statRoutCreateObj OBJECT-TYPE
    SYNTAX OCTET STRING (SIZE (12))
    ACCESS read-write
    STATUS mandatory
    DESCRIPTION "Create a non existing table entry. If the entry already exist,
                 genError is returned.
                 Binary format:
                 4 bytes : statRoutMask
                 4 bytes : statRoutNextHop
                 4 bytes : statRoutMetric
                 "
    ::= { statRoutEntry 6 }

    statRoutDeleteObj OBJECT-TYPE
    SYNTAX INTEGER {
      delete (1)
    }
    ACCESS read-write
    STATUS mandatory
    DESCRIPTION "Delete an existing table entry"
    ::= { statRoutEntry 7 }


--********************** IP Statistics *************************************

    stat                 OBJECT IDENTIFIER ::= { iprouter 2 }

    statIfTable OBJECT-TYPE
    SYNTAX SEQUENCE OF StatIfEntry
    ACCESS not-accessible
    STATUS mandatory
    DESCRIPTION "The table contains statistic information for each IP link."
    ::= { stat 1 }

    statIfEntry OBJECT-TYPE
    SYNTAX StatIfEntry
    ACCESS not-accessible
    STATUS mandatory
    DESCRIPTION "Statistic information for the IP link."
    INDEX { statIfIndex }
    ::= { statIfTable 1 }

    StatIfEntry ::=
    SEQUENCE {
      statIfIndex
        INTEGER,
      statIfType
        INTEGER,
      statIfState
        INTEGER,
      statIfMTU
        INTEGER,
      statIfRxDefHits
        Counter,
      statIfTxDefHits
        Counter
    }

    statIfIndex OBJECT-TYPE
    SYNTAX INTEGER
    ACCESS read-only
    STATUS mandatory
    DESCRIPTION "The ifIndex of the IP link."
    ::= { statIfEntry 1 }

    statIfType OBJECT-TYPE
    SYNTAX INTEGER {
      lan (1),
      wan (2)
    }
    ACCESS read-only
    STATUS mandatory
    DESCRIPTION "The type of the network (LAN or WAN) to which the
                 IP link is connected."
    ::= { statIfEntry 2 }

    statIfState OBJECT-TYPE
    SYNTAX INTEGER {
      up (1),
      down (2)
    }
    ACCESS read-only
    STATUS mandatory
    DESCRIPTION "The actual state of the IP link. The link layer
                 informs the IP link of link state changes."
    ::= { statIfEntry 3 }

    statIfMTU OBJECT-TYPE
    SYNTAX INTEGER
    ACCESS read-only
    STATUS mandatory
    DESCRIPTION "The maximum transmit unit of the IP link. IP packets
                 larger than the MTU will be fragmented."
    ::= { statIfEntry 4 }

    statIfRxDefHits OBJECT-TYPE
    SYNTAX Counter
    ACCESS read-only
    STATUS mandatory
    DESCRIPTION "The number of packets that did not match any of the
                 Rx Filters for the link."
    ::= { statIfEntry 5 }

    statIfTxDefHits OBJECT-TYPE
    SYNTAX Counter
    ACCESS read-only
    STATUS mandatory
    DESCRIPTION "The number of packets that did not match any of the
                 Tx Filters for the link."
    ::= { statIfEntry 6 }

--********************** ARP ************************************************

    arp                  OBJECT IDENTIFIER ::= { iprouter 3 }

    arpIfTable OBJECT-TYPE
    SYNTAX SEQUENCE OF ArpIfEntry
    ACCESS not-accessible
    STATUS mandatory
    DESCRIPTION "The table contains ARP information for each IP link."
    ::= { arp 1 }

    arpIfEntry OBJECT-TYPE
    SYNTAX ArpIfEntry
    ACCESS not-accessible
    STATUS mandatory
    DESCRIPTION "ARP information for the IP link."
    INDEX { arpIfIndex }
    ::= { arpIfTable 1 }

    ArpIfEntry ::=
    SEQUENCE {
      arpIfIndex
        INTEGER,
      arpIfInReq
        Counter,
      arpIfOutRep
        Counter,
      arpIfOutReq
        Counter,
      arpIfInRep
        Counter,
      arpIfInHdrErrors
        Counter
    }

    arpIfIndex OBJECT-TYPE
    SYNTAX INTEGER
    ACCESS read-only
    STATUS mandatory
    DESCRIPTION "The ifIndex of the IP link."
    ::= { arpIfEntry 1 }

    arpIfInReq OBJECT-TYPE
    SYNTAX Counter
    ACCESS read-only
    STATUS mandatory
    DESCRIPTION "The number of ARP requests received on the link."
    ::= { arpIfEntry 2 }

    arpIfOutRep OBJECT-TYPE
    SYNTAX Counter
    ACCESS read-only
    STATUS mandatory
    DESCRIPTION "The number of ARP replies sent on the link."
    ::= { arpIfEntry 3 }

    arpIfOutReq OBJECT-TYPE
    SYNTAX Counter
    ACCESS read-only
    STATUS mandatory
    DESCRIPTION "The number of ARP requests sent on the link."
    ::= { arpIfEntry 4 }

    arpIfInRep OBJECT-TYPE
    SYNTAX Counter
    ACCESS read-only
    STATUS mandatory
    DESCRIPTION "The number of ARP replies received on the link."
    ::= { arpIfEntry 5 }

    arpIfInHdrErrors OBJECT-TYPE
    SYNTAX Counter
    ACCESS read-only
    STATUS mandatory
    DESCRIPTION "The number of ARP packets received on the link
                 which were discarded because of ARP header errors."
    ::= { arpIfEntry 6 }


    arpInReq OBJECT-TYPE
    SYNTAX Counter
    ACCESS read-only
    STATUS mandatory
    DESCRIPTION "The total number of ARP requests received."
    ::= { arp 2 }

    arpOutRep OBJECT-TYPE
    SYNTAX Counter
    ACCESS read-only
    STATUS mandatory
    DESCRIPTION "The total number of ARP replies sent."
    ::= { arp 3 }

    arpOutReq OBJECT-TYPE
    SYNTAX Counter
    ACCESS read-only
    STATUS mandatory
    DESCRIPTION "The total number of ARP requests sent."
    ::= { arp 4 }

    arpInRep OBJECT-TYPE
    SYNTAX Counter
    ACCESS read-only
    STATUS mandatory
    DESCRIPTION "The total number of ARP replies received."
    ::= { arp 5 }

    arpInHdrErrors OBJECT-TYPE
    SYNTAX Counter
    ACCESS read-only
    STATUS mandatory
    DESCRIPTION "The total number of received ARP packets which were
                 discarded because of ARP header errors."
    ::= { arp 6 }

--********************** IP *************************************************

    ip                   OBJECT IDENTIFIER ::= { iprouter 4 }

    ipIfTable OBJECT-TYPE
    SYNTAX SEQUENCE OF IpIfEntry
    ACCESS not-accessible
    STATUS mandatory
    DESCRIPTION "The table contains statistic information for each
                 IP link."
    ::= { ip 1 }

    ipIfEntry OBJECT-TYPE
    SYNTAX IpIfEntry
    ACCESS not-accessible
    STATUS mandatory
    DESCRIPTION "IP information for the IP link."
    INDEX { ipIfIndex }
    ::= { ipIfTable 1 }

    IpIfEntry ::=
    SEQUENCE {
      ipIfIndex
        INTEGER,
      ipIfInReceives
        Counter,
      ipIfInHdrErrors
        Counter,
      ipIfInAddrErrors
        Counter,
      ipIfInDiscards
        Counter,
      ipIfForwDatagrams
        Counter,
      ipIfOutRequests
        Counter,
      ipIfOutDiscards
        Counter
    }

    ipIfIndex OBJECT-TYPE
    SYNTAX INTEGER
    ACCESS read-only
    STATUS mandatory
    DESCRIPTION "The ifIndex of the IP link."
    ::= { ipIfEntry 1 }

    ipIfInReceives OBJECT-TYPE
    SYNTAX Counter
    ACCESS read-only
    STATUS mandatory
    DESCRIPTION "The number of IP packets received on the link."
    ::= { ipIfEntry 2 }

    ipIfInHdrErrors OBJECT-TYPE
    SYNTAX Counter
    ACCESS read-only
    STATUS mandatory
    DESCRIPTION "The number of IP packets received on the link
                 which were discarded because of IP header errors."
    ::= { ipIfEntry 3 }

    ipIfInAddrErrors OBJECT-TYPE
    SYNTAX Counter
    ACCESS read-only
    STATUS mandatory
    DESCRIPTION "The number of IP packets received on the link
                 which were discarded because of IP source or destination
                 address errors."
    ::= { ipIfEntry 4 }

    ipIfInDiscards OBJECT-TYPE
    SYNTAX Counter
    ACCESS read-only
    STATUS mandatory
    DESCRIPTION "The number of IP packets received on the link
                 which were discarded because of lack of buffer space."
    ::= { ipIfEntry 5 }

    ipIfForwDatagrams OBJECT-TYPE
    SYNTAX Counter
    ACCESS read-only
    STATUS mandatory
    DESCRIPTION "The number of IP packets forwarded on the link."
    ::= { ipIfEntry 6 }

    ipIfOutRequests OBJECT-TYPE
    SYNTAX Counter
    ACCESS read-only
    STATUS mandatory
    DESCRIPTION "The number of IP packets sent by the router itself."
    ::= { ipIfEntry 7 }

    ipIfOutDiscards OBJECT-TYPE
    SYNTAX Counter
    ACCESS read-only
    STATUS mandatory
    DESCRIPTION "The number of IP packets which should have been sent
                 on the link, but were discarded because of lack
                 of buffer space or failed ARP requests."
    ::= { ipIfEntry 8 }

--********************** ICMP ***********************************************

    icmp                 OBJECT IDENTIFIER ::= { iprouter 5 }

    icmpIfTable OBJECT-TYPE
    SYNTAX SEQUENCE OF IcmpIfEntry
    ACCESS not-accessible
    STATUS mandatory
    DESCRIPTION "The table contains ICMP information for each IP link."
    ::= { icmp 1 }

    icmpIfEntry OBJECT-TYPE
    SYNTAX IcmpIfEntry
    ACCESS not-accessible
    STATUS mandatory
    DESCRIPTION "ICMP information for the IP link."
    INDEX { icmpIfIndex }
    ::= { icmpIfTable 1 }

    IcmpIfEntry ::=
    SEQUENCE {
      icmpIfIndex
        INTEGER,
      icmpIfInMsgs
        Counter,
      icmpIfInErrors
        Counter,
      icmpIfInEchos
        Counter,
      icmpIfInEchoReps
        Counter,
      icmpIfOutMsgs
        Counter,
      icmpIfOutEchos
        Counter,
      icmpIfOutEchoReps
        Counter
    }

    icmpIfIndex OBJECT-TYPE
    SYNTAX INTEGER
    ACCESS read-only
    STATUS mandatory
    DESCRIPTION "The ifIndex of the IP link."
    ::= { icmpIfEntry 1 }

    icmpIfInMsgs OBJECT-TYPE
    SYNTAX Counter
    ACCESS read-only
    STATUS mandatory
    DESCRIPTION "The number of ICMP messages to the router received
                 on the link."
    ::= { icmpIfEntry 2 }

    icmpIfInErrors OBJECT-TYPE
    SYNTAX Counter
    ACCESS read-only
    STATUS mandatory
    DESCRIPTION "The number of ICMP messages to the router received
                 on the link which were discarded because of ICMP
                 header errors."
    ::= { icmpIfEntry 3 }

    icmpIfInEchos OBJECT-TYPE
    SYNTAX Counter
    ACCESS read-only
    STATUS mandatory
    DESCRIPTION "The number of ICMP echo requests received on the link."
    ::= { icmpIfEntry 4 }

    icmpIfInEchoReps OBJECT-TYPE
    SYNTAX Counter
    ACCESS read-only
    STATUS mandatory
    DESCRIPTION "The number of ICMP echo replies received on the link."
    ::= { icmpIfEntry 5 }

    icmpIfOutMsgs OBJECT-TYPE
    SYNTAX Counter
    ACCESS read-only
    STATUS mandatory
    DESCRIPTION "The number of ICMP messages sent on the link."
    ::= { icmpIfEntry 6 }

    icmpIfOutEchos OBJECT-TYPE
    SYNTAX Counter
    ACCESS read-only
    STATUS mandatory
    DESCRIPTION "The number of ICMP echo requests sent on the link."
    ::= { icmpIfEntry 7 }

    icmpIfOutEchoReps OBJECT-TYPE
    SYNTAX Counter
    ACCESS read-only
    STATUS mandatory
    DESCRIPTION "The number of ICMP echo replies sent on the link."
    ::= { icmpIfEntry 8 }

    icmpInRouterAdvs OBJECT-TYPE
    SYNTAX Counter
    ACCESS read-only
    STATUS mandatory
    DESCRIPTION "The total number of received ICMP Router Advertisements."
    ::= { icmp 2 }

    icmpInRouterSols OBJECT-TYPE
    SYNTAX Counter
    ACCESS read-only
    STATUS mandatory
    DESCRIPTION "The total number of received ICMP Router Solicitations."
    ::= { icmp 3 }

    icmpOutRouterAdvs OBJECT-TYPE
    SYNTAX Counter
    ACCESS read-only
    STATUS mandatory
    DESCRIPTION "The total number of sent ICMP Router Advertisements."
    ::= { icmp 4 }

    icmpOutRouterSols OBJECT-TYPE
    SYNTAX Counter
    ACCESS read-only
    STATUS mandatory
  DESCRIPTION "The total number of sent ICMP Router Solicitations."
    ::= { icmp 5 }


--********************** RIP ************************************************

    rip                  OBJECT IDENTIFIER ::= { iprouter 6 }

    ripIfTable OBJECT-TYPE
    SYNTAX SEQUENCE OF RipIfEntry
    ACCESS not-accessible
    STATUS mandatory
    DESCRIPTION "The table contains RIP information for each IP link."
    ::= { rip 1 }

    ripIfEntry OBJECT-TYPE
    SYNTAX RipIfEntry
    ACCESS not-accessible
    STATUS mandatory
    DESCRIPTION "RIP information for the IP link."
    INDEX { ripIfIndex }
    ::= { ripIfTable 1 }

    RipIfEntry ::=
    SEQUENCE {
      ripIfIndex
        INTEGER,
      ripIfInReceives
        Counter,
      ripIfInHdrErrors
        Counter,
      ripIfInBadSrcAddrs
        Counter,
      ripIfInBadVers
        Counter,
      ripIfInAuthFails
        Counter,
      ripIfInUnknComs
        Counter,
      ripIfOutSent
        Counter,
      ripIfOutDiscards
        Counter
    }

    ripIfIndex OBJECT-TYPE
    SYNTAX INTEGER
    ACCESS read-only
    STATUS mandatory
    DESCRIPTION "The ifIndex of the IP link."
    ::= { ripIfEntry 1 }

    ripIfInReceives OBJECT-TYPE
    SYNTAX Counter
    ACCESS read-only
    STATUS mandatory
    DESCRIPTION "The number of RIP packets received on the link."
    ::= { ripIfEntry 2 }

    ripIfInHdrErrors OBJECT-TYPE
    SYNTAX Counter
    ACCESS read-only
    STATUS mandatory
    DESCRIPTION "The number of RIP packets received on the link
                 which were discarded because of RIP header errors."
    ::= { ripIfEntry 3 }

    ripIfInBadSrcAddrs OBJECT-TYPE
    SYNTAX Counter
    ACCESS read-only
    STATUS mandatory
    DESCRIPTION "The number of RIP packets received on the link which
                 were discarded because of source address errors.
                 This may indicate an IP address configuration error on
                 the link or the link of the router from which the RIP
                 packet was received. The error may also occur if the
                 link is connected to a physical network with multiple
                 logical IP networks. In the latter case a source
                 address error is not an indication of an IP address
                 configuration error."
    ::= { ripIfEntry 4 }

    ripIfInBadVers OBJECT-TYPE
    SYNTAX Counter
    ACCESS read-only
    STATUS mandatory
    DESCRIPTION "The number of RIP packets received on the link which
                 were discarded because of RIP version errors.
                 This indicates a RIP configuration error on the link
                 or the link of the router from which the RIP packet
                 was received. The error occurs when receiving a RIP
                 packet with a version different from the version configured
                 on the link. The error also occurs if a RIP packet
                 is received and the link is configured not to use RIP."
    ::= { ripIfEntry 5 }

    ripIfInAuthFails OBJECT-TYPE
    SYNTAX Counter
    ACCESS read-only
    STATUS mandatory
    DESCRIPTION "The number of RIP packets received on the link which
                 were discarded because of RIP-2 authentication failures."
    ::= { ripIfEntry 6 }

    ripIfInUnknComs OBJECT-TYPE
    SYNTAX Counter
    ACCESS read-only
    STATUS mandatory
    DESCRIPTION "The number of RIP packets received on the link which
                 were discarded because of an unknown command type.
                 This may indicate that the link is not configured to use
                 Triggered RIP and the remote router is using Triggered RIP."
    ::= { ripIfEntry 7 }

    ripIfOutSent OBJECT-TYPE
    SYNTAX Counter
    ACCESS read-only
    STATUS mandatory
    DESCRIPTION "The number of RIP packets sent on the link."
    ::= { ripIfEntry 8 }

    ripIfOutDiscards OBJECT-TYPE
    SYNTAX Counter
    ACCESS read-only
    STATUS mandatory
    DESCRIPTION "The number of RIP packets discarded because
                 of lack of buffer space."
    ::= { ripIfEntry 9 }


    ripInReceives OBJECT-TYPE
    SYNTAX Counter
    ACCESS read-only
    STATUS mandatory
    DESCRIPTION "The total number of received RIP packets."
    ::= { rip 2 }

    ripInHdrErrors OBJECT-TYPE
    SYNTAX Counter
    ACCESS read-only
    STATUS mandatory
    DESCRIPTION "The total number of received RIP packets discarded
                 because of RIP header errors."
    ::= { rip 3 }

    ripInBadSrcAddrs OBJECT-TYPE
    SYNTAX Counter
    ACCESS read-only
    STATUS mandatory
    DESCRIPTION "The total number of received RIP packets discarded
                 because of source address errors."
    ::= { rip 4 }

    ripInBadVers OBJECT-TYPE
    SYNTAX Counter
    ACCESS read-only
    STATUS mandatory
    DESCRIPTION "The total number of received RIP packets discarded
                 because of RIP version errors."
    ::= { rip 5 }

    ripInAuthFails OBJECT-TYPE
    SYNTAX Counter
    ACCESS read-only
    STATUS mandatory
    DESCRIPTION "The total number of RIP-2 authentication failures."
    ::= { rip 6 }

    ripInUnknComs OBJECT-TYPE
    SYNTAX Counter
    ACCESS read-only
    STATUS mandatory
    DESCRIPTION "The total number of received RIP packets discarded
                 because of an unknown command type."
    ::= { rip 7 }

    ripOutSent OBJECT-TYPE
    SYNTAX Counter
    ACCESS read-only
    STATUS mandatory
    DESCRIPTION "The total number of RIP packets sent by the router."
    ::= { rip 8 }

    ripOutDiscards OBJECT-TYPE
    SYNTAX Counter
    ACCESS read-only
    STATUS mandatory
    DESCRIPTION "The total number of RIP packets discarded because
                 of lack of buffer space."
    ::= { rip 9 }

--********************** BOOTP **********************************************

    bootp                OBJECT IDENTIFIER ::= { iprouter 7 }

    bootpIfTable OBJECT-TYPE
    SYNTAX SEQUENCE OF BootpIfEntry
    ACCESS not-accessible
    STATUS mandatory
    DESCRIPTION "The table contains BOOTP information for each IP link."
    ::= { bootp 1 }

    bootpIfEntry OBJECT-TYPE
    SYNTAX BootpIfEntry
    ACCESS not-accessible
    STATUS mandatory
    DESCRIPTION "BOOTP information for the IP link."
    INDEX { bootpIfIndex }
    ::= { bootpIfTable 1 }

    BootpIfEntry ::=
    SEQUENCE {
      bootpIfIndex
        INTEGER,
      bootpIfInRequests
        Counter,
      bootpIfInReplies
        Counter,
      bootpIfInErrors
        Counter,
      bootpIfInDiscards
        Counter,
      bootpIfOutRequests
        Counter,
      bootpIfOutReplies
        Counter,
      bootpIfOutDiscards
        Counter
    }

    bootpIfIndex OBJECT-TYPE
    SYNTAX INTEGER
    ACCESS read-only
    STATUS mandatory
    DESCRIPTION "The ifIndex of the IP link."
    ::= { bootpIfEntry 1 }

    bootpIfInRequests OBJECT-TYPE
    SYNTAX Counter
    ACCESS read-only
    STATUS mandatory
    DESCRIPTION "The number of BOOTP requests received on the link."
    ::= { bootpIfEntry 2 }

    bootpIfInReplies OBJECT-TYPE
    SYNTAX Counter
    ACCESS read-only
    STATUS mandatory
    DESCRIPTION "The number of BOOTP replies received on the link."
    ::= { bootpIfEntry 3 }

    bootpIfInErrors OBJECT-TYPE
    SYNTAX Counter
    ACCESS read-only
    STATUS mandatory
    DESCRIPTION "The number of BOOTP packets received on the link
                 which were discarded because of header errors."
    ::= { bootpIfEntry 4 }

    bootpIfInDiscards OBJECT-TYPE
    SYNTAX Counter
    ACCESS read-only
    STATUS mandatory
    DESCRIPTION "The number of BOOTP requests received on the link
                 which were discarded. This is done in the following
                 situations:
                 - The maximum value of the BOOTP hop count is exceeded.
                 - More than 3 BOOTP packets are received per second.
                 - The router does not have a route back to the assisting
                   router using the receving link."
    ::= { bootpIfEntry 5 }

    bootpIfOutRequests OBJECT-TYPE
    SYNTAX Counter
    ACCESS read-only
    STATUS mandatory
    DESCRIPTION "The number of BOOTP requests sent on the link."
    ::= { bootpIfEntry 6 }

    bootpIfOutReplies OBJECT-TYPE
    SYNTAX Counter
    ACCESS read-only
    STATUS mandatory
    DESCRIPTION "The number of BOOTP replies sent on the link."
    ::= { bootpIfEntry 7 }

    bootpIfOutDiscards OBJECT-TYPE
    SYNTAX Counter
    ACCESS read-only
    STATUS mandatory
    DESCRIPTION "The number of BOOTP requests discarded because
                 of lack of buffer space."
    ::= { bootpIfEntry 8 }


    bootpInRequests OBJECT-TYPE
    SYNTAX Counter
    ACCESS read-only
    STATUS mandatory
    DESCRIPTION "The total number of received BOOTP requests."
    ::= { bootp 2 }

    bootpInReplies OBJECT-TYPE
    SYNTAX Counter
    ACCESS read-only
    STATUS mandatory
    DESCRIPTION "The total number of received BOOTP replies."
    ::= { bootp 3 }

    bootpInErrors OBJECT-TYPE
    SYNTAX Counter
    ACCESS read-only
    STATUS mandatory
    DESCRIPTION "The total number of received BOOTP packets discarded
                 because of header errors."
    ::= { bootp 4 }

    bootpInDiscards OBJECT-TYPE
    SYNTAX Counter
    ACCESS read-only
    STATUS mandatory
    DESCRIPTION "The total number of received BOOTP requests discarded.
                 This is done in the following situations:
                 - The maximum value of the BOOTP hop count is exceeded.
                 - More than 3 BOOTP packets are received per second.
                 - The router does not have a route back to the assisting
                   router using the receiving link."
    ::= { bootp 5 }

    bootpOutRequests OBJECT-TYPE
    SYNTAX Counter
    ACCESS read-only
    STATUS mandatory
    DESCRIPTION "The total number of BOOTP requests sent by the router."
    ::= { bootp 6 }

    bootpOutReplies OBJECT-TYPE
    SYNTAX Counter
    ACCESS read-only
    STATUS mandatory
    DESCRIPTION "The total number of BOOTP replies sent to BOOTP clients."
    ::= { bootp 7 }

    bootpOutDiscards OBJECT-TYPE
    SYNTAX Counter
    ACCESS read-only
    STATUS mandatory
    DESCRIPTION "The total number of BOOTP requests discarded because
                 of lack of buffer space."
    ::= { bootp 8 }

    bootpMaxHops OBJECT-TYPE
    SYNTAX INTEGER
    ACCESS read-write
    STATUS mandatory
    DESCRIPTION "The maximum allowed value of the hop count in received
                 BOOTP requests."
    ::= { bootp 9 }


--********************** Octet counters ************************************

    octetcounters        OBJECT IDENTIFIER ::= { iprouter 8 }

    octetIfTable OBJECT-TYPE
    SYNTAX SEQUENCE OF OctetIfEntry
    ACCESS not-accessible
    STATUS mandatory
    DESCRIPTION "The table contains octet counters for each IP link."
    ::= { octetcounters 1 }

    octetIfEntry OBJECT-TYPE
    SYNTAX OctetIfEntry
    ACCESS not-accessible
    STATUS mandatory
    DESCRIPTION "Octet counter information for the IP link."
    INDEX { octetIfIndex }
    ::= { octetIfTable 1 }

    OctetIfEntry ::=
    SEQUENCE {
      octetIfIndex
        Counter,
      octetIfInTotal
        Counter,
      octetIfOutTotal
        Counter,
      octetIfInOther
        Counter,
      octetIfOutOther
        Counter,
      octetIfInFtp
        Counter,
      octetIfOutFtp
        Counter,
      octetIfInTelnet
        Counter,
      octetIfOutTelnet
        Counter,
      octetIfInSmtp
        Counter,
      octetIfOutSmtp
        Counter,
      octetIfInDns
        Counter,
      octetIfOutDns
        Counter,
      octetIfInBootp
        Counter,
      octetIfOutBootp
        Counter,
      octetIfInHttp
        Counter,
      octetIfOutHttp
        Counter,
      octetIfInSnmp
        Counter,
      octetIfOutSnmp
        Counter,
      octetIfInRip
        Counter,
      octetIfOutRip
        Counter,
      octetIfInTunnel
        Counter,
      octetIfOutTunnel
        Counter
    }

    octetIfIndex OBJECT-TYPE
    SYNTAX INTEGER
    ACCESS read-only
    STATUS mandatory
    DESCRIPTION "The ifIndex of the IP link."
    ::= { octetIfEntry 1 }

    octetIfInTotal OBJECT-TYPE
    SYNTAX Counter
    ACCESS read-only
    STATUS mandatory
    DESCRIPTION "The total number of octets received on the IP link."
    ::= { octetIfEntry 2 }

    octetIfOutTotal OBJECT-TYPE
    SYNTAX Counter
    ACCESS read-only
    STATUS mandatory
    DESCRIPTION "The total number of octets sent on the IP link."
    ::= { octetIfEntry 3 }

    octetIfInOther OBJECT-TYPE
    SYNTAX Counter
    ACCESS read-only
    STATUS mandatory
    DESCRIPTION "The number of octets received on the IP link which
                 were not classified as a specific protocol."
    ::= { octetIfEntry 4 }

    octetIfOutOther OBJECT-TYPE
    SYNTAX Counter
    ACCESS read-only
    STATUS mandatory
    DESCRIPTION "The number of octets sent on the IP link which
                 were not classified as a specific protocol."
    ::= { octetIfEntry 5 }

    octetIfInFtp OBJECT-TYPE
    SYNTAX Counter
    ACCESS read-only
    STATUS mandatory
    DESCRIPTION "The number of FTP octets received on the IP link."
    ::= { octetIfEntry 6 }

    octetIfOutFtp OBJECT-TYPE
    SYNTAX Counter
    ACCESS read-only
    STATUS mandatory
    DESCRIPTION "The number of FTP octets sent on the IP link."
    ::= { octetIfEntry 7 }

    octetIfInTelnet OBJECT-TYPE
    SYNTAX Counter
    ACCESS read-only
    STATUS mandatory
    DESCRIPTION "The number of Telnet octets received on the IP link."
    ::= { octetIfEntry 8 }

    octetIfOutTelnet OBJECT-TYPE
    SYNTAX Counter
    ACCESS read-only
    STATUS mandatory
    DESCRIPTION "The number of Telnet octets sent on the IP link."
    ::= { octetIfEntry 9 }

    octetIfInSmtp OBJECT-TYPE
    SYNTAX Counter
    ACCESS read-only
    STATUS mandatory
    DESCRIPTION "The number of SMTP octets received on the IP link."
    ::= { octetIfEntry 10 }

    octetIfOutSmtp OBJECT-TYPE
    SYNTAX Counter
    ACCESS read-only
    STATUS mandatory
    DESCRIPTION "The number of SMTP octets sent on the IP link."
    ::= { octetIfEntry 11 }

    octetIfInDns OBJECT-TYPE
    SYNTAX Counter
    ACCESS read-only
    STATUS mandatory
    DESCRIPTION "The number of DNS octets received on the IP link."
    ::= { octetIfEntry 12 }

    octetIfOutDns OBJECT-TYPE
    SYNTAX Counter
    ACCESS read-only
    STATUS mandatory
    DESCRIPTION "The number of DNS octets sent on the IP link."
    ::= { octetIfEntry 13 }

    octetIfInBootp OBJECT-TYPE
    SYNTAX Counter
    ACCESS read-only
    STATUS mandatory
    DESCRIPTION "The number of BOOTP octets received on the IP link."
    ::= { octetIfEntry 14 }

    octetIfOutBootp OBJECT-TYPE
    SYNTAX Counter
    ACCESS read-only
    STATUS mandatory
    DESCRIPTION "The number of BOOTP octets sent on the IP link."
    ::= { octetIfEntry 15 }

    octetIfInHttp OBJECT-TYPE
    SYNTAX Counter
    ACCESS read-only
    STATUS mandatory
    DESCRIPTION "The number of HTTP octets received on the IP link."
    ::= { octetIfEntry 16 }

    octetIfOutHttp OBJECT-TYPE
    SYNTAX Counter
    ACCESS read-only
    STATUS mandatory
    DESCRIPTION "The number of HTTP octets sent on the IP link."
    ::= { octetIfEntry 17 }

    octetIfInSnmp OBJECT-TYPE
    SYNTAX Counter
    ACCESS read-only
    STATUS mandatory
    DESCRIPTION "The number of SNMP octets received on the IP link."
    ::= { octetIfEntry 18 }

    octetIfOutSnmp OBJECT-TYPE
    SYNTAX Counter
    ACCESS read-only
    STATUS mandatory
    DESCRIPTION "The number of SNMP octets sent on the IP link."
    ::= { octetIfEntry 19 }

    octetIfInRip OBJECT-TYPE
    SYNTAX Counter
    ACCESS read-only
    STATUS mandatory
    DESCRIPTION "The number of RIP octets received on the IP link."
    ::= { octetIfEntry 20 }

    octetIfOutRip OBJECT-TYPE
    SYNTAX Counter
    ACCESS read-only
    STATUS mandatory
    DESCRIPTION "The number of RIP octets sent on the IP link."
    ::= { octetIfEntry 21 }

    octetIfInTunnel OBJECT-TYPE
    SYNTAX Counter
    ACCESS read-only
    STATUS mandatory
    DESCRIPTION "The number of Tunnel octets received on the IP link."
    ::= { octetIfEntry 22 }

    octetIfOutTunnel OBJECT-TYPE
    SYNTAX Counter
    ACCESS read-only
    STATUS mandatory
    DESCRIPTION "The number of Tunnel octets sent on the IP link."
    ::= { octetIfEntry 23 }

    END
