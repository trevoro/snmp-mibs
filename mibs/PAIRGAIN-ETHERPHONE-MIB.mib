-- file: pgeph.txt

PAIRGAIN-ETHERPHONE-MIB

-- Release 1.0
-- Revision 03/28/97
-- Printed 

-- Copyright 1997 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.  
--
-- It is PairGain’s intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.


DEFINITIONS ::= BEGIN

-- SECTION 1: Top Level Definitions


-- Imports

IMPORTS
        Counter                         FROM RFC1155-SMI        
        OBJECT-TYPE                     FROM RFC-1212
        pgEPhoneLocUnit, 
        pgEPhoneRemUnit                 FROM PAIRGAIN-COMMON-HD-MIB;            
--        PgUnitType                      FROM PAIRGAIN-COMMON-MIB;

-- temporary using local defined unitType instead of importing from pgmib1.txt.
-- since the SR's enumerate -type has problem during importing - 10/17 Clement

TempPgUnitType ::=
        INTEGER {
                empty(1),       -- nothing installed
                other(2),       -- none of the following
                cmu(3),         -- Campus Management Unit
                clu(4),         -- Campus Line Unit without Interface board
                clu-T1-V35(5),  -- Campus Line Unit with T1 V.35
                clu-384-V35(6), -- Campus Line Unit with T1 384
                clu-DSX(7),     -- Campus Line Unit with T1 DSX
                clu-T1-449(8),  -- Campus Line Unit with T1 RS-449
                clu-Flex(9),    -- Campus Line Unit with T1 Flex
                clu-E1-V35(10), -- Campus Line Unit with E1 V.35
                clu-E1-449(11), -- Campus Line Unit with E1 RS-449
                clu-G703(12),   -- Campus Line Unit with E1 G703 
                clu-G120(13),   -- not used 
                clu-X21(14),    -- Campus Line Unit with E1 X21
                cu-T1-V35(15),  -- Campus Unit with T1 V.35
                cu-384-V35(16), -- Campus Unit with 384 V.35
                cu-DSX(17),     -- Campus Unit with T1 DSX
                cu-T1-449(18),  -- Campus Unit with T1 RS-449
                cu-Flex(19),    -- Campus Unit with T1 Flex
                cu-E1-V35(20),  -- Campus Unit with E1 V.35
                cu-E1-449(21),  -- Campus Unit with E1 RS-449
                cu-G703(22),    -- Campus Unit with E1 G703 
                cu-G120(23),    -- not used 
                cu-X21(24),     -- Campus Unit with E1 X21
                cu-DBL(25),     -- Campus Doubler
                hmu(26),        -- Higain Management Unit
                hlu(27),        -- Higain Line Unit
                ps-AC(28),      -- AC Power Supply
                ps-DC(29),      -- 48V DC Power Supply
                clu-384-449(30),-- Campus Line Unit with 384 RS-449
                cu-384-449(31), -- Campus Unit with 384 RS-449
                clu-REX-T1(32), -- Campus Line Unit with REX T1 
                cu-REX-T1(33),  -- Campus Unit with REX T1 
                clu-REX-E1(34), -- Campus Line Unit with REX E1 
                cu-REX-E1(35),   -- Campus Unit with REX E1 
                clu-REX-384(36), -- Campus Line Unit with REX 384  
                cu-REX-384(37),   -- Campus Unit with REX 384
                clu-MM768(38), -- Campus Line Unit with Megabit modem (REX-768)
                cu-MM768(39),   -- Campus Unit with Megabit modem (REX-768)
                mm-220(40),     -- Megabit Modem Line Unit
                mm-768(41),     -- Megabit Modem 768 Desktop
                eph-220(42),    -- EtherPhone 220 with Ethernet Port
                epw-220(43),    -- EtherPhone 220 with Sync WAN port(V.35)
                eph-remote(44), -- EtherPhone Remote Unit
                eph-RT(45)      -- EtherPhone RT NID
                }

-- This type is used to specify a Unit in a PairGain chassis.

-- SECTION 2:PairGain EtherPhone Line Unit Group

-- PairGain EtherPhone Local Unit Table

pgLocUnitEpTable OBJECT-TYPE
        SYNTAX  SEQUENCE OF PgLocUnitEpEntry
        ACCESS  not-accessible
        STATUS  mandatory
        DESCRIPTION
                "The Local Unit EtherPhone table.  This table
                contains an entry for each EtherPhone/MegabitModem 220
                line unit in the chassis.
                The attributes in this table decribe parameters
                associated with each Local Line Unit."
        ::= { pgEPhoneLocUnit 1 }

pgLocUnitEpEntry OBJECT-TYPE
        SYNTAX  PgLocUnitEpEntry
        ACCESS  not-accessible
        STATUS  mandatory
        DESCRIPTION
                "Entries in the Local Unit Port Table."
        INDEX   { pgLocUnitEpIndex }
        ::= { pgLocUnitEpTable 1 }

PgLocUnitEpEntry ::= SEQUENCE {
        pgLocUnitEpIndex
                INTEGER,
        pgLocUnitEpUnitType
                TempPgUnitType,
        pgLocUnitEpHwConfig
                INTEGER,
        pgLocUnitEpXcvrType
                INTEGER,
        pgLocUnitEpAFE
                INTEGER,
        pgLocUnitEpDS0IdleCode
                INTEGER,
        pgLocUnitEpPOTSDS0Alloc
                INTEGER,
        pgLocUnitEpEthernetDS0Alloc
                INTEGER,
        pgLocUnitEpPOTSType
                INTEGER,
        pgLocUnitEpPOTSEnable1
                INTEGER,
        pgLocUnitEpPOTSEnable2
                INTEGER,
        pgLocUnitEpPOTSStatus1
                INTEGER,
        pgLocUnitEpPOTSStatus2
                INTEGER,
        pgLocUnitEpBridgeSWVer
                INTEGER,
        pgLocUnitEpERateMultiplier
                INTEGER,
        pgLocUnitEpMACAddr
                OCTET STRING,
        pgLocUnitEpSpanTreeMode
                INTEGER,
        pgLocUnitEpEncapMode
                INTEGER,
        pgLocUnitEp10BaseTLinkStatus
                INTEGER,
	pgLocUnitEp10BaseTLinkAlarmMode
		INTEGER,
        pgLocUnitEpEPortInFrames
                Counter,
        pgLocUnitEpEPortOutFrames
                Counter,
        pgLocUnitEpEPortInDiscards
                Counter,
        pgLocUnitEpEPortInErrors
                Counter,
        pgLocUnitEpDSLPortInFrames
                Counter,
        pgLocUnitEpDSLPortOutFrames
                Counter,
        pgLocUnitEpDSLPortInDiscards
                Counter,
        pgLocUnitEpDSLPortInErrors
                Counter
	
}

pgLocUnitEpIndex OBJECT-TYPE
        SYNTAX  INTEGER
        ACCESS  read-only
        STATUS  mandatory
        DESCRIPTION
                "Index of the EtherPhone Local Unit."
        ::= { pgLocUnitEpEntry 1 }

pgLocUnitEpUnitType OBJECT-TYPE
        SYNTAX  TempPgUnitType
        ACCESS  read-only
        STATUS  mandatory
        DESCRIPTION
                "The type of Unit this entry represents."
        ::= { pgLocUnitEpEntry 2 }

pgLocUnitEpHwConfig OBJECT-TYPE
        SYNTAX  INTEGER
        ACCESS  read-only
        STATUS  mandatory
        DESCRIPTION
                "Major hardware configuration of the unit."
        ::= { pgLocUnitEpEntry 3 }

pgLocUnitEpXcvrType OBJECT-TYPE
        SYNTAX  INTEGER {
                hybrid768(1),
                hybrid384(2),
                hybrid256(3),
                afe(4)
                }
        ACCESS  read-only
        STATUS  mandatory
        DESCRIPTION
                "The transceiver type of the unit."
        ::= { pgLocUnitEpEntry 4 }

pgLocUnitEpAFE OBJECT-TYPE
        SYNTAX  INTEGER
        ACCESS  read-write
        STATUS  mandatory
        DESCRIPTION
                "For variable rate(AFE) transceiver type, this 
                 object is used to set the rate."
        ::= { pgLocUnitEpEntry 5 }

pgLocUnitEpDS0IdleCode OBJECT-TYPE
        SYNTAX  INTEGER
        ACCESS  read-write
        STATUS  mandatory
        DESCRIPTION
                "Code inserts into all DS0 Channels that are not
                 assigned to either POTS line or the Ethernet port."
        ::= { pgLocUnitEpEntry 6 }

pgLocUnitEpPOTSDS0Alloc OBJECT-TYPE
        SYNTAX  INTEGER
        ACCESS  read-write
        STATUS  mandatory
        DESCRIPTION
                "Number of DS0 channels allocated to POTS line."
        ::= { pgLocUnitEpEntry 7 }

pgLocUnitEpEthernetDS0Alloc OBJECT-TYPE
        SYNTAX  INTEGER
        ACCESS  read-write
        STATUS  mandatory
        DESCRIPTION
                "Number of DS0 channels allocated to Ethernet port."
        ::= { pgLocUnitEpEntry 8 }

pgLocUnitEpPOTSType OBJECT-TYPE
        SYNTAX  INTEGER {
                noPOT(1),
                fxO1(2),
                fxS1(3),
                fxO2(4),
                fxS2(5)
                }
        ACCESS  read-only
        STATUS  mandatory
        DESCRIPTION
                "This object indicates what kind of POTS card is installed,
                 and how many POTS lines are available."
        ::= { pgLocUnitEpEntry 9 }

pgLocUnitEpPOTSEnable1 OBJECT-TYPE
        SYNTAX  INTEGER {
                disable(1),
                enable(2)
                }
        ACCESS  read-write
        STATUS  mandatory
        DESCRIPTION
                "This object enables or disables POTS 1 line."
        ::= { pgLocUnitEpEntry 10 }

pgLocUnitEpPOTSEnable2 OBJECT-TYPE
        SYNTAX  INTEGER {
                disable(1),
                enable(2)
                }
        ACCESS  read-write
        STATUS  mandatory
        DESCRIPTION
                "This object enables or disables POTS 2 line."
        ::= { pgLocUnitEpEntry 11 }

pgLocUnitEpPOTSStatus1 OBJECT-TYPE
        SYNTAX  INTEGER {
                undefined(1),
                ring(2),
                on-hook(3),
                lcfo(4),
                off-hook(5)
                }
        ACCESS  read-only
        STATUS  mandatory
        DESCRIPTION
                "This object represents the status of POTS 1 line."
        ::= { pgLocUnitEpEntry 12 }

pgLocUnitEpPOTSStatus2 OBJECT-TYPE
        SYNTAX  INTEGER {
                undefined(1),
                ring(2),
                on-hook(3),
                lcfo(4),
                off-hook(5)
                }
        ACCESS  read-only
        STATUS  mandatory
        DESCRIPTION
                "This object represents the status of POTS 2 line."
        ::= { pgLocUnitEpEntry 13 }

pgLocUnitEpBridgeSWVer OBJECT-TYPE
        SYNTAX  INTEGER 
        ACCESS  read-only
        STATUS  mandatory
        DESCRIPTION
                "This object represents the bridge's software version."
        ::= { pgLocUnitEpEntry 14 }

pgLocUnitEpERateMultiplier OBJECT-TYPE
        SYNTAX  INTEGER {
                r56(1),
                r64(2)
        }
        ACCESS  read-write
        STATUS  mandatory
        DESCRIPTION
                "This object sets the DS0 channels allocated to the
                 Ethernet port operate as 56Kbps or 64Kbps."
        ::= { pgLocUnitEpEntry 15 }

pgLocUnitEpMACAddr OBJECT-TYPE
        SYNTAX  OCTET STRING
        ACCESS  read-only
        STATUS  mandatory
        DESCRIPTION
                "This object represents the Ethernet MAC address of
                 the Ethernet port."
        ::= { pgLocUnitEpEntry 16 }

pgLocUnitEpSpanTreeMode OBJECT-TYPE
        SYNTAX  INTEGER {
                disable(1),
                enable(2)
                }
        ACCESS  read-write
        STATUS  mandatory
        DESCRIPTION
                "This object enables/disables the spanning tree mode
                 of the bridge."
        ::= { pgLocUnitEpEntry 17 }

pgLocUnitEpEncapMode OBJECT-TYPE
        SYNTAX  INTEGER {
                hdlc(1),
                ppp(2)
                }
        ACCESS  read-write
        STATUS  mandatory
        DESCRIPTION
                "This object sets the encapsulation mode to HDLS or PPP."
        ::= { pgLocUnitEpEntry 18 }

pgLocUnitEp10BaseTLinkStatus OBJECT-TYPE
        SYNTAX  INTEGER {
                link-down(1),
                link-up(2),
                other(3)
                }
        ACCESS  read-only
        STATUS  mandatory
        DESCRIPTION
                "This object represents the Ethernet 10BaseT link status."
        ::= { pgLocUnitEpEntry 19 }

pgLocUnitEp10BaseTLinkAlarmMode OBJECT-TYPE
        SYNTAX  INTEGER {
                disable(1),
                enable(2)
                }
        ACCESS  read-write
        STATUS  mandatory
        DESCRIPTION
                "This object is used to enable/disable 10BaseT link alarm."
        ::= { pgLocUnitEpEntry 20 }

pgLocUnitEpEPortInFrames OBJECT-TYPE
        SYNTAX  Counter
        ACCESS  read-only
        STATUS  mandatory
        DESCRIPTION
                "This object represents the count of received frames of
                 the Ethernet port."
        ::= { pgLocUnitEpEntry 21 }

pgLocUnitEpEPortOutFrames OBJECT-TYPE
        SYNTAX  Counter
        ACCESS  read-only
        STATUS  mandatory
        DESCRIPTION
                "This object represents the count of transmitted frames of
                 the Ethernet port."
        ::= { pgLocUnitEpEntry 22 }

pgLocUnitEpEPortInDiscards OBJECT-TYPE
        SYNTAX  Counter
        ACCESS  read-only
        STATUS  mandatory
        DESCRIPTION
                "This object represents the count of discarded frames of
                 the Ethernet port."
        ::= { pgLocUnitEpEntry 23 }

pgLocUnitEpEPortInErrors OBJECT-TYPE
        SYNTAX  Counter
        ACCESS  read-only
        STATUS  mandatory
        DESCRIPTION
                "This object represents the count of frames with errors of
                 the Ethernet port."
        ::= { pgLocUnitEpEntry 24 }

pgLocUnitEpDSLPortInFrames OBJECT-TYPE
        SYNTAX  Counter
        ACCESS  read-only
        STATUS  mandatory
        DESCRIPTION
                "This object represents the count of received frames of
                 the DSL port."
        ::= { pgLocUnitEpEntry 25 }

pgLocUnitEpDSLPortOutFrames OBJECT-TYPE
        SYNTAX  Counter
        ACCESS  read-only
        STATUS  mandatory
        DESCRIPTION
                "This object represents the count of transmitted frames of
                 the DSL port."
        ::= { pgLocUnitEpEntry 26 }

pgLocUnitEpDSLPortInDiscards OBJECT-TYPE
        SYNTAX  Counter
        ACCESS  read-only
        STATUS  mandatory
        DESCRIPTION
                "This object represents the count of discarded frames of
                 the DSL port."
        ::= { pgLocUnitEpEntry 27 }

pgLocUnitEpDSLPortInErrors OBJECT-TYPE
        SYNTAX  Counter
        ACCESS  read-only
        STATUS  mandatory
        DESCRIPTION
                "This object represents the count of frames with errors of
                 the DSL port."
        ::= { pgLocUnitEpEntry 28 }

-- SECTION 3:PairGain EtherPhone Remote Unit Group

-- PairGain EtherPhone Remote Unit Table

pgRemUnitEpTable OBJECT-TYPE
        SYNTAX  SEQUENCE OF PgRemUnitEpEntry
        ACCESS  not-accessible
        STATUS  mandatory
        DESCRIPTION
                "The Remote Unit EtherPhone table.  This table
                contains an entry for each EtherPhone/MegabitModem 220
                line unit in the chassis.
                The attributes in this table decribe parameters
                associated with each Remote Line Unit."
        ::= { pgEPhoneRemUnit 1 }

pgRemUnitEpEntry OBJECT-TYPE
        SYNTAX  PgRemUnitEpEntry
        ACCESS  not-accessible
        STATUS  mandatory
        DESCRIPTION
                "Entries in the Remote Unit Port Table."
        INDEX   { pgRemUnitEpIndex }
        ::= { pgRemUnitEpTable 1 }

PgRemUnitEpEntry ::= SEQUENCE {
        pgRemUnitEpIndex
                INTEGER,
        pgRemUnitEpUnitType
                TempPgUnitType,
        pgRemUnitEpHwConfig
                INTEGER,
        pgRemUnitEpXcvrType
                INTEGER,
        pgRemUnitEpAFE
                INTEGER,
        pgRemUnitEpDS0IdleCode
                INTEGER,
        pgRemUnitEpPOTSDS0Alloc
                INTEGER,
        pgRemUnitEpEthernetDS0Alloc
                INTEGER,
        pgRemUnitEpPOTSType
                INTEGER,
        pgRemUnitEpPOTSEnable1
                INTEGER,
        pgRemUnitEpPOTSEnable2
                INTEGER,
        pgRemUnitEpPOTSStatus1
                INTEGER,
        pgRemUnitEpPOTSStatus2
                INTEGER,
        pgRemUnitEpBridgeSWVer
                INTEGER,
        pgRemUnitEpERateMultiplier
                INTEGER,
        pgRemUnitEpMACAddr
                OCTET STRING,
        pgRemUnitEpSpanTreeMode
                INTEGER,
        pgRemUnitEpEncapMode
                INTEGER,
        pgRemUnitEp10BaseTLinkStatus
                INTEGER,
	pgRemUnitEp10BaseTLinkAlarmMode
		INTEGER,
        pgRemUnitEpEPortInFrames
                Counter,
        pgRemUnitEpEPortOutFrames
                Counter,
        pgRemUnitEpEPortInDiscards
                Counter,
        pgRemUnitEpEPortInErrors
                Counter,
        pgRemUnitEpDSLPortInFrames
                Counter,
        pgRemUnitEpDSLPortOutFrames
                Counter,
        pgRemUnitEpDSLPortInDiscards
                Counter,
        pgRemUnitEpDSLPortInErrors
                Counter
}

pgRemUnitEpIndex OBJECT-TYPE
        SYNTAX  INTEGER
        ACCESS  read-only
        STATUS  mandatory
        DESCRIPTION
                "Index of the EtherPhone Remote Unit."
        ::= { pgRemUnitEpEntry 1 }

pgRemUnitEpUnitType OBJECT-TYPE
        SYNTAX  TempPgUnitType
        ACCESS  read-only
        STATUS  mandatory
        DESCRIPTION
                "The type of Unit this entry represents."
        ::= { pgRemUnitEpEntry 2 }

pgRemUnitEpHwConfig OBJECT-TYPE
        SYNTAX  INTEGER
        ACCESS  read-only
        STATUS  mandatory
        DESCRIPTION
                "Major hardware configuration of the unit."
        ::= { pgRemUnitEpEntry 3 }

pgRemUnitEpXcvrType OBJECT-TYPE
        SYNTAX  INTEGER {
                hybrid768(1),
                hybrid384(2),
                hybrid256(3),
                afe(4)
                }
        ACCESS  read-only
        STATUS  mandatory
        DESCRIPTION
                "The transceiver type of the unit."
        ::= { pgRemUnitEpEntry 4 }

pgRemUnitEpAFE OBJECT-TYPE
        SYNTAX  INTEGER
        ACCESS  read-write
        STATUS  mandatory
        DESCRIPTION
                "For variable rate(AFE) transceiver type, this 
                 object is used to set the rate."
        ::= { pgRemUnitEpEntry 5 }

pgRemUnitEpDS0IdleCode OBJECT-TYPE
        SYNTAX  INTEGER
        ACCESS  read-write
        STATUS  mandatory
        DESCRIPTION
                "Code inserts into all DS0 Channels that are not
                 assigned to either POTS line or the Ethernet port."
        ::= { pgRemUnitEpEntry 6 }

pgRemUnitEpPOTSDS0Alloc OBJECT-TYPE
        SYNTAX  INTEGER
        ACCESS  read-write
        STATUS  mandatory
        DESCRIPTION
                "Number of DS0 channels allocated to POTS line."
        ::= { pgRemUnitEpEntry 7 }

pgRemUnitEpEthernetDS0Alloc OBJECT-TYPE
        SYNTAX  INTEGER
        ACCESS  read-write
        STATUS  mandatory
        DESCRIPTION
                "Number of DS0 channels allocated to Ethernet port."
        ::= { pgRemUnitEpEntry 8 }

pgRemUnitEpPOTSType OBJECT-TYPE
        SYNTAX  INTEGER {
                noPOT(1),
                fxO1(2),
                fxS1(3),
                fxO2(4),
                fxS2(5)
                }
        ACCESS  read-only
        STATUS  mandatory
        DESCRIPTION
                "This object indicates what kind of POTS card is installed,
                 and how many POTS lines are available."
        ::= { pgRemUnitEpEntry 9 }

pgRemUnitEpPOTSEnable1 OBJECT-TYPE
        SYNTAX  INTEGER {
                disable(1),
                enable(2)
                }
        ACCESS  read-write
        STATUS  mandatory
        DESCRIPTION
                "This object enables or disables POTS 1 line."
        ::= { pgRemUnitEpEntry 10 }

pgRemUnitEpPOTSEnable2 OBJECT-TYPE
        SYNTAX  INTEGER {
                disable(1),
                enable(2)
                }
        ACCESS  read-write
        STATUS  mandatory
        DESCRIPTION
                "This object enables or disables POTS 2 line."
        ::= { pgRemUnitEpEntry 11 }

pgRemUnitEpPOTSStatus1 OBJECT-TYPE
        SYNTAX  INTEGER {
                undefined(1),
                ring(2),
                on-hook(3),
                lcfo(4),
                off-hook(5)
                }
        ACCESS  read-only
        STATUS  mandatory
        DESCRIPTION
                "This object represents the status of POTS 1 line."
        ::= { pgRemUnitEpEntry 12 }

pgRemUnitEpPOTSStatus2 OBJECT-TYPE
        SYNTAX  INTEGER {
                undefined(1),
                ring(2),
                on-hook(3),
                lcfo(4),
                off-hook(5)
                }
        ACCESS  read-only
        STATUS  mandatory
        DESCRIPTION
                "This object represents the status of POTS 2 line."
        ::= { pgRemUnitEpEntry 13 }

pgRemUnitEpBridgeSWVer OBJECT-TYPE
        SYNTAX  INTEGER 
        ACCESS  read-only
        STATUS  mandatory
        DESCRIPTION
                "This object represents the bridge's software version."
        ::= { pgRemUnitEpEntry 14 }

pgRemUnitEpERateMultiplier OBJECT-TYPE
        SYNTAX  INTEGER {
                r56(1),
                r64(2)
        }
        ACCESS  read-write
        STATUS  mandatory
        DESCRIPTION
                "This object sets the DS0 channels allocated to the
                 Ethernet port operate as 56Kbps or 64Kbps."
        ::= { pgRemUnitEpEntry 15 }

pgRemUnitEpMACAddr OBJECT-TYPE
        SYNTAX  OCTET STRING
        ACCESS  read-only
        STATUS  mandatory
        DESCRIPTION
                "This object represents the Ethernet MAC address of
                 the Ethernet port."
        ::= { pgRemUnitEpEntry 16 }

pgRemUnitEpSpanTreeMode OBJECT-TYPE
        SYNTAX  INTEGER {
                disable(1),
                enable(2)
                }
        ACCESS  read-write
        STATUS  mandatory
        DESCRIPTION
                "This object enables/disables the spanning tree mode
                 of the bridge."
        ::= { pgRemUnitEpEntry 17 }

pgRemUnitEpEncapMode OBJECT-TYPE
        SYNTAX  INTEGER {
                hdlc(1),
                ppp(2)
                }
        ACCESS  read-write
        STATUS  mandatory
        DESCRIPTION
                "This object sets the encapsulation mode to HDLS or PPP."
        ::= { pgRemUnitEpEntry 18 }

pgRemUnitEp10BaseTLinkStatus OBJECT-TYPE
        SYNTAX  INTEGER {
                link-down(1),
                link-up(2),
                other(3)
                }
        ACCESS  read-only
        STATUS  mandatory
        DESCRIPTION
                "This object represents the Ethernet 10BaseT link status."
        ::= { pgRemUnitEpEntry 19 }

pgRemUnitEp10BaseTLinkAlarmMode OBJECT-TYPE
        SYNTAX  INTEGER {
                disable(1),
                enable(2)
                }
        ACCESS  read-write
        STATUS  mandatory
        DESCRIPTION
                "This object is used to enable/disable the 10BaseT link alarm."
        ::= { pgRemUnitEpEntry 20 }

pgRemUnitEpEPortInFrames OBJECT-TYPE
        SYNTAX  Counter
        ACCESS  read-only
        STATUS  mandatory
        DESCRIPTION
                "This object represents the count of received frames of
                 the Ethernet port."
        ::= { pgRemUnitEpEntry 21 }

pgRemUnitEpEPortOutFrames OBJECT-TYPE
        SYNTAX  Counter
        ACCESS  read-only
        STATUS  mandatory
        DESCRIPTION
                "This object represents the count of transmitted frames of
                 the Ethernet port."
        ::= { pgRemUnitEpEntry 22 }

pgRemUnitEpEPortInDiscards OBJECT-TYPE
        SYNTAX  Counter
        ACCESS  read-only
        STATUS  mandatory
        DESCRIPTION
                "This object represents the count of discarded frames of
                 the Ethernet port."
        ::= { pgRemUnitEpEntry 23 }

pgRemUnitEpEPortInErrors OBJECT-TYPE
        SYNTAX  Counter
        ACCESS  read-only
        STATUS  mandatory
        DESCRIPTION
                "This object represents the count of frames with errors of
                 the Ethernet port."
        ::= { pgRemUnitEpEntry 24 }

pgRemUnitEpDSLPortInFrames OBJECT-TYPE
        SYNTAX  Counter
        ACCESS  read-only
        STATUS  mandatory
        DESCRIPTION
                "This object represents the count of received frames of
                 the DSL port."
        ::= { pgRemUnitEpEntry 25 }

pgRemUnitEpDSLPortOutFrames OBJECT-TYPE
        SYNTAX  Counter
        ACCESS  read-only
        STATUS  mandatory
        DESCRIPTION
                "This object represents the count of transmitted frames of
                 the DSL port."
        ::= { pgRemUnitEpEntry 26 }

pgRemUnitEpDSLPortInDiscards OBJECT-TYPE
        SYNTAX  Counter
        ACCESS  read-only
        STATUS  mandatory
        DESCRIPTION
                "This object represents the count of discarded frames of
                 the DSL port."
        ::= { pgRemUnitEpEntry 27 }

pgRemUnitEpDSLPortInErrors OBJECT-TYPE
        SYNTAX  Counter
        ACCESS  read-only
        STATUS  mandatory
        DESCRIPTION
                "This object represents the count of frames with errors of
                 the DSL port."
        ::= { pgRemUnitEpEntry 28 }

END
