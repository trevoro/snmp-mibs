--  Copyright (C) 1996, 1997, 1998, 1999 Alcatel Internetworking, Inc., all rights reserved.
--
--           Xylan Private Network-Network Interface MIB ASN.1 Specification
--
-- File:        pnni.mib
--
-- Purpose:     Specifies Xylan's PNNI MIB definitions for the Omnicell
--		platform.
--
-- Conformance: Abstracted from the Forum PNNI MIB, repositioned under the Xylan
--                   MIB Tree, and realigned for SNMP V1.
--
-- Background:  Currently in the IETF, work is ongoing for SNMP V2 in the form
--              of RFCs numbered in the 19xx series. An obsolete set exists in
--              the RFC 14xx series which ATMForum PNNI v1.0 references. 
--
--              Xylan has translated the Forum PNNI Mib spec to a SNMP V1 
--		compatible MIB and incorporated it under its tree. 
--
--              History
--              =======
--                2/18/96 Burt Cyr (Bpc)    Created 
--                3/ 1/96 bpc               Re-aligned from Forum Letter Ballot.
--               11/27/96 Paramesh Kailasam (Changed Unsigned32 to Gauge)
--                8/10/98 BPC               Added adjacency table
--

XPNNI-MIB DEFINITIONS ::= BEGIN
 
IMPORTS
    DisplayString, ifIndex			FROM RFC1213-MIB
    OBJECT-TYPE 				FROM RFC-1212
    Gauge, Counter				FROM RFC1155-SMI
--    TimeStamp, RowStatus 			FROM SNMPv2-TC
--    Gauge32, Integer32, Counter32		FROM SNMPv2-SMI
    xylanPnni					FROM XYLAN-BASE-MIB;


    pnnixMIB OBJECT IDENTIFIER ::= { xylanPnni 1 }

    pnnixMIBObjects OBJECT IDENTIFIER ::= { pnnixMIB 1 }

    -- Unsigned32 ::= Gauge32

    PnnixAtmAddr ::= OCTET STRING (SIZE(0|20))

    PnnixNodeIndex ::= INTEGER (0..65535)

    InterfaceIndex ::= INTEGER

    TruthValue ::= INTEGER { true (1), false (2) }

    -- The value of this object identifies the row in the 
    -- atmTrafficDescrParamTable.  (which we dont support anyway); 
    -- used to be IMPORTED from ATM-MIB
    -- We do (Paramesh)
    
    AtmpTrafficDescrParamIndex ::= INTEGER
 
    PnnixNodeId ::= OCTET STRING (SIZE(22))
 
    PnnixPortId ::= Gauge
 
    PnnixAggrToken ::= Gauge
 
    PnnixPeerGroupId ::= OCTET STRING (SIZE(14))
 
    PnnixLevel ::= INTEGER (0..104)

    PnnixSvccRccIndex ::= INTEGER
 
    AtmAddrPrefix ::= OCTET STRING (SIZE(19))
 
    PnnixPrefixLength ::= INTEGER (0..152)
 
    PnnixMetricsTag ::= INTEGER (0..2147483647)
 
    ServiceCategory ::= INTEGER { other(1),
                                cbr(2),
                                rtVbr(3),
                                nrtVbr(4),
                                abr(5),
                                ubr(6) }

    ClpType ::= INTEGER { clpEqual0(1), clpEqual0Or1(2) }

    TnsType ::= INTEGER { nationalNetworkIdentification(2),
                                other(8) }
 
    TnsPlan ::= INTEGER { carrierIdentificationCode(1),
                                other(16) }
 
    PnnixVersion ::= INTEGER { unsupported(1), version1point0(2) }

    PnnixHelloState ::= INTEGER {
                                notApplicable(1),
                                down(2),
                                attempt(3),
                                oneWayInside(4),
                                twoWayInside(5),
                                oneWayOutside(6),
                                twoWayOutside(7),
                                commonOutside(8)
                                }

-- the base group

pnnixBaseGroup OBJECT IDENTIFIER ::= { pnnixMIBObjects 1 }

pnnixHighestVersion OBJECT-TYPE                           
        SYNTAX        PnnixVersion
        ACCESS        read-only
        STATUS        mandatory
        DESCRIPTION
            "The highest version of the PNNI protocol that the
             software in this switching system is capable of executing."
--      REFERENCE "ATM Forum PNNI 1.0 Section 5.6.1"
        ::= { pnnixBaseGroup 1 }


pnnixLowestVersion OBJECT-TYPE
        SYNTAX        PnnixVersion
        ACCESS        read-only
        STATUS        mandatory
        DESCRIPTION
            "The lowest version of the PNNI Protocol that the
             software in this switching system is capable of executing."
--      REFERENCE "ATM Forum PNNI 1.0 Section 5.6.1"
        ::= { pnnixBaseGroup 2 }
 
pnnixDtlCountOriginator OBJECT-TYPE
        SYNTAX        Counter
        ACCESS        read-only
        STATUS        mandatory
        DESCRIPTION
            "The total number of DTL stacks that this switching system
             has originated as the DTLOriginator and placed into
             signalling messages. This includes the initial DTL stacks
             computed by this system as well as any alternate route
             (second, third choice etc.) DTL stacks computed by this
             switching system in response to crankbacks."
        ::= { pnnixBaseGroup 3 }
 
pnnixDtlCountBorder OBJECT-TYPE
        SYNTAX        Counter
        ACCESS        read-only
        STATUS        mandatory
        DESCRIPTION
            "The number of partial DTL stacks that this switching system
             has added into signalling messages as an entry border node.
             This includes the initial partial DTL stacks computed by
             this system as well as any alternate route (second, third
             choice etc.) partial DTL stacks computed by this switching
             system in response to crankbacks."
        ::= { pnnixBaseGroup 4 }
 
pnnixCrankbackCountOriginator OBJECT-TYPE
        SYNTAX        Counter
        ACCESS        read-only
        STATUS        mandatory
        DESCRIPTION
            "The count of the total number of connection setup messages
             including DTL stacks originated by this switching system
             that have cranked back to this switching system at all
             levels of the hierarchy."
        ::= { pnnixBaseGroup 5 }
 
pnnixCrankbackCountBorder OBJECT-TYPE
        SYNTAX        Counter
        ACCESS        read-only
        STATUS        mandatory
        DESCRIPTION
            "The count of the total number of connection setup messages
             including DTLs added by this switching system as an entry
             border node that have cranked back to this switching system
             at all levels of the hierarchy. This count does not include
             Crankbacks for which this switching system was not the
             crankback destination, only those crankbacks that were
             directed to this switching system are counted here."
        ::= { pnnixBaseGroup 6 }
 
pnnixAltRouteCountOriginator OBJECT-TYPE
        SYNTAX        Counter
        ACCESS        read-only
        STATUS        mandatory
        DESCRIPTION
            "The total number of alternate DTL stacks that this
             switching system has computed and placed into
             signalling messages as the DTLOriginator."
        ::= { pnnixBaseGroup 7 }
 
pnnixAltRouteCountBorder OBJECT-TYPE
        SYNTAX        Counter
        ACCESS        read-only
        STATUS        mandatory
        DESCRIPTION
            "The total number of alternate partial DTL stacks that this
             switching system has computed and placed into signalling
             messages as an entry border node."
        ::= { pnnixBaseGroup 8 }
 
pnnixRouteFailCountOriginator OBJECT-TYPE
        SYNTAX        Counter
        ACCESS        read-only
        STATUS        mandatory
        DESCRIPTION
            "The total number of times where the switching system failed
             to compute a viable DTL stack as the DTLOriginator for some
             call.  It indicates the number of times a call was cleared
             from this switching system due to originator routing
             failure."
        ::= { pnnixBaseGroup 9 }
 
pnnixRouteFailCountBorder OBJECT-TYPE
        SYNTAX        Counter
        ACCESS        read-only
        STATUS        mandatory
        DESCRIPTION
            "The total number of times where the switching system failed
             to compute a viable partial DTL stack as an entry border
             node for some call.  It indicates the number of times a
             call was either cleared or cranked back from this switching
             system due to border routing failure."
        ::= { pnnixBaseGroup 10 }
 
pnnixRouteFailUnreachableOriginator OBJECT-TYPE
        SYNTAX        Counter
        ACCESS        read-only
        STATUS        mandatory
        DESCRIPTION
            "The total number of times where the switching system failed
             to compute a viable DTL stack as the DTLOriginator because
             the destination was unreachable, i.e., those calls that are
             cleared with cause #2 `specified transit network
             unreachable' or cause #3 `destination unreachable' in the
             cause IE."
        ::= { pnnixBaseGroup 11 }
 
pnnixRouteFailUnreachableBorder OBJECT-TYPE
        SYNTAX        Counter
        ACCESS        read-only
        STATUS        mandatory
        DESCRIPTION
            "The total number of times where the switching system failed
             to compute a viable partial DTL stack as an entry border
             node because the target of the path calculation was
             unreachable, i.e., those calls that are cleared or cranked
             back with cause #2 `specified transit network unreachable'
             or cause #3 `destination unreachable' in the cause IE."
        ::= { pnnixBaseGroup 12 }
 
 
-- node table
 
pnnixNodeTable OBJECT-TYPE
        SYNTAX        SEQUENCE OF PnnixNodeEntry
        ACCESS        not-accessible
	STATUS	mandatory
        DESCRIPTION
            "The pnnixNodeTable collects attributes that affect the
             operation of a PNNI logical node.
 
             There is a single row in this table for each PNNI peer
             group that the managed system is expected or eligible
             to become a member of."
--      REFERENCE "ATM Forum PNNI 1.0 Annex F"
        ::= { pnnixMIBObjects 2 }
 
pnnixNodeEntry OBJECT-TYPE
        SYNTAX        PnnixNodeEntry
        ACCESS    not-accessible
	STATUS	mandatory
        DESCRIPTION
            "An entry in the table, containing information about a PNNI
             logical node in this switching system."
--      REFERENCE "ATM Forum PNNI 1.0 Annex F"
        INDEX         { pnnixNodeIndex }
        ::= { pnnixNodeTable 1 }
 
PnnixNodeEntry ::=
        SEQUENCE {
                pnnixNodeIndex           	PnnixNodeIndex,
                pnnixNodeLevel           	PnnixLevel,
                pnnixNodeId              	PnnixNodeId,
                pnnixNodeLowest          	TruthValue,
                pnnixNodeAdminStatus     	INTEGER,
                pnnixNodeOperStatus      	INTEGER,
                pnnixNodeDomainName      	DisplayString,
                pnnixNodeAtmAddress      	PnnixAtmAddr,
                pnnixNodePeerGroupId     	PnnixPeerGroupId,
                pnnixNodeRestrictedTransit       TruthValue,
                pnnixNodeComplexRep      	TruthValue,
                pnnixNodeRestrictedBranching     TruthValue,
                pnnixNodeDatabaseOverload        TruthValue,
                pnnixNodePtses           	Gauge,
                pnnixNodeRowStatus       	INTEGER
                }

pnnixNodeIndex OBJECT-TYPE
        SYNTAX        PnnixNodeIndex
	ACCESS    not-accessible
	STATUS	mandatory
        DESCRIPTION
            "A value assigned to a node in this switching system that
             uniquely identifies it in the MIB."
        ::= { pnnixNodeEntry 1 }
 
pnnixNodeLevel OBJECT-TYPE
        SYNTAX        PnnixLevel
	ACCESS	read-write
	STATUS	mandatory
        DESCRIPTION
            "The level of PNNI hierarchy at which this node exists. This
             attribute is used to determine the default node ID and the
             default peer group ID for this node. This object may only
             be written when pnnixNodeAdminStatus has the value down."
--      REFERENCE "ATM Forum PNNI 1.0 Section 5.3.1, Annex F"
        --DEFVAL { 96 }
        ::= { pnnixNodeEntry 2 }
 
pnnixNodeId OBJECT-TYPE
        SYNTAX        PnnixNodeId
	ACCESS	read-write
	STATUS	mandatory
        DESCRIPTION
            "The value the switching system is using to represent
             itself as this node. This object may only be written when
             pnnixNodeAdminStatus has the value down.
 
             If pnnixNodeLowest is true, then the default node ID takes
             the form defined in Section 5.3.3 for lowest level nodes,
             with the first octet equal to pnnixNodeLevel, the second
             octet equal to 160, and the last 20 octets equal to
             pnnixNodeAtmAddress.
 
             If pnnixNodeLowest is false, then the default
             node ID takes the form defined in Section 5.3.3 for logical
             group nodes, with the first octet equal to pnnixNodeLevel,
             the next fourteen octets equal to the value of
             pnnixNodePeerGroupId for the child node whose election as
             PGL causes this LGN to be instantiated, the next six octets
             equal to the ESI of pnnixNodeAtmAddress, and the last octet
             equal to zero."
--      REFERENCE "ATM Forum PNNI 1.0 Section 5.3.1, Annex F"
        ::= { pnnixNodeEntry 3 }
 
pnnixNodeLowest OBJECT-TYPE
        SYNTAX        TruthValue
	ACCESS	read-write
	STATUS	mandatory
        DESCRIPTION
            "Indicates whether this node acts as a lowest level node or
             whether this node is a logical group node that becomes
             active when one of the other nodes in this switching system
             becomes a peer group leader.  The value 'false' must not be
             used with nodes that are not PGL/LGN capable.

             This object may only be
             written when pnnixNodeAdminStatus has the value down."
        --DEFVAL { true }
        ::= { pnnixNodeEntry 4 }
 
pnnixNodeAdminStatus OBJECT-TYPE
        SYNTAX        INTEGER { up(1), down(2) }
	ACCESS	read-write
	STATUS	mandatory
        DESCRIPTION
            "Indicates whether the administrative status of the node is
             up (the node is allowed to become active) or down (the node
             is forced to be inactive).
 
             When pnnixNodeAdminStatus is down, then pnnixNodeOperStatus
             must also be down."
        --DEFVAL { up }
        ::= { pnnixNodeEntry 5 }
 
pnnixNodeOperStatus OBJECT-TYPE
        SYNTAX        INTEGER { up(1), down(2) }
	ACCESS    read-only
	STATUS	mandatory
        DESCRIPTION
            "Indicates whether the node is active or whether the node
             has yet to become operational.  When the value is down, all
             state has been cleared from the node and the node is not
             communicating with any of its neighbor nodes."
        ::= { pnnixNodeEntry 6 }
 
pnnixNodeDomainName OBJECT-TYPE
        SYNTAX        DisplayString
	ACCESS	read-write
	STATUS	mandatory
        DESCRIPTION
            "The name of the PNNI routing
             domain in which this node participates.  All lowest-level
             PNNI nodes with the same pnnixNodeDomainName are presumed to
             be connected."
        --DEFVAL { "" }
        ::= { pnnixNodeEntry 7 }
 
pnnixNodeAtmAddress OBJECT-TYPE
        SYNTAX        PnnixAtmAddr
	ACCESS	read-write
	STATUS	mandatory
        DESCRIPTION
            "This node's ATM End System Address.  Remote systems wishing
             to exchange PNNI protocol packets with this node should
             direct packets or calls to this address.

             This attribute may only be written when pnnixNodeAdminStatus
             has the value down."
--      REFERENCE "ATM Forum PNNI 1.0 Section 5.2.2"
        ::= { pnnixNodeEntry 8 }
 
pnnixNodePeerGroupId OBJECT-TYPE
        SYNTAX        PnnixPeerGroupId
	ACCESS	read-write
	STATUS	mandatory
        DESCRIPTION
            "The Peer Group Identifier of the peer group that the given
             node is to become a member of.
 
             The default value of this attribute has the first octet
             equal to pnnixNodeLevel, the next pnnixNodeLevel bits equal
             to the pnnixNodeLevel bits starting from the third octet of
             pnnixNodeId, and the remainder padded with zeros.
 
             This object may only be written when pnnixNodeAdminStatus
             has the value down."
--      REFERENCE "ATM Forum PNNI 1.0 Section 5.3.2. Annex F"
        ::= { pnnixNodeEntry 9 }
 
pnnixNodeRestrictedTransit OBJECT-TYPE
        SYNTAX        TruthValue
	ACCESS	read-write
	STATUS	mandatory
        DESCRIPTION
            "Specifies whether the node is restricted to not allowing
             support of SVCs transiting this node.  This attribute
             determines the setting of the restricted transit bit in the
             nodal information group originated by this node."
--      REFERENCE "ATM Forum PNNI 1.0 Section 5.8.1.2.3"
        --DEFVAL { false }
        ::= { pnnixNodeEntry 10 }
 
pnnixNodeComplexRep OBJECT-TYPE
        SYNTAX        TruthValue
	ACCESS	read-write
	STATUS	mandatory
        DESCRIPTION
            "Specifies whether this node uses the complex node
             representation.  A value of `true' indicates that the
             complex node representation is used, whereas a value of
             `false' indicates that the simple node representation is
             used.  This attribute determines the setting of the nodal
             representation bit in the nodal information group
             originated by this node."
--      REFERENCE "ATM Forum PNNI 1.0 Section 5.8.1.2.3"
        ::= { pnnixNodeEntry 11 }

pnnixNodeRestrictedBranching  OBJECT-TYPE
        SYNTAX        TruthValue
	ACCESS    read-only
	STATUS	mandatory
        DESCRIPTION
            "Indicates whether the node is able to support additional
             point-to-multipoint branches.  A value of 'false' indicates
             that additional branches can be supported, and a value of
             'true' indicates that additional branches cannot be
             supported.  This attribute reflects the setting of the
             restricted branching bit in the nodal information group
             originated by this node."
--      REFERENCE "ATM Forum PNNI 1.0 Section 5.8.1.2.3"
        ::= { pnnixNodeEntry 12}

pnnixNodeDatabaseOverload OBJECT-TYPE
        SYNTAX        TruthValue
	ACCESS    read-only
	STATUS	mandatory
        DESCRIPTION
            "Specifies whether the node is currently operating in
             topology database overload state.  This attribute has the
             same value as the Non-transit for PGL Election bit in the
             nodal information group originated by this node."
--      REFERENCE "ATM Forum PNNI 1.0 Section 5.8.1.2.3"
        ::= { pnnixNodeEntry 13 }
 
pnnixNodePtses OBJECT-TYPE
        SYNTAX        Gauge
	ACCESS    read-only
	STATUS	mandatory
        DESCRIPTION
            "Gauges the total number of PTSEs currently in this
             node's topology database(s)."
        ::= { pnnixNodeEntry 14 }
 
pnnixNodeRowStatus OBJECT-TYPE
        SYNTAX        INTEGER {
								create (1),
								modify (2),
								delete (3),
								active (4),
								notActive (5)
							  }
	ACCESS	read-write
	STATUS	mandatory
        DESCRIPTION
            "To create, delete, activate and de-activate a Node."
        ::= { pnnixNodeEntry 15 }


-- PGL election table
 
pnnixNodePglTable OBJECT-TYPE
        SYNTAX        SEQUENCE OF PnnixNodePglEntry
	ACCESS    not-accessible
	STATUS	mandatory
        DESCRIPTION
            "Peer group leader election information for a PNNI node in
             this switching system."
--      REFERENCE "ATM Forum PNNI 1.0 Section 5.10.1"
        ::= { pnnixMIBObjects 3 }
 
pnnixNodePglEntry OBJECT-TYPE
        SYNTAX        PnnixNodePglEntry
	ACCESS    not-accessible
	STATUS	mandatory
        DESCRIPTION
            "An entry in the table, containing PGL election information
             of a PNNI logical node in this switching system."
--      REFERENCE "ATM Forum PNNI 1.0 Section 5.10.1"
        INDEX { pnnixNodeIndex }
        ::= { pnnixNodePglTable 1 }
 
PnnixNodePglEntry ::=
        SEQUENCE {
                pnnixNodePglLeadershipPriority   INTEGER,
                pnnixNodeCfgParentNodeIndex      PnnixNodeIndex,
                pnnixNodePglInitTime             INTEGER,
                pnnixNodePglOverrideDelay        INTEGER,
                pnnixNodePglReelectTime          INTEGER,
                pnnixNodePglState                INTEGER,
                pnnixNodePreferredPgl            PnnixNodeId,
                pnnixNodePeerGroupLeader         PnnixNodeId,
                pnnixNodePglTimeStamp            DisplayString,
                pnnixNodeActiveParentNodeId      PnnixNodeId
                }
 
pnnixNodePglLeadershipPriority OBJECT-TYPE
        SYNTAX        INTEGER (0..205)
	ACCESS	read-write
	STATUS	mandatory
        DESCRIPTION
            "The Leadership priority value this node should advertise in
             its nodal information group for the given peer group.  Only
             the value zero can be used with nodes that are not PGL/LGN
             capable.  If there is no configured parent node index or no
             corresponding entry in the pnnixNodeTable, then the
             advertised leadership priority is zero regardless of this
             value."
--      REFERENCE "ATM Forum PNNI 1.0 Section 5.10.1.2"
        --DEFVAL { 0 }
        ::= { pnnixNodePglEntry 1 }
 
pnnixNodeCfgParentNodeIndex OBJECT-TYPE
        SYNTAX        PnnixNodeIndex
	ACCESS	read-write
	STATUS	mandatory
        DESCRIPTION
            "The local node index used to identify the node that will
             represent this peer group at the next higher level of
             hierarchy, if this node becomes peer group leader.  The
             value 0 indicates that there is no parent node."
--      REFERENCE "ATM Forum PNNI 1.0 Annex F"
        --DEFVAL { 0 }
        ::= { pnnixNodePglEntry 2 }
 
pnnixNodePglInitTime OBJECT-TYPE
        SYNTAX        INTEGER
--      UNITS         "seconds"
	ACCESS	read-write
	STATUS	mandatory
        DESCRIPTION
            "The amount of time in seconds this node will delay
             advertising its choice of preferred PGL after having
             initialized operation and reached the full state with at
             least one neighbor in the peer group."
        --DEFVAL  { 15 }
--      REFERENCE "ATM Forum PNNI 1.0 Annex G PGLInitTime"
        ::= { pnnixNodePglEntry 3 }
 
pnnixNodePglOverrideDelay OBJECT-TYPE
        SYNTAX        INTEGER
--	UNITS         "seconds"
	ACCESS	read-write
	STATUS	mandatory
        DESCRIPTION
            "The amount of time in seconds a node will wait for itself
             to be declared the preferred PGL by unanimous agreement
             among its peers.  In the absence of unanimous agreement
             this will be the amount of time that will pass before this
             node considers a two thirds majority as sufficient
             agreement to declare itself peer group leader, abandoning
             the attempt to get unanimous agreement."
--      REFERENCE "ATM Forum PNNI 1.0 Annex G OverrideDelay"
        --DEFVAL  { 30 }
        ::= { pnnixNodePglEntry 4 }
 
pnnixNodePglReelectTime OBJECT-TYPE
        SYNTAX        INTEGER
--	UNITS         "seconds"
	ACCESS	read-write
	STATUS	mandatory
        DESCRIPTION
            "The amount of time in seconds after losing connectivity to
             the current peer group leader, that this node will wait
             before re-starting the process of electing a new peer group
             leader."
--      REFERENCE "ATM Forum PNNI 1.0 Annex G ReElectionInterval"
        --DEFVAL  { 15 }
        ::= { pnnixNodePglEntry 5 }
 
pnnixNodePglState OBJECT-TYPE
        SYNTAX        INTEGER {
                                starting(1),
                                awaiting(2),
                                awaitingFull(3),
                                initialDelay(4),
                                calculating(5),
                                awaitUnanimity(6),
                                operPgl(7),
                                operNotPgl(8),
                                hungElection(9),
                                awaitReElection(10)
                                }
	ACCESS    read-only
	STATUS	mandatory
        DESCRIPTION
            "Indicates the state that this node is in with respect to
             the Peer Group Leader election that takes place in the
             node's peer group. The values are enumerated in the Peer
             Group Leader State Machine."
--      REFERENCE "ATM Forum PNNI 1.0 5.10.1.1.2"
        ::= { pnnixNodePglEntry 6 }
 
pnnixNodePreferredPgl OBJECT-TYPE
        SYNTAX        PnnixNodeId
	ACCESS    read-only
	STATUS	mandatory
        DESCRIPTION
            "The Node ID of
             the node which the local node believes should be or become
             the peer group leader.  This is also the value the local
             node is currently advertising in the `Preferred Peer Group
             Leader Node ID' field of its nodal information group within
             the given peer group.  If a Preferred PGL has not been
             chosen, this attribute's value is set to (all) zero(s)."
--      REFERENCE "ATM Forum PNNI 1.0 5.10.1.1.6"
        ::= { pnnixNodePglEntry 7 }
 
pnnixNodePeerGroupLeader OBJECT-TYPE
        SYNTAX        PnnixNodeId
	ACCESS    read-only
	STATUS	mandatory
        DESCRIPTION
            "The Node Identifier of the node which is currently
             operating as peer group leader of the peer group this node
             belongs to. If a PGL has not been elected, this attribute's
             value is set to (all) zero(s)."
        ::= { pnnixNodePglEntry 8 }
 
pnnixNodePglTimeStamp OBJECT-TYPE
        SYNTAX        DisplayString
	ACCESS    read-only
	STATUS	mandatory
        DESCRIPTION
            "The time at which the current Peer Group Leader established
             itself."
        ::= { pnnixNodePglEntry 9 }
 
pnnixNodeActiveParentNodeId OBJECT-TYPE
        SYNTAX        PnnixNodeId
	ACCESS    read-only
	STATUS	mandatory
        DESCRIPTION
            "The Node Identifier value being used by the Peer Group
             Leader to represent this peer group at the next higher
             level of the hierarchy. If this node is at the highest
             level of the hierarchy or if no PGL has yet been elected
             the PNNI Protocol Entity sets the value of this attribute
             to (all) zero(s)."
        ::= { pnnixNodePglEntry 10 }
 
 
-- initial timer values table
 
pnnixNodeTimerTable OBJECT-TYPE
        SYNTAX        SEQUENCE OF PnnixNodeTimerEntry
	ACCESS    not-accessible
	STATUS	mandatory
        DESCRIPTION
            "A table of initial PNNI timer values and significant
             change thresholds."
        ::= { pnnixMIBObjects 4 }
 
pnnixNodeTimerEntry OBJECT-TYPE
        SYNTAX        PnnixNodeTimerEntry
	ACCESS    not-accessible
	STATUS	mandatory
        DESCRIPTION
            "An entry in the table, containing initial PNNI timer values
             and significant change thresholds of a PNNI logical node in
             this switching system."
        INDEX { pnnixNodeIndex }
        ::= { pnnixNodeTimerTable 1 }
 
PnnixNodeTimerEntry ::=
        SEQUENCE {
                pnnixNodePtseHolddown            INTEGER,
                pnnixNodeHelloHolddown           INTEGER,
                pnnixNodeHelloInterval           INTEGER,
                pnnixNodeHelloInactivityFactor   INTEGER,
                pnnixNodeHlinkInact              INTEGER,
                pnnixNodePtseRefreshInterval     INTEGER,
                pnnixNodePtseLifetimeFactor      INTEGER,
                pnnixNodeRxmtInterval            INTEGER,
                pnnixNodePeerDelayedAckInterval  INTEGER,
                pnnixNodeAvcrPm                  INTEGER,
                pnnixNodeAvcrMt                  INTEGER,
                pnnixNodeCdvPm                   INTEGER,
                pnnixNodeCtdPm                   INTEGER
                }
 
pnnixNodePtseHolddown OBJECT-TYPE
        SYNTAX        INTEGER
--	UNITS         "100 milliseconds"
	ACCESS	read-write
	STATUS	mandatory
        DESCRIPTION
            "The initial value for the PTSE hold down timer that will be
             used by the given node to limit the rate at which it can
             re-originate PTSEs. It must be a positive non-zero number."
--      REFERENCE "ATM Forum PNNI 1.0 Annex G MinPTSEInterval"
        --DEFVAL { 10 }
        ::= { pnnixNodeTimerEntry 1 }
 
pnnixNodeHelloHolddown OBJECT-TYPE
        SYNTAX        INTEGER
--	UNITS         "100 milliseconds"
	ACCESS	read-write
	STATUS	mandatory
        DESCRIPTION
            "The initial value for the Hello hold down timer that will
             be used by the given node to limit the rate at which it
             sends Hellos. It must be a positive non-zero number."
        --DEFVAL { 10 }
--      REFERENCE "ATM Forum PNNI 1.0 Annex G MinHelloInterval"
        ::= { pnnixNodeTimerEntry 2 }
 
pnnixNodeHelloInterval OBJECT-TYPE
        SYNTAX        INTEGER
--	UNITS         "seconds"
	ACCESS	read-write
	STATUS	mandatory
        DESCRIPTION
            "The initial value for the Hello Timer.
             In the absence of triggered Hellos, this node will send one
             Hello packet on each of its ports on this interval."
        --DEFVAL { 15 }
--      REFERENCE "ATM Forum PNNI 1.0 Annex G HelloInterval"
        ::= { pnnixNodeTimerEntry 3 }
 
pnnixNodeHelloInactivityFactor OBJECT-TYPE
        SYNTAX        INTEGER
	ACCESS	read-write
	STATUS	mandatory
        DESCRIPTION
            "The value for the Hello Inactivity factor that this
             node will use to determine when a neighbor has gone down."
        --DEFVAL { 5 }
--      REFERENCE "ATM Forum PNNI 1.0 Annex G InactivityFactor"
        ::= { pnnixNodeTimerEntry 4 }
 
pnnixNodeHlinkInact OBJECT-TYPE
        SYNTAX        INTEGER
--	UNITS         "seconds"
	ACCESS	read-write
	STATUS	mandatory
        DESCRIPTION
            "The amount of time a node will continue to
             advertise a horizontal (logical) link for which it has
             not received and processed a LGN Horizontal Link
             information group."
--      REFERENCE "ATM Forum PNNI 1.0 Annex G HorizontalLinkInactivityTime"
        --DEFVAL { 120 }
        ::= { pnnixNodeTimerEntry 5 }
 
pnnixNodePtseRefreshInterval OBJECT-TYPE
        SYNTAX        INTEGER
--	UNITS         "seconds"
	ACCESS	read-write
	STATUS	mandatory
        DESCRIPTION
            "The initial value for the Refresh timer that this node will
             use to drive (re-)origination of PTSEs in the absence of
             triggered updates."
        --DEFVAL  { 1800 }
--      REFERENCE "ATM Forum PNNI 1.0 Annex G PtseRefreshInterval"
        ::= { pnnixNodeTimerEntry 6 }
 
pnnixNodePtseLifetimeFactor OBJECT-TYPE
        SYNTAX        INTEGER (101..1000)
--	UNITS         "percent"
	ACCESS	read-write
	STATUS	mandatory
        DESCRIPTION
            "The value for the lifetime multiplier, expressed as a
             percentage.  The result of multiplying the
             pnnixNodePtseRefreshInterval attribute value by this
             attribute value is used as the initial lifetime that this
             node places into self-originated PTSEs."
        --DEFVAL  { 200 }
--      REFERENCE "ATM Forum PNNI 1.0 Annex G PtseLifetimeFactor"
        ::= { pnnixNodeTimerEntry 7 }
 
pnnixNodeRxmtInterval OBJECT-TYPE
        SYNTAX        INTEGER
--	UNITS         "seconds"
	ACCESS	read-write
	STATUS	mandatory
        DESCRIPTION
            "The period between retransmissions of unacknowledged
             Database Summary packets, PTSE Request packets, and PTSPs."
        --DEFVAL { 5 }
--      REFERENCE "ATM Forum PNNI 1.0 Annex G DSRxmtInterval, 
--		RequestRxmtInterval, PTSERetransmissionInterval"
        ::= { pnnixNodeTimerEntry 8 }
 
pnnixNodePeerDelayedAckInterval OBJECT-TYPE
        SYNTAX        INTEGER
--	UNITS         "100 milliseconds"
	ACCESS	read-write
	STATUS	mandatory
        DESCRIPTION
            "The minimum amount of time between transmissions of
             delayed PTSE acknowledgement packets."
        --DEFVAL { 10 }
--      REFERENCE "ATM Forum PNNI 1.0 Annex G PeerDelayedAckInterval"
        ::= { pnnixNodeTimerEntry 9 }
 
pnnixNodeAvcrPm OBJECT-TYPE
        SYNTAX        INTEGER (1..99)
--	UNITS         "percent"
	ACCESS	read-write
	STATUS	mandatory
        DESCRIPTION
            "The proportional multiplier used in the algorithms that
             determine significant change for AvCR parameters, expressed
             as a percentage."
--        REFERENCE "ATM Forum PNNI 1.0 Section 5.8.5.2.5.4, Annex G AvCR_PM"
        --DEFVAL  { 50 }
        ::= { pnnixNodeTimerEntry 10 }
 
pnnixNodeAvcrMt OBJECT-TYPE
        SYNTAX        INTEGER (1..99)
--	UNITS         "percent"
	ACCESS	read-write
	STATUS	mandatory
        DESCRIPTION
            "The minimum threshold used in the algorithms that determine
             significant change for AvCR parameters, expressed as a
             percentage."
--      REFERENCE "ATM Forum PNNI 1.0 Section 5.8.5.2.5.4, Annex G AvCR_mT"
        --DEFVAL  { 3 }
        ::= { pnnixNodeTimerEntry 11 }
 
pnnixNodeCdvPm OBJECT-TYPE
        SYNTAX        INTEGER (1..99)
--	UNITS         "percent"
	ACCESS	read-write
	STATUS	mandatory
        DESCRIPTION
            "The proportional multiplier used in the algorithms that
             determine significant change for CDV metrics, expressed as
             a percentage."
--      REFERENCE "ATM Forum PNNI 1.0 Section 5.8.5.2.5.6, Annex G CDV_PM"
        --DEFVAL  { 25 }
        ::= { pnnixNodeTimerEntry 12 }
 
pnnixNodeCtdPm OBJECT-TYPE
        SYNTAX        INTEGER (1..99)
--	UNITS         "percent"
	ACCESS	read-write
	STATUS	mandatory
        DESCRIPTION
            "The proportional multiplier used in the algorithms that
             determine significant change for CTD metrics, expressed as
             a percentage."
--        REFERENCE "ATM Forum PNNI 1.0 Section 5.8.5.2.5.5, Annex G maxCTD_PM"
        --DEFVAL  { 50 }
        ::= { pnnixNodeTimerEntry 13 }

 
-- nodal SVCC-based RCC variables table
 
pnnixNodeSvccTable OBJECT-TYPE
        SYNTAX        SEQUENCE OF PnnixNodeSvccEntry
	ACCESS    not-accessible
	STATUS	mandatory
        DESCRIPTION
            "A table of variables related to SVCC-based routing control
             channels.."
--        REFERENCE "ATM Forum PNNI 1.0 Section 5.5"
        ::= { pnnixMIBObjects 5 }
 
pnnixNodeSvccEntry OBJECT-TYPE
        SYNTAX        PnnixNodeSvccEntry
	ACCESS    not-accessible
	STATUS	mandatory
        DESCRIPTION
            "An entry in the table, containing SVCC-based RCC variables
             of a PNNI logical node in this switching system."
--        REFERENCE "ATM Forum PNNI 1.0 Section 5.5"
        INDEX { pnnixNodeIndex }
        ::= { pnnixNodeSvccTable 1 }
 
PnnixNodeSvccEntry ::=
        SEQUENCE {
                pnnixNodeSvccInitTime                    INTEGER,
                pnnixNodeSvccRetryTime                   INTEGER,
                pnnixNodeSvccCallingIntegrityTime        INTEGER,
                pnnixNodeSvccCalledIntegrityTime         INTEGER,
           pnnixNodeSvccTrafficDescriptorIndex  AtmpTrafficDescrParamIndex
                }
 
pnnixNodeSvccInitTime OBJECT-TYPE
        SYNTAX        INTEGER
--	UNITS         "seconds"
	ACCESS	read-write
	STATUS	mandatory
        DESCRIPTION
            "The amount of time this node will delay initiating
             establishment of an SVCC to a neighbor with a numerically
             lower ATM address, after determining that such an SVCC
             should be established."
--        REFERENCE "ATM Forum PNNI 1.0 Annex G InitialLGNSVCTimeout"
        --DEFVAL { 4 }
        ::= { pnnixNodeSvccEntry 1 }
 
pnnixNodeSvccRetryTime OBJECT-TYPE
        SYNTAX        INTEGER
--	UNITS         "seconds"
	ACCESS	read-write
	STATUS	mandatory
        DESCRIPTION
            "The amount of time this node will delay after an apparently
             still necessary and viable SVCC-based RCC is unexpectedly
             torn down, before attempting to re-establish it."
--        REFERENCE "ATM Forum PNNI 1.0 Annex G RetryLGNSVCTimeout"
        --DEFVAL { 30 }
        ::= { pnnixNodeSvccEntry 2 }
 
pnnixNodeSvccCallingIntegrityTime OBJECT-TYPE
        SYNTAX        INTEGER
--	UNITS         "seconds"
	ACCESS	read-write
	STATUS	mandatory
        DESCRIPTION
            "The amount of time this node will wait for an SVCC, which
             it has initiated establishment of as the calling party, to
             become fully established before giving up and tearing it
             down."
--        REFERENCE "ATM Forum PNNI 1.0 Annex G SVCCallingIntegrityTime"
        --DEFVAL { 35 }
        ::= { pnnixNodeSvccEntry 3 }
 
pnnixNodeSvccCalledIntegrityTime OBJECT-TYPE
        SYNTAX        INTEGER
--	UNITS         "seconds"
	ACCESS	read-write
	STATUS	mandatory
        DESCRIPTION
            "The amount of time this node will wait for an SVCC, which
             it has decided to accept as the called party, to become
             fully established before giving up and tearing it down."
--        REFERENCE "ATM Forum PNNI 1.0 Annex G SVCCalledIntegrityTime"
        --DEFVAL { 50 }
        ::= { pnnixNodeSvccEntry 4 }
 
pnnixNodeSvccTrafficDescriptorIndex OBJECT-TYPE
        SYNTAX        AtmpTrafficDescrParamIndex
	ACCESS	read-write
	STATUS	mandatory
        DESCRIPTION
            "An index into the atmTrafficDescrParamTable defined in
             RFC 1695.  This traffic descriptor is used when
             establishing switched virtual channels for use as
             SVCC-based RCCs to/from PNNI logical group nodes."
--        REFERENCE "ATM Forum PNNI 1.0 Section 5.5.2, Annex G 
--		RCCMaximumBurstSize, RCCPeakCellRate, RCCSustainableCellRate"
        ::= { pnnixNodeSvccEntry 5 }
 
 
-- scope mapping table

pnnixScopeMappingTable OBJECT-TYPE
        SYNTAX  SEQUENCE OF PnnixScopeMappingEntry
	ACCESS  not-accessible
	STATUS	mandatory
        DESCRIPTION
            "The pnnixScopeTable contains the mappings of membership and
             connection scope from organizational scope values (used at
             UNI interfaces) to PNNI scope (i.e. in terms of PNNI
             routing level indicators)."
--        REFERENCE "ATM Forum PNNI 1.0 Section 5.3.6"
        ::= { pnnixMIBObjects 6 }

pnnixScopeMappingEntry OBJECT-TYPE
        SYNTAX        PnnixScopeMappingEntry
	ACCESS    not-accessible
	STATUS	mandatory
        DESCRIPTION
            "An entry in the table, containing scope mapping information
             for a PNNI logical node in this switching system."
--	REFERENCE "ATM Forum PNNI 1.0 Section 5.3.6"
        INDEX { pnnixNodeIndex }
        ::= { pnnixScopeMappingTable 1 }

PnnixScopeMappingEntry ::=
        SEQUENCE {
                pnnixScopeLocalNetwork           PnnixLevel,
                pnnixScopeLocalNetworkPlusOne    PnnixLevel,
                pnnixScopeLocalNetworkPlusTwo    PnnixLevel,
                pnnixScopeSiteMinusOne           PnnixLevel,
                pnnixScopeIntraSite              PnnixLevel,
                pnnixScopeSitePlusOne            PnnixLevel,
                pnnixScopeOrganizationMinusOne   PnnixLevel,
                pnnixScopeIntraOrganization      PnnixLevel,
                pnnixScopeOrganizationPlusOne    PnnixLevel,
                pnnixScopeCommunityMinusOne      PnnixLevel,
                pnnixScopeIntraCommunity         PnnixLevel,
                pnnixScopeCommunityPlusOne       PnnixLevel,
                pnnixScopeRegional               PnnixLevel,
                pnnixScopeInterRegional          PnnixLevel,
                pnnixScopeGlobal                 PnnixLevel
                }

pnnixScopeLocalNetwork OBJECT-TYPE
        SYNTAX        PnnixLevel
	ACCESS	read-write
	STATUS	mandatory
        DESCRIPTION
            "The highest level of PNNI hierarchy (i.e. smallest PNNI
             routing level) that lies within the organizational scope
             value localNetwork(1)."
        --DEFVAL { 96 }
        ::= { pnnixScopeMappingEntry 1 }

pnnixScopeLocalNetworkPlusOne OBJECT-TYPE
        SYNTAX        PnnixLevel
	ACCESS	read-write
	STATUS	mandatory
        DESCRIPTION
            "The highest level of PNNI hierarchy (i.e. smallest PNNI
             routing level) that lies within the organizational scope
             value localNetworkPlusOne(2)."
        --DEFVAL { 96 }
        ::= { pnnixScopeMappingEntry 2 }

pnnixScopeLocalNetworkPlusTwo OBJECT-TYPE
        SYNTAX        PnnixLevel
	ACCESS	read-write
	STATUS	mandatory
        DESCRIPTION
            "The highest level of PNNI hierarchy (i.e. smallest PNNI
             routing level) that lies within the organizational scope
             value localNetworkPlusTwo(3)."
        --DEFVAL { 96 }
        ::= { pnnixScopeMappingEntry 3 }

pnnixScopeSiteMinusOne OBJECT-TYPE
        SYNTAX        PnnixLevel
	ACCESS	read-write
	STATUS	mandatory
        DESCRIPTION
            "The highest level of PNNI hierarchy  (i.e. smallest PNNI
             routing level) that lies within the organizational scope
             value siteMinusOne(4)."
        --DEFVAL { 80 }
        ::= { pnnixScopeMappingEntry 4 }

pnnixScopeIntraSite OBJECT-TYPE
        SYNTAX        PnnixLevel
	ACCESS	read-write
	STATUS	mandatory
        DESCRIPTION
            "The highest level of PNNI hierarchy (i.e. smallest PNNI
             routing level) that lies within the organizational scope
             value intraSite(5)."
        --DEFVAL { 80 }
        ::= { pnnixScopeMappingEntry 5 }

pnnixScopeSitePlusOne OBJECT-TYPE
        SYNTAX        PnnixLevel
	ACCESS	read-write
	STATUS	mandatory
        DESCRIPTION
            "The highest level of PNNI hierarchy (i.e. smallest PNNI
             routing level) that lies within the organizational scope
             value sitePlusOne(6)."
        --DEFVAL { 72 }
        ::= { pnnixScopeMappingEntry 6 }

pnnixScopeOrganizationMinusOne OBJECT-TYPE
        SYNTAX        PnnixLevel
	ACCESS	read-write
	STATUS	mandatory
        DESCRIPTION
            "The highest level of PNNI hierarchy (i.e. smallest PNNI
             routing level) that lies within the organizational scope
             value organizationMinusOne(7)."
        --DEFVAL { 72 }
        ::= { pnnixScopeMappingEntry 7 }

pnnixScopeIntraOrganization OBJECT-TYPE
        SYNTAX        PnnixLevel
	ACCESS	read-write
	STATUS	mandatory
        DESCRIPTION
            "The highest level of PNNI hierarchy (i.e. smallest PNNI
             routing level) that lies within the organizational scope
             value intraOrganization(8)."
        --DEFVAL { 64 }
        ::= { pnnixScopeMappingEntry 8 }

pnnixScopeOrganizationPlusOne OBJECT-TYPE
        SYNTAX        PnnixLevel
	ACCESS	read-write
	STATUS	mandatory
        DESCRIPTION
            "The highest level of PNNI hierarchy (i.e. smallest PNNI
             routing level) that lies within the organizational scope
             value organizationPlusOne(9)."
        --DEFVAL { 64 }
        ::= { pnnixScopeMappingEntry 9 }

pnnixScopeCommunityMinusOne OBJECT-TYPE
        SYNTAX        PnnixLevel
	ACCESS	read-write
	STATUS	mandatory
        DESCRIPTION
            "The highest level of PNNI hierarchy (i.e. smallest PNNI
             routing level) that lies within the organizational scope
             value communityMinusOne(10)."
        --DEFVAL { 64 }
        ::= { pnnixScopeMappingEntry 10 }

pnnixScopeIntraCommunity OBJECT-TYPE
        SYNTAX        PnnixLevel
	ACCESS	read-write
	STATUS	mandatory
        DESCRIPTION
            "The highest level of PNNI hierarchy (i.e. smallest PNNI
             routing level) that lies within the organizational scope
             value intraCommunity(11)."
        --DEFVAL { 48 }
        ::= { pnnixScopeMappingEntry 11 }

pnnixScopeCommunityPlusOne OBJECT-TYPE
        SYNTAX        PnnixLevel
	ACCESS	read-write
	STATUS	mandatory
        DESCRIPTION
            "The highest level of PNNI hierarchy (i.e. smallest PNNI
             routing level) that lies within the organizational scope
             value communityPlusOne(12)."
        --DEFVAL { 48 }
        ::= { pnnixScopeMappingEntry 12 }

pnnixScopeRegional OBJECT-TYPE
        SYNTAX        PnnixLevel
	ACCESS	read-write
	STATUS	mandatory
        DESCRIPTION
            "The highest level of PNNI hierarchy (i.e. smallest PNNI
             routing level) that lies within the organizational scope
             value regional(13)."
        --DEFVAL { 32 }
        ::= { pnnixScopeMappingEntry 13 }

pnnixScopeInterRegional OBJECT-TYPE
        SYNTAX        PnnixLevel
	ACCESS	read-write
	STATUS	mandatory
        DESCRIPTION
            "The highest level of PNNI hierarchy (i.e. smallest PNNI
             routing level) that lies within the organizational scope
             value interRegional(14)."
        --DEFVAL { 32 }
        ::= { pnnixScopeMappingEntry 14 }

pnnixScopeGlobal OBJECT-TYPE
        SYNTAX        PnnixLevel
	ACCESS	read-write
	STATUS	mandatory
        DESCRIPTION
            "The highest level of PNNI hierarchy (i.e. smallest PNNI
             routing level) that lies within the organizational scope
             value global(15)."
        --DEFVAL { 0 }
        ::= { pnnixScopeMappingEntry 15 }


-- Summary advertising table 
 
pnnixSummaryTable OBJECT-TYPE
        SYNTAX        SEQUENCE OF PnnixSummaryEntry
	ACCESS    not-accessible
	STATUS	mandatory
        DESCRIPTION
            "A list of the summary address prefixes that may be
             advertised by the specified logical PNNI entity."
--	REFERENCE "ATM Forum PNNI 1.0 Section 5.9.2"
        ::= { pnnixMIBObjects 7 }
pnnixSummaryEntry OBJECT-TYPE
        SYNTAX        PnnixSummaryEntry
	ACCESS    not-accessible
	STATUS	mandatory
        DESCRIPTION
            "An entry in the table, containing summary address prefix
             information in this switching system."
--	REFERENCE "ATM Forum PNNI 1.0 Section 5.9.2"
        INDEX         { pnnixNodeIndex,
                        pnnixSummaryAddress,
                        pnnixSummaryPrefixLength }
        ::= { pnnixSummaryTable 1 }
 
PnnixSummaryEntry ::=
        SEQUENCE {
                pnnixSummaryAddress              AtmAddrPrefix,
                pnnixSummaryPrefixLength         PnnixPrefixLength,
                pnnixSummaryType                 INTEGER,
                pnnixSummarySuppress             TruthValue,
                pnnixSummaryState                INTEGER,
                pnnixSummaryRowStatus            INTEGER
        }
 
pnnixSummaryAddress OBJECT-TYPE
        SYNTAX        AtmAddrPrefix
	ACCESS    not-accessible
	STATUS	mandatory
        DESCRIPTION
            "The ATM End System Address prefix for the summary."
        ::= { pnnixSummaryEntry 1 }
 
pnnixSummaryPrefixLength OBJECT-TYPE
        SYNTAX        PnnixPrefixLength
	ACCESS    not-accessible
	STATUS	mandatory
        DESCRIPTION
            "The prefix length for the summary."
        ::= { pnnixSummaryEntry 2 }
 
pnnixSummaryType OBJECT-TYPE
        SYNTAX        INTEGER { internal(1), exterior(2) }
	ACCESS	read-write
	STATUS	mandatory
        DESCRIPTION
            "The type (e.g. internal or exterior) of summary being
                        described."
        --DEFVAL { internal }
        ::= { pnnixSummaryEntry 3 }
 
pnnixSummarySuppress OBJECT-TYPE
        SYNTAX        TruthValue
	ACCESS	read-write
	STATUS	mandatory
        DESCRIPTION
            "Determines what is done with addresses that are being
             summarized by the instance. The default value (e.g. false)
             will indicate that the summary should propagate into the
             peer group. Network Management will be able to set the
             value of this attribute to `suppress' (e.g. true), which
             suppresses the summary and any reachable addresses it
             summarizes from being advertised into the peer group."
        --DEFVAL { false }
        ::= { pnnixSummaryEntry 4 }
 
pnnixSummaryState OBJECT-TYPE
        SYNTAX        INTEGER {
                                advertising(1),
                                suppressing(2),
                                inactive(3)
                                }
	ACCESS    read-only
	STATUS	mandatory
        DESCRIPTION
            "Indicates whether the summary is currently being advertised
             by the node within the local switching system into its peer
             group."
        ::= { pnnixSummaryEntry 5 }
 
pnnixSummaryRowStatus OBJECT-TYPE
        SYNTAX        INTEGER {
								create (1),
								modify (2),
								delete (3),
								active (4),
								notActive (5)
							  }
	ACCESS	read-write
	STATUS	mandatory
        DESCRIPTION
            "To create, delete, activate and de-activate a summary."
        ::= { pnnixSummaryEntry 6 }
 
 
-- Interface table
 
pnnixIfTable OBJECT-TYPE
        SYNTAX        SEQUENCE OF PnnixIfEntry
	ACCESS    not-accessible
	STATUS	mandatory
        DESCRIPTION
            "The pnnixIfTable contains the attributes necessary to
             configure a physical interface on a switching system which
             is capable of being used for PNNI routing.  Interfaces may
             represent physical connection points (i.e. copper/fiber
             connection points) or VPCs which have been configured for
             PNNI's use.  Each interface is attached to a specific
             lowest-level node within the switching system.

             An ifIndex is used as the instance ID to uniquely identify
             the interface on the local switching system. This index has
             the same value as the ifIndex object defined in RFC 1573
             for the same interface, since this table correlates with
             the ifTable in RFC 1573.

             One row in this table is created by the managed system for
             each row in the ifTable that has an ifType of atm(37) or
             atmLogical(80)."
        ::= { pnnixMIBObjects 8 }
 
pnnixIfEntry OBJECT-TYPE
        SYNTAX        PnnixIfEntry
	ACCESS    not-accessible
	STATUS	mandatory
        DESCRIPTION
            "An entry in the table, containing PNNI specific interface
             information in this switching system."
        INDEX         { ifIndex }
        ::= { pnnixIfTable 1 }
 
PnnixIfEntry ::=
        SEQUENCE {
                pnnixIfNodeIndex         	PnnixNodeIndex,
                pnnixIfPortId            	PnnixPortId,
                pnnixIfAggrToken         	PnnixAggrToken,
                pnnixIfVPCapability      	TruthValue,
                pnnixIfAdmWeightCbr      	Gauge,
                pnnixIfAdmWeightRtVbr    	Gauge,
                pnnixIfAdmWeightNrtVbr   	Gauge,
                pnnixIfAdmWeightAbr      	Gauge,
                pnnixIfAdmWeightUbr      	Gauge,
                pnnixIfRccServiceCategory    	ServiceCategory,
                pnnixIfRccTrafficDescrIndex  	AtmpTrafficDescrParamIndex
                }
 
 
pnnixIfNodeIndex OBJECT-TYPE
        SYNTAX        PnnixNodeIndex
	ACCESS    read-write
	STATUS	mandatory
        DESCRIPTION
            "Identifies the node within the switching system that the
             interface is directly attached to."
        --DEFVAL { 1 }
        ::= { pnnixIfEntry 1 }
 
pnnixIfPortId OBJECT-TYPE
        SYNTAX        PnnixPortId
	ACCESS    read-only
	STATUS	mandatory
        DESCRIPTION
            "The Port Identifier of the port as selected by the PNNI
             protocol entity for the given interface.  This value has
             meaning only within the context of the node to which the
             port is attached."
--	REFERENCE "ATM Forum PNNI 1.0 Section 5.3.4"
        ::= { pnnixIfEntry 2 }
 
pnnixIfAggrToken OBJECT-TYPE
        SYNTAX        PnnixAggrToken
	ACCESS    read-write
	STATUS	mandatory
        DESCRIPTION
            "The configured aggregation token for this interface.  The
             aggregation token controls what other links the link
             associated with this interface will be aggregated together
             with."
--	REFERENCE "ATM Forum PNNI 1.0 Sections 5.3.5, 5.10.3.1"
        --DEFVAL { 0 }
        ::= { pnnixIfEntry 3 }
 
pnnixIfVPCapability OBJECT-TYPE
        SYNTAX        TruthValue
	ACCESS    read-write
	STATUS	mandatory
        DESCRIPTION
            "Indicates whether the interface is capable of having VPCs
             established within it or not.
 
             This object may only have the value `true' for physical ATM
             interfaces, i.e. those with an ifType of atm(37)."
--	REFERENCE "ATM Forum PNNI 1.0 Section 5.14.9.1 Table 5-34"
        ::= { pnnixIfEntry 4 }
 
pnnixIfAdmWeightCbr OBJECT-TYPE
        SYNTAX        Gauge
	ACCESS    read-write
	STATUS	mandatory
        DESCRIPTION
            "The administrative weight of this interface for the
             constant bit rate service category."
--	REFERENCE "ATM Forum PNNI 1.0 Section 5.8.1.1.3.4"
        --DEFVAL { 5040 }
        ::= { pnnixIfEntry 5 }
 
pnnixIfAdmWeightRtVbr OBJECT-TYPE
        SYNTAX        Gauge
	ACCESS    read-write
	STATUS	mandatory
        DESCRIPTION
            "The administrative weight of this interface for the
             real-time variable bit rate service category."
--	REFERENCE "ATM Forum PNNI 1.0 Section 5.8.1.1.3.4"
        --DEFVAL { 5040 }
        ::= { pnnixIfEntry 6 }
 
pnnixIfAdmWeightNrtVbr OBJECT-TYPE
        SYNTAX        Gauge
	ACCESS    read-write
	STATUS	mandatory
        DESCRIPTION
            "The administrative weight of this interface for the
             non-real-time variable bit rate service category."
--	REFERENCE "ATM Forum PNNI 1.0 Section 5.8.1.1.3.4"
        --DEFVAL { 5040 }
        ::= { pnnixIfEntry 7 }
 
pnnixIfAdmWeightAbr OBJECT-TYPE
        SYNTAX        Gauge
	ACCESS    read-write
	STATUS	mandatory
        DESCRIPTION
            "The administrative weight of this interface for the
             available bit rate service category."
--	REFERENCE "ATM Forum PNNI 1.0 Section 5.8.1.1.3.4"
        --DEFVAL { 5040 }
        ::= { pnnixIfEntry 8 }
 
pnnixIfAdmWeightUbr OBJECT-TYPE
        SYNTAX        Gauge
	ACCESS    read-write
	STATUS	mandatory
        DESCRIPTION
            "The administrative weight of this interface for the
             unspecified bit rate service category."
--	REFERENCE "ATM Forum PNNI 1.0 Section 5.8.1.1.3.4"
        --DEFVAL { 5040 }
        ::= { pnnixIfEntry 9 }
 
pnnixIfRccServiceCategory OBJECT-TYPE
        SYNTAX        ServiceCategory
	ACCESS    read-write
	STATUS	mandatory
        DESCRIPTION
            "The service category used for the PNNI routing control
             channel (VCI=18) on this interface."
--	REFERENCE "ATM Forum PNNI 1.0 Sections 5.5.2, 5.5.3"
        ::= { pnnixIfEntry 10 }

pnnixIfRccTrafficDescrIndex OBJECT-TYPE
        SYNTAX        AtmpTrafficDescrParamIndex
	ACCESS    read-write
	STATUS	mandatory
        DESCRIPTION
            "The traffic descriptor index referring to the entry in the
             atmTrafficDescrParamTable defined in RFC 1695 that
             specifies the traffic allocation for the PNNI routing
             control channel (VCI=18) on this interface."
--	REFERENCE "ATM Forum PNNI 1.0 Sections 5.5.2, 5.5.3, Annex G 
--		RCCMaximumBurstSize, RCCPeakCellRate, RCCSustainableCellRate"
        ::= { pnnixIfEntry 11 }
 
 
-- link table
 
pnnixLinkTable OBJECT-TYPE
        SYNTAX        SEQUENCE OF PnnixLinkEntry
	ACCESS    not-accessible
	STATUS	mandatory
        DESCRIPTION
            "This table contains the attributes necessary to describe
             the operation of logical links attached to the local
             switching system and the relationship with the neighbor
             nodes on the other end of the links.  Links are attached to
             a specific node within the switching system.  A
             concatenation of the Node Index of the node within the
             local switching system and the port ID are used as the
             instance ID to uniquely identify the link.  Links may
             represent horizontal links between lowest level neighboring
             peers, outside links, uplinks, or horizontal links to/from
             LGNs.

             The entire pnnixLink object is read-only, reflecting the
             fact that this information is discovered dynamically by the
             PNNI protocol rather than configured."
--	REFERENCE "ATM Forum PNNI 1.0 Section 5.6"
        ::= { pnnixMIBObjects 9 }
 
pnnixLinkEntry OBJECT-TYPE
        SYNTAX        PnnixLinkEntry
	ACCESS    not-accessible
	STATUS	mandatory
        DESCRIPTION
            "An entry in the table, containing information about a link
             attached to a PNNI logical node in this switching system."
--	REFERENCE "ATM Forum PNNI 1.0 Section 5.6"
        INDEX         { pnnixNodeIndex,
                        pnnixLinkPortId }
        ::= { pnnixLinkTable 1 }
 
PnnixLinkEntry ::=
        SEQUENCE {
--              pnnixLinkPortId          	PnnixPortId,
                pnnixLinkPortId          	INTEGER,
                pnnixLinkType            	INTEGER,
                pnnixLinkVersion         	PnnixVersion,
                pnnixLinkHelloState      	PnnixHelloState,
                pnnixLinkRemoteNodeId    	PnnixNodeId,
                pnnixLinkRemotePortId    	PnnixPortId,
                pnnixLinkDerivedAggrToken        PnnixAggrToken,
                pnnixLinkUpnodeId        	PnnixNodeId,
                pnnixLinkUpnodeAtmAddress        PnnixAtmAddr,
                pnnixLinkCommonPeerGroupId       PnnixPeerGroupId,
                pnnixLinkIfIndex         	InterfaceIndex,
                pnnixLinkSvccRccIndex    	PnnixSvccRccIndex,
                pnnixLinkRcvHellos       	Counter,
                pnnixLinkXmtHellos       	Counter
                }
 
pnnixLinkPortId OBJECT-TYPE
        SYNTAX        INTEGER
--      SYNTAX        PnnixPortId
	ACCESS    not-accessible
	STATUS	mandatory
        DESCRIPTION
            "The Port Identifier of the link as selected by the local
             node.  This value has meaning only within the context of
             the node to which the port is attached."
        ::= { pnnixLinkEntry 1 }
 
pnnixLinkType OBJECT-TYPE
        SYNTAX        INTEGER {
                                unknown(1),
                                lowestLevelHorizontalLink(2),
                                horizontalLinkToFromLgn(3),
                                lowestLevelOutsideLink(4),
                                uplink(5),
                                outsideLinkAndUplink(6)
                                }
	ACCESS    read-only
	STATUS	mandatory
        DESCRIPTION
            "Indicates the type of link being described."
        ::= { pnnixLinkEntry 2 }
 
pnnixLinkVersion OBJECT-TYPE
        SYNTAX        PnnixVersion
	ACCESS    read-only
	STATUS	mandatory
        DESCRIPTION
            "For horizontal and outside links between lowest-level nodes
             and for links of unknown type, this attribute indicates the
             version of PNNI routing protocol used to exchange
             information over this link.  If communication with the
             neighbor node has not yet been established, then the
             Version is set to `unknown'.  For uplinks (where the
             port ID is not also used for the underlying outside link)
             or links to/from LGNs, the Version is set to `unknown'."
        ::= { pnnixLinkEntry 3 }
 
pnnixLinkHelloState OBJECT-TYPE
        SYNTAX        PnnixHelloState
	ACCESS    read-only
	STATUS	mandatory
        DESCRIPTION
            "For horizontal and outside links between lowest-level nodes
             and for links of unknown type, this attribute indicates the
             state of the Hello protocol exchange over this link.  For
             links to/from LGNs, this attribute indicates the state of
             the corresponding LGN Horizontal Link Hello State Machine.
             For uplinks (where the port ID is not also used for the
             underlying outside link), this attribute is set to
             notApplicable."
--	REFERENCE "ATM Forum PNNI 1.0 Section 5.6.2.1.2"
        ::= { pnnixLinkEntry 4 }
 
pnnixLinkRemoteNodeId OBJECT-TYPE
        SYNTAX        PnnixNodeId
	ACCESS    read-only
	STATUS	mandatory
        DESCRIPTION
            "Indicates the node identifier of the remote (neighboring)
             node on the other end of the link.  If the pnnixLinkType is
             `outside link and uplink', this is the node identifier of
             the lowest-level neighbor node on the other end of the
             outside link.  If the remote node ID is unknown or if the
             pnnixLinkType is `uplink', this attribute is set to all
             zeros."
        ::= { pnnixLinkEntry 5 }
 
pnnixLinkRemotePortId OBJECT-TYPE
        SYNTAX        PnnixPortId
	ACCESS    read-only
	STATUS	mandatory
        DESCRIPTION
            "Indicates the port identifier of the port at the remote end
             of the link as assigned by the remote node.  If the
             pnnixLinkType is `outside link and uplink', this is the port
             identifier assigned by the lowest-level neighbor node to
             identify the outside link.  If the remote port ID is
             unknown or if the pnnixLinkType is `uplink', this attribute
             is set to zero."
        ::= { pnnixLinkEntry 6 }
 
pnnixLinkDerivedAggrToken OBJECT-TYPE
        SYNTAX        PnnixAggrToken
	ACCESS    read-only
	STATUS	mandatory
        DESCRIPTION
            "Indicates the derived aggregation token value used on this
             link.  For horizontal links between lowest-level nodes and
             when the link type is not yet known, this attribute takes
             the value of zero."
--	REFERENCE "ATM Forum PNNI 1.0 Section 5.10.3.1"
        ::= { pnnixLinkEntry 7 }
 
pnnixLinkUpnodeId OBJECT-TYPE
        SYNTAX        PnnixNodeId
	ACCESS    read-only
	STATUS	mandatory
        DESCRIPTION
            "For outside links and uplinks, this attribute contains the
             Node Identifier of the upnode (the neighbor node's identity
             at the level of the common peer group).  When the upnode
             has not yet been identified, this attribute is set to zero.
             For horizontal links or when the link type is not yet
             known, this attribute is set to zero."
        ::= { pnnixLinkEntry 8 }
 
pnnixLinkUpnodeAtmAddress OBJECT-TYPE
        SYNTAX        PnnixAtmAddr
	ACCESS    read-only
	STATUS	mandatory
        DESCRIPTION
            "For outside links and uplinks, this attribute contains the
             ATM End System Address used to establish connections to the
             upnode.  When the upnode has not yet been identified, this
             attribute is set to zero.  For horizontal links or when the
             link type is not yet known, this attribute is set to zero."
        ::= { pnnixLinkEntry 9 }
 
pnnixLinkCommonPeerGroupId OBJECT-TYPE
        SYNTAX        PnnixPeerGroupId
	ACCESS    read-only
	STATUS	mandatory
        DESCRIPTION
            "For outside links and uplinks, this attribute contains the
             peer group identifier of the lowest level common Peer Group
             in the ancestry of the neighboring node and the node within
             the local switching system.  The value of this attribute
             takes on a value determined by the Hello exchange of
             hierarchical information that occurs between the two
             lowest-level border nodes.  When the common peer group has
             not yet been identified, this attribute is set to zero.
             For horizontal links or when the link type is not yet
             known, this attribute is set to all zeros."
        ::= { pnnixLinkEntry 10 }
 
pnnixLinkIfIndex OBJECT-TYPE
        SYNTAX        InterfaceIndex
	ACCESS    read-only
	STATUS	mandatory
        DESCRIPTION
            "For horizontal and outside links between lowest-level nodes
             and for links of unknown type, this attribute identifies
             the interface to which the logical link corresponds.
 
             For all other cases, the value of this object is zero."
        ::= { pnnixLinkEntry 11 }
 
pnnixLinkSvccRccIndex OBJECT-TYPE
        SYNTAX        PnnixSvccRccIndex
	ACCESS    read-only
	STATUS	mandatory
        DESCRIPTION
            "For horizontal links to/from LGNs, this attribute
             identifies the SVCC-based RCC used to exchange information
             with the neighboring peer logical group node.  If the
             pnnixLinkType is not `horizontal link to/from LGN', this
             attribute shall take the value of zero."
        ::= { pnnixLinkEntry 12 }
 
pnnixLinkRcvHellos OBJECT-TYPE
        SYNTAX        Counter
	ACCESS    read-only
	STATUS	mandatory
        DESCRIPTION
            "For horizontal and outside links between lowest-level nodes
             and for links of unknown type, this attribute contains a
             count of the number of Hello Packets received over this
             link.  If the pnnixLinkType is `horizontal link to/from LGN'
             or `uplink', this attribute is set to zero."
        ::= { pnnixLinkEntry 13 }
 
pnnixLinkXmtHellos OBJECT-TYPE
        SYNTAX        Counter
	ACCESS    read-only
	STATUS	mandatory
        DESCRIPTION
            "For horizontal and outside links between lowest-level nodes
             and for links of unknown type, this attribute contains a
             count of the number of Hello Packets transmitted over this
             link.  If the pnnixLinkType is `horizontal link to/from LGN'
             or `uplink', this attribute is set to zero."
        ::= { pnnixLinkEntry 14 }
 
 
-- neighboring peer table
 
pnnixNbrPeerTable OBJECT-TYPE
        SYNTAX        SEQUENCE OF PnnixNbrPeerEntry
	ACCESS    not-accessible
	STATUS	mandatory
        DESCRIPTION
            "The pnnixNbrPeer Object contains all the attributes
             necessary to describe the relationship a node in this
             switching system has with a neighboring node within the
             same peer group.  A concatenation of the Node Identifier of
             the node within the local switching system and the
             neighboring peer's Node Identifier is used to form the
             instance ID for this object.

             The entire pnnixNbrPeer object is read-only, reflecting the
             fact that neighboring peers are discovered dynamically by
             the PNNI protocol rather than configured."
--	REFERENCE "ATM Forum PNNI 1.0 Sections 5.7, 5.8"
        ::= { pnnixMIBObjects 10 }
 
pnnixNbrPeerEntry OBJECT-TYPE
        SYNTAX        PnnixNbrPeerEntry
	ACCESS    not-accessible
	STATUS	mandatory
        DESCRIPTION
            "An entry in the table, containing information about this
             node's relationship with a neighboring peer node."
--	REFERENCE "ATM Forum PNNI 1.0 Sections 5.7, 5.8"
        INDEX         { pnnixNodeIndex,
                        pnnixNbrPeerRemoteNodeId }
        ::= { pnnixNbrPeerTable 1 }
 
PnnixNbrPeerEntry ::=
        SEQUENCE {
                pnnixNbrPeerRemoteNodeId         PnnixNodeId,
                pnnixNbrPeerState                INTEGER,
                pnnixNbrPeerSvccRccIndex         PnnixSvccRccIndex,
                pnnixNbrPeerPortCount            Gauge,
                pnnixNbrPeerRcvDbSums            Counter,
                pnnixNbrPeerXmtDbSums            Counter,
                pnnixNbrPeerRcvPtsps             Counter,
                pnnixNbrPeerXmtPtsps             Counter,
                pnnixNbrPeerRcvPtseReqs          Counter,
                pnnixNbrPeerXmtPtseReqs          Counter,
                pnnixNbrPeerRcvPtseAcks          Counter,
                pnnixNbrPeerXmtPtseAcks          Counter
                }
 
pnnixNbrPeerRemoteNodeId OBJECT-TYPE
        SYNTAX        PnnixNodeId
	ACCESS    not-accessible
	STATUS	mandatory
        DESCRIPTION
            "The Node Identifier of the neighboring peer node."
        ::= { pnnixNbrPeerEntry 1 }
 
pnnixNbrPeerState OBJECT-TYPE
        SYNTAX        INTEGER {
                                npdown(1),
                                negotiating(2),
                                exchanging(3),
                                loading(4),
                                full(5)
                                }
	ACCESS    read-only
	STATUS	mandatory
        DESCRIPTION
            "Indicates the state of this node's Neighboring Peer State
             Machine associated with pnnixNbrPeerRemoteNodeId."
--	REFERENCE "ATM Forum PNNI 1.0 Section 5.7.2"
        ::= { pnnixNbrPeerEntry 2 }
 
pnnixNbrPeerSvccRccIndex OBJECT-TYPE
        SYNTAX        PnnixSvccRccIndex
	ACCESS    read-only
	STATUS	mandatory
        DESCRIPTION
            "Identifies the SVCC-based RCC being used to communicate
             with the neighboring peer if one exists.  If both the local
             node and the neighboring peer node are lowest-level nodes,
             this attribute is set to zero."
        ::= { pnnixNbrPeerEntry 3 }
 
pnnixNbrPeerPortCount OBJECT-TYPE
        SYNTAX        Gauge
	ACCESS    read-only
	STATUS	mandatory
        DESCRIPTION
            "A count of the total number of ports that connect to the
             neighboring peer.  If the neighboring peer only
             communicates via an SVCC-based RCC, the value of this
             attribute is set to zero.  Otherwise it is set to the total
             number of ports to the neighboring peer in the Hello state
             2-WayInside."
        ::= { pnnixNbrPeerEntry 4 }
 
pnnixNbrPeerRcvDbSums OBJECT-TYPE
        SYNTAX        Counter
	ACCESS    read-only
	STATUS	mandatory
        DESCRIPTION
            "A count of the number of Database Summary Packets received
             from the neighboring peer."
        ::= { pnnixNbrPeerEntry 5 }
 
pnnixNbrPeerXmtDbSums OBJECT-TYPE
        SYNTAX        Counter
	ACCESS    read-only
	STATUS	mandatory
        DESCRIPTION
            "A count of the number of Database Summary Packets
             transmitted to the neighboring peer."
        ::= { pnnixNbrPeerEntry 6 }
 
pnnixNbrPeerRcvPtsps OBJECT-TYPE
        SYNTAX        Counter
	ACCESS    read-only
	STATUS	mandatory
        DESCRIPTION
            "A count of the number of PTSPs received from the
             neighboring peer."
        ::= { pnnixNbrPeerEntry 7 }
 
pnnixNbrPeerXmtPtsps OBJECT-TYPE
        SYNTAX        Counter
	ACCESS    read-only
	STATUS	mandatory
        DESCRIPTION
            "A count of the number of PTSPs (re)transmitted to the
             neighboring peer."
        ::= { pnnixNbrPeerEntry 8 }
 
pnnixNbrPeerRcvPtseReqs OBJECT-TYPE
        SYNTAX        Counter
	ACCESS    read-only
	STATUS	mandatory
        DESCRIPTION
            "A count of the number of PTSE Request packets received from
             the neighboring peer."
        ::= { pnnixNbrPeerEntry 9 }
 
pnnixNbrPeerXmtPtseReqs OBJECT-TYPE
        SYNTAX        Counter
	ACCESS    read-only
	STATUS	mandatory
        DESCRIPTION
            "A count of the number of PTSE Request packets transmitted
             to the neighboring peer."
        ::= { pnnixNbrPeerEntry 10 }
 
pnnixNbrPeerRcvPtseAcks OBJECT-TYPE
        SYNTAX        Counter
	ACCESS    read-only
	STATUS	mandatory
        DESCRIPTION
            "A count of the number of PTSE Ack packets received from the
             neighboring peer."
        ::= { pnnixNbrPeerEntry 11 }
 
pnnixNbrPeerXmtPtseAcks OBJECT-TYPE
        SYNTAX        Counter
	ACCESS    read-only
	STATUS	mandatory
        DESCRIPTION
            "A count of the number of PTSE Ack packets transmitted to
             the neighboring peer."
        ::= { pnnixNbrPeerEntry 12 }
 
 
-- neighboring peer port table
 
pnnixNbrPeerPortTable OBJECT-TYPE
        SYNTAX        SEQUENCE OF PnnixNbrPeerPortEntry
	ACCESS    not-accessible
	STATUS	mandatory
        DESCRIPTION
            "A table of all ports in Hello state 2-Way Inside to a given
             neighboring peer node.  A concatenation of the Node Index
             of the node within the local switching system, the
             neighbor's Node Identifier and the Interface Index of the
             port being described forms the instance ID for this object.
             This object is only used for lowest-level nodes."
--	REFERENCE "ATM Forum PNNI 1.0 Section 5.7.1 Port ID List"
        ::= { pnnixMIBObjects 11 }
 
pnnixNbrPeerPortEntry OBJECT-TYPE
        SYNTAX        PnnixNbrPeerPortEntry
	ACCESS    not-accessible
	STATUS	mandatory
        DESCRIPTION
            "An entry in the table, containing information about a port
             in the Hello state 2-Way Inside from a PNNI logical node in
             this switching system to a neighboring peer node."
        INDEX         { pnnixNodeIndex,
                        pnnixNbrPeerRemoteNodeId,
                        pnnixNbrPeerPortId
                         }
        ::= { pnnixNbrPeerPortTable 1 }
 
PnnixNbrPeerPortEntry ::=
        SEQUENCE {
--                pnnixNbrPeerPortId               PnnixPortId,
                pnnixNbrPeerPortId               INTEGER,
                pnnixNbrPeerPortFloodStatus      TruthValue
               }
 
pnnixNbrPeerPortId OBJECT-TYPE
--      SYNTAX        PnnixPortId
        SYNTAX        INTEGER
	ACCESS    not-accessible
	STATUS	mandatory
        DESCRIPTION
            "The port ID of a port to the neighboring peer that is in
             the Hello state 2-Way Inside."
        ::= { pnnixNbrPeerPortEntry 1 }
 
pnnixNbrPeerPortFloodStatus OBJECT-TYPE
        SYNTAX        TruthValue
	ACCESS    read-only
	STATUS	mandatory
        DESCRIPTION
            "Indicates whether the port is being used for transmission
             of flooding and database synchronization information to the
             neighboring peer."
        ::= { pnnixNbrPeerPortEntry 2 }
 
 
-- pnni SVCC-based routing control channel table
 
pnnixSvccRccTable OBJECT-TYPE
        SYNTAX        SEQUENCE OF PnnixSvccRccEntry
	ACCESS    not-accessible
	STATUS	mandatory
        DESCRIPTION
            "A table containing the attributes necessary to analyze the
             operation of the PNNI protocol on SVCC-based Routing
             Control Channels. This entire object is read-only,
             reflecting the fact that SVCC-based RCCs are established
             dynamically during operation of the PNNI protocol rather
             than configured."
--	REFERENCE "ATM Forum PNNI 1.0 Sections 5.5.6, 5.6.3.1"
        ::= { pnnixMIBObjects 12 }
 
pnnixSvccRccEntry OBJECT-TYPE
        SYNTAX        PnnixSvccRccEntry
	ACCESS    not-accessible
	STATUS	mandatory
        DESCRIPTION
            "An entry in the table, containing information about an
             SVCC-based RCC from a PNNI logical node in this switching
             system."
--	REFERENCE "ATM Forum PNNI 1.0 Sections 5.5.6, 5.6.3.1"
        INDEX         { pnnixNodeIndex,
                        pnnixSvccRccIndex }
        ::= { pnnixSvccRccTable 1 }
 
PnnixSvccRccEntry ::=
        SEQUENCE {
                pnnixSvccRccIndex            	PnnixSvccRccIndex,
                pnnixSvccRccVersion          	PnnixVersion,
                pnnixSvccRccHelloState       	PnnixHelloState,
                pnnixSvccRccRemoteNodeId     	PnnixNodeId,
                pnnixSvccRccRemoteAtmAddress     PnnixAtmAddr,
                pnnixSvccRccRcvHellos        	Counter,
                pnnixSvccRccXmtHellos        	Counter,
                pnnixSvccRccIfIndex          	InterfaceIndex,
                pnnixSvccRccVpi              	INTEGER,
                pnnixSvccRccVci              	INTEGER
                }
 
pnnixSvccRccIndex OBJECT-TYPE
        SYNTAX        PnnixSvccRccIndex
	ACCESS    not-accessible
	STATUS	mandatory
        DESCRIPTION
            "An index into the node's tables of SVCC-based RCCs."
        ::= { pnnixSvccRccEntry 1 }
 
pnnixSvccRccVersion OBJECT-TYPE
        SYNTAX        PnnixVersion
	ACCESS    read-only
	STATUS	mandatory
        DESCRIPTION
            "The version of the PNNI routing protocol used to exchange
             information with the neighbor node."
        ::= { pnnixSvccRccEntry 2 }
 
pnnixSvccRccHelloState OBJECT-TYPE
        SYNTAX        PnnixHelloState
	ACCESS    read-only
	STATUS	mandatory
        DESCRIPTION
            "The state of the Hello protocol exchange over the
             SVCC-based RCC.

             Note: the Down state indicates that the SVCC
             establishment is in progress."
        ::= { pnnixSvccRccEntry 3 }
 
pnnixSvccRccRemoteNodeId OBJECT-TYPE
        SYNTAX        PnnixNodeId
	ACCESS    read-only
	STATUS	mandatory
        DESCRIPTION
            "The remote node at which the SVCC-based RCC terminates."
        ::= { pnnixSvccRccEntry 4 }
 
pnnixSvccRccRemoteAtmAddress OBJECT-TYPE
        SYNTAX        PnnixAtmAddr
	ACCESS    read-only
	STATUS	mandatory
        DESCRIPTION
            "The ATM End System Address to which SVCC establishment is
             attempted."
        ::= { pnnixSvccRccEntry 5 }
 
pnnixSvccRccRcvHellos OBJECT-TYPE
        SYNTAX        Counter
	ACCESS    read-only
	STATUS	mandatory
        DESCRIPTION
            "A count of the number of Hello Packets received over this
             SVCC-based RCC."
        ::= { pnnixSvccRccEntry 6 }
 
pnnixSvccRccXmtHellos OBJECT-TYPE
        SYNTAX        Counter
	ACCESS    read-only
	STATUS	mandatory
        DESCRIPTION
            "A count of the number of Hello Packets transmitted over
             this SVCC-based RCC."
        ::= { pnnixSvccRccEntry 7 }
 
pnnixSvccRccIfIndex OBJECT-TYPE
        SYNTAX        InterfaceIndex
	ACCESS    read-only
	STATUS	mandatory
        DESCRIPTION
            "The interface from which the SVCC-based RCC leaves the
             switching system.  If the SVCC-based RCC has not yet been
             established, then this attribute takes the value of zero."
        ::= { pnnixSvccRccEntry 8 }
 
pnnixSvccRccVpi OBJECT-TYPE
        SYNTAX        INTEGER (0..4095)
	ACCESS    read-only
	STATUS	mandatory
        DESCRIPTION
            "The VPI used at the interface from which the SVCC-based RCC
             leaves the switching system.  If the SVCC-based RCC has not
             yet been established, then this attribute takes the value
             of zero "
        ::= { pnnixSvccRccEntry 9 }
 
pnnixSvccRccVci OBJECT-TYPE
        SYNTAX        INTEGER (0..65535)
	ACCESS    read-only
	STATUS	mandatory
        DESCRIPTION
            "The VCI used at the interface from which the SVCC-based RCC
             leaves the switching system.  If the SVCC-based RCC has not
             yet been established, then this attribute takes the value
             of zero "
        ::= { pnnixSvccRccEntry 10 }
 
 
-- PTSE table
 
pnnixPtseTable OBJECT-TYPE
        SYNTAX        SEQUENCE OF PnnixPtseEntry
	ACCESS    not-accessible
	STATUS	mandatory
        DESCRIPTION
            "The pnnixPtse object contains the attributes that describe
             the most recent instances of PTSEs in a node's topology
             database.  A concatenation of the Node Identifier of the
             local node that received the PTSE, the originating Node's
             Node Identifier and the PTSE Identifier are used to form
             the instance ID for an instance of this object."
--	REFERENCE "ATM Forum PNNI 1.0 Section 5.8.2"
        ::= { pnnixMIBObjects 13 }
 
pnnixPtseEntry OBJECT-TYPE
        SYNTAX        PnnixPtseEntry
	ACCESS    not-accessible
	STATUS	mandatory
        DESCRIPTION
            "An entry in the table, containing information about a PTSE
             in the topology database of a PNNI logical node in this
             switching system."
--	REFERENCE "ATM Forum PNNI 1.0 Section 5.8.2"
        INDEX         { pnnixNodeIndex,
                        pnnixPtseOriginatingNodeId,
                        pnnixPtseId }
        ::= { pnnixPtseTable 1 }
 
PnnixPtseEntry ::=
        SEQUENCE {
                pnnixPtseOriginatingNodeId       PnnixNodeId,
--              pnnixPtseId                      Gauge,
                pnnixPtseId                      INTEGER,
                pnnixPtseType                    INTEGER,
                pnnixPtseSequenceNum             Gauge,
                pnnixPtseChecksum                Gauge,
                pnnixPtseLifeTime                Gauge,
                pnnixPtseInfo                    OCTET STRING
                }
 
pnnixPtseOriginatingNodeId OBJECT-TYPE
        SYNTAX        PnnixNodeId
	ACCESS    not-accessible
	STATUS	mandatory
        DESCRIPTION
            "The Node Identifier of the node that originated the PTSE."
        ::= { pnnixPtseEntry 1 }
 
pnnixPtseId OBJECT-TYPE
--      SYNTAX        Gauge
        SYNTAX        INTEGER
	ACCESS    not-accessible
	STATUS	mandatory
        DESCRIPTION
            "The value of the PTSE Identifier assigned to the PTSE by
             its originator."
        ::= { pnnixPtseEntry 2 }
 
pnnixPtseType OBJECT-TYPE
        SYNTAX        INTEGER  {
                                other(1),
                                nodalStateParameters(96),
                                nodalInformation(97),
                                internalReachableAddresses(224),
                                exteriorReachableAddresses(256),
                                horizontalLinks(288),
                                uplinks(289)
                                }
	ACCESS    read-only
	STATUS	mandatory
        DESCRIPTION
            "The type of information contained in the PTSE."
        ::= { pnnixPtseEntry 3 }
 
pnnixPtseSequenceNum OBJECT-TYPE
        SYNTAX        Gauge
	ACCESS    read-only
	STATUS	mandatory
        DESCRIPTION
            "The sequence number of the instance of the PTSE as it
             appears in the local topology database."
        ::= { pnnixPtseEntry 4 }
 
pnnixPtseChecksum OBJECT-TYPE
        SYNTAX        Gauge
	ACCESS    read-only
	STATUS	mandatory
        DESCRIPTION
            "The value of the PTSE checksum as it appears in the local
             topology database."
        ::= { pnnixPtseEntry 5 }
 
pnnixPtseLifeTime OBJECT-TYPE
        SYNTAX        Gauge
--	UNITS         "seconds"
	ACCESS    read-only
	STATUS	mandatory
        DESCRIPTION
            "The value of the remaining lifetime for the given PTSE as
             it appears in the local topology database."
        ::= { pnnixPtseEntry 6 }
 
pnnixPtseInfo OBJECT-TYPE
        SYNTAX        OCTET STRING (SIZE(0..65535))
	ACCESS    read-only
	STATUS	mandatory
        DESCRIPTION
            "An unformatted hexadecimal dump of the PTSE contents in
             full.

             Note: If the size of the PTSE contents is larger than the
             maximum size of SNMP packets then this is truncated."
        ::= { pnnixPtseEntry 7 }
 
 
-- pnni map table
 
pnnixMapTable OBJECT-TYPE
        SYNTAX        SEQUENCE OF PnnixMapEntry
	ACCESS    not-accessible
	STATUS	mandatory
        DESCRIPTION
            "A table containing attributes necessary to find and analyze
             the operation of all links and nodes within the PNNI
             hierarchy, as seen from the perspective of a local node.
             An instance of a pnniMap Object describes a link in terms
             of a node at one end of the link.  Normally there will be
             two instances of the pnniMap object in the MIB for each
             horizontal link. The two instances provide information for
             Network management to map port identifiers from the nodes
             at both ends to the link between them.  A concatenation of
             the Local Node Index, Originating Node Identifier and
             Originating Port Identifier are used to form the instance
             ID for this object.

             This entire object is read-only, reflecting the fact that
             the map is discovered dynamically during operation of the
             PNNI protocol rather than configured."
        ::= { pnnixMIBObjects 14 }
 
pnnixMapEntry OBJECT-TYPE
        SYNTAX        PnnixMapEntry
	ACCESS    not-accessible
	STATUS	mandatory
        DESCRIPTION
            "An entry in the table, containing connectivity information
             about a node or link in the PNNI routing domain, as seen
             from the perspective of a PNNI logical node in this
             switching system."
        INDEX         { pnnixNodeIndex,
                        pnnixMapOriginatingNodeId,
                        pnnixMapOriginatingPortId,
                        pnnixMapIndex }
        ::= { pnnixMapTable 1 }
 
PnnixMapEntry ::=
        SEQUENCE {
                pnnixMapOriginatingNodeId        PnnixNodeId,
                pnnixMapOriginatingPortId        INTEGER,
--              pnnixMapOriginatingPortId        PnnixPortId,
                pnnixMapIndex                    INTEGER,
                pnnixMapType                     INTEGER,
                pnnixMapPeerGroupId              PnnixPeerGroupId,
                pnnixMapAggrToken                PnnixAggrToken,
                pnnixMapRemoteNodeId             PnnixNodeId,
                pnnixMapRemotePortId             PnnixPortId,
                pnnixMapVPCapability             TruthValue,
                pnnixMapPtseId                   Gauge,
                pnnixMapMetricsTag               PnnixMetricsTag
                }
 
pnnixMapOriginatingNodeId OBJECT-TYPE
        SYNTAX        PnnixNodeId
	ACCESS    not-accessible
	STATUS	mandatory
        DESCRIPTION
            "The node identifier of the node whose connectivity within
             itself or to other nodes is being described."
        ::= { pnnixMapEntry 1 }
 
pnnixMapOriginatingPortId OBJECT-TYPE
        SYNTAX        INTEGER
--      SYNTAX        PnnixPortId
	ACCESS    not-accessible
	STATUS	mandatory
        DESCRIPTION
            "The port identifier of the port as assigned by the
             originating node, to which the port is attached."
        ::= { pnnixMapEntry 2 }
 
pnnixMapIndex OBJECT-TYPE
        SYNTAX        INTEGER (0..65535)
	ACCESS    not-accessible
	STATUS	mandatory
        DESCRIPTION
            "An index into the set of link and nodal connectivity
             associated with the originating node and port.  This index
             is needed since there may be multiple entries for nodal
             connectivity from a specific node and port pair, in
             addition to any entry for a horizontal link or uplink."
        ::= { pnnixMapEntry 3 }
 
pnnixMapType OBJECT-TYPE
        SYNTAX        INTEGER {
                                horizontalLink(1),
                                uplink(2),
                                node(3)
                                }
	ACCESS    read-only
	STATUS	mandatory
        DESCRIPTION
            "The type of PNNI entity being described by this entry in
             the table."
        ::= { pnnixMapEntry 4 }
 
pnnixMapPeerGroupId OBJECT-TYPE
        SYNTAX        PnnixPeerGroupId
	ACCESS    read-only
	STATUS	mandatory
        DESCRIPTION
            "Identifies the peer group of the originating node."
        ::= { pnnixMapEntry 5 }
 
pnnixMapAggrToken OBJECT-TYPE
        SYNTAX        PnnixAggrToken
	ACCESS    read-only
	STATUS	mandatory
        DESCRIPTION
            "For horizontal links to/from LGNs and for uplinks, this
             attribute contains the derived aggregation token value for
             this link.  For nodes and for horizontal links between
             lowest-level nodes, this attribute is set to zero."
        ::= { pnnixMapEntry 6 }
 
pnnixMapRemoteNodeId OBJECT-TYPE
        SYNTAX        PnnixNodeId
	ACCESS    read-only
	STATUS	mandatory
        DESCRIPTION
            "For horizontal links and uplinks, this attribute contains
             the node identifier of the node at the other end of the
             link from the originating node.  If unknown, the PNNI
             protocol entity sets this attribute's value to (all)
             zero(s).  For nodes, this attribute's value is set to (all)
             zero(s)."
        ::= { pnnixMapEntry 7 }
 
pnnixMapRemotePortId OBJECT-TYPE
        SYNTAX        PnnixPortId
	ACCESS    read-only
	STATUS	mandatory
        DESCRIPTION
            "For horizontal links and uplinks, this attribute contains
             the port identifier of the port at the remote end of the
             link as assigned by the remote node.  If unknown, the PNNI
             protocol entity sets this attribute's value to zero.

             For nodes, this attribute contains the port identifier of
             the port at the other end of the spoke or bypass from the
             originating port.  When the originating port ID is zero, a
             value of zero indicates the default radius.  When the
             originating port ID is non-zero, a value of zero indicates
             the nodal nucleus."
        ::= { pnnixMapEntry 8 }
 
pnnixMapVPCapability OBJECT-TYPE
        SYNTAX        TruthValue
	ACCESS    read-only
	STATUS	mandatory
        DESCRIPTION
            "Indicates whether VPCs
             can be established across the PNNI entity being described
             by this entry in the pnnixMapTable."
        ::= { pnnixMapEntry 9 } 
 
pnnixMapPtseId OBJECT-TYPE
        SYNTAX        Gauge
	ACCESS    read-only
	STATUS	mandatory
        DESCRIPTION
            "The value of the PTSE Identifier for the PTSE being
             originated by the originating node which contains the
             information group(s) describing the PNNI entity."
        ::= { pnnixMapEntry 10 }
 
pnnixMapMetricsTag OBJECT-TYPE
        SYNTAX        PnnixMetricsTag (1..2147483647)
	ACCESS    read-only
	STATUS	mandatory
        DESCRIPTION
            "An arbitrary integer that is used to associate a set of
             traffic parameters that are always advertised together.
             Within this set, the parameters are distinguished by the
             service categories and direction to which a set of
             parameters apply."
        ::= { pnnixMapEntry 11 }

 
-- nodal map table

pnnixMapNodeTable OBJECT-TYPE
        SYNTAX        SEQUENCE OF PnnixMapNodeEntry
	ACCESS    not-accessible
	STATUS	mandatory
        DESCRIPTION
            "A list of nodes as seen from the perspective of a local
             node.  The pnnixMapNodeTable contains all information
             learned by the local node from nodal information PTSEs.
             This entire object is read-only, reflecting the fact that
             the map is discovered dynamically during operation of the
             PNNI protocol rather than configured."
        ::= { pnnixMIBObjects 15 }

pnnixMapNodeEntry OBJECT-TYPE
        SYNTAX        PnnixMapNodeEntry
	ACCESS    not-accessible
	STATUS	mandatory
        DESCRIPTION
            "An entry in the table, containing information about a node
             in the PNNI routing domain, as seen from the perspective of
             a logical node in this switching system."
        INDEX         { pnnixNodeIndex,
                        pnnixMapNodeId }
        ::= { pnnixMapNodeTable 1 }

PnnixMapNodeEntry ::=
        SEQUENCE {
                pnnixMapNodeId                   PnnixNodeId,
                pnnixMapNodePeerGroupId          PnnixPeerGroupId,
                pnnixMapNodeAtmAddress           PnnixAtmAddr,
                pnnixMapNodeRestrictedTransit    TruthValue,
                pnnixMapNodeComplexRep           TruthValue,
                pnnixMapNodeRestrictedBranching  TruthValue,
                pnnixMapNodeDatabaseOverload     TruthValue,
                pnnixMapNodeIAmLeader            TruthValue,
                pnnixMapNodeLeadershipPriority   INTEGER,
                pnnixMapNodePreferredPgl         PnnixNodeId,
                pnnixMapNodeParentNodeId         PnnixNodeId,
                pnnixMapNodeParentAtmAddress     PnnixAtmAddr,
                pnnixMapNodeParentPeerGroupId    PnnixPeerGroupId,
                pnnixMapNodeParentPglNodeId      PnnixNodeId
                }

pnnixMapNodeId OBJECT-TYPE
        SYNTAX        PnnixNodeId
	ACCESS    not-accessible
	STATUS	mandatory
        DESCRIPTION
            "Identifies the node whose nodal information is being
             described."
        ::= { pnnixMapNodeEntry 1 }

pnnixMapNodePeerGroupId OBJECT-TYPE
        SYNTAX        PnnixPeerGroupId
	ACCESS    read-only
	STATUS	mandatory
        DESCRIPTION
            "Identifies the peer group of the originating node."
        ::= { pnnixMapNodeEntry 2 }

pnnixMapNodeAtmAddress OBJECT-TYPE
        SYNTAX        PnnixAtmAddr
	ACCESS    read-only
	STATUS	mandatory
        DESCRIPTION
            "The ATM End System Address of the originating node."
        ::= { pnnixMapNodeEntry 3 }

pnnixMapNodeRestrictedTransit OBJECT-TYPE
        SYNTAX        TruthValue
	ACCESS    read-only
	STATUS	mandatory
        DESCRIPTION
            "Indicates whether the originating node is restricted to
             only allow support of SVCs originating or terminating at
             this node.  A value of `true' indicates that the transit
             capabilities are restricted, i.e., transit connections are
             not allowed, whereas a value of `false' indicates that
             transit connections are allowed.  This attribute reflects
             the setting of the restricted transit bit received in the
             nodal information PTSE of the originating node."
        ::= { pnnixMapNodeEntry 4 }

pnnixMapNodeComplexRep OBJECT-TYPE
        SYNTAX        TruthValue
	ACCESS    read-only
	STATUS	mandatory
        DESCRIPTION
            "Indicates whether the originating node uses the complex
             node representation.  If the value is `true', the spokes
             and bypasses that make up the complex node representation
             should be found in the pnnixMapTable.  This attribute
             reflects the setting of the nodal representation bit
             received in the nodal information PTSE of the originating
             node."
        ::= { pnnixMapNodeEntry 5 }

pnnixMapNodeRestrictedBranching  OBJECT-TYPE
        SYNTAX      TruthValue
	ACCESS  read-only
	STATUS	mandatory
        DESCRIPTION
            "Indicates whether the originating node is able to support
             additional branches.  If the value is 'false', then it can
             support additional branches.  This attribute reflects the
             setting of the restricted branching bit received in the
             nodal information PTSE of the originating node."
        ::= { pnnixMapNodeEntry 6 }

pnnixMapNodeDatabaseOverload OBJECT-TYPE
        SYNTAX        TruthValue
	ACCESS    read-only
	STATUS	mandatory
        DESCRIPTION
            "Indicates whether the originating node is currently
             operating in topology database overload state.  This 
             attribute has the same value as the Non-transit for PGL
             Election bit in the nodal information group originated by
             this node."
        ::= { pnnixMapNodeEntry 7 }

pnnixMapNodeIAmLeader OBJECT-TYPE
        SYNTAX        TruthValue
	ACCESS    read-only
	STATUS	mandatory
        DESCRIPTION
            "Indicates whether the originating node claims to be peer
             group leader of its peer group.  This attribute reflects
             the setting of the 'I am Leader' bit received in the nodal
             information PTSE of the originating node."
        ::= { pnnixMapNodeEntry 8 }

pnnixMapNodeLeadershipPriority OBJECT-TYPE
        SYNTAX        INTEGER (0..255)
	ACCESS    read-only
	STATUS	mandatory
        DESCRIPTION
            "The Leadership priority value advertised by the originating
             node."
        ::= { pnnixMapNodeEntry 9 }

pnnixMapNodePreferredPgl OBJECT-TYPE
        SYNTAX        PnnixNodeId
	ACCESS    read-only
	STATUS	mandatory
        DESCRIPTION
            "Identifies the node which the originating node believes
             should be or is peer group leader of its peer group.  If
             the originating node has not chosen a Preferred PGL, this
             attribute's value is set to (all) zero(s)."
        ::= { pnnixMapNodeEntry 10 }

pnnixMapNodeParentNodeId OBJECT-TYPE
        SYNTAX        PnnixNodeId
	ACCESS    read-only
	STATUS	mandatory
        DESCRIPTION
            "When the originating node is a peer group leader, indicates
             the node ID of the parent LGN.  If the originating node is
             not peer group leader of its peer group, this attribute's
             value is set to (all) zero(s)."
        ::= { pnnixMapNodeEntry 11 }

pnnixMapNodeParentAtmAddress OBJECT-TYPE
        SYNTAX        PnnixAtmAddr
	ACCESS    read-only
	STATUS	mandatory
        DESCRIPTION
            "When the originating node is a peer group leader, indicates
             the ATM address of the parent LGN.  If the originating node
             is not peer group leader of its peer group, this
             attribute's value is set to (all) zero(s)."
        ::= { pnnixMapNodeEntry 12 }

pnnixMapNodeParentPeerGroupId OBJECT-TYPE
        SYNTAX        PnnixPeerGroupId
	ACCESS    read-only
	STATUS	mandatory
        DESCRIPTION
            "When the originating node is a peer group leader, indicates
             the node's parent peer group ID.  If the originating node
             is not peer group leader of its peer group, this
             attribute's value is set to (all) zero(s)."
        ::= { pnnixMapNodeEntry 13 }

pnnixMapNodeParentPglNodeId OBJECT-TYPE
        SYNTAX        PnnixNodeId
	ACCESS    read-only
	STATUS	mandatory
        DESCRIPTION
            "When the originating node is a peer group leader,
             identifies the node elected as peer group leader of the
             parent peer group.  If the originating node is not peer
             group leader of its peer group, this attribute's value is
             set to (all) zero(s)."
        ::= { pnnixMapNodeEntry 14 }

 
-- address map table
 
pnnixMapAddrTable OBJECT-TYPE
        SYNTAX        SEQUENCE OF PnnixMapAddrEntry
	ACCESS    not-accessible
	STATUS	mandatory
        DESCRIPTION
            "The pnnixMapAddr MIB Object contains a list of all reachable
             addresses from each node visible to the local node.  The
             Local Node Index, Advertising Node ID, Advertised Port ID,
             Reachable Address, and Address prefix length are combined
             to form an instance ID for this object.  The entire object
             is read-only, reflecting the fact that reachable addresses
             are discovered during dynamic operation of the PNNI
             protocol rather than configured."
        ::= { pnnixMIBObjects 16 }
 
pnnixMapAddrEntry OBJECT-TYPE
        SYNTAX        PnnixMapAddrEntry
	ACCESS    not-accessible
	STATUS	mandatory
        DESCRIPTION
            "An entry in the table, containing information about an 
             address prefix reachable from a node in the PNNI routing
             domain, as seen from the perspective of a PNNIX logical node
             in this switching system."
        INDEX         { pnnixNodeIndex,
                        pnnixMapAddrAdvertisingNodeId,
                        pnnixMapAddrAdvertisedPortId,
                        pnnixMapAddrIndex }
        ::= { pnnixMapAddrTable 1 }
 
PnnixMapAddrEntry ::=
        SEQUENCE {
                pnnixMapAddrAdvertisingNodeId    PnnixNodeId,
--              pnnixMapAddrAdvertisedPortId     PnnixPortId,
                pnnixMapAddrAdvertisedPortId     INTEGER,
                pnnixMapAddrIndex                INTEGER,
                pnnixMapAddrAddress              AtmAddrPrefix,
                pnnixMapAddrPrefixLength         PnnixPrefixLength
                }
 
pnnixMapAddrAdvertisingNodeId OBJECT-TYPE
        SYNTAX        PnnixNodeId
	ACCESS    not-accessible
	STATUS	mandatory
        DESCRIPTION
            "The node ID of a node advertising reachability to the
             address prefix."
        ::= { pnnixMapAddrEntry 1 }
 
pnnixMapAddrAdvertisedPortId OBJECT-TYPE
--      SYNTAX        PnnixPortId
        SYNTAX        INTEGER
	ACCESS    not-accessible
	STATUS	mandatory
        DESCRIPTION
            "The port identifier used from the advertising node to reach
             the given address prefix."
        ::= { pnnixMapAddrEntry 2 }
 
pnnixMapAddrIndex OBJECT-TYPE
        SYNTAX        INTEGER (1..2147483647)
	ACCESS    not-accessible
	STATUS	mandatory
        DESCRIPTION
            "An arbitrary index that is used to enumerate all of the
             addresses advertised by the specified node."
        ::= { pnnixMapAddrEntry 3 }
 
pnnixMapAddrAddress OBJECT-TYPE
        SYNTAX        AtmAddrPrefix
	ACCESS    read-only
	STATUS	mandatory
        DESCRIPTION
            "The value of the ATM End System Address prefix."
        ::= { pnnixMapAddrEntry 4 }
 
pnnixMapAddrPrefixLength OBJECT-TYPE
        SYNTAX        PnnixPrefixLength
	ACCESS    read-only
	STATUS	mandatory
        DESCRIPTION
            "The Prefix length to be applied to the ATM End System
             Address prefix."
        ::= { pnnixMapAddrEntry 5 }
 
 
-- TNS map table
 
pnnixMapTnsTable OBJECT-TYPE
        SYNTAX        SEQUENCE OF PnnixMapTnsEntry
	ACCESS    not-accessible
	STATUS	mandatory
        DESCRIPTION
            "A list of all reachable transit networks from each node
             visible to the local node.  The Local Node Index,
             Advertising Node ID, Advertised Port ID, Transit Network
             Type, Transit Network Plan, and Transit Network ID are
             combined to form an instance ID for this object. The entire
             object is read-only, reflecting the fact that reachable
             transit networks are discovered during dynamic operation of
             the PNNI protocol rather than configured.."
        ::= { pnnixMIBObjects 17 }
 
pnnixMapTnsEntry OBJECT-TYPE
        SYNTAX        PnnixMapTnsEntry
	ACCESS    not-accessible
	STATUS	mandatory
        DESCRIPTION
            "An entry in the table, containing information about a 
             transit network reachable from a node in the PNNI routing
             domain, as seen from the perspective of a PNNI logical node
             in this switching system."
        INDEX         { pnnixNodeIndex,
                        pnnixMapTnsAdvertisingNodeId,
                        pnnixMapTnsAdvertisedPortId,
                        pnnixMapTnsType,
                        pnnixMapTnsPlan,
                        pnnixMapTnsId }
        ::= { pnnixMapTnsTable 1 }
 
PnnixMapTnsEntry ::=
        SEQUENCE {
                pnnixMapTnsAdvertisingNodeId     INTEGER,
--              pnnixMapTnsAdvertisedPortId      PnnixPortId,
                pnnixMapTnsAdvertisedPortId      INTEGER,
--              pnnixMapTnsAdvertisedPortId      PnnixPortId,
                pnnixMapTnsType                  TnsType,
                pnnixMapTnsPlan                  TnsPlan,
                pnnixMapTnsId                    DisplayString
                }
 
pnnixMapTnsAdvertisingNodeId OBJECT-TYPE
--      SYNTAX        PnnixNodeId
        SYNTAX        INTEGER
	ACCESS    not-accessible
	STATUS	mandatory
        DESCRIPTION
            "The node ID of a node advertising reachability to the
             transit network."
        ::= { pnnixMapTnsEntry 1 }
 
pnnixMapTnsAdvertisedPortId OBJECT-TYPE
        SYNTAX        INTEGER
--      SYNTAX        PnnixPortId
	ACCESS    not-accessible
	STATUS	mandatory
        DESCRIPTION
            "The port identifier used from the advertising node to reach
             the given transit network."
        ::= { pnnixMapTnsEntry 2 }
 
pnnixMapTnsType OBJECT-TYPE
        SYNTAX        TnsType
	ACCESS    not-accessible
	STATUS	mandatory
        DESCRIPTION
            "The type of network identification used for this transit
             network."
        ::= { pnnixMapTnsEntry 3 }
 
pnnixMapTnsPlan OBJECT-TYPE
        SYNTAX        TnsPlan
	ACCESS    not-accessible
	STATUS	mandatory
        DESCRIPTION
            "The network identification plan according to which network
             identification has been assigned."
        ::= { pnnixMapTnsEntry 4 }
 
pnnixMapTnsId OBJECT-TYPE
        SYNTAX        DisplayString
	ACCESS    read-only
	STATUS	mandatory
        DESCRIPTION
            "The value of the transit network identifier."
        ::= { pnnixMapTnsEntry 5 }
 
 
 
-- pnnix metrics table
 
pnnixMetricsTable OBJECT-TYPE
        SYNTAX        SEQUENCE OF PnnixMetricsEntry
	ACCESS    not-accessible
	STATUS	mandatory
        DESCRIPTION
            "This entity's table of PNNI parameters either associated
             with a PNNI entity or for the connectivity between a PNNI
             node and a reachable address or transit network."
--	REFERENCE "ATM Forum PNNI 1.0 Section 5.8.1.1.3"
        ::= { pnnixMIBObjects 18 }
 
pnnixMetricsEntry OBJECT-TYPE
        SYNTAX        PnnixMetricsEntry
	ACCESS    not-accessible
	STATUS	mandatory
        DESCRIPTION
            "A set of parameters that applies to the connectivity from a
             certain node and port to another node or port or to one or
             more reachable address prefixes and/or transit networks,
             for one (or more) particular service category(s).  Note
             that there can be multiple sets of parameters with the same
             tag, in which case all sets apply to the specified
             connectivity."
--	REFERENCE "ATM Forum PNNI 1.0 Section 5.8.1.1.3"
        INDEX         { pnnixNodeIndex,
                        pnnixMetricsTag,
                        pnnixMetricsDirection,
                        pnnixMetricsIndex }
        ::= { pnnixMetricsTable 1 }
 
PnnixMetricsEntry ::=
        SEQUENCE {
                pnnixMetricsTag          PnnixMetricsTag,
                pnnixMetricsDirection    INTEGER,
                pnnixMetricsIndex        INTEGER,
                pnnixMetricsClasses      INTEGER,
                pnnixMetricsGcacClp      ClpType,
                pnnixMetricsAdminWeight  Gauge,
                pnnixMetrics1            Gauge,
                pnnixMetrics2            Gauge,
                pnnixMetrics3            Gauge,
                pnnixMetrics4            Gauge,
                pnnixMetrics5            Gauge,
                pnnixMetrics6            Gauge,
                pnnixMetrics7            Gauge,
                pnnixMetrics8            Gauge,
                pnnixMetricsRowStatus    INTEGER
                }
 
 
pnnixMetricsTag OBJECT-TYPE
        SYNTAX        PnnixMetricsTag (1..2147483647)
	ACCESS    not-accessible
	STATUS	mandatory
        DESCRIPTION
            "An arbitrary integer that is used to associate a set of
             traffic parameters that are always advertised together.
             Within this set, the parameters are distinguished by the
             service categories and direction to which a set of
             parameters apply."
        ::= { pnnixMetricsEntry 1 }
 
 
pnnixMetricsDirection OBJECT-TYPE
        SYNTAX        INTEGER { incoming(1), outgoing(2) }
	ACCESS    not-accessible
	STATUS	mandatory
        DESCRIPTION
            "The direction, with respect to the advertising node, in
             which the parameters in this entry apply."
        ::= { pnnixMetricsEntry 2 }
 
 
pnnixMetricsIndex OBJECT-TYPE
        SYNTAX        INTEGER (1..2147483647)
	ACCESS    not-accessible
	STATUS	mandatory
        DESCRIPTION
            "An index into the set of parameters associated with the
             given tag and direction."
        ::= { pnnixMetricsEntry 3 }
 
 
pnnixMetricsClasses OBJECT-TYPE
        SYNTAX        INTEGER(0..31)
	ACCESS	read-write
	STATUS	mandatory
        DESCRIPTION
            "The service categories to which this set of parameters
             applies.  This is an integer used as a bit mask with each
             bit that is set representing a single service category for
             which the resources indicated are available.  Bit 5
             represents CBR, bit 4 represents real-time VBR, bit 3
             represents non-real-time VBR, bit 2 represents ABR, and
             bit 1 (LSB) represents UBR."
--	REFERENCE "ATM Forum Traffic Management 4.0 Section 2, ATM Forum 
--	PNNI 1.0 Section 5.8.1.1.3.1"
        ::= { pnnixMetricsEntry 4 }
 
pnnixMetricsGcacClp OBJECT-TYPE
        SYNTAX        ClpType
	ACCESS	read-write
	STATUS	mandatory
        DESCRIPTION
            "Indicates whether the advertised GCAC parameters apply for
             CLP=0 traffic or for CLP=0+1 traffic."
--	REFERENCE "ATM Forum PNNI 1.0 Sections 5.8.1.1.3.1, 5.13.4.1"
        ::= { pnnixMetricsEntry 5 }
 
 
pnnixMetricsAdminWeight OBJECT-TYPE
        SYNTAX        Gauge
	ACCESS	read-write
	STATUS	mandatory
        DESCRIPTION
            "The administrative weight from the advertising node to the
             remote end of the PNNI entity or to the reachable address
             or transit network, for the specified service categories.

             If this metric is not used, its value should be set to
             0xFFFFFFFF."
--	REFERENCE "ATM Forum PNNI 1.0 Section 5.8.1.1.3.4"
        --DEFVAL     { 5040 }
        ::= { pnnixMetricsEntry 6 }
 
 
pnnixMetrics1 OBJECT-TYPE
        SYNTAX        Gauge
	ACCESS	read-write
	STATUS	mandatory
        DESCRIPTION
            "An alternate routing parameter from the advertising node to
             the remote end of the PNNI entity or to the reachable
             address or transit network, for the specified service
             categories.
 
             For information learned from PNNI nodes, this is the
             maximum cell rate in cells per second for the specified
             service categories.

             If this parameter is not used, its value should be set to
             0xFFFFFFFF."
--	REFERENCE "ATM Forum PNNI 1.0 Section 5.8.1.1.3.7"
        --DEFVAL { 'FFFFFFFF'h }
        ::= { pnnixMetricsEntry 7 }
 
 
pnnixMetrics2 OBJECT-TYPE
        SYNTAX        Gauge
	ACCESS	read-write
	STATUS	mandatory
        DESCRIPTION
            "An alternate routing parameter from the advertising node to
             the remote end of the PNNI entity or to the reachable
             address or transit network, for the specified service
             categories.

             For information learned from PNNI nodes, this is the
             available cell rate in cells per second for the specified
             service categories.

             If this parameter is not used, its value should be set to
             0xFFFFFFFF."
--	REFERENCE "ATM Forum PNNI 1.0 Section 5.8.1.1.3.8"
        --DEFVAL { 'FFFFFFFF'h }
        ::= { pnnixMetricsEntry 8 }
 
 
pnnixMetrics3 OBJECT-TYPE
        SYNTAX        Gauge
	ACCESS	read-write
	STATUS	mandatory
        DESCRIPTION
            "An alternate routing parameter from the advertising node to
             the remote end of the PNNI entity or to the reachable
             address or transit network, for the specified service
             categories.
 
             For information learned from PNNI nodes, this is the
             maximum cell transfer delay in microseconds for the
             specified service categories.

             If this parameter is not used, its value should be set to
             0xFFFFFFFF."
--	REFERENCE "ATM Forum PNNI 1.0 Section 5.8.1.1.3.3"
        --DEFVAL { 'FFFFFFFF'h }
        ::= { pnnixMetricsEntry 9 }
 
 
pnnixMetrics4 OBJECT-TYPE
        SYNTAX        Gauge
	ACCESS	read-write
	STATUS	mandatory
        DESCRIPTION
            "An alternate routing parameter from the advertising node to
             the remote end of the PNNI entity or to the reachable
             address or transit network, for the specified service
             categories.
 
             For information learned from PNNI nodes, this is the cell
             delay variation in microseconds for the specified service
             categories.

             If this parameter is not used, its value should be set to
             0xFFFFFFFF."
--	REFERENCE "ATM Forum PNNI 1.0 Section 5.8.1.1.3.2"
        --DEFVAL { 'FFFFFFFF'h }
        ::= { pnnixMetricsEntry 10 }
 
 
pnnixMetrics5 OBJECT-TYPE
        SYNTAX        Gauge
	ACCESS	read-write
	STATUS	mandatory
        DESCRIPTION
            "An alternate routing parameter from the advertising node to
             the remote end of the PNNI entity or to the reachable
             address or transit network, for the specified service
             categories.

             For PNNI, this is the cell loss ratio for CLP=0 traffic for
             the specified service categories.  The cell loss ratio
             value is computed as 10**(-n) where 'n' is the value
             returned in this variable.

             If this parameter is not used, its value should be set to
             0xFFFFFFFF."
--	REFERENCE "ATM Forum PNNI 1.0 Section 5.8.1.1.3.5"
        --DEFVAL { 'FFFFFFFF'h }
        ::= { pnnixMetricsEntry 11 }

pnnixMetrics6 OBJECT-TYPE
        SYNTAX        Gauge
	ACCESS	read-write
	STATUS	mandatory
        DESCRIPTION
            "An alternate routing parameter from the advertising node to
             the remote end of the PNNI entity or to the reachable
             address or transit network, for the specified service
             categories.

             For PNNI, this is the cell loss ratio for CLP=0+1 traffic 
             for the specified service categories.  The cell loss ratio
             value is computed as 10**(-n) where 'n' is the value
             returned in this variable.

             If this parameter is not used, its value should be set to
             0xFFFFFFFF."
--	REFERENCE "ATM Forum PNNI 1.0 Section 5.8.1.1.3.6"
        --DEFVAL { 'FFFFFFFF'h }
        ::= { pnnixMetricsEntry 12 }
 
 
pnnixMetrics7 OBJECT-TYPE
        SYNTAX        Gauge
	ACCESS	read-write
	STATUS	mandatory
        DESCRIPTION
            "An alternate routing parameter from the advertising node to
             the remote end of the PNNI entity or to the reachable
             address or transit network, for the specified service
             categories.

             For information learned from PNNI nodes, this is the cell
             rate margin in cells per second for the specified service
             categories.

             If this parameter is not used, its value should be set to
             0xFFFFFFFF."
--	REFERENCE "ATM Forum PNNI 1.0 Section 5.8.1.1.3.9"
        --DEFVAL { 'FFFFFFFF'h }
        ::= { pnnixMetricsEntry 13 }
 
 
pnnixMetrics8 OBJECT-TYPE
        SYNTAX        Gauge
	ACCESS	read-write
	STATUS	mandatory
        DESCRIPTION
            "An alternate routing parameter from the advertising node to
             the remote end of the PNNI entity or to the reachable
             address or transit network, for the specified service
             categories.

             For information learned from PNNI nodes, this is the
             variance factor in units of 2**(-8) for the specified
             service categories.

             If this parameter is not used, its value should be set to
             0xFFFFFFFF."
--	REFERENCE "ATM Forum PNNI 1.0 Section 5.8.1.1.3.10"
        --DEFVAL { 'FFFFFFFF'h }
        ::= { pnnixMetricsEntry 14 }
 
 
pnnixMetricsRowStatus OBJECT-TYPE
        SYNTAX        INTEGER {
								create (1),
								modify (2),
								delete (3),
								active (4),
								notActive (5)
							  }
	ACCESS	read-write
	STATUS	mandatory
        DESCRIPTION
            "To create, delete, activate and de-activate a set of
             metrics."
        ::= { pnnixMetricsEntry 15 }
 
  
--
--  PNNI Routing Tables
--
 
pnnixRoutingGroup OBJECT IDENTIFIER ::= { pnnixMIBObjects 19 }
pnnixRouteBaseGroup OBJECT IDENTIFIER ::= { pnnixRoutingGroup 1 }
 
pnnixRouteNodeNumber OBJECT-TYPE
        SYNTAX        Gauge
	ACCESS    read-only
	STATUS	mandatory
        DESCRIPTION
            "The number of current precalculated PNNI routes to PNNI
             nodes that are not invalid."
        ::= { pnnixRouteBaseGroup 1 }
 
 
pnnixRouteAddrNumber OBJECT-TYPE
        SYNTAX        Gauge
	ACCESS    read-only
	STATUS	mandatory
        DESCRIPTION
            "The number of current PNNI routes from nodes in the PNNI
             routing domain to addresses and transit networks that are
             not invalid."
        ::= { pnnixRouteBaseGroup 2 }
 
 
-- Table of routes to other nodes

pnnixRouteNodeTable OBJECT-TYPE
        SYNTAX        SEQUENCE OF PnnixRouteNodeEntry
	ACCESS    not-accessible
	STATUS	mandatory
        DESCRIPTION
            "This entity's PNNI Routing table (of routes to other
             nodes)."
        ::= { pnnixRoutingGroup 2 }
 
pnnixRouteNodeEntry OBJECT-TYPE
        SYNTAX        PnnixRouteNodeEntry
	ACCESS    not-accessible
	STATUS	mandatory
        DESCRIPTION
            "A particular route to a particular destination node, under
             a particular policy."
        INDEX         { pnnixNodeIndex,
                        pnnixRouteNodeClass,
                        pnnixRouteNodeDestNodeId,
                        pnnixRouteNodeDTL }
        ::= { pnnixRouteNodeTable 1 }
 
PnnixRouteNodeEntry ::=
        SEQUENCE {
                pnnixRouteNodeClass         ServiceCategory,
                pnnixRouteNodeDestNodeId    PnnixNodeId,
                pnnixRouteNodeDTL           INTEGER,
                pnnixRouteNodeDestPortId    PnnixPortId,
                pnnixRouteNodeProto         INTEGER,
                pnnixRouteNodeTimeStamp     DisplayString,
                pnnixRouteNodeInfo          OBJECT IDENTIFIER,
                pnnixRouteNodeGcacClp       ClpType,
                pnnixRouteNodeFwdMetricAW   Gauge,
                pnnixRouteNodeFwdMetric1    Gauge,
                pnnixRouteNodeFwdMetric2    Gauge,
                pnnixRouteNodeFwdMetric3    Gauge,
                pnnixRouteNodeFwdMetric4    Gauge,
                pnnixRouteNodeFwdMetric5    Gauge,
                pnnixRouteNodeFwdMetric6    Gauge,
                pnnixRouteNodeFwdMetric7    Gauge, 
                pnnixRouteNodeFwdMetric8    Gauge,
                pnnixRouteNodeBwdMetricAW   Gauge,
                pnnixRouteNodeBwdMetric1    Gauge,
                pnnixRouteNodeBwdMetric2    Gauge,
                pnnixRouteNodeBwdMetric3    Gauge,
                pnnixRouteNodeBwdMetric4    Gauge,
                pnnixRouteNodeBwdMetric5    Gauge,
                pnnixRouteNodeBwdMetric6    Gauge,
                pnnixRouteNodeBwdMetric7    Gauge,
                pnnixRouteNodeBwdMetric8    Gauge,
                pnnixRouteNodeVPCapability  TruthValue,
                pnnixRouteNodeStatus        INTEGER
                }
 
pnnixRouteNodeClass OBJECT-TYPE
        SYNTAX        ServiceCategory
	ACCESS    not-accessible
	STATUS	mandatory
        DESCRIPTION
            "Indicates the service category with which this forwarding
             table entry is associated."
        ::= { pnnixRouteNodeEntry 1 }
 
pnnixRouteNodeDestNodeId OBJECT-TYPE
        SYNTAX        PnnixNodeId
	ACCESS    not-accessible
	STATUS	mandatory
        DESCRIPTION
            "The node ID of the destination node to which this route
             proceeds, and at which the DTL stack for this route
             terminates."
        ::= { pnnixRouteNodeEntry 2 }
 
pnnixRouteNodeDTL OBJECT-TYPE
        SYNTAX        INTEGER (1..2147483647)
	ACCESS    not-accessible
	STATUS	mandatory
        DESCRIPTION
            "The index into the owning PNNI node's DTL table of the DTL
             stack that goes with this route."
        ::= { pnnixRouteNodeEntry 3 }

pnnixRouteNodeDestPortId OBJECT-TYPE
        SYNTAX        PnnixPortId
	ACCESS	read-write
	STATUS	mandatory
        DESCRIPTION
            "The port ID of the destination node at which the route
             terminates.  A port ID of zero indicates the node nucleus.
             When the destination node is represented by the simple node
             representation, this value should be set to zero."
        --DEFVAL { 0 }
        ::= { pnnixRouteNodeEntry 4 }

 
pnnixRouteNodeProto OBJECT-TYPE
        SYNTAX        INTEGER {
                                other(1), -- not specified
                                local(2), -- e.g. ILMI
                                mgmt(3), -- configured by management,
                                       -- for example by SNMP or console
                                        -- the following are all dynamic
                                        -- routing protocols
                                pnni(4) -- ATM Forum PNNI
                                }
	ACCESS    read-only
	STATUS	mandatory
        DESCRIPTION
            "The routing mechanism via which this route was learned."
        ::= { pnnixRouteNodeEntry 5 }
 
pnnixRouteNodeTimeStamp OBJECT-TYPE
        SYNTAX        DisplayString
	ACCESS    read-only
	STATUS	mandatory
        DESCRIPTION
            "The time at which this  route  was last  updated  or
             otherwise  determined  to be correct.  Note that no
             semantics of  `too  old' can  be implied except through
             knowledge of the routing  protocol  by  which  the route
             was learned."
        ::= { pnnixRouteNodeEntry 6 }
 
pnnixRouteNodeInfo OBJECT-TYPE
        SYNTAX        OBJECT IDENTIFIER
	ACCESS	read-write
	STATUS	mandatory
        DESCRIPTION
            "A reference to MIB definitions specific to the particular
             routing protocol which is responsible for this route, as
             determined by the value specified in the route's
             pnnixRouteNodeProto value.  If this information is not
             present, its value should be set to the OBJECT IDENTIFIER
             { 0 0 }."
        --DEFVAL { { 0 0 } }
        ::= { pnnixRouteNodeEntry 7 }
 
pnnixRouteNodeGcacClp OBJECT-TYPE
        SYNTAX        ClpType
	ACCESS	read-write
	STATUS	mandatory
        DESCRIPTION
            "For PNNI, indicates whether any advertised GCAC parameters
             apply for CLP=0 traffic or for CLP=0+1 traffic."
        ::= { pnnixRouteNodeEntry 8 }
 
pnnixRouteNodeFwdMetricAW OBJECT-TYPE
        SYNTAX        Gauge
	ACCESS	read-write
	STATUS	mandatory
        DESCRIPTION
            "The cumulative administrative weight calculated for the
             forward direction of this route.  If this metric is not
             used, its value should be set to 0xFFFFFFFF."
--	REFERENCE "ATM Forum PNNI 1.0 Section 5.8.1.1.3.4"
        --DEFVAL { 'FFFFFFFF'h }
        ::= { pnnixRouteNodeEntry 9 }
 
pnnixRouteNodeFwdMetric1 OBJECT-TYPE
        SYNTAX        Gauge
	ACCESS	read-write
	STATUS	mandatory
        DESCRIPTION
            "An alternate routing parameter for the forward direction of
             this route.
 
             For information learned from PNNI nodes, this is the 
             maximum possible cell rate (in cells per second) for the
             forward direction of the route.

             If this parameter is not used, its value should be set to
             0xFFFFFFFF."
--	REFERENCE "ATM Forum PNNI 1.0 Section 5.8.1.1.3.7"
        --DEFVAL { 'FFFFFFFF'h }
        ::= { pnnixRouteNodeEntry 10 }
 
pnnixRouteNodeFwdMetric2 OBJECT-TYPE
        SYNTAX        Gauge
	ACCESS	read-write
	STATUS	mandatory
        DESCRIPTION
            "An alternate routing parameter for the forward direction of
             this route.
 
             For information learned from PNNI nodes, this is the 
             Available cell rate (in cells per second) for the forward
             direction of the route.  Further information on available
             bandwidth may be obtainable by reference to the nodal
             advertisements of the nodes in the path.

             If this parameter is not used, its value should be set to
             0xFFFFFFFF."
--	REFERENCE "ATM Forum PNNI 1.0 Section 5.8.1.1.3.8"
        --DEFVAL { 'FFFFFFFF'h }
        ::= { pnnixRouteNodeEntry 11 }
 
pnnixRouteNodeFwdMetric3 OBJECT-TYPE
        SYNTAX        Gauge
	ACCESS	read-write
	STATUS	mandatory
        DESCRIPTION
            "An alternate routing parameter for the forward direction of
             this route.
 
             For information learned from PNNI nodes, this is the 
             cumulative Maximum Cell Transfer Delay (in microseconds)
             for the forward direction of the route.

             If this parameter is not used, its value should be set to
             0xFFFFFFFF."
--	REFERENCE "ATM Forum PNNI 1.0 Section 5.8.1.1.3.3"
        --DEFVAL { 'FFFFFFFF'h }
        ::= { pnnixRouteNodeEntry 12 }
 
pnnixRouteNodeFwdMetric4 OBJECT-TYPE
        SYNTAX        Gauge
	ACCESS	read-write
	STATUS	mandatory
        DESCRIPTION
            "An alternate routing parameter for the forward direction of
             this route.
 
             For information learned from PNNI nodes, this is the 
             cumulative Cell Delay Variation (in microseconds) for the
             forward direction of the route.

             If this parameter is not used, its value should be set to
             0xFFFFFFFF."
--	REFERENCE "ATM Forum PNNI 1.0 Section 5.8.1.1.3.2"
        --DEFVAL { 'FFFFFFFF'h }
        ::= { pnnixRouteNodeEntry 13 }
 
pnnixRouteNodeFwdMetric5 OBJECT-TYPE
        SYNTAX        Gauge
	ACCESS	read-write
	STATUS	mandatory
        DESCRIPTION
            "An alternate routing parameter for the forward direction of
             this route.
 
             For information learned from PNNI nodes, this is the 
             cumulative Cell Loss Ratio for CLP=0 traffic for the 
             forward direction of the route. The cell loss ratio value
             is computed as 10**(-n) where 'n' is the value returned in
             this variable.

             If this parameter is not used, its value should be set to
             0xFFFFFFFF."
--	REFERENCE "ATM Forum PNNI 1.0 Section 5.8.1.1.3.5"
        --DEFVAL { 'FFFFFFFF'h }
        ::= { pnnixRouteNodeEntry 14 }

pnnixRouteNodeFwdMetric6 OBJECT-TYPE
        SYNTAX        Gauge
	ACCESS	read-write
	STATUS	mandatory
        DESCRIPTION
            "An alternate routing parameter for the forward direction of
             this route.
 
             For information learned from PNNI nodes, this is the 
             cumulative Cell Loss Ratio for CLP=0+1 traffic for the 
             forward direction of the route. The cell loss ratio value
             is computed as 10**(-n) where 'n' is the value returned in
             this variable.

             If this parameter is not used, its value should be set to
             0xFFFFFFFF."
--	REFERENCE "ATM Forum PNNI 1.0 Section 5.8.1.1.3.6"
        --DEFVAL { 'FFFFFFFF'h }
        ::= { pnnixRouteNodeEntry 15 }
 
 
pnnixRouteNodeFwdMetric7 OBJECT-TYPE
        SYNTAX        Gauge
	ACCESS	read-write
	STATUS	mandatory
        DESCRIPTION
            "An alternate routing parameter for the forward direction of
             this route.
 
             For information learned from PNNI nodes, this is the Cell
             Rate Margin (in cells per second) for the forward direction
             of the route.

             If this parameter is not used, its value should be set to
             0xFFFFFFFF."
--	REFERENCE "ATM Forum PNNI 1.0 Section 5.8.1.1.3.9"
        --DEFVAL { 'FFFFFFFF'h }
        ::= { pnnixRouteNodeEntry 16 }
 
pnnixRouteNodeFwdMetric8 OBJECT-TYPE
        SYNTAX        Gauge
	ACCESS	read-write
	STATUS	mandatory
        DESCRIPTION
            "An alternate routing parameter for the forward direction of
             this route.
 
             For information learned from PNNI nodes, this is the 
             Variance Factor (in units of 2**(-8)) for the forward
             direction of the route.

             If this parameter is not used, its value should be set to
             0xFFFFFFFF."
--	REFERENCE "ATM Forum PNNI 1.0 Section 5.8.1.1.3.10"
        --DEFVAL { 'FFFFFFFF'h }
        ::= { pnnixRouteNodeEntry 17 }
 
pnnixRouteNodeBwdMetricAW OBJECT-TYPE
        SYNTAX        Gauge
	ACCESS	read-write
	STATUS	mandatory
        DESCRIPTION
            "The administrative weight calculated for the backward
             direction of this route.  If this metric is not used, its
             value should be set to 0xFFFFFFFF."
--	REFERENCE "ATM Forum PNNI 1.0 Section 5.8.1.1.3.4"
        --DEFVAL { 'FFFFFFFF'h }
        ::= { pnnixRouteNodeEntry 18 }
 
pnnixRouteNodeBwdMetric1 OBJECT-TYPE
        SYNTAX        Gauge
	ACCESS	read-write
	STATUS	mandatory
        DESCRIPTION
            "An alternate routing parameter for the backward direction
             of this route.
 
             For information learned from PNNI nodes, this is the 
             maximum possible cell rate (in cells per second) for the
             backward direction of the route.

             If this parameter is not used, its value should be set to
             0xFFFFFFFF."
--	REFERENCE "ATM Forum PNNI 1.0 Section 5.8.1.1.3.7"
        --DEFVAL { 'FFFFFFFF'h }
        ::= { pnnixRouteNodeEntry 19 }
 
pnnixRouteNodeBwdMetric2 OBJECT-TYPE
        SYNTAX        Gauge
	ACCESS	read-write
	STATUS	mandatory
        DESCRIPTION
            "An alternate routing parameter for the backward direction
             of this route.
 
             For information learned from PNNI nodes, this is the 
             Available cell rate (in cells per second) for the backward
             direction of the route.  Further information on available
             bandwidth may be obtainable by reference to the nodal
             advertisements of the nodes in the path.

             If this parameter is not used, its value should be set to
             0xFFFFFFFF."
--	REFERENCE "ATM Forum PNNI 1.0 Section 5.8.1.1.3.8"
        --DEFVAL { 'FFFFFFFF'h }
        ::= { pnnixRouteNodeEntry 20 }
 
pnnixRouteNodeBwdMetric3 OBJECT-TYPE
        SYNTAX        Gauge
	ACCESS	read-write
	STATUS	mandatory
        DESCRIPTION
            "An alternate routing parameter for the backward direction
             of this route.
 
             For information learned from PNNI nodes, this is the 
             cumulative Maximum Cell Transfer Delay (in microseconds)
             for the backward direction of the route.

             If this parameter is not used, its value should be set to
             0xFFFFFFFF."
--	REFERENCE "ATM Forum PNNI 1.0 Section 5.8.1.1.3.3"
        --DEFVAL { 'FFFFFFFF'h }
        ::= { pnnixRouteNodeEntry 21 }
 
pnnixRouteNodeBwdMetric4 OBJECT-TYPE
        SYNTAX        Gauge
	ACCESS	read-write
	STATUS	mandatory
        DESCRIPTION
            "An alternate routing parameter for the backward direction
             of this route.
 
             For information learned from PNNI nodes, this is the 
             cumulative Cell Delay Variation (in microseconds) for the
             backward direction of the route.

             If this parameter is not used, its value should be set to
             0xFFFFFFFF."
--	REFERENCE "ATM Forum PNNI 1.0 Section 5.8.1.1.3.2"
        --DEFVAL { 'FFFFFFFF'h }
        ::= { pnnixRouteNodeEntry 22 }
 
pnnixRouteNodeBwdMetric5 OBJECT-TYPE
        SYNTAX        Gauge
	ACCESS	read-write
	STATUS	mandatory
        DESCRIPTION
            "An alternate routing parameter for the backward direction
             of this route.
 
             For information learned from PNNI nodes, this is the 
             cumulative Cell Loss Ratio for CLP=0 traffic for the
             backward direction of the route. The cell loss ratio value
             is computed as 10**(-n) where 'n' is the value returned in
             this variable.

             If  this parameter is not used, its value should be set to
             0xFFFFFFFF."
--	REFERENCE "ATM Forum PNNI 1.0 Section 5.8.1.1.3.5"
        --DEFVAL { 'FFFFFFFF'h }
        ::= { pnnixRouteNodeEntry 23 }

pnnixRouteNodeBwdMetric6 OBJECT-TYPE
        SYNTAX        Gauge
	ACCESS	read-write
	STATUS	mandatory
        DESCRIPTION
            "An alternate routing parameter for the backward direction
             of this route.
 
             For information learned from PNNI nodes, this is the 
             cumulative Cell Loss Ratio for CLP=0+1 traffic for the
             backward direction of the route. The cell loss ratio value
             is computed as 10**(-n) where 'n' is the value returned in
             this variable.

             If  this parameter is not used, its value should be set to
             0xFFFFFFFF."
--	REFERENCE "ATM Forum PNNI 1.0 Section 5.8.1.1.3.6"
        --DEFVAL { 'FFFFFFFF'h }
        ::= { pnnixRouteNodeEntry 24 }
 
 
pnnixRouteNodeBwdMetric7 OBJECT-TYPE
        SYNTAX        Gauge
	ACCESS	read-write
	STATUS	mandatory
        DESCRIPTION
            "An alternate routing parameter for the backward direction
             of this route.
 
             For information learned from PNNI nodes, this is the Cell
             Rate Margin (in cells per second) for the backward
             direction of the route.

             If this parameter is not used, its value should be set to
             0xFFFFFFFF."
--	REFERENCE "ATM Forum PNNI 1.0 Section 5.8.1.1.3.9"
        --DEFVAL { 'FFFFFFFF'h }
        ::= { pnnixRouteNodeEntry 25 }
 
pnnixRouteNodeBwdMetric8 OBJECT-TYPE
        SYNTAX        Gauge
	ACCESS	read-write
	STATUS	mandatory
        DESCRIPTION
            "An alternate routing parameter for the backward direction
             of this route.
 
             For information learned from PNNI nodes, this is the 
             Variance Factor (in units of 2**(-8)) for the backward
             direction of the route.

             If this parameter is not used, its value should be set to
             0xFFFFFFFF."
--	REFERENCE "ATM Forum PNNI 1.0 Section 5.8.1.1.3.10"
        --DEFVAL { 'FFFFFFFF'h }
        ::= { pnnixRouteNodeEntry 26 }
 
pnnixRouteNodeVPCapability OBJECT-TYPE
        SYNTAX        TruthValue
	ACCESS	read-write
	STATUS	mandatory
        DESCRIPTION
            "This attribute indicates whether a VPC setup on this route
             is possible."
        ::= { pnnixRouteNodeEntry 27 }
 
pnnixRouteNodeStatus OBJECT-TYPE
        SYNTAX        INTEGER {
								create (1),
								modify (2),
								delete (3),
								active (4),
								notActive (5)
							  }
	ACCESS	read-write
	STATUS	mandatory
        DESCRIPTION
            "The row status variable, used according to row installation
             and removal conventions."
        ::= { pnnixRouteNodeEntry 28 }


-- Table of DTL stacks for routes to other nodes
 
pnnixDTLTable OBJECT-TYPE
        SYNTAX        SEQUENCE OF PnnixDTLEntry
	ACCESS    not-accessible
	STATUS	mandatory
        DESCRIPTION
            "The set of all DTL stacks used for the pre-computed routes
             maintained by this managed entity."
        ::= { pnnixRoutingGroup 3 }
 
pnnixDTLEntry OBJECT-TYPE
        SYNTAX        PnnixDTLEntry
	ACCESS    not-accessible
	STATUS	mandatory
        DESCRIPTION
            "A segment of a DTL stack.  The complete DTL stack is formed
             by traversing the rows of the table for which the
             pnniDTLIndex is the same.  Level transitions are indicated
             using the pnnixDLTLinkType column."
        INDEX {
                pnnixNodeIndex,
                pnnixDTLIndex,
                pnnixDTLEntryIndex
                }
        ::= { pnnixDTLTable 1 }
 
PnnixDTLEntry ::=
        SEQUENCE {
                pnnixDTLIndex      	INTEGER,
                pnnixDTLEntryIndex 	INTEGER,
                pnnixDTLNodeId     	PnnixNodeId,
                pnnixDTLPortId     	PnnixPortId,
                pnnixDTLLinkType   	INTEGER,
                pnnixDTLStatus     	INTEGER
                }
 
pnnixDTLIndex OBJECT-TYPE
        SYNTAX        INTEGER (1..65535)
	ACCESS    not-accessible
	STATUS	mandatory
        DESCRIPTION
            "The index in the node's DTL table of this DTL stack."
        ::= { pnnixDTLEntry 1 }
 
pnnixDTLEntryIndex OBJECT-TYPE
        SYNTAX        INTEGER (1..200)
	ACCESS    not-accessible
	STATUS	mandatory
        DESCRIPTION
            "The index in the current DTL stack of this entry."
        ::= { pnnixDTLEntry 2 }
 
pnnixDTLNodeId OBJECT-TYPE
        SYNTAX        PnnixNodeId
	ACCESS	read-write
	STATUS	mandatory
        DESCRIPTION
            "The node which is this hop in the DTL stack."
        ::= { pnnixDTLEntry 3 }
 
pnnixDTLPortId OBJECT-TYPE
        SYNTAX        PnnixPortId
	ACCESS	read-write
	STATUS	mandatory
        DESCRIPTION
            "The port from the pnnixDTLNodeId to use as the exit.  If the
             DTL stack does not care, this is coded as zero."
        ::= { pnnixDTLEntry 4 }
 
pnnixDTLLinkType OBJECT-TYPE
        SYNTAX        INTEGER {
                                invalid    (1), -- An invalid link
                                horizontal (2), -- A normal link within
                                            -- the containing peer group
                                uplink     (3), -- A link going up a
                                                -- level
                                last       (4) -- The last entry in the
                                               -- DTL stack
                                }
	ACCESS	read-write
	STATUS	mandatory
        DESCRIPTION
            "The type of link out from this node (pnnixDTLNodeId).  This
             is well defined even if the specific port is not
             specified."
        ::= { pnnixDTLEntry 5 }
 
pnnixDTLStatus OBJECT-TYPE
        SYNTAX        INTEGER {
								create (1),
								modify (2),
								delete (3),
								active (4),
								notActive (5)
							  }
	ACCESS	read-write
	STATUS	mandatory
        DESCRIPTION
            "The row status variable, used according to row installation
             and removal conventions."
        ::= { pnnixDTLEntry 6 }
 
 
-- Table of routes from nodes to reachable addresses
 
pnnixRouteAddrTable OBJECT-TYPE
        SYNTAX        SEQUENCE OF PnnixRouteAddrEntry
	ACCESS    not-accessible
	STATUS	mandatory
        DESCRIPTION
            "A table containing all the attributes necessary to
             determine what the PNNI entity believes is reachable in
             terms of ATM End System Addresses and to determine which
             nodes are advertising this reachability.  This table is
             also used to configure static routes to reachable address
             prefixes.  The local node index that received the
             reachability information, reachable address, address prefix
             length, and an index that distinguishes between multiple
             listings of connectivity to a given address prefix from a
             given local node are combined to form an instance ID for
             this object.."
--	REFERENCE "ATM Forum PNNI 1.0 Section 5.8.1.3"
        ::= { pnnixRoutingGroup 4 }
 
pnnixRouteAddrEntry OBJECT-TYPE
        SYNTAX        PnnixRouteAddrEntry
	ACCESS    not-accessible
	STATUS	mandatory
        DESCRIPTION
            "An entry in the table, containing information about a
             reachable address prefix."
--	REFERENCE "ATM Forum PNNI 1.0 Section 5.8.1.3"
        INDEX         { pnnixNodeIndex,
                        pnnixRouteAddrAddress,
                        pnnixRouteAddrPrefixLength,
                        pnnixRouteAddrIndex }
        ::= { pnnixRouteAddrTable 1 } 
PnnixRouteAddrEntry ::=
        SEQUENCE {
                pnnixRouteAddrAddress            	AtmAddrPrefix,
                pnnixRouteAddrPrefixLength       	PnnixPrefixLength,
                pnnixRouteAddrIndex              	INTEGER,
                pnnixRouteAddrIfIndex            	InterfaceIndex,
                pnnixRouteAddrAdvertisingNodeId  	PnnixNodeId,
                pnnixRouteAddrAdvertisedPortId   	PnnixPortId,
                pnnixRouteAddrType               	INTEGER,
                pnnixRouteAddrProto              	INTEGER,
                pnnixRouteAddrPnniScope          	PnnixLevel,
                pnnixRouteAddrVPCapability       	TruthValue,
                pnnixRouteAddrMetricsTag         	PnnixMetricsTag,
                pnnixRouteAddrPtseId             	Gauge,
                pnnixRouteAddrOriginateAdvertisement     TruthValue,
                pnnixRouteAddrInfo               	OBJECT IDENTIFIER,
                pnnixRouteAddrOperStatus         	INTEGER,
                pnnixRouteAddrTimeStamp          	DisplayString,
                pnnixRouteAddrRowStatus          	INTEGER
                }
pnnixRouteAddrAddress OBJECT-TYPE
        SYNTAX        AtmAddrPrefix
	ACCESS    not-accessible
	STATUS	mandatory
        DESCRIPTION
            "The value of the ATM End System Address prefix."
        ::= { pnnixRouteAddrEntry 1 }
 
pnnixRouteAddrPrefixLength OBJECT-TYPE
        SYNTAX        PnnixPrefixLength
	ACCESS    not-accessible
	STATUS	mandatory
        DESCRIPTION
            "The prefix length to be applied to the ATM End System
             Address prefix."
        ::= { pnnixRouteAddrEntry 2 }
 
pnnixRouteAddrIndex OBJECT-TYPE
        SYNTAX        INTEGER (1..65535)
	ACCESS    not-accessible
	STATUS	mandatory
        DESCRIPTION
            "An index into the set of listings of connectivity to a
             given address prefix from a given local node.
             In our implementation we allow the range of 1-5 for each
             type of QOS class."
        ::= { pnnixRouteAddrEntry 3 }

pnnixRouteAddrIfIndex OBJECT-TYPE
        SYNTAX        InterfaceIndex
	ACCESS	read-write
	STATUS	mandatory
        DESCRIPTION
            "The local interface over which the reachable address can be
             reached.  The value zero indicates an unknown interface or
             reachability through a remote node.
 
             This object may only have a non-zero value if the value of
             the corresponding instance of pnniRouteAddrProto is other
             than 'pnni', pnnixRouteAddrType is other than 'reject', and
             the node identified by pnnixRouteAddrAdvertisingNodeId is
             instantiated within this switching system."
        ::= { pnnixRouteAddrEntry 4 }
 
pnnixRouteAddrAdvertisingNodeId OBJECT-TYPE
        SYNTAX        PnnixNodeId
	ACCESS	read-write
	STATUS	mandatory
        DESCRIPTION
            "The node ID of a node advertising reachability to the
             address prefix.  If the local node index is zero, then the
             advertising node ID must be set to all zeros."
        ::= { pnnixRouteAddrEntry 5 }
pnnixRouteAddrAdvertisedPortId OBJECT-TYPE
        SYNTAX        PnnixPortId
	ACCESS	read-write
	STATUS	mandatory
        DESCRIPTION
            "The port identifier used from the advertising node to reach
             the given address prefix."
        --DEFVAL { 0 }
        ::= { pnnixRouteAddrEntry 6 }
 
pnnixRouteAddrType OBJECT-TYPE
        SYNTAX        INTEGER {
                                other(1), -- not specified by this MIB
                                reject(2), -- route which discards
                                           -- traffic
                                internal(3),
                                exterior(4)
                                }
	ACCESS	read-write
	STATUS	mandatory
        DESCRIPTION
            "The type (e.g. internal or exterior) of reachability from
             the advertising node to the address prefix.
 
             Reject(2) refers to an address prefix which, if matched,
             indicates that the message should be discarded as
             unreachable. This is used in some protocols as a means of
             correctly aggregating routes."
--	REFERENCE "ATM Forum PNNI 1.0 Section 5.8.1.3"
        --DEFVAL { exterior }
        ::= { pnnixRouteAddrEntry 7 }
 
pnnixRouteAddrProto OBJECT-TYPE
        SYNTAX        INTEGER {
                                other(1), -- not specified
                                local(2), -- e.g. ILMI
                                mgmt(3), -- configured by management,
                                       -- for example by SNMP or console
                                        -- the following are all dynamic
                                        -- routing protocols
                                pnni(4) -- ATM Forum PNNI
                                }
	ACCESS    read-only
	STATUS	mandatory
        DESCRIPTION
            "The routing mechanism via which the connectivity from the
             advertising node to the reachable address prefix was
             learned."
        ::= { pnnixRouteAddrEntry 8 }
 

pnnixRouteAddrPnniScope OBJECT-TYPE
        SYNTAX        PnnixLevel
	ACCESS	read-write
	STATUS	mandatory
        DESCRIPTION
            "The PNNIX scope of advertisement (i.e. level of PNNI
             hierarchy) of the reachability from the advertising node to
             the address prefix."
--	REFERENCE "ATM Forum PNNI 1.0 Sections 5.3.6, 5.9.1"
        ::= { pnnixRouteAddrEntry 9 }
 
pnnixRouteAddrVPCapability OBJECT-TYPE
        SYNTAX        TruthValue
	ACCESS	read-write
	STATUS	mandatory
        DESCRIPTION
            "Indicates whether VPCs can be established from the
             advertising node to the reachable address prefix."
--	REFERENCE "ATM Forum PNNI 1.0 Section 5.14.9.1 Table 5-34"
        ::= { pnnixRouteAddrEntry 10 }
 
pnnixRouteAddrMetricsTag OBJECT-TYPE
        SYNTAX        PnnixMetricsTag
	ACCESS	read-write
	STATUS	mandatory
        DESCRIPTION
            "The index into the pnnixMetricsTable for the traffic
             parameter values that apply for the connectivity from the
             advertising node to the reachable address prefix.  There
             will be one or more entries in the pnnixMetricsTable whose
             first instance identifier matches the value of this
             variable.
 
             If there are no parameters associated with this reachable
             address prefix then the distinguished value zero is used."
        --DEFVAL { 0 }
        ::= { pnnixRouteAddrEntry 11 }
 
pnnixRouteAddrPtseId OBJECT-TYPE
        SYNTAX        Gauge
	ACCESS    read-only
	STATUS	mandatory
        DESCRIPTION
            "For reachable addresses learned via PNNI, this attribute
             contains the value of the PTSE Identifier for the PTSE
             being originated by the originating node which contains the
             information group(s) describing the reachable address.  For
             reachable addresses learned by means other than PNNI, this
             attribute is set to zero."
--	REFERENCE "ATM Forum PNNI 1.0 Section 5.8.2"
        ::= { pnnixRouteAddrEntry 12 }
 
pnnixRouteAddrOriginateAdvertisement OBJECT-TYPE
        SYNTAX        TruthValue
	ACCESS	read-write
	STATUS	mandatory
        DESCRIPTION
            "Whether or not the reachable address specified by this
             entry is to be advertised by the local node into its PNNI
             routing domain.
 
             This object may only take on the value 'true' when the
             value of the corresponding instance of pnnixRouteAddrProto
             is other than 'pnni'."
        --DEFVAL { true }
        ::= { pnnixRouteAddrEntry 13 }
 
pnnixRouteAddrInfo OBJECT-TYPE
        SYNTAX        OBJECT IDENTIFIER
	ACCESS	read-write
	STATUS	mandatory
        DESCRIPTION
            "A reference to MIB definitions specific to the particular
             routing protocol which is responsible for this reachable
             address prefix, as determined by the value specified in the
             route's pnnixRouteAddrProto value.  If this information is
             not present, its value should be set to the OBJECT
             IDENTIFIER { 0 0 }."
        --DEFVAL { { 0 0 } }
        ::= { pnnixRouteAddrEntry 14 }
 
pnnixRouteAddrOperStatus OBJECT-TYPE
        SYNTAX        INTEGER {
                                inactive(1),
                                active(2), -- i.e. reachability to this
                                           -- prefix exists and is not
                                           -- being advertised in PNNI
                                advertised(3)
                                }
	ACCESS    read-only
	STATUS	mandatory
        DESCRIPTION
            "Indicates whether the reachable address prefix is
             operationally valid and whether it is being advertised by
             this node."
        ::= { pnnixRouteAddrEntry 15 }

pnnixRouteAddrTimeStamp OBJECT-TYPE
        SYNTAX        DisplayString
	ACCESS    read-only
	STATUS	mandatory
        DESCRIPTION
            "Indicates when the connectivity from the advertising node
             to the reachable address prefix became known to the local
             node."
        ::= { pnnixRouteAddrEntry 16 }
 
pnnixRouteAddrRowStatus OBJECT-TYPE
        SYNTAX        INTEGER {
								create (1),
								modify (2),
								delete (3),
								active (4),
								notActive (5)
							  }
	ACCESS	read-write
	STATUS	mandatory
        DESCRIPTION
            "To create, delete, activate and de-activate a reachable
             address prefix."
        ::= { pnnixRouteAddrEntry 17 }
 

-- Table of routes from nodes to reachable transit networks
 
pnnixRouteTnsTable OBJECT-TYPE
        SYNTAX        SEQUENCE OF PnnixRouteTnsEntry
	ACCESS    not-accessible
	STATUS	mandatory
        DESCRIPTION
            "A table containing all the attributes necessary to
             determine what transit networks the PNNI entity believes
             are reachable and to determine which nodes are advertising
             this reachability.  This table is also used to add static
             routes to reachable transit networks.  The local node index
             which received the reachability information, type of
             network identification, network identification plan,
             transit network identifier, and an index that distinguishes
             between multiple listings of connectivity to a given
             transit network from a given local node are combined to
             form an instance ID for this object."
--	REFERENCE "ATM Forum PNNI 1.0 Section 5.8.1.3.2"
        ::= { pnnixRoutingGroup 5 }
 
pnnixRouteTnsEntry OBJECT-TYPE
        SYNTAX        PnnixRouteTnsEntry
	ACCESS    not-accessible
	STATUS	mandatory
        DESCRIPTION
            "An entry in the table, containing information about a
             reachable transit network."
--	REFERENCE "ATM Forum PNNI 1.0 Section 5.8.1.3.2"
        INDEX         { pnnixNodeIndex,
                        pnnixRouteTnsType,
                        pnnixRouteTnsPlan,
                        pnnixRouteTnsId,
                        pnnixRouteTnsIndex }
        ::= { pnnixRouteTnsTable 1 }
 
PnnixRouteTnsEntry ::=
        SEQUENCE {
                pnnixRouteTnsType                	TnsType,
                pnnixRouteTnsPlan                	TnsPlan,
                pnnixRouteTnsId                  	DisplayString,
                pnnixRouteTnsIndex               	INTEGER,
                pnnixRouteTnsIfIndex             	InterfaceIndex,
                pnnixRouteTnsAdvertisingNodeId   	PnnixNodeId,
                pnnixRouteTnsAdvertisedPortId    	PnnixPortId,
                pnnixRouteTnsRouteType           	INTEGER,
                pnnixRouteTnsProto               	INTEGER,
                pnnixRouteTnsPnniScope           	PnnixLevel,
                pnnixRouteTnsVPCapability        	TruthValue,
                pnnixRouteTnsMetricsTag          	PnnixMetricsTag,
                pnnixRouteTnsPtseId              	Gauge,
                pnnixRouteTnsOriginateAdvertisement      TruthValue,
                pnnixRouteTnsInfo                	OBJECT IDENTIFIER,
                pnnixRouteTnsOperStatus          	INTEGER,
                pnnixRouteTnsTimeStamp           	DisplayString,
                pnnixRouteTnsRowStatus           	INTEGER
                }
 
pnnixRouteTnsType OBJECT-TYPE
        SYNTAX        TnsType
	ACCESS    not-accessible
	STATUS	mandatory
        DESCRIPTION
            "The type of network identification used for this transit
             network."
        ::= { pnnixRouteTnsEntry 1 }
 
pnnixRouteTnsPlan OBJECT-TYPE
        SYNTAX        TnsPlan
	ACCESS    not-accessible
	STATUS	mandatory
        DESCRIPTION
            "The network identification plan according to which network
             identification has been assigned."
        ::= { pnnixRouteTnsEntry 2 }
 
pnnixRouteTnsId OBJECT-TYPE
        SYNTAX        DisplayString
	ACCESS    not-accessible
	STATUS	mandatory
        DESCRIPTION
            "The value of the transit network identifier."
        ::= { pnnixRouteTnsEntry 3 }
 
pnnixRouteTnsIndex OBJECT-TYPE
        SYNTAX        INTEGER (1..65535)
	ACCESS    not-accessible
	STATUS	mandatory
        DESCRIPTION
            "An index into the set of listings of connectivity to a
             given transit network from a given local node.
             In our implementation we allow the range of 1-5 for each
             type of QOS class."
        ::= { pnnixRouteTnsEntry 4 }

pnnixRouteTnsIfIndex OBJECT-TYPE
        SYNTAX        InterfaceIndex
	ACCESS	read-write
	STATUS	mandatory
        DESCRIPTION
            "The local interface over which the transit network can be
             reached.  The value zero indicates an unknown interface or
             reachability through a remote node.

             This object may only have a non-zero value if the value of
             the corresponding instance of pnnixRouteTnsProto is other
             than 'pnni' and the node identified by
             pnnixRouteTnsAdvertisingNodeId is instantiated within this
             switching system."
        ::= { pnnixRouteTnsEntry 5 }
 
pnnixRouteTnsAdvertisingNodeId OBJECT-TYPE
        SYNTAX        PnnixNodeId
	ACCESS	read-write
	STATUS	mandatory
        DESCRIPTION
            "The node ID of a node advertising reachability to the
             transit network.  If the local node index is zero, then the
             advertising node ID must also be set to zero."
        ::= { pnnixRouteTnsEntry 6 }
pnnixRouteTnsAdvertisedPortId OBJECT-TYPE
        SYNTAX        PnnixPortId
	ACCESS	read-write
	STATUS	mandatory
        DESCRIPTION
            "The port identifier used from the advertising node to
             reach the given transit network."
        --DEFVAL { 0 }
        ::= { pnnixRouteTnsEntry 7 }
 
pnnixRouteTnsRouteType OBJECT-TYPE
        SYNTAX        INTEGER {
                                other(1), -- not specified by this MIB
                                exterior(4)
                                }
	ACCESS	read-write
	STATUS	mandatory
        DESCRIPTION
            "The type (e.g. exterior or other) of reachability from the
             advertising node to the transit network."
--	REFERENCE "ATM Forum PNNI 1.0 Section 5.8.1.3"
        --DEFVAL { exterior }
        ::= { pnnixRouteTnsEntry 8 }
 
pnnixRouteTnsProto OBJECT-TYPE
        SYNTAX        INTEGER {
                                other(1), -- not specified
                                local(2), -- e.g. ILMI
                                mgmt(3), -- configured by management,
                                       -- for example by SNMP or console
                                        -- the following are all dynamic
                                        -- routing protocols
                                pnni(4) -- ATM Forum PNNI
                                }
	ACCESS    read-only
	STATUS	mandatory
        DESCRIPTION
            "The routing mechanism via which the connectivity from the
             advertising node to the transit network was learned."
        ::= { pnnixRouteTnsEntry 9 }
 

pnnixRouteTnsPnniScope OBJECT-TYPE
        SYNTAX        PnnixLevel
	ACCESS	read-write
	STATUS	mandatory
        DESCRIPTION
            "The PNNI scope of advertisement (i.e. level of PNNI
             hierarchy) of the reachability from the advertising node to
             the transit network."
--	REFERENCE "ATM Forum PNNI 1.0 Section 5.3.6"
        ::= { pnnixRouteTnsEntry 10 }
 
pnnixRouteTnsVPCapability OBJECT-TYPE
        SYNTAX        TruthValue
	ACCESS	read-write
	STATUS	mandatory
        DESCRIPTION
            "Indicates whether VPCs can be established from the
             advertising node to the reachable transit network."
--	REFERENCE "ATM Forum PNNI 1.0 Section 5.14.9.1 Table 5-34"
        ::= { pnnixRouteTnsEntry 11 }
 
pnnixRouteTnsMetricsTag OBJECT-TYPE
        SYNTAX        PnnixMetricsTag
	ACCESS	read-write
	STATUS	mandatory
        DESCRIPTION
            "The index into the pnnixMetricsTable for the traffic
             parameter values that apply for the connectivity from the
             advertising node to the transit network.  There will be one
             or more entries in the pnnixMetricsTable whose first
             instance identifier matches the value of this variable.
 
             If there are no parameters associated with this transit
             network then the distinguished value zero is used."
        --DEFVAL { 0 }
        ::= { pnnixRouteTnsEntry 12 }
 
pnnixRouteTnsPtseId OBJECT-TYPE
        SYNTAX        Gauge
	ACCESS    read-only
	STATUS	mandatory
        DESCRIPTION
            "For reachable transit networks learned via PNNI, this
             attribute contains the value of the PTSE Identifier for the
             PTSE being originated by the originating node which
             contains the information group(s) describing the transit
             network.  For reachable transit networks learned by means
             other than PNNI, this attribute is set to zero."
--	REFERENCE "ATM Forum PNNI 1.0 Section 5.8.2"
        ::= { pnnixRouteTnsEntry 13 }
 
pnnixRouteTnsOriginateAdvertisement OBJECT-TYPE
        SYNTAX        TruthValue
	ACCESS	read-write
	STATUS	mandatory
        DESCRIPTION
            "Whether or not the transit network specified by this entry
             is to be advertised by the local node into its PNNI routing
             domain.
 
             This object may only take on the value 'true' when the
             value of the corresponding instance of pnniRouteNodeProto
             is other than 'pnni'."
        --DEFVAL { true }
        ::= { pnnixRouteTnsEntry 14 }
 
pnnixRouteTnsInfo OBJECT-TYPE
        SYNTAX        OBJECT IDENTIFIER
	ACCESS	read-write
	STATUS	mandatory
        DESCRIPTION
            "A reference to MIB definitions specific to the particular
             routing protocol which is responsible for this transit
             network, as determined by the value specified in the
             route's pnnixRouteTnsProto value.  If this information is
             not present, its value should be set to the OBJECT
             IDENTIFIER { 0 0 }."
        --DEFVAL { { 0 0 } }
        ::= { pnnixRouteTnsEntry 15 }
 
pnnixRouteTnsOperStatus OBJECT-TYPE
        SYNTAX        INTEGER {
                                inactive(1),
                                active(2), -- i.e. reachability to this
                                        -- transit network exists and is
                                        -- not being advertised in PNNI
                                advertised(3)
                                }
	ACCESS    read-only
	STATUS	mandatory
        DESCRIPTION
            "Indicates whether the reachable transit network is
             operationally valid and whether it is being advertised by
             this node."
        ::= { pnnixRouteTnsEntry 16 }

pnnixRouteTnsTimeStamp OBJECT-TYPE
        SYNTAX        DisplayString
	ACCESS    read-only
	STATUS	mandatory
        DESCRIPTION
            "Indicates how long the connectivity from the advertising
             node to the reachable transit network has been known to the
             local node."
        ::= { pnnixRouteTnsEntry 17 }
 
pnnixRouteTnsRowStatus OBJECT-TYPE
        SYNTAX        INTEGER {
								create (1),
								modify (2),
								delete (3),
								active (4),
								notActive (5)
							  }
	ACCESS	read-write
	STATUS	mandatory
        DESCRIPTION
            "To create, delete, activate and de-activate a reachable
             transit network."
        ::= { pnnixRouteTnsEntry 18 }
 
 

-- ILMI Adjacencies 

pnniIAdjMIBObjects OBJECT IDENTIFIER ::= { pnnixMIB 3 }



-- The adjacency group - there's actually a MIB for the ILMI registered 
--    addresses but that is used exlusively by the switch and end station
--    functions.

pnnixIAdjGroup OBJECT IDENTIFIER ::= { pnniIAdjMIBObjects 1 }

pnnixNumIAdj OBJECT-TYPE                           
        SYNTAX        Counter
        ACCESS        read-only
        STATUS        mandatory
        DESCRIPTION
            "The number of adjacencies registered via ILMI in PNNIs
             lowest nodes adjacency table in this switching system."
        ::= { pnnixIAdjGroup 1 }


-- ILMI Adjacency table
 
pnnixIAdjTable OBJECT-TYPE
        SYNTAX        SEQUENCE OF PnnixIAdjEntry
        ACCESS        not-accessible
	STATUS        mandatory
        DESCRIPTION
            "The pnnixIAdjTable stores records of adjacncies which ILMI
             has registered with the lowest level PNNI node in this 
             network.
 
             There is a single row in this table for each adjacency which
             ILMI has registered."
        ::= { pnnixIAdjGroup 2 }
 
pnnixIAdjEntry OBJECT-TYPE
        SYNTAX        PnnixIAdjEntry
        ACCESS        not-accessible
	STATUS	      mandatory
        DESCRIPTION
            "An entry in the table, containing information about a PNNI
             logical node in this switching system."
        INDEX         { pnnixIadjIndex }
        ::= { pnnixIAdjTable 1 }
 
PnnixIAdjEntry ::=
        SEQUENCE {
                pnnixIadjIndex                  INTEGER,
                pnnixIAdjAtmAddress             PnnixAtmAddr,
                pnnixIAdjSlot                   INTEGER,
                pnnixIAdjPort                   INTEGER,
                pnnixIAdjInst                   INTEGER,
                pnnixIAdjCsmPPort               INTEGER,
                pnnixIAdjAdvertised             TruthValue,
                pnnixIAdjSummarized             TruthValue,
                pnnixIAdjLearned                DisplayString
                }

pnnixIadjIndex OBJECT-TYPE
        SYNTAX     INTEGER
	ACCESS     not-accessible
	STATUS	   mandatory
        DESCRIPTION
            "A value assigned to an ILMI client registered via ILMI in this 
             switching system that uniquely identifies it in the PNNI ILMI
             adjacency table."
        ::= { pnnixIAdjEntry 1 }
 
pnnixIAdjAtmAddress OBJECT-TYPE
        SYNTAX     PnnixAtmAddr
	ACCESS	   read-only
	STATUS	   mandatory
        DESCRIPTION
            "This adjacency's ATM End System Address."
        ::= { pnnixIAdjEntry 2 }
 
pnnixIAdjSlot OBJECT-TYPE
        SYNTAX     INTEGER
	ACCESS	   read-only
	STATUS	   mandatory
        DESCRIPTION
            "The slot in which this adjacency is physically connected to this
             switching system."
        ::= { pnnixIAdjEntry 3 }
 
pnnixIAdjPort OBJECT-TYPE
        SYNTAX     INTEGER
	ACCESS	   read-only
	STATUS	   mandatory
        DESCRIPTION
            "The port in the slot which this adjacency is physically 
             connected to this switching system."
        ::= { pnnixIAdjEntry 4 }
 
pnnixIAdjInst OBJECT-TYPE
        SYNTAX     INTEGER
	ACCESS	   read-only
	STATUS	   mandatory
        DESCRIPTION
            "The instance identifier on the slot port pair which this 
             adjacency is physically connected to this switching system.
             In the event that this is not a tunnel, this value will be 
             zero."
        ::= { pnnixIAdjEntry 5 }
 
pnnixIAdjCsmPPort OBJECT-TYPE
        SYNTAX     INTEGER
	ACCESS	   read-only
	STATUS	   mandatory
        DESCRIPTION
            "The unique port id which PNNI has bound to this physical slot,
             port, and instance tuple."
        ::= { pnnixIAdjEntry 6 }
 
pnnixIAdjAdvertised OBJECT-TYPE
        SYNTAX      TruthValue
	ACCESS	    read-only
	STATUS	    mandatory
        DESCRIPTION
            "Indicates if this ILMI client is advertised by this switching
            system. Note that if this value is False, the summary address may
            be used by remote nodes to still reach this ILMI client if
            pnnixIAdjSummarized is set to True (below)."
        ::= { pnnixIAdjEntry 7 }
 
pnnixIAdjSummarized OBJECT-TYPE
        SYNTAX      TruthValue
	ACCESS	    read-only
	STATUS	    mandatory
        DESCRIPTION
            "Indicates if this ILMI client is summarized by this switching
            system. Note that if this value is True, other nodes in the 
            peer group will route to this node's advertised port of 1.
            Calls terminating at end-systems attached to this node will then
            be vectored out the pnnixIAdjCsmPPort."
        ::= { pnnixIAdjEntry 8 }
 
pnnixIAdjLearned OBJECT-TYPE
        SYNTAX      DisplayString
	ACCESS	    read-only
	STATUS	    mandatory
        DESCRIPTION
            "This field contains a timestamp of when ILMI registered this
             adjacency with PNNI."
        ::= { pnnixIAdjEntry 9 }
 





-- PNNI Test Group

pnniTestMIBObjects OBJECT IDENTIFIER ::= { pnnixMIB 4 }

pnniRtstMIBGroup OBJECT IDENTIFIER ::= { pnniTestMIBObjects 1 }


-- The Route test group - This is a single-row table that exists to perform
-- route tests. It may not be written to and get-nexts return NOSUCH.
-- The only operation allowed on this table is a get.
--
-- The route test is performed by getting an Index which specifies the
-- node index, service class requested, route lookup type as well as 
-- 20 byte destination address.
--
-- The row contents are the following:
--	Error - 0 = No-error in which case the other columns contain
--                  non-NULL info;
--		1 = No route to Destination
--		2 = DTL Exhaustion 
--		3 = Unspecified internal failure
--
--	Flags - 1 = DtlAdded (in which case the outboundPort, hopCount, Dtl,
--				and curPtr are non-NULL)
--		2 = Direct (in which case the outboundPort is non-NULL)
--		3 = Myself (in which case the outboundPort is 0)
--		4 = DirectEreach (in which case the outboundPort is non-NULL 
--			and the VPI and E164 address will contain the 
--			user-configured value)
--	outboundPort - 0 = Myself
--		1 = Summary Port
--		n = pnniPort or csmPort (EG. 128 is 3/1)
--	vpi	- specified on EReach configurations only
--	e164Addr- specified on EReach configurations only
--	e164Addrlen- specified on EReach configurations only
--	hopCount - specified when flags == DtlAdded
--	Dtl      - specified when flags == DtlAdded
--	curPtr   - specified when flags == DtlAdded
--

-- Route Test table - 1 row only
 
pnnixRtstTable OBJECT-TYPE
        SYNTAX        SEQUENCE OF PnnixRtstEntry
        ACCESS        not-accessible
        STATUS        mandatory
        DESCRIPTION
            "The pnnixRtstTable is a single-row table which returns the
             results of a route test requested by a remote mgmt station.
             The route test parameters are specified in the INDEX."
        ::= { pnniRtstMIBGroup 1 }
 
pnnixRtstEntry OBJECT-TYPE
        SYNTAX        PnnixRtstEntry
        ACCESS        not-accessible
        STATUS        mandatory
        DESCRIPTION
            "An entry in the route test table, containing information 
             about a route lookup request."
        INDEX         { pnnixNodeIndex,
                        pnnixRtstClass,
                        pnnixRtstType,
                        pnnixRtstDest }
        ::= { pnnixRtstTable 1 }
 
PnnixRtstEntry ::=
        SEQUENCE {
                pnnixRtstClass          INTEGER,
                pnnixRtstType           INTEGER,
                pnnixRtstDest           OCTET STRING,
                pnnixRtstError          INTEGER,
                pnnixRtstFlags          INTEGER,
                pnnixRtstOutboundPort   PnnixPortId,
                pnnixRtstVPI            INTEGER,
                pnnixRtstE164           OCTET STRING,
                pnnixRtstE164len        INTEGER,
                pnnixRtstHopCount       INTEGER,
                pnnixRtstDTL            OCTET STRING,
                pnnixRtstCurPointer     INTEGER
                }

pnnixRtstClass OBJECT-TYPE
        SYNTAX INTEGER { 
                            ubr(1), 
                            cbr(2), 
                            vbrRt(3), 
                            vbrNrt(4), 
                            abr(5) }
        ACCESS not-accessible
        STATUS mandatory
        DESCRIPTION
            "The class the route request is to use."
        --DEFVAL { 1 }
        ::= {pnnixRtstEntry 1 }


pnnixRtstType OBJECT-TYPE
        SYNTAX INTEGER {
                            ptpt(1), 
                            pmp(2) }
        ACCESS not-accessible
        STATUS mandatory
        DESCRIPTION
            "This index specifies the type of call which may be either point
             to point or point to multi-point."
        --DEFVAL { 1 }
        ::= {pnnixRtstEntry 2 }


pnnixRtstDest OBJECT-TYPE
        SYNTAX OCTET STRING (SIZE(20))
        ACCESS not-accessible
        STATUS mandatory
        DESCRIPTION
            "The destination address. This may be specified by the user
             as an address prefix, but the snmp manager must pad this
             out to 20 octets."
-- may not be defaulted
        ::= {pnnixRtstEntry 3 }


pnnixRtstError OBJECT-TYPE
        SYNTAX INTEGER { 
                            success(1), 
                            noRouteToDest(2), 
                            dtlExhaustion(3), 
                            other(4) }
        ACCESS read-only
        STATUS mandatory
        DESCRIPTION
            "Indicates if an error has occurred and if so, the nature of the
             error. If this is set to success, then no error occurred and 
             the rest of the row contains useful information."
        ::= {pnnixRtstEntry 4 }


pnnixRtstFlags OBJECT-TYPE
        SYNTAX INTEGER { 
                            dtlAdded(1), 
                            direct(2), 
                            myself(3), 
                            directEreach(4) }
        ACCESS read-only
        STATUS mandatory
        DESCRIPTION
            "If error is set to success, this flag indicates the nature of
             the route lookup confirmation. 

             If this flag is set to dtlAdded, then the route request resulted
             in a DTL being allocated for this request. In this case, the 
             pnnixRtstOutboundPort, pnnixRtstHopCount, pnnixRtstDTL, and 
             pnnixRtstCurPointer contain useful information. (Also, after 
             this information is conveyed back to the manager, the DTL entry
             is freed.)

             If this flag is set to direct, then the route request is 
             informing the caller to proceed out a directly attached port.
             In this case, the pnnixRtstOutboundPort is valid and is either
             1 (to indicate a match on this node's summary address) or is
             a reference to the pnni advertised outbound port.

             If this flag is set to myself, then the route request is 
             informing the caller that the test call to the node in this 
             switching system (identified by pnnixNodeIndex) returned a
             successful match of myself as the destination. In this case,
             the pnnixRtstOutboundPort is valid and is set to 0 (which 
             indicates a match on this node's own address).
             
             If this flag is set to directEreach, then the route request is 
             informing the caller that the test call to the destination 
             resulted in a direct indication. In this case, the 
             pnnixRtstOutboundPort is valid and is set to the static route's
             pnni advertised port ID. If the user also specified a VPI and 
             E.164 address, then the pnnixRtstVPI and pnnixRtstE164 fields
             will also be present."
        ::= {pnnixRtstEntry 5 }



pnnixRtstOutboundPort OBJECT-TYPE
        SYNTAX PnnixPortId
        ACCESS read-only
        STATUS mandatory
        DESCRIPTION
            "If error is set to success, this indicates the outbound port of
             the route lookup confirmation. 

             If this is set to 0, then this indicates the call was placed to
             this switching system's pnnixNodeIndex.
             
             If this is set to 1, then this indicates the call was placed to
             a reachability which matched this node's summary address. In 
             this event, the IAdj table would be consulted to determine the 
             actual port (if any) where the destination resided.

             If set to any other value, it indicates the pnni advertised port 
             of the static route which caused this port to be returned."
        ::= {pnnixRtstEntry 6 }



pnnixRtstVPI OBJECT-TYPE
        SYNTAX INTEGER
        ACCESS read-only
        STATUS mandatory
        DESCRIPTION
            "If error is set to success, and pnnixRtstFlags is set to 
             directEreach, then this indicates the vpi (if set by the
             user) used to route the call."
        ::= {pnnixRtstEntry 7 }


pnnixRtstE164 OBJECT-TYPE
        SYNTAX OCTET STRING (SIZE(1..20))
        ACCESS read-only
        STATUS mandatory
        DESCRIPTION
            "If error is set to success, and pnnixRtstFlags is set to 
             directEreach, then this indicates the E.164 address (if 
             set by the user) used to route the call."
        ::= {pnnixRtstEntry 8 }


pnnixRtstE164len OBJECT-TYPE
        SYNTAX INTEGER
        ACCESS read-only
        STATUS mandatory
        DESCRIPTION
            "If error is set to success, and pnnixRtstFlags is set to 
             directEreach, then this indicates the number of significant
             octets used in the above E.164 address."
        ::= {pnnixRtstEntry 9 }


pnnixRtstHopCount OBJECT-TYPE
        SYNTAX INTEGER (2..50)
        ACCESS read-only
        STATUS mandatory
        DESCRIPTION
            "If error is set to success, and pnnixRtstFlags is set to 
             dtlAdded, then this indicates the number of hops in the 
             pnnixRtstDTL."
--	REFERENCE "ATM Forum PNNI 1.0 Section 6.4.6.4"
        ::= {pnnixRtstEntry 10 }


pnnixRtstDTL OBJECT-TYPE
        SYNTAX OCTET STRING (SIZE(52..1500))
        ACCESS read-only
        STATUS mandatory
        DESCRIPTION
            "If error is set to success, and pnnixRtstFlags is set to 
             dtlAdded, then this indicates the DTL generated by the
             route lookup function in the switching system. Note that
             this is a complete DTL meaning that the DTL IE header is
             also present.

             It has enough room for 50 entries (50 hops). Each entry
             has a 22-octet node-ID followed by a 4-octet PnniPortId.
             Entries therefore are 26 octets each and each entry is
             contiguous with its predecessor and successor.

             This DTL will not appear in the DTL table since it's freed
             after generating the reply to the management station."
--	REFERENCE "ATM Forum PNNI 1.0 Section 6.4.6.4"
        ::= {pnnixRtstEntry 11 }


pnnixRtstCurPointer OBJECT-TYPE
        SYNTAX INTEGER
        ACCESS read-only
        STATUS mandatory
        DESCRIPTION
            "If error is set to success, and pnnixRtstFlags is set to 
             dtlAdded, then this indicates the offset (in bytes) into
             pnnixRtstDTL of the curPtr."
--	REFERENCE "ATM Forum PNNI 1.0 Section 6.4.6.4"
        ::= {pnnixRtstEntry 12 }

 
-- conformance information
 
pnnixMIBConformance OBJECT IDENTIFIER 		::= { pnnixMIB 2 }
pnnixMIBCompliances OBJECT IDENTIFIER 		::= { pnnixMIBConformance 1 }
pnnixMIBGroups OBJECT IDENTIFIER 		::= { pnnixMIBConformance 2 }

-- compliance statements
 
pnnixMIBCompliance OBJECT IDENTIFIER 		::= { pnnixMIBCompliances 1 }
pnnixGeneralMinGroup OBJECT IDENTIFIER 		::= { pnnixMIBGroups 1  }
pnnixGeneralBorderGroup OBJECT IDENTIFIER 	::= { pnnixMIBGroups 2  }
pnnixNodeMinGroup OBJECT IDENTIFIER 		::= { pnnixMIBGroups 3  }
pnnixNodePglMinGroup OBJECT IDENTIFIER 		::= { pnnixMIBGroups 4  }
pnnixNodePglLgnGroup OBJECT IDENTIFIER 		::= { pnnixMIBGroups 5  }
pnnixNodeTimerMinGroup OBJECT IDENTIFIER 	::= { pnnixMIBGroups 6  }
pnnixNodeTimerLgnGroup OBJECT IDENTIFIER 	::= { pnnixMIBGroups 7  }
pnnixNodeSvccLgnGroup OBJECT IDENTIFIER 	::= { pnnixMIBGroups 8  }
pnnixScopeMinGroup OBJECT IDENTIFIER 		::= { pnnixMIBGroups 9  }
pnnixSummaryLgnGroup OBJECT IDENTIFIER 		::= { pnnixMIBGroups 10 }
pnnixIfMinGroup OBJECT IDENTIFIER 		::= { pnnixMIBGroups 11 }
pnnixIfBorderGroup OBJECT IDENTIFIER 		::= { pnnixMIBGroups 12 }
pnnixLinkMinGroup OBJECT IDENTIFIER 		::= { pnnixMIBGroups 13 }
pnnixLinkBorderOrLgnGroup OBJECT IDENTIFIER 	::= { pnnixMIBGroups 14 }
pnnixLinkLgnGroup OBJECT IDENTIFIER 		::= { pnnixMIBGroups 15 }
pnnixNbrPeerMinGroup OBJECT IDENTIFIER 		::= { pnnixMIBGroups 16 }
pnnixNbrPeerLgnGroup OBJECT IDENTIFIER 		::= { pnnixMIBGroups 17 }
pnnixNbrPeerPortMinGroup OBJECT IDENTIFIER 	::= { pnnixMIBGroups 18 }
pnnixSvccRccLgnGroup OBJECT IDENTIFIER 		::= { pnnixMIBGroups 19 }
pnnixPtseOptionalGroup OBJECT IDENTIFIER 	::= { pnnixMIBGroups 20 }
pnnixMapOptionalGroup OBJECT IDENTIFIER 	::= { pnnixMIBGroups 21 }
pnnixMapNodeOptionalGroup OBJECT IDENTIFIER 	::= { pnnixMIBGroups 22 }
pnnixMapAddrOptionalGroup OBJECT IDENTIFIER 	::= { pnnixMIBGroups 23 }
pnnixMapTnsOptionalGroup OBJECT IDENTIFIER 	::= { pnnixMIBGroups 24 }
pnnixMetricsOptionalGroup OBJECT IDENTIFIER 	::= { pnnixMIBGroups 25 }
pnnixRouteGeneralOptionalGroup OBJECT IDENTIFIER ::= { pnnixMIBGroups 26 }
pnnixRouteNodeOptionalGroup OBJECT IDENTIFIER 	::= { pnnixMIBGroups 27 }
pnnixDTLOptionalGroup OBJECT IDENTIFIER 	::= { pnnixMIBGroups 28 }
pnnixRouteAddrOptionalGroup OBJECT IDENTIFIER 	::= { pnnixMIBGroups 29 }
pnnixRouteTnsOptionalGroup OBJECT IDENTIFIER 	::= { pnnixMIBGroups 30 }
 
 
END
