MWORKS-MIB

        DEFINITIONS ::= BEGIN

        IMPORTS
		enterprises	FROM	RFC1155-SMI
		Counter		FROM	RFC1155-SMI
		OBJECT-TYPE	FROM	RFC-1212;


		tecElite		OBJECT IDENTIFIER ::= { enterprises 217 }
		meterWorks		OBJECT IDENTIFIER ::= { tecElite 16 }
		mw501			OBJECT IDENTIFIER ::= { meterWorks 1 }
		mwMem			OBJECT IDENTIFIER ::= { mw501 1 }
		mwHeap			OBJECT IDENTIFIER ::= { mw501 2 }

	mwMemCeiling OBJECT-TYPE
		SYNTAX	Counter
		ACCESS	read-only
		STATUS	mandatory
		DESCRIPTION
			"bytes of memory the agent memory manager
			will allow the agent to use."
		::= { mwMem 1 }

	mwMemUsed OBJECT-TYPE
		SYNTAX	Counter
		ACCESS	read-only
		STATUS	mandatory
		DESCRIPTION
			"bytes of memory that meterworks has malloc'ed.
			some of this may be in free pools."
		::= { mwMem 2 }

	mwHeapTotal OBJECT-TYPE
		SYNTAX	Counter
		ACCESS	read-only
		STATUS	mandatory
		DESCRIPTION
			"bytes of memory given to the heap manager."
		::= { mwHeap 1 }

	mwHeapUsed OBJECT-TYPE
		SYNTAX	Counter
		ACCESS	read-only
		STATUS	mandatory
		DESCRIPTION
			"bytes of available memory in the heap."
		::= { mwHeap 2 }

END
