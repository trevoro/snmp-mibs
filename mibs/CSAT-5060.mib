--
-- CSAT-5060.my
-- MIB generated by MG-SOFT Visual MIB Builder Version 4.0 Build 349
-- Wednesday, November 23, 2005 at 17:28:28
--

	CSAT-5060 DEFINITIONS ::= BEGIN
 
		IMPORTS
			comtechEFData			
				FROM ComtechEFData			
			OBJECT-GROUP, MODULE-COMPLIANCE			
				FROM SNMPv2-CONF			
			OBJECT-TYPE, MODULE-IDENTITY			
				FROM SNMPv2-SMI;
	
	
		-- 1.3.6.1.4.1.6247.29
		csat5060 MODULE-IDENTITY 
			LAST-UPDATED "200511051629Z"		-- November 05, 2005 at 16:29 GMT
			ORGANIZATION 
				"Comtech EF Data Corp."
			CONTACT-INFO 
				"Comtech EF Data Crop.
				2114 W. 7th Street
				Tempe, AZ  85281 USA
				
				Tel: 480-333-2200
				Fax: 480-333-2540
				Web: http://www.comtechefdata.com"
			DESCRIPTION 
				"Module Identity for CSAT-5060 Transceiver."
			::= { comtechEFData 29 }

		
	
--
-- Node definitions
--
	
		-- 1.3.6.1.4.1.6247.29.1
		csat5060Objects OBJECT IDENTIFIER ::= { csat5060 1 }

		
		-- 1.3.6.1.4.1.6247.29.1.1
		csat5060Select OBJECT-TYPE
			SYNTAX INTEGER
				{
				csat1(1),
				csat2(2)
				}
			MAX-ACCESS read-write
			STATUS current
			DESCRIPTION
				"CSAT Select.
				Use option csat1 for StandAlone unit."
			::= { csat5060Objects 1 }

		
		-- 1.3.6.1.4.1.6247.29.1.2
		csat5060SystemInfo OBJECT IDENTIFIER ::= { csat5060Objects 2 }

		
		-- 1.3.6.1.4.1.6247.29.1.2.1
		csat5060ModelNumberSoftwareVer OBJECT-TYPE
			SYNTAX OCTET STRING (SIZE (20))
			MAX-ACCESS read-only
			STATUS current
			DESCRIPTION
				"CSAT Model Number, Software Version.  (RET?)"
			::= { csat5060SystemInfo 1 }

		
		-- 1.3.6.1.4.1.6247.29.1.2.2
		csat5060UnitSerialNumber OBJECT-TYPE
			SYNTAX OCTET STRING (SIZE (6 | 10))
			MAX-ACCESS read-only
			STATUS current
			DESCRIPTION
				"CSAT Unit Serial Number.  (RSN?)"
			::= { csat5060SystemInfo 2 }

		
		-- 1.3.6.1.4.1.6247.29.1.2.3
		csat5060DeviceTime OBJECT-TYPE
			SYNTAX OCTET STRING (SIZE (8))
			MAX-ACCESS read-write
			STATUS current
			DESCRIPTION
				"CSAT Unit Time.  (TIM?, TIM=)
				A time in the form hh:mm:ss, indicating the time from midnight, where:
				 	hh = hours (00 to 23)
				 	mm = minutes (00 to 59)
				 	ss = seconds (00 to 59)"
			::= { csat5060SystemInfo 3 }

		
		-- 1.3.6.1.4.1.6247.29.1.2.4
		csat5060DeviceDate OBJECT-TYPE
			SYNTAX OCTET STRING (SIZE (8))
			MAX-ACCESS read-write
			STATUS current
			DESCRIPTION
				"CSAT Unit Date.  (DAY?, DAY=)
				A date in the form dd/mm/yy, where
				 	dd = day of the month (01 to 31)
				 	mm = month (01 to 12)
				 	yy = year (00 to 99)"
			::= { csat5060SystemInfo 4 }

		
		-- 1.3.6.1.4.1.6247.29.1.2.5
		csat5060CircuitID OBJECT-TYPE
			SYNTAX OCTET STRING (SIZE (0..24))
			MAX-ACCESS read-write
			STATUS current
			DESCRIPTION
				"CSAT Circuit ID.  (CID?, CID=)"
			::= { csat5060SystemInfo 5 }

		
		-- 1.3.6.1.4.1.6247.29.1.3
		csat5060UnitParameters OBJECT IDENTIFIER ::= { csat5060Objects 3 }

		
		-- 1.3.6.1.4.1.6247.29.1.3.1
		csat5060UnitMuteMode OBJECT-TYPE
			SYNTAX INTEGER
				{
				unmutedAfterFreqChange(0),
				mutedAfterFreqChange(1)
				}
			MAX-ACCESS read-write
			STATUS current
			DESCRIPTION
				"CSAT Unit Mute Mode.  (MUT?, MUT=)"
			::= { csat5060UnitParameters 1 }

		
		-- 1.3.6.1.4.1.6247.29.1.3.2
		csat5060UnitColdStart OBJECT-TYPE
			SYNTAX INTEGER
				{
				disabled(0),
				enabled(1)
				}
			MAX-ACCESS read-write
			STATUS current
			DESCRIPTION
				"CSAT Unit Cold Start.  (CLD?, CLD=)"
			::= { csat5060UnitParameters 2 }

		
		-- 1.3.6.1.4.1.6247.29.1.3.3
		csat5060UnitAutoFaultRecovery OBJECT-TYPE
			SYNTAX INTEGER
				{
				disabled(0),
				enabled(1)
				}
			MAX-ACCESS read-write
			STATUS current
			DESCRIPTION
				"CSAT Auto Fault Recovery.  (AFR?, AFR=)"
			::= { csat5060UnitParameters 3 }

		
		-- 1.3.6.1.4.1.6247.29.1.3.4
		csat5060UnitExtRefFaultLogic OBJECT-TYPE
			SYNTAX INTEGER
				{
				noSummary(0),
				summary(1)
				}
			MAX-ACCESS read-write
			STATUS current
			DESCRIPTION
				"CSAT External Reference Fault Logic.  (XRF?, XRF=)"
			::= { csat5060UnitParameters 4 }

		
		-- 1.3.6.1.4.1.6247.29.1.3.5
		csat5060UnitRefOscAdjust OBJECT-TYPE
			SYNTAX INTEGER (0..255)
			MAX-ACCESS read-write
			STATUS current
			DESCRIPTION
				"CSAT Reference Oscillator Adjust.  (REF?, REF=)"
			::= { csat5060UnitParameters 5 }

		
		-- 1.3.6.1.4.1.6247.29.1.3.6
		csat5060UnitLNACurrentSource OBJECT-TYPE
			SYNTAX INTEGER
				{
				disabled(0),
				enabled(1)
				}
			MAX-ACCESS read-write
			STATUS current
			DESCRIPTION
				"CSAT LNA Current Source.  (LCS?, LCS=)"
			::= { csat5060UnitParameters 6 }

		
		-- 1.3.6.1.4.1.6247.29.1.3.7
		csat5060UnitLNACurrentWindow OBJECT-TYPE
			SYNTAX INTEGER (20..50 | 99)
			MAX-ACCESS read-write
			STATUS current
			DESCRIPTION
				"CSAT LNA Current Window.  (LCW?, LCW=)"
			::= { csat5060UnitParameters 7 }

		
		-- 1.3.6.1.4.1.6247.29.1.3.8
		csat5060UnitLNAFaultLogic OBJECT-TYPE
			SYNTAX INTEGER
				{
				noSummary(0),
				summary(1)
				}
			MAX-ACCESS read-write
			STATUS current
			DESCRIPTION
				"CSAT LNA Fault Logic.  (LFL?, LFL=)"
			::= { csat5060UnitParameters 8 }

		
		-- 1.3.6.1.4.1.6247.29.1.3.9
		csat5060UnitRedundancyMode OBJECT-TYPE
			SYNTAX INTEGER
				{
				manual(0),
				auto(1)
				}
			MAX-ACCESS read-write
			STATUS current
			DESCRIPTION
				"CSAT Redundancy Mode.  Only Supported by ONLINE Unit.  (RAM?, RAM=)"
			::= { csat5060UnitParameters 9 }

		
		-- 1.3.6.1.4.1.6247.29.1.3.10
		csat5060UnitRedForceSwitch OBJECT-TYPE
			SYNTAX INTEGER { yes(1) }
			MAX-ACCESS read-write
			STATUS current
			DESCRIPTION
				"CSAT Force Redundancy Switch.  Write-ONLY.  (RTG=)"
			::= { csat5060UnitParameters 10 }

		
		-- 1.3.6.1.4.1.6247.29.1.4
		csat5060TxParameters OBJECT IDENTIFIER ::= { csat5060Objects 4 }

		
		-- 1.3.6.1.4.1.6247.29.1.4.1
		csat5060TxFrequency OBJECT-TYPE
			SYNTAX INTEGER (5845000..8400000)
			UNITS "KHz"
			MAX-ACCESS read-write
			STATUS current
			DESCRIPTION
				"CSAT TX Frequency in KHz. Frequency divisible by 1MHz or 2.5MHz is allowed. (UFQ?, UFQ=)"
			::= { csat5060TxParameters 1 }

		
		-- 1.3.6.1.4.1.6247.29.1.4.2
		csat5060TxAttenuation OBJECT-TYPE
			SYNTAX INTEGER (0..2500)
			UNITS "dB"
			MAX-ACCESS read-write
			STATUS current
			DESCRIPTION
				"CSAT TX Attenuation.  Value Multiplied by 100.  (UAT?, UAT=)"
			::= { csat5060TxParameters 2 }

		
		-- 1.3.6.1.4.1.6247.29.1.4.3
		csat5060TxAmplifier OBJECT-TYPE
			SYNTAX INTEGER
				{
				off(0),
				on(1)
				}
			MAX-ACCESS read-write
			STATUS current
			DESCRIPTION
				"CSAT TX Amplifier.  (AMP?, AMP=)"
			::= { csat5060TxParameters 3 }

		
		-- 1.3.6.1.4.1.6247.29.1.4.4
		csat5060TxMute OBJECT-TYPE
			SYNTAX INTEGER
				{
				disabled(0),
				enabled(1)
				}
			MAX-ACCESS read-write
			STATUS current
			DESCRIPTION
				"CSAT TX Mute.  (UMU?, UMU=)"
			::= { csat5060TxParameters 4 }

		
		-- 1.3.6.1.4.1.6247.29.1.4.5
		csat5060TxSlopeMode OBJECT-TYPE
			SYNTAX INTEGER
				{
				manual(0),
				calibrated(1)
				}
			MAX-ACCESS read-write
			STATUS current
			DESCRIPTION
				"CSAT TX Slope Mode.  (USM?, USM=)"
			::= { csat5060TxParameters 5 }

		
		-- 1.3.6.1.4.1.6247.29.1.4.6
		csat5060TxSlopeValue OBJECT-TYPE
			SYNTAX INTEGER (0..10)
			MAX-ACCESS read-write
			STATUS current
			DESCRIPTION
				"CSAT TX Slope Value.  Value Multiplied by 10.  (USA?, USA=)"
			::= { csat5060TxParameters 6 }

		
		-- 1.3.6.1.4.1.6247.29.1.4.7
		csat5060TxGainOffset OBJECT-TYPE
			SYNTAX INTEGER (-400..0)
			MAX-ACCESS read-write
			STATUS current
			DESCRIPTION
				"CSAT TX Gain Offset.  Value Multiplied by 100.  (UGO?, UGO=)"
			::= { csat5060TxParameters 7 }

		
		-- 1.3.6.1.4.1.6247.29.1.5
		csat5060RxParameters OBJECT IDENTIFIER ::= { csat5060Objects 5 }

		
		-- 1.3.6.1.4.1.6247.29.1.5.1
		csat5060RxFrequency OBJECT-TYPE
			SYNTAX INTEGER (3400000..7750000)
			UNITS "KHz"
			MAX-ACCESS read-write
			STATUS current
			DESCRIPTION
				"CSAT RX Frequency in KHz. Frequency divisible by 1MHz or 2.5MHz is allowed. (DFQ?, DFQ=)"
			::= { csat5060RxParameters 1 }

		
		-- 1.3.6.1.4.1.6247.29.1.5.2
		csat5060RxAttenuation OBJECT-TYPE
			SYNTAX INTEGER (0..2000)
			UNITS "dB"
			MAX-ACCESS read-write
			STATUS current
			DESCRIPTION
				"CSAT RX Attenuation.  Value Multiplied by 100.  (DAT?, DAT=)"
			::= { csat5060RxParameters 2 }

		
		-- 1.3.6.1.4.1.6247.29.1.5.3
		csat5060RxMute OBJECT-TYPE
			SYNTAX INTEGER
				{
				disabled(0),
				enabled(1)
				}
			MAX-ACCESS read-write
			STATUS current
			DESCRIPTION
				"CSAT RX Mute.  (DMU?, DMU=)"
			::= { csat5060RxParameters 3 }

		
		-- 1.3.6.1.4.1.6247.29.1.5.4
		csat5060RxSlopeMode OBJECT-TYPE
			SYNTAX INTEGER
				{
				manual(0),
				calibrated(1)
				}
			MAX-ACCESS read-write
			STATUS current
			DESCRIPTION
				"CSAT RX Slope Mode.  (DSM?, DSM=)"
			::= { csat5060RxParameters 4 }

		
		-- 1.3.6.1.4.1.6247.29.1.5.5
		csat5060RxSlopeValue OBJECT-TYPE
			SYNTAX INTEGER (0..10)
			MAX-ACCESS read-write
			STATUS current
			DESCRIPTION
				"CSAT RX Slope Value.  Value Multiplied by 10.  (DSA?, DSA=)"
			::= { csat5060RxParameters 5 }

		
		-- 1.3.6.1.4.1.6247.29.1.5.6
		csat5060RxGainOffset OBJECT-TYPE
			SYNTAX INTEGER (-400..0)
			MAX-ACCESS read-write
			STATUS current
			DESCRIPTION
				"CSAT RX Gain Offset.  Value Multiplied by 100.  (DGO?, DGO=)"
			::= { csat5060RxParameters 6 }

		
		-- 1.3.6.1.4.1.6247.29.1.6
		csat5060UnitStatus OBJECT IDENTIFIER ::= { csat5060Objects 6 }

		
		-- 1.3.6.1.4.1.6247.29.1.6.1
		csat5060OnlineState OBJECT-TYPE
			SYNTAX INTEGER
				{
				offline(0),
				online(1)
				}
			MAX-ACCESS read-only
			STATUS current
			DESCRIPTION
				"CSAT Online Status.  (ONL?)"
			::= { csat5060UnitStatus 1 }

		
		-- 1.3.6.1.4.1.6247.29.1.6.2
		csat5060MaintenanceParameters OBJECT-TYPE
			SYNTAX OCTET STRING (SIZE (80))
			MAX-ACCESS read-only
			STATUS current
			DESCRIPTION
				"CSAT Concise Maintenance Parameters.  (CMS?)
				CMS=aaa.abbb.bccc.cddd.deee.efff.fggg.ghhh.hiii.ijjj.jkkk.klll.lmmm.mnnn.nooo.oppp.p
				where: 
				aaa.a = 24V Power Supply
				bbb.b = 20V Power Supply
				ccc.c = 12V Power Supply
				ddd.d = 10V Power Supply
				eee.e = +5V Power Supply
				fff.f = -5V Power Supply
				ggg.g = TX Synthesizer Tuning Voltage
				hhh.h = TX IFLO Tuning Voltage
				iii.i = RX Synthesizer Tuning Voltage
				jjj.j = RX IFLO Tuning Voltage
				kkk.k = Reference Tuning Voltage
				lll.l = LNA Current in milliamps
				mmm.m = Fan Current in milliamps
				nnn.n = Up Conv Heat Sink Temperature
				ooo.o = RF Output Power in dB	
				ppp.p = Down Converter Temperature
				
				Note: Value is xxx.x if not available"
			::= { csat5060UnitStatus 2 }

		
		-- 1.3.6.1.4.1.6247.29.1.6.3
		csat5060UnitFaults OBJECT-TYPE
			SYNTAX INTEGER (0..262143)
			MAX-ACCESS read-only
			STATUS current
			DESCRIPTION
				"CSAT Concise Alarm Status.  (CAS?)
				The return integer value in binary represents CAS? response string.
				
				CAS=abcdefghijklmnopqrs,
				where:  a thru s = 0 or 1, 0 = OK 1 = FT	
				a = 24V Power Supply Alarm
				b = 20V Power Supply Alarm
				c = 12V Power Supply Alarm
				d = 10V Power Supply Alarm
				e = +5V Power Supply Alarm
				f = -5V Power Supply Alarm
				g = TX Synthesizer Lock Detect Alarm
				h = TX IFLO Lock Detect Alarm
				I = RX Synthesizer Lock Detect Alarm
				j = RX IFLO Lock Detect Alarm
				k = Reference Lock Detect Alarm
				l = LNA Current Alarm
				m = Fan Current Alarm
				n = Temperature Alarm
				o = HPA Thermal Shutdown Alarm
				p = Internal IIC-bus Alarm
				q = EEPROM checksum Alarm
				r = NVRAM/RTC Low Battery Alarm
				s = Redundancy switch alarm
				
				For Example, return value 128 (in decimal) = 0b0000000000010000000, 
				where l position is 1 means there is a Rx Synthesizer Lock Detect Alarm,
				other bits are 0s meas no other alarms."
			::= { csat5060UnitStatus 3 }

		
		-- 1.3.6.1.4.1.6247.29.1.7
		csat5060Logs OBJECT IDENTIFIER ::= { csat5060Objects 7 }

		
		-- 1.3.6.1.4.1.6247.29.1.7.1
		csat5060NumberUnreadEvents OBJECT-TYPE
			SYNTAX INTEGER (0..99)
			MAX-ACCESS read-only
			STATUS current
			DESCRIPTION
				"CSAT Number of Unread Events.  (TNA?)"
			::= { csat5060Logs 1 }

		
		-- 1.3.6.1.4.1.6247.29.1.7.2
		csat5060RetrieveNext5Events OBJECT-TYPE
			SYNTAX OCTET STRING
			MAX-ACCESS read-only
			STATUS current
			DESCRIPTION
				"CSAT Retrieve Next 5 Events.  (LNA?)"
			::= { csat5060Logs 2 }

		
		-- 1.3.6.1.4.1.6247.29.1.7.3
		csat5060ClearEventsLog OBJECT-TYPE
			SYNTAX INTEGER { yes(1) }
			MAX-ACCESS read-write
			STATUS current
			DESCRIPTION
				"CSAT Clear Events Log.  Write-ONLY.  (CAA=)"
			::= { csat5060Logs 3 }

		
		-- 1.3.6.1.4.1.6247.29.1.7.4
		csat5060InitializeEventsPointer OBJECT-TYPE
			SYNTAX INTEGER { yes(1) }
			MAX-ACCESS read-write
			STATUS current
			DESCRIPTION
				"CSAT Initialize Events Pointer. Write-ONLY.  (IAP=)"
			::= { csat5060Logs 4 }

		
		-- 1.3.6.1.4.1.6247.29.2
		csat5060Conformance OBJECT IDENTIFIER ::= { csat5060 2 }

		
		-- 1.3.6.1.4.1.6247.29.2.1
		csat5060Groups OBJECT IDENTIFIER ::= { csat5060Conformance 1 }

		
		-- 1.3.6.1.4.1.6247.29.2.1.1
		csat5060ObjectsGroup OBJECT-GROUP
			OBJECTS { csat5060Select, csat5060ModelNumberSoftwareVer, csat5060UnitSerialNumber, csat5060DeviceTime, csat5060DeviceDate, 
				csat5060CircuitID, csat5060UnitMuteMode, csat5060UnitColdStart, csat5060UnitAutoFaultRecovery, csat5060UnitExtRefFaultLogic, 
				csat5060UnitRefOscAdjust, csat5060UnitLNACurrentSource, csat5060UnitLNACurrentWindow, csat5060UnitLNAFaultLogic, csat5060UnitRedundancyMode, 
				csat5060UnitRedForceSwitch, csat5060TxFrequency, csat5060TxAttenuation, csat5060TxAmplifier, csat5060TxMute, 
				csat5060TxSlopeMode, csat5060TxSlopeValue, csat5060TxGainOffset, csat5060RxFrequency, csat5060RxAttenuation, 
				csat5060RxMute, csat5060RxSlopeMode, csat5060RxSlopeValue, csat5060RxGainOffset, csat5060OnlineState, 
				csat5060MaintenanceParameters, csat5060UnitFaults, csat5060InitializeEventsPointer, csat5060ClearEventsLog, csat5060NumberUnreadEvents, 
				csat5060RetrieveNext5Events }
			STATUS current
			DESCRIPTION 
				"CSAT-5060 Objects Group."
			::= { csat5060Groups 1 }

		
		-- 1.3.6.1.4.1.6247.29.2.2
		csat5060Compliances OBJECT IDENTIFIER ::= { csat5060Conformance 2 }

		
		-- 1.3.6.1.4.1.6247.29.2.2.1
		csat5060Compliance MODULE-COMPLIANCE
			STATUS current
			DESCRIPTION 
				"CSAT-5060 Compliance."
			MODULE -- this module
				MANDATORY-GROUPS { csat5060ObjectsGroup }
			::= { csat5060Compliances 1 }

		
	
	END

--
-- CSAT-5060.my
--
