--			Ascend mibatmintnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMINTNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmInternalNetworkProfile  OBJECT IDENTIFIER ::= { configuration 26}

	-- The mibatmInternalNetworkProfile table
	--
	-- This table contains parameters for the mibatmInternalNetworkProfile profile
	--

    mibatmInternalNetworkProfileTable	OBJECT-TYPE
	SYNTAX		SEQUENCE OF MibatmInternalNetworkProfileEntry
	ACCESS		not-accessible
	STATUS		mandatory
	DESCRIPTION	"A list of mibatmInternalNetworkProfile profile entries."
	::= { mibatmInternalNetworkProfile 1 }

    mibatmInternalNetworkProfileEntry	OBJECT-TYPE
	SYNTAX		MibatmInternalNetworkProfileEntry
	ACCESS		not-accessible
	STATUS		mandatory
	DESCRIPTION	"A mibatmInternalNetworkProfile entry containing objects that
			 maps to the parameters of mibatmInternalNetworkProfile profile."
	INDEX		{ atmInternalNetworkProfile-Shelf-o, atmInternalNetworkProfile-Slot-o, atmInternalNetworkProfile-Item-o }
	::= { mibatmInternalNetworkProfileTable 1 }

    MibatmInternalNetworkProfileEntry ::=
	SEQUENCE {
	    atmInternalNetworkProfile-Shelf-o
		INTEGER,
	    atmInternalNetworkProfile-Slot-o
		INTEGER,
	    atmInternalNetworkProfile-Item-o
		INTEGER,
	    atmInternalNetworkProfile-Name
		DisplayString,
	    atmInternalNetworkProfile-PhysicalAddress-Shelf
		INTEGER,
	    atmInternalNetworkProfile-PhysicalAddress-Slot
		INTEGER,
	    atmInternalNetworkProfile-PhysicalAddress-ItemNumber
		INTEGER,
	    atmInternalNetworkProfile-Enabled
		INTEGER,
	    atmInternalNetworkProfile-LineConfig-NailedGroup
		INTEGER,
	    atmInternalNetworkProfile-LineConfig-VpSwitchingVpi
		INTEGER,
	    atmInternalNetworkProfile-Action-o
		INTEGER
	}

    atmInternalNetworkProfile-Shelf-o	OBJECT-TYPE
	SYNTAX	INTEGER
	ACCESS	read-only
	STATUS	mandatory
	DESCRIPTION	""
	::= { mibatmInternalNetworkProfileEntry 1 }

    atmInternalNetworkProfile-Slot-o	OBJECT-TYPE
	SYNTAX	INTEGER
	ACCESS	read-only
	STATUS	mandatory
	DESCRIPTION	""
	::= { mibatmInternalNetworkProfileEntry 2 }

    atmInternalNetworkProfile-Item-o	OBJECT-TYPE
	SYNTAX	INTEGER
	ACCESS	read-only
	STATUS	mandatory
	DESCRIPTION	""
	::= { mibatmInternalNetworkProfileEntry 3 }

    atmInternalNetworkProfile-Name	OBJECT-TYPE
	SYNTAX	DisplayString
	ACCESS	read-write
	STATUS	mandatory
	DESCRIPTION	"For future use. The current design does not use the name field but instead references atm-internal lines by the physical address; we may in the future support referencing atm-internal lines by name as well as by address. The name consists of a null terminated ascii string supplied by the user; it defaults to the ascii form of the atm-internal line physical address."
	::= { mibatmInternalNetworkProfileEntry 4 }

    atmInternalNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibatmInternalNetworkProfileEntry 5 }

    atmInternalNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibatmInternalNetworkProfileEntry 6 }

    atmInternalNetworkProfile-PhysicalAddress-ItemNumber	OBJECT-TYPE
	SYNTAX	INTEGER
	ACCESS	read-write
	STATUS	mandatory
	DESCRIPTION	"A number that specifies an addressable entity within the context of shelf and slot."
	::= { mibatmInternalNetworkProfileEntry 7 }

    atmInternalNetworkProfile-Enabled	OBJECT-TYPE
	SYNTAX	INTEGER {
		    no (1),
		    yes (2)
		}
	ACCESS	read-write
	STATUS	mandatory
	DESCRIPTION	"TRUE if the line is enabled, otherwise FALSE."
	::= { mibatmInternalNetworkProfileEntry 8 }

    atmInternalNetworkProfile-LineConfig-NailedGroup	OBJECT-TYPE
	SYNTAX	INTEGER
	ACCESS	read-write
	STATUS	mandatory
	DESCRIPTION	"A number that identifies the set of lines that makes up a nailed group. 0 means this line is not part of a nailed group."
	::= { mibatmInternalNetworkProfileEntry 9 }

    atmInternalNetworkProfile-LineConfig-VpSwitchingVpi	OBJECT-TYPE
	SYNTAX	INTEGER
	ACCESS	read-write
	STATUS	mandatory
	DESCRIPTION	"The Vpi to be used for the VP switching. Rest of the valid VPIs in valid vpi-vci-range will be used for the VC switching. Changes in this range will take effect immediately. THE USER SHOULD BE VERY CAREFUL WHILE CHANGING THIS VALUE BECAUSE ALL CONNECTIONS ON THE LIM WHERE THIS PORT BELONGS WILL BE DROPPED IN ORDER TO MAKE THIS NEW VALUE EFFECTIVE IMMEDIATELY."
	::= { mibatmInternalNetworkProfileEntry 11 }

    atmInternalNetworkProfile-Action-o	OBJECT-TYPE
	SYNTAX	INTEGER {
		    noAction (1),
		    createProfile (2),
		    deleteProfile (3)
		}
	ACCESS	read-write
	STATUS	mandatory
	DESCRIPTION	""
	::= { mibatmInternalNetworkProfileEntry 10 }

END
