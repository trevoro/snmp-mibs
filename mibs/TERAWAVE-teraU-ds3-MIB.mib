TERAWAVE-teraU-ds3-MIB DEFINITIONS ::= BEGIN
        -- Created by sml2mib compiler 
        IMPORTS

 enterprises,  OBJECT-TYPE,  Counter,  Gauge,  TimeTicks
        FROM RFC1155-SMI
	Counter32, Gauge32 FROM SNMPv2-SMI;

terawave OBJECT IDENTIFIER ::=  { enterprises 4513 }

teraUDs3Group OBJECT IDENTIFIER ::=  { terawave 15 }

     -- teraUds3ConfigTable

teraUds3ConfigTable OBJECT-TYPE
     SYNTAX SEQUENCE OF TeraUds3ConfigTableEntryType
     ACCESS not-accessible
     STATUS mandatory
     DESCRIPTION
          " table teraUds3ConfigTable"
     ::= { teraUDs3Group 1 }

teraUds3ConfigTableEntry OBJECT-TYPE
          SYNTAX TeraUds3ConfigTableEntryType
          ACCESS not-accessible
          STATUS mandatory
          DESCRIPTION
               " table entry teraUds3ConfigTableEntry "
          INDEX {                   teraUds3LineIndex }
     ::= { teraUds3ConfigTable 1 }

TeraUds3ConfigTableEntryType ::= SEQUENCE {
          teraUds3LineIndex   
             INTEGER,
          teraUds3TimeElasped   
             INTEGER (0..899),
          teraUds3ValidIntervals   
             INTEGER (0..96),
          teraUds3LineType   
             INTEGER,
          teraUds3ATMMapping   
             INTEGER,
          teraUds3LineCoding   
             INTEGER,
          teraUds3CircuitIdentifier   
             OCTET STRING,
          teraUds3LoopbackConfig   
             INTEGER,
          teraUds3LineStatus   
             INTEGER,
          teraUds3TransmitClockSource   
             INTEGER,
          teraUds3InvalidIntervals   
             INTEGER (0..96),
          teraUds3LineLength   
             INTEGER,
          teraUds3LoopbackStatus   
             INTEGER,
          teraUds3FarEndLineLoopbackTimeout   
             INTEGER (0..71581),
          teraUds3SendFarEndLoopback   
             INTEGER
}

teraUds3LineIndex OBJECT-TYPE
          SYNTAX INTEGER
          ACCESS read-only
          STATUS mandatory
          DESCRIPTION
               ""
          ::= { teraUds3ConfigTableEntry 1 }

teraUds3TimeElasped OBJECT-TYPE
          SYNTAX INTEGER (0..899)
          ACCESS read-only
          STATUS mandatory
          DESCRIPTION
               ""
          ::= { teraUds3ConfigTableEntry 2 }

teraUds3ValidIntervals OBJECT-TYPE
          SYNTAX INTEGER (0..96)
          ACCESS read-only
          STATUS mandatory
          DESCRIPTION
               ""
          ::= { teraUds3ConfigTableEntry 3 }

teraUds3LineType OBJECT-TYPE
          SYNTAX INTEGER
                  {
                  m23(1),
                  cbitParity(2),
                  e3-G-751(3),
                  e3-G-832(4)
                  }
          ACCESS read-write
          STATUS mandatory
          DESCRIPTION
               ""
          ::= { teraUds3ConfigTableEntry 4 }

teraUds3ATMMapping OBJECT-TYPE
          SYNTAX INTEGER
                  {
                  pLCP(1),
                  direct-Mapping(2)
                  }
          ACCESS read-write
          STATUS mandatory
          DESCRIPTION
               ""
          ::= { teraUds3ConfigTableEntry 5 }

teraUds3LineCoding OBJECT-TYPE
          SYNTAX INTEGER
                  {
                  other(1),
                  b3ZS(2),
                  hDB3(3)
                  }
          ACCESS read-write
          STATUS mandatory
          DESCRIPTION
               ""
          ::= { teraUds3ConfigTableEntry 6 }

teraUds3CircuitIdentifier OBJECT-TYPE
          SYNTAX OCTET STRING
          ACCESS read-write
          STATUS mandatory
          DESCRIPTION
               ""
          ::= { teraUds3ConfigTableEntry 7 }

teraUds3LoopbackConfig OBJECT-TYPE
          SYNTAX INTEGER
                  {
                  noLoop(1),
                  facility(4),
                  equipped(32)
                  }
          ACCESS read-write
          STATUS mandatory
          DESCRIPTION
               ""
          ::= { teraUds3ConfigTableEntry 8 }

teraUds3LineStatus OBJECT-TYPE
          SYNTAX INTEGER
                  {
                  noAlarm(1),
                  rcvRAIFailure(2),
                  xmtRAIAlarm(4),
                  rcvAIS(8),
                  xmitAIS(16),
                  lOF(32),
                  lOS(64),
                  loopbackState(128),
                  rcvTestCode(256),
                  otherFailure(512),
                  unavailSigState(1024),
                  netEquipOOS(2048)
                  }
          ACCESS read-only
          STATUS mandatory
          DESCRIPTION
               ""
          ::= { teraUds3ConfigTableEntry 9 }

teraUds3TransmitClockSource OBJECT-TYPE
          SYNTAX INTEGER
                  {
                  loopTiming(1),
                  localTiming(2),
                  throughTiming(3)
                  }
          ACCESS read-write
          STATUS mandatory
          DESCRIPTION
               ""
          ::= { teraUds3ConfigTableEntry 10 }

teraUds3InvalidIntervals OBJECT-TYPE
          SYNTAX INTEGER (0..96)
          ACCESS read-only
          STATUS mandatory
          DESCRIPTION
               ""
          ::= { teraUds3ConfigTableEntry 11 }

teraUds3LineLength OBJECT-TYPE
          SYNTAX INTEGER
                  {
                  ft-250(1),
                  ft-450(2)
                  }
          ACCESS read-write
          STATUS mandatory
          DESCRIPTION
               ""
          ::= { teraUds3ConfigTableEntry 12 }

teraUds3LoopbackStatus OBJECT-TYPE
          SYNTAX INTEGER
                  {
                  noLoopback(1),
                  nearEndPayloadLoopback(2),
                  nearEndLineLoopback(4),
                  farEndLineLoopback(64)
                  }
          ACCESS read-only
          STATUS mandatory
          DESCRIPTION
               ""
          ::= { teraUds3ConfigTableEntry 13 }

teraUds3FarEndLineLoopbackTimeout OBJECT-TYPE
          SYNTAX INTEGER (0..71581)
          ACCESS read-write
          STATUS mandatory
          DESCRIPTION
               ""
          ::= { teraUds3ConfigTableEntry 14 }

teraUds3SendFarEndLoopback OBJECT-TYPE
          SYNTAX INTEGER
                  {
                  none(1),
                  sendEnable(2),
                  sendDisable(3),
                  cancelLoopback(4)
                  }
          ACCESS read-write
          STATUS mandatory
          DESCRIPTION
               ""
          ::= { teraUds3ConfigTableEntry 15 }

     -- teraUds3BERTConfigTable

teraUds3BERTConfigTable OBJECT-TYPE
     SYNTAX SEQUENCE OF TeraUds3BERTConfigTableEntryType
     ACCESS not-accessible
     STATUS mandatory
     DESCRIPTION
          " table teraUds3BERTConfigTable"
     ::= { teraUDs3Group 2 }

teraUds3BERTConfigTableEntry OBJECT-TYPE
          SYNTAX TeraUds3BERTConfigTableEntryType
          ACCESS not-accessible
          STATUS mandatory
          DESCRIPTION
               " table entry teraUds3BERTConfigTableEntry "
          INDEX {                   teraUds3LineIndex }
     ::= { teraUds3BERTConfigTable 1 }

TeraUds3BERTConfigTableEntryType ::= SEQUENCE {
          teraUds3BERTPattern   
             INTEGER,
          teraUds3BERTUserPattern   
             OCTET STRING,
          teraUds3BERTSyncInfo   
             INTEGER,
          teraUds3BERT-ES   
             Counter32,
          teraUds3BERT-BES   
             Counter32,
          teraUds3BERT-BER   
             Counter32
}

teraUds3BERTPattern OBJECT-TYPE
          SYNTAX INTEGER
                  {
                  none(1),
                  user(2),
                  qRSS(3)
                  }
          ACCESS read-write
          STATUS mandatory
          DESCRIPTION
               ""
          ::= { teraUds3BERTConfigTableEntry 1 }

teraUds3BERTUserPattern OBJECT-TYPE
          SYNTAX OCTET STRING
          ACCESS read-write
          STATUS mandatory
          DESCRIPTION
               ""
          ::= { teraUds3BERTConfigTableEntry 2 }

teraUds3BERTSyncInfo OBJECT-TYPE
          SYNTAX INTEGER
                  {
                  n-a(1),
                  yes(2),
                  no(3)
                  }
          ACCESS read-write
          STATUS mandatory
          DESCRIPTION
               ""
          ::= { teraUds3BERTConfigTableEntry 3 }

teraUds3BERT-ES OBJECT-TYPE
          SYNTAX Counter32
          ACCESS read-only
          STATUS mandatory
          DESCRIPTION
               ""
          ::= { teraUds3BERTConfigTableEntry 4 }

teraUds3BERT-BES OBJECT-TYPE
          SYNTAX Counter32
          ACCESS read-only
          STATUS mandatory
          DESCRIPTION
               ""
          ::= { teraUds3BERTConfigTableEntry 5 }

teraUds3BERT-BER OBJECT-TYPE
          SYNTAX Counter32
          ACCESS read-only
          STATUS mandatory
          DESCRIPTION
               ""
          ::= { teraUds3BERTConfigTableEntry 6 }

     -- teraUds3ExtendTotalTable

teraUds3ExtendTotalTable OBJECT-TYPE
     SYNTAX SEQUENCE OF TeraUds3ExtendTotalTableEntryType
     ACCESS not-accessible
     STATUS mandatory
     DESCRIPTION
          " table teraUds3ExtendTotalTable"
     ::= { teraUDs3Group 3 }

teraUds3ExtendTotalTableEntry OBJECT-TYPE
          SYNTAX TeraUds3ExtendTotalTableEntryType
          ACCESS not-accessible
          STATUS mandatory
          DESCRIPTION
               " table entry teraUds3ExtendTotalTableEntry "
          INDEX {                   teraUds3ExtendTotalIndex,                  teraUds3ExtendTotalNumber }
     ::= { teraUds3ExtendTotalTable 1 }

TeraUds3ExtendTotalTableEntryType ::= SEQUENCE {
          teraUds3ExtendTotalIndex   
             INTEGER,
          teraUds3ExtendTotalNumber   
             INTEGER (1..7),
          teraUds3ExtendTotalPESs   
             Gauge32,
          teraUds3ExtendTotalPSESs   
             Gauge32,
          teraUds3ExtendTotalSEFSs   
             Gauge32,
          teraUds3ExtendTotalUASs   
             Gauge32,
          teraUds3ExtendTotalLCVs   
             Gauge32,
          teraUds3ExtendTotalPCVs   
             Gauge32,
          teraUds3ExtendTotalLESs   
             Gauge32,
          teraUds3ExtendTotalCCVs   
             Gauge32,
          teraUds3ExtendTotalCESs   
             Gauge32,
          teraUds3ExtendTotalCSESs   
             Gauge32,
          teraUds3ExtendTotalValidData   
             INTEGER
}

teraUds3ExtendTotalIndex OBJECT-TYPE
          SYNTAX INTEGER
          ACCESS read-only
          STATUS mandatory
          DESCRIPTION
               ""
          ::= { teraUds3ExtendTotalTableEntry 1 }

teraUds3ExtendTotalNumber OBJECT-TYPE
          SYNTAX INTEGER (1..7)
          ACCESS read-only
          STATUS mandatory
          DESCRIPTION
               ""
          ::= { teraUds3ExtendTotalTableEntry 2 }

teraUds3ExtendTotalPESs OBJECT-TYPE
          SYNTAX Gauge32
          ACCESS read-only
          STATUS mandatory
          DESCRIPTION
               ""
          ::= { teraUds3ExtendTotalTableEntry 3 }

teraUds3ExtendTotalPSESs OBJECT-TYPE
          SYNTAX Gauge32
          ACCESS read-only
          STATUS mandatory
          DESCRIPTION
               ""
          ::= { teraUds3ExtendTotalTableEntry 4 }

teraUds3ExtendTotalSEFSs OBJECT-TYPE
          SYNTAX Gauge32
          ACCESS read-only
          STATUS mandatory
          DESCRIPTION
               ""
          ::= { teraUds3ExtendTotalTableEntry 5 }

teraUds3ExtendTotalUASs OBJECT-TYPE
          SYNTAX Gauge32
          ACCESS read-only
          STATUS mandatory
          DESCRIPTION
               ""
          ::= { teraUds3ExtendTotalTableEntry 6 }

teraUds3ExtendTotalLCVs OBJECT-TYPE
          SYNTAX Gauge32
          ACCESS read-only
          STATUS mandatory
          DESCRIPTION
               ""
          ::= { teraUds3ExtendTotalTableEntry 7 }

teraUds3ExtendTotalPCVs OBJECT-TYPE
          SYNTAX Gauge32
          ACCESS read-only
          STATUS mandatory
          DESCRIPTION
               ""
          ::= { teraUds3ExtendTotalTableEntry 8 }

teraUds3ExtendTotalLESs OBJECT-TYPE
          SYNTAX Gauge32
          ACCESS read-only
          STATUS mandatory
          DESCRIPTION
               ""
          ::= { teraUds3ExtendTotalTableEntry 9 }

teraUds3ExtendTotalCCVs OBJECT-TYPE
          SYNTAX Gauge32
          ACCESS read-only
          STATUS mandatory
          DESCRIPTION
               ""
          ::= { teraUds3ExtendTotalTableEntry 10 }

teraUds3ExtendTotalCESs OBJECT-TYPE
          SYNTAX Gauge32
          ACCESS read-only
          STATUS mandatory
          DESCRIPTION
               ""
          ::= { teraUds3ExtendTotalTableEntry 11 }

teraUds3ExtendTotalCSESs OBJECT-TYPE
          SYNTAX Gauge32
          ACCESS read-only
          STATUS mandatory
          DESCRIPTION
               ""
          ::= { teraUds3ExtendTotalTableEntry 12 }

teraUds3ExtendTotalValidData OBJECT-TYPE
          SYNTAX INTEGER
          ACCESS read-only
          STATUS mandatory
          DESCRIPTION
               ""
          ::= { teraUds3ExtendTotalTableEntry 13 }

     -- teraUds3FarEndExtendTotalTable

teraUds3FarEndExtendTotalTable OBJECT-TYPE
     SYNTAX SEQUENCE OF TeraUds3FarEndExtendTotalTableEntryType
     ACCESS not-accessible
     STATUS mandatory
     DESCRIPTION
          " table teraUds3FarEndExtendTotalTable"
     ::= { teraUDs3Group 4 }

teraUds3FarEndExtendTotalTableEntry OBJECT-TYPE
          SYNTAX TeraUds3FarEndExtendTotalTableEntryType
          ACCESS not-accessible
          STATUS mandatory
          DESCRIPTION
               " table entry teraUds3FarEndExtendTotalTableEntry "
          INDEX {                   teraUds3FarEndExtendTotalIndex,                  teraUds3FarEndExtendTotalNumber }
     ::= { teraUds3FarEndExtendTotalTable 1 }

TeraUds3FarEndExtendTotalTableEntryType ::= SEQUENCE {
          teraUds3FarEndExtendTotalIndex   
             INTEGER,
          teraUds3FarEndExtendTotalNumber   
             INTEGER (1..7),
          teraUds3FarEndExtendTotalCESs   
             Gauge32,
          teraUds3FarEndExtendTotalCSESs   
             Gauge32,
          teraUds3FarEndExtendTotalCCVs   
             Gauge32,
          teraUds3FarEndExtendTotalUASs   
             Gauge32,
          teraUds3FarEndExtendTotalValidData   
             INTEGER
}

teraUds3FarEndExtendTotalIndex OBJECT-TYPE
          SYNTAX INTEGER
          ACCESS read-only
          STATUS mandatory
          DESCRIPTION
               ""
          ::= { teraUds3FarEndExtendTotalTableEntry 1 }

teraUds3FarEndExtendTotalNumber OBJECT-TYPE
          SYNTAX INTEGER (1..7)
          ACCESS read-only
          STATUS mandatory
          DESCRIPTION
               ""
          ::= { teraUds3FarEndExtendTotalTableEntry 2 }

teraUds3FarEndExtendTotalCESs OBJECT-TYPE
          SYNTAX Gauge32
          ACCESS read-only
          STATUS mandatory
          DESCRIPTION
               ""
          ::= { teraUds3FarEndExtendTotalTableEntry 3 }

teraUds3FarEndExtendTotalCSESs OBJECT-TYPE
          SYNTAX Gauge32
          ACCESS read-only
          STATUS mandatory
          DESCRIPTION
               ""
          ::= { teraUds3FarEndExtendTotalTableEntry 4 }

teraUds3FarEndExtendTotalCCVs OBJECT-TYPE
          SYNTAX Gauge32
          ACCESS read-only
          STATUS mandatory
          DESCRIPTION
               ""
          ::= { teraUds3FarEndExtendTotalTableEntry 5 }

teraUds3FarEndExtendTotalUASs OBJECT-TYPE
          SYNTAX Gauge32
          ACCESS read-only
          STATUS mandatory
          DESCRIPTION
               ""
          ::= { teraUds3FarEndExtendTotalTableEntry 6 }

teraUds3FarEndExtendTotalValidData OBJECT-TYPE
          SYNTAX INTEGER
          ACCESS read-only
          STATUS mandatory
          DESCRIPTION
               ""
          ::= { teraUds3FarEndExtendTotalTableEntry 7 }

     -- teraUds3atmInterfacePlcpIntervalTable

teraUds3atmInterfacePlcpIntervalTable OBJECT-TYPE
     SYNTAX SEQUENCE OF TeraUds3atmInterfacePlcpIntervalTableEntryType
     ACCESS not-accessible
     STATUS mandatory
     DESCRIPTION
          " table teraUds3atmInterfacePlcpIntervalTable"
     ::= { teraUDs3Group 5 }

teraUds3atmInterfacePlcpIntervalTableEntry OBJECT-TYPE
          SYNTAX TeraUds3atmInterfacePlcpIntervalTableEntryType
          ACCESS not-accessible
          STATUS mandatory
          DESCRIPTION
               " table entry teraUds3atmInterfacePlcpIntervalTableEntry "
          INDEX {                   ifIndex,                  teraUds3atmInterfacePlcpIntervalNumber }
     ::= { teraUds3atmInterfacePlcpIntervalTable 1 }

TeraUds3atmInterfacePlcpIntervalTableEntryType ::= SEQUENCE {
          teraUds3atmInterfacePlcpIntervalNumber   
             INTEGER (1..96),
          teraUds3atmInterfacePlcpIntervalSEFSs   
             Counter32,
          teraUds3atmInterfacePlcpIntervalAlarmState   
             INTEGER,
          teraUds3atmInterfacePlcpIntervalUASs   
             Counter32,
          teraUds3atmInterfacePlcpIntervalValidData   
             INTEGER
}

teraUds3atmInterfacePlcpIntervalNumber OBJECT-TYPE
          SYNTAX INTEGER (1..96)
          ACCESS read-only
          STATUS mandatory
          DESCRIPTION
               ""
          ::= { teraUds3atmInterfacePlcpIntervalTableEntry 1 }

teraUds3atmInterfacePlcpIntervalSEFSs OBJECT-TYPE
          SYNTAX Counter32
          ACCESS read-only
          STATUS mandatory
          DESCRIPTION
               ""
          ::= { teraUds3atmInterfacePlcpIntervalTableEntry 2 }

teraUds3atmInterfacePlcpIntervalAlarmState OBJECT-TYPE
          SYNTAX INTEGER
                  {
                  noAlarm(0),
                  receivedFarEndAlarm(1),
                  incomingLOF(2)
                  }
          ACCESS read-only
          STATUS mandatory
          DESCRIPTION
               ""
          ::= { teraUds3atmInterfacePlcpIntervalTableEntry 3 }

teraUds3atmInterfacePlcpIntervalUASs OBJECT-TYPE
          SYNTAX Counter32
          ACCESS read-only
          STATUS mandatory
          DESCRIPTION
               ""
          ::= { teraUds3atmInterfacePlcpIntervalTableEntry 4 }

teraUds3atmInterfacePlcpIntervalValidData OBJECT-TYPE
          SYNTAX INTEGER
          ACCESS read-only
          STATUS mandatory
          DESCRIPTION
               ""
          ::= { teraUds3atmInterfacePlcpIntervalTableEntry 5 }

     -- teraUds3atmInterfacePlcpTotalTable

teraUds3atmInterfacePlcpTotalTable OBJECT-TYPE
     SYNTAX SEQUENCE OF TeraUds3atmInterfacePlcpTotalTableEntryType
     ACCESS not-accessible
     STATUS mandatory
     DESCRIPTION
          " table teraUds3atmInterfacePlcpTotalTable"
     ::= { teraUDs3Group 6 }

teraUds3atmInterfacePlcpTotalTableEntry OBJECT-TYPE
          SYNTAX TeraUds3atmInterfacePlcpTotalTableEntryType
          ACCESS not-accessible
          STATUS mandatory
          DESCRIPTION
               " table entry teraUds3atmInterfacePlcpTotalTableEntry "
          INDEX {                   ifIndex }
     ::= { teraUds3atmInterfacePlcpTotalTable 1 }

TeraUds3atmInterfacePlcpTotalTableEntryType ::= SEQUENCE {
          teraUds3atmInterfacePlcpTotalSEFSs   
             Counter32,
          teraUds3atmInterfacePlcpTotalAlarmState   
             INTEGER,
          teraUds3atmInterfacePlcpTotalUASs   
             Counter32
}

teraUds3atmInterfacePlcpTotalSEFSs OBJECT-TYPE
          SYNTAX Counter32
          ACCESS read-only
          STATUS mandatory
          DESCRIPTION
               ""
          ::= { teraUds3atmInterfacePlcpTotalTableEntry 1 }

teraUds3atmInterfacePlcpTotalAlarmState OBJECT-TYPE
          SYNTAX INTEGER
                  {
                  noAlarm(0),
                  receivedFarEndAlarm(1),
                  incomingLOF(2)
                  }
          ACCESS read-only
          STATUS mandatory
          DESCRIPTION
               ""
          ::= { teraUds3atmInterfacePlcpTotalTableEntry 2 }

teraUds3atmInterfacePlcpTotalUASs OBJECT-TYPE
          SYNTAX Counter32
          ACCESS read-only
          STATUS mandatory
          DESCRIPTION
               ""
          ::= { teraUds3atmInterfacePlcpTotalTableEntry 3 }

     -- teraUds3atmInterfacePlcpExtendTotalTable

teraUds3atmInterfacePlcpExtendTotalTable OBJECT-TYPE
     SYNTAX SEQUENCE OF TeraUds3atmInterfacePlcpExtendTotalTableEntryType
     ACCESS not-accessible
     STATUS mandatory
     DESCRIPTION
          " table teraUds3atmInterfacePlcpExtendTotalTable"
     ::= { teraUDs3Group 7 }

teraUds3atmInterfacePlcpExtendTotalTableEntry OBJECT-TYPE
          SYNTAX TeraUds3atmInterfacePlcpExtendTotalTableEntryType
          ACCESS not-accessible
          STATUS mandatory
          DESCRIPTION
               " table entry teraUds3atmInterfacePlcpExtendTotalTableEntry "
          INDEX {                   ifIndex,                  teraUds3atmInterfacePlcpExtendTotalNumber }
     ::= { teraUds3atmInterfacePlcpExtendTotalTable 1 }

TeraUds3atmInterfacePlcpExtendTotalTableEntryType ::= SEQUENCE {
          teraUds3atmInterfacePlcpExtendTotalNumber   
             INTEGER (1..7),
          teraUds3atmInterfacePlcpExtendTotalSEFSs   
             Counter32,
          teraUds3atmInterfacePlcpExtendTotalAlarmState   
             INTEGER,
          teraUds3atmInterfacePlcpExtendTotalUASs   
             Counter32,
          teraUds3atmInterfacePlcpExtendTotalValidData   
             INTEGER
}

teraUds3atmInterfacePlcpExtendTotalNumber OBJECT-TYPE
          SYNTAX INTEGER (1..7)
          ACCESS read-only
          STATUS mandatory
          DESCRIPTION
               ""
          ::= { teraUds3atmInterfacePlcpExtendTotalTableEntry 1 }

teraUds3atmInterfacePlcpExtendTotalSEFSs OBJECT-TYPE
          SYNTAX Counter32
          ACCESS read-only
          STATUS mandatory
          DESCRIPTION
               ""
          ::= { teraUds3atmInterfacePlcpExtendTotalTableEntry 2 }

teraUds3atmInterfacePlcpExtendTotalAlarmState OBJECT-TYPE
          SYNTAX INTEGER
                  {
                  noAlarm(0),
                  receivedFarEndAlarm(1),
                  incomingLOF(2)
                  }
          ACCESS read-only
          STATUS mandatory
          DESCRIPTION
               ""
          ::= { teraUds3atmInterfacePlcpExtendTotalTableEntry 3 }

teraUds3atmInterfacePlcpExtendTotalUASs OBJECT-TYPE
          SYNTAX Counter32
          ACCESS read-only
          STATUS mandatory
          DESCRIPTION
               ""
          ::= { teraUds3atmInterfacePlcpExtendTotalTableEntry 4 }

teraUds3atmInterfacePlcpExtendTotalValidData OBJECT-TYPE
          SYNTAX INTEGER
          ACCESS read-only
          STATUS mandatory
          DESCRIPTION
               ""
          ::= { teraUds3atmInterfacePlcpExtendTotalTableEntry 5 }

     -- teraUds3atmInterfaceTCIntervalTable

teraUds3atmInterfaceTCIntervalTable OBJECT-TYPE
     SYNTAX SEQUENCE OF TeraUds3atmInterfaceTCIntervalTableEntryType
     ACCESS not-accessible
     STATUS mandatory
     DESCRIPTION
          " table teraUds3atmInterfaceTCIntervalTable"
     ::= { teraUDs3Group 8 }

teraUds3atmInterfaceTCIntervalTableEntry OBJECT-TYPE
          SYNTAX TeraUds3atmInterfaceTCIntervalTableEntryType
          ACCESS not-accessible
          STATUS mandatory
          DESCRIPTION
               " table entry teraUds3atmInterfaceTCIntervalTableEntry "
          INDEX {                   ifIndex,                  teraUds3atmInterfaceTCIntervalNumber }
     ::= { teraUds3atmInterfaceTCIntervalTable 1 }

TeraUds3atmInterfaceTCIntervalTableEntryType ::= SEQUENCE {
          teraUds3atmInterfaceTCIntervalNumber   
             INTEGER (1..96),
          teraUds3atmInterfaceTCIntervalOCDEvents   
             Counter32,
          teraUds3atmInterfaceTCIntervalAlarmState   
             INTEGER,
          teraUds3atmInterfaceTCIntervalValidData   
             INTEGER
}

teraUds3atmInterfaceTCIntervalNumber OBJECT-TYPE
          SYNTAX INTEGER (1..96)
          ACCESS read-only
          STATUS mandatory
          DESCRIPTION
               ""
          ::= { teraUds3atmInterfaceTCIntervalTableEntry 1 }

teraUds3atmInterfaceTCIntervalOCDEvents OBJECT-TYPE
          SYNTAX Counter32
          ACCESS read-only
          STATUS mandatory
          DESCRIPTION
               ""
          ::= { teraUds3atmInterfaceTCIntervalTableEntry 2 }

teraUds3atmInterfaceTCIntervalAlarmState OBJECT-TYPE
          SYNTAX INTEGER
                  {
                  noAlarm(1),
                  lcdFailure(2)
                  }
          ACCESS read-only
          STATUS mandatory
          DESCRIPTION
               ""
          ::= { teraUds3atmInterfaceTCIntervalTableEntry 3 }

teraUds3atmInterfaceTCIntervalValidData OBJECT-TYPE
          SYNTAX INTEGER
          ACCESS read-only
          STATUS mandatory
          DESCRIPTION
               ""
          ::= { teraUds3atmInterfaceTCIntervalTableEntry 4 }

     -- teraUds3atmInterfaceTCTotalTable

teraUds3atmInterfaceTCTotalTable OBJECT-TYPE
     SYNTAX SEQUENCE OF TeraUds3atmInterfaceTCTotalTableEntryType
     ACCESS not-accessible
     STATUS mandatory
     DESCRIPTION
          " table teraUds3atmInterfaceTCTotalTable"
     ::= { teraUDs3Group 9 }

teraUds3atmInterfaceTCTotalTableEntry OBJECT-TYPE
          SYNTAX TeraUds3atmInterfaceTCTotalTableEntryType
          ACCESS not-accessible
          STATUS mandatory
          DESCRIPTION
               " table entry teraUds3atmInterfaceTCTotalTableEntry "
          INDEX {                   ifIndex }
     ::= { teraUds3atmInterfaceTCTotalTable 1 }

TeraUds3atmInterfaceTCTotalTableEntryType ::= SEQUENCE {
          teraUds3atmInterfaceTCTotalOCDEvents   
             Counter32,
          teraUds3atmInterfaceTCTotalAlarmState   
             INTEGER
}

teraUds3atmInterfaceTCTotalOCDEvents OBJECT-TYPE
          SYNTAX Counter32
          ACCESS read-only
          STATUS mandatory
          DESCRIPTION
               ""
          ::= { teraUds3atmInterfaceTCTotalTableEntry 1 }

teraUds3atmInterfaceTCTotalAlarmState OBJECT-TYPE
          SYNTAX INTEGER
                  {
                  noAlarm(1),
                  lcdFailure(2)
                  }
          ACCESS read-only
          STATUS mandatory
          DESCRIPTION
               ""
          ::= { teraUds3atmInterfaceTCTotalTableEntry 2 }

     -- teraUds3atmInterfaceTCExtendTotalTable

teraUds3atmInterfaceTCExtendTotalTable OBJECT-TYPE
     SYNTAX SEQUENCE OF TeraUds3atmInterfaceTCExtendTotalTableEntryType
     ACCESS not-accessible
     STATUS mandatory
     DESCRIPTION
          " table teraUds3atmInterfaceTCExtendTotalTable"
     ::= { teraUDs3Group 10 }

teraUds3atmInterfaceTCExtendTotalTableEntry OBJECT-TYPE
          SYNTAX TeraUds3atmInterfaceTCExtendTotalTableEntryType
          ACCESS not-accessible
          STATUS mandatory
          DESCRIPTION
               " table entry teraUds3atmInterfaceTCExtendTotalTableEntry "
          INDEX {                   ifIndex,                  teraUds3atmInterfaceTCExtendTotalNumber }
     ::= { teraUds3atmInterfaceTCExtendTotalTable 1 }

TeraUds3atmInterfaceTCExtendTotalTableEntryType ::= SEQUENCE {
          teraUds3atmInterfaceTCExtendTotalNumber   
             INTEGER (1..7),
          teraUds3atmInterfaceTCExtendTotalOCDEvents   
             Counter32,
          teraUds3atmInterfaceTCExtendTotalAlarmState   
             INTEGER,
          teraUds3atmInterfaceTCExtendTotalValidData   
             INTEGER
}

teraUds3atmInterfaceTCExtendTotalNumber OBJECT-TYPE
          SYNTAX INTEGER (1..7)
          ACCESS read-only
          STATUS mandatory
          DESCRIPTION
               ""
          ::= { teraUds3atmInterfaceTCExtendTotalTableEntry 1 }

teraUds3atmInterfaceTCExtendTotalOCDEvents OBJECT-TYPE
          SYNTAX Counter32
          ACCESS read-only
          STATUS mandatory
          DESCRIPTION
               ""
          ::= { teraUds3atmInterfaceTCExtendTotalTableEntry 2 }

teraUds3atmInterfaceTCExtendTotalAlarmState OBJECT-TYPE
          SYNTAX INTEGER
                  {
                  noAlarm(1),
                  lcdFailure(2)
                  }
          ACCESS read-only
          STATUS mandatory
          DESCRIPTION
               ""
          ::= { teraUds3atmInterfaceTCExtendTotalTableEntry 3 }

teraUds3atmInterfaceTCExtendTotalValidData OBJECT-TYPE
          SYNTAX INTEGER
          ACCESS read-only
          STATUS mandatory
          DESCRIPTION
               ""
          ::= { teraUds3atmInterfaceTCExtendTotalTableEntry 4 }

     -- teraUds3PMControlTable

teraUds3PMControlTable OBJECT-TYPE
     SYNTAX SEQUENCE OF TeraUds3PMControlTableEntryType
     ACCESS not-accessible
     STATUS mandatory
     DESCRIPTION
          " table teraUds3PMControlTable"
     ::= { teraUDs3Group 11 }

teraUds3PMControlTableEntry OBJECT-TYPE
          SYNTAX TeraUds3PMControlTableEntryType
          ACCESS not-accessible
          STATUS mandatory
          DESCRIPTION
               " table entry teraUds3PMControlTableEntry "
          INDEX {                   teraUds3LineIndex }
     ::= { teraUds3PMControlTable 1 }

TeraUds3PMControlTableEntryType ::= SEQUENCE {
          teraUds3PMControlClearAll   
             INTEGER
}

teraUds3PMControlClearAll OBJECT-TYPE
          SYNTAX INTEGER
                  {
                  ok(1),
                  clear(2)
                  }
          ACCESS read-write
          STATUS mandatory
          DESCRIPTION
               ""
          ::= { teraUds3PMControlTableEntry 1 }

END
