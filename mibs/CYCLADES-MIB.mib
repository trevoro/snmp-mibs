-- Cyclades Vendor MIB OID Tree
-- Release 2.0.2 03/12/2003

CYCLADES-MIB DEFINITIONS ::= BEGIN

IMPORTS
   enterprises
      FROM SNMPv2-SMI ;

-- Cyclades Corporation Identifier

cyclades	OBJECT IDENTIFIER ::= { enterprises 2925 }

END
