CENTILLION-LANE-V2-EXT-MIB DEFINITIONS ::= BEGIN
 
-- Centillion LANEv2 Extention MIB Release 1.0.0
-- Revision 6/24/98 
 
-- Copyright 1998 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
-- Imports

IMPORTS
        OBJECT-TYPE
                FROM RFC-1212
	TruthValue
		FROM SNMPv2-TC-v1
        atmLane
		FROM CENTILLION-ROOT-MIB
	AtmLaneAddress
		FROM LAN-EMULATION-CLIENT-MIB
	lesConfIndex
		FROM LAN-EMULATION-LES-MIB
	lecsConfIndex, elanConfIndex
		FROM LAN-EMULATION-ELAN-MIB;


cnLesV2ExtnGroup	OBJECT IDENTIFIER ::= { atmLane 7 }
cnLecsV2ExtnGroup	OBJECT IDENTIFIER ::= { atmLane 8 }
cnElanV2ExtnGroup	OBJECT IDENTIFIER ::= { atmLane 9 }

CnLesLecDataFrameSize ::= INTEGER {
        max1516(2),
        max4544(3),
        max9234(4),
        max18190(5),

        -- LANE 2.0
	max1580(6)
        }


-- SECTION 7: LES LANEv2 Extension Group

cnLesV2ExtnTable  OBJECT-TYPE
	SYNTAX	SEQUENCE OF CnLesV2ExtnEntry
	ACCESS	not-accessible
	STATUS	mandatory
	DESCRIPTION
		"LES LANEv2 extension table"
	::= { cnLesV2ExtnGroup 1 }

cnLesV2ExtnEntry OBJECT-TYPE
	SYNTAX	CnLesV2ExtnEntry
	ACCESS	not-accessible
	STATUS	mandatory
	DESCRIPTION
		"An extension to the lesConfEntry which contains
		 objects associated to a LES."
	INDEX	{ lesConfIndex }
	::= { cnLesV2ExtnTable 1 }

CnLesV2ExtnEntry ::= SEQUENCE {
	cnLesV2ExtnV2Capable 
		TruthValue,
	cnLesV2ExtnElanID
		INTEGER,
	cnLesV2ExtnMaxFrameSize
		CnLesLecDataFrameSize
	}


cnLesV2ExtnV2Capable OBJECT-TYPE
	SYNTAX TruthValue
	ACCESS read-write
	STATUS mandatory
	DESCRIPTION
        	"LES V2 Capable.
		 Indicates whether this LES is setup to behave as 
		 a LANE V2 LES.  A setting which will be used for 
		 the LEC the next time it joins."
        DEFVAL { false }
	::= {cnLesV2ExtnEntry 1}

cnLesV2ExtnElanID OBJECT-TYPE
	SYNTAX INTEGER
	ACCESS read-write
	STATUS mandatory
	DESCRIPTION
        	"The ELAN-ID associated with this LES."
        DEFVAL { 0 }
	::= {cnLesV2ExtnEntry 2}

cnLesV2ExtnMaxFrameSize OBJECT-TYPE
	SYNTAX CnLesLecDataFrameSize
	ACCESS read-write
	STATUS mandatory
	DESCRIPTION
        	"The maximum AAL-5 SDU size of a data
         	 frame that the LE service can guarantee
         	 not to drop because it is too large."
	::= {cnLesV2ExtnEntry 3}


-- SECTION 8: LECS LANEv2 Extension Group

cnLecsV2ExtnTable  OBJECT-TYPE
	SYNTAX	SEQUENCE OF CnLecsV2ExtnEntry
	ACCESS	not-accessible
	STATUS	mandatory
	DESCRIPTION
		"LECS LANEv2 extension table"
	::= { cnLecsV2ExtnGroup 1 }

cnLecsV2ExtnEntry OBJECT-TYPE
	SYNTAX	CnLecsV2ExtnEntry
	ACCESS	not-accessible
	STATUS	mandatory
	DESCRIPTION
		"An extension to the lecsConfEntry which contains
		 objects associated to a LECS."
	INDEX	{ lecsConfIndex }
	::= { cnLecsV2ExtnTable 1 }

CnLecsV2ExtnEntry ::= SEQUENCE {
	cnLecsV2ExtnWellKnownAtmAddress
		AtmLaneAddress
	}

cnLecsV2ExtnWellKnownAtmAddress OBJECT-TYPE
	SYNTAX AtmLaneAddress
	ACCESS read-only
	STATUS mandatory
	DESCRIPTION
        	"LECS LANEv2 well-known ATM Address.
		 For LANEv2: C500790000000000000000000000A03E00000100"
	::= {cnLecsV2ExtnEntry 1}


-- SECTION 9: ELAN V2 Extension Group

cnElanV2ExtnTable  OBJECT-TYPE
	SYNTAX	SEQUENCE OF CnElanV2ExtnEntry
	ACCESS	not-accessible
	STATUS	mandatory
	DESCRIPTION
		"ELAN LANEv2 extension table"
	::= { cnElanV2ExtnGroup 1 }

cnElanV2ExtnEntry OBJECT-TYPE
	SYNTAX	CnElanV2ExtnEntry
	ACCESS	not-accessible
	STATUS	mandatory
	DESCRIPTION
		"An extension to the elanConfEntry which contains
		 objects associated to an ELAN."
	INDEX	{ elanConfIndex }
	::= { cnElanV2ExtnTable 1 }

CnElanV2ExtnEntry ::= SEQUENCE {
	cnElanV2ExtnV2Capable 
		TruthValue,
	cnElanV2ExtnElanID 
		INTEGER 
	}

cnElanV2ExtnV2Capable OBJECT-TYPE
	SYNTAX TruthValue
	ACCESS read-write
	STATUS mandatory
	DESCRIPTION
        	"ELAN V2 Capable.
		 Indicates whether this ELAN is setup to behave as 
		 a LANE V2 ELAN.  A setting which will be used for 
		 the LEC the next time it joins."
        DEFVAL { false }
	::= {cnElanV2ExtnEntry 1}

cnElanV2ExtnElanID OBJECT-TYPE
	SYNTAX INTEGER
	ACCESS read-write
	STATUS mandatory
	DESCRIPTION
        	"The ELAN-ID associated with this ELAN."
        DEFVAL { 0 }
	::= {cnElanV2ExtnEntry 2}


END
-- SECTION 1: Top Level Definitions
