ETH-SWITCH-MIB DEFINITIONS ::= BEGIN

-- Copyright (C) 1997 Intel Corporation. All rights reserved.
--
-- Ethernet Switch MIB, 97-02-27
--
-- This MIB is used for management switching related parameters 
-- inof Intel Express Ethernet Switches.
--
-- Change History:
-- 97-02-27 Intel Express Switches added

IMPORTS
	TRAP-TYPE FROM RFC-1215
        TimeTicks,Counter       FROM RFC1155-SMI
        DisplayString           FROM RFC1213-MIB
        scanet                  FROM SCANET-MIB
        OBJECT-TYPE             FROM RFC-1212;


        ethSwitch               OBJECT IDENTIFIER ::= { scanet 39 }
        control                 OBJECT IDENTIFIER ::= { ethSwitch 1 }
        module                  OBJECT IDENTIFIER ::= { ethSwitch 2 }
        ports                   OBJECT IDENTIFIER ::= { ethSwitch 3 }
        statistic               OBJECT IDENTIFIER ::= { ethSwitch 4 }
        adaptiveForwardMode     OBJECT IDENTIFIER ::= { ethSwitch 5 }
        chipSets                OBJECT IDENTIFIER ::= { ethSwitch 6 }
        cards                   OBJECT IDENTIFIER ::= { ethSwitch 7 }


        ProductIds ::=  INTEGER {
                              notAvailable(1),
                              es-1520(1163072800),
                              es-1530(1163072816),
                              es-1810(1163073552),
                              es-1820(1163073568),
                              es-1830(1163073584),
                              es-1831(1163073585),
                              es-1832(1163073586),
                              es-1840(1163073600),
                              es-1850(1163073616),
                              es100fx(1163073617), -- es1851
                              es10t24(1163076624), -- es2410
                              es10t24plus(1163076640), -- es2420
                              es10mmt12(1163076656), -- es2430
                              es10mmfl(1163076657), -- es2431
                              es-0012(1163067410),  -- 12 x Telco
                              es-0040(1163067456),  -- 4 x Fiber
                              es-0100(1163067648),  -- 100 MBit - 100 + auto
                              es-0101(1163067649),  -- 100 MBit - 100 + auto
                              es100mmfx(1163067650),  -- es0102, 100 MBit - 100 only
                              es-0103(1163067651),  -- 100 MBit - 100 only
                              es100mmtx(1163067664),  -- es0110, 100 MBit - 10/100 + auto
                              es-0111(1163067665),  -- 100 MBit - 10/100 + auto
                              es-0154(1163067732),  -- 100 MBit - 10/100 + auto
                              es-0155(1163067733),  -- 100 MBit - 10/100 + auto
                              lp-3001(1280323585),
                              lp-3002(1280323586),
                              lp-3003(1280323587),
                              lp-3004(1280323588),
                              lp-3005(1280323589),
                              lp-3006(1280323590),
                              lp-3014(1280323604),
                              lp-3015(1280323605)
                        }


        --
        -- Switch control group
        --

          scSegments OBJECT-TYPE
               SYNTAX  INTEGER {
                          segmentA(1),
                          segmentB(2),
                          segmentAandB(3),
                          segmentC(4),
                          segmentAandC(5),
                          segmentBandC(6),
                          segmentAandBandC(7),
                          none(8)
                          }
               ACCESS  read-write
               STATUS  mandatory
               DESCRIPTION
                       "Object controlling the use of the System Center
                       Backplane. Each bus is assigned a bit value in
                       the object"
               ::= { control 1 }

          defaultSwitchMode OBJECT-TYPE
               SYNTAX  INTEGER {
                          cutThrough(2),
                          fragmentFree(3),
                          storeAndForward(4),
                          adaptive(5)
                          }
               ACCESS  read-write
               STATUS  mandatory
               DESCRIPTION
                       "Default Switch mode. used by the object
                        portSwitchMode when its value is default(1)"
               ::= { control 2 }

          defaultThrottleBackMode OBJECT-TYPE
               SYNTAX  INTEGER {
                          enable(2),
                          disable(3)
                          }
               ACCESS  read-write
               STATUS  mandatory
               DESCRIPTION
                       "Default ThrottleBack mode. used by the object
                        portThrottleBack when its value is default(1)"
               ::= { control 3 }

          networkPort OBJECT-TYPE
               SYNTAX  INTEGER
               ACCESS  read-write
               STATUS  mandatory
               DESCRIPTION
                       "For a Workgroup Switch (only one multi MAC address
                        port), this object determines the network port.
                        The value equals the value of portNumber in the
                        portTable.

                        Notice that this object is valid for Workgroup
                        switches only (ES-2410 and ES-1810). Other types
                        of Switches returns the value 0 and has read-only
                        access."
               ::= { control 4 }


          expansionModule OBJECT-TYPE
               SYNTAX  ProductIds
               ACCESS  read-only
               STATUS  mandatory
               DESCRIPTION
                       "An ID that identifies the expansion module"
               ::= { module 1 }



        --
        -- Switch port group
        --

        portLastChange OBJECT-TYPE
                SYNTAX  TimeTicks
                ACCESS  read-only
                STATUS  mandatory
                DESCRIPTION
                        "The value of sysUpTime at the last time any interface
                         has changed state"
              ::= { ports 1 }



        portTable OBJECT-TYPE
                SYNTAX  SEQUENCE OF PortEntry
                ACCESS  not-accessible
                STATUS  mandatory
                DESCRIPTION
                         "Port Table."
                ::= { ports 2 }

                portEntry OBJECT-TYPE
                        SYNTAX  PortEntry
                        ACCESS  not-accessible
                        STATUS  mandatory
                        DESCRIPTION
                                "A Port entry containing object for a
                                 Switch port."
                        INDEX   { portNumber }
                        ::= { portTable 1 }

                PortEntry ::= SEQUENCE {
                        portNumber              INTEGER,
                        portInterfaceIndex      INTEGER,
                        portLED                 OCTET STRING,
                        portState               OCTET STRING,
                        portCardNumber          INTEGER,
                        portPimNumber           INTEGER,
                        portPimPortNumber       INTEGER
                }

                portNumber OBJECT-TYPE
                        SYNTAX  INTEGER
                        ACCESS  read-only
                        STATUS  mandatory
                        DESCRIPTION
                                "A number that uniquely identifies a port"
                        ::= { portEntry 1 }

                portInterfaceIndex OBJECT-TYPE
                        SYNTAX  INTEGER
                        ACCESS  read-only
                        STATUS  mandatory
                        DESCRIPTION
                                "The value of this object equals the ports
                                interface index value, ex. portIfIndex. If
                                the value of this object is zero, then the
                                port is not active, i.e. does not appear
                                in the portIfTable."
                        ::= { portEntry 2 }

                portLED OBJECT-TYPE
                        SYNTAX  OCTET STRING (SIZE (0..15))
                        ACCESS  read-only
                        STATUS  mandatory
                        DESCRIPTION
                                  "The value of this object represent the
                                  status (colour) of the LED(s) attached to
                                  this port.

                                  Lower 3 bits indicates off/colour
                                  (off(0), red(1), green(2), yellow(4)),
                                  Higher 5 bits reserved for flash
                                  frequency. For value 0-9 the resolution
                                  is 0.1 Hz and 10-31 the resolution is
                                  1.0 Hz. Ex. 8 gives 0.8 Hz and 11 gives
                                  2 Hz.

                                  For PIM slots with two LEDs that can
                                  contain either an expansion card, a one
                                  port PIM or a PIM with multiple ports a
                                  special case is needed. The two LEDs
                                  are mapped into a two LED octets. In
                                  case the PIM slot contain a PIM with
                                  multiple ports a third LED octet
                                  represent the first port on the PIM.

                                  In the case there is two LEDs on the
                                  front, the first LED octet is the front
                                  and the second the back."
                        ::= { portEntry 3 }

                portState OBJECT-TYPE
                        SYNTAX  INTEGER
                        ACCESS  read-only
                        STATUS  mandatory
                        DESCRIPTION
                                "This is a bit array which represent the
                                state of the port.

                                bit 0: Disabled due to configuration
                                bit 1: Hardware error
                                bit 2: No linkpulse
                                bit 3: Disabled by manager
                                bit 4: Disabled by access control
                                bit 5: Disabled due to shared port"

                        ::= { portEntry 4 }

                portCardNumber OBJECT-TYPE
                        SYNTAX  INTEGER
                        ACCESS  read-only
                        STATUS  mandatory
                        DESCRIPTION
                                "The cardNumber in the switch system."
                        ::= { portEntry 5 }

                portPimNumber OBJECT-TYPE
                        SYNTAX  INTEGER
                        ACCESS  read-only
                        STATUS  mandatory
                        DESCRIPTION
                                "The pimNumber in the switch system."
                        ::= { portEntry 6 }

                portPimPortNumber OBJECT-TYPE
                        SYNTAX  INTEGER
                        ACCESS  read-only
                        STATUS  mandatory
                        DESCRIPTION
                                "The relative number of the port on the PIM."
                        ::= { portEntry 7 }


        portIfTable OBJECT-TYPE
                SYNTAX  SEQUENCE OF PortIfEntry
                ACCESS  not-accessible
                STATUS  mandatory
                DESCRIPTION
                        "Switch Interface Table."
                ::= { ports 3 }

                portIfEntry OBJECT-TYPE
                        SYNTAX  PortIfEntry
                        ACCESS  not-accessible
                        STATUS  mandatory
                        DESCRIPTION
                                "An entry containing object for
                                a Switch interface."
                        INDEX   { portIfIndex }
                        ::= { portIfTable 1 }

                PortIfEntry ::= SEQUENCE {
                        portIfIndex             INTEGER,
                        portIfDescr             DisplayString,
                        portIfLocation          DisplayString,
                        portIfSwitchMode        INTEGER,
                        portIfDuplex            INTEGER,
                        portIfThrottleBack      INTEGER,
                        portIfType              INTEGER,
                        portIfDuplexSupported   INTEGER,
                        portIfSpeedSupported    INTEGER,
                        portIfSpeedAndDuplex    INTEGER
                }

                portIfIndex OBJECT-TYPE
                        SYNTAX  INTEGER
                        ACCESS  read-only
                        STATUS  mandatory
                        DESCRIPTION
                                "An index value that uniquely identifies
                                an interface. The interface identified by
                                a particular value of this index is the
                                same interface as identified by the same
                                value of ifIndex."
                        ::= { portIfEntry 1 }

                portIfDescr OBJECT-TYPE
                        SYNTAX  DisplayString (SIZE (0..31))
                        ACCESS  read-write
                        STATUS  mandatory
                        DESCRIPTION
                                "User configurable description of the port."
                        ::= { portIfEntry 2 }

                portIfLocation OBJECT-TYPE
                        SYNTAX  DisplayString (SIZE (0..15))
                        ACCESS  read-write
                        STATUS  mandatory
                        DESCRIPTION
                                "User configurable location of the port."
                        ::= { portIfEntry 3 }

                portIfSwitchMode OBJECT-TYPE
                        SYNTAX  INTEGER {
                                  default(1),
                                  cutThrough(2),
                                  fragmentFree(3),
                                  storeAndForward(4),
                                  adaptive(5),
                                  notAvailable(99)
                                }
                        ACCESS  read-write
                        STATUS  mandatory
                        DESCRIPTION
                                "Port Switch mode. If set to default(1) value
                                from defaultSwitchMode is used."
                        ::= { portIfEntry 4 }

                portIfDuplex OBJECT-TYPE
                        SYNTAX  INTEGER {
                                  autoDetect(1),
                                  half(2),
                                  full(3),
                                  autoDetectedHalf(4),
                                  autoDetectedFull(5),
                                  notAvailable(99)
                                }
                        ACCESS  read-only
                        STATUS  mandatory
                        DESCRIPTION
                                "Port Duplex mode. For ports in auto mode
                                the mode may change automatically between
                                autoDetect(1), autoDetectedHalf(3) and
                                autoDetectedFull(5)."
                        ::= { portIfEntry 5 }

                portIfThrottleBack OBJECT-TYPE
                        SYNTAX  INTEGER {
                                  default(1),
                                  enable(2),
                                  disable(3),
                                  notAvailable(99)
                                }
                        ACCESS  read-write
                        STATUS  mandatory
                        DESCRIPTION
                                "Port ThrottleBack mode. If set to
                                default(1) value from
                                defaultThrottleBackMode is used."
                        ::= { portIfEntry 6 }

                portIfType OBJECT-TYPE
                        SYNTAX  INTEGER {
                                  absent(1),
                                  tenbase2(2),
                                  aui(3),
                                  tenbasetutp(4),
                                  tenbasetstp(5),
                                  tenbasefl(6),
                                  tenbaseflfullduplex(7),
                                  tenbasetxutp(14),
                                  tenbasetxstp(15),
                                  hundredbasetx(51),
                                  hundredbasefx(54),
                                  backplane(100),
                                  hsb(101),
                                  internal(102),
                                  layer3link(110)
                                }
                        ACCESS  read-only
                        STATUS  mandatory
                        DESCRIPTION
                                "The type of Physical interface at the port."
                        ::= { portIfEntry 7 }

                portIfDuplexSupported OBJECT-TYPE
                        SYNTAX  INTEGER {
                                        half(1),
                                        full(2),
                                        halfAndFull(3),
                                        auto(4),
                                        autoAndHalfAndFull(7),
                                        notAvailable(99)
                                }
                        ACCESS  read-only
                        STATUS  mandatory
                        DESCRIPTION
                                "The duplex mode supported for a port."
                        ::= { portIfEntry 8 }

                portIfSpeedSupported OBJECT-TYPE
                        SYNTAX  INTEGER {
                                        speed10Mbit(1),
                                        speed100Mbit(2),
                                        speed10And100Mbit(3),
                                        speedAutoAnd10And100Mbit(4),
                                        speed155Mbit(5),
                                        notAvailable(99)
                                }
                        ACCESS  read-only
                        STATUS  mandatory
                        DESCRIPTION
                                "The speed supported for a port."
                        ::= { portIfEntry 9 }

                portIfSpeedAndDuplex OBJECT-TYPE
                        SYNTAX  OCTET STRING (SIZE (5))
                        ACCESS  read-write
                        STATUS  mandatory
                        DESCRIPTION
                                "This object is used to configure the speed
                                and duplex mode for a port.

                                Byte 1: negotiation
                                                manual(0)
                                                autoDisable(1)
                                                autoAlternative(2)
                                Byte 2: speed
                                                auto(1)
                                                10(2)
                                                100(3)
                                                155(4)
                                Byte 3: alternativeSpeed
                                                unused(0)   (read-only)
                                Byte 4: duplexMode
                                                auto(1)
                                                half(2)
                                                full(3)
                                Byte 5: alternativeDuplexMode
                                                unused(0)   (read-only)
                                                half(2)
                                                full(3)

                                Explanation of the different negotiation:

                                Manual: The port does not support auto
                                detect of speed and duplex which means
                                that only fixed values are legal.

                                AutoDisable: The port supports auto
                                negotiation and if the connected port
                                does not except the suggested values the
                                port will be disabled.

                                AutoAlternative: The port supports auto
                                negotiation and if the connected port
                                does not except the suggested values the
                                port will be set to some alternative
                                values."
                        ::= { portIfEntry 10 }


        --
        -- Switch statistic group
        --

        txStatTable OBJECT-TYPE
                SYNTAX  SEQUENCE OF TxStatEntry
                ACCESS  not-accessible
                STATUS  mandatory
                DESCRIPTION
                        "MIA ASIC Transmit statistic Table."
                ::= { statistic 1 }

                txStatEntry OBJECT-TYPE
                        SYNTAX  TxStatEntry
                        ACCESS  not-accessible
                        STATUS  mandatory
                        DESCRIPTION
                                "An entry containing object for
                                MIA ASIC Transmit statistic."
                        INDEX   { txStatIndex }
                        ::= { txStatTable 1 }

                -- The following counters are available in RFC1643:
                --      txCSenseErrors
                --      txSQEErrors
                --      txLateCollisions
                --      txCollisions[CollCount]
                --      txExcessiveCollisionErrors

                TxStatEntry ::= SEQUENCE {
                        txStatIndex                   INTEGER,
                        txUCPkts64Octets              Counter,
                        txUCPkts65To127Octets         Counter,
                        txUCPkts128To255Octets        Counter,
                        txUCPkts256To511Octets        Counter,
                        txUCPkts512To1023Octets       Counter,
                        txUCPkts1024To1518Octets      Counter,
                        txMCPkts64Octets              Counter,
                        txMCPkts65To127Octets         Counter,
                        txMCPkts128To255Octets        Counter,
                        txMCPkts256To511Octets        Counter,
                        txMCPkts512To1023Octets       Counter,
                        txMCPkts1024To1518Octets      Counter,
                        txBCPkts64Octets              Counter,
                        txBCPkts65To127Octets         Counter,
                        txBCPkts128To255Octets        Counter,
                        txBCPkts256To511Octets        Counter,
                        txBCPkts512To1023Octets       Counter,
                        txBCPkts1024To1518Octets      Counter,
                        txDeffereds                   Counter,
                        txOctetsHis                   Counter,
                        txOctetsLos                   Counter,
                        txExcessiveDefferalsErrors    Counter,
                        txForwardedRxError            Counter,
                        txNiaUnderRunDrops            Counter,
                        txLinkDownEvents              Counter,
                        txAllCounterPackets           OCTET STRING,
                        txAllCounterOthers            OCTET STRING
                }

                txStatIndex OBJECT-TYPE
                        SYNTAX  INTEGER
                        ACCESS  read-only
                        STATUS  mandatory
                        DESCRIPTION
                                "An index value that uniquely identifies
                                an interface. The interface identified by
                                a particular value of this index is the
                                same interface as identified by the same
                                value of ifIndex."
                        ::= { txStatEntry 1 }

                txUCPkts64Octets OBJECT-TYPE
                        SYNTAX  Counter
                        ACCESS  read-only
                        STATUS  mandatory
                        DESCRIPTION
                                "64 byte unicast packets transmitted"
                        ::= { txStatEntry 2 }

                txUCPkts65To127Octets OBJECT-TYPE
                        SYNTAX  Counter
                        ACCESS  read-only
                        STATUS  mandatory
                        DESCRIPTION
                                "65 to 127 byte unicast packets transmitted"
                        ::= { txStatEntry 3 }

                txUCPkts128To255Octets OBJECT-TYPE
                        SYNTAX  Counter
                        ACCESS  read-only
                        STATUS  mandatory
                        DESCRIPTION "128 to 255 byte unicast packets
                                transmitted"
                        ::= { txStatEntry 4 }

                txUCPkts256To511Octets OBJECT-TYPE
                        SYNTAX  Counter
                        ACCESS  read-only
                        STATUS  mandatory
                        DESCRIPTION
                                "256 to 511 byte unicast packets transmitted"
                        ::= { txStatEntry 5 }

                txUCPkts512To1023Octets OBJECT-TYPE
                        SYNTAX  Counter
                        ACCESS  read-only
                        STATUS  mandatory
                        DESCRIPTION
                                "512 to 1023 byte unicast packets transmitted"
                        ::= { txStatEntry 6 }

                txUCPkts1024To1518Octets OBJECT-TYPE
                        SYNTAX  Counter
                        ACCESS  read-only
                        STATUS  mandatory
                        DESCRIPTION
                                "1024 to 1518 byte unicast packets transmitted"
                        ::= { txStatEntry 7 }

                txMCPkts64Octets OBJECT-TYPE
                        SYNTAX  Counter
                        ACCESS  read-only
                        STATUS  mandatory
                        DESCRIPTION
                                "64 byte multicast packets transmitted"
                        ::= { txStatEntry 8 }

                txMCPkts65To127Octets OBJECT-TYPE
                        SYNTAX  Counter
                        ACCESS  read-only
                        STATUS  mandatory
                        DESCRIPTION
                                "65 to 127 byte multicast packets transmitted"
                        ::= { txStatEntry 9 }

                txMCPkts128To255Octets OBJECT-TYPE
                        SYNTAX  Counter
                        ACCESS  read-only
                        STATUS  mandatory
                        DESCRIPTION
                                "128 to 255 byte multicast packets transmitted"
                        ::= { txStatEntry 10 }

                txMCPkts256To511Octets OBJECT-TYPE
                        SYNTAX  Counter
                        ACCESS  read-only
                        STATUS  mandatory
                        DESCRIPTION
                                "256 to 511 byte multicast packets transmitted"
                        ::= { txStatEntry 11 }

                txMCPkts512To1023Octets OBJECT-TYPE
                        SYNTAX  Counter
                        ACCESS  read-only
                        STATUS  mandatory
                        DESCRIPTION
                                "512 to 1023 byte multicast packets
                                transmitted"
                        ::= { txStatEntry 12 }

                txMCPkts1024To1518Octets OBJECT-TYPE
                        SYNTAX  Counter
                        ACCESS  read-only
                        STATUS  mandatory
                        DESCRIPTION
                                "1024 to 1518 byte multicast packets
                                 transmitted"
                        ::= { txStatEntry 13 }

                txBCPkts64Octets OBJECT-TYPE
                        SYNTAX  Counter
                        ACCESS  read-only
                        STATUS  mandatory
                        DESCRIPTION
                                "64 byte broadcast packets transmitted"
                        ::= { txStatEntry 14 }

                txBCPkts65To127Octets OBJECT-TYPE
                        SYNTAX  Counter
                        ACCESS  read-only
                        STATUS  mandatory
                        DESCRIPTION
                                "65 to 127 byte broadcast packets
                                transmitted"
                        ::= { txStatEntry 15 }

                txBCPkts128To255Octets OBJECT-TYPE
                        SYNTAX  Counter
                        ACCESS  read-only
                        STATUS  mandatory
                        DESCRIPTION
                                "128 to 255 byte broadcast packets
                                transmitted"
                        ::= { txStatEntry 16 }

                txBCPkts256To511Octets OBJECT-TYPE
                        SYNTAX  Counter
                        ACCESS  read-only
                        STATUS  mandatory
                        DESCRIPTION
                                "256 to 511 byte broadcast packets
                                transmitted"
                        ::= { txStatEntry 17 }

                txBCPkts512To1023Octets OBJECT-TYPE
                        SYNTAX  Counter
                        ACCESS  read-only
                        STATUS  mandatory
                        DESCRIPTION
                                "512 to 1023 byte broadcast packets
                                transmitted"
                        ::= { txStatEntry 18 }

                txBCPkts1024To1518Octets OBJECT-TYPE
                        SYNTAX  Counter
                        ACCESS  read-only
                        STATUS  mandatory
                        DESCRIPTION
                                "1024 to 1518 byte broadcast packets
                                transmitted"
                        ::= { txStatEntry 19 }

                txDeffereds OBJECT-TYPE
                        SYNTAX  Counter
                        ACCESS  read-only
                        STATUS  mandatory
                        DESCRIPTION
                                "A transmission must await a silent
                                net in Simplex mode. If the transmission
                                is delayed due to a non silent net the
                                transmission is deffered."
                        ::= { txStatEntry 20 }

                txOctetsHis OBJECT-TYPE
                        SYNTAX  Counter
                        ACCESS  read-only
                        STATUS  mandatory
                        DESCRIPTION
                                "High part of a 64 bit octet
                                transmitted counter"
                        ::= { txStatEntry 21 }

                txOctetsLos OBJECT-TYPE
                        SYNTAX  Counter
                        ACCESS  read-only
                        STATUS  mandatory
                        DESCRIPTION
                                "Low part of a 64 bit octet
                                transmitted counter"
                        ::= { txStatEntry 22 }

                txExcessiveDefferalsErrors OBJECT-TYPE
                        SYNTAX  Counter
                        ACCESS  read-only
                        STATUS  mandatory
                        DESCRIPTION
                                "Maximum defferal should be the
                                duration of a maximum length packet, if
                                no errors on the net. Excessive defferal
                                is indicated if defferal duration is more
                                than approximately 2 maximum packets."
                        ::= { txStatEntry 23 }

                txForwardedRxError OBJECT-TYPE
                        SYNTAX  Counter
                        ACCESS  read-only
                        STATUS  mandatory
                        DESCRIPTION
                                "The transmission are aborted on the
                                transmitting port of the switch if the
                                receiving port of the present packet
                                receives are packet with error or
                                receives a collision fragment. This
                                should never occur in Store and forward
                                mode, while collisions never should
                                provoke this event in fragment free mode,
                                except for at late collisions on the
                                receiving net."
                        ::= { txStatEntry 24 }

                txNiaUnderRunDrops OBJECT-TYPE
                        SYNTAX  Counter
                        ACCESS  read-only
                        STATUS  mandatory
                        DESCRIPTION
                                "The NIA TX buffer gets in underrun
                                if the nimbus is overloaded. This should
                                only happen if a configuration is made
                                which loads the Nimbus with more than a
                                load equal to 44 simplex 10Mbit net.

                                NOTE: This only counts for NIA100 interfaces."
                        ::= { txStatEntry 25 }

                txLinkDownEvents OBJECT-TYPE
                        SYNTAX  Counter
                        ACCESS  read-only
                        STATUS  mandatory
                        DESCRIPTION
                                "No link pulses are received. Usually
                                this means that the cable are removed."
                        ::= {txStatEntry 26 }

                txAllCounterPackets OBJECT-TYPE
                        SYNTAX  OCTET STRING (SIZE (127))
                        ACCESS  read-only
                        STATUS  mandatory
                        DESCRIPTION
                                "A collection of all counters for byte
                                and packet counters. This object is
                                needed to optimise SNMP traffic. The
                                counters in this string are

                                txStatIndex                   INTEGER
                                txOctetsHis                   Counter
                                txOctetsLos                   Counter
                                txUCPkts64Octets              Counter
                                txUCPkts65To127Octets         Counter
                                txUCPkts128To255Octets        Counter
                                txUCPkts256To511Octets        Counter
                                txUCPkts512To1023Octets       Counter
                                txUCPkts1024To1518Octets      Counter
                                txMCPkts64Octets              Counter
                                txMCPkts65To127Octets         Counter
                                txMCPkts128To255Octets        Counter
                                txMCPkts256To511Octets        Counter
                                txMCPkts512To1023Octets       Counter
                                txMCPkts1024To1518Octets      Counter
                                txBCPkts64Octets              Counter
                                txBCPkts65To127Octets         Counter
                                txBCPkts128To255Octets        Counter
                                txBCPkts256To511Octets        Counter
                                txBCPkts512To1023Octets       Counter
                                txBCPkts1024To1518Octets      Counter

                                The values are represented in the OCTET
                                STRING in the listed order, each value
                                stored as a 32 bits big engine value."
                        ::= { txStatEntry 27 }


                txAllCounterOthers OBJECT-TYPE
                        SYNTAX  OCTET STRING (SIZE (127))
                        ACCESS  read-only
                        STATUS  mandatory
                        DESCRIPTION
                                "A collection of all counters other than
                                for byte and packet counters. This object is
                                needed to optimise SNMP traffic. The
                                counters in this string are

                                txStatIndex                   INTEGER
                                txDeffereds                   Counter
                                txExcessiveDefferalsErrors    Counter
                                txForwardedRxError            Counter
                                txNiaUnderRunDrops            Counter
                                txLinkDownEvents              Counter

                                -- Counters from RFC1643
                                txCSenseErrors                Counter
                                txSQEErrors                   Counter
                                txLateCollisions              Counter
                                txExcessiveCollisionErrors    Counter
                                txSingleCollisionFrames       Counter
                                txMultipleCollisionFrames     Counter

                                The values are represented in the OCTET
                                STRING in the listed order, each value
                                stored as a 32 bits big engine value."
                        ::= { txStatEntry 28 }




        rxStatTable OBJECT-TYPE
                SYNTAX  SEQUENCE OF RxStatEntry
                ACCESS  not-accessible
                STATUS  mandatory
                DESCRIPTION
                        "MIA ASIC Receive statistic Table."
                ::= { statistic 2 }

                rxStatEntry OBJECT-TYPE
                        SYNTAX  RxStatEntry
                        ACCESS  not-accessible
                        STATUS  mandatory
                        DESCRIPTION
                                "An entry containing object for
                                MIA ASIC Receive statistic."
                        INDEX   { rxStatIndex }
                        ::= { rxStatTable 1 }

                -- The following counters are available in RFC1643:
                --      rxAlignErrors
                --      rxFCSErrors

                RxStatEntry ::= SEQUENCE {
                        rxStatIndex                        INTEGER,
                        rxUCPkts64OctetsLocals             Counter,
                        rxUCPkts64OctetsForwardeds         Counter,
                        rxUCPkts65To127OctetsLocals        Counter,
                        rxUCPkts65To127OctetsForwardeds    Counter,
                        rxUCPkts128To255OctetsLocals       Counter,
                        rxUCPkts128To255OctetsForwardeds   Counter,
                        rxUCPkts256To511OctetsLocals       Counter,
                        rxUCPkts256To511OctetsForwardeds   Counter,
                        rxUCPkts512To1023OctetsLocals      Counter,
                        rxUCPkts512To1023OctetsForwardeds  Counter,
                        rxUCPkts1024To1518OctetsLocals     Counter,
                        rxUCPkts1024To1518OctetsForwardeds Counter,
                        rxShortErrors                      Counter,
                        rxRuntErrors                       Counter,
                        rxDataRateMMErrors                 Counter,
                        rxMCPkts64OctetsLocals             Counter,
                        rxMCPkts64OctetsForwardeds         Counter,
                        rxMCPkts65To127OctetsLocals        Counter,
                        rxMCPkts65To127OctetsForwardeds    Counter,
                        rxMCPkts128To255OctetsLocals       Counter,
                        rxMCPkts128To255OctetsForwardeds   Counter,
                        rxMCPkts256To511OctetsLocals       Counter,
                        rxMCPkts256To511OctetsForwardeds   Counter,
                        rxMCPkts512To1023OctetsLocals      Counter,
                        rxMCPkts512To1023OctetsForwardeds  Counter,
                        rxMCPkts1024To1518OctetsLocals     Counter,
                        rxMCPkts1024To1518OctetsForwardeds Counter,
                        rxOctetsLocalHis                   Counter,
                        rxOctetsLocalLos                   Counter,
                        rxOctetsForwardedHis               Counter,
                        rxOctetsForwardedLos               Counter,
                        rxBCPkts64OctetsLocals             Counter,
                        rxBCPkts64OctetsForwardeds         Counter,
                        rxBCPkts65To127OctetsLocals        Counter,
                        rxBCPkts65To127OctetsForwardeds    Counter,
                        rxBCPkts128To255OctetsLocals       Counter,
                        rxBCPkts128To255OctetsForwardeds   Counter,
                        rxBCPkts256To511OctetsLocals       Counter,
                        rxBCPkts256To511OctetsForwardeds   Counter,
                        rxBCPkts512To1023OctetsLocals      Counter,
                        rxBCPkts512To1023OctetsForwardeds  Counter,
                        rxBCPkts1024To1518OctetsLocals     Counter,
                        rxBCPkts1024To1518OctetsForwardeds Counter,
                        rxFilterMACUnexp2ndPortDrops       Counter,
                        rxFilterIllegalMACDrops            Counter,
                        rxFlowCtrlCollCounter              Counter,
                        rxVeryLongErrors                   Counter,
                        rxLongErrors                       Counter,
                        rxPiaOutOfPoolsDrop                Counter,
                        rxManchesterCodeViolationErrors    Counter,
                        rxRxJabbers                        Counter,
                        rxNiaOverRunDrops                  Counter,
                        rxAllCounterPackets                OCTET STRING,
                        rxAllCounterOthers                 OCTET STRING
                }

                rxStatIndex OBJECT-TYPE
                        SYNTAX  INTEGER
                        ACCESS  read-only
                        STATUS  mandatory
                        DESCRIPTION
                                "An index value that uniquely identifies
                                an interface. The interface identified by
                                a particular value of this index is the
                                same interface as identified by the same
                                value of ifIndex."
                        ::= { rxStatEntry 1 }

                rxUCPkts64OctetsLocals OBJECT-TYPE
                        SYNTAX  Counter
                        ACCESS  read-only
                        STATUS  mandatory
                        DESCRIPTION
                                "64 byte unicast packets received
                                which has not been forwarded"
                        ::= { rxStatEntry 2 }

                rxUCPkts64OctetsForwardeds OBJECT-TYPE
                        SYNTAX  Counter
                        ACCESS  read-only
                        STATUS  mandatory
                        DESCRIPTION
                                "64 byte unicast packets received
                                which has been forwarded"
                        ::= { rxStatEntry 3 }

                rxUCPkts65To127OctetsLocals OBJECT-TYPE
                        SYNTAX  Counter
                        ACCESS  read-only
                        STATUS  mandatory
                        DESCRIPTION
                                "65 to 127 byte unicast packets received
                                which has not been forwarded"
                        ::= { rxStatEntry 4 }

                rxUCPkts65To127OctetsForwardeds OBJECT-TYPE
                        SYNTAX  Counter
                        ACCESS  read-only
                        STATUS  mandatory
                        DESCRIPTION
                                "65 to 127 byte unicast packets received
                                which has been forwarded"
                        ::= { rxStatEntry 5 }

                rxUCPkts128To255OctetsLocals OBJECT-TYPE
                        SYNTAX  Counter
                        ACCESS  read-only
                        STATUS  mandatory
                        DESCRIPTION
                                "128 to 255 byte unicast packets received
                                which has not been forwarded"
                        ::= { rxStatEntry 6 }

                rxUCPkts128To255OctetsForwardeds OBJECT-TYPE
                        SYNTAX  Counter
                        ACCESS  read-only
                        STATUS  mandatory
                        DESCRIPTION
                                "128 to 255 byte unicast packets received
                                which has been forwarded"
                        ::= { rxStatEntry 7 }

                rxUCPkts256To511OctetsLocals OBJECT-TYPE
                        SYNTAX  Counter
                        ACCESS  read-only
                        STATUS  mandatory
                        DESCRIPTION
                                "256 to 511 byte unicast packets received
                                which has not been forwarded"
                        ::= { rxStatEntry 8 }

                rxUCPkts256To511OctetsForwardeds OBJECT-TYPE
                        SYNTAX  Counter
                        ACCESS  read-only
                        STATUS  mandatory
                        DESCRIPTION
                                "255 to 511 byte unicast packets received
                                which has been forwarded"
                        ::= { rxStatEntry 9 }

                rxUCPkts512To1023OctetsLocals OBJECT-TYPE
                        SYNTAX  Counter
                        ACCESS  read-only
                        STATUS  mandatory
                        DESCRIPTION
                                "512 to 1023 byte unicast packets received
                                which has not been forwarded"
                        ::= { rxStatEntry 10 }

                rxUCPkts512To1023OctetsForwardeds OBJECT-TYPE
                        SYNTAX  Counter
                        ACCESS  read-only
                        STATUS  mandatory
                        DESCRIPTION
                                "512 to 1023 byte unicast packets received
                                which has been forwarded"
                        ::= { rxStatEntry 11 }

                rxUCPkts1024To1518OctetsLocals OBJECT-TYPE
                        SYNTAX  Counter
                        ACCESS  read-only
                        STATUS  mandatory
                        DESCRIPTION
                                "1024 to 1518 byte unicast packets received
                                which has not been forwarded"
                        ::= { rxStatEntry 12 }

                rxUCPkts1024To1518OctetsForwardeds OBJECT-TYPE
                        SYNTAX  Counter
                        ACCESS  read-only
                        STATUS  mandatory
                        DESCRIPTION
                                "1024 to 1518 byte unicast packets received
                                which has been forwarded"
                        ::= { rxStatEntry 13 }

                rxShortErrors OBJECT-TYPE
                        SYNTAX  Counter
                        ACCESS  read-only
                        STATUS  mandatory
                        DESCRIPTION
                                "Receive fragments shorter than
                                minimum ordinary collision fragment."
                          ::= {rxStatEntry 14 }

                rxRuntErrors OBJECT-TYPE
                        SYNTAX  Counter
                        ACCESS  read-only
                        STATUS  mandatory
                        DESCRIPTION
                                "Ordinary collision fragments received."
                        ::= { rxStatEntry 15 }

                rxDataRateMMErrors OBJECT-TYPE
                        SYNTAX  Counter
                        ACCESS  read-only
                        STATUS  mandatory
                        DESCRIPTION
                                "Data Rate Miss Match Error occurs if
                                the data rate deviation is larger
                                than allowed. This should only occur if
                                problems with the TX oscillator in the
                                adapter transmitting the frame."
                        ::= {rxStatEntry 16 }

                rxMCPkts64OctetsLocals OBJECT-TYPE
                        SYNTAX  Counter
                        ACCESS  read-only
                        STATUS  mandatory
                        DESCRIPTION
                                "64 byte multicast packets received
                                which has not been forwarded"
                        ::= { rxStatEntry 17 }

                rxMCPkts64OctetsForwardeds OBJECT-TYPE
                        SYNTAX  Counter
                        ACCESS  read-only
                        STATUS  mandatory
                        DESCRIPTION
                                "64 byte multicast packets received
                                which has been forwarded"
                        ::= { rxStatEntry 18 }

                rxMCPkts65To127OctetsLocals OBJECT-TYPE
                        SYNTAX  Counter
                        ACCESS  read-only
                        STATUS  mandatory
                        DESCRIPTION
                                "65 to 127 byte multicast packets received
                                which has not been forwarded"
                        ::= { rxStatEntry 19 }

                rxMCPkts65To127OctetsForwardeds OBJECT-TYPE
                        SYNTAX  Counter
                        ACCESS  read-only
                        STATUS  mandatory
                        DESCRIPTION
                                "65 to 127 byte multicast packets received
                                which has been forwarded"
                        ::= { rxStatEntry 20 }

                rxMCPkts128To255OctetsLocals OBJECT-TYPE
                        SYNTAX  Counter
                        ACCESS  read-only
                        STATUS  mandatory
                        DESCRIPTION
                                "128 to 255 byte multicast packets received
                                which has not been forwarded"
                        ::= { rxStatEntry 21 }

                rxMCPkts128To255OctetsForwardeds OBJECT-TYPE
                        SYNTAX  Counter
                        ACCESS  read-only
                        STATUS  mandatory
                        DESCRIPTION
                                "128 to 255 byte multicast packets received
                                which has been forwarded"
                        ::= { rxStatEntry 22 }

                rxMCPkts256To511OctetsLocals OBJECT-TYPE
                        SYNTAX  Counter
                        ACCESS  read-only
                        STATUS  mandatory
                        DESCRIPTION
                                "256 to 511 byte multicast packets received
                                which has not been forwarded"
                        ::= { rxStatEntry 23 }

                rxMCPkts256To511OctetsForwardeds OBJECT-TYPE
                        SYNTAX  Counter
                        ACCESS  read-only
                        STATUS  mandatory
                        DESCRIPTION
                                "256 to 511 byte multicast packets received
                                which has been forwarded"
                        ::= { rxStatEntry 24 }

                rxMCPkts512To1023OctetsLocals OBJECT-TYPE
                        SYNTAX  Counter
                        ACCESS  read-only
                        STATUS  mandatory
                        DESCRIPTION
                                "512 to 1023 byte multicast packets received
                                which has not been forwarded"
                        ::= { rxStatEntry 25 }

                rxMCPkts512To1023OctetsForwardeds OBJECT-TYPE
                        SYNTAX  Counter
                        ACCESS  read-only
                        STATUS  mandatory
                        DESCRIPTION
                                "512 to 1023 byte multicast packets received
                                which has been forwarded"
                        ::= { rxStatEntry 26 }

                rxMCPkts1024To1518OctetsLocals OBJECT-TYPE
                        SYNTAX  Counter
                        ACCESS  read-only
                        STATUS  mandatory
                        DESCRIPTION
                                "1024 to 1518 byte multicast packets received
                                which has not been forwarded"
                        ::= { rxStatEntry 27 }

                rxMCPkts1024To1518OctetsForwardeds OBJECT-TYPE
                        SYNTAX  Counter
                        ACCESS  read-only
                        STATUS  mandatory
                        DESCRIPTION
                                "1024 to 1518 byte multicast packets received
                                which has been forwarded"
                        ::= { rxStatEntry 28 }

                rxOctetsLocalHis OBJECT-TYPE
                        SYNTAX  Counter
                        ACCESS  read-only
                        STATUS  mandatory
                        DESCRIPTION
                                "High part of a 64 bit octet received
                                counter which has not been forwarded"
                        ::= { rxStatEntry 29 }

                rxOctetsLocalLos OBJECT-TYPE
                        SYNTAX  Counter
                        ACCESS  read-only
                        STATUS  mandatory
                        DESCRIPTION
                                "Low part of a 64 bit octet received
                                counter which has not been forwarded"
                        ::= { rxStatEntry 30 }

                rxOctetsForwardedHis OBJECT-TYPE
                        SYNTAX  Counter
                        ACCESS  read-only
                        STATUS  mandatory
                        DESCRIPTION
                                "High part of a 64 bit octet received
                                counter which has been forwarded"
                        ::= { rxStatEntry 31 }

                rxOctetsForwardedLos OBJECT-TYPE
                        SYNTAX  Counter
                        ACCESS  read-only
                        STATUS  mandatory
                        DESCRIPTION
                                "Low part of a 64 bit octet received
                                counter which has been forwarded"
                        ::= { rxStatEntry 32 }

                rxBCPkts64OctetsLocals OBJECT-TYPE
                        SYNTAX  Counter
                        ACCESS  read-only
                        STATUS  mandatory
                        DESCRIPTION
                                "64 byte broadcast packets received
                                which has not been forwarded"
                        ::= { rxStatEntry 33 }

                rxBCPkts64OctetsForwardeds OBJECT-TYPE
                        SYNTAX  Counter
                        ACCESS  read-only
                        STATUS  mandatory
                        DESCRIPTION
                                "64 byte broadcast packets received
                                which has been forwarded"
                        ::= { rxStatEntry 34 }

                rxBCPkts65To127OctetsLocals OBJECT-TYPE
                        SYNTAX  Counter
                        ACCESS  read-only
                        STATUS  mandatory
                        DESCRIPTION
                                "65 to 127 byte broadcast packets received
                                which has not been forwarded"
                        ::= { rxStatEntry 35 }

                rxBCPkts65To127OctetsForwardeds OBJECT-TYPE
                        SYNTAX  Counter
                        ACCESS  read-only
                        STATUS  mandatory
                        DESCRIPTION
                                "65 to 127 byte broadcast packets received
                                which has been forwarded"
                        ::= { rxStatEntry 36 }

                rxBCPkts128To255OctetsLocals OBJECT-TYPE
                        SYNTAX  Counter
                        ACCESS  read-only
                        STATUS  mandatory
                        DESCRIPTION
                                "128 to 255 byte broadcast packets received
                                which has not been forwarded"
                        ::= { rxStatEntry 37 }

                rxBCPkts128To255OctetsForwardeds OBJECT-TYPE
                        SYNTAX  Counter
                        ACCESS  read-only
                        STATUS  mandatory
                        DESCRIPTION
                                "128 to 255 byte broadcast packets received
                                which has been forwarded"
                        ::= { rxStatEntry 38 }

                rxBCPkts256To511OctetsLocals OBJECT-TYPE
                        SYNTAX  Counter
                        ACCESS  read-only
                        STATUS  mandatory
                        DESCRIPTION
                                "256 to 511 byte broadcast packets received
                                which has not been forwarded"
                        ::= { rxStatEntry 39 }

                rxBCPkts256To511OctetsForwardeds OBJECT-TYPE
                        SYNTAX  Counter
                        ACCESS  read-only
                        STATUS  mandatory
                        DESCRIPTION
                                "256 to 511 byte broadcast packets received
                                which has been forwarded"
                        ::= { rxStatEntry 40 }

                rxBCPkts512To1023OctetsLocals OBJECT-TYPE
                        SYNTAX  Counter
                        ACCESS  read-only
                        STATUS  mandatory
                        DESCRIPTION
                                "512 to 1023 byte broadcast packets received
                                which has not been forwarded"
                        ::= { rxStatEntry 41 }

                rxBCPkts512To1023OctetsForwardeds OBJECT-TYPE
                        SYNTAX  Counter
                        ACCESS  read-only
                        STATUS  mandatory
                        DESCRIPTION
                                "512 to 1023 byte broadcast packets received
                                which has been forwarded"
                        ::= { rxStatEntry 42 }

                rxBCPkts1024To1518OctetsLocals OBJECT-TYPE
                        SYNTAX  Counter
                        ACCESS  read-only
                        STATUS  mandatory
                        DESCRIPTION
                                "1024 to 1518 byte broadcast packets received
                                which has not been forwarded"
                        ::= { rxStatEntry 43 }

                rxBCPkts1024To1518OctetsForwardeds OBJECT-TYPE
                        SYNTAX  Counter
                        ACCESS  read-only
                        STATUS  mandatory
                        DESCRIPTION
                                "1024 to 1518 byte broadcast packets received
                                which has been forwarded"
                        ::= { rxStatEntry 44 }

                rxFilterMACUnexp2ndPortDrops OBJECT-TYPE
                        SYNTAX  Counter
                        ACCESS  read-only
                        STATUS  mandatory
                        DESCRIPTION
                                "MAC address has been moved from one
                                port to another"
                        ::= { rxStatEntry 45 }

                rxFilterIllegalMACDrops OBJECT-TYPE
                        SYNTAX  Counter
                        ACCESS  read-only
                        STATUS  mandatory
                        DESCRIPTION
                                "Indicate more than one MAC address
                                on a port which is not a network port or
                                in general that the filter discards a
                                packet due to an illegal source MAC
                                address"
                        ::= { rxStatEntry 46 }

                rxFlowCtrlCollCounter OBJECT-TYPE
                        SYNTAX  Counter
                        ACCESS  read-only
                        STATUS  mandatory
                        DESCRIPTION
                                "This counter counts the number of
                                Flow Control collisions, which are
                                generated due to flow control. Flow
                                control are used when most of the pool
                                memory are used to limit further amount of
                                RX data until memory available.  "
                        ::= { rxStatEntry 47 }

                rxVeryLongErrors OBJECT-TYPE
                        SYNTAX  Counter
                        ACCESS  read-only
                        STATUS  mandatory
                        DESCRIPTION
                                "Occurs only if frame longer than
                                6000 bytes are received."
                        ::= { rxStatEntry 48 }

                rxLongErrors OBJECT-TYPE
                        SYNTAX  Counter
                        ACCESS  read-only
                        STATUS  mandatory
                        DESCRIPTION
                                "Occurs if a frame longer than 1518
                                bytes and shorter than 6000 bytes are
                                received."
                        ::= { rxStatEntry 49 }

                rxPiaOutOfPoolsDrop OBJECT-TYPE
                        SYNTAX  Counter
                        ACCESS  read-only
                        STATUS  mandatory
                        DESCRIPTION
                                "Reception is aborted due to lack of
                                Pool memory. The switch is overloaded."
                        ::= { rxStatEntry 50 }

                rxManchesterCodeViolationErrors OBJECT-TYPE
                        SYNTAX  Counter
                        ACCESS  read-only
                        STATUS  mandatory
                        DESCRIPTION
                                "An illegal symbol received on a
                                100Base-X port."
                        ::= { rxStatEntry 51 }

                rxRxJabbers OBJECT-TYPE
                        SYNTAX  Counter
                        ACCESS  read-only
                        STATUS  mandatory
                        DESCRIPTION
                                "Jabber is counted instead of a long
                                error if the frame contains dribble bits
                                or FCS error."
                        ::= { rxStatEntry 52 }

                rxNiaOverRunDrops OBJECT-TYPE
                        SYNTAX  Counter
                        ACCESS  read-only
                        STATUS  mandatory
                        DESCRIPTION
                                "The NIA RX buffer gets in overrun if
                                the nimbus is overloaded. This should
                                only happen if a configuration is made
                                which loads the Nimbus with more than a
                                load equal to 44 simplex 10Mbit net. "
                        ::= { rxStatEntry 53 }

                rxAllCounterPackets OBJECT-TYPE
                        SYNTAX  OCTET STRING (SIZE (164))
                        ACCESS  read-only
                        STATUS  mandatory
                        DESCRIPTION
                                "A collection of all counters for byte
                                and packet counters. This object is
                                needed to optimise SNMP traffic. The
                                counters in this string are

                                rxStatIndex                        INTEGER
                                rxOctetsLocalHis                   Counter
                                rxOctetsLocalLos                   Counter
                                rxOctetsForwardedHis               Counter
                                rxOctetsForwardedLos               Counter
                                rxUCPkts64OctetsLocals             Counter
                                rxUCPkts64OctetsForwardeds         Counter
                                rxUCPkts65To127OctetsLocals        Counter
                                rxUCPkts65To127OctetsForwardeds    Counter
                                rxUCPkts128To255OctetsLocals       Counter
                                rxUCPkts128To255OctetsForwardeds   Counter
                                rxUCPkts256To511OctetsLocals       Counter
                                rxUCPkts256To511OctetsForwardeds   Counter
                                rxUCPkts512To1023OctetsLocals      Counter
                                rxUCPkts512To1023OctetsForwardeds  Counter
                                rxUCPkts1024To1518OctetsLocals     Counter
                                rxUCPkts1024To1518OctetsForwardeds Counter
                                rxMCPkts64OctetsLocals             Counter
                                rxMCPkts64OctetsForwardeds         Counter
                                rxMCPkts65To127OctetsLocals        Counter
                                rxMCPkts65To127OctetsForwardeds    Counter
                                rxMCPkts128To255OctetsLocals       Counter
                                rxMCPkts128To255OctetsForwardeds   Counter
                                rxMCPkts256To511OctetsLocals       Counter
                                rxMCPkts256To511OctetsForwardeds   Counter
                                rxMCPkts512To1023OctetsLocals      Counter
                                rxMCPkts512To1023OctetsForwardeds  Counter
                                rxMCPkts1024To1518OctetsLocals     Counter
                                rxMCPkts1024To1518OctetsForwardeds Counter
                                rxBCPkts64OctetsLocals             Counter
                                rxBCPkts64OctetsForwardeds         Counter
                                rxBCPkts65To127OctetsLocals        Counter
                                rxBCPkts65To127OctetsForwardeds    Counter
                                rxBCPkts128To255OctetsLocals       Counter
                                rxBCPkts128To255OctetsForwardeds   Counter
                                rxBCPkts256To511OctetsLocals       Counter
                                rxBCPkts256To511OctetsForwardeds   Counter
                                rxBCPkts512To1023OctetsLocals      Counter
                                rxBCPkts512To1023OctetsForwardeds  Counter
                                rxBCPkts1024To1518OctetsLocals     Counter
                                rxBCPkts1024To1518OctetsForwardeds Counter

                                The values are represented in the OCTET
                                STRING in the listed order, each value
                                stored as a 32 bits big engine value."
                        ::= { rxStatEntry 54 }


                rxAllCounterOthers OBJECT-TYPE
                        SYNTAX  OCTET STRING (SIZE (60))
                        ACCESS  read-only
                        STATUS  mandatory
                        DESCRIPTION
                                "A collection of all counters other than
                                for byte and packet counters. This object is
                                needed to optimise SNMP traffic. The
                                counters in this string are

                                rxStatIndex                        INTEGER
                                rxShortErrors                      Counter
                                rxRuntErrors                       Counter
                                rxDataRateMMErrors                 Counter
                                rxFilterMACUnexp2ndPortDrops       Counter
                                rxFilterIllegalMACDrops            Counter
                                rxFlowCtrlCollCounter              Counter
                                rxVeryLongErrors                   Counter
                                rxLongErrors                       Counter
                                rxPiaOutOfPoolsDrop                Counter
                                rxManchesterCodeViolationErrors    Counter
                                rxRxJabbers                        Counter
                                rxNiaOverRunDrops                  Counter

                                -- Counters from RFC1643
                                rxAlignErrors                      Counter
                                rxFCSErrors                        Counter


                                The values are represented in the OCTET
                                STRING in the listed order, each value
                                stored as a 32 bits big engine value."
                        ::= { rxStatEntry 55 }

                totalRxTxPackets OBJECT-TYPE
                        SYNTAX  OCTET STRING
                        ACCESS  read-only
                        STATUS  mandatory
                        DESCRIPTION
                                "This object is used for LED control to display
                                traffic. Values in the string are all packets
                                transmitted and received at each port. The number
                                and order of values equals the ifIndex. Each entry
                                is 4 bytes. The first 4 bytes of the string is the
                                value of portLastChange."
                        ::= { statistic 3 }

                totalCollisions OBJECT-TYPE
                        SYNTAX  OCTET STRING
                        ACCESS  read-only
                        STATUS  mandatory
                        DESCRIPTION
                                "This object is used for LED control to display
                                collision. Values in the string are the total
                                collisions at each port. The number and order of
                                values equals the ifIndex. Each entry is 4 bytes.
                                The first 4 bytes of the string is the value of
                                portLastChange."
                        ::= { statistic 4 }


          adaptiveForwardModeSampleTime OBJECT-TYPE
               SYNTAX  INTEGER
               ACCESS  read-write
               STATUS  mandatory
               DESCRIPTION
                       "Specify how long (sec) the received packets will be
                        monitored. The resulting forwarding mode will
                        be based on the quality of the packets"
               ::= { adaptiveForwardMode 1 }

          adaptiveForwardModeRuntsOffset OBJECT-TYPE
               SYNTAX  INTEGER
               ACCESS  read-write
               STATUS  mandatory
               DESCRIPTION
                       "Specifies the minimum amount of runts during the
                       sample time which forces the port out of
                       cutThrough(2). The value is specified in per mille
                       * 1000"
               ::= { adaptiveForwardMode 2 }

          adaptiveForwardModeRuntsRange OBJECT-TYPE
               SYNTAX  INTEGER
               ACCESS  read-write
               STATUS  mandatory
               DESCRIPTION
                       "Specifies together with
                       adaptiveForwardModeRuntsOffset the maximum amount
                       of runts allowed during the sample time, which
                       forces the port back to cutThrough(2). The value is
                       specified in per mille * 1000"
               ::= { adaptiveForwardMode 3 }

          adaptiveForwardModeCrcsOffset OBJECT-TYPE
               SYNTAX  INTEGER
               ACCESS  read-write
               STATUS  mandatory
               DESCRIPTION
                       "Specifies the maximum amount of crc errors during
                       the sample time which forces the port out of Store
                       and Forward. The value is specified in per mille *
                       1000"
               ::= { adaptiveForwardMode 4 }

          adaptiveForwardModeCrcsRange OBJECT-TYPE
               SYNTAX  INTEGER
               ACCESS  read-write
               STATUS  mandatory
               DESCRIPTION
                       "Specifies together with
                       adaptiveForwardModeCrcsOffset the maximum amount
                       of crc errors during the sample time which forces
                       the port out of Store and Forward. The value is
                       specified in per mille * 1000"
               ::= { adaptiveForwardMode 5 }


        chipSetNIA10  OBJECT IDENTIFIER ::= { chipSets 1 }
        chipSetNIA100 OBJECT IDENTIFIER ::= { chipSets 2 }



        cardTable OBJECT-TYPE
                SYNTAX  SEQUENCE OF CardEntry
                ACCESS  not-accessible
                STATUS  mandatory
                DESCRIPTION
                        "This table describes which cards a switch
                        system consist of and how they are connected."
                ::= { cards 1 }

                cardEntry OBJECT-TYPE
                        SYNTAX  CardEntry
                        ACCESS  not-accessible
                        STATUS  mandatory
                        DESCRIPTION
                                "An entry contains either a card or an
                                expansion card and how many PIMs it contains."
                        INDEX { cardNumber }
                        ::= { cardTable 1 }

                CardEntry ::= SEQUENCE {
                        cardNumber              INTEGER,
                        cardId                  ProductIds,
                        cardFirstPort           INTEGER,
                        cardMaxPims             INTEGER
                }

                cardNumber OBJECT-TYPE
                        SYNTAX  INTEGER
                        ACCESS  read-only
                        STATUS  mandatory
                        DESCRIPTION
                                "The card index number."
                        ::= { cardEntry 1 }

                cardId OBJECT-TYPE
                        SYNTAX  ProductIds
                        ACCESS  read-only
                        STATUS  mandatory
                        DESCRIPTION
                                "The produce identification the card."
                        ::= { cardEntry 2 }

                cardFirstPort OBJECT-TYPE
                        SYNTAX  INTEGER
                        ACCESS  read-only
                        STATUS  mandatory
                        DESCRIPTION
                                "The portNumber of the first port on the card."
                        ::= { cardEntry 3 }

                cardMaxPims OBJECT-TYPE
                        SYNTAX  INTEGER
                        ACCESS  read-only
                        STATUS  mandatory
                        DESCRIPTION
                                "The maximum number of PIMs this card
                                can contain."
                        ::= { cardEntry 4 }


        pimTable OBJECT-TYPE
                SYNTAX  SEQUENCE OF PimEntry
                ACCESS  not-accessible
                STATUS  mandatory
                DESCRIPTION
                        "This table describes the PIMs inserted in
                        the switch system."
                ::= { cards 2 }

                pimEntry OBJECT-TYPE
                        SYNTAX  PimEntry
                        ACCESS  not-accessible
                        STATUS  mandatory
                        DESCRIPTION
                                "An entry describes the PIM."
                        INDEX { pimCardNumber, pimNumber }
                        ::= { pimTable 1 }

                PimEntry ::= SEQUENCE {
                        pimCardNumber           INTEGER,
                        pimNumber               INTEGER,
                        pimId                   ProductIds,
                        pimFirstPort            INTEGER,
                        pimNumberOfPorts        INTEGER
                }

                pimCardNumber OBJECT-TYPE
                        SYNTAX  INTEGER
                        ACCESS  read-only
                        STATUS  mandatory
                        DESCRIPTION
                                "The card number in the cardTable that
                                this PIM is inserted in."
                        ::= { pimEntry 1 }

                pimNumber OBJECT-TYPE
                        SYNTAX  INTEGER
                        ACCESS  read-only
                        STATUS  mandatory
                        DESCRIPTION
                                "The number of the PIM."
                        ::= { pimEntry 2 }

                pimId OBJECT-TYPE
                        SYNTAX  ProductIds
                        ACCESS  read-only
                        STATUS  mandatory
                        DESCRIPTION
                                "The product identification of the PIM."
                        ::= { pimEntry 3 }

                pimFirstPort OBJECT-TYPE
                        SYNTAX  INTEGER
                        ACCESS  read-only
                        STATUS  mandatory
                        DESCRIPTION
                                "The portNumber of the first port on the PIM."
                        ::= { pimEntry 4 }

                pimNumberOfPorts OBJECT-TYPE
                        SYNTAX  INTEGER
                        ACCESS  read-only
                        STATUS  mandatory
                        DESCRIPTION
                                "The number of ports on the PIM."
                        ::= { pimEntry 5 }



---
--- Trap section
---

    ethSwitchPermVioEvent TRAP-TYPE
        ENTERPRISE  ethSwitch
        VARIABLES   { portIfIndex}
        DESCRIPTION
                    "This trap is sent when there has been a permanent entry
                     violation. A MAC address has been detected at an other
                     port than the port where it has been configured as a
                     permanent entry.
                     The variable portIfIndex indicates the port where the
                     MAC incorrectly has been detected.
                     The problem can be solved by re-configuring the MAC's
                     permanent entry, or by physical moving the MAC to the
                     port it has been configured for."
    ::= 1


    ethSwitchOnlyOneMACEvent TRAP-TYPE
        ENTERPRISE  ethSwitch
        VARIABLES   { portIfIndex}
        DESCRIPTION
                    "This trap is sent when a port detects more that one MAC
                     address at a port intended for only one MAC.
                     This Trap can only be sent from a Concentrator Switch
                     where only one MAC is allowed, except from the network
                     port. It can NOT be sent from a Backbone Switch since
                     it allows multiple MAC's at all ports.
                     The variable portIfIndex indicates the port where the
                     MAC limit of one has bee exceeded.
                     The problem can be solved by physical moving the MAC
                     to a spare Concentrator Switch port."
    ::= 2


    ethSwitchMACVioEvent TRAP-TYPE
        ENTERPRISE  ethSwitch
        VARIABLES   { portIfIndex }
        DESCRIPTION
                    "This trap is sent when there has been detected a MAC
                     access control violation.
                     A MAC address has been detected at a port with MAC
                     access restriction, and the MAC was not allowed.
                     The variable portIfIndex indicates the port with the
                     MAC access violation."
    ::= 3

    ethSwitchAdaptiveForwEvent TRAP-TYPE
        ENTERPRISE  ethSwitch
        VARIABLES   { portIfIndex, portIfSwitchMode, portIfSwitchMode }
        DESCRIPTION
                    "This trap is sent when a port automatically is
                    changing forwarding mode. This will only happen when
                    the port has been configured to Adaptive mode.
                    The syntax is (Portnumber, New mode, Old mode)
                    Mode numbers is:
                        2 = Cut-Through
                        3 = Fragment Free
                        4 = Store and Forward"
    ::= 4

    ethSwitchMACFilterVioEvent TRAP-TYPE
        ENTERPRISE  ethSwitch
        VARIABLES   { portIfIndex }
        DESCRIPTION
                    "Port/MAC filter MAC violation on port: %portIfIndex%

                     This trap is sent when there has been detected a MAC
                     address on a port (portIfIndex), where this MAC is
                     not allowed access through the switch. Access restriction
                     is due to entry in the Port/MAC filters of the switch."
    ::= 5


        END
