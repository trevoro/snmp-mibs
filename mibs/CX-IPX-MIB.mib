-- HQL  Juin 20th, 1994. Modified from ipx.mib to reflect only objects
-- that are manageable in our ipx code.


CX-IPX-MIB DEFINITIONS ::= BEGIN

IMPORTS
     Counter
        FROM RFC1155-SMI
    cxIpx
         FROM CXProduct-SMI
    OBJECT-TYPE
         FROM RFC-1212;


-- The IPX interface statistics group

ipxStatsTable OBJECT-TYPE
   SYNTAX  SEQUENCE OF IpxStatsEntry
   ACCESS  not-accessible
   STATUS  mandatory
   DESCRIPTION
"Provides a set of statistics for each IPX port.

Each row (entry) of the table corresponds to a particular IPX port.

Values in this table are read-only."
   ::= {cxIpx 2 }                         -- is this OK ???

   ipxStatsEntry OBJECT-TYPE
      SYNTAX  IpxStatsEntry
      ACCESS  not-accessible
      STATUS  mandatory
      DESCRIPTION
"Provides a set of statistics for a particular IPX port."
      INDEX   {ipxSysIndex}
      ::= {ipxStatsTable 1 }

   IpxStatsEntry ::= SEQUENCE {
      ipxSysIndex
         INTEGER,
      ipxSysInReceives             -- statistics of IPX interface group
         Counter,
      ipxSysInHdrErrors
         Counter,
      ipxSysInFiltered
         Counter,
      ipxSysInDiscards
         Counter,
      ipxSysForwPackets
         Counter,
      ipxSysOutFiltered
         Counter,
      ipxSysOutDiscards
         Counter,
      ipxSysOutPackets
         Counter,
      ipxSysResourceFailures
         Counter,
      ripsapSysRIPIncorrectPackets -- statistics of RIP SAP system group
         Counter,
      ripsapSysSAPIncorrectPackets
         Counter,
      ripsapCircRIPOutPackets      -- statistics of RIP/SAP circuit group
         Counter,
      ripsapCircRIPInPackets
         Counter,
      ripsapCircSAPOutPackets
         Counter,
      ripsapCircSAPInPackets
         Counter,
      ipxSysWatchReq
         Counter,
      ipxSysWatchRsp
         Counter,
      ipxSysSerRcv
         Counter        
   }


   ipxSysIndex OBJECT-TYPE
      SYNTAX  INTEGER
      ACCESS  read-only
      STATUS  mandatory
      DESCRIPTION
"Identifies the number of an IPX port. This number is used as an index for 
this and the cxCfgIpxPortTable.

Range of Values: 1 to 34

Default Value: None"       
   ::= { ipxStatsEntry 1 }

   ipxSysInReceives OBJECT-TYPE
      SYNTAX  Counter
      ACCESS  read-only
      STATUS  mandatory
      DESCRIPTION
"Identifies the total number of IPX packets that have been received by 
this port. The sum includes those received in error. 

Range of Values: 0 to 4, 294, 967, 295 

Default Value: 0"
      ::= { ipxStatsEntry 2 }

   ipxSysInHdrErrors OBJECT-TYPE
      SYNTAX  Counter
      ACCESS  read-only
      STATUS  mandatory
      DESCRIPTION
"Identifies the number of IPX packets discarded due to errors in their 
headers. This number includes any IPX packet with a size less than the 
minimum of 30 bytes.

Range of Values: 0 to 4, 294, 967, 295

Default Value: 0"
      ::= { ipxStatsEntry 3 }

   ipxSysInFiltered OBJECT-TYPE
      SYNTAX  Counter
      ACCESS  read-only
      STATUS  mandatory
      DESCRIPTION
"Identifies the number of incoming packets that have been discarded due to 
filtering.

Range of Values: 0 to 4, 294, 967, 295 

Default Value: 0"
      ::= { ipxStatsEntry 4 }

   ipxSysInDiscards OBJECT-TYPE
      SYNTAX  Counter
      ACCESS  read-only
      STATUS  mandatory
      DESCRIPTION
"Identifies the number of non-IPX packets received and discarded.

Range of Values: 0 to 4, 294, 967, 295

Default Value: 0"
      ::= { ipxStatsEntry 5 }

   ipxSysForwPackets OBJECT-TYPE
      SYNTAX  Counter
      ACCESS  read-only
      STATUS  mandatory
      DESCRIPTION
"Identifies the total number of IPX packets that have been forwarded by 
the port.

Range of Values: 0 to 4, 294, 967, 295  

Default Value: 0"
      ::= { ipxStatsEntry 6 }

   ipxSysOutFiltered OBJECT-TYPE
      SYNTAX  Counter
      ACCESS  read-only
      STATUS  mandatory
      DESCRIPTION
"Identifies the number of outgoing IPX packets that have been discarded 
due to filtering.

Range of Values: 0 to 4, 294, 967, 295 

Default Value: 0"
      ::= { ipxStatsEntry 7 }

   ipxSysOutDiscards OBJECT-TYPE
      SYNTAX  Counter
      ACCESS  read-only
      STATUS  mandatory
      DESCRIPTION
"Identifies the number of outgoing IPX packets discarded due to a 
formatting error.

Range of Values: 0 to 4, 294, 967, 295 

Default Value: 0"
      ::= { ipxStatsEntry 8 }

   ipxSysOutPackets OBJECT-TYPE
      SYNTAX  Counter
      ACCESS  read-only
      STATUS  mandatory
      DESCRIPTION
"Identifies the total number of IPX packets transmitted by the port.

Range of Values: 0 to 4, 294, 967, 295 

Default Value: 0"
      ::= { ipxStatsEntry 9 }

   ipxSysResourceFailures OBJECT-TYPE
      SYNTAX  Counter
      ACCESS  read-only
      STATUS  mandatory
      DESCRIPTION
"Identifies the number of times the IPX port has been unable to obtain 
needed resources, such as memory.

Range of Values: 0 to 4, 294, 967, 295 

Default Value: 0"
      ::= { ipxStatsEntry 10 }

   ripsapSysRIPIncorrectPackets OBJECT-TYPE
      SYNTAX  Counter
      ACCESS  read-only
      STATUS  mandatory
      DESCRIPTION
"Identifies the number of times that the Port received an incorrectly 
formatted RIP packet

Range of Values: 0 to 4,x294,x967,x295  

Default Value: 0"
      ::= { ipxStatsEntry 11 }

   ripsapSysSAPIncorrectPackets OBJECT-TYPE
      SYNTAX  Counter
      ACCESS  read-only
      STATUS  mandatory
      DESCRIPTION
"Identifies the number of times that the IPX port received an incorrectly 
formatted SAP packet.

Range of Values: 0 to 4, 294, 967, 295 

Default Value: 0"
      ::= { ipxStatsEntry 12 }

   ripsapCircRIPOutPackets OBJECT-TYPE
      SYNTAX  Counter
      ACCESS  read-only
      STATUS  mandatory
      DESCRIPTION
"Identifies the number of RIP packets sent by this IPX port.

Range of Values: 0 to 4, 294, 967, 295 

Default Value: 0"
      ::= { ipxStatsEntry 13 }

   ripsapCircRIPInPackets OBJECT-TYPE
      SYNTAX  Counter
      ACCESS  read-only
      STATUS  mandatory
      DESCRIPTION
"Identifies the number of RIP packets received by this IPX port.

Range of Values: 0 to 4, 294, 967, 295 

Default Value: 0"
      ::= { ipxStatsEntry 14 }

   ripsapCircSAPOutPackets OBJECT-TYPE
      SYNTAX  Counter
      ACCESS  read-only
      STATUS  mandatory
      DESCRIPTION
"Identifies the number of SAP packets sent by this IPX port

Range of Values: 0 to 4, 294, 967, 295 

Default Value: 0"
      ::= { ipxStatsEntry 15 }

   ripsapCircSAPInPackets OBJECT-TYPE
      SYNTAX  Counter
      ACCESS  read-only
      STATUS  mandatory
      DESCRIPTION
"Identifies the number of SAP packets received by this IPX port.

Range of Values: 0 to 4, 294, 967, 295 

Default Value: 0"
      ::= { ipxStatsEntry 16 }

   ipxSysWatchReq OBJECT-TYPE
      SYNTAX  Counter
      ACCESS  read-only
      STATUS  mandatory
      DESCRIPTION
"Identifies the number of IPX Watchdog Request packets received on this 
port.

Range of Values: 0 to 4, 294, 967, 295 

Default Value: 0"
      ::= { ipxStatsEntry 17 }
      
   ipxSysWatchRsp OBJECT-TYPE
      SYNTAX  Counter
      ACCESS  read-only
      STATUS  mandatory
      DESCRIPTION
"Identifies the number of Ipx Watchdog Response packets received on this 
port.

Range of Values: 0 to 4, 294, 967, 295  

Default Value: 0"
      ::= { ipxStatsEntry 18 }
   
   ipxSysSerRcv OBJECT-TYPE              
      SYNTAX  Counter
      ACCESS  read-only
      STATUS  mandatory
      DESCRIPTION
"Identifies the number of IPX Serialization packets received on this port.

Range of Values: 0 to 4, 294, 967, 295 

Default Value: 0"
      ::= { ipxStatsEntry 19 }
END
