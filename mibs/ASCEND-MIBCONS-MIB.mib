--			Ascend mibcons MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCONS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibserialInterfaceProfile  OBJECT IDENTIFIER ::= { configuration 69}

	-- The mibserialInterfaceProfile table
	--
	-- This table contains parameters for the mibserialInterfaceProfile profile
	--

    mibserialInterfaceProfileTable	OBJECT-TYPE
	SYNTAX		SEQUENCE OF MibserialInterfaceProfileEntry
	ACCESS		not-accessible
	STATUS		mandatory
	DESCRIPTION	"A list of mibserialInterfaceProfile profile entries."
	::= { mibserialInterfaceProfile 1 }

    mibserialInterfaceProfileEntry	OBJECT-TYPE
	SYNTAX		MibserialInterfaceProfileEntry
	ACCESS		not-accessible
	STATUS		mandatory
	DESCRIPTION	"A mibserialInterfaceProfile entry containing objects that
			 maps to the parameters of mibserialInterfaceProfile profile."
	INDEX		{ serialInterfaceProfile-Shelf-o, serialInterfaceProfile-Slot-o, serialInterfaceProfile-Item-o }
	::= { mibserialInterfaceProfileTable 1 }

    MibserialInterfaceProfileEntry ::=
	SEQUENCE {
	    serialInterfaceProfile-Shelf-o
		INTEGER,
	    serialInterfaceProfile-Slot-o
		INTEGER,
	    serialInterfaceProfile-Item-o
		INTEGER,
	    serialInterfaceProfile-PhysicalAddress-Shelf
		INTEGER,
	    serialInterfaceProfile-PhysicalAddress-Slot
		INTEGER,
	    serialInterfaceProfile-PhysicalAddress-ItemNumber
		INTEGER,
	    serialInterfaceProfile-TermRate
		INTEGER,
	    serialInterfaceProfile-FlowControl
		INTEGER,
	    serialInterfaceProfile-UserProfile
		DisplayString,
	    serialInterfaceProfile-AutoLogout
		INTEGER,
	    serialInterfaceProfile-ConsoleMode
		INTEGER,
	    serialInterfaceProfile-Action-o
		INTEGER
	}

    serialInterfaceProfile-Shelf-o	OBJECT-TYPE
	SYNTAX	INTEGER
	ACCESS	read-only
	STATUS	mandatory
	DESCRIPTION	""
	::= { mibserialInterfaceProfileEntry 1 }

    serialInterfaceProfile-Slot-o	OBJECT-TYPE
	SYNTAX	INTEGER
	ACCESS	read-only
	STATUS	mandatory
	DESCRIPTION	""
	::= { mibserialInterfaceProfileEntry 2 }

    serialInterfaceProfile-Item-o	OBJECT-TYPE
	SYNTAX	INTEGER
	ACCESS	read-only
	STATUS	mandatory
	DESCRIPTION	""
	::= { mibserialInterfaceProfileEntry 3 }

    serialInterfaceProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibserialInterfaceProfileEntry 4 }

    serialInterfaceProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibserialInterfaceProfileEntry 5 }

    serialInterfaceProfile-PhysicalAddress-ItemNumber	OBJECT-TYPE
	SYNTAX	INTEGER
	ACCESS	read-write
	STATUS	mandatory
	DESCRIPTION	"A number that specifies an addressable entity within the context of shelf and slot."
	::= { mibserialInterfaceProfileEntry 6 }

    serialInterfaceProfile-TermRate	OBJECT-TYPE
	SYNTAX	INTEGER {
		    n-300Bps (1),
		    n-1200Bps (2),
		    n-2400Bps (3),
		    n-4800Bps (4),
		    n-9600Bps (5),
		    n-19200Bps (6),
		    n-38400Bps (7),
		    n-57600Bps (8),
		    n-115200Bps (9)
		}
	ACCESS	read-write
	STATUS	mandatory
	DESCRIPTION	"The bit rate of the management terminal port."
	::= { mibserialInterfaceProfileEntry 7 }

    serialInterfaceProfile-FlowControl	OBJECT-TYPE
	SYNTAX	INTEGER {
		    none (1),
		    xonXoff (2),
		    hardwareHandshake (3)
		}
	ACCESS	read-write
	STATUS	mandatory
	DESCRIPTION	"The flow control method used on the serial port."
	::= { mibserialInterfaceProfileEntry 8 }

    serialInterfaceProfile-UserProfile	OBJECT-TYPE
	SYNTAX	DisplayString
	ACCESS	read-write
	STATUS	mandatory
	DESCRIPTION	"The name of the default user profile associated with this port. If none is specified, the user must log in."
	::= { mibserialInterfaceProfileEntry 9 }

    serialInterfaceProfile-AutoLogout	OBJECT-TYPE
	SYNTAX	INTEGER {
		    no (1),
		    yes (2)
		}
	ACCESS	read-write
	STATUS	mandatory
	DESCRIPTION	"When TRUE, go back to the default user profile on loss of DTR from the serial port."
	::= { mibserialInterfaceProfileEntry 10 }

    serialInterfaceProfile-ConsoleMode	OBJECT-TYPE
	SYNTAX	INTEGER {
		    on (1),
		    off (2),
		    yCable (3)
		}
	ACCESS	read-write
	STATUS	mandatory
	DESCRIPTION	"The console-mode used on the serial port. Not used by CM-v1."
	::= { mibserialInterfaceProfileEntry 12 }

    serialInterfaceProfile-Action-o	OBJECT-TYPE
	SYNTAX	INTEGER {
		    noAction (1),
		    createProfile (2),
		    deleteProfile (3)
		}
	ACCESS	read-write
	STATUS	mandatory
	DESCRIPTION	""
	::= { mibserialInterfaceProfileEntry 11 }

END
