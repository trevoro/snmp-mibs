-- DL MIB

-- v 1.03  12/30/02

-- Copyright (c) 2002 by Asentria Corp.  All rights reserved.


DL-MIB DEFINITIONS ::= BEGIN

IMPORTS
 ObjectName, enterprises, IpAddress
    FROM RFC1155-SMI 
 OBJECT-TYPE
    FROM RFC-1212
 DisplayString
    FROM SNMPv2-TC
 TRAP-TYPE
    FROM RFC-1215 ;


--***************************************************************************************
--TOP-LEVEL OBJECT IDENTIFIERS
--***************************************************************************************

	asentria  OBJECT IDENTIFIER ::= { enterprises 3052 }
  	--1.3.6.1.4.1.3052

	dl  OBJECT IDENTIFIER ::= { asentria 3 }
  	--1.3.6.1.4.1.3052.3

	productIds OBJECT IDENTIFIER ::= { dl 3 }
	--1.3.6.1.4.1.3052.3.3


--***************************************************************************************
--OBJECT DEFINITIONS
--***************************************************************************************

siteID OBJECT-TYPE
	SYNTAX DisplayString
	ACCESS not-accessible
	STATUS mandatory
	DESCRIPTION
		"Site ID string; Max 40 characters."
	::= { productIds 1 }
	--1.3.6.1.4.1.3052.3.3.1

stockTrapString OBJECT-TYPE
	SYNTAX DisplayString
	ACCESS not-accessible
	STATUS mandatory
	DESCRIPTION
		"The message defined for the event that triggers a trap."
	::= { productIds 3 }
	--1.3.6.1.4.1.3052.3.3.3

trapTypeString OBJECT-TYPE
	SYNTAX DisplayString
	ACCESS not-accessible
	STATUS mandatory
	DESCRIPTION
		"The cause of the trap."
	::= {productIds 8 }
	--1.3.6.1.4.1.3052.3.3.8
	


--***************************************************************************************
--TRAP DEFINITIONS
--***************************************************************************************

dlStockTrap TRAP-TYPE
	ENTERPRISE dl
	VARIABLES { siteID, stockTrapString }
	DESCRIPTION
		"The stock trap is issued when a data, no data, 
		scheduled, percent full, or test trap event happens."
	::= 1

dlStockDbasePfullTrap TRAP-TYPE
	ENTERPRISE dl
	VARIABLES { siteID, stockTrapString, trapTypeString }
	DESCRIPTION
		"The stock database percent full trap is issued
		when the database size surpasses the threshold."
	::= 501

dlStockDataAlarmTrap TRAP-TYPE
	ENTERPRISE dl
	VARIABLES { siteID, stockTrapString, trapTypeString }
	DESCRIPTION
		"The stock data alarm trap is issued when a
		data alarm happens."
	::= 503

dlStockNoDataAlarmTrap TRAP-TYPE
	ENTERPRISE dl
	VARIABLES { siteID, stockTrapString, trapTypeString }
	DESCRIPTION
		"The stock no-data alarm trap is issued when
		the unit has received no data for a configured
		interval within a configured schedule."
	::= 505

dlStockSchedTrap TRAP-TYPE
	ENTERPRISE dl
	VARIABLES { siteID, stockTrapString, trapTypeString }
	DESCRIPTION
		"The stock scheduled alarm trap is issued 
		when the current time reaches the scheduled
		alarm time."
	::= 506

dlStockImmediateTrap TRAP-TYPE
	ENTERPRISE dl
	VARIABLES { siteID, stockTrapString, trapTypeString }
	DESCRIPTION
		"The stock immediate alarm trap is issued
		when the user enters the DOTRAP command."
	::= 507
	
dlStockSocketLostTrap TRAP-TYPE
	ENTERPRISE dl
	VARIABLES { siteID, stockTrapString, trapTypeString }
	DESCRIPTION
		"The stock socket lost trap is issued when 
		the IPRC socket is disconnected."
	::= 508

dlUserTrap1000 TRAP-TYPE
	ENTERPRISE dl
	VARIABLES { siteID, stockTrapString, trapTypeString }
	DESCRIPTION
		"This user-defined trap is issued when an event happens
		that causes a trap with specific trap type 1000."
	::= 1000

dlUserTrap1001 TRAP-TYPE
	ENTERPRISE dl
	VARIABLES { siteID, stockTrapString, trapTypeString }
	DESCRIPTION
		"This user-defined trap is issued when an event happens
		that causes a trap with specific trap type 1001."
	::= 1001

dlUserTrap1002 TRAP-TYPE
	ENTERPRISE dl
	VARIABLES { siteID, stockTrapString, trapTypeString }
	DESCRIPTION
		"This user-defined trap is issued when an event happens
		that causes a trap with specific trap type 1002."
	::= 1002

dlUserTrap1003 TRAP-TYPE
	ENTERPRISE dl
	VARIABLES { siteID, stockTrapString, trapTypeString }
	DESCRIPTION
		"This user-defined trap is issued when an event happens
		that causes a trap with specific trap type 1003."
	::= 1003

dlUserTrap1004 TRAP-TYPE
	ENTERPRISE dl
	VARIABLES { siteID, stockTrapString, trapTypeString }
	DESCRIPTION
		"This user-defined trap is issued when an event happens
		that causes a trap with specific trap type 1004."
	::= 1004

dlUserTrap1005 TRAP-TYPE
	ENTERPRISE dl
	VARIABLES { siteID, stockTrapString, trapTypeString }
	DESCRIPTION
		"This user-defined trap is issued when an event happens
		that causes a trap with specific trap type 1005."
	::= 1005

dlUserTrap1006 TRAP-TYPE
	ENTERPRISE dl
	VARIABLES { siteID, stockTrapString, trapTypeString }
	DESCRIPTION
		"This user-defined trap is issued when an event happens
		that causes a trap with specific trap type 1006."
	::= 1006

dlUserTrap1007 TRAP-TYPE
	ENTERPRISE dl
	VARIABLES { siteID, stockTrapString, trapTypeString }
	DESCRIPTION
		"This user-defined trap is issued when an event happens
		that causes a trap with specific trap type 1007."
	::= 1007

dlUserTrap1008 TRAP-TYPE
	ENTERPRISE dl
	VARIABLES { siteID, stockTrapString, trapTypeString }
	DESCRIPTION
		"This user-defined trap is issued when an event happens
		that causes a trap with specific trap type 1008."
	::= 1008

dlUserTrap1009 TRAP-TYPE
	ENTERPRISE dl
	VARIABLES { siteID, stockTrapString, trapTypeString }
	DESCRIPTION
		"This user-defined trap is issued when an event happens
		that causes a trap with specific trap type 1009."
	::= 1009

dlUserTrap1010 TRAP-TYPE
	ENTERPRISE dl
	VARIABLES { siteID, stockTrapString, trapTypeString }
	DESCRIPTION
		"This user-defined trap is issued when an event happens
		that causes a trap with specific trap type 1010."
	::= 1010

dlUserTrap1011 TRAP-TYPE
	ENTERPRISE dl
	VARIABLES { siteID, stockTrapString, trapTypeString }
	DESCRIPTION
		"This user-defined trap is issued when an event happens
		that causes a trap with specific trap type 1011."
	::= 1011

dlUserTrap1012 TRAP-TYPE
	ENTERPRISE dl
	VARIABLES { siteID, stockTrapString, trapTypeString }
	DESCRIPTION
		"This user-defined trap is issued when an event happens
		that causes a trap with specific trap type 1012."
	::= 1012

dlUserTrap1013 TRAP-TYPE
	ENTERPRISE dl
	VARIABLES { siteID, stockTrapString, trapTypeString }
	DESCRIPTION
		"This user-defined trap is issued when an event happens
		that causes a trap with specific trap type 1013."
	::= 1013

dlUserTrap1014 TRAP-TYPE
	ENTERPRISE dl
	VARIABLES { siteID, stockTrapString, trapTypeString }
	DESCRIPTION
		"This user-defined trap is issued when an event happens
		that causes a trap with specific trap type 1014."
	::= 1014

dlUserTrap1015 TRAP-TYPE
	ENTERPRISE dl
	VARIABLES { siteID, stockTrapString, trapTypeString }
	DESCRIPTION
		"This user-defined trap is issued when an event happens
		that causes a trap with specific trap type 1015."
	::= 1015

dlUserTrap1016 TRAP-TYPE
	ENTERPRISE dl
	VARIABLES { siteID, stockTrapString, trapTypeString }
	DESCRIPTION
		"This user-defined trap is issued when an event happens
		that causes a trap with specific trap type 1016."
	::= 1016

dlUserTrap1017 TRAP-TYPE
	ENTERPRISE dl
	VARIABLES { siteID, stockTrapString, trapTypeString }
	DESCRIPTION
		"This user-defined trap is issued when an event happens
		that causes a trap with specific trap type 1017."
	::= 1017

dlUserTrap1018 TRAP-TYPE
	ENTERPRISE dl
	VARIABLES { siteID, stockTrapString, trapTypeString }
	DESCRIPTION
		"This user-defined trap is issued when an event happens
		that causes a trap with specific trap type 1018."
	::= 1018

dlUserTrap1019 TRAP-TYPE
	ENTERPRISE dl
	VARIABLES { siteID, stockTrapString, trapTypeString }
	DESCRIPTION
		"This user-defined trap is issued when an event happens
		that causes a trap with specific trap type 1019."
	::= 1019

dlUserTrap1020 TRAP-TYPE
	ENTERPRISE dl
	VARIABLES { siteID, stockTrapString, trapTypeString }
	DESCRIPTION
		"This user-defined trap is issued when an event happens
		that causes a trap with specific trap type 1020."
	::= 1020

dlUserTrap1021 TRAP-TYPE
	ENTERPRISE dl
	VARIABLES { siteID, stockTrapString, trapTypeString }
	DESCRIPTION
		"This user-defined trap is issued when an event happens
		that causes a trap with specific trap type 1021."
	::= 1021

dlUserTrap1022 TRAP-TYPE
	ENTERPRISE dl
	VARIABLES { siteID, stockTrapString, trapTypeString }
	DESCRIPTION
		"This user-defined trap is issued when an event happens
		that causes a trap with specific trap type 1022."
	::= 1022

dlUserTrap1023 TRAP-TYPE
	ENTERPRISE dl
	VARIABLES { siteID, stockTrapString, trapTypeString }
	DESCRIPTION
		"This user-defined trap is issued when an event happens
		that causes a trap with specific trap type 1023."
	::= 1023

dlUserTrap1024 TRAP-TYPE
	ENTERPRISE dl
	VARIABLES { siteID, stockTrapString, trapTypeString }
	DESCRIPTION
		"This user-defined trap is issued when an event happens
		that causes a trap with specific trap type 1024."
	::= 1024

dlUserTrap1025 TRAP-TYPE
	ENTERPRISE dl
	VARIABLES { siteID, stockTrapString, trapTypeString }
	DESCRIPTION
		"This user-defined trap is issued when an event happens
		that causes a trap with specific trap type 1025."
	::= 1025

dlUserTrap1026 TRAP-TYPE
	ENTERPRISE dl
	VARIABLES { siteID, stockTrapString, trapTypeString }
	DESCRIPTION
		"This user-defined trap is issued when an event happens
		that causes a trap with specific trap type 1026."
	::= 1026

dlUserTrap1027 TRAP-TYPE
	ENTERPRISE dl
	VARIABLES { siteID, stockTrapString, trapTypeString }
	DESCRIPTION
		"This user-defined trap is issued when an event happens
		that causes a trap with specific trap type 1027."
	::= 1027

dlUserTrap1028 TRAP-TYPE
	ENTERPRISE dl
	VARIABLES { siteID, stockTrapString, trapTypeString }
	DESCRIPTION
		"This user-defined trap is issued when an event happens
		that causes a trap with specific trap type 1028."
	::= 1028

dlUserTrap1029 TRAP-TYPE
	ENTERPRISE dl
	VARIABLES { siteID, stockTrapString, trapTypeString }
	DESCRIPTION
		"This user-defined trap is issued when an event happens
		that causes a trap with specific trap type 1029."
	::= 1029

dlUserTrap1030 TRAP-TYPE
	ENTERPRISE dl
	VARIABLES { siteID, stockTrapString, trapTypeString }
	DESCRIPTION
		"This user-defined trap is issued when an event happens
		that causes a trap with specific trap type 1030."
	::= 1030

dlUserTrap1031 TRAP-TYPE
	ENTERPRISE dl
	VARIABLES { siteID, stockTrapString, trapTypeString }
	DESCRIPTION
		"This user-defined trap is issued when an event happens
		that causes a trap with specific trap type 1031."
	::= 1031

dlUserTrap1032 TRAP-TYPE
	ENTERPRISE dl
	VARIABLES { siteID, stockTrapString, trapTypeString }
	DESCRIPTION
		"This user-defined trap is issued when an event happens
		that causes a trap with specific trap type 1032."
	::= 1032

dlUserTrap1033 TRAP-TYPE
	ENTERPRISE dl
	VARIABLES { siteID, stockTrapString, trapTypeString }
	DESCRIPTION
		"This user-defined trap is issued when an event happens
		that causes a trap with specific trap type 1033."
	::= 1033

dlUserTrap1034 TRAP-TYPE
	ENTERPRISE dl
	VARIABLES { siteID, stockTrapString, trapTypeString }
	DESCRIPTION
		"This user-defined trap is issued when an event happens
		that causes a trap with specific trap type 1034."
	::= 1034

dlUserTrap1035 TRAP-TYPE
	ENTERPRISE dl
	VARIABLES { siteID, stockTrapString, trapTypeString }
	DESCRIPTION
		"This user-defined trap is issued when an event happens
		that causes a trap with specific trap type 1035."
	::= 1035

dlUserTrap1036 TRAP-TYPE
	ENTERPRISE dl
	VARIABLES { siteID, stockTrapString, trapTypeString }
	DESCRIPTION
		"This user-defined trap is issued when an event happens
		that causes a trap with specific trap type 1036."
	::= 1036

dlUserTrap1037 TRAP-TYPE
	ENTERPRISE dl
	VARIABLES { siteID, stockTrapString, trapTypeString }
	DESCRIPTION
		"This user-defined trap is issued when an event happens
		that causes a trap with specific trap type 1037."
	::= 1037

dlUserTrap1038 TRAP-TYPE
	ENTERPRISE dl
	VARIABLES { siteID, stockTrapString, trapTypeString }
	DESCRIPTION
		"This user-defined trap is issued when an event happens
		that causes a trap with specific trap type 1038."
	::= 1038

dlUserTrap1039 TRAP-TYPE
	ENTERPRISE dl
	VARIABLES { siteID, stockTrapString, trapTypeString }
	DESCRIPTION
		"This user-defined trap is issued when an event happens
		that causes a trap with specific trap type 1039."
	::= 1039

dlUserTrap1040 TRAP-TYPE
	ENTERPRISE dl
	VARIABLES { siteID, stockTrapString, trapTypeString }
	DESCRIPTION
		"This user-defined trap is issued when an event happens
		that causes a trap with specific trap type 1040."
	::= 1040

dlUserTrap1041 TRAP-TYPE
	ENTERPRISE dl
	VARIABLES { siteID, stockTrapString, trapTypeString }
	DESCRIPTION
		"This user-defined trap is issued when an event happens
		that causes a trap with specific trap type 1041."
	::= 1041

dlUserTrap1042 TRAP-TYPE
	ENTERPRISE dl
	VARIABLES { siteID, stockTrapString, trapTypeString }
	DESCRIPTION
		"This user-defined trap is issued when an event happens
		that causes a trap with specific trap type 1042."
	::= 1042

dlUserTrap1043 TRAP-TYPE
	ENTERPRISE dl
	VARIABLES { siteID, stockTrapString, trapTypeString }
	DESCRIPTION
		"This user-defined trap is issued when an event happens
		that causes a trap with specific trap type 1043."
	::= 1043

dlUserTrap1044 TRAP-TYPE
	ENTERPRISE dl
	VARIABLES { siteID, stockTrapString, trapTypeString }
	DESCRIPTION
		"This user-defined trap is issued when an event happens
		that causes a trap with specific trap type 1044."
	::= 1044

dlUserTrap1045 TRAP-TYPE
	ENTERPRISE dl
	VARIABLES { siteID, stockTrapString, trapTypeString }
	DESCRIPTION
		"This user-defined trap is issued when an event happens
		that causes a trap with specific trap type 1045."
	::= 1045

dlUserTrap1046 TRAP-TYPE
	ENTERPRISE dl
	VARIABLES { siteID, stockTrapString, trapTypeString }
	DESCRIPTION
		"This user-defined trap is issued when an event happens
		that causes a trap with specific trap type 1046."
	::= 1046

dlUserTrap1047 TRAP-TYPE
	ENTERPRISE dl
	VARIABLES { siteID, stockTrapString, trapTypeString }
	DESCRIPTION
		"This user-defined trap is issued when an event happens
		that causes a trap with specific trap type 1047."
	::= 1047

dlUserTrap1048 TRAP-TYPE
	ENTERPRISE dl
	VARIABLES { siteID, stockTrapString, trapTypeString }
	DESCRIPTION
		"This user-defined trap is issued when an event happens
		that causes a trap with specific trap type 1048."
	::= 1048

dlUserTrap1049 TRAP-TYPE
	ENTERPRISE dl
	VARIABLES { siteID, stockTrapString, trapTypeString }
	DESCRIPTION
		"This user-defined trap is issued when an event happens
		that causes a trap with specific trap type 1049."
	::= 1049

dlUserTrap1050 TRAP-TYPE
	ENTERPRISE dl
	VARIABLES { siteID, stockTrapString, trapTypeString }
	DESCRIPTION
		"This user-defined trap is issued when an event happens
		that causes a trap with specific trap type 1050."
	::= 1050

dlUserTrap1051 TRAP-TYPE
	ENTERPRISE dl
	VARIABLES { siteID, stockTrapString, trapTypeString }
	DESCRIPTION
		"This user-defined trap is issued when an event happens
		that causes a trap with specific trap type 1051."
	::= 1051

dlUserTrap1052 TRAP-TYPE
	ENTERPRISE dl
	VARIABLES { siteID, stockTrapString, trapTypeString }
	DESCRIPTION
		"This user-defined trap is issued when an event happens
		that causes a trap with specific trap type 1052."
	::= 1052

dlUserTrap1053 TRAP-TYPE
	ENTERPRISE dl
	VARIABLES { siteID, stockTrapString, trapTypeString }
	DESCRIPTION
		"This user-defined trap is issued when an event happens
		that causes a trap with specific trap type 1053."
	::= 1053

dlUserTrap1054 TRAP-TYPE
	ENTERPRISE dl
	VARIABLES { siteID, stockTrapString, trapTypeString }
	DESCRIPTION
		"This user-defined trap is issued when an event happens
		that causes a trap with specific trap type 1054."
	::= 1054

dlUserTrap1055 TRAP-TYPE
	ENTERPRISE dl
	VARIABLES { siteID, stockTrapString, trapTypeString }
	DESCRIPTION
		"This user-defined trap is issued when an event happens
		that causes a trap with specific trap type 1055."
	::= 1055

dlUserTrap1056 TRAP-TYPE
	ENTERPRISE dl
	VARIABLES { siteID, stockTrapString, trapTypeString }
	DESCRIPTION
		"This user-defined trap is issued when an event happens
		that causes a trap with specific trap type 1056."
	::= 1056

dlUserTrap1057 TRAP-TYPE
	ENTERPRISE dl
	VARIABLES { siteID, stockTrapString, trapTypeString }
	DESCRIPTION
		"This user-defined trap is issued when an event happens
		that causes a trap with specific trap type 1057."
	::= 1057

dlUserTrap1058 TRAP-TYPE
	ENTERPRISE dl
	VARIABLES { siteID, stockTrapString, trapTypeString }
	DESCRIPTION
		"This user-defined trap is issued when an event happens
		that causes a trap with specific trap type 1058."
	::= 1058

dlUserTrap1059 TRAP-TYPE
	ENTERPRISE dl
	VARIABLES { siteID, stockTrapString, trapTypeString }
	DESCRIPTION
		"This user-defined trap is issued when an event happens
		that causes a trap with specific trap type 1059."
	::= 1059

dlUserTrap1060 TRAP-TYPE
	ENTERPRISE dl
	VARIABLES { siteID, stockTrapString, trapTypeString }
	DESCRIPTION
		"This user-defined trap is issued when an event happens
		that causes a trap with specific trap type 1060."
	::= 1060

dlUserTrap1061 TRAP-TYPE
	ENTERPRISE dl
	VARIABLES { siteID, stockTrapString, trapTypeString }
	DESCRIPTION
		"This user-defined trap is issued when an event happens
		that causes a trap with specific trap type 1061."
	::= 1061

dlUserTrap1062 TRAP-TYPE
	ENTERPRISE dl
	VARIABLES { siteID, stockTrapString, trapTypeString }
	DESCRIPTION
		"This user-defined trap is issued when an event happens
		that causes a trap with specific trap type 1062."
	::= 1062

dlUserTrap1063 TRAP-TYPE
	ENTERPRISE dl
	VARIABLES { siteID, stockTrapString, trapTypeString }
	DESCRIPTION
		"This user-defined trap is issued when an event happens
		that causes a trap with specific trap type 1063."
	::= 1063

dlUserTrap1064 TRAP-TYPE
	ENTERPRISE dl
	VARIABLES { siteID, stockTrapString, trapTypeString }
	DESCRIPTION
		"This user-defined trap is issued when an event happens
		that causes a trap with specific trap type 1064."
	::= 1064

dlUserTrap1065 TRAP-TYPE
	ENTERPRISE dl
	VARIABLES { siteID, stockTrapString, trapTypeString }
	DESCRIPTION
		"This user-defined trap is issued when an event happens
		that causes a trap with specific trap type 1065."
	::= 1065

dlUserTrap1066 TRAP-TYPE
	ENTERPRISE dl
	VARIABLES { siteID, stockTrapString, trapTypeString }
	DESCRIPTION
		"This user-defined trap is issued when an event happens
		that causes a trap with specific trap type 1066."
	::= 1066

dlUserTrap1067 TRAP-TYPE
	ENTERPRISE dl
	VARIABLES { siteID, stockTrapString, trapTypeString }
	DESCRIPTION
		"This user-defined trap is issued when an event happens
		that causes a trap with specific trap type 1067."
	::= 1067

dlUserTrap1068 TRAP-TYPE
	ENTERPRISE dl
	VARIABLES { siteID, stockTrapString, trapTypeString }
	DESCRIPTION
		"This user-defined trap is issued when an event happens
		that causes a trap with specific trap type 1068."
	::= 1068

dlUserTrap1069 TRAP-TYPE
	ENTERPRISE dl
	VARIABLES { siteID, stockTrapString, trapTypeString }
	DESCRIPTION
		"This user-defined trap is issued when an event happens
		that causes a trap with specific trap type 1069."
	::= 1069

dlUserTrap1070 TRAP-TYPE
	ENTERPRISE dl
	VARIABLES { siteID, stockTrapString, trapTypeString }
	DESCRIPTION
		"This user-defined trap is issued when an event happens
		that causes a trap with specific trap type 1070."
	::= 1070

dlUserTrap1071 TRAP-TYPE
	ENTERPRISE dl
	VARIABLES { siteID, stockTrapString, trapTypeString }
	DESCRIPTION
		"This user-defined trap is issued when an event happens
		that causes a trap with specific trap type 1071."
	::= 1071

dlUserTrap1072 TRAP-TYPE
	ENTERPRISE dl
	VARIABLES { siteID, stockTrapString, trapTypeString }
	DESCRIPTION
		"This user-defined trap is issued when an event happens
		that causes a trap with specific trap type 1072."
	::= 1072

dlUserTrap1073 TRAP-TYPE
	ENTERPRISE dl
	VARIABLES { siteID, stockTrapString, trapTypeString }
	DESCRIPTION
		"This user-defined trap is issued when an event happens
		that causes a trap with specific trap type 1073."
	::= 1073

dlUserTrap1074 TRAP-TYPE
	ENTERPRISE dl
	VARIABLES { siteID, stockTrapString, trapTypeString }
	DESCRIPTION
		"This user-defined trap is issued when an event happens
		that causes a trap with specific trap type 1074."
	::= 1074

dlUserTrap1075 TRAP-TYPE
	ENTERPRISE dl
	VARIABLES { siteID, stockTrapString, trapTypeString }
	DESCRIPTION
		"This user-defined trap is issued when an event happens
		that causes a trap with specific trap type 1075."
	::= 1075

dlUserTrap1076 TRAP-TYPE
	ENTERPRISE dl
	VARIABLES { siteID, stockTrapString, trapTypeString }
	DESCRIPTION
		"This user-defined trap is issued when an event happens
		that causes a trap with specific trap type 1076."
	::= 1076

dlUserTrap1077 TRAP-TYPE
	ENTERPRISE dl
	VARIABLES { siteID, stockTrapString, trapTypeString }
	DESCRIPTION
		"This user-defined trap is issued when an event happens
		that causes a trap with specific trap type 1077."
	::= 1077

dlUserTrap1078 TRAP-TYPE
	ENTERPRISE dl
	VARIABLES { siteID, stockTrapString, trapTypeString }
	DESCRIPTION
		"This user-defined trap is issued when an event happens
		that causes a trap with specific trap type 1078."
	::= 1078

dlUserTrap1079 TRAP-TYPE
	ENTERPRISE dl
	VARIABLES { siteID, stockTrapString, trapTypeString }
	DESCRIPTION
		"This user-defined trap is issued when an event happens
		that causes a trap with specific trap type 1079."
	::= 1079

dlUserTrap1080 TRAP-TYPE
	ENTERPRISE dl
	VARIABLES { siteID, stockTrapString, trapTypeString }
	DESCRIPTION
		"This user-defined trap is issued when an event happens
		that causes a trap with specific trap type 1080."
	::= 1080

dlUserTrap1081 TRAP-TYPE
	ENTERPRISE dl
	VARIABLES { siteID, stockTrapString, trapTypeString }
	DESCRIPTION
		"This user-defined trap is issued when an event happens
		that causes a trap with specific trap type 1081."
	::= 1081

dlUserTrap1082 TRAP-TYPE
	ENTERPRISE dl
	VARIABLES { siteID, stockTrapString, trapTypeString }
	DESCRIPTION
		"This user-defined trap is issued when an event happens
		that causes a trap with specific trap type 1082."
	::= 1082

dlUserTrap1083 TRAP-TYPE
	ENTERPRISE dl
	VARIABLES { siteID, stockTrapString, trapTypeString }
	DESCRIPTION
		"This user-defined trap is issued when an event happens
		that causes a trap with specific trap type 1083."
	::= 1083

dlUserTrap1084 TRAP-TYPE
	ENTERPRISE dl
	VARIABLES { siteID, stockTrapString, trapTypeString }
	DESCRIPTION
		"This user-defined trap is issued when an event happens
		that causes a trap with specific trap type 1084."
	::= 1084

dlUserTrap1085 TRAP-TYPE
	ENTERPRISE dl
	VARIABLES { siteID, stockTrapString, trapTypeString }
	DESCRIPTION
		"This user-defined trap is issued when an event happens
		that causes a trap with specific trap type 1085."
	::= 1085

dlUserTrap1086 TRAP-TYPE
	ENTERPRISE dl
	VARIABLES { siteID, stockTrapString, trapTypeString }
	DESCRIPTION
		"This user-defined trap is issued when an event happens
		that causes a trap with specific trap type 1086."
	::= 1086

dlUserTrap1087 TRAP-TYPE
	ENTERPRISE dl
	VARIABLES { siteID, stockTrapString, trapTypeString }
	DESCRIPTION
		"This user-defined trap is issued when an event happens
		that causes a trap with specific trap type 1087."
	::= 1087

dlUserTrap1088 TRAP-TYPE
	ENTERPRISE dl
	VARIABLES { siteID, stockTrapString, trapTypeString }
	DESCRIPTION
		"This user-defined trap is issued when an event happens
		that causes a trap with specific trap type 1088."
	::= 1088

dlUserTrap1089 TRAP-TYPE
	ENTERPRISE dl
	VARIABLES { siteID, stockTrapString, trapTypeString }
	DESCRIPTION
		"This user-defined trap is issued when an event happens
		that causes a trap with specific trap type 1089."
	::= 1089

dlUserTrap1090 TRAP-TYPE
	ENTERPRISE dl
	VARIABLES { siteID, stockTrapString, trapTypeString }
	DESCRIPTION
		"This user-defined trap is issued when an event happens
		that causes a trap with specific trap type 1090."
	::= 1090

dlUserTrap1091 TRAP-TYPE
	ENTERPRISE dl
	VARIABLES { siteID, stockTrapString, trapTypeString }
	DESCRIPTION
		"This user-defined trap is issued when an event happens
		that causes a trap with specific trap type 1091."
	::= 1091

dlUserTrap1092 TRAP-TYPE
	ENTERPRISE dl
	VARIABLES { siteID, stockTrapString, trapTypeString }
	DESCRIPTION
		"This user-defined trap is issued when an event happens
		that causes a trap with specific trap type 1092."
	::= 1092

dlUserTrap1093 TRAP-TYPE
	ENTERPRISE dl
	VARIABLES { siteID, stockTrapString, trapTypeString }
	DESCRIPTION
		"This user-defined trap is issued when an event happens
		that causes a trap with specific trap type 1093."
	::= 1093

dlUserTrap1094 TRAP-TYPE
	ENTERPRISE dl
	VARIABLES { siteID, stockTrapString, trapTypeString }
	DESCRIPTION
		"This user-defined trap is issued when an event happens
		that causes a trap with specific trap type 1094."
	::= 1094

dlUserTrap1095 TRAP-TYPE
	ENTERPRISE dl
	VARIABLES { siteID, stockTrapString, trapTypeString }
	DESCRIPTION
		"This user-defined trap is issued when an event happens
		that causes a trap with specific trap type 1095."
	::= 1095

dlUserTrap1096 TRAP-TYPE
	ENTERPRISE dl
	VARIABLES { siteID, stockTrapString, trapTypeString }
	DESCRIPTION
		"This user-defined trap is issued when an event happens
		that causes a trap with specific trap type 1096."
	::= 1096

dlUserTrap1097 TRAP-TYPE
	ENTERPRISE dl
	VARIABLES { siteID, stockTrapString, trapTypeString }
	DESCRIPTION
		"This user-defined trap is issued when an event happens
		that causes a trap with specific trap type 1097."
	::= 1097

dlUserTrap1098 TRAP-TYPE
	ENTERPRISE dl
	VARIABLES { siteID, stockTrapString, trapTypeString }
	DESCRIPTION
		"This user-defined trap is issued when an event happens
		that causes a trap with specific trap type 1098."
	::= 1098

dlUserTrap1099 TRAP-TYPE
	ENTERPRISE dl
	VARIABLES { siteID, stockTrapString, trapTypeString }
	DESCRIPTION
		"This user-defined trap is issued when an event happens
		that causes a trap with specific trap type 1099."
	::= 1099

dlUserTrap1100 TRAP-TYPE
	ENTERPRISE dl
	VARIABLES { siteID, stockTrapString, trapTypeString }
	DESCRIPTION
		"This user-defined trap is issued when an event happens
		that causes a trap with specific trap type 1100."
	::= 1100

dlUserTrap1101 TRAP-TYPE
	ENTERPRISE dl
	VARIABLES { siteID, stockTrapString, trapTypeString }
	DESCRIPTION
		"This user-defined trap is issued when an event happens
		that causes a trap with specific trap type 1101."
	::= 1101

dlUserTrap1102 TRAP-TYPE
	ENTERPRISE dl
	VARIABLES { siteID, stockTrapString, trapTypeString }
	DESCRIPTION
		"This user-defined trap is issued when an event happens
		that causes a trap with specific trap type 1102."
	::= 1102

dlUserTrap1103 TRAP-TYPE
	ENTERPRISE dl
	VARIABLES { siteID, stockTrapString, trapTypeString }
	DESCRIPTION
		"This user-defined trap is issued when an event happens
		that causes a trap with specific trap type 1103."
	::= 1103

dlUserTrap1104 TRAP-TYPE
	ENTERPRISE dl
	VARIABLES { siteID, stockTrapString, trapTypeString }
	DESCRIPTION
		"This user-defined trap is issued when an event happens
		that causes a trap with specific trap type 1104."
	::= 1104

dlUserTrap1105 TRAP-TYPE
	ENTERPRISE dl
	VARIABLES { siteID, stockTrapString, trapTypeString }
	DESCRIPTION
		"This user-defined trap is issued when an event happens
		that causes a trap with specific trap type 1105."
	::= 1105

dlUserTrap1106 TRAP-TYPE
	ENTERPRISE dl
	VARIABLES { siteID, stockTrapString, trapTypeString }
	DESCRIPTION
		"This user-defined trap is issued when an event happens
		that causes a trap with specific trap type 1106."
	::= 1106

dlUserTrap1107 TRAP-TYPE
	ENTERPRISE dl
	VARIABLES { siteID, stockTrapString, trapTypeString }
	DESCRIPTION
		"This user-defined trap is issued when an event happens
		that causes a trap with specific trap type 1107."
	::= 1107

dlUserTrap1108 TRAP-TYPE
	ENTERPRISE dl
	VARIABLES { siteID, stockTrapString, trapTypeString }
	DESCRIPTION
		"This user-defined trap is issued when an event happens
		that causes a trap with specific trap type 1108."
	::= 1108

dlUserTrap1109 TRAP-TYPE
	ENTERPRISE dl
	VARIABLES { siteID, stockTrapString, trapTypeString }
	DESCRIPTION
		"This user-defined trap is issued when an event happens
		that causes a trap with specific trap type 1109."
	::= 1109

dlUserTrap1110 TRAP-TYPE
	ENTERPRISE dl
	VARIABLES { siteID, stockTrapString, trapTypeString }
	DESCRIPTION
		"This user-defined trap is issued when an event happens
		that causes a trap with specific trap type 1110."
	::= 1110

dlUserTrap1111 TRAP-TYPE
	ENTERPRISE dl
	VARIABLES { siteID, stockTrapString, trapTypeString }
	DESCRIPTION
		"This user-defined trap is issued when an event happens
		that causes a trap with specific trap type 1111."
	::= 1111

dlUserTrap1112 TRAP-TYPE
	ENTERPRISE dl
	VARIABLES { siteID, stockTrapString, trapTypeString }
	DESCRIPTION
		"This user-defined trap is issued when an event happens
		that causes a trap with specific trap type 1112."
	::= 1112

dlUserTrap1113 TRAP-TYPE
	ENTERPRISE dl
	VARIABLES { siteID, stockTrapString, trapTypeString }
	DESCRIPTION
		"This user-defined trap is issued when an event happens
		that causes a trap with specific trap type 1113."
	::= 1113

dlUserTrap1114 TRAP-TYPE
	ENTERPRISE dl
	VARIABLES { siteID, stockTrapString, trapTypeString }
	DESCRIPTION
		"This user-defined trap is issued when an event happens
		that causes a trap with specific trap type 1114."
	::= 1114

dlUserTrap1115 TRAP-TYPE
	ENTERPRISE dl
	VARIABLES { siteID, stockTrapString, trapTypeString }
	DESCRIPTION
		"This user-defined trap is issued when an event happens
		that causes a trap with specific trap type 1115."
	::= 1115

dlUserTrap1116 TRAP-TYPE
	ENTERPRISE dl
	VARIABLES { siteID, stockTrapString, trapTypeString }
	DESCRIPTION
		"This user-defined trap is issued when an event happens
		that causes a trap with specific trap type 1116."
	::= 1116

dlUserTrap1117 TRAP-TYPE
	ENTERPRISE dl
	VARIABLES { siteID, stockTrapString, trapTypeString }
	DESCRIPTION
		"This user-defined trap is issued when an event happens
		that causes a trap with specific trap type 1117."
	::= 1117

dlUserTrap1118 TRAP-TYPE
	ENTERPRISE dl
	VARIABLES { siteID, stockTrapString, trapTypeString }
	DESCRIPTION
		"This user-defined trap is issued when an event happens
		that causes a trap with specific trap type 1118."
	::= 1118

dlUserTrap1119 TRAP-TYPE
	ENTERPRISE dl
	VARIABLES { siteID, stockTrapString, trapTypeString }
	DESCRIPTION
		"This user-defined trap is issued when an event happens
		that causes a trap with specific trap type 1119."
	::= 1119

dlUserTrap1120 TRAP-TYPE
	ENTERPRISE dl
	VARIABLES { siteID, stockTrapString, trapTypeString }
	DESCRIPTION
		"This user-defined trap is issued when an event happens
		that causes a trap with specific trap type 1120."
	::= 1120

dlUserTrap1121 TRAP-TYPE
	ENTERPRISE dl
	VARIABLES { siteID, stockTrapString, trapTypeString }
	DESCRIPTION
		"This user-defined trap is issued when an event happens
		that causes a trap with specific trap type 1121."
	::= 1121

dlUserTrap1122 TRAP-TYPE
	ENTERPRISE dl
	VARIABLES { siteID, stockTrapString, trapTypeString }
	DESCRIPTION
		"This user-defined trap is issued when an event happens
		that causes a trap with specific trap type 1122."
	::= 1122

dlUserTrap1123 TRAP-TYPE
	ENTERPRISE dl
	VARIABLES { siteID, stockTrapString, trapTypeString }
	DESCRIPTION
		"This user-defined trap is issued when an event happens
		that causes a trap with specific trap type 1123."
	::= 1123

dlUserTrap1124 TRAP-TYPE
	ENTERPRISE dl
	VARIABLES { siteID, stockTrapString, trapTypeString }
	DESCRIPTION
		"This user-defined trap is issued when an event happens
		that causes a trap with specific trap type 1124."
	::= 1124

dlUserTrap1125 TRAP-TYPE
	ENTERPRISE dl
	VARIABLES { siteID, stockTrapString, trapTypeString }
	DESCRIPTION
		"This user-defined trap is issued when an event happens
		that causes a trap with specific trap type 1125."
	::= 1125

dlUserTrap1126 TRAP-TYPE
	ENTERPRISE dl
	VARIABLES { siteID, stockTrapString, trapTypeString }
	DESCRIPTION
		"This user-defined trap is issued when an event happens
		that causes a trap with specific trap type 1126."
	::= 1126

dlUserTrap1127 TRAP-TYPE
	ENTERPRISE dl
	VARIABLES { siteID, stockTrapString, trapTypeString }
	DESCRIPTION
		"This user-defined trap is issued when an event happens
		that causes a trap with specific trap type 1127."
	::= 1127

dlUserTrap1128 TRAP-TYPE
	ENTERPRISE dl
	VARIABLES { siteID, stockTrapString, trapTypeString }
	DESCRIPTION
		"This user-defined trap is issued when an event happens
		that causes a trap with specific trap type 1128."
	::= 1128

dlUserTrap1129 TRAP-TYPE
	ENTERPRISE dl
	VARIABLES { siteID, stockTrapString, trapTypeString }
	DESCRIPTION
		"This user-defined trap is issued when an event happens
		that causes a trap with specific trap type 1129."
	::= 1129

dlUserTrap1130 TRAP-TYPE
	ENTERPRISE dl
	VARIABLES { siteID, stockTrapString, trapTypeString }
	DESCRIPTION
		"This user-defined trap is issued when an event happens
		that causes a trap with specific trap type 1130."
	::= 1130

dlUserTrap1131 TRAP-TYPE
	ENTERPRISE dl
	VARIABLES { siteID, stockTrapString, trapTypeString }
	DESCRIPTION
		"This user-defined trap is issued when an event happens
		that causes a trap with specific trap type 1131."
	::= 1131

dlUserTrap1132 TRAP-TYPE
	ENTERPRISE dl
	VARIABLES { siteID, stockTrapString, trapTypeString }
	DESCRIPTION
		"This user-defined trap is issued when an event happens
		that causes a trap with specific trap type 1132."
	::= 1132

dlUserTrap1133 TRAP-TYPE
	ENTERPRISE dl
	VARIABLES { siteID, stockTrapString, trapTypeString }
	DESCRIPTION
		"This user-defined trap is issued when an event happens
		that causes a trap with specific trap type 1133."
	::= 1133

dlUserTrap1134 TRAP-TYPE
	ENTERPRISE dl
	VARIABLES { siteID, stockTrapString, trapTypeString }
	DESCRIPTION
		"This user-defined trap is issued when an event happens
		that causes a trap with specific trap type 1134."
	::= 1134

dlUserTrap1135 TRAP-TYPE
	ENTERPRISE dl
	VARIABLES { siteID, stockTrapString, trapTypeString }
	DESCRIPTION
		"This user-defined trap is issued when an event happens
		that causes a trap with specific trap type 1135."
	::= 1135

dlUserTrap1136 TRAP-TYPE
	ENTERPRISE dl
	VARIABLES { siteID, stockTrapString, trapTypeString }
	DESCRIPTION
		"This user-defined trap is issued when an event happens
		that causes a trap with specific trap type 1136."
	::= 1136

dlUserTrap1137 TRAP-TYPE
	ENTERPRISE dl
	VARIABLES { siteID, stockTrapString, trapTypeString }
	DESCRIPTION
		"This user-defined trap is issued when an event happens
		that causes a trap with specific trap type 1137."
	::= 1137

dlUserTrap1138 TRAP-TYPE
	ENTERPRISE dl
	VARIABLES { siteID, stockTrapString, trapTypeString }
	DESCRIPTION
		"This user-defined trap is issued when an event happens
		that causes a trap with specific trap type 1138."
	::= 1138

dlUserTrap1139 TRAP-TYPE
	ENTERPRISE dl
	VARIABLES { siteID, stockTrapString, trapTypeString }
	DESCRIPTION
		"This user-defined trap is issued when an event happens
		that causes a trap with specific trap type 1139."
	::= 1139

dlUserTrap1140 TRAP-TYPE
	ENTERPRISE dl
	VARIABLES { siteID, stockTrapString, trapTypeString }
	DESCRIPTION
		"This user-defined trap is issued when an event happens
		that causes a trap with specific trap type 1140."
	::= 1140

dlUserTrap1141 TRAP-TYPE
	ENTERPRISE dl
	VARIABLES { siteID, stockTrapString, trapTypeString }
	DESCRIPTION
		"This user-defined trap is issued when an event happens
		that causes a trap with specific trap type 1141."
	::= 1141

dlUserTrap1142 TRAP-TYPE
	ENTERPRISE dl
	VARIABLES { siteID, stockTrapString, trapTypeString }
	DESCRIPTION
		"This user-defined trap is issued when an event happens
		that causes a trap with specific trap type 1142."
	::= 1142

dlUserTrap1143 TRAP-TYPE
	ENTERPRISE dl
	VARIABLES { siteID, stockTrapString, trapTypeString }
	DESCRIPTION
		"This user-defined trap is issued when an event happens
		that causes a trap with specific trap type 1143."
	::= 1143

dlUserTrap1144 TRAP-TYPE
	ENTERPRISE dl
	VARIABLES { siteID, stockTrapString, trapTypeString }
	DESCRIPTION
		"This user-defined trap is issued when an event happens
		that causes a trap with specific trap type 1144."
	::= 1144

dlUserTrap1145 TRAP-TYPE
	ENTERPRISE dl
	VARIABLES { siteID, stockTrapString, trapTypeString }
	DESCRIPTION
		"This user-defined trap is issued when an event happens
		that causes a trap with specific trap type 1145."
	::= 1145

dlUserTrap1146 TRAP-TYPE
	ENTERPRISE dl
	VARIABLES { siteID, stockTrapString, trapTypeString }
	DESCRIPTION
		"This user-defined trap is issued when an event happens
		that causes a trap with specific trap type 1146."
	::= 1146

dlUserTrap1147 TRAP-TYPE
	ENTERPRISE dl
	VARIABLES { siteID, stockTrapString, trapTypeString }
	DESCRIPTION
		"This user-defined trap is issued when an event happens
		that causes a trap with specific trap type 1147."
	::= 1147

dlUserTrap1148 TRAP-TYPE
	ENTERPRISE dl
	VARIABLES { siteID, stockTrapString, trapTypeString }
	DESCRIPTION
		"This user-defined trap is issued when an event happens
		that causes a trap with specific trap type 1148."
	::= 1148

dlUserTrap1149 TRAP-TYPE
	ENTERPRISE dl
	VARIABLES { siteID, stockTrapString, trapTypeString }
	DESCRIPTION
		"This user-defined trap is issued when an event happens
		that causes a trap with specific trap type 1149."
	::= 1149

dlUserTrap1150 TRAP-TYPE
	ENTERPRISE dl
	VARIABLES { siteID, stockTrapString, trapTypeString }
	DESCRIPTION
		"This user-defined trap is issued when an event happens
		that causes a trap with specific trap type 1150."
	::= 1150

dlUserTrap1151 TRAP-TYPE
	ENTERPRISE dl
	VARIABLES { siteID, stockTrapString, trapTypeString }
	DESCRIPTION
		"This user-defined trap is issued when an event happens
		that causes a trap with specific trap type 1151."
	::= 1151

dlUserTrap1152 TRAP-TYPE
	ENTERPRISE dl
	VARIABLES { siteID, stockTrapString, trapTypeString }
	DESCRIPTION
		"This user-defined trap is issued when an event happens
		that causes a trap with specific trap type 1152."
	::= 1152

dlUserTrap1153 TRAP-TYPE
	ENTERPRISE dl
	VARIABLES { siteID, stockTrapString, trapTypeString }
	DESCRIPTION
		"This user-defined trap is issued when an event happens
		that causes a trap with specific trap type 1153."
	::= 1153

dlUserTrap1154 TRAP-TYPE
	ENTERPRISE dl
	VARIABLES { siteID, stockTrapString, trapTypeString }
	DESCRIPTION
		"This user-defined trap is issued when an event happens
		that causes a trap with specific trap type 1154."
	::= 1154

dlUserTrap1155 TRAP-TYPE
	ENTERPRISE dl
	VARIABLES { siteID, stockTrapString, trapTypeString }
	DESCRIPTION
		"This user-defined trap is issued when an event happens
		that causes a trap with specific trap type 1155."
	::= 1155

dlUserTrap1156 TRAP-TYPE
	ENTERPRISE dl
	VARIABLES { siteID, stockTrapString, trapTypeString }
	DESCRIPTION
		"This user-defined trap is issued when an event happens
		that causes a trap with specific trap type 1156."
	::= 1156

dlUserTrap1157 TRAP-TYPE
	ENTERPRISE dl
	VARIABLES { siteID, stockTrapString, trapTypeString }
	DESCRIPTION
		"This user-defined trap is issued when an event happens
		that causes a trap with specific trap type 1157."
	::= 1157

dlUserTrap1158 TRAP-TYPE
	ENTERPRISE dl
	VARIABLES { siteID, stockTrapString, trapTypeString }
	DESCRIPTION
		"This user-defined trap is issued when an event happens
		that causes a trap with specific trap type 1158."
	::= 1158

dlUserTrap1159 TRAP-TYPE
	ENTERPRISE dl
	VARIABLES { siteID, stockTrapString, trapTypeString }
	DESCRIPTION
		"This user-defined trap is issued when an event happens
		that causes a trap with specific trap type 1159."
	::= 1159

dlUserTrap1160 TRAP-TYPE
	ENTERPRISE dl
	VARIABLES { siteID, stockTrapString, trapTypeString }
	DESCRIPTION
		"This user-defined trap is issued when an event happens
		that causes a trap with specific trap type 1160."
	::= 1160

dlUserTrap1161 TRAP-TYPE
	ENTERPRISE dl
	VARIABLES { siteID, stockTrapString, trapTypeString }
	DESCRIPTION
		"This user-defined trap is issued when an event happens
		that causes a trap with specific trap type 1161."
	::= 1161

dlUserTrap1162 TRAP-TYPE
	ENTERPRISE dl
	VARIABLES { siteID, stockTrapString, trapTypeString }
	DESCRIPTION
		"This user-defined trap is issued when an event happens
		that causes a trap with specific trap type 1162."
	::= 1162

dlUserTrap1163 TRAP-TYPE
	ENTERPRISE dl
	VARIABLES { siteID, stockTrapString, trapTypeString }
	DESCRIPTION
		"This user-defined trap is issued when an event happens
		that causes a trap with specific trap type 1163."
	::= 1163

dlUserTrap1164 TRAP-TYPE
	ENTERPRISE dl
	VARIABLES { siteID, stockTrapString, trapTypeString }
	DESCRIPTION
		"This user-defined trap is issued when an event happens
		that causes a trap with specific trap type 1164."
	::= 1164

dlUserTrap1165 TRAP-TYPE
	ENTERPRISE dl
	VARIABLES { siteID, stockTrapString, trapTypeString }
	DESCRIPTION
		"This user-defined trap is issued when an event happens
		that causes a trap with specific trap type 1165."
	::= 1165

dlUserTrap1166 TRAP-TYPE
	ENTERPRISE dl
	VARIABLES { siteID, stockTrapString, trapTypeString }
	DESCRIPTION
		"This user-defined trap is issued when an event happens
		that causes a trap with specific trap type 1166."
	::= 1166

dlUserTrap1167 TRAP-TYPE
	ENTERPRISE dl
	VARIABLES { siteID, stockTrapString, trapTypeString }
	DESCRIPTION
		"This user-defined trap is issued when an event happens
		that causes a trap with specific trap type 1167."
	::= 1167

dlUserTrap1168 TRAP-TYPE
	ENTERPRISE dl
	VARIABLES { siteID, stockTrapString, trapTypeString }
	DESCRIPTION
		"This user-defined trap is issued when an event happens
		that causes a trap with specific trap type 1168."
	::= 1168

dlUserTrap1169 TRAP-TYPE
	ENTERPRISE dl
	VARIABLES { siteID, stockTrapString, trapTypeString }
	DESCRIPTION
		"This user-defined trap is issued when an event happens
		that causes a trap with specific trap type 1169."
	::= 1169

dlUserTrap1170 TRAP-TYPE
	ENTERPRISE dl
	VARIABLES { siteID, stockTrapString, trapTypeString }
	DESCRIPTION
		"This user-defined trap is issued when an event happens
		that causes a trap with specific trap type 1170."
	::= 1170

dlUserTrap1171 TRAP-TYPE
	ENTERPRISE dl
	VARIABLES { siteID, stockTrapString, trapTypeString }
	DESCRIPTION
		"This user-defined trap is issued when an event happens
		that causes a trap with specific trap type 1171."
	::= 1171

dlUserTrap1172 TRAP-TYPE
	ENTERPRISE dl
	VARIABLES { siteID, stockTrapString, trapTypeString }
	DESCRIPTION
		"This user-defined trap is issued when an event happens
		that causes a trap with specific trap type 1172."
	::= 1172

dlUserTrap1173 TRAP-TYPE
	ENTERPRISE dl
	VARIABLES { siteID, stockTrapString, trapTypeString }
	DESCRIPTION
		"This user-defined trap is issued when an event happens
		that causes a trap with specific trap type 1173."
	::= 1173

dlUserTrap1174 TRAP-TYPE
	ENTERPRISE dl
	VARIABLES { siteID, stockTrapString, trapTypeString }
	DESCRIPTION
		"This user-defined trap is issued when an event happens
		that causes a trap with specific trap type 1174."
	::= 1174

dlUserTrap1175 TRAP-TYPE
	ENTERPRISE dl
	VARIABLES { siteID, stockTrapString, trapTypeString }
	DESCRIPTION
		"This user-defined trap is issued when an event happens
		that causes a trap with specific trap type 1175."
	::= 1175

dlUserTrap1176 TRAP-TYPE
	ENTERPRISE dl
	VARIABLES { siteID, stockTrapString, trapTypeString }
	DESCRIPTION
		"This user-defined trap is issued when an event happens
		that causes a trap with specific trap type 1176."
	::= 1176

dlUserTrap1177 TRAP-TYPE
	ENTERPRISE dl
	VARIABLES { siteID, stockTrapString, trapTypeString }
	DESCRIPTION
		"This user-defined trap is issued when an event happens
		that causes a trap with specific trap type 1177."
	::= 1177

dlUserTrap1178 TRAP-TYPE
	ENTERPRISE dl
	VARIABLES { siteID, stockTrapString, trapTypeString }
	DESCRIPTION
		"This user-defined trap is issued when an event happens
		that causes a trap with specific trap type 1178."
	::= 1178

dlUserTrap1179 TRAP-TYPE
	ENTERPRISE dl
	VARIABLES { siteID, stockTrapString, trapTypeString }
	DESCRIPTION
		"This user-defined trap is issued when an event happens
		that causes a trap with specific trap type 1179."
	::= 1179

dlUserTrap1180 TRAP-TYPE
	ENTERPRISE dl
	VARIABLES { siteID, stockTrapString, trapTypeString }
	DESCRIPTION
		"This user-defined trap is issued when an event happens
		that causes a trap with specific trap type 1180."
	::= 1180

dlUserTrap1181 TRAP-TYPE
	ENTERPRISE dl
	VARIABLES { siteID, stockTrapString, trapTypeString }
	DESCRIPTION
		"This user-defined trap is issued when an event happens
		that causes a trap with specific trap type 1181."
	::= 1181

dlUserTrap1182 TRAP-TYPE
	ENTERPRISE dl
	VARIABLES { siteID, stockTrapString, trapTypeString }
	DESCRIPTION
		"This user-defined trap is issued when an event happens
		that causes a trap with specific trap type 1182."
	::= 1182

dlUserTrap1183 TRAP-TYPE
	ENTERPRISE dl
	VARIABLES { siteID, stockTrapString, trapTypeString }
	DESCRIPTION
		"This user-defined trap is issued when an event happens
		that causes a trap with specific trap type 1183."
	::= 1183

dlUserTrap1184 TRAP-TYPE
	ENTERPRISE dl
	VARIABLES { siteID, stockTrapString, trapTypeString }
	DESCRIPTION
		"This user-defined trap is issued when an event happens
		that causes a trap with specific trap type 1184."
	::= 1184

dlUserTrap1185 TRAP-TYPE
	ENTERPRISE dl
	VARIABLES { siteID, stockTrapString, trapTypeString }
	DESCRIPTION
		"This user-defined trap is issued when an event happens
		that causes a trap with specific trap type 1185."
	::= 1185

dlUserTrap1186 TRAP-TYPE
	ENTERPRISE dl
	VARIABLES { siteID, stockTrapString, trapTypeString }
	DESCRIPTION
		"This user-defined trap is issued when an event happens
		that causes a trap with specific trap type 1186."
	::= 1186

dlUserTrap1187 TRAP-TYPE
	ENTERPRISE dl
	VARIABLES { siteID, stockTrapString, trapTypeString }
	DESCRIPTION
		"This user-defined trap is issued when an event happens
		that causes a trap with specific trap type 1187."
	::= 1187

dlUserTrap1188 TRAP-TYPE
	ENTERPRISE dl
	VARIABLES { siteID, stockTrapString, trapTypeString }
	DESCRIPTION
		"This user-defined trap is issued when an event happens
		that causes a trap with specific trap type 1188."
	::= 1188

dlUserTrap1189 TRAP-TYPE
	ENTERPRISE dl
	VARIABLES { siteID, stockTrapString, trapTypeString }
	DESCRIPTION
		"This user-defined trap is issued when an event happens
		that causes a trap with specific trap type 1189."
	::= 1189

dlUserTrap1190 TRAP-TYPE
	ENTERPRISE dl
	VARIABLES { siteID, stockTrapString, trapTypeString }
	DESCRIPTION
		"This user-defined trap is issued when an event happens
		that causes a trap with specific trap type 1190."
	::= 1190

dlUserTrap1191 TRAP-TYPE
	ENTERPRISE dl
	VARIABLES { siteID, stockTrapString, trapTypeString }
	DESCRIPTION
		"This user-defined trap is issued when an event happens
		that causes a trap with specific trap type 1191."
	::= 1191

dlUserTrap1192 TRAP-TYPE
	ENTERPRISE dl
	VARIABLES { siteID, stockTrapString, trapTypeString }
	DESCRIPTION
		"This user-defined trap is issued when an event happens
		that causes a trap with specific trap type 1192."
	::= 1192

dlUserTrap1193 TRAP-TYPE
	ENTERPRISE dl
	VARIABLES { siteID, stockTrapString, trapTypeString }
	DESCRIPTION
		"This user-defined trap is issued when an event happens
		that causes a trap with specific trap type 1193."
	::= 1193

dlUserTrap1194 TRAP-TYPE
	ENTERPRISE dl
	VARIABLES { siteID, stockTrapString, trapTypeString }
	DESCRIPTION
		"This user-defined trap is issued when an event happens
		that causes a trap with specific trap type 1194."
	::= 1194

dlUserTrap1195 TRAP-TYPE
	ENTERPRISE dl
	VARIABLES { siteID, stockTrapString, trapTypeString }
	DESCRIPTION
		"This user-defined trap is issued when an event happens
		that causes a trap with specific trap type 1195."
	::= 1195

dlUserTrap1196 TRAP-TYPE
	ENTERPRISE dl
	VARIABLES { siteID, stockTrapString, trapTypeString }
	DESCRIPTION
		"This user-defined trap is issued when an event happens
		that causes a trap with specific trap type 1196."
	::= 1196

dlUserTrap1197 TRAP-TYPE
	ENTERPRISE dl
	VARIABLES { siteID, stockTrapString, trapTypeString }
	DESCRIPTION
		"This user-defined trap is issued when an event happens
		that causes a trap with specific trap type 1197."
	::= 1197

dlUserTrap1198 TRAP-TYPE
	ENTERPRISE dl
	VARIABLES { siteID, stockTrapString, trapTypeString }
	DESCRIPTION
		"This user-defined trap is issued when an event happens
		that causes a trap with specific trap type 1198."
	::= 1198

dlUserTrap1199 TRAP-TYPE
	ENTERPRISE dl
	VARIABLES { siteID, stockTrapString, trapTypeString }
	DESCRIPTION
		"This user-defined trap is issued when an event happens
		that causes a trap with specific trap type 1199."
	::= 1199

END
