--			Ascend mibimahw MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIMAHW-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibimaHwConfig  OBJECT IDENTIFIER ::= { configuration 24}

	-- The mibimaHwConfig table
	--
	-- This table contains parameters for the mibimaHwConfig profile
	--

    mibimaHwConfigTable	OBJECT-TYPE
	SYNTAX		SEQUENCE OF MibimaHwConfigEntry
	ACCESS		not-accessible
	STATUS		mandatory
	DESCRIPTION	"A list of mibimaHwConfig profile entries."
	::= { mibimaHwConfig 1 }

    mibimaHwConfigEntry	OBJECT-TYPE
	SYNTAX		MibimaHwConfigEntry
	ACCESS		not-accessible
	STATUS		mandatory
	DESCRIPTION	"A mibimaHwConfig entry containing objects that
			 maps to the parameters of mibimaHwConfig profile."
	INDEX		{ imaHwConfig-Shelf-o, imaHwConfig-Slot-o, imaHwConfig-Item-o }
	::= { mibimaHwConfigTable 1 }

    MibimaHwConfigEntry ::=
	SEQUENCE {
	    imaHwConfig-Shelf-o
		INTEGER,
	    imaHwConfig-Slot-o
		INTEGER,
	    imaHwConfig-Item-o
		INTEGER,
	    imaHwConfig-Name
		DisplayString,
	    imaHwConfig-PhysicalAddress-Shelf
		INTEGER,
	    imaHwConfig-PhysicalAddress-Slot
		INTEGER,
	    imaHwConfig-PhysicalAddress-ItemNumber
		INTEGER,
	    imaHwConfig-AlphaImaValue
		INTEGER,
	    imaHwConfig-BetaImaValue
		INTEGER,
	    imaHwConfig-GammaImaValue
		INTEGER,
	    imaHwConfig-AlphaCellDelinValue
		INTEGER,
	    imaHwConfig-DeltaCellDelinValue
		INTEGER,
	    imaHwConfig-Action-o
		INTEGER
	}

    imaHwConfig-Shelf-o	OBJECT-TYPE
	SYNTAX	INTEGER
	ACCESS	read-only
	STATUS	mandatory
	DESCRIPTION	""
	::= { mibimaHwConfigEntry 1 }

    imaHwConfig-Slot-o	OBJECT-TYPE
	SYNTAX	INTEGER
	ACCESS	read-only
	STATUS	mandatory
	DESCRIPTION	""
	::= { mibimaHwConfigEntry 2 }

    imaHwConfig-Item-o	OBJECT-TYPE
	SYNTAX	INTEGER
	ACCESS	read-only
	STATUS	mandatory
	DESCRIPTION	""
	::= { mibimaHwConfigEntry 3 }

    imaHwConfig-Name	OBJECT-TYPE
	SYNTAX	DisplayString
	ACCESS	read-write
	STATUS	mandatory
	DESCRIPTION	"Name of IMA HW profile."
	::= { mibimaHwConfigEntry 4 }

    imaHwConfig-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibimaHwConfigEntry 5 }

    imaHwConfig-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibimaHwConfigEntry 6 }

    imaHwConfig-PhysicalAddress-ItemNumber	OBJECT-TYPE
	SYNTAX	INTEGER
	ACCESS	read-write
	STATUS	mandatory
	DESCRIPTION	"A number that specifies an addressable entity within the context of shelf and slot."
	::= { mibimaHwConfigEntry 7 }

    imaHwConfig-AlphaImaValue	OBJECT-TYPE
	SYNTAX	INTEGER
	ACCESS	read-write
	STATUS	mandatory
	DESCRIPTION	"Alpha value used to specify the number of consecutive invalid ICP cells to be detected before moving to IMA HUNT state from the SYNC state"
	::= { mibimaHwConfigEntry 8 }

    imaHwConfig-BetaImaValue	OBJECT-TYPE
	SYNTAX	INTEGER
	ACCESS	read-write
	STATUS	mandatory
	DESCRIPTION	"Beta value used to specify the number of consecutive errored ICP cells to be detected before moving to IMA HUNT state from the SYNC state"
	::= { mibimaHwConfigEntry 9 }

    imaHwConfig-GammaImaValue	OBJECT-TYPE
	SYNTAX	INTEGER
	ACCESS	read-write
	STATUS	mandatory
	DESCRIPTION	"Gamma value used to specify the number of consecutive valid ICP cells to be detected before moving to IMA SYNC state from the PRESYNC state"
	::= { mibimaHwConfigEntry 10 }

    imaHwConfig-AlphaCellDelinValue	OBJECT-TYPE
	SYNTAX	INTEGER
	ACCESS	read-write
	STATUS	mandatory
	DESCRIPTION	"Cell Delineation alpha value: number of consecutive cells with incoredct HEC to leave the SYNC to go to the HUNT state"
	::= { mibimaHwConfigEntry 11 }

    imaHwConfig-DeltaCellDelinValue	OBJECT-TYPE
	SYNTAX	INTEGER
	ACCESS	read-write
	STATUS	mandatory
	DESCRIPTION	"Cell Delineation delta value: number of consecutive cells with correct HEC to leave the PRESYNC state to go to the SYNC state."
	::= { mibimaHwConfigEntry 12 }

    imaHwConfig-Action-o	OBJECT-TYPE
	SYNTAX	INTEGER {
		    noAction (1),
		    createProfile (2),
		    deleteProfile (3)
		}
	ACCESS	read-write
	STATUS	mandatory
	DESCRIPTION	""
	::= { mibimaHwConfigEntry 13 }

END
