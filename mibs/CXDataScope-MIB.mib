CXDataScope-MIB DEFINITIONS ::= BEGIN

IMPORTS
   Counter,IpAddress   FROM RFC1155-SMI
   OBJECT-TYPE         FROM RFC-1212

--  Proprietary Imports
    cxDataScope        FROM CXProduct-SMI;

-- Under csDataScope node, there are three node
-- Global Control 
--       1.dsDataBaseSize
--       2. ... 
-- Database Control
--       1. # of events to read for one read operation
--       2.op-mode 
--       3. ...
-- Register(&Tracing Control) Table 
--       1. index (1..16)
--       2. AppID
--       3. ...

dsControl 
OBJECT IDENTIFIER
::= { cxDataScope  1 }

dsDataBaseVersion OBJECT-TYPE
   SYNTAX  OCTET STRING
   ACCESS  read-only
   STATUS  mandatory
DESCRIPTION " Version of the Database of Data Scope.
Default Value: none"
   ::= { dsControl 1 }

dsDataBaseSize OBJECT-TYPE
   SYNTAX  INTEGER (1..65535)
   ACCESS  read-write
   STATUS  mandatory
DESCRIPTION "The size of Database in Kbytes."
   ::= { dsControl 2 }

dsDataBaseReady OBJECT-TYPE
   SYNTAX  INTEGER {
            not-ready (1),
            ready     (2)
          }
   ACCESS  read-only
   STATUS  mandatory
   DESCRIPTION 
"Status of Database. READY if Database has memory; 
NOT-READY if it failed to allocate memory."
   DEFVAL { not-ready }
   ::= { dsControl 3 }

dsRTTYIpAddress OBJECT-TYPE
   SYNTAX  IpAddress
   ACCESS  read-write
   STATUS  mandatory
   DESCRIPTION 
" The IP address of RTTY. For the time being, only ONE RTTY is supported."
   ::= { dsControl 4 }


dsOutLostCounter1 OBJECT-TYPE
   SYNTAX  Counter
   ACCESS  read-only
   STATUS  mandatory
   DESCRIPTION 
"The number of data records discarded when sent to Local Console."
   ::= { dsControl 5 }

dsOutLostCounter2 OBJECT-TYPE
   SYNTAX  Counter
   ACCESS  read-only
   STATUS  mandatory
   DESCRIPTION 
"The number of data records discarded when sent to RTTY."
   ::= { dsControl 6 }
    
dsOutLostCounter3 OBJECT-TYPE
   SYNTAX  Counter
   ACCESS  read-only
   STATUS  mandatory
   DESCRIPTION 
"The number of data records discarded when sent to PC."
   ::= { dsControl 7 }

dsDataBase 
OBJECT IDENTIFIER
::= { cxDataScope  2 }

dsOperationMode OBJECT-TYPE
   SYNTAX  INTEGER {
            stop-mode      (1),
            write-mode     (2),
            read-mode      (3)
          }
   ACCESS  read-write
   STATUS  mandatory
   DESCRIPTION 
"Operational Mode of Database. No more data records can be saved 
to Database if the operational mode is in read-mode."
   DEFVAL { stop-mode }
   ::= { dsDataBase 1 }

dsTotalRecord OBJECT-TYPE
   SYNTAX  Counter
   ACCESS  read-only
   STATUS  mandatory
   DESCRIPTION 
"The total data records in the Database."
   ::= { dsDataBase 2 }

dsOverwrittenRecord OBJECT-TYPE
   SYNTAX  Counter
   ACCESS  read-only
   STATUS  mandatory
   DESCRIPTION 
"The amount of data records overwritten since last deleting operation."
   ::= { dsDataBase 3 }

dsReadNumberRecord OBJECT-TYPE
   SYNTAX  INTEGER (1..65535)
   ACCESS  read-write
   STATUS  mandatory
   DESCRIPTION 
"The number of data records that will be read per read operation."
   DEFVAL { 20 }
   ::= { dsDataBase 4 }

dsReadOutputDir OBJECT-TYPE
   SYNTAX  INTEGER {
            to-local-console   (1),
            to-RTTY-console    (2)
            }
   ACCESS  read-write
   STATUS  mandatory
   DESCRIPTION 
"Indicates where to send the data records when reading Database. When value is not
equal to 1 or 2, output will be sent to local console."
   DEFVAL { to-local-console }
   ::= { dsDataBase 5 }

dsDBControl OBJECT-TYPE
   SYNTAX  INTEGER (1..6)
   ACCESS  write-only
   STATUS  mandatory
   DESCRIPTION 
"Control of how to read/delete data resocrds in the Database: 
   1 - idle, no action,
   2 - read dsReadNumberRecord number of Previous records and keep those records,
   3 - read dsReadNumberRecord number of Previous records and erase those records,
   4 - read dsReadNumberRecord number of Next-records, and keep those records,
   5 - read dsReadNumberRecord number of Next-records, and erase those records,
   6 - Erase All Records."
   ::= { dsDataBase 6 }

dsReadFormat OBJECT-TYPE
   SYNTAX  INTEGER {
      ascii-format   (1),
      binary-format  (2)
      }
   ACCESS  read-write
   STATUS  mandatory
   DESCRIPTION 
"The output data format for reading data records in Database."
   DEFVAL { ascii-format }
   ::= { dsDataBase 7 }

dsRegistryTable OBJECT-TYPE
   SYNTAX  SEQUENCE OF DsRegistryEntry
   ACCESS  not-accessible
   STATUS  mandatory
   DESCRIPTION "Trace and Registry Control Table."
   REFERENCE
     "Data Scope Design Description. Memotec internal document"
   ::= { cxDataScope 3 }

    dsRegistryEntry  OBJECT-TYPE
     SYNTAX  DsRegistryEntry
     ACCESS  not-accessible
     STATUS  mandatory
     DESCRIPTION "Trace and Registry Control Table Entry."
     INDEX { dsRegAppID }
     ::= { dsRegistryTable 1 }

     DsRegistryEntry ::=
     SEQUENCE {
        dsRegAppID           INTEGER,
        dsRegTrafficType     INTEGER,
        dsRegIFIndex         INTEGER,
        dsRegDirFilter       INTEGER,
        dsRegState           INTEGER,
        dsRegDfMask          OCTET STRING,
        dsRegDfValue         OCTET STRING,
        dsRegDfCriteria      INTEGER,
        dsRegDfOffset        INTEGER,
        dsRegStartMask       OCTET STRING,
        dsRegStartValue      OCTET STRING,
        dsRegStartCriteria   INTEGER,
        dsRegStartOffset     INTEGER,
        dsRegStopMask        OCTET STRING,
        dsRegStopValue       OCTET STRING,
        dsRegStopCriteria    INTEGER,
        dsRegStopOffset      INTEGER,
        dsRegStatus          INTEGER,
        dsRegDataLength      INTEGER,
        dsRegDataOffset      INTEGER,
        dsRegOutputDir       INTEGER,
        dsRegOutputFormat    INTEGER
     }

   dsRegAppID OBJECT-TYPE
      SYNTAX  INTEGER 
      ACCESS  read-only
      STATUS  mandatory
      DESCRIPTION 
 "It is sap ID for driver tasks, or pre=defined application ID for other tasks."
     ::= { dsRegistryEntry 1 }

   dsRegTrafficType OBJECT-TYPE
     SYNTAX  INTEGER
     ACCESS  read-only
     STATUS  mandatory
     DESCRIPTION 
 "It is port type for driver tasks, or logical port type for other tasks."
     ::= { dsRegistryEntry 2 }

   dsRegIFIndex OBJECT-TYPE
     SYNTAX  INTEGER
     ACCESS  read-only
     STATUS  mandatory
     DESCRIPTION "It is the globalIndex in the ifTbl."
     ::= { dsRegistryEntry 3 }

   dsRegDirFilter OBJECT-TYPE
     SYNTAX  INTEGER {
            tx-and-rx    (1),
            tx-only      (2),
            rx-only      (3)
            }
     ACCESS  read-write
     STATUS  mandatory
     DESCRIPTION  
 "Filter on OsMessage Direction (Type)."
     DEFVAL { tx-and-rx }
     ::= { dsRegistryEntry 4 }

   dsRegState OBJECT-TYPE
     SYNTAX  INTEGER {
            disabled   (1),
            enabled    (2)
            }
     ACCESS  read-write
     STATUS  mandatory
     DESCRIPTION 
 "Indicating if Data Scope accepts data from the task registered at this entry."
     DEFVAL { disabled }
     ::= { dsRegistryEntry 5 }

   dsRegDfMask  OBJECT-TYPE
     SYNTAX  OCTET STRING (SIZE(1..4))
     ACCESS  read-write
     STATUS  mandatory
     DESCRIPTION 
 "Mask of the data filter. This mask will be ANDed with data chosen 
 by dfOffset. The result is checked against dsRegDfValue."
      DEFVAL { "00000000" }
     ::= { dsRegistryEntry 6 }

   dsRegDfValue OBJECT-TYPE
     SYNTAX  OCTET STRING (SIZE(1..4))
     ACCESS  read-write
     STATUS  mandatory
     DESCRIPTION 
 "Value of the data filter."    
     DEFVAL { "00000000" }
     ::= { dsRegistryEntry 7 }

   dsRegDfCriteria OBJECT-TYPE
     SYNTAX  INTEGER {
         equal    (1),
         not-equal (2)
         }
     ACCESS  read-write
     STATUS  mandatory
     DESCRIPTION 
 "The criteria of comparing dfValue with the value obtained 
 by ANDing dfMask with data."
     DEFVAL { equal }
     ::= { dsRegistryEntry 8 }

   dsRegDfOffset OBJECT-TYPE
     SYNTAX  INTEGER
     ACCESS  read-write
     STATUS  mandatory
     DESCRIPTION 
 "The offset of data to be checked."
     DEFVAL { 0 }
     ::= { dsRegistryEntry 9 }

   dsRegStartMask OBJECT-TYPE
     SYNTAX  OCTET STRING (SIZE(1..4))
     ACCESS  read-write
     STATUS  mandatory
     DESCRIPTION 
 "The mask of the data-match structure to trigger a start event."
     DEFVAL { "00000000" }
     ::= { dsRegistryEntry 20 }

   dsRegStartValue OBJECT-TYPE
     SYNTAX  OCTET STRING (SIZE(1..4))
     ACCESS  read-write
     STATUS  mandatory
     DESCRIPTION 
     "The value of the data-match structure to trigger a start event."
     DEFVAL { "00000000" }
     ::= { dsRegistryEntry 21 }

   dsRegStartCriteria OBJECT-TYPE
     SYNTAX  INTEGER {
         equal    (1),
         not-equal (2)
         }
     ACCESS  read-write
     STATUS  mandatory
     DESCRIPTION 
     "The criteria of the data-match structure to trigger a start event."
     DEFVAL { equal }
     ::= { dsRegistryEntry 22 }

   dsRegStartOffset OBJECT-TYPE
     SYNTAX  INTEGER
     ACCESS  read-write
     STATUS  mandatory
     DESCRIPTION 
     "The data offset of the data-match structure to trigger a start event."
     DEFVAL { 0 }
     ::= { dsRegistryEntry 23 }

   dsRegStopMask OBJECT-TYPE
     SYNTAX  OCTET STRING (SIZE(1..4))
     ACCESS  read-write
     STATUS  mandatory
      DESCRIPTION 
      "The mask of the data-match structure to trigger a stop event."
     DEFVAL { "00000000" }
     ::= { dsRegistryEntry 24 }

   dsRegStopValue OBJECT-TYPE
     SYNTAX  OCTET STRING (SIZE(1..4))
     ACCESS  read-write
     STATUS  mandatory
     DESCRIPTION 
     "The value of the data-match structure to trigger a stop event."
     DEFVAL { "00000000" }
     ::= { dsRegistryEntry 25 }

   dsRegStopCriteria OBJECT-TYPE
     SYNTAX  INTEGER {
         equal    (1),
         not-equal (2)
         }
     ACCESS  read-write
     STATUS  mandatory
     DESCRIPTION 
     "The criteria of the data-match structure to trigger a stop event. The 
     values other than 1 and 2 mean the number of events that Data Scope will
     trace before a stop event is generated."
     DEFVAL { equal }
     ::= { dsRegistryEntry 26 }

   dsRegStopOffset OBJECT-TYPE
     SYNTAX  INTEGER
     ACCESS  read-write
     STATUS  mandatory
     DESCRIPTION 
     "The data offset of the data-match structure to trigger a stop event."
     DEFVAL { 0 }
     ::= { dsRegistryEntry 27 }

   dsRegStatus OBJECT-TYPE
     SYNTAX  INTEGER {
            non-recording  (1),
            recording      (2)
            }     
     ACCESS  read-only
     STATUS  mandatory
     DESCRIPTION 
     "the state of this trace-registry entry, could be RECORDING or NON-RECORDING.
     When state is NON-RECORDING, a start event will change state to RECORDING; and 
     a stop event will changes state from RECORDING to NON-RECORDING."
     DEFVAL { non-recording }
     ::= { dsRegistryEntry 41 }

   dsRegDataLength OBJECT-TYPE
     SYNTAX  INTEGER 
     ACCESS  read-write
     STATUS  mandatory
     DESCRIPTION 
     "The maximum length of data that will be captured. Max. value is 65535."
     DEFVAL { 0 }
     ::= { dsRegistryEntry 42 }

   dsRegDataOffset OBJECT-TYPE
     SYNTAX  INTEGER
     ACCESS  read-write
     STATUS  mandatory
     DESCRIPTION 
     "The offset from where to start data capturing. Max. value is 65535."
     DEFVAL { 0 }
     ::= { dsRegistryEntry 43 }

   dsRegOutputDir OBJECT-TYPE
     SYNTAX  INTEGER
     ACCESS  read-write
     STATUS  mandatory
     DESCRIPTION 
 "a bitmap object indicating where to output the traced data.
     When Bit 0 set to 1: Output data to local console;
     When Bit 1 set to 1: Output data to RTTY;
     When Bit 2 set to 1: Output data to Database;"
     ::= { dsRegistryEntry 44 }
    
   dsRegOutputFormat OBJECT-TYPE
     SYNTAX  INTEGER {
         ascii-format      (1),
         binary-format     (2)
         } 
     ACCESS  read-write
     STATUS  mandatory
     DESCRIPTION 
"indicats the format to be used to output the traced data."
     DEFVAL { ascii-format }
     ::= { dsRegistryEntry 45 }
     
END
