ASYNCOS-MAIL-MIB DEFINITIONS ::= BEGIN

-- Enterprise MIB for IronPort Systems Mail Gateway Appliances
-- Compatible with SNMP Version 2.

IMPORTS
    MODULE-IDENTITY, Counter32, Gauge32, OBJECT-TYPE, NOTIFICATION-TYPE FROM SNMPv2-SMI
    DisplayString, TruthValue FROM SNMPv2-TC
    asyncOSMail FROM  IRONPORT-SMI;

asyncOSMailObjects MODULE-IDENTITY
    LAST-UPDATED "200811190000Z"
    ORGANIZATION "IronPort Systems"
    CONTACT-INFO "Postal: 950 Elm Avenue
                  San Bruno, CA 94066

                  Email:  customercare@ironport.com"
    DESCRIPTION
                  "Enterprise MIB for IronPort Systems Mail Gateway Appliances"
    REVISION      "200811190000Z"
                  DESCRIPTION
                     "Intial Release."
                  ::= { asyncOSMail 1 }


asyncOSMailNotifications OBJECT IDENTIFIER ::= { asyncOSMail 2 }

perCentMemoryUtilization OBJECT-TYPE
    SYNTAX INTEGER(0..100)
    MAX-ACCESS read-only
    STATUS current
    DESCRIPTION
        "Percent memory utilization."
    ::= {asyncOSMailObjects 1}

perCentCPUUtilization OBJECT-TYPE
    SYNTAX INTEGER(0..100)
    MAX-ACCESS read-only
    STATUS current
    DESCRIPTION
        "Percent CPU utilization."
    ::= {asyncOSMailObjects 2}

perCentDiskIOUtilization OBJECT-TYPE
    SYNTAX INTEGER(0..100)
    MAX-ACCESS read-only
    STATUS current
    DESCRIPTION
        "Percent disk I/O utilization."
    ::= {asyncOSMailObjects 3}

perCentQueueUtilization OBJECT-TYPE
    SYNTAX INTEGER(0..100)
    MAX-ACCESS read-only
    STATUS current
    DESCRIPTION
        "Percent of total queue capacity used."
    ::= {asyncOSMailObjects 4}

queueAvailabilityStatus OBJECT-TYPE
    SYNTAX INTEGER {
        queueSpaceAvailable(1),
        queueSpaceShortage(2),
        queueFull(3)
        }
    MAX-ACCESS read-only
    STATUS current
    DESCRIPTION
        "Queue space status: enough space, queue near full or queue full."
    ::= { asyncOSMailObjects 5}

resourceConservationReason OBJECT-TYPE
    SYNTAX INTEGER {
        noResourceConservation(1),
        memoryShortage(2),
        queueSpaceShortage(3),
        queueFull(4)
        }
    MAX-ACCESS read-only
    STATUS current
    DESCRIPTION
        "Reason system is in Resource Conservation Mode."
    ::= { asyncOSMailObjects 6}

memoryAvailabilityStatus OBJECT-TYPE
    SYNTAX INTEGER {
        memoryAvailable(1),
        memoryShortage(2),
        memoryFull(3)
        }
    MAX-ACCESS read-only
    STATUS current
    DESCRIPTION
        "Mail Transfer process's memory availability status."
    ::= { asyncOSMailObjects 7}

powerSupplyTable OBJECT-TYPE
    SYNTAX SEQUENCE OF PowerSupplyEntry
    MAX-ACCESS not-accessible
    STATUS current
    DESCRIPTION
        "A list of power supply entries."
    ::= {asyncOSMailObjects 8}

powerSupplyEntry OBJECT-TYPE
    SYNTAX PowerSupplyEntry
    MAX-ACCESS not-accessible
    STATUS current
    DESCRIPTION
        "Entry containing status of a power supply."
    INDEX { powerSupplyIndex }
    ::= { powerSupplyTable 1 }

PowerSupplyEntry ::= SEQUENCE {
    powerSupplyIndex INTEGER,
    powerSupplyStatus INTEGER,
    powerSupplyRedundancy INTEGER,
    powerSupplyName DisplayString
    }

powerSupplyIndex OBJECT-TYPE
    SYNTAX INTEGER(1..8)
    MAX-ACCESS not-accessible
    STATUS current
    DESCRIPTION
        "Module index into powerSupplyTable."
    ::= { powerSupplyEntry 1 }

powerSupplyStatus OBJECT-TYPE
    SYNTAX INTEGER {
        powerSupplyNotInstalled(1),
        powerSupplyHealthy(2),
        powerSupplyNoAC(3),
        powerSupplyFaulty(4)
        }
    MAX-ACCESS read-only
    STATUS current
    DESCRIPTION
        "The overall status of power supply."
    ::= { powerSupplyEntry 2 }

powerSupplyRedundancy OBJECT-TYPE
    SYNTAX INTEGER {
        powerSupplyRedundancyOK(1),
        powerSupplyRedundancyLost(2)
        }
    MAX-ACCESS read-only
    STATUS current
    DESCRIPTION
        "The status of power supply redundancy."
    ::= { powerSupplyEntry 3 }

powerSupplyName OBJECT-TYPE
    SYNTAX DisplayString
    MAX-ACCESS read-only
    STATUS current
    DESCRIPTION
        "Name of power supply.  E.g., PS 1."
    ::= { powerSupplyEntry 4 }

temperatureTable OBJECT-TYPE
    SYNTAX SEQUENCE OF TemperatureEntry
    MAX-ACCESS not-accessible
    STATUS current
    DESCRIPTION
        "A set of temperature entries."
    ::= {asyncOSMailObjects 9}

temperatureEntry OBJECT-TYPE
    SYNTAX TemperatureEntry
    MAX-ACCESS not-accessible
    STATUS current
    DESCRIPTION
        "Entry containing temperature in Celsius and name of sensor."
    INDEX { temperatureIndex }
    ::= { temperatureTable 1 }

TemperatureEntry ::= SEQUENCE {
    temperatureIndex INTEGER,
    degreesCelsius INTEGER,
    temperatureName DisplayString
    }

temperatureIndex OBJECT-TYPE
    SYNTAX INTEGER(1..8)
    MAX-ACCESS not-accessible
    STATUS current
    DESCRIPTION
        "Index into temperatureTable."
    ::= { temperatureEntry 1 }

degreesCelsius OBJECT-TYPE
    SYNTAX INTEGER
    MAX-ACCESS read-only
    STATUS current
    DESCRIPTION
        "Temperature in degrees Celsius."
    ::= { temperatureEntry 2 }

temperatureName OBJECT-TYPE
    SYNTAX DisplayString
    MAX-ACCESS read-only
    STATUS current
    DESCRIPTION
        "Descriptive name of measurement.  E.g. Ambient Temperature."
    ::= { temperatureEntry 3 }

fanTable OBJECT-TYPE
    SYNTAX SEQUENCE OF FanEntry
    MAX-ACCESS not-accessible
    STATUS current
    DESCRIPTION
        "A set of fan entries."
    ::= {asyncOSMailObjects 10}

fanEntry OBJECT-TYPE
    SYNTAX FanEntry
    MAX-ACCESS not-accessible
    STATUS current
    DESCRIPTION
        "Entry containing speed of fan in RPMs."
    INDEX { fanIndex }
    ::= { fanTable 1 }

FanEntry ::= SEQUENCE {
    fanIndex INTEGER,
    fanRPMs Gauge32,
    fanName DisplayString
    }

fanIndex OBJECT-TYPE
    SYNTAX INTEGER(1..8)
    MAX-ACCESS not-accessible
    STATUS current
    DESCRIPTION
        "Index into fanTable."
    ::= { fanEntry 1 }

fanRPMs OBJECT-TYPE
    SYNTAX Gauge32
    MAX-ACCESS read-only
    STATUS current
    DESCRIPTION
        "Fan speed in RPMs."
    ::= { fanEntry 2 }

fanName OBJECT-TYPE
    SYNTAX DisplayString
    MAX-ACCESS read-only
    STATUS current
    DESCRIPTION
        "Name of Fan.  E.g., FAN 1."
    ::= { fanEntry 3 }

workQueueMessages OBJECT-TYPE
    SYNTAX Gauge32
    MAX-ACCESS read-only
    STATUS current
    DESCRIPTION
        "Number of messages in the work queue."
    ::= {asyncOSMailObjects 11}

keyExpirationTable OBJECT-TYPE
    SYNTAX SEQUENCE OF KeyExpirationEntry
    MAX-ACCESS not-accessible
    STATUS current
    DESCRIPTION
        "A set of key expiration entries."
    ::= {asyncOSMailObjects 12}

keyExpirationEntry OBJECT-TYPE
    SYNTAX KeyExpirationEntry
    MAX-ACCESS not-accessible
    STATUS current
    DESCRIPTION
        "Entry containing a key's expiration status."
    INDEX { keyExpirationIndex }
    ::= { keyExpirationTable 1 }

KeyExpirationEntry ::= SEQUENCE {
    keyExpirationIndex INTEGER,
    keyDescription DisplayString,
    keyIsPerpetual TruthValue,
    keySecondsUntilExpire Gauge32
    }

keyExpirationIndex OBJECT-TYPE
    SYNTAX INTEGER(1..1024)
    MAX-ACCESS not-accessible
    STATUS current
    DESCRIPTION
        "Index into key Expiration Table."
    ::= { keyExpirationEntry 1 }

keyDescription OBJECT-TYPE
    SYNTAX DisplayString
    MAX-ACCESS read-only
    STATUS current
    DESCRIPTION
        "Description of key."
    ::= { keyExpirationEntry 2 }

keyIsPerpetual OBJECT-TYPE
    SYNTAX TruthValue
--    Rsyntax INTEGER {
--        true(1),
--        false(2)
--        }
    MAX-ACCESS read-only
    STATUS current
    DESCRIPTION
        "True if key is perpetual"
    ::= { keyExpirationEntry 3 }

keySecondsUntilExpire OBJECT-TYPE
    SYNTAX Gauge32
    MAX-ACCESS read-only
    STATUS current
    DESCRIPTION
        "Seconds until key expires."
    ::= { keyExpirationEntry 4 }

updateTable OBJECT-TYPE
    SYNTAX SEQUENCE OF UpdateEntry
    MAX-ACCESS not-accessible
    STATUS current
    DESCRIPTION
        "A set of update entries."
    ::= {asyncOSMailObjects 13}

updateEntry OBJECT-TYPE
    SYNTAX UpdateEntry
    MAX-ACCESS not-accessible
    STATUS current
    DESCRIPTION
        "Entry containing updates and update failures."
    INDEX { updateIndex }
    ::= { updateTable 1 }

UpdateEntry ::= SEQUENCE {
    updateIndex INTEGER,
    updateServiceName DisplayString,
    updates Counter32,
    updateFailures Counter32
    }

updateIndex OBJECT-TYPE
    SYNTAX INTEGER(1..1024)
    MAX-ACCESS not-accessible
    STATUS current
    DESCRIPTION
        "Index into updateTable."
    ::= { updateEntry 1 }

updateServiceName OBJECT-TYPE
    SYNTAX DisplayString
    MAX-ACCESS read-only
    STATUS current
    DESCRIPTION
        "Name of service for which update has been done."
    ::= { updateEntry 2 }

updates OBJECT-TYPE
    SYNTAX Counter32
    MAX-ACCESS read-only
    STATUS current
    DESCRIPTION
        "Number of updates."
    ::= { updateEntry 3 }

updateFailures OBJECT-TYPE
    SYNTAX Counter32
    MAX-ACCESS read-only
    STATUS current
    DESCRIPTION
        "Number of update failures."
    ::= { updateEntry 4 }

oldestMessageAge OBJECT-TYPE
    SYNTAX Gauge32
    MAX-ACCESS read-only
    STATUS current
    DESCRIPTION
        "The number of seconds the oldest message has been in queue"
    ::= {asyncOSMailObjects 14}

outstandingDNSRequests OBJECT-TYPE
    SYNTAX Gauge32
    MAX-ACCESS read-only
    STATUS current
    DESCRIPTION
        "Number of DNS requests that have been sent but for which no
         reply has been received."
    ::= {asyncOSMailObjects 15}

pendingDNSRequests OBJECT-TYPE
    SYNTAX Gauge32
    MAX-ACCESS read-only
    STATUS current
    DESCRIPTION
        "Number of DNS requests waiting to be sent."
    ::= {asyncOSMailObjects 16}

raidEvents OBJECT-TYPE
    SYNTAX Counter32
    MAX-ACCESS read-only
    STATUS current
    DESCRIPTION
        "Number of RAID events."
    ::= {asyncOSMailObjects 17}

raidTable                 OBJECT-TYPE
    SYNTAX SEQUENCE OF RAIDEntry
    MAX-ACCESS not-accessible
    STATUS current
    DESCRIPTION
        "A set of RAID entries"
    ::= {asyncOSMailObjects 18}

raidEntry OBJECT-TYPE
    SYNTAX RAIDEntry
    MAX-ACCESS not-accessible
    STATUS current
    DESCRIPTION
        "Entry containing status of a RAID drive."
    INDEX { raidIndex }
    ::= { raidTable 1 }

RAIDEntry ::= SEQUENCE {
    raidIndex INTEGER,
    raidStatus INTEGER,
    raidID DisplayString,
    raidLastError DisplayString
    }

raidIndex OBJECT-TYPE
    SYNTAX INTEGER(1..8)
    MAX-ACCESS not-accessible
    STATUS current
    DESCRIPTION
        "Index into raidTable."
    ::= { raidEntry 1 }

raidStatus OBJECT-TYPE
    SYNTAX INTEGER {
        driveHealthy(1),
        driveFailure(2),
        driveRebuild(3)
        }
    MAX-ACCESS read-only
    STATUS current
    DESCRIPTION
        "Status reported by RAID controller."
    ::= { raidEntry 2 }

raidID OBJECT-TYPE
    SYNTAX DisplayString
    MAX-ACCESS read-only
    STATUS current
    DESCRIPTION
        "Name of RAID component.  E.g.: RAID 1, DISK 2."
    ::= { raidEntry 3 }


raidLastError OBJECT-TYPE
    SYNTAX DisplayString
    MAX-ACCESS read-only
    STATUS current
    DESCRIPTION
        "Last RAID Error Message."
    ::= { raidEntry 4 }

openFilesOrSockets OBJECT-TYPE
    SYNTAX Gauge32
    MAX-ACCESS read-only
    STATUS current
    DESCRIPTION
        "Number of open files or sockets."
    ::= {asyncOSMailObjects 19}

mailTransferThreads OBJECT-TYPE
    SYNTAX Gauge32
    MAX-ACCESS read-only
    STATUS current
    DESCRIPTION
        "Number of threads that perform some task related to
         transferring mail."
    ::= {asyncOSMailObjects 20}

connectionURL OBJECT-TYPE
    SYNTAX DisplayString
    MAX-ACCESS read-only
    STATUS current
    DESCRIPTION
        "The connecting backend URL (?)"
    ::= { asyncOSMailObjects 21 }

memoryUtilization OBJECT-TYPE
    SYNTAX Gauge32
    MAX-ACCESS read-only
    STATUS current
    DESCRIPTION
	"The Memory utilization (?)"
    ::= {asyncOSMailObjects 22}

cpuUtilization OBJECT-TYPE
    SYNTAX Gauge32
    MAX-ACCESS read-only
    STATUS current
    DESCRIPTION
	"The CPU utilization (?)"
    ::= {asyncOSMailObjects 23}

--
--  Notifications
--

resourceConservationMode NOTIFICATION-TYPE
    OBJECTS { resourceConservationReason }
    STATUS current
    DESCRIPTION
        "Memory or queue utilization caused system to enter resource
         conservation mode."
    ::= { asyncOSMailNotifications 1 }

powerSupplyStatusChange NOTIFICATION-TYPE
    OBJECTS { powerSupplyStatus }
    STATUS current
    DESCRIPTION
        "Sent when power supply status changes."
    ::= { asyncOSMailNotifications 2 }

highTemperature NOTIFICATION-TYPE
    OBJECTS { temperatureName }
    STATUS current
    DESCRIPTION
        "Temperature has exceeded a recoverable failure threshold."
    ::= { asyncOSMailNotifications 3 }

fanFailure NOTIFICATION-TYPE
    OBJECTS { fanName }
    STATUS current
    DESCRIPTION
        "Speed of fan fanName has gone to zero."
    ::= { asyncOSMailNotifications 4 }

keyExpiration NOTIFICATION-TYPE
    OBJECTS { keyDescription }
    STATUS current
    DESCRIPTION
        "Key will expire."
    ::= { asyncOSMailNotifications 5 }

updateFailure NOTIFICATION-TYPE
    OBJECTS { updateServiceName }
    STATUS current
    DESCRIPTION
        "Update failure (spam rules, virus patterns, outbreak updates, etc.)"
    ::= { asyncOSMailNotifications 6 }

raidStatusChange NOTIFICATION-TYPE
    OBJECTS { raidID }
    STATUS current
    DESCRIPTION
        "Drive with ID: RAIDID has changed status."
    ::= { asyncOSMailNotifications 7 }

connectivityFailure NOTIFICATION-TYPE
    OBJECTS { connectionURL }
    STATUS current
    DESCRIPTION
        "There was a failure connecting to connectionURL."
    ::= { asyncOSMailNotifications 8 }

memoryUtilizationExceeded NOTIFICATION-TYPE
    OBJECTS { memoryUtilization }
    STATUS current
    DESCRIPTION
        "The memory utilization exceeded the configured threshold."
    ::= { asyncOSMailNotifications 9 }


cpuUtilizationExceeded NOTIFICATION-TYPE
    OBJECTS { cpuUtilization }
    STATUS current
    DESCRIPTION
        "The cpu's utilization exceeded the configured threshold."
    ::=  { asyncOSMailNotifications 10 }


END
