--			Ascend mibbgp MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBBGP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfBgpGlobal  OBJECT IDENTIFIER ::= { configuration 57}
    mibmibProfBgpPolicy  OBJECT IDENTIFIER ::= { configuration 60}
    mibmibProfBgpSummary  OBJECT IDENTIFIER ::= { configuration 59}
    mibmibProfBgpPeer  OBJECT IDENTIFIER ::= { configuration 58}

	-- The mibmibProfBgpGlobal table
	--
	-- This table contains parameters for the mibmibProfBgpGlobal profile
	--

    mibmibProfBgpGlobalTable	OBJECT-TYPE
	SYNTAX		SEQUENCE OF MibmibProfBgpGlobalEntry
	ACCESS		not-accessible
	STATUS		mandatory
	DESCRIPTION	"A list of mibmibProfBgpGlobal profile entries."
	::= { mibmibProfBgpGlobal 1 }

    mibmibProfBgpGlobalEntry	OBJECT-TYPE
	SYNTAX		MibmibProfBgpGlobalEntry
	ACCESS		not-accessible
	STATUS		mandatory
	DESCRIPTION	"A mibmibProfBgpGlobal entry containing objects that
			 maps to the parameters of mibmibProfBgpGlobal profile."
	INDEX		{ mibProfBgpGlobal-Index-o }
	::= { mibmibProfBgpGlobalTable 1 }

    MibmibProfBgpGlobalEntry ::=
	SEQUENCE {
	    mibProfBgpGlobal-Index-o
		INTEGER,
	    mibProfBgpGlobal-Enable
		INTEGER,
	    mibProfBgpGlobal-AutonomousSystem
		INTEGER,
	    mibProfBgpGlobal-Id
		IpAddress,
	    mibProfBgpGlobal-ConnectRetryInterval
		INTEGER,
	    mibProfBgpGlobal-KeepaliveTime
		INTEGER,
	    mibProfBgpGlobal-HoldTime
		INTEGER,
	    mibProfBgpGlobal-SubAs
		INTEGER,
	    mibProfBgpGlobal-ClusterId
		IpAddress,
	    mibProfBgpGlobal-IgpLockstep
		INTEGER,
	    mibProfBgpGlobal-MaxMultiPaths
		INTEGER,
	    mibProfBgpGlobal-StaticRouteRedistPolicy
		DisplayString,
	    mibProfBgpGlobal-ConnRouteRedistPolicy
		DisplayString,
	    mibProfBgpGlobal-LocalPrefDefault
		INTEGER,
	    mibProfBgpGlobal-AlwaysCompareMed
		INTEGER,
	    mibProfBgpGlobal-Action-o
		INTEGER
	}

    mibProfBgpGlobal-Index-o	OBJECT-TYPE
	SYNTAX	INTEGER
	ACCESS	read-only
	STATUS	mandatory
	DESCRIPTION	""
	::= { mibmibProfBgpGlobalEntry 1 }

    mibProfBgpGlobal-Enable	OBJECT-TYPE
	SYNTAX	INTEGER {
		    no (1),
		    yes (2)
		}
	ACCESS	read-write
	STATUS	mandatory
	DESCRIPTION	"Enable/Disable BGP on the box"
	::= { mibmibProfBgpGlobalEntry 2 }

    mibProfBgpGlobal-AutonomousSystem	OBJECT-TYPE
	SYNTAX	INTEGER
	ACCESS	read-write
	STATUS	mandatory
	DESCRIPTION	"Local Autonomous System number."
	::= { mibmibProfBgpGlobalEntry 3 }

    mibProfBgpGlobal-Id	OBJECT-TYPE
	SYNTAX	IpAddress
	ACCESS	read-write
	STATUS	mandatory
	DESCRIPTION	"Local BGP router id."
	::= { mibmibProfBgpGlobalEntry 4 }

    mibProfBgpGlobal-ConnectRetryInterval	OBJECT-TYPE
	SYNTAX	INTEGER
	ACCESS	read-write
	STATUS	mandatory
	DESCRIPTION	"The connection retry interval in seconds."
	::= { mibmibProfBgpGlobalEntry 5 }

    mibProfBgpGlobal-KeepaliveTime	OBJECT-TYPE
	SYNTAX	INTEGER
	ACCESS	read-write
	STATUS	mandatory
	DESCRIPTION	"The keep alive time interval in seconds."
	::= { mibmibProfBgpGlobalEntry 6 }

    mibProfBgpGlobal-HoldTime	OBJECT-TYPE
	SYNTAX	INTEGER
	ACCESS	read-write
	STATUS	mandatory
	DESCRIPTION	"The hold time interval in seconds."
	::= { mibmibProfBgpGlobalEntry 7 }

    mibProfBgpGlobal-SubAs	OBJECT-TYPE
	SYNTAX	INTEGER
	ACCESS	read-write
	STATUS	mandatory
	DESCRIPTION	"If non-zero, AS number within a confederation."
	::= { mibmibProfBgpGlobalEntry 16 }

    mibProfBgpGlobal-ClusterId	OBJECT-TYPE
	SYNTAX	IpAddress
	ACCESS	read-write
	STATUS	mandatory
	DESCRIPTION	"Cluster Identifier."
	::= { mibmibProfBgpGlobalEntry 9 }

    mibProfBgpGlobal-IgpLockstep	OBJECT-TYPE
	SYNTAX	INTEGER {
		    no (1),
		    yes (2)
		}
	ACCESS	read-write
	STATUS	mandatory
	DESCRIPTION	"Enable/Disable BGP igp-lockstep"
	::= { mibmibProfBgpGlobalEntry 10 }

    mibProfBgpGlobal-MaxMultiPaths	OBJECT-TYPE
	SYNTAX	INTEGER
	ACCESS	read-write
	STATUS	mandatory
	DESCRIPTION	"Maximum number of equal cost paths installed in the routing table"
	::= { mibmibProfBgpGlobalEntry 13 }

    mibProfBgpGlobal-StaticRouteRedistPolicy	OBJECT-TYPE
	SYNTAX	DisplayString
	ACCESS	read-write
	STATUS	mandatory
	DESCRIPTION	"BGP-POLICY profile to be used for static route redistribution policy"
	::= { mibmibProfBgpGlobalEntry 14 }

    mibProfBgpGlobal-ConnRouteRedistPolicy	OBJECT-TYPE
	SYNTAX	DisplayString
	ACCESS	read-write
	STATUS	mandatory
	DESCRIPTION	"BGP-POLICY profile to be used for connected routes redistribution policy"
	::= { mibmibProfBgpGlobalEntry 15 }

    mibProfBgpGlobal-LocalPrefDefault	OBJECT-TYPE
	SYNTAX	INTEGER
	ACCESS	read-write
	STATUS	mandatory
	DESCRIPTION	"Default Local Preference."
	::= { mibmibProfBgpGlobalEntry 17 }

    mibProfBgpGlobal-AlwaysCompareMed	OBJECT-TYPE
	SYNTAX	INTEGER {
		    no (1),
		    yes (2)
		}
	ACCESS	read-write
	STATUS	mandatory
	DESCRIPTION	"Enable/Disable BGP to compare MED from different AS's"
	::= { mibmibProfBgpGlobalEntry 18 }

    mibProfBgpGlobal-Action-o	OBJECT-TYPE
	SYNTAX	INTEGER {
		    noAction (1),
		    createProfile (2),
		    deleteProfile (3)
		}
	ACCESS	read-write
	STATUS	mandatory
	DESCRIPTION	""
	::= { mibmibProfBgpGlobalEntry 11 }


	-- The mibmibProfBgpPolicy table
	--
	-- This table contains parameters for the mibmibProfBgpPolicy profile
	--

    mibmibProfBgpPolicyTable	OBJECT-TYPE
	SYNTAX		SEQUENCE OF MibmibProfBgpPolicyEntry
	ACCESS		not-accessible
	STATUS		mandatory
	DESCRIPTION	"A list of mibmibProfBgpPolicy profile entries."
	::= { mibmibProfBgpPolicy 1 }

    mibmibProfBgpPolicyEntry	OBJECT-TYPE
	SYNTAX		MibmibProfBgpPolicyEntry
	ACCESS		not-accessible
	STATUS		mandatory
	DESCRIPTION	"A mibmibProfBgpPolicy entry containing objects that
			 maps to the parameters of mibmibProfBgpPolicy profile."
	INDEX		{ mibProfBgpPolicy-Name }
	::= { mibmibProfBgpPolicyTable 1 }

    MibmibProfBgpPolicyEntry ::=
	SEQUENCE {
	    mibProfBgpPolicy-Name
		DisplayString,
	    mibProfBgpPolicy-NextPolicy
		DisplayString,
	    mibProfBgpPolicy-Action-o
		INTEGER
	}

    mibProfBgpPolicy-Name	OBJECT-TYPE
	SYNTAX	DisplayString
	ACCESS	read-only
	STATUS	mandatory
	DESCRIPTION	"The name of the BGP Policy."
	::= { mibmibProfBgpPolicyEntry 1 }

    mibProfBgpPolicy-NextPolicy	OBJECT-TYPE
	SYNTAX	DisplayString
	ACCESS	read-write
	STATUS	mandatory
	DESCRIPTION	"The name of the next BGP policy to scan for rules"
	::= { mibmibProfBgpPolicyEntry 3 }

    mibProfBgpPolicy-Action-o	OBJECT-TYPE
	SYNTAX	INTEGER {
		    noAction (1),
		    createProfile (2),
		    deleteProfile (3)
		}
	ACCESS	read-write
	STATUS	mandatory
	DESCRIPTION	""
	::= { mibmibProfBgpPolicyEntry 2 }


	-- The mibmibProfBgpPolicy__rule table
	--
	-- This table contains parameters for the mibmibProfBgpPolicy__rule profile
	--

    mibmibProfBgpPolicy-RuleTable	OBJECT-TYPE
	SYNTAX		SEQUENCE OF MibmibProfBgpPolicy-RuleEntry
	ACCESS		not-accessible
	STATUS		mandatory
	DESCRIPTION	"A list of mibmibProfBgpPolicy__rule profile entries."
	::= { mibmibProfBgpPolicy 2 }

    mibmibProfBgpPolicy-RuleEntry	OBJECT-TYPE
	SYNTAX		MibmibProfBgpPolicy-RuleEntry
	ACCESS		not-accessible
	STATUS		mandatory
	DESCRIPTION	"A mibmibProfBgpPolicy__rule entry containing objects that
			 maps to the parameters of mibmibProfBgpPolicy__rule profile."
	INDEX		{ mibProfBgpPolicy-Rule-Name, mibProfBgpPolicy-Rule-Index-o }
	::= { mibmibProfBgpPolicy-RuleTable 1 }

    MibmibProfBgpPolicy-RuleEntry ::=
	SEQUENCE {
	    mibProfBgpPolicy-Rule-Name
		DisplayString,
	    mibProfBgpPolicy-Rule-Index-o
		INTEGER,
	    mibProfBgpPolicy-Rule
		DisplayString
	}

    mibProfBgpPolicy-Rule-Name	OBJECT-TYPE
	SYNTAX	DisplayString
	ACCESS	read-only
	STATUS	mandatory
	DESCRIPTION	""
	::= { mibmibProfBgpPolicy-RuleEntry 1 }

    mibProfBgpPolicy-Rule-Index-o	OBJECT-TYPE
	SYNTAX	INTEGER
	ACCESS	read-only
	STATUS	mandatory
	DESCRIPTION	""
	::= { mibmibProfBgpPolicy-RuleEntry 2 }

    mibProfBgpPolicy-Rule	OBJECT-TYPE
	SYNTAX	DisplayString
	ACCESS	read-write
	STATUS	mandatory
	DESCRIPTION	"The rule of the BGP Policy."
	::= { mibmibProfBgpPolicy-RuleEntry 3 }


	-- The mibmibProfBgpSummary table
	--
	-- This table contains parameters for the mibmibProfBgpSummary profile
	--

    mibmibProfBgpSummaryTable	OBJECT-TYPE
	SYNTAX		SEQUENCE OF MibmibProfBgpSummaryEntry
	ACCESS		not-accessible
	STATUS		mandatory
	DESCRIPTION	"A list of mibmibProfBgpSummary profile entries."
	::= { mibmibProfBgpSummary 1 }

    mibmibProfBgpSummaryEntry	OBJECT-TYPE
	SYNTAX		MibmibProfBgpSummaryEntry
	ACCESS		not-accessible
	STATUS		mandatory
	DESCRIPTION	"A mibmibProfBgpSummary entry containing objects that
			 maps to the parameters of mibmibProfBgpSummary profile."
	INDEX		{ mibProfBgpSummary-Prefix-IpAddress, mibProfBgpSummary-Prefix-Netmask }
	::= { mibmibProfBgpSummaryTable 1 }

    MibmibProfBgpSummaryEntry ::=
	SEQUENCE {
	    mibProfBgpSummary-Prefix-IpAddress
		IpAddress,
	    mibProfBgpSummary-Prefix-Netmask
		IpAddress,
	    mibProfBgpSummary-Enable
		INTEGER,
	    mibProfBgpSummary-SummarizationPolicy
		DisplayString,
	    mibProfBgpSummary-Action-o
		INTEGER
	}

    mibProfBgpSummary-Prefix-IpAddress	OBJECT-TYPE
	SYNTAX	IpAddress
	ACCESS	read-only
	STATUS	mandatory
	DESCRIPTION	"An IP address."
	::= { mibmibProfBgpSummaryEntry 8 }

    mibProfBgpSummary-Prefix-Netmask	OBJECT-TYPE
	SYNTAX	IpAddress
	ACCESS	read-only
	STATUS	mandatory
	DESCRIPTION	"The netmask"
	::= { mibmibProfBgpSummaryEntry 11 }

    mibProfBgpSummary-Enable	OBJECT-TYPE
	SYNTAX	INTEGER {
		    no (1),
		    yes (2)
		}
	ACCESS	read-write
	STATUS	mandatory
	DESCRIPTION	"Enable/Disable Bgp-Summarization"
	::= { mibmibProfBgpSummaryEntry 9 }

    mibProfBgpSummary-SummarizationPolicy	OBJECT-TYPE
	SYNTAX	DisplayString
	ACCESS	read-write
	STATUS	mandatory
	DESCRIPTION	"BGP-POLICY profile to be used for summarization policy"
	::= { mibmibProfBgpSummaryEntry 12 }

    mibProfBgpSummary-Action-o	OBJECT-TYPE
	SYNTAX	INTEGER {
		    noAction (1),
		    createProfile (2),
		    deleteProfile (3)
		}
	ACCESS	read-write
	STATUS	mandatory
	DESCRIPTION	""
	::= { mibmibProfBgpSummaryEntry 7 }


	-- The mibmibProfBgpPeer table
	--
	-- This table contains parameters for the mibmibProfBgpPeer profile
	--

    mibmibProfBgpPeerTable	OBJECT-TYPE
	SYNTAX		SEQUENCE OF MibmibProfBgpPeerEntry
	ACCESS		not-accessible
	STATUS		mandatory
	DESCRIPTION	"A list of mibmibProfBgpPeer profile entries."
	::= { mibmibProfBgpPeer 1 }

    mibmibProfBgpPeerEntry	OBJECT-TYPE
	SYNTAX		MibmibProfBgpPeerEntry
	ACCESS		not-accessible
	STATUS		mandatory
	DESCRIPTION	"A mibmibProfBgpPeer entry containing objects that
			 maps to the parameters of mibmibProfBgpPeer profile."
	INDEX		{ mibProfBgpPeer-PeerName }
	::= { mibmibProfBgpPeerTable 1 }

    MibmibProfBgpPeerEntry ::=
	SEQUENCE {
	    mibProfBgpPeer-PeerName
		DisplayString,
	    mibProfBgpPeer-Enable
		INTEGER,
	    mibProfBgpPeer-PeerIpAddress
		IpAddress,
	    mibProfBgpPeer-MyIpAddress
		IpAddress,
	    mibProfBgpPeer-AutonomousSystem
		INTEGER,
	    mibProfBgpPeer-AlwaysNextHop
		INTEGER,
	    mibProfBgpPeer-RouteReflectorClient
		INTEGER,
	    mibProfBgpPeer-ConfederationMember
		INTEGER,
	    mibProfBgpPeer-DefaultGatewayMetric
		INTEGER,
	    mibProfBgpPeer-AcceptPolicy
		DisplayString,
	    mibProfBgpPeer-InjectPolicy
		DisplayString,
	    mibProfBgpPeer-AdvertisePolicy
		DisplayString,
	    mibProfBgpPeer-Action-o
		INTEGER
	}

    mibProfBgpPeer-PeerName	OBJECT-TYPE
	SYNTAX	DisplayString
	ACCESS	read-only
	STATUS	mandatory
	DESCRIPTION	"Name of bgp peer"
	::= { mibmibProfBgpPeerEntry 14 }

    mibProfBgpPeer-Enable	OBJECT-TYPE
	SYNTAX	INTEGER {
		    no (1),
		    yes (2)
		}
	ACCESS	read-write
	STATUS	mandatory
	DESCRIPTION	"Enable/Disable Bgp-peer"
	::= { mibmibProfBgpPeerEntry 4 }

    mibProfBgpPeer-PeerIpAddress	OBJECT-TYPE
	SYNTAX	IpAddress
	ACCESS	read-write
	STATUS	mandatory
	DESCRIPTION	"The IP address of the BGP Peer."
	::= { mibmibProfBgpPeerEntry 15 }

    mibProfBgpPeer-MyIpAddress	OBJECT-TYPE
	SYNTAX	IpAddress
	ACCESS	read-write
	STATUS	mandatory
	DESCRIPTION	"The IP address of the Local BGP Peer."
	::= { mibmibProfBgpPeerEntry 16 }

    mibProfBgpPeer-AutonomousSystem	OBJECT-TYPE
	SYNTAX	INTEGER
	ACCESS	read-write
	STATUS	mandatory
	DESCRIPTION	"Autonomous System number of the BGP Peer."
	::= { mibmibProfBgpPeerEntry 3 }

    mibProfBgpPeer-AlwaysNextHop	OBJECT-TYPE
	SYNTAX	INTEGER {
		    no (1),
		    yes (2)
		}
	ACCESS	read-write
	STATUS	mandatory
	DESCRIPTION	"Always use local IP address as the next hop in update packets."
	::= { mibmibProfBgpPeerEntry 6 }

    mibProfBgpPeer-RouteReflectorClient	OBJECT-TYPE
	SYNTAX	INTEGER {
		    no (1),
		    yes (2)
		}
	ACCESS	read-write
	STATUS	mandatory
	DESCRIPTION	"Enable/Disable Bgp Peer as route refelector client"
	::= { mibmibProfBgpPeerEntry 7 }

    mibProfBgpPeer-ConfederationMember	OBJECT-TYPE
	SYNTAX	INTEGER {
		    no (1),
		    yes (2)
		}
	ACCESS	read-write
	STATUS	mandatory
	DESCRIPTION	"Is this peer a member of our confederation ?"
	::= { mibmibProfBgpPeerEntry 8 }

    mibProfBgpPeer-DefaultGatewayMetric	OBJECT-TYPE
	SYNTAX	INTEGER
	ACCESS	read-write
	STATUS	mandatory
	DESCRIPTION	"Metric to use when injecting this peer as gateway to default (0.0.0.0/0) route."
	::= { mibmibProfBgpPeerEntry 17 }

    mibProfBgpPeer-AcceptPolicy	OBJECT-TYPE
	SYNTAX	DisplayString
	ACCESS	read-write
	STATUS	mandatory
	DESCRIPTION	"BGP-POLICY profile to be used for accept policy"
	::= { mibmibProfBgpPeerEntry 10 }

    mibProfBgpPeer-InjectPolicy	OBJECT-TYPE
	SYNTAX	DisplayString
	ACCESS	read-write
	STATUS	mandatory
	DESCRIPTION	"BGP-POLICY profile to be used for inject policy"
	::= { mibmibProfBgpPeerEntry 11 }

    mibProfBgpPeer-AdvertisePolicy	OBJECT-TYPE
	SYNTAX	DisplayString
	ACCESS	read-write
	STATUS	mandatory
	DESCRIPTION	"BGP-POLICY profile to be used for advertise policy"
	::= { mibmibProfBgpPeerEntry 12 }

    mibProfBgpPeer-Action-o	OBJECT-TYPE
	SYNTAX	INTEGER {
		    noAction (1),
		    createProfile (2),
		    deleteProfile (3)
		}
	ACCESS	read-write
	STATUS	mandatory
	DESCRIPTION	""
	::= { mibmibProfBgpPeerEntry 13 }

END
