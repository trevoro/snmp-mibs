--			Ascend mibcmmodem MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCMMODEM-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmodemProfile  OBJECT IDENTIFIER ::= { configuration 144}

	-- The mibmodemProfile table
	--
	-- This table contains parameters for the mibmodemProfile profile
	--

    mibmodemProfileTable	OBJECT-TYPE
	SYNTAX		SEQUENCE OF MibmodemProfileEntry
	ACCESS		not-accessible
	STATUS		mandatory
	DESCRIPTION	"A list of mibmodemProfile profile entries."
	::= { mibmodemProfile 1 }

    mibmodemProfileEntry	OBJECT-TYPE
	SYNTAX		MibmodemProfileEntry
	ACCESS		not-accessible
	STATUS		mandatory
	DESCRIPTION	"A mibmodemProfile entry containing objects that
			 maps to the parameters of mibmodemProfile profile."
	INDEX		{ modemProfile-Shelf-o, modemProfile-Slot-o, modemProfile-Item-o }
	::= { mibmodemProfileTable 1 }

    MibmodemProfileEntry ::=
	SEQUENCE {
	    modemProfile-Shelf-o
		INTEGER,
	    modemProfile-Slot-o
		INTEGER,
	    modemProfile-Item-o
		INTEGER,
	    modemProfile-PhysicalAddress-Shelf
		INTEGER,
	    modemProfile-PhysicalAddress-Slot
		INTEGER,
	    modemProfile-PhysicalAddress-ItemNumber
		INTEGER,
	    modemProfile-AutoAnswer
		INTEGER,
	    modemProfile-CountryCode
		INTEGER,
	    modemProfile-Action-o
		INTEGER
	}

    modemProfile-Shelf-o	OBJECT-TYPE
	SYNTAX	INTEGER
	ACCESS	read-only
	STATUS	mandatory
	DESCRIPTION	""
	::= { mibmodemProfileEntry 1 }

    modemProfile-Slot-o	OBJECT-TYPE
	SYNTAX	INTEGER
	ACCESS	read-only
	STATUS	mandatory
	DESCRIPTION	""
	::= { mibmodemProfileEntry 2 }

    modemProfile-Item-o	OBJECT-TYPE
	SYNTAX	INTEGER
	ACCESS	read-only
	STATUS	mandatory
	DESCRIPTION	""
	::= { mibmodemProfileEntry 3 }

    modemProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmodemProfileEntry 4 }

    modemProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmodemProfileEntry 5 }

    modemProfile-PhysicalAddress-ItemNumber	OBJECT-TYPE
	SYNTAX	INTEGER
	ACCESS	read-write
	STATUS	mandatory
	DESCRIPTION	"A number that specifies an addressable entity within the context of shelf and slot."
	::= { mibmodemProfileEntry 6 }

    modemProfile-AutoAnswer	OBJECT-TYPE
	SYNTAX	INTEGER {
		    on (1),
		    off (2),
		    primaryOnly (3)
		}
	ACCESS	read-write
	STATUS	mandatory
	DESCRIPTION	"The auto answer mode used on controller's modem."
	::= { mibmodemProfileEntry 7 }

    modemProfile-CountryCode	OBJECT-TYPE
	SYNTAX	INTEGER {
		    australia (10),
		    austria (11),
		    belgium (16),
		    brazil (23),
		    bulgaria (28),
		    canada (33),
		    china (39),
		    czechslovak (47),
		    denmark (50),
		    finland (61),
		    france (62),
		    germany (67),
		    greece (71),
		    hongkong (81),
		    hungary (82),
		    india (84),
		    ireland (88),
		    israel (89),
		    italy (90),
		    japan (1),
		    korea (98),
		    luxembourg (106),
		    malaysia (109),
		    mexico (116),
		    netherlands (124),
		    newzealand (127),
		    norway (131),
		    philippines (138),
		    poland (139),
		    portugal (140),
		    russia (185),
		    singapore (157),
		    southafrica (160),
		    spain (161),
		    sweden (166),
		    switzerland (167),
		    taiwan (255),
		    unitedkingdom (181),
		    unitedstates (182)
		}
	ACCESS	read-write
	STATUS	mandatory
	DESCRIPTION	"The country code programmed into the controller's modem."
	::= { mibmodemProfileEntry 9 }

    modemProfile-Action-o	OBJECT-TYPE
	SYNTAX	INTEGER {
		    noAction (1),
		    createProfile (2),
		    deleteProfile (3)
		}
	ACCESS	read-write
	STATUS	mandatory
	DESCRIPTION	""
	::= { mibmodemProfileEntry 8 }

END
