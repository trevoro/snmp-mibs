-- *****************************************************************
-- CISCO-DHCP-SNOOPING-CAPABILITY.my:
-- Cisco CISCO-DHCP-SNOOPING-MIB AGENT-CAPABILITIES
--
-- March 2004, Edward Pham 
--
-- Copyright (c) 2004, 2006 by Cisco Systems, Inc.
-- All rights reserved.
-- *****************************************************************

CISCO-DHCP-SNOOPING-CAPABILITY DEFINITIONS ::= BEGIN

IMPORTS
        MODULE-IDENTITY
                FROM SNMPv2-SMI

        AGENT-CAPABILITIES
                FROM SNMPv2-CONF

        ciscoAgentCapability
                FROM CISCO-SMI;

ciscoDhcpSnoopingCapability MODULE-IDENTITY
        LAST-UPDATED    "200606280000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 CISCO-DHCP-SNOOPING-MIB."
        REVISION        "200606280000Z"
        DESCRIPTION
                "Added capability statements 
                 cdsCapabilityV08R0601Cat6kPfc and
                 cdsCapabilityV08R0601Cat6kPfc3." 
        REVISION        "200403090000Z"
        DESCRIPTION
                "Initial version of this MIB module."
        ::= { ciscoAgentCapability 383 }

cdsCapabilityV08R0301Cat6kPfc AGENT-CAPABILITIES
    PRODUCT-RELEASE      "Cisco CatOS 8.3(1) on Catalyst 6000/6500
                          and Cisco 7600 series devices with PFC
                          or PFC2 card."
    STATUS               current
    DESCRIPTION         "CISCO-DHCP-SNOOPING-MIB capabilities."
 
    SUPPORTS             CISCO-DHCP-SNOOPING-MIB
        INCLUDES         { cdsIfConfigGroup,
                           cdsBindingsGroup,
                           cdsGlobalEnableGroup, 
                           cdsVlanConfigGroup,
                           cdsStatisticsGroup,
                           cdsRelayAgentInfoOptGroup,
                           cdsRelayAgentRemoteIdGroup,
                           cdsMatchMacAddressGroup }

        VARIATION        cdsFeatureEnable 
            ACCESS       read-only
            DESCRIPTION
                   "Only support read-only access."

        VARIATION        cdsVlanDhcpSnoopingEnable 
            ACCESS       read-only
            DESCRIPTION
                   "Only support read-only access."

    ::= { ciscoDhcpSnoopingCapability 1 }

cdsCapabilityV08R0301Cat6kPfc3 AGENT-CAPABILITIES
    PRODUCT-RELEASE      "Cisco CatOS 8.3(1) on Catalyst 6000/6500
                          and Cisco 7600 series devices with PFC3
                          card."
    STATUS               current
    DESCRIPTION         "CISCO-DHCP-SNOOPING-MIB capabilities."
 
    SUPPORTS             CISCO-DHCP-SNOOPING-MIB
        INCLUDES         { cdsIfConfigGroup,
                           cdsBindingsGroup,
                           cdsGlobalEnableGroup, 
                           cdsVlanConfigGroup,
                           cdsStatisticsGroup,
                           cdsRelayAgentInfoOptGroup,
                           cdsRelayAgentRemoteIdGroup,
                           cdsMatchMacAddressGroup,
                           cdsIfSrcGuardGroup }

        VARIATION        cdsFeatureEnable 
            ACCESS       read-only
            DESCRIPTION
                   "Only support read-only access."

        VARIATION        cdsVlanDhcpSnoopingEnable 
            ACCESS       read-only
            DESCRIPTION
                   "Only support read-only access."

    ::= { ciscoDhcpSnoopingCapability 2 }

cdsCapabilityV08R0601Cat6kPfc AGENT-CAPABILITIES
    PRODUCT-RELEASE      "Cisco CatOS 8.6(1) on Catalyst 6000/6500
                          and Cisco 7600 series devices with PFC
                          or PFC2 card."
    STATUS               current
    DESCRIPTION         "CISCO-DHCP-SNOOPING-MIB capabilities."
 
    SUPPORTS             CISCO-DHCP-SNOOPING-MIB
        INCLUDES         { cdsIfConfigGroup,
                           cdsBindingsGroup,
                           cdsGlobalEnableGroup, 
                           cdsVlanConfigGroup,
                           cdsStatisticsGroup,
                           cdsRelayAgentInfoOptGroup,
                           cdsRelayAgentRemoteIdGroup,
                           cdsMatchMacAddressGroup,
                           cdsBindingsLimitGroup
                         }

        VARIATION        cdsFeatureEnable 
            ACCESS       read-only
            DESCRIPTION
                   "Cannot set this object in CatOS."

        VARIATION        cdsVlanDhcpSnoopingEnable 
            ACCESS       read-only
            DESCRIPTION
                   "Cannot set this object in CatOS."

        VARIATION        cdsGlobalMaxBindingsLimit 
            ACCESS       read-only
            DESCRIPTION
                   "Cannot set this object in CatOS."

    ::= { ciscoDhcpSnoopingCapability 3 }

cdsCapabilityV08R0601Cat6kPfc3 AGENT-CAPABILITIES
    PRODUCT-RELEASE      "Cisco CatOS 8.6(1) on Catalyst 6000/6500
                          and Cisco 7600 series devices with PFC3
                          card."
    STATUS               current
    DESCRIPTION         "CISCO-DHCP-SNOOPING-MIB capabilities."
 
    SUPPORTS             CISCO-DHCP-SNOOPING-MIB
        INCLUDES         { cdsIfConfigGroup,
                           cdsBindingsGroup,
                           cdsGlobalEnableGroup, 
                           cdsVlanConfigGroup,
                           cdsStatisticsGroup,
                           cdsRelayAgentInfoOptGroup,
                           cdsRelayAgentRemoteIdGroup,
                           cdsMatchMacAddressGroup,
                           cdsIfSrcGuardGroup,
                           cdsBindingsLimitGroup }

        VARIATION        cdsFeatureEnable 
            ACCESS       read-only
            DESCRIPTION
                   "Cannot set this object in CatOS."

        VARIATION        cdsVlanDhcpSnoopingEnable 
            ACCESS       read-only
            DESCRIPTION
                   "Cannot set this object in CatOS."

        VARIATION        cdsGlobalMaxBindingsLimit 
            ACCESS       read-only
            DESCRIPTION
                   "Cannot set this object in CatOS."

    ::= { ciscoDhcpSnoopingCapability 4 }

END
