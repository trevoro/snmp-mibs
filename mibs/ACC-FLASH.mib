ACC-FLASH DEFINITIONS ::= BEGIN

    IMPORTS
	 OBJECT-TYPE FROM RFC1155-SMI
 	 accTrapLogSeqNum FROM ACC-SYSTEM
	accBRG, DisplayString, RowStatus, IfIndex, SmdsAddress
             FROM ACC-MIB;
-- Bridge FDB Group
      accBridge OBJECT IDENTIFIER ::= { accBRG 4 }
	accBrFdbTimeout		OBJECT-TYPE   
			SYNTAX	INTEGER (10..65535)
			ACCESS	read-write
			STATUS	mandatory
			DESCRIPTION
                 " Time (seconds) for which a learned Forwarding Database
                   entry is valid before being deleted if it has not been seen."
			::= { accBridge 1 }  
	accBrFdbLearnMode	OBJECT-TYPE   
			SYNTAX	INTEGER {
				on(1),
				off(2)
				}
			ACCESS	read-write
			STATUS	mandatory
			DESCRIPTION
                " When Learning Mode is active, Bridges update their
                  Forwarding Database with dynamic entries learned by
                  inspection of the Source MAC Address of received frames.
                  When learning mode is off, Bridges discard packets which
                  are not indicated as forward in their Forwarding Database.
		"
			::= { accBridge 2 }
	accBrFdbRamCurrSize	OBJECT-TYPE   
			SYNTAX	INTEGER
			ACCESS	read-only
			STATUS	mandatory
			DESCRIPTION
                 " The number of entries in the RAM FDB table that contains
                   static as well as dynamic entries."
			::= { accBridge 3 }
	accBrFdbRamMaxSize	OBJECT-TYPE   
			SYNTAX	INTEGER (64..1024)
			ACCESS	read-write
			STATUS	mandatory
			DESCRIPTION
                 " The maximum number of entries configured for the RAM
                   FDB table."
			::= { accBridge 5 }
	accBrFdbNvmMaxSize	OBJECT-TYPE   
			SYNTAX	INTEGER
			ACCESS	read-only
			STATUS	mandatory
			DESCRIPTION
                 " Number of static FDB entries that can be saved
                   in the NVM RAM."
			::= { accBridge 6 }
	accBrFdbTable	OBJECT-TYPE
			SYNTAX SEQUENCE OF AccBrFdbEntry
			ACCESS not-accessible
			STATUS mandatory
			 DESCRIPTION
                 " A list of Forwarding Database entries. Entries may be
                   added/deleted either through learning or explicit
                   management action."
			 ::= { accBridge 7 }
	  accBrFdbEntry OBJECT-TYPE
			SYNTAX AccBrFdbEntry
			ACCESS not-accessible
			STATUS mandatory
			DESCRIPTION
                " A Forwarding Database entry which defines Bridge action
                  to be taken based upon the destination MAC Address of
                  received frames."
                        INDEX { accBrFdbEntMacAddr }
			::= { accBrFdbTable 1 }
	  AccBrFdbEntry  ::= SEQUENCE {
	    	accBrFdbEntMacAddr	OCTET STRING, -- (SIZE(6))
	    	accBrFdbEntDisp		INTEGER,
	    	accBrFdbEntPort		INTEGER,
	    	accBrFdbEntTimer	INTEGER
		}
	    accBrFdbEntMacAddr	OBJECT-TYPE   
			SYNTAX	OCTET STRING -- (SIZE(6))
			ACCESS	read-write
			STATUS	mandatory
			DESCRIPTION
                " MAC Address of the Forwarding Database Entry.
	          Set this object to NULL to delete entry."
			::= { accBrFdbEntry 1 }
	    accBrFdbEntDisp	OBJECT-TYPE   
			SYNTAX	INTEGER {
				forward(0),
				flood(1),
				discard(2)
				}
			ACCESS	read-write
			STATUS	mandatory
			DESCRIPTION
                 " Disposition of received Frame. Note that a Frame is
                   never sent back out on the Port on which it was received.
		   "
			::= { accBrFdbEntry 2 }
	    accBrFdbEntPort	OBJECT-TYPE   
			SYNTAX	INTEGER
			ACCESS	read-write
			STATUS	mandatory
			DESCRIPTION
                " Port to which frame is to be relayed for frame to be
                  forwarded.  Has no meaning for other dispositions."
			::= { accBrFdbEntry 3 }
	    accBrFdbEntTimer	OBJECT-TYPE   
			SYNTAX	INTEGER
			ACCESS	read-only
			STATUS	mandatory
			DESCRIPTION
                 " Age of Forwarding Database Entry.  A value of
                  zero indicates a static entry."
			::= { accBrFdbEntry 4 }
	accBrFpTable	OBJECT-TYPE
			SYNTAX SEQUENCE OF AccBrFpEntry
			ACCESS not-accessible
			STATUS mandatory
			DESCRIPTION
                 " A list of Forwarding Priority Entries.
		   Entries are added/deleted via management action."
			::= { accBridge 8 }
	  accBrFpEntry	OBJECT-TYPE
			SYNTAX  AccBrFpEntry
			ACCESS not-accessible
			STATUS mandatory
			DESCRIPTION
                   " Relative Priority between frames to be forwarded
                     on a Bridge Port. "
                        INDEX { accBrFpIndex }
			::= { accBrFpTable 1 }
             AccBrFpEntry ::= SEQUENCE {
	    	accBrFpIndex 	INTEGER,
	    	accBrFpProt	INTEGER,
	    	accBrFpPrio	INTEGER
		}
	    accBrFpIndex OBJECT-TYPE   
			SYNTAX	INTEGER 
			ACCESS	read-write
			STATUS	mandatory
			DESCRIPTION
			 " Port number "
			::= { accBrFpEntry 1 }
	    accBrFpProt OBJECT-TYPE   
			SYNTAX	INTEGER (0..65535)
			ACCESS	read-write
			STATUS	mandatory
			DESCRIPTION
			 " protocol type.
			   Set this object to NULL to delete the entry."
			::= { accBrFpEntry 2 }
	    accBrFpPrio OBJECT-TYPE   
			SYNTAX	INTEGER {
				discard(0),
				low(1),
				normal(2),
				high(3)
				}
			ACCESS	read-write
			STATUS	mandatory
			DESCRIPTION
                  " Relative forwarding priority assigned to protocol.
		"
			::= { accBrFpEntry 3 }
	accBrFpPriDefault	OBJECT-TYPE   
			SYNTAX	INTEGER {
				discard(0),
				low(1),
				normal(2),
				high(3)
				}
			ACCESS	read-write
			STATUS	mandatory
			DESCRIPTION
                " Default priority to use for protocol types not specifically
                  enumerated in table.
		"
			::= { accBridge 9 }
	accBrNumPorts	OBJECT-TYPE	
			SYNTAX	INTEGER (2..16)
			ACCESS	read-write
			STATUS	mandatory
			DESCRIPTION
                 " Number of physical ports of unit."
			::= { accBridge 10 }
	accBrCompress	OBJECT-TYPE	
			SYNTAX	INTEGER {
			       on(1),
			       off(2)
			       }
			ACCESS	read-write
			STATUS	mandatory
			DESCRIPTION
                 " Bridge frame compression mode."
			::= { accBridge 11 }
	accBrPortFRTable OBJECT-TYPE
		SYNTAX SEQUENCE OF AccBrPortFREntry
		ACCESS not-accessible
		STATUS mandatory
		DESCRIPTION
			 " "
		::= { accBridge 13 }
	accBrPortFREntry  OBJECT-TYPE
		SYNTAX AccBrPortFREntry
		ACCESS not-accessible
		STATUS mandatory
		DESCRIPTION
			 " "
                INDEX { accBrPortFRport }
		::= { accBrPortFRTable 1 }
	AccBrPortFREntry ::= SEQUENCE {
		accBrPortFRport		INTEGER,
		accBrPortFRdlci		INTEGER
			}
	accBrPortFRport  OBJECT-TYPE
		SYNTAX INTEGER
		ACCESS read-only
		STATUS mandatory
		DESCRIPTION
		 " "
		::= { accBrPortFREntry 1 }
	accBrPortFRdlci  OBJECT-TYPE
		SYNTAX INTEGER
		ACCESS read-write
		STATUS mandatory
		DESCRIPTION
		 " "
		::= { accBrPortFREntry 2 }
        accBrPortX25Table       OBJECT-TYPE
                      SYNTAX  SEQUENCE OF AccBrPortX25Entry
                      ACCESS  not-accessible
                      STATUS  mandatory
                      DESCRIPTION
                           " A table of X.25 bridge port parameters."
                      ::= { accBridge 14 }
        accBrPortX25Entry       OBJECT-TYPE
                      SYNTAX  AccBrPortX25Entry
                      ACCESS  not-accessible
                      STATUS  mandatory
                      DESCRIPTION
                      " An entry in the table of X.25 bridge port parameters."
                      INDEX	{ accBrPortX25port }
                      ::= { accBrPortX25Table 1 }
        AccBrPortX25Entry ::= SEQUENCE {
			accBrPortX25port	INTEGER,
			accBrPortX25addr1	INTEGER,
			accBrPortX25addr2	INTEGER,
			accBrPortX25idleTime	INTEGER,
			accBrPortX25pktNegot	INTEGER,
			accBrPortX25windowNegot	INTEGER,
			accBrPortX25FacIndex	INTEGER
                     }
	accBrPortX25port  OBJECT-TYPE
		SYNTAX INTEGER
		ACCESS read-only
		STATUS mandatory
		DESCRIPTION
			 " "
		::= { accBrPortX25Entry 1 }
	accBrPortX25addr1  OBJECT-TYPE
		SYNTAX INTEGER
		ACCESS read-write
		STATUS mandatory
		DESCRIPTION
			 " "
		::= { accBrPortX25Entry 2 }
	accBrPortX25addr2  OBJECT-TYPE
		SYNTAX INTEGER
		ACCESS read-write
		STATUS mandatory
		DESCRIPTION
			 " "
		::= { accBrPortX25Entry 3 }
	accBrPortX25idleTime  OBJECT-TYPE
		SYNTAX INTEGER
		ACCESS read-write
		STATUS mandatory
		DESCRIPTION
			 " "
		::= { accBrPortX25Entry 4 }
	accBrPortX25pktNegot  OBJECT-TYPE
		SYNTAX INTEGER
		ACCESS read-write
		STATUS mandatory
		DESCRIPTION
			 " "
		::= { accBrPortX25Entry 5 }
	accBrPortX25windowNegot  OBJECT-TYPE
		SYNTAX INTEGER
		ACCESS read-write
		STATUS mandatory
		DESCRIPTION
		 " "
		::= { accBrPortX25Entry 6 }
        accBrPortX25FacIndex  OBJECT-TYPE
                SYNTAX  INTEGER (0..255)
                ACCESS  read-write
                STATUS  mandatory
                DESCRIPTION
                " Index of optional facility string or 0."
                DEFVAL  { 0 }
                ::= { accBrPortX25Entry 7 }
	accBrMode	OBJECT-TYPE
			SYNTAX	INTEGER {
				bridging(1),	-- bridging is enabled
				off(2), -- bridging is disabled
				passive(3) -- forwarding is disabled
				}
			ACCESS	read-write
			STATUS	mandatory
			DESCRIPTION
		" Bridge mode.  When the mode is set to 'passive',
		  internally generated traffic is forwarded or flooded
		  as appropriate; external traffic is not forwarded to
		  other external ports."
			::= { accBridge 15 }
-- Bridge Filter Group
	accBrFilterMode	OBJECT-TYPE   
			SYNTAX	INTEGER {
				on	(1),
				off	(2)
				}
			ACCESS	read-write
			STATUS	mandatory
			DESCRIPTION
                " When Filter Mode is on, entries in the Filtering table
		  are used to determine the disposition of each frame.
                  When Filter mode is off, no filtering is done."
			::= { accBridge 16 }
	accBrFilterDefault	OBJECT-TYPE   
			SYNTAX	INTEGER {
				forward	(1),
				discard	(2)
				}
			ACCESS	read-write
			STATUS	mandatory
			DESCRIPTION
                 " The default disposition for all received frames when
		   filter mode is ON. Note: When filtering is ON, and the
		   bridge filter table search does NOT provide a match,
		   the default action will be performed."
			::= { accBridge 17 }
	accBrFilterTable	OBJECT-TYPE
			SYNTAX SEQUENCE OF AccBrFilterEntry
			ACCESS not-accessible
			STATUS deprecated
			DESCRIPTION
                 " A list of Filtering entries."
			 ::= { accBridge 18 }
	  accBrFilterEntry OBJECT-TYPE
			SYNTAX AccBrFilterEntry
			ACCESS not-accessible
			STATUS deprecated
			DESCRIPTION
                " A Filtering entry which defines Bridge action
                  to be taken based upon the destination AND source
		  MAC Addresses, port number, port protocol and logic op of
		  received frames."
                        INDEX {	accBrFilterEntDstMacAddr,
				accBrFilterEntSrcMacAddr,
				accBrFilterEntPort,
				accBrFilterEntLogicalOp,
				accBrFilterEntProtocol}
			::= { accBrFilterTable 1 }
	  AccBrFilterEntry  ::= SEQUENCE {
	    	accBrFilterEntDstMacAddr	OCTET STRING,
	    	accBrFilterEntSrcMacAddr	OCTET STRING,
	    	accBrFilterEntPort		INTEGER,
	    	accBrFilterEntLogicalOp		INTEGER,
	    	accBrFilterEntProtocol		OCTET STRING,
	    	accBrFilterEntDisp		INTEGER,
-- The following two items are not actually part of the SEQUENCE but were
-- defined as such. They have been placed in the SEQUENCE definition to avoid
-- MIB compiler problems.
		accBrFilterDiscards		INTEGER,
		accBrFilterEntries		INTEGER
		}
	    accBrFilterEntDstMacAddr	OBJECT-TYPE   
			SYNTAX	OCTET STRING -- (SIZE(6))
			ACCESS	read-write
			STATUS	deprecated
			DESCRIPTION
                " Destination MAC Address of the Filtering entry."
			::= { accBrFilterEntry 1 }
	    accBrFilterEntSrcMacAddr	OBJECT-TYPE   
			SYNTAX	OCTET STRING -- (SIZE(6))
			ACCESS	read-write
			STATUS	deprecated
			DESCRIPTION
                " Source MAC Address of the Filtering entry."
			::= { accBrFilterEntry 2 }
	    accBrFilterEntDisp	OBJECT-TYPE   
			SYNTAX	INTEGER {
				forward	(1),
				discard	(2)
				}
			ACCESS	read-write
			STATUS	deprecated
			DESCRIPTION
                 " Disposition of received Frame. Note that a Frame is
                   never sent back out on the Port on which it was received."
			::= { accBrFilterEntry 3 }
	    accBrFilterEntPort	OBJECT-TYPE   
			SYNTAX	INTEGER
			ACCESS	read-write
			STATUS	deprecated
			DESCRIPTION
                " In all cases, the destination port of the received 
                  frame."
			::= { accBrFilterEntry 4 }
	    accBrFilterEntLogicalOp	OBJECT-TYPE   
			SYNTAX	INTEGER {
				any		(1),
				equal		(2),
				notequal	(3)
				}
			ACCESS	read-write
			STATUS	deprecated
			DESCRIPTION
                 " Logical operation to be performed in conjunction with
		   specified protocol. This is an optional parameter."
			::= { accBrFilterEntry 5 }
	    accBrFilterEntProtocol	OBJECT-TYPE   
			SYNTAX  OCTET STRING -- (SIZE(2))	
			ACCESS	read-write
			STATUS	deprecated
			DESCRIPTION
                 " Protocol to be used in conjunction with logical operation
		   to determine the disposition of all received packets."
			::= { accBrFilterEntry 6 }
-- This unfortunate arrangement is done to make the object id's in the MIB
-- align with those that are implemented. This will produce an error message
-- in smic.
	    accBrFilterDiscards	OBJECT-TYPE   
			SYNTAX	INTEGER
			ACCESS	read-only
			STATUS	deprecated
			DESCRIPTION
                 " The number of packets discarded as a result of bridge
		   filtering. Maintained globally for all ports."
			::= { accBrFilterEntry 7 }
	    accBrFilterEntries	OBJECT-TYPE   
			SYNTAX	INTEGER
			ACCESS	read-only
			STATUS	deprecated
			DESCRIPTION
                 " The number of entries currently in the bridge filtering
		   table. The maximum number of entries is 50."
			::= { accBrFilterEntry 8 }
-- Extensions to the original Bridge filter group
	accBrFiltIITable	OBJECT-TYPE
			SYNTAX SEQUENCE OF AccBrFiltIIEntry
			ACCESS not-accessible
			STATUS mandatory
			DESCRIPTION
                 " A list of Filtering entries."
			 ::= { accBridge 19 }
	  accBrFiltIIEntry OBJECT-TYPE
			SYNTAX AccBrFiltIIEntry
			ACCESS not-accessible
			STATUS mandatory
			DESCRIPTION
                " A Filtering entry which defines the SR action
                  to be taken based upon the destination AND source
                  MAC Addresses AFTER applying the address masks,
                  port number, port protocol and logic op of received frames."
                        INDEX {	accBrFiltIIEntDstMacAddr,
				accBrFiltIIEntDstMacAddrMask,
				accBrFiltIIEntSrcMacAddr,
				accBrFiltIIEntSrcMacAddrMask,
				accBrFiltIIEntPort,
				accBrFiltIIEntLogicalOp,
				accBrFiltIIEntProtocol}
			::= { accBrFiltIITable 1 }
	  AccBrFiltIIEntry  ::= SEQUENCE {
	    	accBrFiltIIEntDstMacAddr	OCTET STRING,
	    	accBrFiltIIEntDstMacAddrMask	OCTET STRING,
	    	accBrFiltIIEntSrcMacAddr	OCTET STRING,
	    	accBrFiltIIEntSrcMacAddrMask	OCTET STRING,
	    	accBrFiltIIEntPort		INTEGER,
	    	accBrFiltIIEntLogicalOp		INTEGER,
	    	accBrFiltIIEntProtocol		INTEGER,
	    	accBrFiltIIEntDisp		INTEGER,
	    	accBrFiltIIEntStatus		INTEGER
		}
	    accBrFiltIIEntDstMacAddr	OBJECT-TYPE   
			SYNTAX	OCTET STRING -- (SIZE(6))
			ACCESS	read-write
			STATUS	mandatory
			DESCRIPTION
                " Destination MAC Address of the Filtering entry."
			::= { accBrFiltIIEntry 1 }
	    accBrFiltIIEntSrcMacAddr	OBJECT-TYPE   
			SYNTAX	OCTET STRING -- (SIZE(6))
			ACCESS	read-write
			STATUS	mandatory
			DESCRIPTION
                " Source MAC Address of the Filtering entry."
			::= { accBrFiltIIEntry 2 }
	    accBrFiltIIEntDisp	OBJECT-TYPE   
			SYNTAX	INTEGER {
				forward	(1),
				discard	(2)
				}
			ACCESS	read-write
			STATUS	mandatory
			DESCRIPTION
                 " Disposition of received Frame. Note that a Frame is
                   never sent back out on the Port on which it was received."
			::= { accBrFiltIIEntry 3 }
	    accBrFiltIIEntPort	OBJECT-TYPE   
			SYNTAX	INTEGER
			ACCESS	read-write
			STATUS	mandatory
			DESCRIPTION
                " In all cases, the destination port of the received 
                  frame."
			::= { accBrFiltIIEntry 4 }
	    accBrFiltIIEntLogicalOp	OBJECT-TYPE   
			SYNTAX	INTEGER {
				any		(1),
				equal		(2),
				notequal	(3)
				}
			ACCESS	read-write
			STATUS	mandatory
			DESCRIPTION
                 " Logical operation to be performed in conjunction with
		   specified protocol. This is an optional parameter."
			::= { accBrFiltIIEntry 5 }
	    accBrFiltIIEntProtocol	OBJECT-TYPE   
			SYNTAX  INTEGER	
			ACCESS	read-write
			STATUS	mandatory
			DESCRIPTION
                 " Protocol to be used in conjunction with logical operation
		   to determine the disposition of all received packets."
			::= { accBrFiltIIEntry 6 }
	    accBrFiltIIEntDstMacAddrMask	OBJECT-TYPE   
			SYNTAX	OCTET STRING -- (SIZE(6))
			ACCESS	read-write
			STATUS	mandatory
			DESCRIPTION
                " Destination MAC Address Mask for the Filtering entry.
                  The mask is ANDed with the Destination address to
                  determine that part of the MAC address which is used in
                  the filtering decision."
			::= { accBrFiltIIEntry 7 }
	    accBrFiltIIEntSrcMacAddrMask	OBJECT-TYPE   
			SYNTAX	OCTET STRING -- (SIZE(6))
			ACCESS	read-write
			STATUS	mandatory
			DESCRIPTION
                " Source MAC Address Mask for the Filtering entry.
                  The mask is ANDed with the Source address to
                  determine that part of the MAC address which is used in
                  the filtering decision."
			::= { accBrFiltIIEntry 8 }
	    accBrFiltIIEntStatus	OBJECT-TYPE   
			SYNTAX	INTEGER
			ACCESS	read-write
			STATUS	mandatory
			DESCRIPTION
                " 0 indicates that the entry is invalid,
		  1 indicates that the entry is valid."
			::= { accBrFiltIIEntry 9 }
	    accBrFiltIIDiscards	OBJECT-TYPE   
			SYNTAX	INTEGER
			ACCESS	read-only
			STATUS	mandatory
			DESCRIPTION
                 " The number of packets discarded as a result of bridge
		   filtering. Maintained globally for all ports."
			::= { accBridge 20 }
	    accBrFiltIIEntries	OBJECT-TYPE   
			SYNTAX	INTEGER
			ACCESS	read-only
			STATUS	mandatory
			DESCRIPTION
                 " The number of entries currently in the bridge filtering
		   table. The maximum number of entries is 150."
			::= { accBridge 21 }
    --
    --          The Bridge Pattern Filtering Table
    --
    	accBrFiltPatternTable OBJECT-TYPE
        	SYNTAX  SEQUENCE OF AccBrFiltPatternEntry
        	ACCESS          not-accessible
        	STATUS          mandatory
        	DESCRIPTION
             		""
    		::= { accBridge 22 }
    	accBrFiltPatternEntry OBJECT-TYPE
        	SYNTAX  AccBrFiltPatternEntry
        	ACCESS  not-accessible
       		STATUS  mandatory
		DESCRIPTION
			" "
        	INDEX   { accBrFiltPatternIndex }
        	::= { accBrFiltPatternTable  1 }
    	AccBrFiltPatternEntry ::=
        	SEQUENCE {
                	accBrFiltPatternIndex           INTEGER,
                	accBrFiltPatternPort		INTEGER,
                	accBrFiltPatternPath		INTEGER,
                	accBrFiltPatternByteOff		INTEGER,
                	accBrFiltPatternMask		OCTET STRING,
                	accBrFiltPatternCompVal		OCTET STRING,
                	accBrFiltPatternDisp		INTEGER,
                	accBrFiltPatternHitCount	INTEGER,
                	accBrFiltPatternStatus		INTEGER}
        accBrFiltPatternIndex OBJECT-TYPE
                SYNTAX  INTEGER
                ACCESS  read-write
                STATUS  mandatory
                DESCRIPTION
                     "Bridge Pattern Filter Table Index"
                ::= { accBrFiltPatternEntry  1 }
        accBrFiltPatternPort OBJECT-TYPE
                SYNTAX  INTEGER
                ACCESS  read-write
                STATUS  mandatory
                DESCRIPTION
                     "Bridge Pattern Filter table bridge port"
                ::= { accBrFiltPatternEntry  2 }
        accBrFiltPatternPath OBJECT-TYPE
                SYNTAX  INTEGER {
				in(1),
				out(2)
		}
                ACCESS  read-write
                STATUS  mandatory
                DESCRIPTION
                     "Bridge Pattern Filter table packet direction (input\output)."
                ::= { accBrFiltPatternEntry  3 }
	accBrFiltPatternByteOff OBJECT-TYPE
                SYNTAX  INTEGER
                ACCESS  read-write
                STATUS  mandatory
                DESCRIPTION
                     "Bridge Pattern Filter table byte offset into the packet."
                ::= { accBrFiltPatternEntry  4 }
	 accBrFiltPatternMask OBJECT-TYPE
                SYNTAX  OCTET STRING
                ACCESS  read-write
                STATUS  mandatory
                DESCRIPTION
                     "Bridge Pattern Filter table user defined hex mask."
                ::= { accBrFiltPatternEntry  5 }
	 accBrFiltPatternCompVal OBJECT-TYPE
                SYNTAX  OCTET STRING
                ACCESS  read-write
                STATUS  mandatory
                DESCRIPTION
                     "Bridge Pattern Filter table user defined comparison value."
                ::= { accBrFiltPatternEntry  6 }
	 accBrFiltPatternDisp OBJECT-TYPE
                SYNTAX  INTEGER {
				discard(1),
				low(2),
				normal(3),
				high(4)
			}
                ACCESS  read-write
                STATUS  mandatory
                DESCRIPTION
                     "Bridge Pattern Filter table packet disposition 
			(i.e. forward with priority or discard)."
                ::= { accBrFiltPatternEntry  7 }
	accBrFiltPatternHitCount OBJECT-TYPE
                SYNTAX  INTEGER
                ACCESS  read-write
                STATUS  mandatory
                DESCRIPTION
                     "Bridge Pattern Filter table filters that have been hit."
                ::= { accBrFiltPatternEntry  8 }
	accBrFiltPatternStatus OBJECT-TYPE
                SYNTAX  INTEGER
                ACCESS  read-only
                STATUS  mandatory
                DESCRIPTION
                     "This reads in the status of a user command that 
			defines if the filter is being added or deleted."
                ::= { accBrFiltPatternEntry  9 }
	    accFdbWhichAddr	OBJECT-TYPE   
                        SYNTAX  INTEGER {
                                destination      (1),
                                source           (2)
                                }
			ACCESS	read-write
			STATUS	mandatory
			DESCRIPTION
                 " Selects whether the MAC address in the forwarding
                   database is to be compared to the destination
                   or source MAC address in the traffic packets."
			::= { accBridge 23 }

END
