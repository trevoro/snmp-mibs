T2514-MIB DEFINITIONS ::= BEGIN


IMPORTS
	enterprises
		FROM RFC1155-SMI
	OBJECT-TYPE
		FROM RFC-1212;
  
  DisplayString ::= OCTET STRING

comet         OBJECT IDENTIFIER ::= { enterprises 22626 }
products      OBJECT IDENTIFIER ::= { comet 1 }
t2514         OBJECT IDENTIFIER ::= { products 2 }
readings      OBJECT IDENTIFIER ::= { t2514 1 }
settings      OBJECT IDENTIFIER ::= { t2514 2 }
readingsint   OBJECT IDENTIFIER ::= { t2514 3 }
settingsint   OBJECT IDENTIFIER ::= { t2514 4 }
traps         OBJECT IDENTIFIER ::= { t2514 5 }
tables	      OBJECT IDENTIFIER ::= { t2514 6 }

-- Power Source MIB
-- Parameters (Prefix ps)

pressure OBJECT-TYPE
	SYNTAX  	DisplayString (SIZE (0..8))
	ACCESS		read-only
	STATUS		mandatory
	DESCRIPTION	"Pressure"
::= { readings 4 }

-----------------------------------------------------------------------
-- settings
-----------------------------------------------------------------------

presslow OBJECT-TYPE
	SYNTAX  	DisplayString (SIZE (0..8))
	ACCESS		read-only
	STATUS		mandatory
	DESCRIPTION	"Pressure Limit Low"
::= { settings 13 }

presshigh OBJECT-TYPE
	SYNTAX  	DisplayString (SIZE (0..8))
	ACCESS		read-only
	STATUS		mandatory
	DESCRIPTION	"Pressure Limit High"
::= { settings 14 }

presstime OBJECT-TYPE
	SYNTAX		INTEGER (0..65535)
	ACCESS		read-only
	STATUS		mandatory
	DESCRIPTION	"Pressure alaram delay"
::= { settings 15 }

pressureHyst OBJECT-TYPE
	SYNTAX  	DisplayString (SIZE (0..8))
	ACCESS		read-only
	STATUS		mandatory
	DESCRIPTION	"Pressure hysteresis"
::= { settings 16 }

-----------------------------------------------------------------------
-- readingsint
-----------------------------------------------------------------------

pressurei OBJECT-TYPE
	SYNTAX  	INTEGER(-2000..6000)
	ACCESS		read-only
	STATUS		mandatory
	DESCRIPTION	"Pressure *10"
::= { readingsint 4 }

-----------------------------------------------------------------------
-- settingsint
-----------------------------------------------------------------------

presslowi OBJECT-TYPE
	SYNTAX  	INTEGER(0..65535)
	ACCESS		read-write
	STATUS		mandatory
	DESCRIPTION	"Pressure Limit Low *10"
::= { settingsint 13 }

presshighi OBJECT-TYPE
	SYNTAX  	INTEGER(0..11000)
	ACCESS		read-write
	STATUS		mandatory
	DESCRIPTION	"Pressure Limit High *10"
::= { settingsint 14 }

presstimei OBJECT-TYPE
	SYNTAX		INTEGER (0..65535)
	ACCESS		read-write
	STATUS		mandatory
	DESCRIPTION	"Pressure alaram delay"
::= { settingsint 15 }

pressHysti OBJECT-TYPE
	SYNTAX  	INTEGER(-2000..6000)
	ACCESS		read-write
	STATUS		mandatory
	DESCRIPTION	"Pressure hysteresis *10"
::= { settingsint 16 }

-----------------------------------------------------------------------
messageString OBJECT-TYPE
	SYNTAX		DisplayString (SIZE (0..30))
	ACCESS		read-only
	STATUS		mandatory
	DESCRIPTION	"Message giving more detailed information on alarms."
::= { traps 1 }

alarmPressure OBJECT-TYPE
	SYNTAX  	INTEGER(0..2)
	ACCESS		read-only
	STATUS		mandatory
	DESCRIPTION	"Pressure alarm
0 = Computed value OK
1 = Computed value too high
2 = Computed value too low"
	::= { traps 5 }

historyTable OBJECT-TYPE
	SYNTAX  SEQUENCE OF HistoryEntry
	ACCESS  not-accessible
	STATUS  mandatory
	DESCRIPTION	"Table of the history values."
::= { tables 1 }

historyEntry OBJECT-TYPE
	SYNTAX  HistoryEntry
	ACCESS  not-accessible
	STATUS  optional
	DESCRIPTION	"History values entries."
	INDEX   { histpressure }
::= { historyTable 1 }

HistoryEntry ::=
	SEQUENCE {
		histpressure
			INTEGER
		}

histpressure OBJECT-TYPE
	SYNTAX  INTEGER (1..65535)
	ACCESS  read-only
	STATUS  mandatory
	DESCRIPTION	"Pressure reading."
::= { historyEntry 4 }

END
