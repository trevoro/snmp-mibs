C-PRODUCT-MCPU-MIB DEFINITIONS ::= BEGIN


IMPORTS
    mcpu                 FROM C-PRODUCT-GROUP-MIB
    cardSlot,
    vcpSideId            FROM C-PRODUCT-BASE-MIB
    IpAddress            FROM RFC1155-SMI
    OBJECT-TYPE          FROM RFC-1212;

-- MCPU group

mcpuVc           OBJECT IDENTIFIER ::= { mcpu   1 }
mcpuNewVc        OBJECT IDENTIFIER ::= { mcpu   2 }
shaper           OBJECT IDENTIFIER ::= { mcpu   3 }

-- Mcpu VC subgroup 
-- This table is used to access the VC's on the MCPU card For PBS600
-- Release 1.4 & 1.5.
-- Mcpu New VC Subgroup is used by PBS330 & PBS600 Rel 2.0 onwards.

mcpuNewVcTable OBJECT-TYPE
    SYNTAX SEQUENCE OF McpuNewVcEntry
    ACCESS not-accessible
    STATUS mandatory
    DESCRIPTION
            "The mcpu VC information table."
    ::= { mcpuNewVc 1 }

mcpuNewVcEntry OBJECT-TYPE
    SYNTAX McpuNewVcEntry
    ACCESS not-accessible
    STATUS mandatory
    DESCRIPTION
            "Information about a MCPU VC.  The slot number (vcPortSlot) 
             of the MCPU card should be 1. The port number (vcPortPort) 
             should be 1."
    INDEX { vcpSideId }
    ::= { mcpuNewVcTable 1 }

McpuNewVcEntry ::=
    SEQUENCE {
        mcpuNewVcShaper
            INTEGER,
        mcpuNewVcIpAddress
            IpAddress,
        mcpuNewVcSubnetMask
            IpAddress
    }

mcpuNewVcShaper OBJECT-TYPE
    SYNTAX INTEGER { dr-56K    (1),
		     dr-112K   (2),
		     dr-224K   (3),
		     dr-448K   (4),
		     dr-673K   (5),
		     dr-1344K  (6),
		     dr-149M   (7),
		     dr-1536M  (8),
		     dr-192M   (9),
		     dr-238M   (10),
		     dr-4M     (11),
		     dr-6M     (12),
		     dr-8M     (13),
		     dr-10M    (14),
		     dr-17M    (15)  }
    ACCESS read-write
    STATUS mandatory
    DESCRIPTION
            "Data rate supported by the MCPU VC. "
    ::= { mcpuNewVcEntry 1 }

mcpuNewVcIpAddress OBJECT-TYPE
    SYNTAX  IpAddress
    ACCESS  read-write
    STATUS  mandatory
    DESCRIPTION
            "Management VC IP address."
    DEFVAL  { '00000000'h }
    ::= { mcpuNewVcEntry 2 }

mcpuNewVcSubnetMask OBJECT-TYPE
    SYNTAX  IpAddress
    ACCESS  read-write
    STATUS  mandatory
    DESCRIPTION
            "Management VC IP subnet mask."
    DEFVAL  { '00000000'h }
    ::= { mcpuNewVcEntry 3 }



-- shaper Configuration Group

shaperTable OBJECT-TYPE
    SYNTAX  SEQUENCE OF ShaperEntry
    ACCESS  not-accessible
    STATUS  mandatory
    DESCRIPTION
            "The shaper Table contains up to 15 shapers rate. This 
	     table uses cardSlot and Shaper number as an index which
	     is uniquely assoicate to entry of each shaper. " 
    ::= { shaper 1 }

shaperEntry OBJECT-TYPE
    SYNTAX  ShaperEntry
    ACCESS  not-accessible
    STATUS  mandatory
    DESCRIPTION
            "Each entry in the table contains the information of
             a shaper."      
    INDEX { cardSlot, shaperNumber }
    ::= { shaperTable 1 }

ShaperEntry ::=
    SEQUENCE {
        shaperNumber
            INTEGER,
        shaperSustainableCellRateInbps
            INTEGER,
        shaperSustainableCellRateIncps
            INTEGER,
        shaperPeakCellRateInbps
            INTEGER,
        shaperPeakCellRateIncps
            INTEGER,
        shaperMaximumBurstSizeInBits
            INTEGER,
        shaperMaximumBurstSizeInCells
            INTEGER
    }

shaperNumber OBJECT-TYPE
    SYNTAX INTEGER (1..15)
    ACCESS not-accessible
    STATUS mandatory
    DESCRIPTION
            "Shaper Number of a frame based card"
    ::= { shaperEntry 1 }

shaperSustainableCellRateInbps OBJECT-TYPE
    SYNTAX  INTEGER (16000..17000000)
    ACCESS  read-write
    STATUS  mandatory
    DESCRIPTION
            "Sustainable Cell Rate (SCR), in bits per second, is an upper
	     bound on the conforming average rate of an ATM connection 
	     over time scales."
    ::= { shaperEntry 2 }

shaperSustainableCellRateIncps OBJECT-TYPE
    SYNTAX  INTEGER 
    ACCESS  read-only
    STATUS  mandatory
    DESCRIPTION
            "Sustainable Cell Rate (SCR), in cells per second, is an upper
	     bound on the conforming average rate of an ATM connection 
	     over time scales. The value is calculated based on the
	     input from SCR in bps."
    ::= { shaperEntry 3 }

shaperPeakCellRateInbps OBJECT-TYPE
    SYNTAX  INTEGER (784000..17000000)
    ACCESS  read-write
    STATUS  mandatory
    DESCRIPTION
            "Peak Cell Rate (PCR), in bits per second, is the rate at 
	     which ATM source end system can send to a referenced 
	     physical service access point that is equal to the 
	     inverse of the minimum cell interarrival time.  The 
	     value of Peak Rate Cell Rate (PCR) cannot be lower 
	     than Sustainable Cell Rate (SCR). " 
    ::= { shaperEntry 4 }

shaperPeakCellRateIncps OBJECT-TYPE
    SYNTAX  INTEGER 
    ACCESS  read-only
    STATUS  mandatory
    DESCRIPTION
            "Peak Cell Rate (PCR), in cells per second, is the rate at 
	     which ATM source end system can send to a referenced 
	     physical service access point that is equal to the 
	     inverse of the minimum cell interarrival time.  The 
	     value of Peak Rate Cell Rate (PCR) is calculated 
	     based on the input from PCR in bps.  "
    ::= { shaperEntry 5 }

shaperMaximumBurstSizeInBits OBJECT-TYPE
    SYNTAX  INTEGER 
    ACCESS  read-only
    STATUS  mandatory
    DESCRIPTION
            "Maximum Burst Size in bits. 
	    This value is read only and is calculated again
	    when MBS (in cells) is changed"
    ::= { shaperEntry 6 }

shaperMaximumBurstSizeInCells OBJECT-TYPE
    SYNTAX  INTEGER (1..255)
    ACCESS  read-write
    STATUS  mandatory
    DESCRIPTION
            "Maximum Burst Size in cells.
	    Minimum value is 1 cell and maximum value is 
	    255 cells. "
    ::= { shaperEntry 7 }


END
