-- extracted from draft-ietf-hubmib-efm-epon-mib-03.txt
-- at Sat Mar 12 06:25:43 2005

   DOT3-EFM-EPON-MIB DEFINITIONS ::= BEGIN

        IMPORTS
            MODULE-IDENTITY, mib-2, OBJECT-TYPE, Counter32,
            Integer32
                FROM SNMPv2-SMI
            TruthValue, MacAddress
                FROM SNMPv2-TC
            ifIndex
                FROM IF-MIB
            MODULE-COMPLIANCE, OBJECT-GROUP
                FROM SNMPv2-CONF
            ;

   dot3EfmeponMIB MODULE-IDENTITY
       LAST-UPDATED "200503100000Z"  -- March 10, 2005
       ORGANIZATION "IETF Ethernet Interfaces and Hub MIB Working
                    Group"
       CONTACT-INFO
                    "WG charter:
                 http://www.ietf.org/html.charters/hubmib-charter.html
                     Mailing Lists:
                       General Discussion: hubmib@ietf.org
                       To Subscribe: hubmib-request@ietf.org
                       In Body: subscribe your_email_address
                       Chair: Dan Romascanu
                       Postal: Avaya
                               Atidim Technology Park, Bldg. 3
                               Tel Aviv 61131
                               Israel
                        Tel: +972-3-645-8414
                        E-mail: dromasca@avaya.com

                     Editor: Lior Khermosh
                     Postal: Passave Technologies Inc.
                             Kohav Hertzelia bldg,
                             4 Hasadnaot St.
                             Hertzliya Pituach 46120,
                             ISRAEL
                     P.O.Box 2089 Hertzliya Pituach 46120 Israel
                     Tel:    +972-9-9628000 Ext: 302
                        E-mail: lior.khermosh@passave.com"
       DESCRIPTION
               "The objects in this MIB module are used to manage the
                Ethernet in the First Mile (EFM) Multi Point Control
                Protocol (MPCP) Interfaces as defined in IEEE P802.3
                clause 64,65.
            The following reference is used throughout this MIB module:
              [802.3] refers to:
                IEEE Draft P802.3: 'Information technology -
                Telecommunications and information exchange between
                systems - Local and metropolitan area networks -
                Specific requirements -
                Part 3: Carrier sense multiple access with collision
                detection (CSMA/CD) access method and physical layer
                specifications - Media Access Control Parameters,
                Physical Layers and Management Parameters for
                subscriber access networks', 8 December 2004.

             Of particular interest are Clause 64(MPCP) 65(P2MP RS) and
             60 (PON PMDs). Clause 30, 'Management', and Clause 45,
             'Management Data Input/Output (MDIO) Interface'.

             Copyright (C) The Internet Society (2005).  This version
             of this MIB module is part of XXXX see the RFC itself for
             full legal notices."

             -- Editor's Note: Replace XXXX with the actual RFC number
             -- assigned by RFC Editor and remove this note

       REVISION    "200503100000Z"  -- March 10, 2005
       DESCRIPTION "Initial version, published as RFC XXXX."

       ::= { mib-2 1 }

       -- Editor's Note: Replace XXX with a real OID once it is
       -- assigned by IANA and remove this note.


   -- Editor-s note: MPCP MIB modules definitions ([802.3]
   --- clause 30.3.5)
   -- Editor-s note: Description in attributes with References should be
   -- minimized in later versions

   dot3MpcpMIB OBJECT IDENTIFIER ::= { dot3EfmeponMIB 1}

   dot3MpcpObjects OBJECT IDENTIFIER ::= { dot3MpcpMIB 1}

   dot3MpcpConformance OBJECT IDENTIFIER ::= { dot3MpcpMIB 2}
   dot3MpcpTable OBJECT-TYPE
       SYNTAX  SEQUENCE OF Dot3MpcpEntry
       MAX-ACCESS  not-accessible
       STATUS  current
       DESCRIPTION
               "Table for dot3 Multi-Point Control Protocol (MPCP)
               MIB modules."
       ::= { dot3MpcpObjects 1 }

   dot3MpcpEntry OBJECT-TYPE
       SYNTAX  Dot3MpcpEntry
       MAX-ACCESS  not-accessible
       STATUS  current
       DESCRIPTION
               "An entry in the dot3 MPCP MIB modules table."
       INDEX  { ifIndex }
       ::= { dot3MpcpTable 1 }

   Dot3MpcpEntry ::=
       SEQUENCE {
           dot3MpcpID                           Integer32,
           dot3MpcpOperStatus                   TruthValue,
           dot3MpcpMode                         INTEGER,
           dot3MpcpLinkID                       Integer32,
           dot3MpcpRemoteMACAddress             MacAddress,
           dot3MpcpRegistrationState            INTEGER,
           dot3MpcpTransmitElapsed              Integer32,
           dot3MpcpReceiveElapsed               Integer32,
           dot3MpcpRoundTripTime                Integer32,
           dot3MpcpMaximumPendingGrants         Integer32,
           dot3MpcpAdminState                   TruthValue,
           dot3MpcpOnTime                       Integer32,
           dot3MpcpOffTime                      Integer32,
           dot3MpcpSyncTime                     Integer32
       }

   dot3MpcpID OBJECT-TYPE
       SYNTAX  Integer32
       MAX-ACCESS  read-only
       STATUS  current
       DESCRIPTION
               "This variable is assigned so as to uniquely identify the
                Multi-Point MAC  Control (MPCP) entity, as defined in
                [802.3] clause 64, among the subordinate managed
                objects of the containing object.
                This attribute is relevant for an OLT and an ONU."
       REFERENCE   "[802.3], 30.3.5.1.1."
       ::= { dot3MpcpEntry 1 }

   dot3MpcpOperStatus OBJECT-TYPE
       SYNTAX  TruthValue
       MAX-ACCESS  read-only
       STATUS  current
       DESCRIPTION
               "This variable can be used to define the operational
                state of the Multi-Point MAC Control sublayer as
                defined in [802.3] clause 64. Selecting admin for an
                interface with Multi-Point MAC Control sublayer. When
                the attribute is True the the interface will act as if
                Multi-point control protocol is enabled. When the
                attribute is False the interface will act as if it does
                not have the Multi-point control protocol. The
                operational state can be changed using the
                dot3MpcpAdminState attribute.
                This attribute is relevant for an OLT and an ONU."
       REFERENCE   "[802.3], 30.3.5.1.2."
       ::= { dot3MpcpEntry 2 }

   dot3MpcpMode  OBJECT-TYPE
       SYNTAX  INTEGER {
               olt(1),
               onu(2)
       }
       MAX-ACCESS  read-only
       STATUS  current
       DESCRIPTION
               "This variable can be used to identify the operational
                state of the Multi-Point MAC Control sublayer as
                defined in [802.3] clause 64. Reading olt(1) for an
                OLT (server) mode and onu(2) for an ONU (client) mode.
                This attribute is relevant for an OLT and an ONU."
       REFERENCE   "[802.3], 30.3.5.1.3."
       DEFVAL { 1 }
       ::= { dot3MpcpEntry 3 }

   dot3MpcpLinkID OBJECT-TYPE
       SYNTAX  Integer32
       MAX-ACCESS  read-only
       STATUS  current
       DESCRIPTION
               "A read-only value that identifies the Logical Link
                identity (LLID) associated with the MAC port as
                specified in [802.3] clause 65.1.3.2.2.
                This attribute is relevant for an OLT and an ONU."
       REFERENCE   "[802.3], 30.3.5.1.4."
       ::= { dot3MpcpEntry 4 }

   dot3MpcpRemoteMACAddress OBJECT-TYPE
       SYNTAX  MacAddress
       MAX-ACCESS  read-only
       STATUS  current
       DESCRIPTION
               "A read-only value that identifies the source_address
                parameter of the last MPCPDUs passed to the MAC Control.
                This value is updated on reception of a valid frame with
                (1) a destination Field equal to the reserved multicast
                address for MAC Control specified in [802.3] Annex
                31A, (2) lengthOrType field value equal to the reserved
                Type for MAC Control as specified in [802.3] Annex
                31A. (3) an MPCP subtype value equal to the subtype
                reserved for MPCP as specified in [802.3] Annex 31A.
                This attribute is relevant for an OLT and an ONU."
       REFERENCE   "[802.3], 30.3.5.1.5."
       ::= { dot3MpcpEntry 5 }

   dot3MpcpRegistrationState OBJECT-TYPE
       SYNTAX  INTEGER {
               unregistered(1),
               registering(2),
               registered(3)
       }
       MAX-ACCESS  read-only
       STATUS  current
       DESCRIPTION
               "A read-only value that identifies the operational state
                of the Multi-Point MAC Control sublayer as defined in
                [802.3] clause 64. When this attribute has the
                enumeration unregistered(1) the interface may be used
                for registering a link partner. When this attribute has
                the enumeration registering(2) the interface is in the
                process of registering a link-partner. When this
                attribute has the enumeration registered(3) the
                interface has an established link-partner.
                This attribute is relevant for an OLT and an ONU. For
                the OLT it provides an indication per LLID."
       REFERENCE   "[802.3], 30.3.5.1.6."
       ::= { dot3MpcpEntry 6 }

   dot3MpcpTransmitElapsed OBJECT-TYPE
       SYNTAX  Integer32
       UNITS       "TQ (16nsec)"
       MAX-ACCESS  read-only
       STATUS  current
       DESCRIPTION
               "A read-only value that reports the interval from last
                MPCP frame transmission in increments of Time Quanta
                (TQ) 16ns. The value returned shall be (interval from
                last MPCP frame transmission in ns)/16. If this value
                exceeds (2^32-1) the value (2^32-1) shall be returned.
                This attribute is relevant for an OLT and an ONU."
       REFERENCE   "[802.3], 30.3.5.1.19."
       ::= { dot3MpcpEntry 7 }

   dot3MpcpReceiveElapsed OBJECT-TYPE
       SYNTAX  Integer32
       UNITS       "TQ (16nsec)"
       MAX-ACCESS  read-only
       STATUS  current
       DESCRIPTION
               "A read-only value that reports the interval from last
                MPCP frame reception in increments of Time Quanta (TQ)
                16ns. The value returned shall be (interval from last
                MPCP last MPCP frame reception in ns)/16. If this value
                exceeds (2^32-1) the value (2^32-1) shall be returned.
                This attribute is relevant for an OLT and an ONU."
       REFERENCE   "[802.3], 30.3.5.1.20."
       ::= { dot3MpcpEntry 8 }

   dot3MpcpRoundTripTime OBJECT-TYPE
       SYNTAX  Integer32
       UNITS       "TQ (16nsec)"
       MAX-ACCESS  read-only
       STATUS  current
       DESCRIPTION
               "A read-only value that reports the MPCP round trip time
                in increments of Time Quanta (TQ) 16ns. The value
                returned shall be (round trip time in ns)/16. If this
                value exceeds (2^16-1) the value (2^16-1)  shall be
                returned. This attribute is relevant for an OLT only.
                For the OLT there is a value per LLID"
       REFERENCE   "[802.3], 30.3.5.1.21."
       ::= { dot3MpcpEntry 9 }

   dot3MpcpMaximumPendingGrants OBJECT-TYPE
       SYNTAX  Integer32 (0..255)
       MAX-ACCESS  read-only
       STATUS  current
       DESCRIPTION
               "A read-only value that indicates the maximum number of
                grants an ONU can store. The maximum number of grants an
                ONU can store has a range of 0 to 255.
                This attribute is relevant for an OLT and an ONU. For
                the OLT there is a value per LLID"

       REFERENCE   "[802.3], 30.3.5.1.24."
       ::= { dot3MpcpEntry 10 }

   dot3MpcpAdminState OBJECT-TYPE
       SYNTAX  TruthValue
       MAX-ACCESS  read-write
       STATUS  current
       DESCRIPTION
               "This variable can be used to define the operational
                state of the Multi-Point MAC Control sublayer as defined
                in [802.3] clause 64. Selecting admin for an interface
                with Multi-Point MAC Control sublayer. When selecting
                the value as True the interface Multi-Point control
                protocol is enabled. When selecting the value as False
                the interface acts as if the Multi-point Control
                protocol does not exist. Reading reflects the state of
                the attribute and the operation of the Multi-point
                control protocol mode of the interface.
                Writing can be done all the time.
                This attribute is relevant for an OLT and an ONU."
       REFERENCE   "[802.3], 30.3.5.2.1."
       DEFVAL { false }
       ::= { dot3MpcpEntry 11 }


   dot3MpcpOnTime OBJECT-TYPE
       SYNTAX  Integer32
       UNITS       "TQ (16nsec)"
       MAX-ACCESS  read-only
       STATUS  current
       DESCRIPTION
               "A read-only value that reports the -on time- for a grant
                burst in increments of Time Quanta (TQ) 16ns as defined
                in [802.3] 60,64. The value returned shall be (on time
                ns)/16. If this value exceeds (2^32-1) the value
                (2^32-1) shall be returned. Value is 32 TQs.
                This attribute is relevant for an OLT and an ONU."
       REFERENCE   "[802.3], 64.3.5.1."
       ::= { dot3MpcpEntry 12 }

   dot3MpcpOffTime OBJECT-TYPE
       SYNTAX  Integer32
       UNITS       "TQ (16nsec)"
       MAX-ACCESS  read-only
       STATUS  current
       DESCRIPTION
               "A read-only value that reports the -off time- for a
                grant burst in increments of Time Quanta (TQ) 16ns as
                defined in [802.3] 60,64. The value returned shall be
                (off time ns)/16. If this value exceeds (2^32-1) the
                value (2^32-1) shall be returned. Value is 32 TQs.
                This attribute is relevant for an OLT and an ONU."
       REFERENCE   "[802.3], 64.3.5.1."
       ::= { dot3MpcpEntry 13 }

   dot3MpcpSyncTime OBJECT-TYPE
       SYNTAX  Integer32
       UNITS       "TQ (16nsec)"
       MAX-ACCESS  read-only
       STATUS  current
       DESCRIPTION
               "A read-only value that reports the -sync lock time- for
                an OLT receiver in increments of Time Quanta (TQ) 16ns
                as defined in [802.3] 60,64,65. The value returned
                shall be (sync lock time ns)/16. If this value exceeds
                (2^32-1) the value (2^32-1) shall be returned.
                This attribute is relevant for an OLT and an ONU."
       REFERENCE   "[802.3], 64.3.3.2."
      ::= { dot3MpcpEntry 14 }



   dot3MpcpStatTable OBJECT-TYPE
       SYNTAX     SEQUENCE OF Dot3MpcpStatEntry
       MAX-ACCESS not-accessible
       STATUS     current
       DESCRIPTION
               "This table defines the list of statistics counters of
                [802.3] clause 64 MPCP interface."
   ::= { dot3MpcpObjects 2 }

   dot3MpcpStatEntry OBJECT-TYPE
       SYNTAX     Dot3MpcpStatEntry
       MAX-ACCESS not-accessible
       STATUS     current
       DESCRIPTION
               "Table entries for table of statistics counters of
                [802.3] clause 64 MPCP interface."
       INDEX       { ifIndex }
       ::= { dot3MpcpStatTable 1 }

   Dot3MpcpStatEntry ::=
       SEQUENCE {
               dot3MpcpMACCtrlFramesTransmitted       Counter32,
               dot3MpcpMACCtrlFramesReceived          Counter32,
               dot3MpcpDiscoveryWindowsSent           Counter32,
               dot3MpcpDiscoveryTimeout               Counter32,
               dot3MpcpTxRegRequest                   Counter32,
               dot3MpcpRxRegRequest                   Counter32,
               dot3MpcpTxRegAck                       Counter32,
               dot3MpcpRxRegAck                       Counter32,
               dot3MpcpTxReport                       Counter32,
               dot3MpcpRxReport                       Counter32,
               dot3MpcpTxGate                         Counter32,
               dot3MpcpRxGate                         Counter32,
               dot3MpcpTxRegister                     Counter32,
               dot3MpcpRxRegister                     Counter32
       }

   dot3MpcpMACCtrlFramesTransmitted OBJECT-TYPE
       SYNTAX  Counter32
       UNITS      "frames"
       MAX-ACCESS  read-only
       STATUS  current
       DESCRIPTION
               "A count of MPCP frames passed to the MAC sublayer for
                transmission. This counter is incremented when a
                MA_CONTROL.request service primitive is generated within
                the MAC control sublayer with an opcode indicating a
                MPCP frame.
                This attribute is relevant for an OLT and an ONU."
       REFERENCE   "[802.3], 30.3.5.1.7."
       ::= { dot3MpcpStatEntry 1 }

   dot3MpcpMACCtrlFramesReceived OBJECT-TYPE
       SYNTAX  Counter32
       UNITS      "frames"
       MAX-ACCESS  read-only
       STATUS  current
       DESCRIPTION
               "A count of MPCP frames passed by the MAC sublayer to the
                MAC Control sublayer. This counter is incremented when a
                ReceiveFrame function call returns a valid frame with:
                (1) a lengthOrType field value equal to the reserved
                Type for 802.3_MAC_Control as specified in 31.4.1.3, and
                (2) an opcode indicating a MPCP frame.
                This attribute is relevant for an OLT and an ONU."
       REFERENCE   "[802.3], 30.3.5.1.8."
       ::= { dot3MpcpStatEntry 2}

   dot3MpcpDiscoveryWindowsSent OBJECT-TYPE
       SYNTAX  Counter32
       MAX-ACCESS  read-only
       STATUS  current
       DESCRIPTION
               "A count of discovery windows generated. The counter is
                incremented by one for each generated discovery window.
                This attribute is relevant for an OLT and an ONU. At the
                ONU value should be zero."
       REFERENCE   "[802.3], 30.3.5.1.22."
       ::= { dot3MpcpStatEntry 3}

   dot3MpcpDiscoveryTimeout OBJECT-TYPE
       SYNTAX  Counter32
       MAX-ACCESS  read-only
       STATUS  current
       DESCRIPTION
               "A count of the number of times a discovery timeout
                occurs. Increment the counter by one for each discovery
                processing state-machine reset resulting from timeout
                waiting for message arrival.
                This attribute is relevant for an OLT and an ONU."
       REFERENCE   "[802.3], 30.3.5.1.23."
       ::= { dot3MpcpStatEntry 4}


   dot3MpcpTxRegRequest OBJECT-TYPE
       SYNTAX  Counter32
       UNITS      "frames"
       MAX-ACCESS  read-only
       STATUS  current
       DESCRIPTION
               "A count of the number of times a REGISTER_REQ MPCP
                frames transmission occurs. Increment the counter by one
                for each REGISTER_REQ MPCP frame transmitted as defined
                in [802.3] clause 64. This counter is mandatory for an
                ONU. This attribute is relevant for an OLT and an ONU.
                At the OLT value should be zero."
       REFERENCE   "[802.3], 30.3.5.1.12."
       ::= { dot3MpcpStatEntry 5}

   dot3MpcpRxRegRequest OBJECT-TYPE
       SYNTAX  Counter32
       UNITS      "frames"
       MAX-ACCESS  read-only
       STATUS  current
       DESCRIPTION
               "A count of the number of times a REGISTER_REQ MPCP
                frames reception occurs. A single counter at the ONU and
                a set of counters, one for each LLID, at the OLT.
                Increment the counter by one for each REGISTER_REQ MPCP
                frame received for each LLID as defined in [802.3]
                clause 64. This counter is mandatory for an ONU and for
                an OLT. At the ONU value should be zero."
       REFERENCE   "[802.3], 30.3.5.1.17."
       ::= { dot3MpcpStatEntry 6}

   dot3MpcpTxRegAck OBJECT-TYPE
       SYNTAX  Counter32
       UNITS      "frames"
       MAX-ACCESS  read-only
       STATUS  current
       DESCRIPTION
               "A count of the number of times a REGISTER_ACK MPCP
                frames transmission occurs. Increment the counter by one
                for each REGISTER_ACK MPCP frame transmitted as defined
                in [802.3] clause 64. This counter is mandatory for an
                ONU. This attribute is relevant for an OLT and an ONU.
                At the OLT the value should be zero."
       REFERENCE   "[802.3], 30.3.5.1.10."
       ::= { dot3MpcpStatEntry 7}

   dot3MpcpRxRegAck OBJECT-TYPE
       SYNTAX  Counter32
       UNITS      "frames"
       MAX-ACCESS  read-only
       STATUS  current
       DESCRIPTION
               "A count of the number of times a REGISTER_ACK MPCP
                frames reception occurs. A single counter at the ONU and
                a set of counters, one for each LLID, at the OLT.
                Increment the counter by one for each REGISTER_ACK MPCP
                frame received for each LLID, as defined in [802.3]
                clause 64. This counter is mandatory for an ONU and for
                an OLT. At the ONU the value should be zero."
       REFERENCE   "[802.3], 30.3.5.1.15."
       ::= { dot3MpcpStatEntry 8}

   dot3MpcpTxReport OBJECT-TYPE
       SYNTAX  Counter32
       UNITS      "frames"
       MAX-ACCESS  read-only
       STATUS  current
       DESCRIPTION
               "A count of the number of times a REPORT MPCP frames
                transmission occurs. Increment the counter by one for
                each REPORT MPCP frame transmitted as defined in
                [802.3] clause 64. This counter is mandatory for an
                ONU. This attribute is relevant for an OLT and an ONU.
                At the OLT value should be zero."

       REFERENCE   "[802.3], 30.3.5.1.13."
       ::= { dot3MpcpStatEntry 9}

   dot3MpcpRxReport OBJECT-TYPE
       SYNTAX  Counter32
       UNITS      "frames"
       MAX-ACCESS  read-only
       STATUS  current
       DESCRIPTION
               "A count of the number of times a REPORT MPCP frames
                reception occurs. A single counter at the ONU and a set
                of counters, one for each LLID, at the OLT. Increment
                the counter by one for each REPORT MPCP frame received
                for each LLID, as defined in [802.3] clause 64.
                This counter is mandatory for an ONU and for an OLT.
                At the ONU value should be zero."
       REFERENCE   "[802.3], 30.3.5.1.18."
       ::= { dot3MpcpStatEntry 10}

   dot3MpcpTxGate OBJECT-TYPE
       SYNTAX  Counter32
       UNITS      "frames"
       MAX-ACCESS  read-only
       STATUS  current
       DESCRIPTION
               "A count of the number of times a GATE MPCP frames
                transmission occurs. A set of counters, one for each
                LLID, at the OLT. Increment the counter by one for each
                GATE MPCP frame transmitted, for each LLID, as defined
                in [802.3] clause 64. This counter is mandatory for an
                OLT. This attribute is relevant for an OLT and an ONU.
                At the ONU the value should be zero."
       REFERENCE   "[802.3], 30.3.5.1.9."
       ::= { dot3MpcpStatEntry 11}

   dot3MpcpRxGate OBJECT-TYPE
       SYNTAX  Counter32
       UNITS      "frames"
       MAX-ACCESS  read-only
       STATUS  current
       DESCRIPTION
               "A count of the number of times a GATE MPCP frames
                reception occurs. A single counter at the ONU and a set
                of counters, one for each LLID ,at the OLT. Increment
                the counter by one for each GATE MPCP frame received,
                for each LLID, as defined in [802.3] clause 64. This
                counter is mandatory for an ONU and for an OLT. At the
                OLT the value should be zero."

       REFERENCE   "[802.3], 30.3.5.1.14."
       ::= { dot3MpcpStatEntry 12}

   dot3MpcpTxRegister OBJECT-TYPE
       SYNTAX  Counter32
       UNITS      "frames"
       MAX-ACCESS  read-only
       STATUS  current
       DESCRIPTION
               "A count of the number of times a REGISTER MPCP frames
                transmission occurs. A set of counters, one for each
                LLID, at the OLT. Increment the counter by one for each
                REGISTER MPCP frame transmitted, for each LLID, as
                defined in [802.3] clause 64. This counter is
                mandatory for an OLT. This attribute is relevant for an
                OLT and an ONU. At the ONU the value should be zero."
       REFERENCE   "[802.3], 30.3.5.1.11."
       ::= { dot3MpcpStatEntry 13}

   dot3MpcpRxRegister OBJECT-TYPE
       SYNTAX  Counter32
       UNITS      "frames"
       MAX-ACCESS  read-only
       STATUS  current
       DESCRIPTION
               "A count of the number of times a REGISTER MPCP frames
                reception occurs. A single counter at the ONU and a set
                of counters, one for each LLID, at the OLT. Increment
                the counter by one for each REGISTER MPCP frame
                received, for each LLID, as defined in [802.3] clause
                64. This counter is mandatory for an ONU and for an OLT.
                at the OLT the value should be zero."
       REFERENCE   "[802.3], 30.3.5.1.16."
       ::= { dot3MpcpStatEntry 14}




        -- Conformance Statements

   -- Conformance Groups

   dot3MpcpGroups      OBJECT IDENTIFIER ::= { dot3MpcpConformance 1 }

   dot3MpcpGroupBase OBJECT-GROUP
       OBJECTS {
               dot3MpcpID,
               dot3MpcpOperStatus,
               dot3MpcpMode,
               dot3MpcpLinkID,
               dot3MpcpRemoteMACAddress,
               dot3MpcpRegistrationState,
               dot3MpcpMaximumPendingGrants,
               dot3MpcpAdminState
       }
       STATUS  current
       DESCRIPTION
               "A collection of objects of dot3 Mpcp Basic entity state
               definition."
       ::= { dot3MpcpGroups 1 }

   dot3MpcpGroupParam OBJECT-GROUP
       OBJECTS {
               dot3MpcpTransmitElapsed,
               dot3MpcpReceiveElapsed,
               dot3MpcpRoundTripTime,
               dot3MpcpOnTime,
               dot3MpcpOffTime,
               dot3MpcpSyncTime
       }
       STATUS  current
       DESCRIPTION
               "A collection of objects of dot3 Mpcp for P2MP
                parameters."
       ::= { dot3MpcpGroups 2 }

   dot3MpcpGroupStat OBJECT-GROUP
       OBJECTS {
               dot3MpcpMACCtrlFramesTransmitted,
               dot3MpcpMACCtrlFramesReceived,
               dot3MpcpDiscoveryWindowsSent,
               dot3MpcpDiscoveryTimeout ,
               dot3MpcpTxRegRequest,
               dot3MpcpRxRegRequest,
               dot3MpcpTxRegAck,
               dot3MpcpRxRegAck,
               dot3MpcpTxReport,
               dot3MpcpRxReport,
               dot3MpcpTxGate,
               dot3MpcpRxGate,
               dot3MpcpTxRegister,
               dot3MpcpRxRegister
       }
       STATUS  current
       DESCRIPTION
               "A collection of objects of dot3 Mpcp Statistics"
       ::= { dot3MpcpGroups 3 }


   -- Compliance

   dot3MpcpCompliances OBJECT IDENTIFIER ::= { dot3MpcpConformance 2 }

   dot3MPCPCompliance MODULE-COMPLIANCE
       STATUS      current
       DESCRIPTION "The compliance statement for Multi-point
                    control protocol interfaces."

       MODULE  -- this module
       MANDATORY-GROUPS { dot3MpcpGroupBase}

      GROUP       dot3MpcpGroupParam
      DESCRIPTION "This group is mandatory for all MPCP supporting
                   interfaces for configuration of the Multipoint
                   Parameters."
      GROUP       dot3MpcpGroupStat
      DESCRIPTION "This group is mandatory for all MPCP supporting
                   interfaces for Statistics collection."
      ::= { dot3MpcpCompliances 1}





   -- Editor-s note:   OMPEmulation managed object definitions

   dot3OmpEmulationMIB OBJECT IDENTIFIER ::= { dot3EfmeponMIB 2}

   dot3OmpEmulationObjects OBJECT IDENTIFIER ::={dot3OmpEmulationMIB 1}

   dot3OmpeConformance OBJECT IDENTIFIER ::= { dot3OmpEmulationMIB 2 }


   dot3OmpEmulationTable OBJECT-TYPE
       SYNTAX  SEQUENCE OF Dot3OmpEmulationEntry
       MAX-ACCESS  not-accessible
       STATUS  current
       DESCRIPTION
               "Table for dot3 OmpEmulation MIB modules."
       ::= { dot3OmpEmulationObjects 1 }

   dot3OmpEmulationEntry OBJECT-TYPE
       SYNTAX  Dot3OmpEmulationEntry
       MAX-ACCESS  not-accessible
       STATUS  current
       DESCRIPTION
               "An entry in the dot3 OmpEmulation MIB modules table."
       INDEX  { ifIndex }
       ::= { dot3OmpEmulationTable 1 }

       Dot3OmpEmulationEntry ::=
       SEQUENCE {
               dot3OmpEmulationID            Integer32,
               dot3OmpEmulationType               INTEGER
       }

   dot3OmpEmulationID OBJECT-TYPE
       SYNTAX  Integer32
       MAX-ACCESS  read-only
       STATUS  current
       DESCRIPTION
               "The value of dot3OmpEmulationID is assigned so as to
                uniquely identify a OMPEmulation entity among the
                subordinate managed objects of the containing object.
                The value is mandated for an ONU."
       REFERENCE   "[802.3], 30.3.7.1.1."
       ::= { dot3OmpEmulationEntry 1}

   dot3OmpEmulationType OBJECT-TYPE
       SYNTAX  INTEGER {
               unknown(1),
               olt(2),
               onu(3)
       }
       MAX-ACCESS  read-only
       STATUS  current
       DESCRIPTION
               "A read-only value that indicates that mode of operation
                of the Reconciliation Sublayer for Point to Point
                Emulation (see [802.3] clause 65.1). unknown(1) value
                is assigned in initializing, true state or type not yet
                known. olt(2) value is assigned when Sublayer operating
                in OLT mode. onu(3) value is assigned when Sublayer
                operating in ONU mode."
       REFERENCE   "[802.3], 30.3.7.1.2."
       ::= { dot3OmpEmulationEntry 2}

   dot3OmpEmulationStatTable OBJECT-TYPE
       SYNTAX     SEQUENCE OF Dot3OmpEmulationStatEntry
       MAX-ACCESS not-accessible
       STATUS     current
       DESCRIPTION
               "This table defines the list of statistics counters of
                [802.3] clause 65 OMP interface."
       ::= { dot3OmpEmulationObjects 2}

   dot3OmpEmulationStatEntry OBJECT-TYPE
       SYNTAX     Dot3OmpEmulationStatEntry
       MAX-ACCESS not-accessible
       STATUS     current
       DESCRIPTION
               "Table entries for Table of statistics counters of
                [802.3] clause 65 OMP interface."
       INDEX       { ifIndex }
       ::= { dot3OmpEmulationStatTable 1 }

   Dot3OmpEmulationStatEntry::=
       SEQUENCE {
               dot3OmpEmulationSLDErrors                 Counter32,
               dot3OmpEmulationCRC8Errors                Counter32,
               dot3OmpEmulationBadLLID                   Counter32,
               dot3OmpEmulationGoodLLID                  Counter32,
               dot3OmpEmulationOnuPonCastLLID            Counter32,
               dot3OmpEmulationOltPonCastLLID            Counter32,
               dot3OmpEmulationBroadcastBitNotOnuLlid     Counter32,
               dot3OmpEmulationOnuLLIDNotBroadcast       Counter32,
               dot3OmpEmulationBroadcastBitPlusOnuLlid    Counter32,
               dot3OmpEmulationNotBroadcastBitNotOnuLlid  Counter32
       }

   dot3OmpEmulationSLDErrors OBJECT-TYPE
       SYNTAX  Counter32
       UNITS      "frames"
       MAX-ACCESS  read-only
       STATUS  current
       DESCRIPTION
               "A count of frames received that do not contain a valid
                SLD field as defined in [802.3] clause 65.1.3.3.1.
                This attribute is mandatory for an OLT and for an ONU."
       REFERENCE   "[802.3], 30.3.7.1.3."
       ::= { dot3OmpEmulationStatEntry 1}

   dot3OmpEmulationCRC8Errors OBJECT-TYPE
       SYNTAX  Counter32
       UNITS      "frames"
       MAX-ACCESS  read-only
       STATUS  current
       DESCRIPTION
               "A count of frames received that contain a valid SLD
                field, as defined in [802.3] clause 65.1.3.3.1, but do
                not pass the CRC-8 check as defined in [802.3] clause
                65.1.3.3.3. This attribute is mandatory for an OLT and
                for an ONU."
       REFERENCE   "[802.3], 30.3.7.1.4."
       ::= { dot3OmpEmulationStatEntry 2}


   dot3OmpEmulationBadLLID OBJECT-TYPE
       SYNTAX  Counter32
       UNITS      "frames"
       MAX-ACCESS  read-only
       STATUS  current
       DESCRIPTION
               "A count of frames received that contain a valid SLD
                field, as defined in [802.3] clause 65.1.3.3.1, and
                pass the CRC-8 check, as defined in [802.3] clause
                65.1.3.3.3, but are discarded due to the LLID check as
                defined in [802.3] clause 65.1.3.3.2.
                This attribute is relevant for an OLT and an ONU."
       REFERENCE   "[802.3], 30.3.7.1.8."
       ::= { dot3OmpEmulationStatEntry 3}

   dot3OmpEmulationGoodLLID OBJECT-TYPE
       SYNTAX  Counter32
       UNITS      "frames"
       MAX-ACCESS  read-only
       STATUS  current
       DESCRIPTION
               "A count of frames received that contain a valid SLD
                field, as defined in [802.3] clause 65.1.3.3.1, and
                pass the CRC-8 check, as defined in [802.3] clause
                65.1.3.3.3.
                This attribute is relevant for an OLT and an ONU."
       REFERENCE   "[802.3], 30.3.7.1.5."
       ::= { dot3OmpEmulationStatEntry 4}


   dot3OmpEmulationOnuPonCastLLID OBJECT-TYPE
       SYNTAX  Counter32
       UNITS      "frames"
       MAX-ACCESS  read-only
       STATUS  current
       DESCRIPTION
               "A count of frames received that contain a valid SLD
                field in an ONU, as defined in [802.3] 65.1.3.3.1,
                passes the CRC-8 check, as defined in [802.3]
                65.1.3.3.3, and the frame meets the rule for acceptance
                defined in [802.3] 65.1.3.3.2."

       REFERENCE   "[802.3], 30.3.7.1.6."
       ::= { dot3OmpEmulationStatEntry 5}

   dot3OmpEmulationOltPonCastLLID OBJECT-TYPE
       SYNTAX  Counter32
       UNITS      "frames"
       MAX-ACCESS  read-only
       STATUS  current
       DESCRIPTION
               "A count of frames received that contain a valid SLD
                field in an OLT, as defined in [802.3] 65.1.3.3.1,
                passes the CRC-8 check, as defined in [802.3]
                65.1.3.3.3, and the frame meets the rule for acceptance
                defined in [802.3] 65.1.3.3.2."
       REFERENCE   "[802.3], 30.3.7.1.7."
       ::= { dot3OmpEmulationStatEntry 6}

   dot3OmpEmulationBroadcastBitNotOnuLlid OBJECT-TYPE
       SYNTAX  Counter32
       UNITS      "frames"
       MAX-ACCESS  read-only
       STATUS  current
       DESCRIPTION
               "A count of frames received that contain a valid SLD
                field in a OLT, as defined in [802.3] clause
                65.1.3.3.1, and pass the CRC-8 check, as defined in
                [802.3] clause 65.1.3.3.3, and contain broadcast bit
                in LLID and not the ONU's LLID (frame accepted) as
                defined in [802.3] clause 65 .
                This attribute is mandatory for an OLT and for an ONU."
       ::= { dot3OmpEmulationStatEntry 7}

   dot3OmpEmulationOnuLLIDNotBroadcast OBJECT-TYPE
       SYNTAX  Counter32
       UNITS      "frames"
       MAX-ACCESS  read-only
       STATUS  current
       DESCRIPTION
               "A count of frames received that contain a valid SLD
                field in a OLT, as defined in [802.3] clause
                65.1.3.3.1, and pass the CRC-8 check, as defined in
                [802.3] clause 65.1.3.3.3, and contain the ONU's LLID
                as defined in [802.3] clause 65. This attribute is
                mandatory for an ONU and mandatory for an OLT (a
                counter per LLID)."
       ::= { dot3OmpEmulationStatEntry 8}

   dot3OmpEmulationBroadcastBitPlusOnuLlid OBJECT-TYPE
       SYNTAX  Counter32
       UNITS      "frames"
       MAX-ACCESS  read-only
       STATUS  current
       DESCRIPTION
               "A count of frames received that contain a valid SLD
                field in a OLT, as defined in [802.3] clause
                65.1.3.3.1, and pass the CRC-8 check, as defined in
                [802.3] clause 65.1.3.3.3, and contain the broadcast
                bit in LLID and the ONU's LLID (frame reflected) as
                defined in [802.3] clause 65. This attribute is
                mandatory for an ONU and mandatory for an OLT (a
                counter per LLID)."
       ::= { dot3OmpEmulationStatEntry 9}

   dot3OmpEmulationNotBroadcastBitNotOnuLlid OBJECT-TYPE
       SYNTAX  Counter32
       UNITS      "frames"
       MAX-ACCESS  read-only
       STATUS  current
       DESCRIPTION
               "A count of frames received that contain a valid SLD
                field in a OLT, as defined in [802.3] clause
                65.1.3.3.1, and pass the CRC-8 check, as defined in
                [802.3] clause 65.1.3.3.3, and and does not contain
                the ONU's LLID as defined in [802.3] clause 65.
                This attribute is mandatory for an ONU"
       ::= { dot3OmpEmulationStatEntry 10}



        -- Conformance Statements

   -- Conformance Groups

   dot3OmpeGroups OBJECT IDENTIFIER ::={ dot3OmpeConformance 1}


   dot3OmpeGroupID OBJECT-GROUP
       OBJECTS {
               dot3OmpEmulationID,
               dot3OmpEmulationType

       }
       STATUS  current
       DESCRIPTION
               "A collection of objects of dot3 OMP emulation ID entity
                state definition."
       ::= { dot3OmpeGroups 1 }


   dot3OmpeGroupStat OBJECT-GROUP
       OBJECTS {
               dot3OmpEmulationSLDErrors,
               dot3OmpEmulationCRC8Errors,
               dot3OmpEmulationBadLLID,
               dot3OmpEmulationGoodLLID,
               dot3OmpEmulationOnuPonCastLLID,
               dot3OmpEmulationOltPonCastLLID,
               dot3OmpEmulationBroadcastBitNotOnuLlid,
               dot3OmpEmulationOnuLLIDNotBroadcast,
               dot3OmpEmulationBroadcastBitPlusOnuLlid,
               dot3OmpEmulationNotBroadcastBitNotOnuLlid
       }
       STATUS  current
       DESCRIPTION
               "A collection of objects of dot3 OMP emulation
                Statistics"
       ::= { dot3OmpeGroups 2 }


   -- Compliance

   dot3OmpeCompliances OBJECT IDENTIFIER ::= { dot3OmpeConformance 2 }

   dot3OmpeCompliance MODULE-COMPLIANCE
       STATUS      current
       DESCRIPTION "The compliance statement for OMPEmulation
                    interfaces."

       MODULE  -- this module
       MANDATORY-GROUPS { dot3OmpeGroupID}

       GROUP       dot3OmpeGroupStat
       DESCRIPTION "This group is mandatory for all OMPemulation
                    supporting interfaces for Statistics collection."

       ::= { dot3OmpeCompliances 1}




   -- Editor-s note:   MAU managed object definitions (30.5.1)

   dot3EponMauMIB OBJECT IDENTIFIER ::= { dot3EfmeponMIB 3}
   dot3EponMauObjects OBJECT IDENTIFIER ::= { dot3EponMauMIB 1}

   dot3EponMauConformance OBJECT IDENTIFIER ::= { dot3EponMauMIB 2 }

   dot3EponMauTable OBJECT-TYPE
       SYNTAX  SEQUENCE OF Dot3EponMauEntry
       MAX-ACCESS  not-accessible
       STATUS  current
       DESCRIPTION
               "Table for dot3 MAU EPON MIB modules."
       ::= { dot3EponMauObjects 1 }

   dot3EponMauEntry OBJECT-TYPE
       SYNTAX  Dot3EponMauEntry
       MAX-ACCESS  not-accessible
       STATUS  current
       DESCRIPTION
               "An entry in the dot3 MAU EPON MIB modules table."
       INDEX  { ifIndex }
       ::= { dot3EponMauTable 1 }

   Dot3EponMauEntry ::=
       SEQUENCE {
               dot3EponMauPCSCodingViolation           Counter32,
               dot3EponMauFecAbility                   INTEGER,
               dot3EponMauFecMode                      INTEGER,
               dot3EponMauFECCorrectedBlocks           Counter32,
               dot3EponMauFECUncorrectableBlocks       Counter32,
               dot3EponMauBufferHeadCodingViolation    Counter32
       }


   dot3EponMauPCSCodingViolation OBJECT-TYPE
       SYNTAX  Counter32
       UNITS      "octets"
       MAX-ACCESS  read-only
       STATUS  current
       DESCRIPTION
               "For 100 Mb/ s operation it is a count of the number of
                times an invalid code-group is received, other than the
                /H/ code-group. For 1000 Mb/ s operation it is a count
                of the number of times an invalid codegroup is received,
                other than the /V/ code-group."
       REFERENCE   "[802.3], 30.5.1.1.12."
       ::= { dot3EponMauEntry 1}

   dot3EponMauFecAbility OBJECT-TYPE
       SYNTAX  INTEGER {
               unknown (1),
               nonsupported (2),
               supported (3)
       }
       MAX-ACCESS  read-only
       STATUS  current
       DESCRIPTION
               "A read-only value that indicates the support of
                operation of the 1000BASE-PX PHY optional FEC Sublayer
                for Forward error correction see [802.3] clause 65.2).
                unknown(1) value is assigned in initializing, for non
                FEC support state or type not yet known. nonsupported(2)
                value is assigned when Sublayer is not support.
                supported(3) value is assigned when Sublayer is
                supported."
       REFERENCE   "[802.3], 30.5.1.1.13."
       ::= { dot3EponMauEntry 2}

   dot3EponMauFecMode OBJECT-TYPE
       SYNTAX  INTEGER {
               unknown (1),
               disabled (2),
               enabled (3)
       }
       MAX-ACCESS  read-write
       STATUS  current
       DESCRIPTION
               "A read-write value that indicates the mode of operation
                of the 1000BASE-PX PHY optional FEC Sublayer for Forward
                error correction see [802.3] clause 65.2).
                A GET operation returns the current mode of operation
                the PHY. A SET operation changes the mode of operation
                of the PHY to the indicated value. unknown(1) value is
                assigned in initializing, for non FEC support state or
                type not yet known. disabled(2) value is assigned when
                Sublayer operating in disabled mode. enabled(3) value is
                assigned when Sublayer operating in FEC mode. writing
                can be done all the time."
       REFERENCE   "[802.3], 30.5.1.1.14."
       DEFVAL { 1 }
       ::= { dot3EponMauEntry 3}

   dot3EponMauFECCorrectedBlocks OBJECT-TYPE
       SYNTAX  Counter32
       MAX-ACCESS  read-only
       STATUS  current
       DESCRIPTION
               "For 10PASS-TS, 2BASE-TL and 1000BASE-PX PHYs, a count
                of corrected FEC blocks. This counter will not increment
                for other PHY Types. Increment the counter by one for
                each received block that is corrected by the FEC
                function in the PHY."
       REFERENCE   "[802.3], 30.5.1.1.15."
       ::= { dot3EponMauEntry 4}

   dot3EponMauFECUncorrectableBlocks OBJECT-TYPE
       SYNTAX  Counter32
       MAX-ACCESS  read-only
       STATUS  current
       DESCRIPTION
               "For 10PASS-TS, 2BASE-TL and 1000BASE-PX PHYs, a count of
                uncorrectable FEC blocks. This counter will not
                increment for other PHY Types. Increment the counter by
                one for each FEC block that is determined to be
                uncorrectable by the FEC function in the PHY."
       REFERENCE   "[802.3], 30.5.1.1.16."
       ::= { dot3EponMauEntry 5}

   dot3EponMauBufferHeadCodingViolation OBJECT-TYPE
       SYNTAX  Counter32
       UNITS      "octets"
       MAX-ACCESS  read-only
       STATUS  current
       DESCRIPTION
               "For 1000 Mbps operation it is a counts of the number of
                invalid code-group received directly from the link."
       ::= { dot3EponMauEntry 6}


        -- Conformance Statements

   -- Conformance Groups

   dot3EponMauGroups OBJECT IDENTIFIER ::={ dot3EponMauConformance 1}

   dot3EponMauGroupAll OBJECT-GROUP
       OBJECTS {
               dot3EponMauPCSCodingViolation
       }
       STATUS  current
       DESCRIPTION
               "A collection of objects of dot3 MAU definition."
       ::= { dot3EponMauGroups 1 }

   dot3EponMauGroupFEC OBJECT-GROUP
       OBJECTS {
               dot3EponMauFecAbility,
               dot3EponMauFecMode,
               dot3EponMauFECCorrectedBlocks,
               dot3EponMauFECUncorrectableBlocks,
               dot3EponMauBufferHeadCodingViolation
       }
       STATUS  current
       DESCRIPTION
               "A collection of objects of FEC group definition."
       ::= { dot3EponMauGroups 2 }


   -- Compliance

   dot3EponMauCompliances OBJECT IDENTIFIER::={dot3EponMauConformance 2}

   dot3EponMauCompliance MODULE-COMPLIANCE
       STATUS      current
       DESCRIPTION "The compliance statement for MAU EPON interfaces."

       MODULE  -- this module
       MANDATORY-GROUPS { dot3EponMauGroupAll }

       GROUP       dot3EponMauGroupFEC
       DESCRIPTION "This group is mandatory for all EPON MAU devices
                    Supporting FEC functionality as for Definitions and
                    BER Statistics collection."

       ::= { dot3EponMauCompliances 1}


   END

-- 
--    Copyright (C) The Internet Society (2005).  This document is subject
--    to the rights, licenses and restrictions contained in BCP 78, and
--    except as set forth therein, the authors retain all their rights.
-- Acknowledgment
-- 
--    Funding for the RFC Editor function is currently provided by the
--    Internet Society.
