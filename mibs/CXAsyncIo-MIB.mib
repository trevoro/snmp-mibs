CXAsyncIo-MIB DEFINITIONS ::= BEGIN


IMPORTS
    Counter                         FROM RFC1155-SMI
    OBJECT-TYPE                     FROM RFC-1212
    TRAP-TYPE                       FROM RFC-1215
    cxAsyncIo,
    Alias                           FROM CXProduct-SMI;


--  Active Configuration Table

--  The table describing:
--  active (current) parameters used in each Async Driver SAP and its 
--  associated hardware port. 
--  
--  parameters required to configure traps at Async Driver SAPs for 
--  their associated hardware port.
--
--  status and statistics for each hardware port that is associated 
--  with an Async Driver SAP.


asioSapOprTable OBJECT-TYPE
    SYNTAX  SEQUENCE OF AsioSapOprEntry
    ACCESS  not-accessible
    STATUS  mandatory
    DESCRIPTION
"Contains configuration information about each Async driver SAP (service 
access point) and its associated hardware port."

    ::= { cxAsyncIo 1 }


    asioSapOprEntry OBJECT-TYPE
        SYNTAX  AsioSapOprEntry
        ACCESS  not-accessible
        STATUS  mandatory
        DESCRIPTION
"Contains configuration information for a specific Async driver SAP (service 
access point) and its associated hardware port."

        INDEX { asioSapOprNumber }
        ::= { asioSapOprTable 1 }


    AsioSapOprEntry ::=
        SEQUENCE {
            asioSapOprNumber
                INTEGER,
            asioSapOprAlias
                Alias,
            asioSapOprPortSpeed
                INTEGER,
            asioSapOprPortCharacterSize
                INTEGER,
            asioSapOprPortStopBits
                INTEGER,
            asioSapOprPortBreakLength
                INTEGER,
            asioSapOprPortMaxQueueLength
                INTEGER,
            asioSapOprPortQueueUpperThreshold
                INTEGER,
            asioSapOprPortQueueLowerThreshold
                INTEGER,
            asioSapOprPortSignalDownTimer
                INTEGER,
            asioSapOprPortMaxTimeDelay
                INTEGER,
            asioSapOprPortMaxInterruptCharacters
                INTEGER,
            asioSapOprPortSignalSamplingPeriod
                INTEGER,
            asioSapOprPortDcdDtrSignalSamples
                INTEGER,
            asioSapOprPortCtsRtsSignalSamples
                INTEGER,
            asioSapOprPortDsrDrsSignalSamples
                INTEGER,
            asioSapOprPortTmLlSignalSamples
                INTEGER,
            asioSapOprPortRiRlSignalSamples
                INTEGER,
            asioSapOprPortStatisticsTimer
                INTEGER,
            asioSapOprPortCarrierAction
                INTEGER,
            asioOprPortTrap
                INTEGER,
            asioOprControlLine
                INTEGER,
            asioOprControlStats
                INTEGER,
            asioStatOprPortType
                INTEGER,
            asioStatOprPortInterfaceType
                INTEGER,
            asioStatOprPortState
                INTEGER,
            asioStatOprDCDState
                INTEGER,
            asioStatOprDTRState
                INTEGER,
            asioStatOprRTSState
                INTEGER,
            asioStatOprCTSState
                INTEGER,
            asioStatOprDSRState
                INTEGER,
            asioStatOprDRSState
                INTEGER,
            asioStatOprTMState
                INTEGER,
            asioStatOprLLState
                INTEGER,
            asioStatOprRIState
                INTEGER,
            asioStatOprRLState
                INTEGER,
            asioStatOprTxBps
                Counter,
            asioStatOprRxBps
                Counter,
            asioStatOprTxBpsMax
                Counter,
            asioStatOprRxBpsMax
                Counter,
            asioStatOprTxCharacters
                Counter,
            asioStatOprTxBadStateDiscards
                Counter,
            asioStatOprTxResetDiscards
                Counter,
            asioStatOprTxSysCongestionDiscards
                Counter,
            asioStatOprRxCharacters
                Counter,
            asioStatOprRxOverrunErrorCharacters
                Counter,
            asioStatOprRxParityErrorCharacters
                Counter,
            asioStatOprRxFramingErrorCharacters
                Counter,
            asioStatOprRxNoiseErrorCharacters
                Counter,
            asioStatOprRxBreakCharacters
                Counter,
            asioStatOprRxBadStateDiscards
                Counter,
            asioStatOprRxBusyDiscards
                Counter,
            asioStatOprPortStateChanges
                Counter,
            asioStatOprDCDStateChanges
                Counter,
            asioStatOprDTRStateChanges
                Counter,
            asioStatOprRTSStateChanges
                Counter,
            asioStatOprCTSStateChanges
                Counter,
            asioStatOprDSRStateChanges
                Counter,
            asioStatOprDRSStateChanges
                Counter,
            asioStatOprTMStateChanges
                Counter,
            asioStatOprLLStateChanges
                Counter,
            asioStatOprRIStateChanges
                Counter,
            asioStatOprRLStateChanges
                Counter,
            asioStatOprPortResets
                Counter
            }


    asioSapOprNumber OBJECT-TYPE
        SYNTAX  INTEGER
        ACCESS  read-only
        STATUS  mandatory
        DESCRIPTION
"Indicates the table row containing configuration or monitoring objects for a
SAP (service access point) associated with the slot and port for this card. 

Range of Values: 11 - 71

Note: First digit indicates the slot and the second digit indicates the port.

Default Value: none"
        ::= { asioSapOprEntry 1 }


    asioSapOprAlias OBJECT-TYPE
        SYNTAX  Alias
        ACCESS  read-only
        STATUS  mandatory
        DESCRIPTION
"Determines the name which uniquely identifies the SAP (service access 
point).

Range of Values: 1 to 16 alphanumeric characters starting with an alpha 
character

Default Value: none

Configuration Changed: Administrative "

        ::= { asioSapOprEntry 2 }


    asioSapOprPortSpeed OBJECT-TYPE
        SYNTAX  INTEGER (50 .. 115200)
        ACCESS  read-only
        STATUS  mandatory
        DESCRIPTION
"Defines the input and output speed, in bits per second, for the associated 
hardware port. 
Any value between 50 and 115200 will be accepted.

Note: 134.5 bit/s is the minimum speed supported on ports in slots 5, 6 and 7 when 
the Data Expansion Module is installed.

Default Value: 9600 bit/s"
        ::= { asioSapOprEntry 3 }


    asioSapOprPortCharacterSize OBJECT-TYPE
        SYNTAX  INTEGER (5 .. 8)
        ACCESS  read-only
        STATUS  mandatory
        DESCRIPTION
"Defines the character size, in number of bits, to be used on the associated 
hardware port. 

Options: 
5,6, 7 or 8

Note: This value does not include the start, stop or parity bits."
        ::= { asioSapOprEntry 5 }


    asioSapOprPortStopBits OBJECT-TYPE
        SYNTAX  INTEGER {
                    one             (1),
                    one-point-five  (2),
                    two             (3)
                    }
        ACCESS  read-only
        STATUS  mandatory
        DESCRIPTION
"Defines the number of stop bits to be used on the associated hardware 
port.

Options:  
one (1 bit)

one-point-five (1.5 bits)

two (2 bits)

Default Value: 1 bit"
        ::= { asioSapOprEntry 6 }


    asioSapOprPortBreakLength OBJECT-TYPE
        SYNTAX  INTEGER (0 .. 65535)
        ACCESS  read-only
        STATUS  mandatory
        DESCRIPTION
"Defines the number of break characters to be transmitted on the line when a 
reset is requested by the upper layer. 

A break is an all-zeroes character without a stop bit(s).

Range of Values: 0 - 65535

Default Value: 10"
        ::= { asioSapOprEntry 7 
}


    asioSapOprPortMaxQueueLength OBJECT-TYPE
        SYNTAX  INTEGER (1 .. 100)
        ACCESS  read-write
        STATUS  mandatory
        DESCRIPTION
"Defines the maximum transmitter queue length, in number of buffers. 

If more data requests are received from the upper layer after the queue has 
reached its maximum value, the data is discarded and the object 
asyStatOprTxSysCongestionDiscards is incremented. 

You must be careful when updating this object dynamically because queued data 
can be lost if the size of the transmitter queue is decreased.

Range of Values: 1 - 100

Default Value: 50

Configuration Changed: Operative only "
        ::= { asioSapOprEntry 8 }


    asioSapOprPortQueueUpperThreshold OBJECT-TYPE
        SYNTAX  INTEGER (1 .. 100)
        ACCESS  read-write
        STATUS  mandatory
        DESCRIPTION
"Defines the queue length, in number of buffers, after which the Async driver 
starts flow controlling the upper layer. 

After the queue has reached this length, the Async driver will queue more 
data requests on the transmit queue up to the length specified in object 
asySapOprPortMaxQueueLength. Data is discarded above that length. 

The value for this object should always be less than the value of object 
asySapOprPortMaxQueueLength 

Range of Values: 1 - 100

Default Value: 45

Configuration Changed: Operative only "
        ::= { asioSapOprEntry 9 }


    asioSapOprPortQueueLowerThreshold OBJECT-TYPE
        SYNTAX  INTEGER (1 .. 100)
        ACCESS  read-write
        STATUS  mandatory
        DESCRIPTION
"Defines the queue length, in number of buffers, after which the Async driver 
stops flow controlling the upper layer. 

The value for this object should always be less than or equal to the value of 
object asySapOprPortQueueUpperThreshold.

Range of Values: 1 - 100

Default Value: 15

Configuration Changed: Operative only "

        ::= { asioSapOprEntry 10 }


    asioSapOprPortSignalDownTimer OBJECT-TYPE
        SYNTAX  INTEGER (0 .. 255)
        ACCESS  read-only
        STATUS  mandatory
        DESCRIPTION
"Defines the length of time, in seconds, after which the Async port will drop 
its signals when it has received a disconnect request from the upper layer.

Range of Values: 0 - 255

Default Value: 3"
        ::= { asioSapOprEntry 11 }


    asioSapOprPortMaxTimeDelay OBJECT-TYPE
        SYNTAX  INTEGER (1 .. 5)
        ACCESS  read-only
        STATUS  mandatory
        DESCRIPTION
"Defines the maximum time, in milliseconds, the port must wait before 
processing received characters.

Range of Values: 1 - 5

Default Value: 5"
        ::= { asioSapOprEntry 12 }


    asioSapOprPortMaxInterruptCharacters OBJECT-TYPE
        SYNTAX  INTEGER (5 .. 40)
        ACCESS  read-write
        STATUS  obsolete
        DESCRIPTION
"Obsolete."
        ::= { asioSapOprEntry 13 }


-- gap (6) for future parameters


    asioSapOprPortSignalSamplingPeriod OBJECT-TYPE
        SYNTAX  INTEGER (3..100)
        ACCESS  read-write
        STATUS  mandatory
        DESCRIPTION
"Determines the sampling period, in 100 millisecond increments, that the 
associated hardware port uses to sample detectable signals.

Range of Values: 3 - 100

Default Value: 5

Configuration Changed: Operative only "
        ::= { asioSapOprEntry 20 }


    asioSapOprPortDcdDtrSignalSamples OBJECT-TYPE
        SYNTAX  INTEGER (1..30)
        ACCESS  read-write
        STATUS  mandatory
        DESCRIPTION
"Defines the number of samples of object asySapPortSignalSamplingPeriod that 
the associated hardware port must detect before validating the DCD 
(Data Carrier Detect) signals if the port is physically strapped as a DTE, 
or DTR (Data Terminal Ready) signals if the port is strapped as a DCE.

Range of Values: 1 - 30

Default Value: 3

Configuration Changed: Operative only "
        ::= { asioSapOprEntry 21 }


    asioSapOprPortCtsRtsSignalSamples OBJECT-TYPE
        SYNTAX  INTEGER (1..30)
        ACCESS  read-write
        STATUS  mandatory
        DESCRIPTION
"Defines the number of samples of object asySapPortSignalSamplingPeriod that 
the associated hardware port must detect before validating the 
CTS (Clear To Send) signals if the port is physically strapped as a DTE, 
or RTS (Request To Send) signals if the port is strapped as a DCE.

Range of Values: 1 - 30

Default Value: 3

Configuration Changed: Operative only "
        ::= { asioSapOprEntry 22 }


    asioSapOprPortDsrDrsSignalSamples OBJECT-TYPE
        SYNTAX  INTEGER (1..30)
        ACCESS  read-write
        STATUS  mandatory
        DESCRIPTION
"Defines the number of samples of object asySapPortSignalSamplingPeriod that 
the associated hardware port must detect before validating the DRS (Data Rate 
Selector) signals if the port is physically strapped as a DTE, 
or DSR (Data Set Ready) signals if the port is strapped as a DCE.

Range of Values: 1 - 30

Default Value: 3

Configuration Changed: Operative only "
        ::= { asioSapOprEntry 23 }


    asioSapOprPortTmLlSignalSamples OBJECT-TYPE
        SYNTAX  INTEGER (1..30)
        ACCESS  read-write
        STATUS  mandatory
        DESCRIPTION
"Defines the number of samples of object asySapPortSignalSamplingPeriod that 
the associated hardware port must detect before validating the TM (Test Mode) 
signals if the port is physically strapped as a DTE, or LL (Local Loopback) 
signals if the port is strapped as a DCE.

Range of Values: 1 - 30

Default Value: 3

Configuration Changed: Operative only "
        ::= { asioSapOprEntry 24 }


    asioSapOprPortRiRlSignalSamples OBJECT-TYPE
        SYNTAX  INTEGER (1..30)
        ACCESS  read-write
        STATUS  mandatory
        DESCRIPTION
"Defines the number of samples of object asySapPortSignalSamplingPeriod that 
the associated hardware port must detect before validating the 
RI (Ring Indicator)signals if the port is physically strapped as a DTE, 
RL (Remote Loopback) signals if the port is strapped as a DCE.

Range of Values: 1 - 30

Default Value: 3

Configuration Changed: Operative only "
        ::= { asioSapOprEntry 25 }


    asioSapOprPortStatisticsTimer OBJECT-TYPE
        SYNTAX  INTEGER (0..60)
        ACCESS  read-only
        STATUS  mandatory
        DESCRIPTION
"Determines the period of time, in seconds, that is used to measure Async 
driver performance and collect statistics. 

Range of Values: 0 - 60.

Default Value: 0 

(Performance  statistics are not measured)"

        ::= { asioSapOprEntry 26 }


    asioSapOprPortCarrierAction OBJECT-TYPE
        SYNTAX  INTEGER {
                    disabled        (1),
                    enabled         (2)
                    }
        ACCESS  read-write
        STATUS  mandatory
        DESCRIPTION
"Determines whether or not this SAP (service access point) will inform the 
associated upper layer SAP that service is no longer available because its 
associated hardware port has detected a loss of DCD (Data Carrier Detect) if 
the port is physically strapped as a DTE, or a loss of DTR (Data Terminal 
Ready) if the port is physically strapped as a DCE.

Options: 
disabled (1)

enabled (2)

Default Value: disabled

Configuration Changed: Operative only "
        ::= { asioSapOprEntry 27 }


-- gap (2) for future parameters


    asioOprPortTrap OBJECT-TYPE
        SYNTAX  INTEGER {
                    disabled        (1),
                    enabled         (2)
                    }
        ACCESS  read-write
        STATUS  mandatory
        DESCRIPTION
"Indicates whether or not this SAP (service access point) produces the object 
asyPortStatusChange trap.

Options: 
disabled (1)

enabled (2)

Default Value: disabled

Configuration Changed: Operative only "
        ::= { asioSapOprEntry 30 }


-- gap (3) for future traps


    asioOprControlLine OBJECT-TYPE
        SYNTAX  INTEGER {
                    forceDown       (1),
                    forceUp         (2),
                    forceReset      (3)
                    }
        ACCESS  write-only
        STATUS  mandatory
        DESCRIPTION
"Controls the state of the hardware port associated with the specified SAP 
(service access point).

Options:
forceDown (1)

forceUp (2)

forceReset (3)


Configuration Changed: Operative only "
        ::= { asioSapOprEntry 34 }


    asioOprControlStats OBJECT-TYPE
        SYNTAX  INTEGER {
                    clearSapStats   (1)
                    }
        ACCESS  write-only
        STATUS  mandatory
        DESCRIPTION
"Controls the handling of statistics collected at the associated hardware 
port.

Option: clearSAPStats (1)

Configuration Changed: Operative only "
        ::= { asioSapOprEntry 35 }


-- gap (2) for future write-only commands


    asioStatOprPortType OBJECT-TYPE
        SYNTAX  INTEGER {
                    unknown         (1),
                    dte             (2),
                    dce             (3)
                    }
        ACCESS  read-only
        STATUS  mandatory
        DESCRIPTION
"Identifies the hardware strapping used at the associated hardware 
port.

Options:
unknown (1)

dte (2)

dce (3)"

        ::= { asioSapOprEntry 38 }


    asioStatOprPortInterfaceType OBJECT-TYPE
        SYNTAX  INTEGER {
                    unknown         (1),
                    rs232d          (2)
                    }
        ACCESS  read-only
        STATUS  mandatory
        DESCRIPTION
"Identifies the type of hardware interface needed for the associated hardware 
port.

Options:
unknown (1)

rs232d"
        ::= { asioSapOprEntry 39 }


    asioStatOprPortState OBJECT-TYPE
        SYNTAX  INTEGER {
                    portUp                          (1),
                    portDown                        (2),
                    portShutDown                    (3),
                    portDownBadConfiguration        (4),
                    portOutOfOrder                  (5)
                    }
        ACCESS  read-only
        STATUS  mandatory
        DESCRIPTION
"Indicates the state of the associated hardware 
port.

Options:
portUp (1)

portDown (2)

portShutDown (3)

portDownBadConfiguration (4)

portOutOfOrder (5)"

        ::= { asioSapOprEntry 40 }


-- gap (4) for future states


    asioStatOprDCDState OBJECT-TYPE
        SYNTAX  INTEGER {
                    unknown         (1),
                    inactive        (2),
                    active          (3)
                    }
        ACCESS  read-only
        STATUS  mandatory
        DESCRIPTION
"Indicates the current state (active- high or active-low) of the DCD (Data 
Carrier Detect) signal at the associated hardware port. 

Options:
unknown (1)

inactive (2)

active (3)"

        ::= { asioSapOprEntry 45 }


    asioStatOprDTRState OBJECT-TYPE
        SYNTAX  INTEGER {
                    unknown         (1),
                    inactive        (2),
                    active          (3)
                    }
        ACCESS  read-only
        STATUS  mandatory
        DESCRIPTION
"Indicates the current state (active- high or active-low) of the DTR (Data 
Terminal Ready) signal at the associated hardware port. 

Options:
unknown (1)

inactive (2)

active (3)"

        ::= { asioSapOprEntry 46 }


    asioStatOprRTSState OBJECT-TYPE
        SYNTAX  INTEGER {
                    unknown         (1),
                    inactive        (2),
                    active          (3)
                    }
        ACCESS  read-only
        STATUS  mandatory
        DESCRIPTION
"Indicates the current state (active- high or active-low) of the RTS (Request 
To Send) signal at the associated hardware port. 

Options:
unknown (1)

inactive (2)

active (3)"
        ::= { asioSapOprEntry 47 }


    asioStatOprCTSState OBJECT-TYPE
        SYNTAX  INTEGER {
                    unknown         (1),
                    inactive        (2),
                    active          (3)
                    }
        ACCESS  read-only
        STATUS  mandatory
        DESCRIPTION
"Indicates the current state (active- high or active-low) of the CTS (Clear 
To Send) signal at the associated hardware port. 

Options:
unknown (1)

inactive (2)

active (3)"

        ::= { asioSapOprEntry 48 }


    asioStatOprDSRState OBJECT-TYPE
        SYNTAX  INTEGER {
                    unknown         (1),
                    inactive        (2),
                    active          (3)
                    }
        ACCESS  read-only
        STATUS  mandatory
        DESCRIPTION
"Indicates the current state (active- high or active-low) of the DSR (Data 
Set Ready) signal at the associated hardware port.

Options:
unknown (1)

inactive (2)

active (3)"
        ::= { asioSapOprEntry 49 }


    asioStatOprDRSState OBJECT-TYPE
        SYNTAX  INTEGER {
                    unknown         (1),
                    inactive        (2),
                    active          (3)
                    }
        ACCESS  read-only
        STATUS  mandatory
        DESCRIPTION
"Indicates the current state (active- high or active-low) of the DRS (Data 
Rate Selection) signal at the associated hardware port.

Options:

unknown (1)

inactive (2)

active (3)"
        ::= { asioSapOprEntry 50 }


    asioStatOprTMState OBJECT-TYPE
        SYNTAX  INTEGER {
                    unknown         (1),
                    inactive        (2),
                    active          (3)
                    }
        ACCESS  read-only
        STATUS  mandatory
        DESCRIPTION
"Indicates the current state (active- high or active-low) of the TM (Test 
Mode) signal at the associated hardware port.

Options:

unknown (1)

inactive (2)

active (3)"
        ::= { asioSapOprEntry 51 }


    asioStatOprLLState OBJECT-TYPE
        SYNTAX  INTEGER {
                    unknown         (1),
                    inactive        (2),
                    active          (3)
                    }
        ACCESS  read-only
        STATUS  mandatory
        DESCRIPTION
"Indicates the current state (active- high or active-low) of the LL (Local 
Loopback) signal at the associated hardware port.

Options:

unknown (1)

inactive (2)

active (3)"
        ::= { asioSapOprEntry 52 }


    asioStatOprRIState OBJECT-TYPE
        SYNTAX  INTEGER {
                    unknown         (1),
                    inactive        (2),
                    active          (3)
                    }
        ACCESS  read-only
        STATUS  mandatory
        DESCRIPTION
"Indicates the current state (active- high or active-low) of the RI (Ring 
Indicator) signal at the associated hardware port.

Options:
unknown (1)

inactive (2)

active (3)"
        ::= { asioSapOprEntry 53 }


    asioStatOprRLState OBJECT-TYPE
        SYNTAX  INTEGER {
                    unknown         (1),
                    inactive        (2),
                    active          (3)
                    }
        ACCESS  read-only
        STATUS  mandatory
        DESCRIPTION
"Indicates the current state (active- high or active-low) of the RL (Remote 
Loopback) signal at the associated hardware port.

Options:

unknown (1)

inactive (2)

active (3)"
        ::= { asioSapOprEntry 54 }


-- gap (4) for future states


    asioStatOprTxBps OBJECT-TYPE
        SYNTAX   Counter
        ACCESS   read-only
        STATUS   mandatory
        DESCRIPTION
"Indicates the number of bits per second that were transmitted during the 
sampling period entered in object asySapAdmPortStatisticsTimer."
        ::= { asioSapOprEntry 59 }


    asioStatOprRxBps OBJECT-TYPE
        SYNTAX   Counter
        ACCESS   read-only
        STATUS   mandatory
        DESCRIPTION
"Indicates the number of bits per second that were received during the 
sampling period entered in object asySapAdmPortStatisticsTimer."
        ::= { asioSapOprEntry 60 }


    asioStatOprTxBpsMax OBJECT-TYPE
        SYNTAX   Counter
        ACCESS   read-only
        STATUS   mandatory
        DESCRIPTION
"Indicates the maximum number of bits per second transmitted, since the 
statistics were last reset, during the sampling period entered in object 
asySapAdmPortStatisticsTimer."
        ::= { asioSapOprEntry 61 }


    asioStatOprRxBpsMax OBJECT-TYPE
        SYNTAX   Counter
        ACCESS   read-only
        STATUS   mandatory
        DESCRIPTION
"Indicates the maximum number of bits per second received, since the 
statistics were last reset, during the sampling period entered in object 
asySapAdmPortStatisticsTimer."

        ::= { asioSapOprEntry 62 }


    asioStatOprTxCharacters OBJECT-TYPE
        SYNTAX   Counter
        ACCESS   read-only
        STATUS   mandatory
        DESCRIPTION
"Indicates the number of characters transmitted from this port, since the 
statistics were last reset, during the sampling period entered in object
 asySapAdmPortStatisticsTimer."
        ::= { asioSapOprEntry 63 }


    asioStatOprTxBadStateDiscards OBJECT-TYPE
        SYNTAX  Counter
        ACCESS  read-only
        STATUS  mandatory
        DESCRIPTION
"Indicates the number of characters that were discarded at this SAP (service 
access point) since the last power-up. The characters were discarded as a 
result of a frame transmission requested while the port was in an invalid 
state, during the sampling period entered in object 
asySapAdmPortStatisticsTimer."
        ::= { asioSapOprEntry 64 }


    asioStatOprTxResetDiscards OBJECT-TYPE
        SYNTAX  Counter
        ACCESS  read-only
        STATUS  mandatory
        DESCRIPTION
"Indicates the number of characters that were discarded at this SAP (service 
access point) since the last power-up as a result of a management requested 
line reset during the sampling period entered in object 
asySapAdmPortStatisticsTimer."
        ::= { asioSapOprEntry 65 }


    asioStatOprTxSysCongestionDiscards OBJECT-TYPE
        SYNTAX  Counter
        ACCESS  read-only
        STATUS  mandatory
        DESCRIPTION
"Indicates the number of characters that were discarded at this SAP (service 
 access point) since the last power-up as a result of system congestion, 
 during the sampling period entered in object  
asySapAdmPortStatisticsTimer."
        ::= { asioSapOprEntry 66 }


-- gap (5) for future transmit type statistics


    asioStatOprRxCharacters OBJECT-TYPE
        SYNTAX   Counter
        ACCESS   read-only
        STATUS   mandatory
        DESCRIPTION
"Indicates the number of characters that were received through this port 
since the statistics were last reset, during the sampling period entered in 
object asySapAdmPortStatisticsTimer."
        ::= { asioSapOprEntry 72 
}


    asioStatOprRxOverrunErrorCharacters OBJECT-TYPE
        SYNTAX  Counter
        ACCESS  read-only
        STATUS  mandatory
        DESCRIPTION
"Indicates the number of overrun error characters that were received by the 
 associated hardware port since the last power-up, during the sampling period 
 entered in object asySapAdmPortStatisticsTimer."

        ::= { asioSapOprEntry 73 }


    asioStatOprRxParityErrorCharacters OBJECT-TYPE
        SYNTAX  Counter
        ACCESS  read-only
        STATUS  mandatory
        DESCRIPTION
"Indicates the number of parity error characters that were received by the 
 associated hardware port since the last power-up, during the sampling period 
 entered in object asySapAdmPortStatisticsTimer."

        ::= { asioSapOprEntry 74 }


    asioStatOprRxFramingErrorCharacters OBJECT-TYPE
        SYNTAX  Counter
        ACCESS  read-only
        STATUS  mandatory
        DESCRIPTION
"Indicates the number of framing error characters that were received by the 
 associated hardware port since the last power-up, during the sampling period 
 entered in object asySapAdmPortStatisticsTimer."
        ::= { asioSapOprEntry 75 
}


    asioStatOprRxNoiseErrorCharacters OBJECT-TYPE
        SYNTAX  Counter
        ACCESS  read-only
        STATUS  mandatory
        DESCRIPTION
"Indicates the number of noise error characters that were received by the 
 associated hardware port since the last power-up, during the sampling period 
 entered in object asySapAdmPortStatisticsTimer."
        ::= { asioSapOprEntry 76 
}


    asioStatOprRxBreakCharacters OBJECT-TYPE
        SYNTAX  Counter
        ACCESS  read-only
        STATUS  mandatory
        DESCRIPTION
"Indicates the number of break characters that were received by the  
associated hardware port since the last power-up, during the sampling period 
entered in object asySapAdmPortStatisticsTimer."
        ::= { asioSapOprEntry 77 }


    asioStatOprRxBadStateDiscards OBJECT-TYPE
        SYNTAX  Counter
        ACCESS  read-only
        STATUS  mandatory
        DESCRIPTION
"Indicates the number of characters that were discarded at this SAP (service 
access point) since the last power-up.  They were discarded as a result of a 
frame reception while in an invalid state, during the sampling period entered 
in object asySapAdmPortStatisticsTimer."
        ::= { asioSapOprEntry 78 
}


    asioStatOprRxBusyDiscards OBJECT-TYPE
        SYNTAX  Counter
        ACCESS  read-only
        STATUS  mandatory
        DESCRIPTION
"Indicates the number of characters that were discarded at this SAP (service 
access point) since the last power-up.  They were discarded as a result of a 
busy condition, during the sampling period entered in object  
asySapAdmPortStatisticsTimer.

Note: The busy condition occurs as a result of a slow response to data 
reception."

        ::= { asioSapOprEntry 79 }


-- gap (5) for future receive type statistics


    asioStatOprPortStateChanges OBJECT-TYPE
        SYNTAX  Counter
        ACCESS  read-only
        STATUS  mandatory
        DESCRIPTION
"Indicates the number of state transitions that have occurred at the 
associated hardware port since the last power-up, during the sampling period 
 entered in object asySapAdmPortStatisticsTimer.

Note: One state transition is defined as a change between any of the states defined 
 in object asyStatOprPortState."
        ::= { asioSapOprEntry 85 
}


    asioStatOprDCDStateChanges OBJECT-TYPE
        SYNTAX  Counter
        ACCESS  read-only
        STATUS  mandatory
        DESCRIPTION
"Indicates the number of DCD (Data Carrier Detect) state transitions that 
have occurred at the associated hardware port since the last power-up, during 
the sampling period entered in object asySapAdmPortStatisticsTimer.

Note: One state transition is defined as a change from inactive to active, or vice- 
versa."

        ::= { asioSapOprEntry 86 }


    asioStatOprDTRStateChanges OBJECT-TYPE
        SYNTAX  Counter
        ACCESS  read-only
        STATUS  mandatory
        DESCRIPTION
"Indicates the number of DTR (Data Terminal Ready) state transitions that 
have occurred at the associated hardware port since the last power-up, during 
the sampling period entered in object asySapAdmPortStatisticsTimer.

Note: One state transition is defined as a change from inactive to active, or vice- 
versa."
        ::= { asioSapOprEntry 87 }


    asioStatOprRTSStateChanges OBJECT-TYPE
        SYNTAX  Counter
        ACCESS  read-only
        STATUS  mandatory
        DESCRIPTION
"Indicates the number of RTS (Request To Send) state transitions that have 
occurred at the associated hardware port since the last power-up, during the 
sampling period entered in object asySapAdmPortStatisticsTimer.

Note: One state transition is defined as a change from inactive to active, or vice- 
versa."
        ::= { asioSapOprEntry 88 }


    asioStatOprCTSStateChanges OBJECT-TYPE
        SYNTAX  Counter
        ACCESS  read-only
        STATUS  mandatory
        DESCRIPTION
"Indicates the number of CTS (Clear To Send) state transitions that have 
occurred at the associated hardware port since the last power-up, during the 
sampling period entered in object asySapAdmPortStatisticsTimer.

Note: One state transition is defined as a change from inactive to active, or vice 
versa."
        ::= { asioSapOprEntry 89 }


    asioStatOprDSRStateChanges OBJECT-TYPE
        SYNTAX  Counter
        ACCESS  read-only
        STATUS  mandatory
        DESCRIPTION
"Indicates the number of DSR (Data Set Ready) state transitions that have 
occurred at the associated hardware port since the last power-up, during the 
sampling period entered in object asySapAdmPortStatisticsTimer.

Note: One state transition is defined as a change from inactive to active, or vice- 
versa."
        ::= { asioSapOprEntry 90 }


    asioStatOprDRSStateChanges OBJECT-TYPE
        SYNTAX  Counter
        ACCESS  read-only
        STATUS  mandatory
        DESCRIPTION
"Indicates the number of DRS (Data Rate Selector) state transitions that have 
occurred at the associated hardware port since the last power-up, during the 
sampling period entered in object asySapAdmPortStatisticsTimer.

Note: One state transition is defined as a change from inactive to active, or vice- 
versa."
        ::= { asioSapOprEntry 91 }


    asioStatOprTMStateChanges OBJECT-TYPE
        SYNTAX  Counter
        ACCESS  read-only
        STATUS  mandatory
        DESCRIPTION
"Indicates the number of TM (Test Mode) state transitions that have occurred 
at the associated hardware port since the last power-up, during the sampling 
period entered in object asySapAdmPortStatisticsTimer.

Note: One state transition is defined as a change from inactive to active, or vice- 
versa."
        ::= { asioSapOprEntry 92 }


    asioStatOprLLStateChanges OBJECT-TYPE
        SYNTAX  Counter
        ACCESS  read-only
        STATUS  mandatory
        DESCRIPTION
"Indicates the number of LL (Local Loopback) state transitions that have 
occurred at the associated hardware port since the last power-up, during the 
sampling period entered in object asySapAdmPortStatisticsTimer.

Note: One state transition is defined as a change from inactive to active, or vice- 
versa."
        ::= { asioSapOprEntry 93 }


    asioStatOprRIStateChanges OBJECT-TYPE
        SYNTAX  Counter
        ACCESS  read-only
        STATUS  mandatory
        DESCRIPTION
"Indicates the number of RI (Ring Indicator) state transitions that have 
occurred at the associated hardware port since the last power-up, during the 
sampling period entered in object asySapAdmPortStatisticsTimer.

Note: One state transition is defined as a change from inactive to active, or vice- 
versa."
        ::= { asioSapOprEntry 94 }


    asioStatOprRLStateChanges OBJECT-TYPE
        SYNTAX  Counter
        ACCESS  read-only
        STATUS  mandatory
        DESCRIPTION
"Indicates the number of RL (Remote Loopback) state transitions that have 
occurred at the associated hardware port since the last power-up, during the 
sampling period entered in object asySapAdmPortStatisticsTimer.

Note: One state transition is defined as a change from inactive to active, or vice- 
versa."
        ::= { asioSapOprEntry 95 }


    asioStatOprPortResets OBJECT-TYPE
        SYNTAX  Counter
        ACCESS  read-only
        STATUS  mandatory
        DESCRIPTION
"Indicates the number of port resets that have occurred at the associated 
hardware port since the last power-up, during the sampling period entered in 
object asySapAdmPortStatisticsTimer."
        ::= { asioSapOprEntry 96 }

--  Planned Configuration and Control Table

--  The table describing:
--      parameters used to configure each Async driver SAP and its 
--      associated hardware port.
--
--      parameters required to configure traps at Async driver SAPs for 
--      their associated hardware port.
--
--      parameters used to effect specific and immediate actions at each 
--      hardware port associated with an Async driver SAP.


asioSapAdmTable OBJECT-TYPE
    SYNTAX  SEQUENCE OF AsioSapAdmEntry
    ACCESS  not-accessible
    STATUS  mandatory
    DESCRIPTION
"Contains the planned configuration information for each Async driver SAP 
(service access point) and its associated hardware port."
    ::= { cxAsyncIo 2 }


    asioSapAdmEntry OBJECT-TYPE
        SYNTAX  AsioSapAdmEntry
        ACCESS  not-accessible
        STATUS  mandatory
        DESCRIPTION
"Contains the planned configuration information for a specific Async driver 
SAP (service access point) and its associated hardware port."
        INDEX { asioSapAdmNumber }
        ::= { asioSapAdmTable 1 }


    AsioSapAdmEntry ::=
        SEQUENCE {
            asioSapAdmNumber
                INTEGER,
            asioSapAdmAlias
                Alias,
            asioSapAdmPortSpeed
                INTEGER,
            asioSapAdmPortCharacterSize
                INTEGER,
            asioSapAdmPortStopBits
                INTEGER,
            asioSapAdmPortBreakLength
                INTEGER,
            asioSapAdmPortMaxQueueLength
                INTEGER,
            asioSapAdmPortQueueUpperThreshold
                INTEGER,
            asioSapAdmPortQueueLowerThreshold
                INTEGER,
            asioSapAdmPortSignalDownTimer
                INTEGER,
            asioSapAdmPortMaxTimeDelay
                INTEGER,
            asioSapAdmPortMaxInterruptCharacters
                INTEGER,
            asioSapAdmPortSignalSamplingPeriod
                INTEGER,
            asioSapAdmPortDcdDtrSignalSamples
                INTEGER,
            asioSapAdmPortCtsRtsSignalSamples
                INTEGER,
            asioSapAdmPortDsrDrsSignalSamples
                INTEGER,
            asioSapAdmPortTmLlSignalSamples
                INTEGER,
            asioSapAdmPortRiRlSignalSamples
                INTEGER,
            asioSapAdmPortStatisticsTimer
                INTEGER,
            asioSapAdmPortCarrierAction
                INTEGER,
            asioAdmPortTrap
                INTEGER
               }

    asioSapAdmNumber OBJECT-TYPE
        SYNTAX  INTEGER
        ACCESS  read-only
        STATUS  mandatory
        DESCRIPTION
"Indicates the table row containing configuration or monitoring objects for a 
 SAP (service access point) associated with the slot and a port for this card. 

Range of Values: 11 - 71

Note: First digit indicates the slot and the second digit indicates the port.

Default Value: None"
        ::= { asioSapAdmEntry 1 }


    asioSapAdmAlias OBJECT-TYPE
        SYNTAX  Alias
        ACCESS  read-write
        STATUS  mandatory
        DESCRIPTION
"Determines the name which uniquely identifies the SAP (service access 
point).

Range of Values: 1 to 16 alphanumeric characters beginning with an alpha
character

Default Value: none

Configuration Changed: Administrative "
        ::= { asioSapAdmEntry 2 }


    asioSapAdmPortSpeed OBJECT-TYPE
        SYNTAX  INTEGER (50 .. 115200)
        ACCESS  read-write
        STATUS  mandatory
        DESCRIPTION
"Defines the input and output speed, in bits per second, for the associated 
hardware port.

Any value between 50 and 115200 will be accepted.

Note: 134.5 bit/s is the minimum speed supported on ports in slots 5, 6 and 7
when the Data Expansion Module is installed.

Default Value: 9600 bit/s

Configuration Changed: Administrative "


        DEFVAL { 9600 }
        ::= { asioSapAdmEntry 3 }


    asioSapAdmPortCharacterSize OBJECT-TYPE
        SYNTAX  INTEGER (5 .. 8)
        ACCESS  read-write
        STATUS  mandatory
        DESCRIPTION
"Defines the character size, in number of bits, to be used on the associated 
hardware port. 

Options: 5, 6, 7 or 8

Note: This value does not include the start, stop or parity bits.

Default Value: 8

Configuration Changed: Administrative "
        DEFVAL { 8 }
        ::= { asioSapAdmEntry 5 }


    asioSapAdmPortStopBits OBJECT-TYPE
        SYNTAX  INTEGER {
                    one             (1),
                    one-point-five  (2),
                    two             (3)
                    }
        ACCESS  read-write
        STATUS  mandatory
        DESCRIPTION
"Defines the number of stop bits to be used on the associated hardware port.

Options:  
one (1 bit)

one-point-five (1.5 bits)

two (2 bits)

Default Value: 1 bit

Configuration Changed: Administrative "
        DEFVAL { one }
        ::= { asioSapAdmEntry 6 }


    asioSapAdmPortBreakLength OBJECT-TYPE
        SYNTAX  INTEGER (0 .. 65535)
        ACCESS  read-write
        STATUS  mandatory
        DESCRIPTION
"Defines the number of break characters to be transmitted on the line when a 
reset is requested by the upper layer. 

A break is an all-zeroes character without a stop bit(s).

Range of Values: 0 - 65535

Default Value: 3

Configuration Changed: Administrative "
        DEFVAL { 10 }
        ::= { asioSapAdmEntry 7 }


    asioSapAdmPortMaxQueueLength OBJECT-TYPE
        SYNTAX  INTEGER (1 .. 100)
        ACCESS  read-write
        STATUS  mandatory
        DESCRIPTION
"Defines the maximum transmitter queue length, in number of buffers. 

If more data requests are received from the upper layer after the queue has 
reached its maximum value, the data is discarded and the object 
asyStatOprTxSysCongestionDiscards is incremented. 

You must be careful when updating this object dynamically because queued data 
can be lost if the size of the transmitter queue is decreased.

Range of Values: 1 - 100

Default Value: 50

Configuration Changed: Administrative "
        DEFVAL { 50 }
        ::= { asioSapAdmEntry 8 }


    asioSapAdmPortQueueUpperThreshold OBJECT-TYPE
        SYNTAX  INTEGER (1 .. 100)
        ACCESS  read-write
        STATUS  mandatory
        DESCRIPTION
"Defines the queue length, in number of buffers, after which the Async driver 
starts flow controlling the upper layer. 

After the queue has reached this length, the Async driver will queue more 
data requests on the transmit queue up to the length specified in object 
 asySapOprPortMaxQueueLength. Data is discarded above that length. 

The value for this object should always be less than or equal to the value of 
object asySapOprPortMaxQueueLength 

Range of Values: 1 - 100

Default Value: 45

Configuration Changed: Administrative "
        DEFVAL { 45 }
        ::= { asioSapAdmEntry 9 }


    asioSapAdmPortQueueLowerThreshold OBJECT-TYPE
        SYNTAX  INTEGER (1 .. 100)
        ACCESS  read-write
        STATUS  mandatory
        DESCRIPTION
"Defines the queue length, in number of buffers, after which the Async driver 
stops flow controlling the upper layer. 

The value for this object should always be less than or equal to the value of 
object asySapOprPortQueueUpperThreshold.

Range of Values: 1 - 100

Default Value: 15

Configuration Changed: Administrative "
        DEFVAL { 15 }
        ::= { asioSapAdmEntry 10 }


    asioSapAdmPortSignalDownTimer OBJECT-TYPE
        SYNTAX  INTEGER (0 .. 255)
        ACCESS  read-write
        STATUS  mandatory
        DESCRIPTION
"Defines the length of time, in seconds, after which the Async port will drop 
its signals when it has received a disconnect request from the upper layer.

Range of Values: 0 - 255

Default Value: 3

Configuration Changed: Administrative "
        DEFVAL { 3 }
        ::= { asioSapAdmEntry 11 }


    asioSapAdmPortMaxTimeDelay OBJECT-TYPE
        SYNTAX  INTEGER (1 .. 5)
        ACCESS  read-write
        STATUS  mandatory
        DESCRIPTION
"Defines the maximum time, in milliseconds, the port must wait before 
processing received characters.

Range of Values: 1 - 5

Default Value: 5

Configuration Changed: Administrative "
        DEFVAL { 5 }
        ::= { asioSapAdmEntry 12 }


    asioSapAdmPortMaxInterruptCharacters OBJECT-TYPE
        SYNTAX  INTEGER (5 .. 40)
        ACCESS  read-write
        STATUS  obsolete
        DESCRIPTION
"Obsolete."

        DEFVAL { 8 }
        ::= { asioSapAdmEntry 13 }


-- gap (6) for future parameters


    asioSapAdmPortSignalSamplingPeriod OBJECT-TYPE
        SYNTAX  INTEGER (3..100)
        ACCESS  read-write
        STATUS  mandatory
        DESCRIPTION
"Determines the sampling period, in 100 millisecond increments, that the 
associated hardware port uses to sample detectable signals.

Range of Values: 3 - 100

Default Value: 5

Configuration Changed: Administrative "
        DEFVAL { 5 }
        ::= { asioSapAdmEntry 20 }


    asioSapAdmPortDcdDtrSignalSamples OBJECT-TYPE
        SYNTAX  INTEGER (1..30)
        ACCESS  read-write
        STATUS  mandatory
        DESCRIPTION
"Defines the number of samples of object asySapPortSignalSamplingPeriod that 
the associated hardware port must detect before validating the DCD (Data 
Carrier Detect) signals if the port is physically strapped as a DTE, or DTR 
(Data Terminal Ready) signals if the port is strapped as a DCE.

Range of Values: 1 - 30

Default Value: 3

Configuration Changed: Administrative "
        DEFVAL { 3 }
        ::= { asioSapAdmEntry 21 }


    asioSapAdmPortCtsRtsSignalSamples OBJECT-TYPE
        SYNTAX  INTEGER (1..30)
        ACCESS  read-write
        STATUS  mandatory
        DESCRIPTION
"Defines the number of samples of object asySapPortSignalSamplingPeriod that 
the associated hardware port must detect before validating the CTS (Clear To 
Send) signals if the port is physically strapped as a DTE, or RTS (Request To 
Send) signals if the port is strapped as a DCE. 


Range of Values: 1 - 30

Default Value: 3

Configuration Changed: Administrative "
        DEFVAL { 3 }
        ::= { asioSapAdmEntry 22 }


    asioSapAdmPortDsrDrsSignalSamples OBJECT-TYPE
        SYNTAX  INTEGER (1..30)
        ACCESS  read-write
        STATUS  mandatory
        DESCRIPTION
"Defines the number of samples of object asySapPortSignalSamplingPeriod that 
the associated hardware port must detect before validating the DRS (Data Rate 
Selector) signals if the port is physically strapped as a DTE, or DSR (Data 
Set Ready) signals if the port is strapped as a DCE.

Range of Values: 1 - 30

Default Value: 3

Configuration Changed: Administrative "
        DEFVAL { 3 }
        ::= { asioSapAdmEntry 23 }


    asioSapAdmPortTmLlSignalSamples OBJECT-TYPE
        SYNTAX  INTEGER (1..30)
        ACCESS  read-write
        STATUS  mandatory
        DESCRIPTION
"Defines the number of samples of object asySapPortSignalSamplingPeriod that 
the associated hardware port must detect before validating the TM (Test Mode) 
signals if the port is physically strapped as a DTE, or LL (Local Loopback) 
signals if the port is strapped as a DCE.

Range of Values: 1 - 30

Default Value: 3

Configuration Changed: Administrative "
        DEFVAL { 3 }
        ::= { asioSapAdmEntry 24 }


    asioSapAdmPortRiRlSignalSamples OBJECT-TYPE
        SYNTAX  INTEGER (1..30)
        ACCESS  read-write
        STATUS  mandatory
        DESCRIPTION
"Defines the number of samples of object asySapPortSignalSamplingPeriod that 
the associated hardware port must detect before validating the RI (Ring 
Indicator)signals if the port is physically strapped as a DTE, RL (Remote  
Loopback) signals if the port is strapped as a DCE.

Range of Values: 1 - 30

Default Value: 3

Configuration Changed: Administrative "
        DEFVAL { 3 }
        ::= { asioSapAdmEntry 25 }


    asioSapAdmPortStatisticsTimer OBJECT-TYPE
        SYNTAX  INTEGER (0..60)
        ACCESS  read-write
        STATUS  mandatory
        DESCRIPTION
"Determines the period of time, in seconds, that is used to measure Async 
driver performance and collect statistics. 

Range of Values: 0 - 60.

Default Value: 0 = Performance 
statistics are not measured"
        DEFVAL { 0 }
        ::= { asioSapAdmEntry 26 }


    asioSapAdmPortCarrierAction OBJECT-TYPE
        SYNTAX  INTEGER {
                    disabled        (1),
                    enabled         (2)
                    }
        ACCESS  read-write
        STATUS  mandatory
        DESCRIPTION
"Determines whether or not this SAP (service access point) will inform the 
associated upper layer SAP that service is no longer available because its 
associated hardware port has detected a loss of DCD (Data Carrier Detect) if 
the port is physically strapped as a DTE, or a loss of DTR (Data Terminal 
Ready) if the port is physically strapped as a DCE.

Options: 
disabled (1)

enabled (2)

Default Value: enabled

Configuration Changed: Administrative "
        DEFVAL { enabled }
        ::= { asioSapAdmEntry 27 }


-- gap (2) for future parameters


    asioAdmPortTrap OBJECT-TYPE
        SYNTAX  INTEGER {
                    disabled        (1),
                    enabled         (2)
                    }
        ACCESS  read-write
        STATUS  mandatory
        DESCRIPTION
"Indicates whether on not this SAP (service access point) produces the 
asyPortStatusChange trap.

Options: 
disabled (1)

enabled (2)

Default Value: disabled

Configuration Changed: Administrative "
        DEFVAL { disabled }
        ::= { asioSapAdmEntry 30 }


-- Service access point related traps


asioPortStatusChange TRAP-TYPE
    ENTERPRISE      cxAsyncIo
    VARIABLES       {       asioSapOprNumber,
                asioStatOprPortState
            }
    DESCRIPTION
"Indicates that the associated hardware port has changed state. It has 
toggled between any of the states as defined in object asyStatOprPortState."
    ::= 1


END
