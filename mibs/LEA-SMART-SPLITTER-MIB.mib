LEA-SMART-SPLITTER-MIB DEFINITIONS ::= BEGIN

IMPORTS
    MODULE-IDENTITY, OBJECT-TYPE, Integer32 FROM SNMPv2-SMI
    SnmpAdminString                         FROM SNMP-FRAMEWORK-MIB
    leaSplitters                            FROM LEA-MIB;


leaSmartSplitter MODULE-IDENTITY
        LAST-UPDATED "200210040000Z"
        ORGANIZATION "www.leacom.fr"
        CONTACT-INFO
                "postal:   Regis Urvoy
                        52/54 rue du capitaine Guynemer
                        92415 Courbevoie Cedex
                        France

                email:    regis.urvoy@leacom.fr"
        DESCRIPTION
                "LEA Smart Splitter Management Information Base"
        REVISION     "200209260000Z"
        DESCRIPTION
                "Beta 1"
        ::= { leaSplitters 1 }

--
-- top level structure
--
splitterRelay       OBJECT IDENTIFIER ::= { leaSmartSplitter 1 }

relayActiveDuration OBJECT-TYPE
    SYNTAX      INTEGER (1..300)
    MAX-ACCESS  read-write
    STATUS      current
    DESCRIPTION 
      "Duration that a bypass relay is active in seconds. As a fail-safe
      mechanism, the relay will automatically return a line back to normal
      operational mode when this timer has expired. The same relay timer value
      will be used for every port."
    DEFVAL { 60 }
    ::= { splitterRelay 1 }

numberOfActiveRelays OBJECT-TYPE
    SYNTAX      INTEGER(1..15)
    MAX-ACCESS  read-only
    STATUS      current
    DESCRIPTION
      "Total count of active relays. The agent controls the number of active
      relays so that the maximum is not exceeded in order to keep power
      consumption down."
    DEFVAL { 0 }
    ::= { splitterRelay 2 }

heartBeat OBJECT-TYPE
    SYNTAX      INTEGER { ack (1) }
    MAX-ACCESS  read-only
    STATUS      current
    DESCRIPTION
	"This parameter returns a simply acknowledge following a request from
        the manager. "
    DEFVAL { 1 }
    ::= { splitterRelay 3 }

relayTable OBJECT-TYPE
    SYNTAX      SEQUENCE OF RelayTableEntry
    MAX-ACCESS  not-accessible
    STATUS      current
    DESCRIPTION
	"Table of relay status"
    ::= { splitterRelay 4 }

relayTableEntry OBJECT-TYPE
    SYNTAX      RelayTableEntry
    MAX-ACCESS  not-accessible
    STATUS      current
    DESCRIPTION
	"A row describing a relay status"
    INDEX   { relayIndex }
    ::= { relayTable 1 }

RelayTableEntry ::= SEQUENCE {
	relayIndex	Integer32,
        relaySlot	INTEGER,
        relayPort	INTEGER,
	relayStatus	INTEGER
}

relayIndex OBJECT-TYPE
    SYNTAX      Integer32
    MAX-ACCESS  not-accessible
    STATUS      current
    DESCRIPTION
	"The index of the table. Its value is (relaySlot-1)*24+relayPort"
    ::= { relayTableEntry 1 }

relaySlot OBJECT-TYPE
    SYNTAX      INTEGER {
    			slot-1 (1),
    			slot-2 (2),
    			slot-3 (3),
    			slot-4 (4),
    			slot-5 (5),
    			slot-6 (6),
    			slot-7 (7),
    			slot-8 (8),
    			slot-9 (9),
    			slot-10 (10),
    			slot-11 (11),
    			slot-12 (12),
    			slot-13 (13),
    			slot-14 (14),
    			slot-15 (15)
       		}
    MAX-ACCESS  read-only
    STATUS      current
    DESCRIPTION
	"The slot being addressed"
    ::= { relayTableEntry 2 }

relayPort OBJECT-TYPE
    SYNTAX      INTEGER {
    			port-1 (1),
    			port-2 (2),
    			port-3 (3),
    			port-4 (4),
    			port-5 (5),
    			port-6 (6),
    			port-7 (7),
    			port-8 (8),
    			port-9 (9),
    			port-10 (10),
    			port-11 (11),
    			port-12 (12),
    			port-13 (13),
    			port-14 (14),
    			port-15 (15),
    			port-16 (16),
    			port-17 (17),
    			port-18 (18),
    			port-19 (19),
    			port-20 (20),
    			port-21 (21),
    			port-22 (22),
    			port-23 (23),
    			port-24 (24)
		}
    MAX-ACCESS  read-only
    STATUS      current
    DESCRIPTION
	"The port being addressed"
    ::= { relayTableEntry 3 }

relayStatus OBJECT-TYPE
    SYNTAX      INTEGER {
                    normal (1),
                    closed (2)
                }
    MAX-ACCESS  read-write
    STATUS      current
    DESCRIPTION
	"This parameter describes whether a particular POTS line is in a normal
        or closed loop condition. By setting this parameter, the manager can
        switch the relays in order to bypass the LPF (Low Pass Filter) for POTS
        closed loop testing (closed) or force a relay back to normal operation
        mode before the Relay Active Duration timer times out (normal)"
    DEFVAL { 1 }
    ::= { relayTableEntry 4 }

relayResetAll OBJECT-TYPE
    SYNTAX      INTEGER {
                        unchanged (1),
                        reset (2)
       		}
    MAX-ACCESS  read-write
    STATUS      current
    DESCRIPTION
	"This parameter would allow the operator to force a relay back to
        normal operation for all ports."
    DEFVAL { 1 }
    ::= { splitterRelay 5 }

relayChangeNotification OBJECT-TYPE
    SYNTAX      SnmpAdminString
    MAX-ACCESS  accessible-for-notify
    STATUS      current
    DESCRIPTION
        "This notification is sent to the manager after a line status (or
        relay) change.  It takes three parameters : the slot (relaySlot) and
        port (relayPort) of the line, and its new status (relayStatus)"
    ::= { splitterRelay 6 }


END
