--			Ascend mibthermal MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBTHERMAL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibthermalProfile  OBJECT IDENTIFIER ::= { configuration 129}

	-- The mibthermalProfile table
	--
	-- This table contains parameters for the mibthermalProfile profile
	--

    mibthermalProfileTable	OBJECT-TYPE
	SYNTAX		SEQUENCE OF MibthermalProfileEntry
	ACCESS		not-accessible
	STATUS		mandatory
	DESCRIPTION	"A list of mibthermalProfile profile entries."
	::= { mibthermalProfile 1 }

    mibthermalProfileEntry	OBJECT-TYPE
	SYNTAX		MibthermalProfileEntry
	ACCESS		not-accessible
	STATUS		mandatory
	DESCRIPTION	"A mibthermalProfile entry containing objects that
			 maps to the parameters of mibthermalProfile profile."
	INDEX		{ thermalProfile-Index-o }
	::= { mibthermalProfileTable 1 }

    MibthermalProfileEntry ::=
	SEQUENCE {
	    thermalProfile-Index-o
		INTEGER,
	    thermalProfile-FantrayLownoiseRpm
		INTEGER,
	    thermalProfile-OperationMode
		INTEGER,
	    thermalProfile-LowTemperatureThreshold
		INTEGER,
	    thermalProfile-HighTemperatureThreshold
		INTEGER,
	    thermalProfile-AlarmTemperatureTrigger
		INTEGER,
	    thermalProfile-BottomLowTemperatureThreshold
		INTEGER,
	    thermalProfile-BottomHighTemperatureThreshold
		INTEGER,
	    thermalProfile-TopLowTemperatureThreshold
		INTEGER,
	    thermalProfile-TopHighTemperatureThreshold
		INTEGER,
	    thermalProfile-Action-o
		INTEGER
	}

    thermalProfile-Index-o	OBJECT-TYPE
	SYNTAX	INTEGER
	ACCESS	read-only
	STATUS	mandatory
	DESCRIPTION	""
	::= { mibthermalProfileEntry 1 }

    thermalProfile-FantrayLownoiseRpm	OBJECT-TYPE
	SYNTAX	INTEGER
	ACCESS	read-write
	STATUS	mandatory
	DESCRIPTION	"RPM of the fantray in Low-Noise mode"
	::= { mibthermalProfileEntry 2 }

    thermalProfile-OperationMode	OBJECT-TYPE
	SYNTAX	INTEGER {
		    fullSpeedOnly (1),
		    lowNoiseSpeedOnly (2),
		    autoRegulation (3)
		}
	ACCESS	read-write
	STATUS	mandatory
	DESCRIPTION	"Operation mode of the fantray"
	::= { mibthermalProfileEntry 3 }

    thermalProfile-LowTemperatureThreshold	OBJECT-TYPE
	SYNTAX	INTEGER
	ACCESS	read-write
	STATUS	mandatory
	DESCRIPTION	"Low shelf-controller temperature trigger level (in Celsius). When operation-mode = auto-regulation and the temperature falls below this value, the fans return to low-noise mode"
	::= { mibthermalProfileEntry 4 }

    thermalProfile-HighTemperatureThreshold	OBJECT-TYPE
	SYNTAX	INTEGER
	ACCESS	read-write
	STATUS	mandatory
	DESCRIPTION	"High shelf-controller temperature trigger level (in Celsius). When operation-mode = auto-regulation and this temperature is exceeded, the fans switch to full speed"
	::= { mibthermalProfileEntry 5 }

    thermalProfile-AlarmTemperatureTrigger	OBJECT-TYPE
	SYNTAX	INTEGER
	ACCESS	read-write
	STATUS	mandatory
	DESCRIPTION	"Temperature that if exceeded, will trigger an ALARM state (in Celsius)"
	::= { mibthermalProfileEntry 6 }

    thermalProfile-BottomLowTemperatureThreshold	OBJECT-TYPE
	SYNTAX	INTEGER
	ACCESS	read-write
	STATUS	mandatory
	DESCRIPTION	"Bottom thermal sensor low temperature trigger level (in Celsius). When temperature falls below this value, trigger ALARM state"
	::= { mibthermalProfileEntry 8 }

    thermalProfile-BottomHighTemperatureThreshold	OBJECT-TYPE
	SYNTAX	INTEGER
	ACCESS	read-write
	STATUS	mandatory
	DESCRIPTION	"Bottom thermal sensor high temperature trigger level (in Celsius). When this temperature is exceeded, trigger ALARM state"
	::= { mibthermalProfileEntry 9 }

    thermalProfile-TopLowTemperatureThreshold	OBJECT-TYPE
	SYNTAX	INTEGER
	ACCESS	read-write
	STATUS	mandatory
	DESCRIPTION	"Top thermal sensor low temperature trigger level (in Celsius). When temperature falls below this value, trigger ALARM state"
	::= { mibthermalProfileEntry 10 }

    thermalProfile-TopHighTemperatureThreshold	OBJECT-TYPE
	SYNTAX	INTEGER
	ACCESS	read-write
	STATUS	mandatory
	DESCRIPTION	"Top thermal sensor high temperature trigger level (in Celsius). When this temperature is exceeded, trigger ALARM state"
	::= { mibthermalProfileEntry 11 }

    thermalProfile-Action-o	OBJECT-TYPE
	SYNTAX	INTEGER {
		    noAction (1),
		    createProfile (2),
		    deleteProfile (3)
		}
	ACCESS	read-write
	STATUS	mandatory
	DESCRIPTION	""
	::= { mibthermalProfileEntry 7 }

END
