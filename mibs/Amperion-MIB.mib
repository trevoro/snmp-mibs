-- This File has been fixed
--*******************************************************************************
-- MIB amperion from project `Amperion'
-- 
-- Auto-generated by SNMP IQ Application Builder on 12/18/2003
-- Version: 1.5.1.0
-- Authored on: 05/08/2003
-- 
--  Amperion Inc. private MIB
-- 
--*******************************************************************************

Amperion-MIB DEFINITIONS ::= BEGIN

	IMPORTS
		MODULE-IDENTITY,
		OBJECT-TYPE,
		NOTIFICATION-TYPE,
		enterprises,
		Integer32,
		Unsigned32,
		Counter32,
		Counter64,
		Gauge32,
		IpAddress,
		TimeTicks,
		Opaque
			FROM SNMPv2-SMI

		OBJECT-GROUP
			FROM SNMPv2-CONF

		DisplayString,
		RowStatus,
		TruthValue
			FROM SNMPv2-TC

		ifIndex
			FROM RFC1213-MIB;

amperion        MODULE-IDENTITY
	LAST-UPDATED "200305080000Z"
	ORGANIZATION "Amperion"
	CONTACT-INFO "Sanjay Jaiman"
	DESCRIPTION
		" Amperion Inc. private MIB"
	::= { enterprises 13995 }

-- ***********************************************************
-- ***********************************************************
ds2             OBJECT IDENTIFIER ::= { amperion 1 }
powerline       OBJECT IDENTIFIER ::= { ds2 1 }
plMibIIExtension OBJECT IDENTIFIER ::= { powerline 1 }
plCards         OBJECT IDENTIFIER ::= { plMibIIExtension 2 }

plCdNumber      OBJECT-TYPE
	SYNTAX Integer32
	MAX-ACCESS read-only
	STATUS current
	DESCRIPTION
		"Number of Cards available. Maximum index of plCdTable"
	::= { plCards 1 }


-- *** Begin Table plCdTable       ***************************
plCdTable       OBJECT-TYPE
	SYNTAX SEQUENCE OF PlCdEntry
	MAX-ACCESS not-accessible
	STATUS current
	DESCRIPTION
		"Powerline Cards Table. List of attributes of each Card available in the System. Indexed by the number of the Card (from 1 to plCdNumber)."
	::= { plCards 2 }


plCdEntry       OBJECT-TYPE
	SYNTAX PlCdEntry
	MAX-ACCESS not-accessible
	STATUS current
	DESCRIPTION
		"Row of table plCdTable"
	INDEX { plCdIndex }
	::= { plCdTable 1 }


PlCdEntry       ::= 
	SEQUENCE {
	   plCdIndex
	      Integer32,
	   plCdType
	      INTEGER,
	   plCdLink
	      INTEGER,
	   plCdShortMacAddress
	      Integer32,
	   plCdLongMacAddress
	      DisplayString,
	   plCdHardwareVersion
	      DisplayString,
	   plCdFirmwareVersion
	      DisplayString,
	   plCdDriverVersion
	      DisplayString,
	   plCdReset
	      Integer32,
	   plCdFactoryReset
	      Integer32,
	   plCdSaveAsPermanent
	      Integer32,
	   plCdStatus
	      Integer32,
	   plCdRemoteList
	      DisplayString,
	   plCdNumRemoteList
	      Integer32 
	}

plCdIndex       OBJECT-TYPE
	SYNTAX Integer32
	MAX-ACCESS not-accessible
	STATUS current
	DESCRIPTION
		"Number of powerline card. Maximum: plCdNumber"
	::= { plCdEntry 1 }


plCdType        OBJECT-TYPE
	SYNTAX INTEGER { he(0), cpe(1) } 
	MAX-ACCESS read-only
	STATUS current
	DESCRIPTION
		"Type of card: 
		0 => HE
		1 => CPE"
	::= { plCdEntry 2 }


plCdLink        OBJECT-TYPE
	SYNTAX INTEGER { link1(1), link2(2), link3(3), link4(4), link5(5), link6(6) } 
	MAX-ACCESS read-write
	STATUS current
	DESCRIPTION
		"Type of link:
		1 => Link 1
		2 => Link 2
		3 => Link 3
		4 => Link 4
		5 => Link 5
		6 => Link 6"
	::= { plCdEntry 3 }


plCdShortMacAddress OBJECT-TYPE
	SYNTAX Integer32
	MAX-ACCESS read-write
	STATUS current
	DESCRIPTION
		"Short MAC Address of the Card"
	::= { plCdEntry 4 }


plCdLongMacAddress OBJECT-TYPE
	SYNTAX DisplayString(SIZE(0..255))
	MAX-ACCESS read-only
	STATUS current
	DESCRIPTION
		"Long MAC Address of the Card"
	::= { plCdEntry 5 }


plCdHardwareVersion OBJECT-TYPE
	SYNTAX DisplayString(SIZE(0..255))
	MAX-ACCESS read-only
	STATUS current
	DESCRIPTION
		"Hardware Version"
	::= { plCdEntry 6 }


plCdFirmwareVersion OBJECT-TYPE
	SYNTAX DisplayString(SIZE(0..255))
	MAX-ACCESS read-only
	STATUS current
	DESCRIPTION
		"Firmware Version"
	::= { plCdEntry 7 }


plCdDriverVersion OBJECT-TYPE
	SYNTAX DisplayString(SIZE(0..255))
	MAX-ACCESS read-only
	STATUS current
	DESCRIPTION
		"Driver Version"
	::= { plCdEntry 8 }


plCdReset       OBJECT-TYPE
	SYNTAX Integer32
	MAX-ACCESS read-write
	STATUS current
	DESCRIPTION
		"Reset to Saved Values. Soft Reset."
	::= { plCdEntry 9 }


plCdFactoryReset OBJECT-TYPE
	SYNTAX Integer32
	MAX-ACCESS read-write
	STATUS current
	DESCRIPTION
		"Reset to factory values. Hard Reset."
	::= { plCdEntry 10 }


plCdSaveAsPermanent OBJECT-TYPE
	SYNTAX Integer32
	MAX-ACCESS read-write
	STATUS current
	DESCRIPTION
		"Save MIB values as default values: the information of the Remote List (long MAC address and short MAC address of each user) is saved and will be restored after a reboot or a poweroff."
	::= { plCdEntry 11 }


plCdStatus      OBJECT-TYPE
	SYNTAX Integer32
	MAX-ACCESS read-only
	STATUS current
	DESCRIPTION
		"Status related to the interface:
		0 => OK."
	::= { plCdEntry 12 }


plCdRemoteList  OBJECT-TYPE
	SYNTAX DisplayString(SIZE(0..255))
	MAX-ACCESS read-only
	STATUS current
	DESCRIPTION
		"List of Long MAC Address that can be connected with HE (only HE). Returns a string with the list of long MAC address (not separated by spaces)"
	::= { plCdEntry 13 }


plCdNumRemoteList OBJECT-TYPE
	SYNTAX Integer32
	MAX-ACCESS read-only
	STATUS current
	DESCRIPTION
		"Number of CPE in remote list (only HE). This is the maximum value for cpeId in Network table."
	::= { plCdEntry 14 }


-- *** End Table plCdTable       *****************************
plNetwork       OBJECT IDENTIFIER ::= { powerline 2 }

-- *** Begin Table plNetTable      ***************************
plNetTable      OBJECT-TYPE
	SYNTAX SEQUENCE OF PlNetEntry
	MAX-ACCESS not-accessible
	STATUS current
	DESCRIPTION
		"Network Topology. Indexed by number of card and number of remote user (.plCdIndex.cpeId). Maximum values for indexes: plCdNumber and plCdNumRemoteList. Only available in HE."
	::= { plNetwork 1 }


plNetEntry      OBJECT-TYPE
	SYNTAX PlNetEntry
	MAX-ACCESS not-accessible
	STATUS current
	DESCRIPTION
		"Row of table plNetTable"
	INDEX { plNetShortMacAddress }
	::= { plNetTable 1 }


PlNetEntry      ::= 
	SEQUENCE {
	   plNetShortMacAddress
	      Integer32,
	   plNetLongMacAddress
	      DisplayString,
	   plNetRowStatus
	      RowStatus 
	}

plNetShortMacAddress OBJECT-TYPE
	SYNTAX Integer32(1..9)
	MAX-ACCESS not-accessible
	STATUS current
	DESCRIPTION
		"SMAC of remote CPE."
	::= { plNetEntry 1 }


plNetLongMacAddress OBJECT-TYPE
	SYNTAX DisplayString(SIZE(0..14))
	MAX-ACCESS read-create
	STATUS current
	DESCRIPTION
		"Long Mac Address of Remote Node."
	DEFVAL { "0x000000000000" }
	::= { plNetEntry 3 }


plNetRowStatus  OBJECT-TYPE
	SYNTAX RowStatus
	MAX-ACCESS read-create
	STATUS current
	DESCRIPTION
		"Row Status"
	DEFVAL { createAndWait }
	::= { plNetEntry 8 }


-- *** End Table plNetTable      *****************************
plTransmission  OBJECT IDENTIFIER ::= { powerline 3 }

-- *** Begin Table plInpTable      ***************************
plInpTable      OBJECT-TYPE
	SYNTAX SEQUENCE OF PlInpEntry
	MAX-ACCESS not-accessible
	STATUS current
	DESCRIPTION
		"Input Channel Table. Common input characteristics. 
		Indexed by number of card.
		Maximum value of index: plCdNumber"
	::= { plTransmission 2 }


plInpEntry      OBJECT-TYPE
	SYNTAX PlInpEntry
	MAX-ACCESS not-accessible
	STATUS current
	DESCRIPTION
		"Row of table plInpTable"
	INDEX { ifIndex }
	::= { plInpTable 1 }


PlInpEntry      ::= 
	SEQUENCE {
	   plInpTotalOctets
	      Integer32,
	   plInpGain
	      Integer32,
	   plInpAGC
	      INTEGER,
	   plInpMaxGain
	      Integer32,
	   plInpThresholds
	      DisplayString,
	   plInpAttenuationGain
	      Integer32,
	   plInpSamsDecode
	      Integer32,
	   plInpSamsGood
	      Integer32,
	   plInpSamsBad
	      Integer32 
	}

plInpTotalOctets OBJECT-TYPE
	SYNTAX Integer32
	MAX-ACCESS read-only
	STATUS current
	DESCRIPTION
		"Total number of rx octets (including FEC overhead)"
	::= { plInpEntry 1 }


plInpGain       OBJECT-TYPE
	SYNTAX Integer32
	MAX-ACCESS read-write
	STATUS current
	DESCRIPTION
		"Reception gain"
	::= { plInpEntry 2 }


plInpAGC        OBJECT-TYPE
	SYNTAX INTEGER { agcdisabled(0), agcenabled(1) } 
	MAX-ACCESS read-write
	STATUS current
	DESCRIPTION
		"To enable or disable Adaptive Rx Gain Control.
		0 => AGC disabled
		1 => AGC enabled."
	::= { plInpEntry 3 }


plInpMaxGain    OBJECT-TYPE
	SYNTAX Integer32
	MAX-ACCESS read-write
	STATUS current
	DESCRIPTION
		"Maximum reception gain"
	::= { plInpEntry 4 }


plInpThresholds OBJECT-TYPE
	SYNTAX DisplayString(SIZE(0..255))
	MAX-ACCESS read-write
	STATUS current
	DESCRIPTION
		"SNR Thresholds in dB. Returns a string containing 4 integers."
	::= { plInpEntry 5 }


plInpAttenuationGain OBJECT-TYPE
	SYNTAX Integer32
	MAX-ACCESS read-write
	STATUS current
	DESCRIPTION
		"Attenuation Gain (only HE)"
	::= { plInpEntry 6 }


plInpSamsDecode OBJECT-TYPE
	SYNTAX Integer32
	MAX-ACCESS read-only
	STATUS current
	DESCRIPTION
		"Number of decoded SAMS (only CPE)"
	::= { plInpEntry 7 }


plInpSamsGood   OBJECT-TYPE
	SYNTAX Integer32
	MAX-ACCESS read-only
	STATUS current
	DESCRIPTION
		"Number of used SAMS (only CPE)"
	::= { plInpEntry 8 }


plInpSamsBad    OBJECT-TYPE
	SYNTAX Integer32
	MAX-ACCESS read-only
	STATUS current
	DESCRIPTION
		"Number of discarded SAMS (only CPE)"
	::= { plInpEntry 9 }


-- *** End Table plInpTable      *****************************

-- *** Begin Table plInpNodeTable  ***************************
plInpNodeTable  OBJECT-TYPE
	SYNTAX SEQUENCE OF PlInpNodeEntry
	MAX-ACCESS not-accessible
	STATUS current
	DESCRIPTION
		"Input Characteristics Remote equipments connected"
	::= { plTransmission 4 }


plInpNodeEntry  OBJECT-TYPE
	SYNTAX PlInpNodeEntry
	MAX-ACCESS not-accessible
	STATUS current
	DESCRIPTION
		"Row of table plInpNodeTable"
	INDEX { ifIndex, plNetShortMacAddress }
	::= { plInpNodeTable 1 }


PlInpNodeEntry  ::= 
	SEQUENCE {
	   plInpNodeReceivedPkts
	      Integer32,
	   plInpNodeReceivedUnrecPkts
	      Integer32,
	   plInpNodeReceivedCorrectedPkts
	      Integer32,
	   plInpNodeReceivedOctets
	      Integer32,
	   plInpNodeReceivedCorrectedOctets
	      Integer32,
	   plInpNodeReceivedPower
	      Integer32,
	   plInpNodePLR
	      Integer32,
	   plInpNodeMeanBPC
	      Integer32,
	   plInpNodeSNRChanges
	      Integer32,
	   plInpNodeSNR
	      DisplayString,
	   plInpNodeBPC
	      DisplayString,
	   plInpNodeCFR
	      DisplayString,
	   plInpNodeEnableCarriers
	      DisplayString,
	   plInpNodeProtocolEnableCarriers
	      DisplayString,
	   plInpNodeEnableProtocolEnableCarriers
	      Integer32 
	}

plInpNodeReceivedPkts OBJECT-TYPE
	SYNTAX Integer32
	MAX-ACCESS read-only
	STATUS current
	DESCRIPTION
		"Number of Packets received from cpeId user"
	::= { plInpNodeEntry 1 }


plInpNodeReceivedUnrecPkts OBJECT-TYPE
	SYNTAX Integer32
	MAX-ACCESS read-only
	STATUS current
	DESCRIPTION
		"Number of Unrecoverable received packets"
	::= { plInpNodeEntry 2 }


plInpNodeReceivedCorrectedPkts OBJECT-TYPE
	SYNTAX Integer32
	MAX-ACCESS read-only
	STATUS current
	DESCRIPTION
		"Number of Corrected (by FEC) received packets"
	::= { plInpNodeEntry 3 }


plInpNodeReceivedOctets OBJECT-TYPE
	SYNTAX Integer32
	MAX-ACCESS read-only
	STATUS current
	DESCRIPTION
		"Number of Received bytes"
	::= { plInpNodeEntry 4 }


plInpNodeReceivedCorrectedOctets OBJECT-TYPE
	SYNTAX Integer32
	MAX-ACCESS read-only
	STATUS current
	DESCRIPTION
		"Number of Corrected (by FEC) received bytes"
	::= { plInpNodeEntry 5 }


plInpNodeReceivedPower OBJECT-TYPE
	SYNTAX Integer32
	MAX-ACCESS read-only
	STATUS current
	DESCRIPTION
		"Total received power"
	::= { plInpNodeEntry 6 }


plInpNodePLR    OBJECT-TYPE
	SYNTAX Integer32
	MAX-ACCESS read-only
	STATUS current
	DESCRIPTION
		"Packet Loss Rate"
	::= { plInpNodeEntry 7 }


plInpNodeMeanBPC OBJECT-TYPE
	SYNTAX Integer32
	MAX-ACCESS read-only
	STATUS current
	DESCRIPTION
		"Mean BPC: sum of current bits configuration"
	::= { plInpNodeEntry 8 }


plInpNodeSNRChanges OBJECT-TYPE
	SYNTAX Integer32
	MAX-ACCESS read-only
	STATUS current
	DESCRIPTION
		"Changes of SNR"
	::= { plInpNodeEntry 9 }


plInpNodeSNR    OBJECT-TYPE
	SYNTAX DisplayString(SIZE(0..255))
	MAX-ACCESS read-only
	STATUS current
	DESCRIPTION
		"String with SNR per carrier: contains 512 bytes if it is a HE or 768 if it is a CPE."
	::= { plInpNodeEntry 10 }


plInpNodeBPC    OBJECT-TYPE
	SYNTAX DisplayString(SIZE(0..255))
	MAX-ACCESS read-only
	STATUS current
	DESCRIPTION
		"String with BPC per carrier configuration: contains 256 bytes if it is a HE or 384 if it is a CPE."
	::= { plInpNodeEntry 11 }


plInpNodeCFR    OBJECT-TYPE
	SYNTAX DisplayString(SIZE(0..255))
	MAX-ACCESS read-only
	STATUS current
	DESCRIPTION
		"String with CFR per carrier: contains 512 bytes if it is a HE or 768 if it is a CPE."
	::= { plInpNodeEntry 12 }


plInpNodeEnableCarriers OBJECT-TYPE
	SYNTAX DisplayString(SIZE(0..255))
	MAX-ACCESS read-write
	STATUS current
	DESCRIPTION
		"String with enabled (1) and disabled (0) carriers: contains 256 bytes if it is a HE or 384 if it is a CPE."
	::= { plInpNodeEntry 13 }


plInpNodeProtocolEnableCarriers OBJECT-TYPE
	SYNTAX DisplayString(SIZE(0..255))
	MAX-ACCESS read-only
	STATUS current
	DESCRIPTION
		"String with enabled (1) and disabled (0) carriers: contains 256 bytes if it is a HE or 384 if it is a CPE."
	::= { plInpNodeEntry 14 }


plInpNodeEnableProtocolEnableCarriers OBJECT-TYPE
	SYNTAX Integer32
	MAX-ACCESS read-write
	STATUS current
	DESCRIPTION
		"Enable protocol (1) and disable protocol (0)."
	::= { plInpNodeEntry 15 }


-- *** End Table plInpNodeTable  *****************************
plTraps         OBJECT IDENTIFIER ::= { powerline 4 }
plRemoteCPE     OBJECT IDENTIFIER ::= { powerline 5 }
internal        OBJECT IDENTIFIER ::= { ds2 2 }
amperionSystem  OBJECT IDENTIFIER ::= { amperion 2 }

serialNumber    OBJECT-TYPE
	SYNTAX DisplayString(SIZE(0..32))
	MAX-ACCESS read-only
	STATUS current
	DESCRIPTION
		"The serial number of the board, which is unique per part number"
	DEFVAL { "####" }
	::= { amperionSystem 1 }


partNumber      OBJECT-TYPE
	SYNTAX DisplayString(SIZE(0..32))
	MAX-ACCESS read-only
	STATUS current
	DESCRIPTION
		"The part number of the board, which identifies the board type"
	DEFVAL { "####" }
	::= { amperionSystem 2 }


rombootVersion  OBJECT-TYPE
	SYNTAX DisplayString(SIZE(0..80))
	MAX-ACCESS read-only
	STATUS current
	DESCRIPTION
		"The string that identifies the Romboot software"
	DEFVAL { "####" }
	::= { amperionSystem 3 }


-- *** Begin Table alarms          ***************************
alarms          OBJECT-TYPE
	SYNTAX SEQUENCE OF AlarmsEntry
	MAX-ACCESS not-accessible
	STATUS current
	DESCRIPTION
		"Dynamic alarm table - shows all the outstanding alarms on 
		the system"
	::= { amperionSystem 4 }


alarmsEntry     OBJECT-TYPE
	SYNTAX AlarmsEntry
	MAX-ACCESS not-accessible
	STATUS current
	DESCRIPTION
		"Row of table alarms"
	INDEX { alarmIndex }
	::= { alarms 1 }


AlarmsEntry     ::= 
	SEQUENCE {
	   alarmIndex
	      Integer32,
	   description
	      DisplayString 
	}

alarmIndex      OBJECT-TYPE
	SYNTAX Integer32
	MAX-ACCESS not-accessible
	STATUS current
	DESCRIPTION
		"The alarmIndex uniquely identifies alarms on the system"
	::= { alarmsEntry 1 }


description     OBJECT-TYPE
	SYNTAX DisplayString(SIZE(0..80))
	MAX-ACCESS read-only
	STATUS current
	DESCRIPTION
		"Textual description of the alarm"
	::= { alarmsEntry 2 }


-- *** End Table alarms          *****************************

productType     OBJECT-TYPE
	SYNTAX INTEGER { unknown(0), ohInjector(1), ohExtractor(2), ohRepeater(3), ohRepeaterExt(4), ugInjector(5), ugExtractor(6), ugRepeater(7), ugRepeaterExt(8) } 
	MAX-ACCESS read-only
	STATUS current
	DESCRIPTION
		"injector/extractor/repeator"
	DEFVAL { unknown }
	::= { amperionSystem 5 }


linuxVersion    OBJECT-TYPE
	SYNTAX DisplayString(SIZE(0..80))
	MAX-ACCESS read-only
	STATUS current
	DESCRIPTION
		"The string that identifies the Linux kernel software"
	DEFVAL { "####" }
	::= { amperionSystem 8 }


amperionSysDescr OBJECT-TYPE
	SYNTAX DisplayString(SIZE(0..255))
	MAX-ACCESS read-only
	STATUS current
	DESCRIPTION
		"A textual description of the entity.  This value
		should include the full name and version
		identification of the system's hardware type,
		software operating-system, and networking
		software.  It is mandatory that this only contain
		printable ASCII characters."
	DEFVAL { "####" }
	::= { amperionSystem 10 }


amperionSysObjectID OBJECT-TYPE
	SYNTAX OBJECT IDENTIFIER
	MAX-ACCESS read-only
	STATUS current
	DESCRIPTION
		"The vendor's authoritative identification of the
		network management subsystem contained in the
		entity.  This value is allocated within the SMI
		enterprises subtree (1.3.6.1.4.1) and provides an
		easy and unambiguous means for determining `what
		kind of box' is being managed.  For example, if
		vendor `Flintstones, Inc.' was assigned the
		subtree 1.3.6.1.4.1.4242, it could assign the
		identifier 1.3.6.1.4.1.4242.1.1 to its `Fred
		Router'."
	DEFVAL { { 0 0  } }
	::= { amperionSystem 11 }


amperionSysUpTime OBJECT-TYPE
	SYNTAX TimeTicks
	MAX-ACCESS read-only
	STATUS current
	DESCRIPTION
		"The time (in hundredths of a second) since the
		network management portion of the system was last
		re-initialized."
	::= { amperionSystem 12 }


amperionSysContact OBJECT-TYPE
	SYNTAX DisplayString(SIZE(0..255))
	MAX-ACCESS read-write
	STATUS current
	DESCRIPTION
		"The textual identification of the contact person
		for this managed node, together with information
		on how to contact this person."
	DEFVAL { "Amperion Inc. Andover MA" }
	::= { amperionSystem 13 }


amperionSysName OBJECT-TYPE
	SYNTAX DisplayString(SIZE(0..255))
	MAX-ACCESS read-write
	STATUS current
	DESCRIPTION
		"An administratively-assigned name for this
		managed node.  By convention, this is the node's
		fully-qualified domain name."
	DEFVAL { "Amperion" }
	::= { amperionSystem 14 }


amperionSysLocation OBJECT-TYPE
	SYNTAX DisplayString(SIZE(0..255))
	MAX-ACCESS read-write
	STATUS current
	DESCRIPTION
		"The physical location of this node (e.g.,
		`telephone closet, 3rd floor')."
	DEFVAL { "default" }
	::= { amperionSystem 15 }


amperionSysServices OBJECT-TYPE
	SYNTAX Integer32(0..127)
	MAX-ACCESS read-only
	STATUS current
	DESCRIPTION
		"A value which indicates the set of services that
		this entity primarily offers.
		 The value is a sum.  This sum initially takes the
		value zero, Then, for each layer, L, in the range
		1 through 7, that this node performs transactions
		for, 2 raised to (L - 1) is added to the sum.  For
		example, a node which performs primarily routing
		functions would have a value of 4 (2^(3-1)).  In
		contrast, a node which is a host offering
		application services would have a value of 72
		(2^(4-1) + 2^(7-1)).  Note that in the context of
		the Internet suite of protocols, values should be
		calculated accordingly:
		      layer  functionality
		         1  physical (e.g., repeaters)
		         2  datalink/subnetwork (e.g., bridges)
		         3  internet (e.g., IP gateways)
		         4  end-to-end  (e.g., IP hosts)
		         7  applications (e.g., mail relays)
		
		For systems including OSI protocols, layers 5 and
		6 may also be counted."
	DEFVAL { 0 }
	::= { amperionSystem 16 }


amperionTrapMgr1 OBJECT-TYPE
	SYNTAX IpAddress
	MAX-ACCESS read-write
	STATUS current
	DESCRIPTION
		"IP address of Manager receceiving traps"
	DEFVAL { '7f000001'h }
	::= { amperionSystem 18 }


amperionTrapMgr2 OBJECT-TYPE
	SYNTAX IpAddress
	MAX-ACCESS read-write
	STATUS current
	DESCRIPTION
		"IP address of Manager receceiving traps"
	DEFVAL { '7f000001'h }
	::= { amperionSystem 19 }


amperionTrapMgr3 OBJECT-TYPE
	SYNTAX IpAddress
	MAX-ACCESS read-write
	STATUS current
	DESCRIPTION
		"amperionTrapMgr3"
	DEFVAL { '7f000001'h }
	::= { amperionSystem 20 }


userGpsInfoString OBJECT-TYPE
	SYNTAX DisplayString(SIZE(1..128))
	MAX-ACCESS read-write
	STATUS current
	DESCRIPTION
		"User defined string for the user to put the GPS info of this device"
	DEFVAL { "none" }
	::= { amperionSystem 6 }

softwareUpgrade OBJECT IDENTIFIER ::= { amperion 3 }

serverAddress   OBJECT-TYPE
	SYNTAX DisplayString(SIZE(0..80))
	MAX-ACCESS read-write
	STATUS current
	DESCRIPTION
		"Name or IP Address of the primary file server from which to retrieve new software."
	DEFVAL { "0.0.0.0" }
	::= { softwareUpgrade 1 }


currentState    OBJECT-TYPE
	SYNTAX INTEGER { idle(1), inProgress(2) } 
	MAX-ACCESS read-only
	STATUS current
	DESCRIPTION
		"Current state of the software upgrade."
	DEFVAL { idle }
	::= { softwareUpgrade 3 }


bootPartition   OBJECT-TYPE
	SYNTAX INTEGER { primary(1), backup(2) } 
	MAX-ACCESS read-write
	STATUS current
	DESCRIPTION
		"Image in this partition will be used when the system boots."
	DEFVAL { primary }
	::= { softwareUpgrade 4 }


upgradePartition OBJECT-TYPE
	SYNTAX INTEGER { primary(1), backup(2) } 
	MAX-ACCESS read-write
	STATUS current
	DESCRIPTION
		"Default partition to erase and load with a new image."
	DEFVAL { backup }
	::= { softwareUpgrade 5 }


currentPartition OBJECT-TYPE
	SYNTAX INTEGER { unknown(0), primary(1), backup(2) } 
	MAX-ACCESS read-only
	STATUS current
	DESCRIPTION
		"Partition from which currently running software was loaded."
	DEFVAL { unknown }
	::= { softwareUpgrade 6 }


commandOptions  OBJECT-TYPE
	SYNTAX DisplayString(SIZE(0..80))
	MAX-ACCESS read-write
	STATUS current
	DESCRIPTION
		"Software upgrade options: Reserved for future use"
	DEFVAL { "none" }
	::= { softwareUpgrade 7 }


primaryPartitionContents OBJECT-TYPE
	SYNTAX DisplayString(SIZE(0..80))
	MAX-ACCESS read-only
	STATUS current
	DESCRIPTION
		"Description of image in primary partition."
	DEFVAL { "none" }
	::= { softwareUpgrade 2 }


primaryCRC      OBJECT-TYPE
	SYNTAX INTEGER { unknown(0), ok(1), failed(2) } 
	MAX-ACCESS read-only
	STATUS current
	DESCRIPTION
		"CRC status of image in primary partition."
	DEFVAL { unknown }
	::= { softwareUpgrade 9 }


backupPartitionContents OBJECT-TYPE
	SYNTAX DisplayString(SIZE(0..80))
	MAX-ACCESS read-only
	STATUS current
	DESCRIPTION
		"Description of image in backup partition."
	DEFVAL { "none" }
	::= { softwareUpgrade 8 }


backupCRC       OBJECT-TYPE
	SYNTAX INTEGER { unknown(0), ok(1), failed(2) } 
	MAX-ACCESS read-only
	STATUS current
	DESCRIPTION
		"CRC status of image in backup partition."
	DEFVAL { unknown }
	::= { softwareUpgrade 10 }


lastStatus      OBJECT-TYPE
	SYNTAX DisplayString(SIZE(0..80))
	MAX-ACCESS read-only
	STATUS current
	DESCRIPTION
		"Status of current or last software upgrade performed (since last reboot)."
	DEFVAL { "none" }
	::= { softwareUpgrade 11 }


filename        OBJECT-TYPE
	SYNTAX DisplayString(SIZE(0..80))
	MAX-ACCESS read-write
	STATUS current
	DESCRIPTION
		"Path to filename to retrieve for software upgrade"
	DEFVAL { "ampmulti" }
	::= { softwareUpgrade 12 }


server1Address  OBJECT-TYPE
	SYNTAX DisplayString(SIZE(0..80))
	MAX-ACCESS read-write
	STATUS current
	DESCRIPTION
		"Name or IP Address of the alternate file server from which to retrieve new software."
	DEFVAL { "0.0.0.0" }
	::= { softwareUpgrade 13 }


server2Address  OBJECT-TYPE
	SYNTAX DisplayString(SIZE(0..80))
	MAX-ACCESS read-write
	STATUS current
	DESCRIPTION
		"Name or IP Address of the second alternate file server from which to retrieve new software."
	DEFVAL { "0.0.0.0" }
	::= { softwareUpgrade 14 }


upgradeSchedule OBJECT-TYPE
	SYNTAX DisplayString(SIZE(0..80))
	MAX-ACCESS read-write
	STATUS current
	DESCRIPTION
		"Scheduled upgrade date and time in MMDDhhmm format."
	DEFVAL { "None scheduled" }
	::= { softwareUpgrade 15 }


rebootSchedule  OBJECT-TYPE
	SYNTAX DisplayString(SIZE(0..80))
	MAX-ACCESS read-write
	STATUS current
	DESCRIPTION
		"Scheduled reboot date and time in MMDDhhmm format."
	DEFVAL { "None scheduled" }
	::= { softwareUpgrade 16 }


login           OBJECT-TYPE
	SYNTAX DisplayString(SIZE(0..80))
	MAX-ACCESS read-write
	STATUS current
	DESCRIPTION
		"login to use for software upgrade file server access."
	DEFVAL { "anonymous" }
	::= { softwareUpgrade 17 }


password        OBJECT-TYPE
	SYNTAX DisplayString(SIZE(0..80))
	MAX-ACCESS read-write
	STATUS current
	DESCRIPTION
		"password to use for software upgrade file server access."
	DEFVAL { "root@Amperion000000.com" }
	::= { softwareUpgrade 18 }


-- *** Begin Trap swupgradeCompleted ****************************
swupgradeCompleted NOTIFICATION-TYPE
	OBJECTS {
	   backupPartitionContents,
	   backupCRC,
	   primaryPartitionContents,
	   primaryCRC,
	   bootPartition
	}
	STATUS current
	DESCRIPTION
		"swupgradeCompleted"
	::= { softwareUpgrade 19 }

-- *** End Trap swupgradeCompleted ******************************
psGroup         OBJECT IDENTIFIER ::= { amperion 4 }

-- *** Begin Trap psImageChecksumError ****************************
psImageChecksumError NOTIFICATION-TYPE
	OBJECTS {
	   eventDescription
	}
	STATUS current
	DESCRIPTION
		"The power supply is notifying the main digital board that its main image
		crc is incorrect.  The main digital board needs to reprogram the new 
		power supply image again, or revert back to an older good image"
	::= { psGroup 14 }

-- *** End Trap psImageChecksumError ******************************

-- *** Begin Trap criticalBatteryShutdownWarning ****************************
criticalBatteryShutdownWarning NOTIFICATION-TYPE
	OBJECTS {
	   eventDescription
	}
	STATUS current
	DESCRIPTION
		"The power supply is warning the main digital board that we have 
		lost AC Line voltage and the battery is running low. The system will be
		shutting down in seconds. Perform necessary backup."
	::= { psGroup 15 }

-- *** End Trap criticalBatteryShutdownWarning ******************************

-- *** Begin Trap p12vOutOfRange  ****************************
p12vOutOfRange  NOTIFICATION-TYPE
	OBJECTS {
	   eventDescription
	}
	STATUS current
	DESCRIPTION
		"The power supply is warning the main digital board that the +12v
		regulator is out of range. If the condition is such that it is too high, 
		the decision may be to shutdown the regulator to avoid destroying the hardware"
	::= { psGroup 16 }

-- *** End Trap p12vOutOfRange  ******************************

-- *** Begin Trap m8point5vOutOfRange ****************************
m8point5vOutOfRange NOTIFICATION-TYPE
	OBJECTS {
	   eventDescription
	}
	STATUS current
	DESCRIPTION
		"The power supply is warning the main digital board that the -8.5v
		regulator is out of range. Note that the -8.5v regulator is the same 
		regulator as the +12v. If the condition is such that it is too high, the decision may be to shutdown the regulator to avoid destroying the hardware."
	::= { psGroup 17 }

-- *** End Trap m8point5vOutOfRange ******************************

-- *** Begin Trap p5vOutOfRange   ****************************
p5vOutOfRange   NOTIFICATION-TYPE
	OBJECTS {
	   eventDescription
	}
	STATUS current
	DESCRIPTION
		"The power supply is warning the main digital board that the +5v 
		regulator is out of range. If the condition is such that it is too high,
		the decision may be to shutdown the regulator to avoid destroying
		the hardware."
	::= { psGroup 18 }

-- *** End Trap p5vOutOfRange   ******************************

-- *** Begin Trap p3point3vOutOfRange ****************************
p3point3vOutOfRange NOTIFICATION-TYPE
	OBJECTS {
	   eventDescription
	}
	STATUS current
	DESCRIPTION
		"The power supply is warning the main digital board that the +3.3v
		regulator is out of range. If the condition is such that it is too high, 
		the decision may be to shutdown the regulator to avoid destroying 
		the hardware."
	::= { psGroup 19 }

-- *** End Trap p3point3vOutOfRange ******************************

-- *** Begin Trap batteryVoltsOutOfRange ****************************
batteryVoltsOutOfRange NOTIFICATION-TYPE
	OBJECTS {
	   eventDescription
	}
	STATUS current
	DESCRIPTION
		"The power supply is warning the main digital board that the
		battery voltage is out of range."
	::= { psGroup 20 }

-- *** End Trap batteryVoltsOutOfRange ******************************

-- *** Begin Trap mcuTempOutOfRange ****************************
mcuTempOutOfRange NOTIFICATION-TYPE
	OBJECTS {
	   eventDescription
	}
	STATUS current
	DESCRIPTION
		"The power supply is warning the main digital board that the
		microcontroller unit core temperature is out of range."
	::= { psGroup 21 }

-- *** End Trap mcuTempOutOfRange ******************************

-- *** Begin Trap batteryTempOutOfRange ****************************
batteryTempOutOfRange NOTIFICATION-TYPE
	OBJECTS {
	   eventDescription
	}
	STATUS current
	DESCRIPTION
		"The power supply is warning the main digital board that the battery
		temperature is out of range"
	::= { psGroup 22 }

-- *** End Trap batteryTempOutOfRange ******************************

-- *** Begin Trap psDetectedCommLapse ****************************
psDetectedCommLapse NOTIFICATION-TYPE
	OBJECTS {
	   eventDescription
	}
	STATUS current
	DESCRIPTION
		"Power Supply notifies main digital board that it did not communnicate to the power supply within the agreed upon periodic interval"
	::= { psGroup 23 }

-- *** End Trap psDetectedCommLapse ******************************

-- *** Begin Trap criticalRequestAborted ****************************
criticalRequestAborted NOTIFICATION-TYPE
	OBJECTS {
	   eventDescription
	}
	STATUS current
	DESCRIPTION
		"The power supply is notifying the main digital board that one of the
		critical requests was aborted due to not receiving it twice in a row."
	::= { psGroup 24 }

-- *** End Trap criticalRequestAborted ******************************

-- *** Begin Trap powerSupplyInternalError ****************************
powerSupplyInternalError NOTIFICATION-TYPE
	OBJECTS {
	   eventDescription
	}
	STATUS current
	DESCRIPTION
		"Power Supply / netmgt (PS thread) detected an internal error condition"
	::= { psGroup 25 }

-- *** End Trap powerSupplyInternalError ******************************

-- *** Begin Trap psBatteryNotConnected ****************************
psBatteryNotConnected NOTIFICATION-TYPE
	OBJECTS {
	   eventDescription
	}
	STATUS current
	DESCRIPTION
		"Power Supply Battery Not Connected. There is no battery backup for the system."
	::= { psGroup 26 }

-- *** End Trap psBatteryNotConnected ******************************

-- *** Begin Trap psAcOnOff       ****************************
psAcOnOff       NOTIFICATION-TYPE
	OBJECTS {
	   eventDescription
	}
	STATUS current
	DESCRIPTION
		"Power Supply detected AC going ON / OFF"
	::= { psGroup 27 }

-- *** End Trap psAcOnOff       ******************************

-- *** Begin Trap psHardwareError ****************************
psHardwareError NOTIFICATION-TYPE
	OBJECTS {
	   eventDescription
	}
	STATUS current
	DESCRIPTION
		"The power supply is notifying the main digital board that it incurred a hardware error"
	::= { psGroup 29 }

-- *** End Trap psHardwareError ******************************

-- *** Begin Trap npuDetectedCommLapse ****************************
npuDetectedCommLapse NOTIFICATION-TYPE
	OBJECTS {
	   eventDescription
	}
	STATUS current
	DESCRIPTION
		"Network processing unit could not  communnicate to the power supply"
	::= { psGroup 34 }

-- *** End Trap npuDetectedCommLapse ******************************

acLineVoltage   OBJECT-TYPE
	SYNTAX INTEGER { off(0), on(1) } 
	MAX-ACCESS read-only
	STATUS current
	DESCRIPTION
		"State of AC Line voltage (on/off)"
	::= { psGroup 1 }


plus12v         OBJECT-TYPE
	SYNTAX DisplayString(SIZE(0..255))
	MAX-ACCESS read-only
	STATUS current
	DESCRIPTION
		"Regulated 12 volt supply"
	::= { psGroup 2 }


minus8point5v   OBJECT-TYPE
	SYNTAX DisplayString(SIZE(0..255))
	MAX-ACCESS read-only
	STATUS current
	DESCRIPTION
		"Regulated -8.5 volt supply"
	::= { psGroup 3 }


plus5v          OBJECT-TYPE
	SYNTAX DisplayString(SIZE(0..255))
	MAX-ACCESS read-only
	STATUS current
	DESCRIPTION
		"Regulated +5 volt supply"
	::= { psGroup 4 }


plus3point3v    OBJECT-TYPE
	SYNTAX DisplayString(SIZE(0..255))
	MAX-ACCESS read-only
	STATUS current
	DESCRIPTION
		"Regulated +3.3 volt supply"
	::= { psGroup 5 }


batteryCaseTemp OBJECT-TYPE
	SYNTAX DisplayString(SIZE(0..255))
	MAX-ACCESS read-only
	STATUS current
	DESCRIPTION
		"Battery Case Temperature"
	::= { psGroup 6 }


internalMcuTemp OBJECT-TYPE
	SYNTAX DisplayString(SIZE(0..255))
	MAX-ACCESS read-only
	STATUS current
	DESCRIPTION
		"Internal Micro Controller Unit Temperature"
	::= { psGroup 7 }


batteryCurrent  OBJECT-TYPE
	SYNTAX DisplayString(SIZE(0..255))
	MAX-ACCESS read-only
	STATUS current
	DESCRIPTION
		"Battery Current"
	::= { psGroup 8 }


batteryVoltage  OBJECT-TYPE
	SYNTAX DisplayString(SIZE(0..255))
	MAX-ACCESS read-only
	STATUS current
	DESCRIPTION
		"Battery Voltage"
	::= { psGroup 9 }


mcuSoftwareVersion OBJECT-TYPE
	SYNTAX DisplayString(SIZE(0..30))
	MAX-ACCESS read-only
	STATUS current
	DESCRIPTION
		"Micro Controller Unit Software Version"
	::= { psGroup 10 }


powerCycleNpu   OBJECT-TYPE
	SYNTAX INTEGER { idle(0), commit(1) } 
	MAX-ACCESS read-write
	STATUS current
	DESCRIPTION
		"Power Cycle the Network Processor Unit"
	DEFVAL { idle }
	::= { psGroup 11 }


psMode          OBJECT-TYPE
	SYNTAX INTEGER { protocol(0), dump(1) } 
	MAX-ACCESS read-only
	STATUS current
	DESCRIPTION
		"Power Supply mode, normal mode is protocol; 
		dump mode is a debug mode which displays debug prints from the MCU"
	::= { psGroup 12 }


shutdownNpu     OBJECT-TYPE
	SYNTAX INTEGER { idle(0), commit(1) } 
	MAX-ACCESS read-write
	STATUS current
	DESCRIPTION
		"Shut down 12v, -8.5v, 3.3v and 5v regulators driving the
		Network Processor Unit. This should only be used if one of the voltages
		 is too high."
	DEFVAL { idle }
	::= { psGroup 13 }


psEt            OBJECT-TYPE
	SYNTAX DisplayString(SIZE(0..80))
	MAX-ACCESS read-only
	STATUS current
	DESCRIPTION
		"Power Supply elapsed time since powerup"
	::= { psGroup 30 }


npuEt           OBJECT-TYPE
	SYNTAX DisplayString(SIZE(0..80))
	MAX-ACCESS read-only
	STATUS current
	DESCRIPTION
		"Power Supply elapsed time since powerup"
	::= { psGroup 31 }


npuPuTimes      OBJECT-TYPE
	SYNTAX Integer32
	MAX-ACCESS read-only
	STATUS current
	DESCRIPTION
		"Number of times the Network Processing Unit has been powered up."
	::= { psGroup 32 }


eventDescription OBJECT-TYPE
	SYNTAX DisplayString(SIZE(0..80))
	MAX-ACCESS read-only
	STATUS current
	DESCRIPTION
		"Description of the Last Event - Used in sending traps"
	::= { psGroup 33 }


psHardwareVersion OBJECT-TYPE
	SYNTAX DisplayString(SIZE(0..30))
	MAX-ACCESS read-only
	STATUS current
	DESCRIPTION
		"Hardware Version of the Power SUpply"
	::= { psGroup 28 }

amperionInterfaces OBJECT IDENTIFIER ::= { amperion 5 }

-- *** Begin Trap interfaceAdminDown ****************************
interfaceAdminDown NOTIFICATION-TYPE
	OBJECTS {
	   amperionifDescr
	}
	STATUS current
	DESCRIPTION
		"Admin of Interface being set down"
	::= { amperionInterfaces 3 }

-- *** End Trap interfaceAdminDown ******************************

-- *** Begin Trap interfaceAdminUp ****************************
interfaceAdminUp NOTIFICATION-TYPE
	OBJECTS {
	   amperionifDescr
	}
	STATUS current
	DESCRIPTION
		"Interface is being set up"
	::= { amperionInterfaces 4 }

-- *** End Trap interfaceAdminUp ******************************

amperionifNumber OBJECT-TYPE
	SYNTAX Integer32
	MAX-ACCESS read-only
	STATUS current
	DESCRIPTION
		"The number of network interfaces (regardless of
		their current state) present on this system."
	::= { amperionInterfaces 1 }


-- *** Begin Table amperionifTable ***************************
amperionifTable OBJECT-TYPE
	SYNTAX SEQUENCE OF AmperionifEntry
	MAX-ACCESS not-accessible
	STATUS current
	DESCRIPTION
		"A list of interface entries.  The number of
		entries is given by the value of ifNumber."
	::= { amperionInterfaces 2 }


amperionifEntry OBJECT-TYPE
	SYNTAX AmperionifEntry
	MAX-ACCESS not-accessible
	STATUS current
	DESCRIPTION
		"Row of table amperionifTable"
	INDEX { ifIndex }
	::= { amperionifTable 1 }


AmperionifEntry ::= 
	SEQUENCE {
	   amperionifDescr
	      DisplayString,
	   amperionifType
	      INTEGER,
	   amperionifMtu
	      Integer32,
	   amperionifSpeed
	      Gauge32,
	   amperionifPhysAddress
	      DisplayString,
	   amperionifAdminStatus
	      INTEGER,
	   amperionifOperStatus
	      INTEGER,
	   amperionifLastChange
	      TimeTicks,
	   amperionifInOctets
	      Counter32,
	   amperionifInUcastPkts
	      Counter32,
	   amperionifInNUcastPkts
	      Counter32,
	   amperionifInDiscards
	      Counter32,
	   amperionifInErrors
	      Counter32,
	   amperionifInUnknownProtos
	      Counter32,
	   amperionifOutOctets
	      Counter32,
	   amperionifOutUcastPkts
	      Counter32,
	   amperionifOutNUcastPkts
	      Counter32,
	   amperionifOutDiscards
	      Counter32,
	   amperionifOutErrors
	      Counter32,
	   amperionifOutQLen
	      Gauge32,
	   amperionifSpecific
	      OBJECT IDENTIFIER,
	   amperionWirelessConfigEssid
	      DisplayString,
	   amperionWirelessConfigMode
	      INTEGER,
	   amperionWirelessConfigChanFreq
	      Unsigned32,
	   amperionWirelessConfigKey
	      DisplayString,
	   amperionWirelessConfigWifType
	      INTEGER,
	   amperionWirelessLinkQuality
	      Unsigned32,
	   amperionWirelessSignalLevel
	      Unsigned32,
	   amperionWirelessNoiseLevel
	      Unsigned32,
	   amperionWirelessActivate
	      TruthValue,
	   amperionWirelessConfigBitRate
	      Integer32,
	   amperionWirelessConfigWDSPeer
	      DisplayString 
	}

amperionifDescr OBJECT-TYPE
	SYNTAX DisplayString(SIZE(0..255))
	MAX-ACCESS read-only
	STATUS current
	DESCRIPTION
		"A textual string containing information about the
		interface.  This string should include the name of
		the manufacturer, the product name and the version
		of the hardware interface."
	DEFVAL { "none" }
	::= { amperionifEntry 2 }


amperionifType  OBJECT-TYPE
	SYNTAX INTEGER { other(1), regular1822(2), hdh1822(3), ddnx25(4), rfc877x25(5), ethernetcsmacd(6), iso88023csmacd(7), iso88024tokenBus(8), iso88025tokenRing(9), iso88026man(10), starLan(11), proteon10Mbit(12), proteon80Mbit(13), hyperchannel(14), fddi(15), lapb(16), sdlc(17), ds1(18), e1(19), basicISDN(20), primaryISDN(21), propPointToPointSerial(22), ppp(23), softwareLoopback(24), eon(25), ethernet3Mbit(26), nsip(27), slip(28), ultra(29), ds3(30), sip(31), framerelay(32), ieee80211b(33), ieee80211a(34), ieee80211g(35) } 
	MAX-ACCESS read-only
	STATUS current
	DESCRIPTION
		"The type of interface, distinguished according to
		the physical/link protocol(s) immediately `below'
		the network layer in the protocol stack."
	::= { amperionifEntry 3 }


amperionifMtu   OBJECT-TYPE
	SYNTAX Integer32
	MAX-ACCESS read-only
	STATUS current
	DESCRIPTION
		"The size of the largest datagram which can be
		sent/received on the interface, specified in
		octets.  For interfaces that are used for
		transmitting network datagrams, this is the size
		of the largest network datagram that can be sent
		on the interface."
	::= { amperionifEntry 4 }


amperionifSpeed OBJECT-TYPE
	SYNTAX Gauge32
	MAX-ACCESS read-only
	STATUS current
	DESCRIPTION
		"An estimate of the interface's current bandwidth
		in bits per second.  For interfaces which do not
		vary in bandwidth or for those where no accurate
		estimation can be made, this object should contain
		the nominal bandwidth."
	::= { amperionifEntry 5 }


amperionifPhysAddress OBJECT-TYPE
	SYNTAX DisplayString(SIZE(0..255))
	MAX-ACCESS read-only
	STATUS current
	DESCRIPTION
		"The interface's address at the protocol layer
		immediately `below' the network layer in the
		protocol stack.  For interfaces which do not have
		such an address (e.g., a serial line), this object
		should contain an octet string of zero length."
	DEFVAL { "none" }
	::= { amperionifEntry 6 }


amperionifAdminStatus OBJECT-TYPE
	SYNTAX INTEGER { up(1), down(2), testing(3) } 
	MAX-ACCESS read-write
	STATUS current
	DESCRIPTION
		"The desired state of the interface.  The
		testing(3) state indicates that no operational
		packets can be passed."
	::= { amperionifEntry 7 }


amperionifOperStatus OBJECT-TYPE
	SYNTAX INTEGER { up(1), down(2), testing(3) } 
	MAX-ACCESS read-only
	STATUS current
	DESCRIPTION
		"The current operational state of the interface.
		The testing(3) state indicates that no operational
		packets can be passed."
	::= { amperionifEntry 8 }


amperionifLastChange OBJECT-TYPE
	SYNTAX TimeTicks
	MAX-ACCESS read-only
	STATUS current
	DESCRIPTION
		"The value of sysUpTime at the time the interface
		entered its current operational state.  If the
		current state was entered prior to the last re-
		initialization of the local network management
		subsystem, then this object contains a zero
		value."
	::= { amperionifEntry 9 }


amperionifInOctets OBJECT-TYPE
	SYNTAX Counter32
	MAX-ACCESS read-only
	STATUS current
	DESCRIPTION
		"The total number of octets received on the
		interface, including framing characters."
	::= { amperionifEntry 10 }


amperionifInUcastPkts OBJECT-TYPE
	SYNTAX Counter32
	MAX-ACCESS read-only
	STATUS current
	DESCRIPTION
		"The number of subnetwork-unicast packets
		delivered to a higher-layer protocol."
	::= { amperionifEntry 11 }


amperionifInNUcastPkts OBJECT-TYPE
	SYNTAX Counter32
	MAX-ACCESS read-only
	STATUS current
	DESCRIPTION
		"The number of non-unicast (i.e., subnetwork-
		broadcast or subnetwork-multicast) packets
		delivered to a higher-layer protocol."
	::= { amperionifEntry 12 }


amperionifInDiscards OBJECT-TYPE
	SYNTAX Counter32
	MAX-ACCESS read-only
	STATUS current
	DESCRIPTION
		"The number of inbound packets which were chosen
		to be discarded even though no errors had been
		detected to prevent their being deliverable to a
		higher-layer protocol.  One possible reason for
		discarding such a packet could be to free up
		buffer space."
	::= { amperionifEntry 13 }


amperionifInErrors OBJECT-TYPE
	SYNTAX Counter32
	MAX-ACCESS read-only
	STATUS current
	DESCRIPTION
		"The number of inbound packets that contained
		errors preventing them from being deliverable to a
		higher-layer protocol."
	::= { amperionifEntry 14 }


amperionifInUnknownProtos OBJECT-TYPE
	SYNTAX Counter32
	MAX-ACCESS read-only
	STATUS current
	DESCRIPTION
		"The number of packets received via the interface
		which were discarded because of an unknown or
		unsupported protocol."
	::= { amperionifEntry 15 }


amperionifOutOctets OBJECT-TYPE
	SYNTAX Counter32
	MAX-ACCESS read-only
	STATUS current
	DESCRIPTION
		"The total number of octets transmitted out of the
		interface, including framing characters."
	::= { amperionifEntry 16 }


amperionifOutUcastPkts OBJECT-TYPE
	SYNTAX Counter32
	MAX-ACCESS read-only
	STATUS current
	DESCRIPTION
		"The total number of packets that higher-level
		protocols requested be transmitted to a
		subnetwork-unicast address, including those that
		were discarded or not sent."
	::= { amperionifEntry 17 }


amperionifOutNUcastPkts OBJECT-TYPE
	SYNTAX Counter32
	MAX-ACCESS read-only
	STATUS current
	DESCRIPTION
		"The total number of packets that higher-level
		protocols requested be transmitted to a non-
		unicast (i.e., a subnetwork-broadcast or
		subnetwork-multicast) address, including those
		that were discarded or not sent."
	::= { amperionifEntry 18 }


amperionifOutDiscards OBJECT-TYPE
	SYNTAX Counter32
	MAX-ACCESS read-only
	STATUS current
	DESCRIPTION
		"The number of outbound packets which were chosen
		to be discarded even though no errors had been
		detected to prevent their being transmitted.  One
		possible reason for discarding such a packet could
		be to free up buffer space."
	::= { amperionifEntry 19 }


amperionifOutErrors OBJECT-TYPE
	SYNTAX Counter32
	MAX-ACCESS read-only
	STATUS current
	DESCRIPTION
		"The number of outbound packets that could not be
		transmitted because of errors."
	::= { amperionifEntry 20 }


amperionifOutQLen OBJECT-TYPE
	SYNTAX Gauge32
	MAX-ACCESS read-only
	STATUS current
	DESCRIPTION
		"The length of the output packet queue (in
		packets)."
	::= { amperionifEntry 21 }


amperionifSpecific OBJECT-TYPE
	SYNTAX OBJECT IDENTIFIER
	MAX-ACCESS read-only
	STATUS current
	DESCRIPTION
		"A reference to MIB definitions specific to the
		particular media being used to realize the
		interface.  For example, if the interface is
		realized by an ethernet, then the value of this
		object refers to a document defining objects
		specific to ethernet.  If this information is not
		present, its value should be set to the OBJECT
		IDENTIFIER { 0 0 }, which is a syntatically valid
		object identifier, and any conformant
		implementation of ASN.1 and BER must be able to
		generate and recognize this value."
	::= { amperionifEntry 22 }


amperionWirelessConfigEssid OBJECT-TYPE
	SYNTAX DisplayString(SIZE(0..33))
	MAX-ACCESS read-write
	STATUS current
	DESCRIPTION
		"802.11 network name"
	DEFVAL { "none" }
	::= { amperionifEntry 23 }


amperionWirelessConfigMode OBJECT-TYPE
	SYNTAX INTEGER { none(0), adhoc(1), managed(2), master(3), repeater(4) } 
	MAX-ACCESS read-write
	STATUS current
	DESCRIPTION
		"802.11 station operational mode"
	DEFVAL { master }
	::= { amperionifEntry 24 }


amperionWirelessConfigChanFreq OBJECT-TYPE
	SYNTAX Unsigned32
	MAX-ACCESS read-write
	STATUS current
	DESCRIPTION
		"802.11 Channel ID"
	::= { amperionifEntry 25 }


amperionWirelessConfigKey OBJECT-TYPE
	SYNTAX DisplayString(SIZE(0..33))
	MAX-ACCESS read-write
	STATUS current
	DESCRIPTION
		"802.11 encryption or scrambling keys and encryption mode."
	DEFVAL { "none" }
	::= { amperionifEntry 26 }


amperionWirelessConfigWifType OBJECT-TYPE
	SYNTAX INTEGER { wtype11a(1), wtype11b(2), wtype11g(3) } 
	MAX-ACCESS read-write
	STATUS current
	DESCRIPTION
		"802.11 protocol type."
	DEFVAL { wtype11b }
	::= { amperionifEntry 30 }


amperionWirelessLinkQuality OBJECT-TYPE
	SYNTAX Unsigned32
	MAX-ACCESS read-only
	STATUS current
	DESCRIPTION
		"A measure of how good the received signal is."
	DEFVAL { 0 }
	::= { amperionifEntry 27 }


amperionWirelessSignalLevel OBJECT-TYPE
	SYNTAX Unsigned32
	MAX-ACCESS read-only
	STATUS current
	DESCRIPTION
		"Received signal strength (how strong the received signal is)."
	DEFVAL { 0 }
	::= { amperionifEntry 28 }


amperionWirelessNoiseLevel OBJECT-TYPE
	SYNTAX Unsigned32
	MAX-ACCESS read-only
	STATUS current
	DESCRIPTION
		"Background noise level (when no packet is transmited)."
	DEFVAL { 0 }
	::= { amperionifEntry 29 }


amperionWirelessActivate OBJECT-TYPE
	SYNTAX TruthValue
	MAX-ACCESS read-write
	STATUS current
	DESCRIPTION
		"Command to activate 802.11 parameters on demand."
	DEFVAL { true }
	::= { amperionifEntry 1 }


amperionWirelessConfigBitRate OBJECT-TYPE
	SYNTAX Integer32
	MAX-ACCESS read-write
	STATUS current
	DESCRIPTION
		"The bit transmission rate in Megabits per second. (0 = autonegotiated)"
	DEFVAL { 0 }
	::= { amperionifEntry 31 }


amperionWirelessConfigWDSPeer OBJECT-TYPE
	SYNTAX DisplayString(SIZE(0..80))
	MAX-ACCESS read-write
	STATUS current
	DESCRIPTION
		"The MAC address of any WDS peer."
	DEFVAL { "0" }
	::= { amperionifEntry 32 }


-- *** End Table amperionifTable *****************************
amperionWireless OBJECT IDENTIFIER ::= { amperion 6 }

-- *** Begin Table ampMacAcceptTable ***************************
ampMacAcceptTable OBJECT-TYPE
	SYNTAX SEQUENCE OF AmpMacAcceptEntry
	MAX-ACCESS not-accessible
	STATUS current
	DESCRIPTION
		"List of Mac address to be accepted"
	::= { amperionWireless 3 }


ampMacAcceptEntry OBJECT-TYPE
	SYNTAX AmpMacAcceptEntry
	MAX-ACCESS not-accessible
	STATUS current
	DESCRIPTION
		"Row of table ampMacAcceptTable"
	INDEX { macAcceptTableIndex }
	::= { ampMacAcceptTable 1 }


AmpMacAcceptEntry ::= 
	SEQUENCE {
	   macAcceptTableIndex
	      Unsigned32,
	   macAcceptTableRowStatus
	      RowStatus,
	   macAcceptTableMacAddress
	      DisplayString,
	   macAcceptTableWirelessIf
	      Unsigned32 
	}

macAcceptTableIndex OBJECT-TYPE
	SYNTAX Unsigned32(1..65536)
	MAX-ACCESS not-accessible
	STATUS current
	DESCRIPTION
		"Unique index"
	::= { ampMacAcceptEntry 3 }


macAcceptTableRowStatus OBJECT-TYPE
	SYNTAX RowStatus
	MAX-ACCESS read-create
	STATUS current
	DESCRIPTION
		"Row Status"
	DEFVAL { createAndGo }
	::= { ampMacAcceptEntry 2 }


macAcceptTableMacAddress OBJECT-TYPE
	SYNTAX DisplayString(SIZE(0..17))
	MAX-ACCESS read-create
	STATUS current
	DESCRIPTION
		"Mac address to be accepted"
	DEFVAL { "00:00:00:00:00:00" }
	::= { ampMacAcceptEntry 1 }


macAcceptTableWirelessIf OBJECT-TYPE
	SYNTAX Unsigned32
	MAX-ACCESS read-create
	STATUS current
	DESCRIPTION
		"The wireless interface (e.g. wlan0) that ACL table is applied to."
	DEFVAL { 0 }
	::= { ampMacAcceptEntry 4 }


-- *** End Table ampMacAcceptTable *****************************

accessControlStatus OBJECT-TYPE
	SYNTAX INTEGER { disable(1), enable(2) } 
	MAX-ACCESS read-write
	STATUS current
	DESCRIPTION
		"Status of the access control table"
	DEFVAL { disable }
	::= { amperionWireless 1 }


-- *** Begin Table amperionipAddrTable ***************************
amperionipAddrTable OBJECT-TYPE
	SYNTAX SEQUENCE OF AmperionipAddrEntry
	MAX-ACCESS not-accessible
	STATUS current
	DESCRIPTION
		"The table of addressing information relevant to
		this entity's IP addresses."
	::= { amperion 7 }


amperionipAddrEntry OBJECT-TYPE
	SYNTAX AmperionipAddrEntry
	MAX-ACCESS not-accessible
	STATUS current
	DESCRIPTION
		"Row of table amperionipAddrTable"
	INDEX { amperionipAdEntAddr }
	::= { amperionipAddrTable 1 }


AmperionipAddrEntry ::= 
	SEQUENCE {
	   amperionipAdEntAddr
	      IpAddress,
	   amperionipAdEntIfName
	      DisplayString,
	   amperionipAdEntNetMask
	      IpAddress,
	   amperionipAdEntBcastAddr
	      Integer32,
	   amperionipAdEntReasmMaxSize
	      Integer32,
	   amperionipAdEntActivate
	      TruthValue,
	   amperionipAdRowStatus
	      RowStatus 
	}

amperionipAdEntAddr OBJECT-TYPE
	SYNTAX IpAddress
	MAX-ACCESS not-accessible
	STATUS current
	DESCRIPTION
		"The IP address to which this entry's addressing
		information pertains."
	::= { amperionipAddrEntry 1 }


amperionipAdEntIfName OBJECT-TYPE
	SYNTAX DisplayString(SIZE(1..80))
	MAX-ACCESS read-only
	STATUS current
	DESCRIPTION
		"The name which uniquely identifies the
		interface to which this entry is applicable."
	::= { amperionipAddrEntry 2 }


amperionipAdEntNetMask OBJECT-TYPE
	SYNTAX IpAddress
	MAX-ACCESS read-only
	STATUS current
	DESCRIPTION
		"The subnet mask associated with the IP address of
		this entry.  The value of the mask is an IP
		address with all the network bits set to 1 and all
		the hosts bits set to 0."
	::= { amperionipAddrEntry 3 }


amperionipAdEntBcastAddr OBJECT-TYPE
	SYNTAX Integer32
	MAX-ACCESS read-only
	STATUS current
	DESCRIPTION
		"The value of the least-significant bit in the IP
		broadcast address used for sending datagrams on
		the (logical) interface associated with the IP
		address of this entry.  For example, when the
		Internet standard all-ones broadcast address is
		used, the value will be 1.  This value applies to
		both the subnet and network broadcasts addresses
		used by the entity on this (logical) interface."
	::= { amperionipAddrEntry 4 }


amperionipAdEntReasmMaxSize OBJECT-TYPE
	SYNTAX Integer32(0..65535)
	MAX-ACCESS read-only
	STATUS current
	DESCRIPTION
		"The size of the largest IP datagram which this
		entity can re-assemble from incoming IP fragmented
		datagrams received on this interface."
	::= { amperionipAddrEntry 5 }


amperionipAdEntActivate OBJECT-TYPE
	SYNTAX TruthValue
	MAX-ACCESS read-create
	STATUS current
	DESCRIPTION
		"Command to activate the new IP address/netmask on demand."
	DEFVAL { true }
	::= { amperionipAddrEntry 7 }


amperionipAdRowStatus OBJECT-TYPE
	SYNTAX RowStatus
	MAX-ACCESS read-create
	STATUS current
	DESCRIPTION
		"Row status"
	::= { amperionipAddrEntry 6 }


-- *** End Table amperionipAddrTable *****************************
qualityOfService OBJECT IDENTIFIER ::= { amperion 8 }

serviceClassA   OBJECT-TYPE
	SYNTAX Unsigned32(64..65536)
	MAX-ACCESS read-write
	STATUS current
	DESCRIPTION
		"Service Class A (Bandwidth in Kbps)"
	DEFVAL { 1024 }
	::= { qualityOfService 1 }


serviceClassB   OBJECT-TYPE
	SYNTAX Unsigned32(64..65536)
	MAX-ACCESS read-write
	STATUS current
	DESCRIPTION
		"Service Class B (Bandwidth in Kbps)"
	DEFVAL { 512 }
	::= { qualityOfService 2 }


serviceClassC   OBJECT-TYPE
	SYNTAX Unsigned32(64..65536)
	MAX-ACCESS read-write
	STATUS current
	DESCRIPTION
		"Service Class C (Bandwidth in Kbps)"
	DEFVAL { 256 }
	::= { qualityOfService 3 }


serviceClassD   OBJECT-TYPE
	SYNTAX Unsigned32(64..65536)
	MAX-ACCESS read-write
	STATUS current
	DESCRIPTION
		"Service Class D (Bandwidth in Kbps)"
	DEFVAL { 128 }
	::= { qualityOfService 4 }


-- *** Begin Table subscriberTable ***************************
subscriberTable OBJECT-TYPE
	SYNTAX SEQUENCE OF SubscriberEntry
	MAX-ACCESS not-accessible
	STATUS current
	DESCRIPTION
		"List of subscribers"
	::= { qualityOfService 5 }


subscriberEntry OBJECT-TYPE
	SYNTAX SubscriberEntry
	MAX-ACCESS not-accessible
	STATUS current
	DESCRIPTION
		"Row of table subscriberTable"
	INDEX { index }
	::= { subscriberTable 1 }


SubscriberEntry ::= 
	SEQUENCE {
	   index
	      Unsigned32,
	   name
	      DisplayString,
	   ipAddress
	      IpAddress,
	   macAddress
	      DisplayString,
	   serviceClass
	      INTEGER,
	   rowStatus
	      RowStatus 
	}

index           OBJECT-TYPE
	SYNTAX Unsigned32(1..65536)
	MAX-ACCESS not-accessible
	STATUS current
	DESCRIPTION
		"Subscriber unique identification"
	::= { subscriberEntry 1 }


name            OBJECT-TYPE
	SYNTAX DisplayString(SIZE(0..32))
	MAX-ACCESS read-create
	STATUS current
	DESCRIPTION
		"Subscriber Name"
	DEFVAL { "none" }
	::= { subscriberEntry 2 }


ipAddress       OBJECT-TYPE
	SYNTAX IpAddress
	MAX-ACCESS read-create
	STATUS current
	DESCRIPTION
		"Subscriber IP address"
	DEFVAL { '0'h }
	::= { subscriberEntry 3 }


macAddress      OBJECT-TYPE
	SYNTAX DisplayString(SIZE(0..17))
	MAX-ACCESS read-create
	STATUS current
	DESCRIPTION
		"Subscriber MAC address"
	DEFVAL { "00:00:00:00:00:00" }
	::= { subscriberEntry 4 }


serviceClass    OBJECT-TYPE
	SYNTAX INTEGER { none(0), classA(1), classB(2), classC(3), classD(4) } 
	MAX-ACCESS read-create
	STATUS current
	DESCRIPTION
		"Subscriber Server Class"
	DEFVAL { none }
	::= { subscriberEntry 5 }


rowStatus       OBJECT-TYPE
	SYNTAX RowStatus
	MAX-ACCESS read-create
	STATUS current
	DESCRIPTION
		"A special field used to create new rows."
	DEFVAL { createAndGo }
	::= { subscriberEntry 6 }


-- *** End Table subscriberTable *****************************

upstreamDownstreamRatio OBJECT-TYPE
	SYNTAX DisplayString(SIZE(1..32))
	MAX-ACCESS read-write
	STATUS current
	DESCRIPTION
		"Upstream bandwidth to downstream bandwidth ratio"
	DEFVAL { "1:3" }
	::= { qualityOfService 6 }


qosStatus       OBJECT-TYPE
	SYNTAX INTEGER { disable(1), enable(2) } 
	MAX-ACCESS read-write
	STATUS current
	DESCRIPTION
		"Enable or disable status of Qos"
	DEFVAL { disable }
	::= { qualityOfService 7 }

afe             OBJECT IDENTIFIER ::= { amperion 9 }
afeExtractor    OBJECT IDENTIFIER ::= { afe 1 }

afeExtTxGain    OBJECT-TYPE
	SYNTAX Integer32
	MAX-ACCESS read-write
	STATUS current
	DESCRIPTION
		"afeExtTxGain"
	::= { afeExtractor 1 }


afeExtRxGain    OBJECT-TYPE
	SYNTAX Integer32
	MAX-ACCESS read-write
	STATUS current
	DESCRIPTION
		"afeExtRxGain"
	::= { afeExtractor 2 }


afeExtDownstream OBJECT-TYPE
	SYNTAX DisplayString(SIZE(3..4))
	MAX-ACCESS read-write
	STATUS current
	DESCRIPTION
		"afeExtDownstream"
	::= { afeExtractor 3 }


afeExtUpstream  OBJECT-TYPE
	SYNTAX DisplayString(SIZE(3..4))
	MAX-ACCESS read-write
	STATUS current
	DESCRIPTION
		"afeExtUpstream"
	::= { afeExtractor 4 }


afeExtActivate  OBJECT-TYPE
	SYNTAX TruthValue
	MAX-ACCESS read-write
	STATUS current
	DESCRIPTION
		"afeExtActivate"
	DEFVAL { true }
	::= { afeExtractor 5 }

afeInjector     OBJECT IDENTIFIER ::= { afe 2 }

afeInjTxGain    OBJECT-TYPE
	SYNTAX Integer32
	MAX-ACCESS read-write
	STATUS current
	DESCRIPTION
		"afeInjTxGain"
	::= { afeInjector 1 }


afeInjRxGain    OBJECT-TYPE
	SYNTAX Integer32
	MAX-ACCESS read-write
	STATUS current
	DESCRIPTION
		"afeInjRxGain"
	::= { afeInjector 2 }


afeInjDownstream OBJECT-TYPE
	SYNTAX DisplayString(SIZE(3..4))
	MAX-ACCESS read-write
	STATUS current
	DESCRIPTION
		"afeInjDownstream"
	::= { afeInjector 3 }


afeInjUpstream  OBJECT-TYPE
	SYNTAX DisplayString(SIZE(3..4))
	MAX-ACCESS read-write
	STATUS current
	DESCRIPTION
		"afeInjUpstream"
	::= { afeInjector 4 }


afeInjActivate  OBJECT-TYPE
	SYNTAX TruthValue
	MAX-ACCESS read-write
	STATUS current
	DESCRIPTION
		"afeInjActivate"
	DEFVAL { true }
	::= { afeInjector 5 }

amperionRoutes  OBJECT IDENTIFIER ::= { amperion 10 }

-- *** Begin Table amperionRouteTable ***************************
amperionRouteTable OBJECT-TYPE
	SYNTAX SEQUENCE OF AmperionRouteEntry
	MAX-ACCESS not-accessible
	STATUS current
	DESCRIPTION
		"This entity's IP Routing table."
	::= { amperionRoutes 1 }


amperionRouteEntry OBJECT-TYPE
	SYNTAX AmperionRouteEntry
	MAX-ACCESS not-accessible
	STATUS current
	DESCRIPTION
		"Row of table amperionRouteTable"
	INDEX { ipRouteDest }
	::= { amperionRouteTable 1 }


AmperionRouteEntry ::= 
	SEQUENCE {
	   ipRouteDest
	      IpAddress,
	   ipRouteIfIndex
	      Integer32,
	   ipRouteMetric1
	      Integer32,
	   ipRouteMetric2
	      Integer32,
	   ipRouteMetric3
	      Integer32,
	   ipRouteMetric4
	      Integer32,
	   ipRouteNextHop
	      IpAddress,
	   ipRouteType
	      INTEGER,
	   ipRouteProto
	      INTEGER,
	   ipRouteAge
	      Integer32,
	   ipRouteMask
	      IpAddress,
	   ipRouteMetric5
	      Integer32,
	   ipRouteInfo
	      OBJECT IDENTIFIER,
	   ipDefRouteActivate
	      TruthValue 
	}

ipRouteDest     OBJECT-TYPE
	SYNTAX IpAddress
	MAX-ACCESS read-only
	STATUS current
	DESCRIPTION
		"The destination IP address of this route.  An
		entry with a value of 0.0.0.0 is considered a
		default route.  Multiple routes to a single
		 destination can appear in the table, but access to
		 such multiple entries is dependent on the table-
		 access mechanisms defined by the network
		                      management protocol in use."
	::= { amperionRouteEntry 1 }


ipRouteIfIndex  OBJECT-TYPE
	SYNTAX Integer32
	MAX-ACCESS read-write
	STATUS current
	DESCRIPTION
		"The index value which uniquely identifies the
		local interface through which the next hop of this
		route should be reached.  The interface identified
		by a particular value of this index is the same
		interface as identified by the same value of
		ifIndex."
	::= { amperionRouteEntry 2 }


ipRouteMetric1  OBJECT-TYPE
	SYNTAX Integer32
	MAX-ACCESS read-write
	STATUS current
	DESCRIPTION
		"The primary routing metric for this route.  The
		semantics of this metric are determined by the
		routing-protocol specified in the route's
		ipRouteProto value.  If this metric is not used,
		its value should be set to -1."
	::= { amperionRouteEntry 3 }


ipRouteMetric2  OBJECT-TYPE
	SYNTAX Integer32
	MAX-ACCESS read-write
	STATUS current
	DESCRIPTION
		"An alternate routing metric for this route.  The
		semantics of this metric are determined by the
		routing-protocol specified in the route's
		ipRouteProto value.  If this metric is not used,
		its value should be set to -1."
	::= { amperionRouteEntry 4 }


ipRouteMetric3  OBJECT-TYPE
	SYNTAX Integer32
	MAX-ACCESS read-write
	STATUS current
	DESCRIPTION
		"An alternate routing metric for this route.  The
		semantics of this metric are determined by the
		routing-protocol specified in the route's
		ipRouteProto value.  If this metric is not used,
		its value should be set to -1."
	::= { amperionRouteEntry 5 }


ipRouteMetric4  OBJECT-TYPE
	SYNTAX Integer32
	MAX-ACCESS read-write
	STATUS current
	DESCRIPTION
		"An alternate routing metric for this route.  The
		semantics of this metric are determined by the
		routing-protocol specified in the route's
		ipRouteProto value.  If this metric is not used,
		its value should be set to -1."
	::= { amperionRouteEntry 6 }


ipRouteNextHop  OBJECT-TYPE
	SYNTAX IpAddress
	MAX-ACCESS read-write
	STATUS current
	DESCRIPTION
		"The IP address of the next hop of this route.
		(In the case of a route bound to an interface
		which is realized via a broadcast media, the value
		of this field is the agent's IP address on that
		interface.)"
	::= { amperionRouteEntry 7 }


ipRouteType     OBJECT-TYPE
	SYNTAX INTEGER { other(1), invalid(2), direct(3), indirect(4) } 
	MAX-ACCESS read-only
	STATUS current
	DESCRIPTION
		"The type of route.  Note that the values
		direct(3) and indirect(4) refer to the notion of
		direct and indirect routing in the IP
		architecture.
		
		Setting this object to the value invalid(2) has
		the effect of invalidating the corresponding entry
		in the ipRouteTable object.  That is, it
		effectively dissasociates the destination
		identified with said entry from the route
		identified with said entry.  It is an
		implementation-specific matter as to whether the
		agent removes an invalidated entry from the table.
		Accordingly, management stations must be prepared
		to receive tabular information from agents that
		corresponds to entries not currently in use.
		Proper interpretation of such entries requires
		examination of the relevant ipRouteType object."
	DEFVAL { direct }
	::= { amperionRouteEntry 8 }


ipRouteProto    OBJECT-TYPE
	SYNTAX INTEGER { other(1), local(2), netmgt(3), icmp(4), egp(5), ggp(6), hello(7), rip(8), isis(9), esis(10), ciscoIgrp(11), bbnSpfIgp(12), ospf(13), bgp(14) } 
	MAX-ACCESS read-only
	STATUS current
	DESCRIPTION
		"The routing mechanism via which this route was
		learned.  Inclusion of values for gateway routing
		protocols is not intended to imply that hosts
		should support those protocols."
	::= { amperionRouteEntry 9 }


ipRouteAge      OBJECT-TYPE
	SYNTAX Integer32
	MAX-ACCESS read-write
	STATUS current
	DESCRIPTION
		"The number of seconds since this route was last
		updated or otherwise determined to be correct.
		Note that no semantics of `too old' can be implied
		except through knowledge of the routing protocol
		by which the route was learned."
	::= { amperionRouteEntry 10 }


ipRouteMask     OBJECT-TYPE
	SYNTAX IpAddress
	MAX-ACCESS read-write
	STATUS current
	DESCRIPTION
		"Indicate the mask to be logical-ANDed with the
		destination address before being compared to the
		value in the ipRouteDest field.  For those systems
		that do not support arbitrary subnet masks, an
		agent constructs the value of the ipRouteMask by
		determining whether the value of the correspondent
		ipRouteDest field belong to a class-A, B, or C
		network, and then using one of:
		
		                             mask           network
		                           255.0.0.0      class-A
		                           255.255.0.0    class-B
		                           255.255.255.0  class-C
		
		If the value of the ipRouteDest is 0.0.0.0 (a
		default route), then the mask value is also
		0.0.0.0.  It should be noted that all IP routing
		subsystems implicitly use this mechanism."
	::= { amperionRouteEntry 11 }


ipRouteMetric5  OBJECT-TYPE
	SYNTAX Integer32
	MAX-ACCESS read-write
	STATUS current
	DESCRIPTION
		"An alternate routing metric for this route.  The
		semantics of this metric are determined by the
		routing-protocol specified in the route's
		ipRouteProto value.  If this metric is not used,
		its value should be set to -1."
	::= { amperionRouteEntry 12 }


ipRouteInfo     OBJECT-TYPE
	SYNTAX OBJECT IDENTIFIER
	MAX-ACCESS read-only
	STATUS current
	DESCRIPTION
		"A reference to MIB definitions specific to the
		particular routing protocol which is responsible
		for this route, as determined by the value
		specified in the route's ipRouteProto value.  If
		this information is not present, its value should
		be set to the OBJECT IDENTIFIER { 0 0 }, which is
		a syntatically valid object identifier, and any
		conformant implementation of ASN.1 and BER must be
		able to generate and recognize this value."
	::= { amperionRouteEntry 13 }


ipDefRouteActivate OBJECT-TYPE
	SYNTAX TruthValue
	MAX-ACCESS read-write
	STATUS current
	DESCRIPTION
		"Command to activate the new default route."
	DEFVAL { true }
	::= { amperionRouteEntry 14 }


-- *** End Table amperionRouteTable *****************************
plc             OBJECT IDENTIFIER ::= { amperion 11 }
plcExtractor    OBJECT IDENTIFIER ::= { plc 1 }

plcExtTxGain    OBJECT-TYPE
	SYNTAX Integer32(0..10)
	MAX-ACCESS read-write
	STATUS current
	DESCRIPTION
		"plcExtTxGain"
	::= { plcExtractor 1 }


plcExtRxGain    OBJECT-TYPE
	SYNTAX Integer32(0..10)
	MAX-ACCESS read-write
	STATUS current
	DESCRIPTION
		"plcExtRxGain"
	::= { plcExtractor 2 }

plcInjector     OBJECT IDENTIFIER ::= { plc 2 }

plcInjTxGain    OBJECT-TYPE
	SYNTAX Integer32(0..10)
	MAX-ACCESS read-write
	STATUS current
	DESCRIPTION
		"plcInjTxGain"
	::= { plcInjector 1 }


plcInjRxGain    OBJECT-TYPE
	SYNTAX Integer32(0..10)
	MAX-ACCESS read-write
	STATUS current
	DESCRIPTION
		"plcInjRxGain"
	::= { plcInjector 2 }


-- *** Begin Trap plcUp           ****************************
plcUp           NOTIFICATION-TYPE
	OBJECTS {
	   plcEventDescription
	}
	STATUS current
	DESCRIPTION
		"Extractor's PLC interface came up"
	::= { plc 3 }

-- *** End Trap plcUp           ******************************

-- *** Begin Trap plcDown         ****************************
plcDown         NOTIFICATION-TYPE
	OBJECTS {
	   plcEventDescription
	}
	STATUS current
	DESCRIPTION
		"Extractor's PLC interface went down"
	::= { plc 4 }

-- *** End Trap plcDown         ******************************

afeCpldResetCount OBJECT-TYPE
	SYNTAX Counter32
	MAX-ACCESS read-only
	STATUS current
	DESCRIPTION
		"afe Cpld Reset Count"
	::= { plc 5 }


plcLossCount    OBJECT-TYPE
	SYNTAX Counter32
	MAX-ACCESS read-only
	STATUS current
	DESCRIPTION
		"plc Loss Count"
	::= { plc 6 }


resetCounters   OBJECT-TYPE
	SYNTAX INTEGER { idle(1), reset(2) } 
	MAX-ACCESS read-write
	STATUS current
	DESCRIPTION
		"reset Counters"
	::= { plc 7 }


-- *** Begin Table optimizationTable ***************************
optimizationTable OBJECT-TYPE
	SYNTAX SEQUENCE OF OptimizationEntry
	MAX-ACCESS not-accessible
	STATUS current
	DESCRIPTION
		"If Injector - 
		   This table contains the frequencies(channels) / gains / 
		    throughput of all the extractors down stream.
		If Extractor -
		   This table should contain frequencies(channels) / gains / 
		    throughput for the the plc segment between this extractor
		    and the injector/repeator upstream."
	::= { plc 8 }


optimizationEntry OBJECT-TYPE
	SYNTAX OptimizationEntry
	MAX-ACCESS not-accessible
	STATUS current
	DESCRIPTION
		"Row of table optimizationTable"
	INDEX { extrIpaddress, extrChannelNumber }
	::= { optimizationTable 1 }


OptimizationEntry ::= 
	SEQUENCE {
	   extrIpaddress
	      IpAddress,
	   extrChannelNumber
	      Integer32,
	   upstreamFreq
	      DisplayString,
	   downstreamFreq
	      DisplayString,
	   rxGain
	      DisplayString,
	   txGain
	      DisplayString,
	   plcThroughput
	      DisplayString,
	   upStreamDownStream
	      INTEGER,
	   gpsInfo
	      DisplayString 
	}

extrIpaddress   OBJECT-TYPE
	SYNTAX IpAddress
	MAX-ACCESS read-only
	STATUS current
	DESCRIPTION
		"extractor's ipaddress"
	::= { optimizationEntry 1 }


extrChannelNumber OBJECT-TYPE
	SYNTAX Integer32
	MAX-ACCESS read-only
	STATUS current
	DESCRIPTION
		"Extractor Channel Number"
	::= { optimizationEntry 2 }


upstreamFreq    OBJECT-TYPE
	SYNTAX DisplayString
	MAX-ACCESS read-only
	STATUS current
	DESCRIPTION
		"Upstream Frequency"
	::= { optimizationEntry 3 }


downstreamFreq  OBJECT-TYPE
	SYNTAX DisplayString
	MAX-ACCESS read-only
	STATUS current
	DESCRIPTION
		"Downstream Frequency"
	::= { optimizationEntry 4 }


rxGain          OBJECT-TYPE
	SYNTAX DisplayString
	MAX-ACCESS read-only
	STATUS current
	DESCRIPTION
		"rxGain setting"
	::= { optimizationEntry 5 }


txGain          OBJECT-TYPE
	SYNTAX DisplayString
	MAX-ACCESS read-only
	STATUS current
	DESCRIPTION
		"Tx Gain Setting"
	::= { optimizationEntry 6 }


plcThroughput   OBJECT-TYPE
	SYNTAX DisplayString
	MAX-ACCESS read-only
	STATUS current
	DESCRIPTION
		"plcThroughput"
	::= { optimizationEntry 7 }


upStreamDownStream OBJECT-TYPE
	SYNTAX INTEGER { upstream(1), downstream(2), unknown(3) } 
	MAX-ACCESS read-only
	STATUS current
	DESCRIPTION
		"This to indicate if this entry pertains to the upstream segment 
		or the downstream segment"
	::= { optimizationEntry 8 }


gpsInfo         OBJECT-TYPE
	SYNTAX DisplayString(SIZE(1..128))
	MAX-ACCESS read-only
	STATUS current
	DESCRIPTION
		"GPS co-ordinates.  Currently this is  a string which means the machine
		just picks up whatever GPS info is defined in it's system group and sends it 
		to the extractor"
	DEFVAL { "none" }
	::= { optimizationEntry 9 }


-- *** End Table optimizationTable *****************************

plcEventDescription OBJECT-TYPE
	SYNTAX DisplayString(SIZE(1..128))
	MAX-ACCESS read-only
	STATUS current
	DESCRIPTION
		"String to be sent in the plc up/down event.  Will contain ip address of the
		unit which just went down or will say 'local system' if current system"
	::= { plc 9 }

tempGroup       OBJECT IDENTIFIER ::= { amperion 12 }

tempFanState    OBJECT-TYPE
	SYNTAX INTEGER { off(0), on(1) } 
	MAX-ACCESS read-only
	STATUS current
	DESCRIPTION
		"The fans may be on or off."
	DEFVAL { off }
	::= { tempGroup 1 }


tempFanTargetTemp OBJECT-TYPE
	SYNTAX Integer32(0..70)
	UNITS "degrees celcius"
	MAX-ACCESS read-write
	STATUS current
	DESCRIPTION
		"The target temperature is the average temperature we would like the 
		system to operate at if possible. It is used to calculate how long the fans 
		should stay on during a cycle which is part of a duty cycle algorithm.
		
		Temperature is in degrees celsius."
	DEFVAL { 25 }
	::= { tempGroup 2 }


tempEventDescription OBJECT-TYPE
	SYNTAX DisplayString(SIZE(1..130))
	MAX-ACCESS read-only
	STATUS current
	DESCRIPTION
		"String to be sent with the temperature trap events."
	::= { tempGroup 5 }


-- *** Begin Trap tempHighWarnLimitTrap ****************************
tempHighWarnLimitTrap NOTIFICATION-TYPE
	OBJECTS {
	   tempEventDescription,
	   tempHighWarnLimit,
	   tempSystemTemp
	}
	STATUS current
	DESCRIPTION
		"The system temperature has exceeded the High Warning threshold."
	::= { tempGroup 4 }

-- *** End Trap tempHighWarnLimitTrap ******************************

-- *** Begin Trap tempHighErrorLimitTrap ****************************
tempHighErrorLimitTrap NOTIFICATION-TYPE
	OBJECTS {
	   tempEventDescription,
	   tempHighErrorLimit,
	   tempSystemTemp
	}
	STATUS current
	DESCRIPTION
		"The system temperature has exceeded the High Error Threshold."
	::= { tempGroup 6 }

-- *** End Trap tempHighErrorLimitTrap ******************************

-- *** Begin Trap tempLowWarnLimitTrap ****************************
tempLowWarnLimitTrap NOTIFICATION-TYPE
	OBJECTS {
	   tempEventDescription,
	   tempLowWarnLimit,
	   tempSystemTemp
	}
	STATUS current
	DESCRIPTION
		"The system temperature has gone below the Low Warning Threshold."
	::= { tempGroup 7 }

-- *** End Trap tempLowWarnLimitTrap ******************************

-- *** Begin Trap tempLowErrorLimitTrap ****************************
tempLowErrorLimitTrap NOTIFICATION-TYPE
	OBJECTS {
	   tempEventDescription,
	   tempLowErrorLimit,
	   tempSystemTemp
	}
	STATUS current
	DESCRIPTION
		"The system temperature has gone below the Low Error Threshold."
	::= { tempGroup 8 }

-- *** End Trap tempLowErrorLimitTrap ******************************

tempHighWarnLimit OBJECT-TYPE
	SYNTAX Integer32(0..150)
	UNITS "degrees Celsius"
	MAX-ACCESS read-write
	STATUS current
	DESCRIPTION
		"The system temperature has exceeded a high temperature warning threshold.
		
		Temperature is in degrees Celsius."
	DEFVAL { 65 }
	::= { tempGroup 3 }


tempHighErrorLimit OBJECT-TYPE
	SYNTAX Integer32(0..150)
	UNITS "degrees Celscius"
	MAX-ACCESS read-write
	STATUS current
	DESCRIPTION
		"The system temperature has exceeded a high temperature error threshold.
		
		Temperature is in degrees Celsius."
	DEFVAL { 100 }
	::= { tempGroup 9 }


tempLowWarnLimit OBJECT-TYPE
	SYNTAX Integer32(-100..60)
	UNITS "degrees Celscius"
	MAX-ACCESS read-write
	STATUS current
	DESCRIPTION
		"The system temperature has gone below a low temperature warning threshold.
		
		Temperature is in degrees Celscius."
	DEFVAL { -10 }
	::= { tempGroup 10 }


tempLowErrorLimit OBJECT-TYPE
	SYNTAX Integer32(-100..60)
	UNITS "degrees Celscius"
	MAX-ACCESS read-write
	STATUS current
	DESCRIPTION
		"The system temperature has gone below the Low Temperature Error Threshold.
		
		The temperature is in degrees Celscius."
	DEFVAL { -30 }
	::= { tempGroup 11 }


tempHighWarnHist OBJECT-TYPE
	SYNTAX Integer32(-10..150)
	UNITS "degrees Celsius"
	MAX-ACCESS read-write
	STATUS current
	DESCRIPTION
		"Hysteresis value for the High Temperature Warning Condition. Once the
		system temperature has reached or exceeded the High Temperature
		Warning threshold, it must go down to or below the Hysteresis temperature
		before sending the trap again.
		
		The hysteresis temperature is in degrees Celcius."
	DEFVAL { 55 }
	::= { tempGroup 12 }


tempHighErrorHist OBJECT-TYPE
	SYNTAX Integer32(-10..150)
	UNITS "degrees Celscius"
	MAX-ACCESS read-write
	STATUS current
	DESCRIPTION
		"Hysteresis value for the High Temperature Error Condition. Once the
		system temperature has reached or exceeded the High Temperature
		Error Threshold, it must go down to or below the Hysteresis temperature
		before sending the trap again.
		
		The hysteresis temperature is in degrees Celcius."
	DEFVAL { 90 }
	::= { tempGroup 13 }


tempLowWarnHist OBJECT-TYPE
	SYNTAX Integer32(-100..60)
	UNITS "degrees Celscius"
	MAX-ACCESS read-write
	STATUS current
	DESCRIPTION
		"Hysteresis value for the Low Temperature Warning Condition. Once the
		system temperature is less than or equal to the LowTemperature Warning 
		threshold, it must go up to or above the Hysteresis temperature
		before sending the trap again.
		
		The hysteresis temperature is in degrees Celcius."
	DEFVAL { 0 }
	::= { tempGroup 14 }


tempLowErrorHist OBJECT-TYPE
	SYNTAX Integer32(-100..60)
	UNITS "degrees Celsius"
	MAX-ACCESS read-write
	STATUS current
	DESCRIPTION
		"Hysteresis value for the Low Temperature Error Condition. Once the
		system temperature is less than or equal to the LowTemperature Error 
		threshold, it must go up to or above the Hysteresis temperature
		before sending the trap again.
		
		The hysteresis temperature is in degrees Celcius."
	DEFVAL { -20 }
	::= { tempGroup 15 }


tempSystemTemp  OBJECT-TYPE
	SYNTAX Integer32
	MAX-ACCESS read-only
	STATUS current
	DESCRIPTION
		"The temperature of the Main Digital Board. The temperature is obtained
		by reading a chip located on the digital board."
	DEFVAL { 0 }
	::= { tempGroup 16 }


END
