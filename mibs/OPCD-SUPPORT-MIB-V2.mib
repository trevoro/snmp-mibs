--
-- OPCD-SUPPORT-MIB-V2
-- Last Modified: Monday, Feb 08, 2009
--


OPCD-SUPPORT-MIB-V2 DEFINITIONS ::= BEGIN


--  OPCD-SUPPORT-MIB:
--    A private enterprise mib for Opencode Support applications.


IMPORTS
	MODULE-IDENTITY, OBJECT-TYPE, NOTIFICATION-TYPE, enterprises	FROM SNMPv2-SMI
	DisplayString							FROM SNMPv2-TC;


opencode-systems MODULE-IDENTITY
    LAST-UPDATED "200703061233Z"  -- March 6, 2007 at 11:20 GMT
    ORGANIZATION
        "Opencode Systems"
    CONTACT-INFO
        "Opencode Systems
        1784 Sofia Bulgaria
        Tsarigradsko shosse 7-mi km
        BIC IZOT 629B


        Internet: http://www.opencode.com/
        E-mail: opencode@opencode.com


        Phone: +359 2 971 83 14
        Fax: +359 2 971 82 31"
    DESCRIPTION
        "Opencode Support"

::= { enterprises 30374 }



--  opencode support  branch: 30374.3
--  opencode support traps branch: 30374.3.1

ocsupport OBJECT IDENTIFIER ::= { opencode-systems 3 }
ocsupport-traps OBJECT IDENTIFIER ::= { ocsupport 1 }
definitions OBJECT IDENTIFIER ::= { ocsupport-traps 0 }
vars OBJECT IDENTIFIER ::= { ocsupport-traps 1 }

--
-- Node definitions






mcr-Host OBJECT-TYPE
	SYNTAX DisplayString (SIZE (0..255))
	MAX-ACCESS accessible-for-notify
	STATUS current
	DESCRIPTION
		"String containing hostname of fault node."
	::= { vars 1 }


mcr-Severity OBJECT-TYPE
	SYNTAX INTEGER{
		critical(1),
		major(2),
		minor(3),
		normal(4),
		warning(5)
	}
	MAX-ACCESS accessible-for-notify
	STATUS mandatory
	DESCRIPTION
		"Alarm severity."
	::= { vars 2 }


mcr-Text OBJECT-TYPE
	SYNTAX DisplayString (SIZE (0..255))
	MAX-ACCESS accessible-for-notify
	STATUS current
	DESCRIPTION
		"String containing text of the alarm."
	::= { vars 3 }
--
-- Traps
--


------------------------------------------------------------------------------------------------


------------------------------------------------------------------------------------------


-- 1.3.6......0.2
mcr-FAN NOTIFICATION-TYPE
		OBJECTS	{ mcr-Host, mcr-Severity, mcr-Text}	
		STATUS	current
		DESCRIPTION	"Fan Failed!!"
		--#SUMMARY   "Alarm on host: $1 (ocsupport applications) :  $3"
		--#CATEGORY  "Error Alarms"
        	--#ARGUMENTS {}
        	--#SEVERITY  WARNING
		::= { definitions 2 }

-- 1.3.6......0.3
mcr-FAN-Canceled NOTIFICATION-TYPE
		OBJECTS	{ mcr-Host, mcr-Severity, mcr-Text}	
		STATUS	current
		DESCRIPTION	"Fan is OK!!"
		--#SUMMARY   "Alarm on host: $1 (ocsupport applications) :  $3"
		--#CATEGORY  "Error Alarms"
        	--#ARGUMENTS {}
        	--#SEVERITY  NORMAL
		::= { definitions 3 }



-- 1.3.6......0.4
mcr-POWER NOTIFICATION-TYPE
		OBJECTS	{ mcr-Host, mcr-Severity, mcr-Text}	
		STATUS	current
		DESCRIPTION	"Power Supply Failed!!"
		--#SUMMARY   "Alarm on host: $1 (ocsupport applications) :  $3"
		--#CATEGORY  "Error Alarms"
        	--#ARGUMENTS {}
        	--#SEVERITY  WARNING
		::= { definitions 4 }


-- 1.3.6......0.5
mcr-POWER-Canceled NOTIFICATION-TYPE
		OBJECTS	{ mcr-Host, mcr-Severity, mcr-Text}	
		STATUS	current
		DESCRIPTION	"Power Supply is OK!!"
		--#SUMMARY   "Alarm on host: $1 (ocsupport applications) :  $3"
		--#CATEGORY  "Error Alarms"
        	--#ARGUMENTS {}
        	--#SEVERITY  NORMAL
		::= { definitions 5 }


-- 1.3.6......0.6
mcr-TEMPERATURE NOTIFICATION-TYPE
		OBJECTS	{ mcr-Host, mcr-Severity, mcr-Text}	
		STATUS	current
		DESCRIPTION	"Temperature alarm!!Possible high temperature for zones on the server."
		--#SUMMARY   "Alarm on host: $1 (ocsupport applications) :  $3"
		--#CATEGORY  "Error Alarms"
        	--#ARGUMENTS {}
        	--#SEVERITY  WARNING
		::= { definitions 6 }


-- 1.3.6......0.7
mcr-TEMPERATURE-Canceled NOTIFICATION-TYPE
		OBJECTS	{ mcr-Host, mcr-Severity, mcr-Text}	
		STATUS	current
		DESCRIPTION	"Temperature is in normal level."
		--#SUMMARY   "Alarm on host: $1 (ocsupport applications) :  $3"
		--#CATEGORY  "Error Alarms"
        	--#ARGUMENTS {}
        	--#SEVERITY  NORMAL
		::= { definitions 7 }


-- 1.3.6......0.8
mcr-HddFreeSpace NOTIFICATION-TYPE
		OBJECTS	{ mcr-Host, mcr-Severity, mcr-Text}	
		STATUS	current
		DESCRIPTION	"Low disk space!!"
		--#SUMMARY   "Alarm on host: $1 (ocsupport applications) :  $3"
		--#CATEGORY  "Error Alarms"
        	--#ARGUMENTS {}
        	--#SEVERITY  WARNING
		::= { definitions 8 }


-- 1.3.6......0.9
mcr-HddFreeSpace-Canceled NOTIFICATION-TYPE
		OBJECTS	{ mcr-Host, mcr-Severity, mcr-Text}	
		STATUS	current
		DESCRIPTION	"Cancel alarm for low disk space."
		--#SUMMARY   "Alarm on host: $1 (ocsupport applications) :  $3"
		--#CATEGORY  "Error Alarms"
        	--#ARGUMENTS {}
        	--#SEVERITY  NORMAL
		::= { definitions 9 }


-- 1.3.6......0.10
mcr-MysqlService NOTIFICATION-TYPE
		OBJECTS	{ mcr-Host, mcr-Severity, mcr-Text}	
		STATUS	current
		DESCRIPTION	"Mysql Service is not accessible!!"
		--#SUMMARY   "Alarm on host: $1 (ocsupport applications) :  $3"
		--#CATEGORY  "Error Alarms"
        	--#ARGUMENTS {}
        	--#SEVERITY  WARNING
		::= { definitions 10 }


-- 1.3.6......0.11
mcr-MysqlService-Canceled NOTIFICATION-TYPE
		OBJECTS	{ mcr-Host, mcr-Severity, mcr-Text}	
		STATUS	current
		DESCRIPTION	"Mysql Service is accessible."
		--#SUMMARY   "Alarm on host: $1 (ocsupport applications) :  $3"
		--#CATEGORY  "Error Alarms"
        	--#ARGUMENTS {}
        	--#SEVERITY  NORMAL
		::= { definitions 11 }


-- 1.3.6......0.12
mcr-DbFloatingIp NOTIFICATION-TYPE
		OBJECTS	{ mcr-Host, mcr-Severity, mcr-Text}	
		STATUS	current
		DESCRIPTION	"USSD DB Floating IP problem!! Possible floating ip down."
		--#SUMMARY   "Alarm on host: $1 (ocsupport applications) :  $3"
		--#CATEGORY  "Error Alarms"
        	--#ARGUMENTS {}
        	--#SEVERITY  WARNING
		::= { definitions 12 }


--1.3.6......0.13
mcr-DbFloatingIp-Canceled NOTIFICATION-TYPE
		OBJECTS	{ mcr-Host, mcr-Severity, mcr-Text}	
		STATUS	current
		DESCRIPTION	"Floating ip is accessible now."
		--#SUMMARY   "Alarm on host: $1 (ocsupport applications) :  $3"
		--#CATEGORY  "Error Alarms"
        	--#ARGUMENTS {}
        	--#SEVERITY  NORMAL
		::= { definitions 13 }

-- 1.3.6......0.14
mcr-FailedEth NOTIFICATION-TYPE
		OBJECTS	{ mcr-Host, mcr-Severity, mcr-Text}	
		STATUS	current
		DESCRIPTION	"Network(ethernet) interface Failure!!"
		--#SUMMARY   "Alarm on host: $1 (ocsupport applications) :  $3"
		--#CATEGORY  "Error Alarms"
        	--#ARGUMENTS {}
        	--#SEVERITY  WARNING
		::= { definitions 14 }


-- 1.3.6......0.15
mcr-FailedEth-Canceled NOTIFICATION-TYPE
		OBJECTS	{ mcr-Host, mcr-Severity, mcr-Text}	
		STATUS	current
		DESCRIPTION	"Failed Network(ethernet) interface is up."
		--#SUMMARY   "Alarm on host: $1 (ocsupport applications) :  $3"
		--#CATEGORY  "Error Alarms"
        	--#ARGUMENTS {}
        	--#SEVERITY  NORMAL
		::= { definitions 15 }



-- 1.3.6......0.16
mcr-UpsStatus NOTIFICATION-TYPE
		OBJECTS	{ mcr-Host, mcr-Severity, mcr-Text}	
		STATUS	current
		DESCRIPTION	"Problem on ups system.Possible main power down."
		--#SUMMARY   "Alarm on host: $1 (ocsupport applications) :  $3"
		--#CATEGORY  "Error Alarms"
        	--#ARGUMENTS {}
        	--#SEVERITY  WARNING
		::= { definitions 16 }

-- 1.3.6......0.17
mcr-UpsStatus-Canceled NOTIFICATION-TYPE
		OBJECTS	{ mcr-Host, mcr-Severity, mcr-Text}	
		STATUS	current
		DESCRIPTION	"Main Power is up.Alarm is canceled."
		--#SUMMARY   "Alarm on host: $1 (ocsupport applications) :  $3"
		--#CATEGORY  "Error Alarms"
        	--#ARGUMENTS {}
        	--#SEVERITY  NORMAL
		::= { definitions 17 }


-- 1.3.6......0.18
mcr-SwitchConnection NOTIFICATION-TYPE
		OBJECTS	{ mcr-Host, mcr-Severity, mcr-Text}	
		STATUS	current
		DESCRIPTION	"No connection to ethernet switch!! Possible network problem with switch."
		--#SUMMARY   "Alarm on host: $1 (ocsupport applications) :  $3"
		--#CATEGORY  "Error Alarms"
        	--#ARGUMENTS {}
        	--#SEVERITY  WARNING
		::= { definitions 18 }

-- 1.3.6......0.19
mcr-SwitchConnection-Canceled NOTIFICATION-TYPE
		OBJECTS	{ mcr-Host, mcr-Severity, mcr-Text}	
		STATUS	current
		DESCRIPTION	"Switch now is up."
		--#SUMMARY   "Alarm on host: $1 (ocsupport applications) :  $3"
		--#CATEGORY  "Error Alarms"
        	--#ARGUMENTS {}
        	--#SEVERITY  NORMAL
		::= { definitions 19 }


-- 1.3.6......0.20
mcr-HddBayCheck NOTIFICATION-TYPE
		OBJECTS	{ mcr-Host, mcr-Severity, mcr-Text}	
		STATUS	current
		DESCRIPTION	"HDD Drive Bay problem detected! Possible problem with failed disk or raid"
		--#SUMMARY   "Alarm on host: $1 (ocsupport applications) :  $3"
		--#CATEGORY  "Error Alarms"
        	--#ARGUMENTS {}
        	--#SEVERITY  WARNING
		::= { definitions 20 }

-- 1.3.6......0.21
mcr-HddBayCheck-Canceled NOTIFICATION-TYPE
		OBJECTS	{ mcr-Host, mcr-Severity, mcr-Text}	
		STATUS	current
		DESCRIPTION	"HDD is ok."
		--#SUMMARY   "Alarm on host: $1 (ocsupport applications) :  $3"
		--#CATEGORY  "Error Alarms"
        	--#ARGUMENTS {}
        	--#SEVERITY  NORMAL
		::= { definitions 21 }



-- 1.3.6......0.22
ss7LinkDown NOTIFICATION-TYPE
		OBJECTS	{ mcr-Host, mcr-Severity, mcr-Text}	
		STATUS	current
		DESCRIPTION	"SS7 link down"
		--#SUMMARY   "Alarm on host: $1 (ocsupport applications) :  $3"
		--#CATEGORY  "Error Alarms"
        	--#ARGUMENTS {}
        	--#SEVERITY  MAJOR
		::= { definitions 22 }

-- 1.3.6......0.23
ss7LinkDown-Canceled NOTIFICATION-TYPE
		OBJECTS	{ mcr-Host, mcr-Severity, mcr-Text}	
		STATUS	current
		DESCRIPTION	"SS7 link/s is/are up now."
		--#SUMMARY   "Alarm on host: $1 (ocsupport applications) :  $3"
		--#CATEGORY  "Error Alarms"
        	--#ARGUMENTS {}
        	--#SEVERITY  NORMAL
		::= { definitions 23 }


-- 1.3.6......0.24
ussdb-RunSlave NOTIFICATION-TYPE
		OBJECTS	{ mcr-Host, mcr-Severity, mcr-Text}	
		STATUS  current
		DESCRIPTION  "Ussdbrowser was started on slave Node!"
		--#SUMMARY   "Alarm on host: $1 (ocsupport applications) :  $3"
		--#CATEGORY  "Error Alarms"
      	--#ARGUMENTS {}
      	--#SEVERITY  CRITICAL
		::= { definitions 24 }


-- 1.3.6......0.25
ussdb-RunSlave-Canceled NOTIFICATION-TYPE
		OBJECTS	{ mcr-Host, mcr-Severity, mcr-Text}	
		STATUS  current
		DESCRIPTION  "Ussdbrowser is running in noramal mode now."
		--#SUMMARY   "Alarm on host: $1 (ocsupport applications) :  $3"
		--#CATEGORY  "Error Alarms"
      	--#ARGUMENTS {}
      	--#SEVERITY  NORMAL
		::= { definitions 25 }

-- 1.3.6......0.26
ussdb-HeartbeatDown NOTIFICATION-TYPE                 
		OBJECTS	{ mcr-Host, mcr-Severity, mcr-Text}	
		STATUS  current
		DESCRIPTION  "Heartbeat is down!"
		--#SUMMARY   "Alarm on host: $1 (ocsupport applications) :  $3"
		--#CATEGORY  "Error Alarms"
      	--#ARGUMENTS {}
      	--#SEVERITY  WARNING
		::= { definitions 26 }

-- 1.3.6......0.27
ussdb-HeartbeatDown-Canceled NOTIFICATION-TYPE                 
		OBJECTS	{ mcr-Host, mcr-Severity, mcr-Text}	
		STATUS  current
		DESCRIPTION  "Heartbeat is down!"
		--#SUMMARY   "Alarm on host: $1 (ocsupport applications) :  $3"
		--#CATEGORY  "Error Alarms"
      	--#ARGUMENTS {}
      	--#SEVERITY  NORMAL
		::= { definitions 27 }

-- 1.3.6......0.28
ussdb-ConnectionDown NOTIFICATION-TYPE
		OBJECTS	{ mcr-Host, mcr-Severity, mcr-Text}	
		STATUS  current
		DESCRIPTION  "USSD Browser floating IP is down on the Master Node!"
		--#SUMMARY   "Alarm on host: $1 (ocsupport applications) :  $3"
		--#CATEGORY  "Error Alarms"
      	--#ARGUMENTS {}
      	--#SEVERITY  WARNING
		::= { definitions 28 }


-- 1.3.6......0.29
ussdb-ConnectionDown-Canceled NOTIFICATION-TYPE
		OBJECTS	{ mcr-Host, mcr-Severity, mcr-Text}	
		STATUS  current
		DESCRIPTION  "USSD Browser floating IP is up."
		--#SUMMARY   "Alarm on host: $1 (ocsupport applications) :  $3"
		--#CATEGORY  "Error Alarms"
      	--#ARGUMENTS {}
      	--#SEVERITY  NORMAL
		::= { definitions 29 }


-- 1.3.6......0.30
ussdb-Switched NOTIFICATION-TYPE                      
		OBJECTS	{ mcr-Host, mcr-Severity, mcr-Text}	
		STATUS  current
		DESCRIPTION  "Ussdbrowser Master has been switched!!"
		--#SUMMARY   "Alarm on host: $1 (ocsupport applications) :  $3"
		--#CATEGORY  "Error Alarms"
      	--#ARGUMENTS {}
      	--#SEVERITY  CRITICAL
		::= { definitions 30 }

-- 1.3.6......0.31
ussdb-Switched-Canceled NOTIFICATION-TYPE                      
		OBJECTS	{ mcr-Host, mcr-Severity, mcr-Text}	
		STATUS  current
		DESCRIPTION  "Ussdbrowser Master has been switched - canceled!!"
		--#SUMMARY   "Alarm on host: $1 (ocsupport applications) :  $3"
		--#CATEGORY  "Error Alarms"
      	--#ARGUMENTS {}
      	--#SEVERITY  NORMAL
		::= { definitions 31 }



-- 1.3.6......0.32
ussdb-AppDown NOTIFICATION-TYPE                        
		OBJECTS	{ mcr-Host, mcr-Severity, mcr-Text}	
		STATUS  current
		DESCRIPTION  "Ussdbrowser Application down!!"
		--#SUMMARY   "Alarm on host: $1 (ocsupport applications) :  $3"
		--#CATEGORY  "Error Alarms"
      	--#ARGUMENTS {}
      	--#SEVERITY  CRITICAL
		::= { definitions 32 }

-- 1.3.6......0.33
ussdb-AppDown-Canceled NOTIFICATION-TYPE                        
		OBJECTS	{ mcr-Host, mcr-Severity, mcr-Text}	
		STATUS  current
		DESCRIPTION  "Ussdbrowser Application is up-Canceled"
		--#SUMMARY   "Alarm on host: $1 (ocsupport applications) :  $3"
		--#CATEGORY  "Error Alarms"
      	--#ARGUMENTS {}
      	--#SEVERITY  NORMAL
		::= { definitions 33 }


-- 1.3.6......0.34
ussdb-DbDown NOTIFICATION-TYPE      
		OBJECTS	{ mcr-Host, mcr-Severity, mcr-Text}	
		STATUS  current
		DESCRIPTION  "Database Down!"
		--#SUMMARY   "Alarm on host: $1 (ocsupport applications) :  $3"
		--#CATEGORY  "Error Alarms"
      	--#ARGUMENTS {}
      	--#SEVERITY  CRITICAL
		::= { definitions 34 }


-- 1.3.6......0.35
ussdb-DbDown-Canceled NOTIFICATION-TYPE      
		OBJECTS	{ mcr-Host, mcr-Severity, mcr-Text}	
		STATUS  current
		DESCRIPTION  "Database is up!"
		--#SUMMARY   "Alarm on host: $1 (ocsupport applications) :  $3"
		--#CATEGORY  "Error Alarms"
      	--#ARGUMENTS {}
      	--#SEVERITY  NORMAL
		::= { definitions 35 }



-- 1.3.6......0.36
mcr-DBbackup NOTIFICATION-TYPE      
		OBJECTS	{ mcr-Host, mcr-Severity, mcr-Text}	
		STATUS  current
		DESCRIPTION  "DB backup problem"
		--#SUMMARY   "Alarm on host: $1 (ocsupport applications) :  $3"
		--#CATEGORY  "Error Alarms"
      	--#ARGUMENTS {}
      	--#SEVERITY  WARNING
		::= { definitions 36 }


-- 1.3.6......0.37
mcr-DBbackup-Canceled NOTIFICATION-TYPE      
		OBJECTS	{ mcr-Host, mcr-Severity, mcr-Text}	
		STATUS  current
		DESCRIPTION  "DB backup problem alarm is canceled"
		--#SUMMARY   "Alarm on host: $1 (ocsupport applications) :  $3"
		--#CATEGORY  "Error Alarms"
      	--#ARGUMENTS {}
      	--#SEVERITY  NORMAL
		::= { definitions 37 }


-- 1.3.6......0.38
voicetrunks NOTIFICATION-TYPE
                OBJECTS	{ mcr-Host, mcr-Severity, mcr-Text}	
				STATUS  current
                DESCRIPTION  "Voice trunk Failure"
                --#SUMMARY   "Alarm on host: $1 (ocsupport applications) :$3"
                --#CATEGORY  "Error Alarms"
        --#ARGUMENTS {}
        --#SEVERITY  MAJOR
                ::= { definitions 38 }


-- 1.3.6......0.39
voicetrunks-Canceled NOTIFICATION-TYPE
                OBJECTS	{ mcr-Host, mcr-Severity, mcr-Text}	
				STATUS  current
                DESCRIPTION  "Voice trunk Failure canceled"
                --#SUMMARY   "Alarm on host: $1 (ocsupport applications) :$3"
                --#CATEGORY  "Error Alarms"
        --#ARGUMENTS {}
        --#SEVERITY  NORMAL
                ::= { definitions 39 }


-- 1.3.6......0.40
nodedown NOTIFICATION-TYPE
                OBJECTS	{ mcr-Host, mcr-Severity, mcr-Text}	
				STATUS  current
                DESCRIPTION  "Node seems to be down"
                --#SUMMARY   "Alarm on host: $1 (ocsupport applications) :$3"
                --#CATEGORY  "Error Alarms"
        --#ARGUMENTS {}
        --#SEVERITY  MAJOR
                ::= { definitions 40 }


-- 1.3.6......0.41
nodedown-Canceled NOTIFICATION-TYPE
                OBJECTS	{ mcr-Host, mcr-Severity, mcr-Text}	
				STATUS  current
                DESCRIPTION  "Node seems to be up now."
                --#SUMMARY   "Alarm on host: $1 (ocsupport applications) :$3"
                --#CATEGORY  "Error Alarms"
        --#ARGUMENTS {}
        --#SEVERITY  NORMAL
                ::= { definitions 41 }

-- 1.3.6......0.42
test NOTIFICATION-TYPE
                OBJECTS	{ mcr-Host, mcr-Severity, mcr-Text}	
				STATUS  current
                DESCRIPTION  "Test alarm"
                --#SUMMARY   "Alarm on host: $1 (ocsupport applications) :$3"
                --#CATEGORY  "Error Alarms"
        	--#ARGUMENTS {}
        	--#SEVERITY  NORMAL
                ::= { definitions 42 }

-- 1.3.6......0.43
test-Canceled NOTIFICATION-TYPE
                OBJECTS	{ mcr-Host, mcr-Severity, mcr-Text}	
				STATUS  current
                DESCRIPTION  "Test alarm canceled"
                --#SUMMARY   "Alarm on host: $1 (ocsupport applications) :$3"
                --#CATEGORY  "Error Alarms"
        	--#ARGUMENTS {}
        	--#SEVERITY  NORMAL
                ::= { definitions 43 }


-- 1.3.6......0.44
mcr-MSA2012-Problem NOTIFICATION-TYPE
                OBJECTS	{ mcr-Host, mcr-Severity, mcr-Text}	
				STATUS  current
                DESCRIPTION  "MSA 2012 storage problem detected.
			      Possible problems:


				1.Hard disk failed.
				2.Power supply failed.
				3.Network connection failed.
				4.Controller failed."
                --#SUMMARY   "Alarm on host: $1 (ocsupport applications) :$3"
                --#CATEGORY  "Error Alarms"
        	--#ARGUMENTS {}
        	--#SEVERITY  MAJOR
                ::= { definitions 44 }

-- 1.3.6......0.45
mcr-MSA2012-Problem-Canceled NOTIFICATION-TYPE
                OBJECTS	{ mcr-Host, mcr-Severity, mcr-Text}	
				STATUS  current
                DESCRIPTION  "MSA 2012 storage problem detected - canceled"
                --#SUMMARY   "Alarm on host: $1 (ocsupport applications) :$3"
                --#CATEGORY  "Error Alarms"
        	--#ARGUMENTS {}
        	--#SEVERITY  NORMAL
                ::= { definitions 45 }


-- 1.3.6......0.46
mcr-TEMPERATURE-CUST NOTIFICATION-TYPE
                OBJECTS	{ mcr-Host, mcr-Severity, mcr-Text}	
				STATUS  current
                DESCRIPTION  "Temperature alarm!!Possible high temperature for zones on the server.
                              To check the status execute commands hplog -t"
                --#SUMMARY   "Alarm on host: $1 (ocsupport applications) :$3"
                --#CATEGORY  "Error Alarms"
        	--#ARGUMENTS {}
        	--#SEVERITY  MAJOR
                ::= { definitions 46 }

-- 1.3.6......0.47
mcr-TEMPERATURE-CUST-Canceled NOTIFICATION-TYPE
                OBJECTS	{ mcr-Host, mcr-Severity, mcr-Text}	
				STATUS  current
                DESCRIPTION  "Temperature is in normal level."
                --#SUMMARY   "Alarm on host: $1 (ocsupport applications) :$3"
                --#CATEGORY  "Error Alarms"
        	--#ARGUMENTS {}
        	--#SEVERITY  NORMAL
                ::= { definitions 47 }

-- 1.3.6......0.48
mcr-DBReplication NOTIFICATION-TYPE
                OBJECTS	{ mcr-Host, mcr-Severity, mcr-Text}	
				STATUS  current
                DESCRIPTION  "Replication problem detected.Check status with
command 'show slave status' from mysql cli for more information."
                --#SUMMARY   "Alarm on host: $1 (ocsupport applications) :$3"
                --#CATEGORY  "Error Alarms"
                --#ARGUMENTS {}
                --#SEVERITY  MAJOR
                ::= { definitions 48 }

-- 1.3.6......0.49
mcr-DBReplication-Canceled NOTIFICATION-TYPE
                OBJECTS	{ mcr-Host, mcr-Severity, mcr-Text}	
				STATUS  current
                DESCRIPTION  "Replication is working without problems."
                --#SUMMARY   "Alarm on host: $1 (ocsupport applications) :$3"
                --#CATEGORY  "Error Alarms"
                --#ARGUMENTS {}
                --#SEVERITY  NORMAL
                ::= { definitions 49 }

----------------------------------------------------------------------------------------------


END


--
-- OPCD-USSDGW-MIB-V2
--
