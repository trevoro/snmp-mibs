RDN-SYSLOG-MIB DEFINITIONS ::= BEGIN

        IMPORTS
            NOTIFICATION-TYPE, MODULE-IDENTITY, OBJECT-TYPE,
			IpAddress, Integer32
                FROM SNMPv2-SMI
            DisplayString
			    FROM RFC1213-MIB
			riverdelta
				FROM RDN-MIB;


		-- RiverDelta Networks enterprise syslog module definition

        rdnSyslog MODULE-IDENTITY
            LAST-UPDATED "0006140000Z" -- example "9501201225Z"
									   -- Fri Jan 20 12:25:50 PST 1995
            ORGANIZATION "Motorola"
            CONTACT-INFO "Motorola
                          3 Highwood Drive
                          Tewksbury, MA 01867
                          Tel: +1 978 858 2000
                          Fax: +1 978 858 2399
                          E-mail:  BSRSNMP@maillist2001.mot.com

                          Tom Keske 
                          Motorola BCS
                          20 Cabot Blvd. MA07 M2-330
                          Mansfield, MA 02048
                          Tel: 1-508-851-8325
                          Fax: 1-508-851-8510
                          E-mail: Tom.Keske@motorola.com"
            DESCRIPTION
                    "MIB module for Motorola
					syslog."
            REVISION     "0006140000Z"
            DESCRIPTION
                    "Added variable syslogRateLimitAutoRestart to allow
					turning on/off syslog rate-limit auto-restart."
            REVISION     "0006080000Z"
            DESCRIPTION
                    "Added syslogMessageTable."
            REVISION     "0005230000Z"
            DESCRIPTION
                    "Changed import of the riverdelta chassis mib to
					just the riverdelta definition mib."
            REVISION     "0005170000Z"
            DESCRIPTION
                    "Initial creation."
            ::= { riverdelta 3 }


          --
          -- syslog group should be present in all products.
          --

               rdnSyslogSize OBJECT-TYPE
                   SYNTAX  Integer32
                   MAX-ACCESS  read-only
                   STATUS  current
                   DESCRIPTION
                           "Current size in bytes of the syslog file."
                   ::= { rdnSyslog 1 }

               rdnSyslogMaxSize OBJECT-TYPE
                   SYNTAX  Integer32
                   MAX-ACCESS  read-write
                   STATUS  current
                   DESCRIPTION
                           "Maximum size in bytes of the syslog file."
                   ::= { rdnSyslog 2 }

               rdnSyslogServerEnable OBJECT-TYPE
                   SYNTAX  INTEGER {
                           enabled(1),
						   disabled(2)
						   }
                   MAX-ACCESS  read-write
                   STATUS  current
                   DESCRIPTION
                           "Enable or disable logging to remote syslog
                            servers."
                   ::= { rdnSyslog 3 }

               rdnSyslogServerTable OBJECT-TYPE
                   SYNTAX  SEQUENCE OF RdnSyslogServerTableEntry
                   MAX-ACCESS  not-accessible
                   STATUS  current
                   DESCRIPTION
                            "Table of remote syslog servers, of which
							there can be at most 3 entries."
                   ::= { rdnSyslog 4 }

               rdnSyslogServerTableEntry OBJECT-TYPE
                   SYNTAX RdnSyslogServerTableEntry
                   MAX-ACCESS  not-accessible
                   STATUS  current
                   DESCRIPTION
                            "syslog table entry."
                   INDEX { rdnSyslogServerIndex }
               ::= { rdnSyslogServerTable 1 }

               RdnSyslogServerTableEntry ::=
                   SEQUENCE {
                       rdnSyslogServerIndex
                           Integer32,
                       rdnSyslogServerAddress
                           IpAddress,
                       rdnSyslogServerStatus
                           INTEGER
                   }

               --
               -- start of syslog server table
               --

               rdnSyslogServerIndex OBJECT-TYPE
                   SYNTAX  Integer32
                   MAX-ACCESS  not-accessible
                   STATUS  current
                   DESCRIPTION
                           "Index into the remote syslog server table."
                   ::= { rdnSyslogServerTableEntry 1 }

               rdnSyslogServerAddress OBJECT-TYPE
                   SYNTAX  IpAddress
                   MAX-ACCESS  read-write
                   STATUS  current
                   DESCRIPTION
                           "The IP address of this syslog server."
                   ::= { rdnSyslogServerTableEntry 2 }

               rdnSyslogServerStatus OBJECT-TYPE
                   SYNTAX  INTEGER {
                           enabled(1),
						   disabled(2)
						   }
                   MAX-ACCESS  read-write
                   STATUS  current
                   DESCRIPTION
                           "Status of remote syslog server. Always enabled;
						   set to disable to delete a syslog server from
						   the syslogServerTable. Setting this to disabled
						   will remove this entry from the table."
                   ::= { rdnSyslogServerTableEntry 3 }

               -- end of syslog server table


               rdnSyslogSeverity OBJECT-TYPE
                   SYNTAX  INTEGER {
                           informational(1),
						   notifications(2),
						   warnings(3)
						   }
                   MAX-ACCESS  read-write
                   STATUS  current
                   DESCRIPTION
                           "Severity of syslog messages reported/sent to a
						   remote syslog server.

						   Severity Levels:
						   o informational - System information, permitting
						   informational, notifications, warnings, and errors.
						   o notifications - Normal level, permitting
						   notifications, warnings, and errors.
						   o warnings - Warning conditions, permitting warnings
						   and errors."
                   ::= { rdnSyslog 5 }

               rdnSyslogConsoleSeverity OBJECT-TYPE
                   SYNTAX  INTEGER {
                           informational(1),
						   notifications(2),
						   warnings(3)
						   }
                   MAX-ACCESS  read-write
                   STATUS  current
                   DESCRIPTION
                           "Severity of syslog messages reported/sent to a
						   console.

						   Severity Levels:
						   o informational - System information, permitting
						   informational, notifications, warnings, and errors.
						   o notifications - Normal level, permitting
						   notifications, warnings, and errors.
						   o warnings - Warning conditions, permitting warnings
						   and errors."
                   ::= { rdnSyslog 6 }

               rdnSyslogClear OBJECT-TYPE
                   SYNTAX  INTEGER {
                           true(1),
						   false(2)
						   }
                   MAX-ACCESS  read-write
                   STATUS  current
                   DESCRIPTION
                           "Indicates whether syslog file contains syslog
						   messages. This value is FALSE if syslog contains
						   syslog messages, TRUE otherwise. Set to TRUE to
						   clear all messages from the syslog file."
                   ::= { rdnSyslog 7 }

               rdnSyslogTrapSeverity OBJECT-TYPE
                   SYNTAX  INTEGER {
                           disable(1),
                           informational(2),
						   notifications(3),
						   warnings(4),
						   errors(5),
						   debug(6)
						   }
                   MAX-ACCESS  read-write
                   STATUS  current
                   DESCRIPTION
                           "SNMP trap severity level for which a syslog
						   message severity level equal to or above will
						   generate an SNMP trap. Set to disable to turn
						   off generation of any traps."
                   ::= { rdnSyslog 8 }

               rdnSyslogMessageTable OBJECT-TYPE
                   SYNTAX  SEQUENCE OF RdnSyslogMessageTableEntry
                   MAX-ACCESS  not-accessible
                   STATUS  current
                   DESCRIPTION
                            "Table of the latest syslog message strings."
                   ::= { rdnSyslog 9 }

               rdnSyslogMessageTableEntry OBJECT-TYPE
                   SYNTAX RdnSyslogMessageTableEntry
                   MAX-ACCESS  not-accessible
                   STATUS  current
                   DESCRIPTION
                            "syslog message table entry."
                   INDEX { rdnSyslogMessageIndex }
               ::= { rdnSyslogMessageTable 1 }

               RdnSyslogMessageTableEntry ::=
                   SEQUENCE {
                       rdnSyslogMessageIndex
                           Integer32,
                       rdnSyslogMessageString
                           DisplayString
                   }

               --
               -- start of syslog message table
               --

               rdnSyslogMessageIndex OBJECT-TYPE
                   SYNTAX  Integer32
                   MAX-ACCESS  not-accessible
                   STATUS  current
                   DESCRIPTION
                           "Index into the syslog message table."
                   ::= { rdnSyslogMessageTableEntry 1 }

               rdnSyslogMessageString OBJECT-TYPE
                   SYNTAX  DisplayString (SIZE (0..512))
                   MAX-ACCESS  read-only
                   STATUS  current
                   DESCRIPTION
                           "Actual message string of entry in syslog
						   message table."
                   ::= { rdnSyslogMessageTableEntry 2 }

               -- end of syslog message table


               rdnSyslogRateLimitAutoRestart OBJECT-TYPE
                   SYNTAX  INTEGER {
                           enabled(1),
						   disabled(2)
						   }
                   MAX-ACCESS  read-write
                   STATUS  current
                   DESCRIPTION
                           "Enable or disable rate-limit auto-restart
                            on logging of syslog messages."
                   ::= { rdnSyslog 10 }


        -- traps

		rdnSyslogMIB        OBJECT IDENTIFIER ::= { rdnSyslog 0 }
		rdnSyslogTraps      OBJECT IDENTIFIER ::= { rdnSyslogMIB 0 }

		rdnSyslogSeverityTrap NOTIFICATION-TYPE
            OBJECTS { rdnSyslogTrapSeverity }
			STATUS  current
			DESCRIPTION
					"A syslogSeverityTrap trap signifies that the
					system logger has received a syslog message
					with its own severity level greater than or
					equal to the severity level of syslog MIB
					Object syslogTrapSeverity."
			::= { rdnSyslogTraps 1 }


        -- conformance information


        -- compliance statements


        -- units of conformance

    END
