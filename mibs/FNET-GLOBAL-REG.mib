--
-- Global Registration Module for Fluke Networks
--
-- Definitions for Fluke Network's OID infrastructure and other
-- registrations.  
--

    FNET-GLOBAL-REG DEFINITIONS ::= BEGIN


        IMPORTS
            enterprises        FROM RFC1155-SMI;

        -- OID registrations

        fnet OBJECT IDENTIFIER
            -- The root of the OID sub-tree assigned to Fluke Networks
            -- by Internet Assigned Numbers Authority (IANA)
            ::= { enterprises 1226 }

        fnetReg OBJECT IDENTIFIER
            -- Sub-tree for registrations identifying products, product
            -- components and MIB related items.  These items are never
            -- queried by a NMS.  Instead, these object identifiers may
            -- be returned as the values of queries.
            ::= { fnet 1 }

            fnetOneTouch OBJECT IDENTIFIER
                ::= { fnetReg 2 }

            fnetOptiView OBJECT IDENTIFIER
                ::= { fnetReg 3 }

                fnetOvIna OBJECT IDENTIFIER
                    ::= { fnetOptiView 1 }

                fnetOvWga OBJECT IDENTIFIER
                    ::= { fnetOptiView 2 }

				fnetOvLa OBJECT IDENTIFIER
            		-- DESCRIPTION "The Fluke OptiView Link Analyzer."
					::= { fnetOptiView 3 }

                fnetOvWanFiber OBJECT IDENTIFIER
                    ::= { fnetOptiView 4 }
					 
                fnetOvWanCopper OBJECT IDENTIFIER
                    ::= { fnetOptiView 5 }

            fnetTrafficAnalyzer OBJECT IDENTIFIER
                ::= { fnetReg 6 }

            fnetLinkAnalyzer OBJECT IDENTIFIER
                ::= { fnetReg 8 }

			fnetProtocolExpert OBJECT IDENTIFIER
				-- DESCRIPTION "The Fluke OptiView Protocol Expert."
				::= { fnetReg 9 }

            fnetLanMeter OBJECT IDENTIFIER
                ::= { fnetReg 685 }

        fnetGeneric OBJECT IDENTIFIER
            -- Sub-tree for common object and event definitions.
            ::= { fnet 2 }

            fnetOptiViewGeneric OBJECT IDENTIFIER
                -- Sub-tree for OptiView common objects and events.
                ::= { fnetGeneric 1 }

        fnetProduct OBJECT IDENTIFIER
            -- Sub-tree for specific object and event definitions.
            ::= { fnet 3 }

            fnetOptiViewProduct OBJECT IDENTIFIER
                -- Sub-tree for OptiView specific objects and events.
                ::= { fnetProduct 1 }

        fnetCapabilities OBJECT IDENTIFIER
            -- Sub-tree for agent profiles
            ::= { fnet 4 }

        fnetRequirements OBJECT IDENTIFIER
            -- Sub-tree for managment applications requirements.
            ::= { fnet 5 }

        fnetExperimental OBJECT IDENTIFIER
            -- Sub-tree for experimental definitions
            ::= { fnet 6 }
    END
