ACC-NAT DEFINITIONS ::= BEGIN

    IMPORTS
	 OBJECT-TYPE, IpAddress, TimeTicks, Gauge, Counter FROM RFC1155-SMI
        accTrapLogSeqNum FROM ACC-SYSTEM
	accBRG, DisplayString, RowStatus, IfIndex, SmdsAddress
             FROM ACC-MIB;

-- NAT Group
-- Interface / IP map address table
accNAT            OBJECT IDENTIFIER ::= { accBRG 61 }
	accNATMapTable		OBJECT-TYPE
		SYNTAX	SEQUENCE OF AccNATMapEntry
		ACCESS	not-accessible
		STATUS	mandatory
		DESCRIPTION
		" A table of NAT mappings for IP interfaces."
		::= { accNAT 1 }
	accNATMapEntry		OBJECT-TYPE
		SYNTAX	AccNATMapEntry
		ACCESS	not-accessible
		STATUS	mandatory
		DESCRIPTION
		" An NAT mapping entry for an IP interface."
		INDEX	{ accNATMapIfIndex }
		::= { accNATMapTable 1 }
	AccNATMapEntry ::=	SEQUENCE {
				accNATMapIfIndex	INTEGER,
				accNATMapMapAddr	IpAddress
				}
	accNATMapIfIndex		OBJECT-TYPE
		SYNTAX	INTEGER
		ACCESS	read-only
		STATUS	mandatory
		DESCRIPTION
		" The IfIndex of this NAT interface."
		::= { accNATMapEntry 1 }
	accNATMapMapAddr		OBJECT-TYPE
		SYNTAX	IpAddress
		ACCESS	read-only
		STATUS	mandatory
		DESCRIPTION
		" The mapped address on this NAT interface."
		::= { accNATMapEntry 2 }
-- Statistics table
	accNATMapStatTable	OBJECT-TYPE
		SYNTAX	SEQUENCE OF AccNATMapStatEntry
		ACCESS	not-accessible
		STATUS	mandatory
		DESCRIPTION
		" A table of NAT mapping statistics for IP interfaces."
		::= { accNAT 2 }
	accNATMapStatEntry		OBJECT-TYPE
		SYNTAX	AccNATMapStatEntry
		ACCESS	not-accessible
		STATUS	mandatory
		DESCRIPTION
		" NAT mapping entry statistics for an IP interface."
		INDEX	{accNATMapIfIndex }
		::= { accNATMapStatTable 1 }
	AccNATMapStatEntry ::=	SEQUENCE {
				accNatMapStatTblIfIndex		INTEGER,
				accNatMapStatTblMapAddr		IpAddress,
				accNatMapStatTblSrcAddr		IpAddress,
				accNatMapStatTblDstAddr		IpAddress,
				accNatMapStatTblMapPort		INTEGER,
				accNatMapStatTblSrcPort		INTEGER,
				accNatMapStatTblDstPort		INTEGER,
				accNatMapStatTblMapCnts		Counter,
				accNatMapStatTblUnmapCnts	Counter,
				accNatMapStatTblProto		INTEGER
				}
	accNatMapStatTblIfIndex	OBJECT-TYPE
		SYNTAX	INTEGER
		ACCESS	read-only
		STATUS	mandatory
		DESCRIPTION
		" The index of this NAT mapping interface."
		::= { accNATMapStatEntry 1 }
	accNatMapStatTblMapAddr	OBJECT-TYPE
		SYNTAX	IpAddress
		ACCESS	read-only
		STATUS	mandatory
		DESCRIPTION
		" The map-to address in this Nat table entry."
		::= { accNATMapStatEntry 2 }
	accNatMapStatTblSrcAddr	OBJECT-TYPE
		SYNTAX	IpAddress
		ACCESS	read-only
		STATUS	mandatory
		DESCRIPTION
		" The source address in this Nat table entry."
		::= { accNATMapStatEntry 3 }
	accNatMapStatTblDstAddr	OBJECT-TYPE
		SYNTAX	IpAddress
		ACCESS	read-only
		STATUS	mandatory
		DESCRIPTION
		" The destination address in this Nat table entry."
		::= { accNATMapStatEntry 4 }
	accNatMapStatTblMapPort	OBJECT-TYPE
		SYNTAX	INTEGER
		ACCESS	read-only
		STATUS	mandatory
		DESCRIPTION
		" The map-to port in this Nat table entry."
		::= { accNATMapStatEntry 5 }
	accNatMapStatTblSrcPort	OBJECT-TYPE
		SYNTAX	INTEGER
		ACCESS	read-only
		STATUS	mandatory
		DESCRIPTION
		" The source port in this Nat table entry."
		::= { accNATMapStatEntry 6 }
	accNatMapStatTblDstPort	OBJECT-TYPE
		SYNTAX	INTEGER
		ACCESS	read-only
		STATUS	mandatory
		DESCRIPTION
		" The destination port in this Nat table entry."
		::= { accNATMapStatEntry 7 }
	accNatMapStatTblMapCnts	OBJECT-TYPE
		SYNTAX	Counter
		ACCESS	read-only
		STATUS	mandatory
		DESCRIPTION
		" The number of times this address mapping has occured."
		::= { accNATMapStatEntry 8 }
	accNatMapStatTblUnmapCnts	OBJECT-TYPE
		SYNTAX	Counter
		ACCESS	read-only
		STATUS	mandatory
		DESCRIPTION
		" The number of times this address unmapping has occured."
		::= { accNATMapStatEntry 9 }
	accNatMapStatTblProto	OBJECT-TYPE
		SYNTAX	INTEGER
		ACCESS	read-only
		STATUS	mandatory
		DESCRIPTION
		" The IP protocol detected in this Nat table entry."
		::= { accNATMapStatEntry 10 }
--NAV Objects are commented out since they are not implemented yet,  Romero
--  6/24/97
--NAV TABLE
--
accNAVMapTable		OBJECT-TYPE
		SYNTAX	SEQUENCE OF AccNAVMapEntry
		ACCESS	not-accessible
		STATUS	mandatory
		DESCRIPTION
		" A table of NAV mappings for IP interfaces."
		::= { accNAT 3 }
	accNAVMapEntry		OBJECT-TYPE
		SYNTAX	AccNAVMapEntry
		ACCESS	not-accessible
		STATUS	mandatory
		DESCRIPTION
		" An NAV mapping entry for an IP interface."
		INDEX { accNAVMapIfIndex }
		::= { accNAVMapTable 1 }
	AccNAVMapEntry ::=	SEQUENCE {
					accNAVMapIfIndex	INTEGER,
					accNAVMapServerPort	INTEGER,
					accNAVMapServerAddr	IpAddress
				}
	accNAVMapIfIndex		OBJECT-TYPE
		SYNTAX	INTEGER
		ACCESS	read-only
		STATUS	mandatory
		DESCRIPTION
		" The IfIndex of this NAV interface."
		::= { accNAVMapEntry 1 }
	accNAVMapServerPort		OBJECT-TYPE
		SYNTAX	INTEGER
		ACCESS	read-write
		STATUS	mandatory
		DESCRIPTION
		" The TCP/UDP port of this server entry." 
		::= { accNAVMapEntry 2 }
	accNAVMapServerAddr		OBJECT-TYPE
		SYNTAX	IpAddress
		ACCESS	read-write
		STATUS	mandatory
		DESCRIPTION
		" The IP address of the destination server on this NAV interface."
		::= { accNAVMapEntry 3 }
accNATTable		OBJECT-TYPE
		SYNTAX	SEQUENCE OF AccNATEntry
		ACCESS	not-accessible
		STATUS	mandatory
		DESCRIPTION
		" A table of NAT mappings for IP interfaces."
		::= { accNAT 4 }
	accNATEntry		OBJECT-TYPE
		SYNTAX	AccNATEntry
		ACCESS	not-accessible
		STATUS	mandatory
		DESCRIPTION
		" An NAT mapping entry for an IP interface."
		INDEX { accNATIfIndex }
		::= { accNATTable 1 }
	AccNATEntry ::=	SEQUENCE {
					accNATIfIndex		INTEGER,
					accNATSourceAddr	IpAddress,
					accNATSourceSubnetMask	IpAddress,
					accNATMapAddr		IpAddress,
					accNATMapSubnetMask	IpAddress
				}
	accNATIfIndex		OBJECT-TYPE
		SYNTAX	INTEGER
		ACCESS	read-only
		STATUS	mandatory
		DESCRIPTION
		" The IfIndex of this NAT interface."
		::= { accNATEntry 1 }
	accNATSourceAddr		OBJECT-TYPE
		SYNTAX	IpAddress
		ACCESS	read-write
		STATUS	mandatory
		DESCRIPTION
		" The IP address of the source host/network to be mapped"
		::= { accNATEntry 2 }
	accNATSourceSubnetMask		OBJECT-TYPE
		SYNTAX	IpAddress
		ACCESS	read-write
		STATUS	mandatory
		DESCRIPTION
		" The subnet mask of the IP address of the source host/network to be mapped"
		::= { accNATEntry 3 }
	accNATMapAddr		OBJECT-TYPE
		SYNTAX	IpAddress
		ACCESS	read-write
		STATUS	mandatory
		DESCRIPTION
		" The  Mapping IP address on the interface"
		::= { accNATEntry 4 }
	accNATMapSubnetMask		OBJECT-TYPE
		SYNTAX	IpAddress
		ACCESS	read-write
		STATUS	mandatory
		DESCRIPTION
		" The  subnet mask of the Mapping IP address on the interface"
		::= { accNATEntry 5 }

END
