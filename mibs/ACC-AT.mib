ACC-AT DEFINITIONS ::= BEGIN

    IMPORTS
	 OBJECT-TYPE, TimeTicks, Counter FROM RFC1155-SMI
   	 accTrapLogSeqNum FROM ACC-SYSTEM
	accBRG, DisplayString, RowStatus, IfIndex, SmdsAddress
             FROM ACC-MIB;

-- AppleTalk Group
     accAt OBJECT IDENTIFIER ::= { accBRG 28 }
     -- The AtNode Group
     accAtNode OBJECT IDENTIFIER ::= { accAt 1 }
		-- Configuration or operational parameters maintained
		-- and reported on a per-node basis.
     accAtNodeAdState OBJECT-TYPE
		SYNTAX	INTEGER {
			on(1),
			off(3)
		}
		ACCESS	read-write
		STATUS	mandatory
		DESCRIPTION
		 " The administrative state of the AppleTalk router.  If
		   set to on(1), AppleTalk packets will be routed on ports
		   which have been administratively enabled.  If set to
		   off(3), AppleTalk packets will be bridged."
		::= { accAtNode 1 }
     accAtNodeChecksum OBJECT-TYPE
		SYNTAX	INTEGER {
			on(1),
			off(2)
		}
		ACCESS	read-write
		STATUS	mandatory
		DESCRIPTION
		 " The AppleTalk checksum mode.  If set to on(1), output
		   packets will be generated with the standard AppleTalk
		   checksum.  If set to off(2), output packets will be
		   generated with a null checksum.  Checksum verification
		   is performed on input if and only if a DDP checksum is
		   present."
		::= { accAtNode 2 }
     accAtNodeAarpExpire OBJECT-TYPE
		SYNTAX	TimeTicks -- (6000..1800000)
		ACCESS	read-write
		STATUS	mandatory
		DESCRIPTION
		 " The AARP database expiration interval.  AARP database
		   entries which are not updated within this interval of
		   time are deleted from the database.  The default value
		   is 360000 (1 hour)."
		::= { accAtNode 3 }
     accAtNodeFfrRouting OBJECT-TYPE
		SYNTAX  INTEGER	{
		    half(1),
		    full(2)
		}
		ACCESS	read-write
		STATUS  mandatory	
		DESCRIPTION
		 "This object indicates whether appletalk uses a half (ACC) or
		   full (Cisco) router model for frame relay. "
		::= { accAtNode 4 }
     -- The AtAarpTable Group
     accAtAarpTable OBJECT-TYPE
		SYNTAX	SEQUENCE OF AccAtAarpEntry
		ACCESS	not-accessible
		STATUS	mandatory
		DESCRIPTION
		 " The AARP database containing AppleTalk protocol to
		   hardware address mappings.  This view of the AARP
		   database differs from the standard view as seen from
		   the experimental branch of the MIB."
		::= { accAt 2 }
     accAtAarpEntry OBJECT-TYPE
		SYNTAX	AccAtAarpEntry
		ACCESS	not-accessible
		STATUS	mandatory
		DESCRIPTION
		 " An AARP database entry which maps a particular AppleTalk
		   protocol address into a MAC-layer hardware address. "
		INDEX { accAtAarpTabPort,
		        accAtAarpTabNetAddr }
		::= { accAtAarpTable 1 }
     AccAtAarpEntry ::= SEQUENCE {
		accAtAarpTabPort		INTEGER,
		accAtAarpTabMacAddr		OCTET STRING,
		accAtAarpTabNetAddr		OCTET STRING,
		accAtAarpTabStatus		INTEGER
     }
     accAtAarpTabPort OBJECT-TYPE
		SYNTAX	INTEGER (1..255)
		ACCESS	read-only
		STATUS	mandatory
		DESCRIPTION
		 " The logical port number of a directly-connected
		   AppleTalk network."
		::= { accAtAarpEntry 1 }
     accAtAarpTabMacAddr OBJECT-TYPE
		SYNTAX	OCTET STRING
		ACCESS	read-only
		STATUS	mandatory
		DESCRIPTION
		 " The 48-bit Ethernet or Token Ring MAC-layer address
		   which corresponds to the AppleTalk network address."
		::= { accAtAarpEntry 2 }
     accAtAarpTabNetAddr OBJECT-TYPE
		SYNTAX  OCTET STRING -- (SIZE(3))	
		ACCESS	read-only
		STATUS	mandatory
		DESCRIPTION
		 " The 24-bit AppleTalk network address consisting of a
		   16-bit network number and 8-bit node id."
		::= { accAtAarpEntry 3 }
     accAtAarpTabStatus OBJECT-TYPE
		SYNTAX	INTEGER {
			dynamic(1),
			static(2),
			pending(3)
		}
		ACCESS	read-only
		STATUS	mandatory
		DESCRIPTION
		 " The status of the entry.  A status of dynamic(1)
		   indicates the entry can be deleted when the expiration
		   interval expires, a status of static(1) indicates the
		   entry contains the address of a local port, and a status
		   of pending(3) indicates the entry is not complete (i.e.,
		   the hardware or protocol address is unknown)."
		::= { accAtAarpEntry 4 }
     -- The AtAarpStatsTable Group
     accAtAarpStatsTable OBJECT-TYPE
		SYNTAX	SEQUENCE OF AccAtAarpStatsEntry
		ACCESS	not-accessible
		STATUS	mandatory
		DESCRIPTION
		 " AppleTalk Address Resolution Protocol (AARP) statistics
		   maintained and reported on a per-port basis."
		::= { accAt 3 }
     accAtAarpStatsEntry OBJECT-TYPE
		SYNTAX	AccAtAarpStatsEntry
		ACCESS	not-accessible
		STATUS	mandatory
		DESCRIPTION
		 " The AARP statistics for a particular logical port.  If
		   the port is not connected to an AppleTalk network which
		   uses AARP, all statistics will be reported with a zero
		   value. "
                INDEX { accAtPortTabIndex }
		::= { accAtAarpStatsTable 1 }
     AccAtAarpStatsEntry ::= SEQUENCE {
		accAtAarpStatsInRequests	Counter,
		accAtAarpStatsInResponses	Counter,
		accAtAarpStatsInProbes		Counter,
		accAtAarpStatsOutRequests	Counter,
		accAtAarpStatsOutResponses	Counter,
		accAtAarpStatsOutProbes		Counter,
		accAtAarpStatsNoReplys		Counter,
		accAtAarpStatsExpires		Counter,
		accAtAarpStatsDiscards		Counter,
		accAtAarpStatsInErrors		Counter,
		accAtAarpStatsOutErrors		Counter
     }
     accAtAarpStatsInRequests OBJECT-TYPE
		SYNTAX	Counter
		ACCESS	read-only
		STATUS	mandatory
		DESCRIPTION
		 " The number of AARP request packets received."
		::= { accAtAarpStatsEntry 1 }
     accAtAarpStatsInResponses OBJECT-TYPE
		SYNTAX	Counter
		ACCESS	read-only
		STATUS	mandatory
		DESCRIPTION
		 " The number of AARP response packets received."
		::= { accAtAarpStatsEntry 2 }
     accAtAarpStatsInProbes OBJECT-TYPE
		SYNTAX	Counter
		ACCESS	read-only
		STATUS	mandatory
		DESCRIPTION
		 " The number of AARP probe packets received."
		::= { accAtAarpStatsEntry 3 }
     accAtAarpStatsOutRequests OBJECT-TYPE
		SYNTAX	Counter
		ACCESS	read-only
		STATUS	mandatory
		DESCRIPTION
		 " The number of AARP request packets sent."
		::= { accAtAarpStatsEntry 4 }
     accAtAarpStatsOutResponses OBJECT-TYPE
		SYNTAX	Counter
		ACCESS	read-only
		STATUS	mandatory
		DESCRIPTION
		 " The number of AARP response packets sent."
		::= { accAtAarpStatsEntry 5 }
     accAtAarpStatsOutProbes OBJECT-TYPE
		SYNTAX	Counter
		ACCESS	read-only
		STATUS	mandatory
		DESCRIPTION
		 " The number of AARP probe packets sent."
		::= { accAtAarpStatsEntry 6 }
     accAtAarpStatsNoReplys OBJECT-TYPE
		SYNTAX	Counter
		ACCESS	read-only
		STATUS	mandatory
		DESCRIPTION
		 " The number of times an AARP request packet and its
		   subsequent retransmissions received no response."
		::= { accAtAarpStatsEntry 7 }
     accAtAarpStatsExpires OBJECT-TYPE
		SYNTAX	Counter
		ACCESS	read-only
		STATUS	mandatory
		DESCRIPTION
		 " The number of times an entry was deleted from the AARP
		   database because the expiration interval had expired."
		::= { accAtAarpStatsEntry 8 }
     accAtAarpStatsDiscards OBJECT-TYPE
		SYNTAX	Counter
		ACCESS	read-only
		STATUS	mandatory
		DESCRIPTION
		 " The number of queued output packets discarded because
		   of an unanswered AARP request."
		::= { accAtAarpStatsEntry 9 }
     accAtAarpStatsInErrors OBJECT-TYPE
		SYNTAX	Counter
		ACCESS	read-only
		STATUS	mandatory
		DESCRIPTION
		 " The number of AARP packets received which were invalid
		   or which could not be processed because of some internal
		   error."
		::= { accAtAarpStatsEntry 10 }
     accAtAarpStatsOutErrors OBJECT-TYPE
		SYNTAX	Counter
		ACCESS	read-only
		STATUS	mandatory
		DESCRIPTION
		 " The number of AARP packets which could not be sent
		   because of some internal error."
		::= { accAtAarpStatsEntry 11 }
     -- The AtAdbStats Group
     accAtAdbStats OBJECT IDENTIFIER ::= { accAt 4 }
		-- AARP database statistics maintained and reported on a
		-- per-node basis.
     accAtAdbStatsCacheds OBJECT-TYPE
		SYNTAX	Counter
		ACCESS	read-only
		STATUS	mandatory
		DESCRIPTION
		 " The number of times the desired database entry was the
		   first entry in the hash bucket (i.e., it had already
		   been rotated to the beginning of the list of entries
		   with the same hash value)."
		::= { accAtAdbStats 1 }
     accAtAdbStatsRotates OBJECT-TYPE
		SYNTAX	Counter
		ACCESS	read-only
		STATUS	mandatory
		DESCRIPTION
		 " The number of times the desired database entry was not
		   the first entry in the hash bucket and had to be rotated
		   to the beginning of the list."
		::= { accAtAdbStats 2 }
     accAtAdbStatsNoEntries OBJECT-TYPE
		SYNTAX	Counter
		ACCESS	read-only
		STATUS	mandatory
		DESCRIPTION
		 " The number of times the desired entry was not in the
		   AARP database."
		::= { accAtAdbStats 3 }
     accAtAdbStatsAdds OBJECT-TYPE
		SYNTAX	Counter
		ACCESS	read-only
		STATUS	mandatory
		DESCRIPTION
		 " The number of times a new entry was added to the AARP
		   database."
		::= { accAtAdbStats 4 }
     accAtAdbStatsUpdates OBJECT-TYPE
		SYNTAX	Counter
		ACCESS	read-only
		STATUS	mandatory
		DESCRIPTION
		 " The number of times an existing entry was updated."
		::= { accAtAdbStats 5 }
     accAtAdbStatsDeletes OBJECT-TYPE
		SYNTAX	Counter
		ACCESS	read-only
		STATUS	mandatory
		DESCRIPTION
		 " The number of times an entry was deleted from the AARP
		   database."
		::= { accAtAdbStats 6 }
     accAtAdbStatsTrims OBJECT-TYPE
		SYNTAX	Counter
		ACCESS	read-only
		STATUS	mandatory
		DESCRIPTION
		 " The number of times the AARP database was trimmed to
		   make room for a new entry."
		::= { accAtAdbStats 7 }
     accAtAdbStatsDiscards OBJECT-TYPE
		SYNTAX	Counter
		ACCESS	read-only
		STATUS	mandatory
		DESCRIPTION
		 " The number of queued output packets discarded because
		   the anchoring database entry was deleted."
		::= { accAtAdbStats 8 }
     -- The AtDdpStats Group
     accAtDdpStats OBJECT IDENTIFIER ::= { accAt 5 }
		-- Datagram Delivery Protocol (DDP) statistics maintained
		-- and reported on a per-node basis.  These statistics
		-- supplement the standard DDP statistics defined in the
		-- experimental branch of the MIB.
     accAtDdpStatsNoOutRoutes OBJECT-TYPE
		SYNTAX	Counter
		ACCESS	read-only
		STATUS	mandatory
		DESCRIPTION
		 " The number of output packets generated by local protocol
		   handlers for which there was not route to the destination
		   network."
		::= { accAtDdpStats 1 }
     accAtDdpStatsInErrors OBJECT-TYPE
		SYNTAX	Counter
		ACCESS	read-only
		STATUS	mandatory
		DESCRIPTION
		 " The number of packets received which could not be
		   delivered because of some internal error."
		::= { accAtDdpStats 2 }
     accAtDdpStatsOutErrors OBJECT-TYPE
		SYNTAX	Counter
		ACCESS	read-only
		STATUS	mandatory
		DESCRIPTION
		 " The number of packets locally generated which could
		   not be sent because of some internal error."
		::= { accAtDdpStats 3 }
     -- The AtNetTable Group
     accAtNetTable OBJECT-TYPE
		SYNTAX	SEQUENCE OF AccAtNetEntry
		ACCESS	not-accessible
		STATUS	mandatory
		DESCRIPTION
		 " AppleTalk network configuration table stored in NVM."
		::= { accAt 6 }
     accAtNetEntry OBJECT-TYPE
		SYNTAX	AccAtNetEntry
		ACCESS	not-accessible
		STATUS	mandatory
		DESCRIPTION
		 " The information stored in NVM which defines an AppleTalk
		   network or half-router serial port.  This information
		   supplements standard configuration parameters defined
		   in the experimental branch of the MIB."
                INDEX { atportIndex }
		::= { accAtNetTable 1 }
     AccAtNetEntry ::= SEQUENCE {
		accAtNetTabProtocol		INTEGER,
		accAtNetTabRtmpIncr		INTEGER,
		accAtNetTabRtmpSend		TimeTicks,
		accAtNetTabX25Addr1		OCTET STRING,
		accAtNetTabX25Addr2		OCTET STRING,
		accAtNetTabX25Idle		TimeTicks,
		accAtNetTabX25PktSize		INTEGER,
		accAtNetTabX25WinSize		INTEGER,
		accAtNetTabX25FacIndex		INTEGER
     }
     accAtNetTabProtocol OBJECT-TYPE
		SYNTAX	INTEGER {
			ethertalk1(1),
			ethertalk2(2),
			tokentalk(3),
			lapb(4),
			x25(5),
			framerelay(6),
			ppp(7),
			fddi(8),
			dial(11),
			multilinkgroup(12)
		}
		ACCESS	read-write
		STATUS	mandatory
		DESCRIPTION
		 " The type of data-link protocol used.  These types
		   augment the standard definitions in the experimental
		   branch of the MIB and are used to maintain conformity
		   with ACC management commands.  Setting this object
		   will cause all other objects associated with this
		   entry to be reset to their default values."
		::= { accAtNetEntry 1 }
     accAtNetTabRtmpIncr OBJECT-TYPE
		SYNTAX	INTEGER (1..15)
		ACCESS	read-write
		STATUS	mandatory
		DESCRIPTION
		 " The RTMP hop-count increment to be applied to packets
		   forwarded via this port or routing tuples received
		   received on this port."
                DEFVAL { 1 }
		::= { accAtNetEntry 2 }
     accAtNetTabRtmpSend OBJECT-TYPE
		SYNTAX	TimeTicks -- (1000..30000)
		ACCESS	read-write
		STATUS	mandatory
		DESCRIPTION
		 " The RTMP send interval for routing updates sent via
		   this port. The RTMP send interval may be
		   set to a higher value on serial ports to limit the
		   amount of bandwidth consumed by routing updates."
                DEFVAL { 1000 }
		::= { accAtNetEntry 3 }
     accAtNetTabX25Addr1 OBJECT-TYPE
		SYNTAX	OCTET STRING
		ACCESS	read-write
		STATUS	mandatory
		DESCRIPTION
		 " The normal DTE address to use for sending or receiving
		   packets via an X.25 virtual circuit."
		::= { accAtNetEntry 4 }
     accAtNetTabX25Addr2 OBJECT-TYPE
		SYNTAX	OCTET STRING
		ACCESS	read-write
		STATUS	mandatory
		DESCRIPTION
		 " An alternate DTE address to use for receiving packets
		   via an X.25 virtual circuit."
		::= { accAtNetEntry 5 }
     accAtNetTabX25Idle OBJECT-TYPE
		SYNTAX	TimeTicks -- (6000..6480000)
		ACCESS	read-write
		STATUS	mandatory
		DESCRIPTION
		 " The interval which governs how long an X.25 circuit
		   can be idle before it is cleared. "
                DEFVAL { 30000 }
		::= { accAtNetEntry 6 }
     accAtNetTabX25PktSize OBJECT-TYPE
		SYNTAX	INTEGER 
		ACCESS	read-write
		STATUS	mandatory
		DESCRIPTION
		 " The desired packet size to be negotiated during X.25
		   call establishment.
			pktsize1(0),
			pktsize2(16),
			pktsize3(32),
			pktsize4(64),
			pktsize5(128),
			pktsize6(256),
			pktsize7(512),
			pktsize8(1024)
		   "
                DEFVAL { 0 }
		::= { accAtNetEntry 7 }
     accAtNetTabX25WinSize OBJECT-TYPE
		SYNTAX	INTEGER (0..127)
		ACCESS	read-write
		STATUS	mandatory
		DESCRIPTION
		 " The desired window size to be negotiated during X.25
		   call establishment."
                DEFVAL { 127 }
		::= { accAtNetEntry 8 }
	accAtNetTabX25FacIndex OBJECT-TYPE
	               SYNTAX  INTEGER (0..255)
	               ACCESS  read-write
	               STATUS  mandatory
	               DESCRIPTION
	                " Index of optional facility string or zero."
	                 DEFVAL { 0 }
	               ::= { accAtNetEntry 9 }
     -- The AtPortTable Group
     accAtPortTable OBJECT-TYPE
		SYNTAX	SEQUENCE OF AccAtPortEntry
		ACCESS	not-accessible
		STATUS	mandatory
		DESCRIPTION
		 " The AppleTalk port table stored in RAM.  For each
		   valid network table entry configured in NVM when
		   the port table is initialized (after system reset)
		   there is a corresponding port table entry in RAM."
		::= { accAt 7 }
     accAtPortEntry OBJECT-TYPE
		SYNTAX	AccAtPortEntry
		ACCESS	not-accessible
		STATUS	mandatory
		DESCRIPTION
		 " The information maintained in RAM for a particular
		   logical port." 
                INDEX { accAtPortTabIndex }
		::= { accAtPortTable 1 }
     AccAtPortEntry ::= SEQUENCE {
		accAtPortTabIndex		INTEGER,
		accAtPortTabNetAddr		OCTET STRING,
		accAtPortTabState		INTEGER,
		accAtPortTabDescr		DisplayString,
		accAtPortTabErrCode		INTEGER,
		accAtPortTabErrTime		TimeTicks,
		accAtPortTabErrAddr		OCTET STRING,
		accAtPortTabErrDescr		DisplayString,
		accAtPortTabErrCount		INTEGER
     }
     accAtPortTabIndex OBJECT-TYPE
		SYNTAX	INTEGER (1..255)
		ACCESS	read-only
		STATUS	mandatory
		DESCRIPTION
		 " The logical port number.  Only ports which were defined
		   prior to the last system reset and whose configuration
		   entries contained valid parameters are initialized and
		   stored in RAM."
		::= { accAtPortEntry 1 }
     accAtPortTabNetAddr OBJECT-TYPE
		SYNTAX	OCTET STRING
		ACCESS	read-only
		STATUS	mandatory
		DESCRIPTION
		 " The ports DDP network address consisting of a 16-bit
		   AppleTalk network number and 8-bit node id.  This
		   address is determined dynamically during port start
		   up and may change after a system reset."
		::= { accAtPortEntry 2 }
     accAtPortTabState OBJECT-TYPE
		SYNTAX	INTEGER {
			down(1),
			start1(2),
			probe1(3),
			start2(4),
			up(5),
			probe2(6),
			query(7),
			ready(8),
			stop2(9),
			stop1(10),
			error(11)
		}
		ACCESS	read-only
		STATUS	mandatory
		DESCRIPTION
		 " The operational state of the port."
		::= { accAtPortEntry 3 }
     accAtPortTabDescr OBJECT-TYPE
		SYNTAX  DisplayString
		ACCESS	read-only
		STATUS	mandatory
		DESCRIPTION
		 " Displayable text describing the type of logical port."
		::= { accAtPortEntry 4 }
     accAtPortTabErrCode OBJECT-TYPE
		SYNTAX	INTEGER
		ACCESS	read-only
		STATUS	mandatory
		DESCRIPTION
		 " An error code indicating why the logical port has been
		   disabled.  This value is set when the operational state
		   (accAtPortTabState) of a port is set to error(11) due
		   to some condition which may prevent continued operation."
		::= { accAtPortEntry 5 }
     accAtPortTabErrTime OBJECT-TYPE
		SYNTAX	TimeTicks
		ACCESS	read-only
		STATUS	mandatory
		DESCRIPTION
		 " The time (relative to the last system reset) at which
		   the port became disabled."
		::= { accAtPortEntry 6 }
     accAtPortTabErrAddr OBJECT-TYPE
		SYNTAX	OCTET STRING
		ACCESS	read-only
		STATUS	mandatory
		DESCRIPTION
		 " The DDP network address of a neighboring router or
		   AppleTalk node which was the source of information
		   causing the port to become disabled.  The DDP address
		   consists of a 16-bit AppleTalk network number and
		   8-bit node id."
		::= { accAtPortEntry 7 }
     accAtPortTabErrDescr OBJECT-TYPE
		SYNTAX  DisplayString	
		ACCESS	read-only
		STATUS	mandatory
		DESCRIPTION
		 " Displayable text which describes why the port has been
		   disabled."
		::= { accAtPortEntry 8 }
     accAtPortTabErrCount OBJECT-TYPE
		SYNTAX	INTEGER
		ACCESS	read-only
		STATUS	mandatory
		DESCRIPTION
		 " The number of subsequent errors which have been detected
		   while a port is disabled."
		::= { accAtPortEntry 9 }
     -- The AtPortStatsTable Group
     accAtPortStatsTable OBJECT-TYPE
		SYNTAX	SEQUENCE OF AccAtPortStatsEntry
		ACCESS	not-accessible
		STATUS	mandatory
		DESCRIPTION
		 " Datagram Delivery Protocol (DDP) statistics maintained
		   and reported on a per-port basis."
		::= { accAt 8 }
     accAtPortStatsEntry OBJECT-TYPE
		SYNTAX	AccAtPortStatsEntry
		ACCESS	not-accessible
		STATUS	mandatory
		DESCRIPTION
		 " The DDP statistics maintained for a particular logical
		   port."
                INDEX { accAtPortTabIndex }
		::= { accAtPortStatsTable 1 }
     AccAtPortStatsEntry ::= SEQUENCE {
		accAtPortStatsInTotals		Counter,
		accAtPortStatsInShorts		Counter,
		accAtPortStatsNotForMes		Counter,
		accAtPortStatsTooShorts		Counter,
		accAtPortStatsTooLongs		Counter,
		accAtPortStatsChksums		Counter,
		accAtPortStatsNotMyNets		Counter,
		accAtPortStatsInFwdReqs		Counter,
		accAtPortStatsFwdBcasts		Counter,
		accAtPortStatsNoFwdRoutes	Counter,
		accAtPortStatsHopCounts		Counter,
		accAtPortStatsReflects		Counter,
		accAtPortStatsOutTotals		Counter,
		accAtPortStatsOutShorts		Counter,
		accAtPortStatsOutFwdReqs	Counter,
		accAtPortStatsInErrors		Counter,
		accAtPortStatsOutErrors		Counter
     }
     accAtPortStatsInTotals OBJECT-TYPE
		SYNTAX	Counter
		ACCESS	read-only
		STATUS	mandatory
		DESCRIPTION
		 " The total number of DDP packets received via the port."
		::= { accAtPortStatsEntry 1 }
     accAtPortStatsInShorts OBJECT-TYPE
		SYNTAX	Counter
		ACCESS	read-only
		STATUS	mandatory
		DESCRIPTION
		 " The total number of DDP packets received with short
		   headers."
		::= { accAtPortStatsEntry 2 }
     accAtPortStatsNotForMes OBJECT-TYPE
		SYNTAX	Counter
		ACCESS	read-only
		STATUS	mandatory
		DESCRIPTION
		 " The number of Phase 1 unicast packets received with a
		   LLAP header whose destination node id did not match
		   that of the receiving port."
		::= { accAtPortStatsEntry 3 }
     accAtPortStatsTooShorts OBJECT-TYPE
		SYNTAX	Counter
		ACCESS	read-only
		STATUS	mandatory
		DESCRIPTION
		 " The number of DDP packets received whose length was
		   less than that of a DDP header or whose physical length
		   was less than the logical length."
		::= { accAtPortStatsEntry 4 }
     accAtPortStatsTooLongs OBJECT-TYPE
		SYNTAX	Counter
		ACCESS	read-only
		STATUS	mandatory
		DESCRIPTION
		 " The number of of DDP packets received whose length
		   exceeded the maximum datagram size or whose physical
		   length was greater than the logical length."
		::= { accAtPortStatsEntry 5 }
     accAtPortStatsChksums OBJECT-TYPE
		SYNTAX	Counter
		ACCESS	read-only
		STATUS	mandatory
		DESCRIPTION
		 " The number of DDP packets received with an invalid
		   checksum."
		::= { accAtPortStatsEntry 6 }
     accAtPortStatsNotMyNets OBJECT-TYPE
		SYNTAX	Counter
		ACCESS	read-only
		STATUS	mandatory
		DESCRIPTION
		 " The number of DDP broadcast packets received whose
		   destination network number was within the range of the
		   connected network but which did not match the network
		   number assigned to the port."
		::= { accAtPortStatsEntry 7 }
     accAtPortStatsInFwdReqs OBJECT-TYPE
		SYNTAX	Counter
		ACCESS	read-only
		STATUS	mandatory
		DESCRIPTION
		 " The number of DDP packets received which were not
		   addressed to the receiving port (although some may
		   have been addressed to another port on the same
		   router)."
		::= { accAtPortStatsEntry 8 }
     accAtPortStatsFwdBcasts OBJECT-TYPE
		SYNTAX	Counter
		ACCESS	read-only
		STATUS	mandatory
		DESCRIPTION
		 " The number of DDP broadcast packets receive whose
		   destination network number was not within the range
		   of the connected network."
		::= { accAtPortStatsEntry 9 }
     accAtPortStatsNoFwdRoutes OBJECT-TYPE
		SYNTAX	Counter
		ACCESS	read-only
		STATUS	mandatory
		DESCRIPTION
		 " The number of DDP packets received for which no route
		   to the destination network existed."
		::= { accAtPortStatsEntry 10 }
     accAtPortStatsHopCounts OBJECT-TYPE
		SYNTAX	Counter
		ACCESS	read-only
		STATUS	mandatory
		DESCRIPTION
		 " The number of DDP packets received which were discarded
		   because the hop count had exceeded the maximum value."
		::= { accAtPortStatsEntry 11 }
     accAtPortStatsReflects OBJECT-TYPE
		SYNTAX	Counter
		ACCESS	read-only
		STATUS	mandatory
		DESCRIPTION
		 " The number of DDP packets received which were addressed
		   to another node on the same network."
		::= { accAtPortStatsEntry 12 }
     accAtPortStatsOutTotals OBJECT-TYPE
		SYNTAX	Counter
		ACCESS	read-only
		STATUS	mandatory
		DESCRIPTION
		 " The total number of DDP packets sent via the port."
		::= { accAtPortStatsEntry 13 }
     accAtPortStatsOutShorts OBJECT-TYPE
		SYNTAX	Counter
		ACCESS	read-only
		STATUS	mandatory
		DESCRIPTION
		 " The number of DDP packets send with short headers."
		::= { accAtPortStatsEntry 14 }
     accAtPortStatsOutFwdReqs OBJECT-TYPE
		SYNTAX	Counter
		ACCESS	read-only
		STATUS	mandatory
		DESCRIPTION
		 " The number of DDP packets forwarded to this port from
		   all other ports."
		::= { accAtPortStatsEntry 15 }
     accAtPortStatsInErrors OBJECT-TYPE
		SYNTAX	Counter
		ACCESS	read-only
		STATUS	mandatory
		DESCRIPTION
		 " The number of DDP packets received which could not be
		   processed because of some internal error."
		::= { accAtPortStatsEntry 16 }
     accAtPortStatsOutErrors OBJECT-TYPE
		SYNTAX	Counter
		ACCESS	read-only
		STATUS	mandatory
		DESCRIPTION
		 " The number of DDP packets which could not be sent
		   because of some internal error."
		::= { accAtPortStatsEntry 17 }
     -- The AtRtmpStats Group
     accAtRtmpStats OBJECT IDENTIFIER ::= { accAt 9 }
		-- Routing Table Maintenance Protocol (RTMP) statistics
		-- maintained and reported on a per-node basis.
     accAtRtmpStatsInRequests OBJECT-TYPE
		SYNTAX	Counter
		ACCESS	read-only
		STATUS	mandatory
		DESCRIPTION
		 " The number of RTMP request packets received."
		::= { accAtRtmpStats 1 }
     accAtRtmpStatsInDataReqs OBJECT-TYPE
		SYNTAX	Counter
		ACCESS	read-only
		STATUS	mandatory
		DESCRIPTION
		 " The number of RTMP route data request packets received."
		::= { accAtRtmpStats 2 }
     accAtRtmpStatsInResponses OBJECT-TYPE
		SYNTAX	Counter
		ACCESS	read-only
		STATUS	mandatory
		DESCRIPTION
		 " The number of RTMP response packets received."
		::= { accAtRtmpStats 3 }
     accAtRtmpStatsInDataResps OBJECT-TYPE
		SYNTAX	Counter
		ACCESS	read-only
		STATUS	mandatory
		DESCRIPTION
		 " The number of RTMP route data response packets received."
		::= { accAtRtmpStats 4 }
     accAtRtmpStatsOutRequests OBJECT-TYPE
		SYNTAX	Counter
		ACCESS	read-only
		STATUS	mandatory
		DESCRIPTION
		 " The number of RTMP request packets sent."
		::= { accAtRtmpStats 5 }
     accAtRtmpStatsOutDataReqs OBJECT-TYPE
		SYNTAX	Counter
		ACCESS	read-only
		STATUS	mandatory
		DESCRIPTION
		 " The number of RTMP route data request packets sent."
		::= { accAtRtmpStats 6 }
     accAtRtmpStatsOutResponses OBJECT-TYPE
		SYNTAX	Counter
		ACCESS	read-only
		STATUS	mandatory
		DESCRIPTION
		 " The number of RTMP response packets sent."
		::= { accAtRtmpStats 7 }
     accAtRtmpStatsOutDataResps OBJECT-TYPE
		SYNTAX	Counter
		ACCESS	read-only
		STATUS	mandatory
		DESCRIPTION
		 " The number of RTMP route data response packets sent."
		::= { accAtRtmpStats 8 }
     accAtRtmpStatsNetConflicts OBJECT-TYPE
		SYNTAX	Counter
		ACCESS	read-only
		STATUS	mandatory
		DESCRIPTION
		 " The number of RTMP packets received which conflicted
		   with the network number range configured for the
		   receiving port or garnered from another router."
		::= { accAtRtmpStats 9 }
     accAtRtmpStatsInErrors OBJECT-TYPE
		SYNTAX	Counter
		ACCESS	read-only
		STATUS	mandatory
		DESCRIPTION
		 " The number of RTMP packets received containing a
		   format error or which could not be processed because
		   of some internal error."
		::= { accAtRtmpStats 10 }
     accAtRtmpStatsOutErrors OBJECT-TYPE
		SYNTAX	Counter
		ACCESS	read-only
		STATUS	mandatory
		DESCRIPTION
		 " The number of RTMP packets which could not be sent
		   because of some internal error."
		::= { accAtRtmpStats 11 }
     -- The AtRdbStats Group
     accAtRdbStats OBJECT IDENTIFIER ::= { accAt 10 }
		-- Routing database statistics maintained and reported
		-- on a per-node basis.
     accAtRdbStatsCacheds OBJECT-TYPE
		SYNTAX	Counter
		ACCESS	read-only
		STATUS	mandatory
		DESCRIPTION
		 " The number of times the desired route was already
		   cached."
		::= { accAtRdbStats 1 }
     accAtRdbStatsSearchs OBJECT-TYPE
		SYNTAX	Counter
		ACCESS	read-only
		STATUS	mandatory
		DESCRIPTION
		 " The number of times the desired route was not cached
		   and the routing database had to be searched."
		::= { accAtRdbStats 2 }
     accAtRdbStatsNoRoutes OBJECT-TYPE
		SYNTAX	Counter
		ACCESS	read-only
		STATUS	mandatory
		DESCRIPTION
		 " The number of times no route could be found to the
		   destination network."
		::= { accAtRdbStats 3 }
     accAtRdbStatsAdds OBJECT-TYPE
		SYNTAX	Counter
		ACCESS	read-only
		STATUS	mandatory
		DESCRIPTION
		 " The number of times a new network was added to the
		   routing database."
		::= { accAtRdbStats 4 }
     accAtRdbStatsUpdates OBJECT-TYPE
		SYNTAX	Counter
		ACCESS	read-only
		STATUS	mandatory
		DESCRIPTION
		 " The number of times an existing route was updated."
		::= { accAtRdbStats 5 }
     accAtRdbStatsDeletes OBJECT-TYPE
		SYNTAX	Counter
		ACCESS	read-only
		STATUS	mandatory
		DESCRIPTION
		 " The number of times a route was deleted from the
		   routing database."
		::= { accAtRdbStats 6 }
     -- The AtNbpStats Group
     accAtNbpStats OBJECT IDENTIFIER ::= { accAt 11 }
		-- Name Binding Protocol (NBP) statistics maintained and
		-- reported on a per-node basis.
     accAtNbpStatsInBrReqs OBJECT-TYPE
		SYNTAX	Counter
		ACCESS	read-only
		STATUS	mandatory
		DESCRIPTION
		 " The number of NBP broadcast request packets received."
		::= { accAtNbpStats 1 }
     accAtNbpStatsInLkUpReqs OBJECT-TYPE
		SYNTAX	Counter
		ACCESS	read-only
		STATUS	mandatory
		DESCRIPTION
		 " The number of NBP lookup request packets received."
		::= { accAtNbpStats 2 }
     accAtNbpStatsInLkUpResps OBJECT-TYPE
		SYNTAX	Counter
		ACCESS	read-only
		STATUS	mandatory
		DESCRIPTION
		 " The number of NBP lookup response packets received."
		::= { accAtNbpStats 3 }
     accAtNbpStatsInFwdReqs OBJECT-TYPE
		SYNTAX	Counter
		ACCESS	read-only
		STATUS	mandatory
		DESCRIPTION
		 " The number of NBP forward request packets received."
		::= { accAtNbpStats 4 }
     accAtNbpStatsOutBrReqs OBJECT-TYPE
		SYNTAX	Counter
		ACCESS	read-only
		STATUS	mandatory
		DESCRIPTION
		 " The number of NBP broadcast request packets sent."
		::= { accAtNbpStats 5 }
     accAtNbpStatsOutLkUpReqs OBJECT-TYPE
		SYNTAX	Counter
		ACCESS	read-only
		STATUS	mandatory
		DESCRIPTION
		 " The number of NBP lookup request packets sent."
		::= { accAtNbpStats 6 }
     accAtNbpStatsOutLkUpResps OBJECT-TYPE
		SYNTAX	Counter
		ACCESS	read-only
		STATUS	mandatory
		DESCRIPTION
		 " The number of NBP lookup response packets sent."
		::= { accAtNbpStats 7 }
     accAtNbpStatsOutFwdReqs OBJECT-TYPE
		SYNTAX	Counter
		ACCESS	read-only
		STATUS	mandatory
		DESCRIPTION
		 " The number of NBP forward request packets sent."
		::= { accAtNbpStats 8 }
     accAtNbpStatsNoZones OBJECT-TYPE
		SYNTAX	Counter
		ACCESS	read-only
		STATUS	mandatory
		DESCRIPTION
		 " The number of NBP request packets received which
		   referenced a zone name which was not in the zone
		   database."
		::= { accAtNbpStats 9 }
     accAtNbpStatsInErrors OBJECT-TYPE
		SYNTAX	Counter
		ACCESS	read-only
		STATUS	mandatory
		DESCRIPTION
		 " The number of NBP packets received which were invalid
		   or which could not be processed because of some internal
		   error."
		::= { accAtNbpStats 10 }
     accAtNbpStatsOutErrors OBJECT-TYPE
		SYNTAX	Counter
		ACCESS	read-only
		STATUS	mandatory
		DESCRIPTION
		 " The number of NBP packets which could not be sent
		   because of some internal error."
		::= { accAtNbpStats 11 }
     -- The AtZipStats Group
     accAtZipStats OBJECT IDENTIFIER ::= { accAt 12 }
		-- Zone Information Protocol (ZIP) statistics maintained
		-- and reported on a per-node basis.
     accAtZipStatsInQuerys OBJECT-TYPE
		SYNTAX	Counter
		ACCESS	read-only
		STATUS	mandatory
		DESCRIPTION
		 " The number of ZIP zone-list-query packets received."
		::= { accAtZipStats 1 }
     accAtZipStatsInReplies OBJECT-TYPE
		SYNTAX	Counter
		ACCESS	read-only
		STATUS	mandatory
		DESCRIPTION
		 " The number of ZIP zone-list-reply packets received."
		::= { accAtZipStats 2 }
     accAtZipStatsInExtReplies OBJECT-TYPE
		SYNTAX	Counter
		ACCESS	read-only
		STATUS	mandatory
		DESCRIPTION
		 " The number of ZIP extended zone-list-reply packets
		   received."
		::= { accAtZipStats 3 }
     accAtZipStatsInInfoReqs OBJECT-TYPE
		SYNTAX	Counter
		ACCESS	read-only
		STATUS	mandatory
		DESCRIPTION
		 " The number of ZIP get-network-information request
		   packets received."
		::= { accAtZipStats 4 }
     accAtZipStatsInInfoReps OBJECT-TYPE
		SYNTAX	Counter
		ACCESS	read-only
		STATUS	mandatory
		DESCRIPTION
		 " The number of ZIP get-network-information reply
		   packets received."
		::= { accAtZipStats 5 }
     accAtZipStatsInTakeDowns OBJECT-TYPE
		SYNTAX	Counter
		ACCESS	read-only
		STATUS	mandatory
		DESCRIPTION
		 " The number of ZIP take-down request packets received."
		::= { accAtZipStats 6 }
     accAtZipStatsInBringUps OBJECT-TYPE
		SYNTAX	Counter
		ACCESS	read-only
		STATUS	mandatory
		DESCRIPTION
		 " The number of ZIP bring-up request packets received."
		::= { accAtZipStats 7 }
     accAtZipStatsInNotifies OBJECT-TYPE
		SYNTAX	Counter
		ACCESS	read-only
		STATUS	mandatory
		DESCRIPTION
		 " The number of ZIP notify request packets received."
		::= { accAtZipStats 8 }
     accAtZipStatsInGetZLReqs OBJECT-TYPE
		SYNTAX	Counter
		ACCESS	read-only
		STATUS	mandatory
		DESCRIPTION
		 " The number of ZIP get-zone-list request packets
		   received."
		::= { accAtZipStats 9 }
     accAtZipStatsInGetLZReqs OBJECT-TYPE
		SYNTAX	Counter
		ACCESS	read-only
		STATUS	mandatory
		DESCRIPTION
		 " The number of ZIP get-local-zones request packets
		   received."
		::= { accAtZipStats 10 }
     accAtZipStatsInGetMZReqs OBJECT-TYPE
		SYNTAX	Counter
		ACCESS	read-only
		STATUS	mandatory
		DESCRIPTION
		 " The number of ZIP get-my-zone request packets received."
		::= { accAtZipStats 11 }
     accAtZipStatsOutQueries OBJECT-TYPE
		SYNTAX	Counter
		ACCESS	read-only
		STATUS	mandatory
		DESCRIPTION
		 " The number of ZIP zone-list-query packets sent."
		::= { accAtZipStats 12 }
     accAtZipStatsOutReplies OBJECT-TYPE
		SYNTAX	Counter
		ACCESS	read-only
		STATUS	mandatory
		DESCRIPTION
		 " The number of ZIP zone-list-reply packets sent."
		::= { accAtZipStats 13 }
     accAtZipStatsOutExtReplies OBJECT-TYPE
		SYNTAX	Counter
		ACCESS	read-only
		STATUS	mandatory
		DESCRIPTION
		 " The number of ZIP extended zone-list-reply packets
		   sent."
		::= { accAtZipStats 14 }
     accAtZipStatsOutInfoReqs OBJECT-TYPE
		SYNTAX	Counter
		ACCESS	read-only
		STATUS	mandatory
		DESCRIPTION
		 " The number of ZIP get-network-information request
		   packets sent."
		::= { accAtZipStats 15 }
     accAtZipStatsOutInfoReps OBJECT-TYPE
		SYNTAX	Counter
		ACCESS	read-only
		STATUS	mandatory
		DESCRIPTION
		 " The number of ZIP get-network-information reply
		   packets sent."
		::= { accAtZipStats 16 }
     accAtZipStatsOutGetZLReps OBJECT-TYPE
		SYNTAX	Counter
		ACCESS	read-only
		STATUS	mandatory
		DESCRIPTION
		 " The number of get-zone-list reply packets sent."
		::= { accAtZipStats 17 }
     accAtZipStatsOutGetLZReps OBJECT-TYPE
		SYNTAX	Counter
		ACCESS	read-only
		STATUS	mandatory
		DESCRIPTION
		 " The number of get-local-zones reply packets sent."
		::= { accAtZipStats 18 }
     accAtZipStatsOutGetMZReps OBJECT-TYPE
		SYNTAX	Counter
		ACCESS	read-only
		STATUS	mandatory
		DESCRIPTION
		 " The number of get-my-zone reply packets sent."
		::= { accAtZipStats 19 }
     accAtZipStatsZoneConflicts OBJECT-TYPE
		SYNTAX	Counter
		ACCESS	read-only
		STATUS	mandatory
		DESCRIPTION
		 " The number of ZIP packets received which conflicted
		   with zone list or default zone information configured
		   for the receiving port or garnered from another router."
		::= { accAtZipStats 20 }
     accAtZipStatsInErrors OBJECT-TYPE
		SYNTAX	Counter
		ACCESS	read-only
		STATUS	mandatory
		DESCRIPTION
		 " The number of ZIP packets received containing a
		   formatting error or which could not be processed
		   because of some internal error."
		::= { accAtZipStats 21 }
     accAtZipStatsOutErrors OBJECT-TYPE
		SYNTAX	Counter
		ACCESS	read-only
		STATUS	mandatory
		DESCRIPTION
		 " The number of ZIP packets which could not be sent
		   because of some internal error."
		::= { accAtZipStats 22 }
     -- The AtAepStats Group
     accAtAepStats OBJECT IDENTIFIER ::= { accAt 13 }
		-- AppleTalk Echo Protocol (AEP) statistics maintained
		-- and reported on a per-node basis.
     accAtAepStatsInErrors OBJECT-TYPE
		SYNTAX	Counter
		ACCESS	read-only
		STATUS	mandatory
		DESCRIPTION
		 " The number of AEP packets received which were invalid
		   or which could not be processed because of some internal
		   error."
		::= { accAtAepStats 1 }
     accAtAepStatsOutErrors OBJECT-TYPE
		SYNTAX	Counter
		ACCESS	read-only
		STATUS	mandatory
		DESCRIPTION
		 " The number of AEP packets which could not be sent
		   because of some internal error."
		::= { accAtAepStats 2 }
     -- The AtZoneListTable Group
     accAtZoneListTable OBJECT-TYPE
		SYNTAX	SEQUENCE OF AccAtZoneListEntry
		ACCESS	not-accessible
		STATUS	mandatory
		DESCRIPTION
		 " The zones list table for directly-connected AppleTalk
		   networks.  AppleTalk networks which are configured in
		   the network table have their zones list configured
		   here.  Zone names for individual networks are inter-
		   mingled in this table. "
		::= { accAt 14 }
     accAtZoneListEntry OBJECT-TYPE
		SYNTAX	AccAtZoneListEntry
		ACCESS	not-accessible
		STATUS	mandatory
		DESCRIPTION
		 " An entry defining a zone name for some directly
		   connected AppleTalk network."
                INDEX { accAtZoneListPort,
                            accAtZoneListName }
		::= { accAtZoneListTable 1 }
     AccAtZoneListEntry ::= SEQUENCE {
		accAtZoneListPort		INTEGER,
		accAtZoneListStatus		INTEGER,
		accAtZoneListName		DisplayString	
     }
     accAtZoneListPort OBJECT-TYPE
		SYNTAX	INTEGER (1..255)
		ACCESS	read-only
		STATUS	mandatory
		DESCRIPTION
		 " The logical port number."
		::= { accAtZoneListEntry 1 }
     accAtZoneListStatus OBJECT-TYPE
		SYNTAX	INTEGER {
			configured(1),
			default(2),
			invalid(3)
		}
		ACCESS	read-write
		STATUS	mandatory
		DESCRIPTION
		 " The status of the zone list entry.  If set to
		   default(2), the entry defines the default zone.
		   Entries are deleted by setting the entry status
		   to invalid(3)."
		::= { accAtZoneListEntry 2 }
     accAtZoneListName OBJECT-TYPE
		SYNTAX  DisplayString	
		ACCESS	read-only
		STATUS	mandatory
		DESCRIPTION
		 " The zone name.  Zone names can contain up to 32
		   case-insensitive characters from the Apple Macintosh
		   character set."
		::= { accAtZoneListEntry 3 }
     -- The AtZoneBynameTable Group
     accAtZoneBynameTable OBJECT-TYPE
		SYNTAX	SEQUENCE OF AccAtZoneBynameEntry
		ACCESS	not-accessible
		STATUS	mandatory
		DESCRIPTION
		 " Used to display entries in the Zone Information
		   Table (ZIT) which are associated with a particular
		   zone name."
		::= { accAt 15 }
     accAtZoneBynameEntry OBJECT-TYPE
		SYNTAX	AccAtZoneBynameEntry
		ACCESS	not-accessible
		STATUS	mandatory
		DESCRIPTION
		 " An entry in the zone information table (ZIT) with a
		   given zone name."
                INDEX { accAtZoneBynameNetMin,
		            accAtZoneBynameName }
		::= { accAtZoneBynameTable 1 }
     AccAtZoneBynameEntry ::= SEQUENCE {
		accAtZoneBynameNetMin		OCTET STRING,
		accAtZoneBynameNetMax		OCTET STRING,
		accAtZoneBynameName		DisplayString	
     }
     accAtZoneBynameNetMin OBJECT-TYPE
		SYNTAX	OCTET STRING
		ACCESS	read-only
		STATUS	mandatory
		DESCRIPTION
		 " The 16-bit range start value for an AppleTalk network."
		::= { accAtZoneBynameEntry 1 }
     accAtZoneBynameNetMax OBJECT-TYPE
		SYNTAX	OCTET STRING
		ACCESS	read-only
		STATUS	mandatory
		DESCRIPTION
		 " The 16-bit range end value for an AppleTalk network."
		::= { accAtZoneBynameEntry 2 }
     accAtZoneBynameName OBJECT-TYPE
		SYNTAX  DisplayString	
		ACCESS	read-only
		STATUS	mandatory
		DESCRIPTION
		 " The AppleTalk zone name."
		::= { accAtZoneBynameEntry 3 }
     -- The AtZoneBynetTable Group
     accAtZoneBynetTable OBJECT-TYPE
		SYNTAX	SEQUENCE OF AccAtZoneBynetEntry
		ACCESS	not-accessible
		STATUS	mandatory
		DESCRIPTION
		 " Used to display entries in the Zone Information
		   Table (ZIT) which are associated with a particular
		   AppleTalk network."
		::= { accAt 16 }
     accAtZoneBynetEntry OBJECT-TYPE
		SYNTAX	AccAtZoneBynetEntry
		ACCESS	not-accessible
		STATUS	mandatory
		DESCRIPTION
		 " An entry in the zone information table (ZIT) associated
		   with a given AppleTalk network."
                INDEX { accAtZoneBynameNetMin,
		            accAtZoneBynameName }
		::= { accAtZoneBynetTable 1 }
     AccAtZoneBynetEntry ::= SEQUENCE {
		accAtZoneBynetNetMin		OCTET STRING,
		accAtZoneBynetNetMax		OCTET STRING,
		accAtZoneBynetName		DisplayString	
     }
     accAtZoneBynetNetMin OBJECT-TYPE
		SYNTAX	OCTET STRING
		ACCESS	read-only
		STATUS	mandatory
		DESCRIPTION
		 " The 16-bit range start value for an AppleTalk network."
		::= { accAtZoneBynetEntry 1 }
     accAtZoneBynetNetMax OBJECT-TYPE
		SYNTAX	OCTET STRING
		ACCESS	read-only
		STATUS	mandatory
		DESCRIPTION
		 " The 16-bit range end value for an AppleTalk network."
		::= { accAtZoneBynetEntry 2 }
     accAtZoneBynetName OBJECT-TYPE
		SYNTAX  DisplayString	
		ACCESS	read-only
		STATUS	mandatory
		DESCRIPTION
		 " The AppleTalk zone name."
		::= { accAtZoneBynetEntry 3 }
--  AppleTalk Forwarding Filter Table
--	AppleTalk Filters are of the form:
--
--	if message is within
--		to-address-range
--		from-address-range
--		socket-range
--		AppleTalk Application
--	then
--		{DISCARD | LOW | NORMAL | HIGH}
     accAtForwardFilterTable OBJECT-TYPE
         SYNTAX   SEQUENCE OF AccAtForwardFilterEntry
         ACCESS   not-accessible
         STATUS   mandatory
         DESCRIPTION
              " A list of descriptions of specific AppleTalk Filters."
         ::= { accAt 17 }
        accAtForwardFilterEntry OBJECT-TYPE
            SYNTAX   AccAtForwardFilterEntry
            ACCESS   not-accessible
            STATUS   mandatory
            DESCRIPTION
                  " The parameters for a single AppleTalk Filter."
            INDEX { accAtForwardFilterToMin, 
                accAtForwardFilterToMax,
	        accAtForwardFilterFromMin, 
                accAtForwardFilterFromMax,
	        accAtForwardFilterSocketMin, 
                accAtForwardFilterSocketMax,
	        accAtForwardFilterType }
            ::= { accAtForwardFilterTable 1 }
        AccAtForwardFilterEntry ::=
            SEQUENCE {
                accAtForwardFilterToMin
                    OCTET STRING,
                accAtForwardFilterToMax
                    OCTET STRING,
                accAtForwardFilterFromMin
                    OCTET STRING,
                accAtForwardFilterFromMax
                    OCTET STRING,
                accAtForwardFilterSocketMin
                    INTEGER,
                accAtForwardFilterSocketMax
                    INTEGER,
                accAtForwardFilterType
                    INTEGER,
                accAtForwardFilterDisposition
                    INTEGER,
                accAtForwardFilterStatus
                    INTEGER
	        }
           accAtForwardFilterToMin OBJECT-TYPE
               SYNTAX   OCTET STRING -- (SIZE(2))
               ACCESS   read-write
               STATUS   mandatory
               DESCRIPTION
                   "  The least value in the destination network address range."
               ::= { accAtForwardFilterEntry 1 }
           accAtForwardFilterToMax OBJECT-TYPE
               SYNTAX   OCTET STRING  -- (SIZE(2))
               ACCESS   read-write
               STATUS   mandatory
               DESCRIPTION
                     " The greatest value in the destination network address range."
               ::= { accAtForwardFilterEntry 2 }
           accAtForwardFilterFromMin OBJECT-TYPE
               SYNTAX   OCTET STRING  -- (SIZE(2))
               ACCESS   read-write
               STATUS   mandatory
               DESCRIPTION
                     " The least value in the source network address range."
               ::= { accAtForwardFilterEntry 3 }
           accAtForwardFilterFromMax OBJECT-TYPE
               SYNTAX   OCTET STRING  -- (SIZE(2))
               ACCESS   read-write
               STATUS   mandatory
               DESCRIPTION
                    " The greatest value in the source network address range."
               ::= { accAtForwardFilterEntry 4 }
           accAtForwardFilterSocketMin OBJECT-TYPE
               SYNTAX   INTEGER (0..255)
               ACCESS   read-write
               STATUS   mandatory
               DESCRIPTION
                    " The least value in the range of affected sockets."
               ::= { accAtForwardFilterEntry 5 }
           accAtForwardFilterSocketMax OBJECT-TYPE
               SYNTAX   INTEGER (0..255)
               ACCESS   read-write
               STATUS   mandatory
               DESCRIPTION
                    " The greatest value in the range of affected sockets."
               ::= { accAtForwardFilterEntry 6 }
           accAtForwardFilterType OBJECT-TYPE
               SYNTAX   INTEGER {
                           any(1),	-- all traffic
                           nbp(2),	-- Name Binding Protocol
                           atp(3),	-- Transaction Protocol
                           aep(4),	-- Echo Protocol
                           rtmp(5),	-- Routing Table Management Protocol
				-- request/response (type 5) or
				-- update (type 1)
                           zip(6),	-- Zone Information Protocol
		           adsp(7),	-- Data Stream Protocol
                           nbpBroadcast(8),
                           nbpRequest(9),	
                           nbpResponse(10),
                           nbpForwardRequest(11)
                        }
               ACCESS   read-write
               STATUS   mandatory
               DESCRIPTION
                       " The affected message types.
                         Name Binding Protocol messages are called out separately,
                         as some applications call for selective discrimination."
               ::= { accAtForwardFilterEntry 7 }
           accAtForwardFilterDisposition OBJECT-TYPE
               SYNTAX   INTEGER {
                           discard(0),
                           lowPriority(1),
                           normalPriority(2),
                           highPriority(3)
                        }
               ACCESS   read-write
               STATUS   mandatory
               DESCRIPTION
                      " Upon a filter match, this specifies the action taken.
			"
               ::= { accAtForwardFilterEntry 8 }
           accAtForwardFilterStatus OBJECT-TYPE
               SYNTAX   INTEGER {
                           invalid(1),
                           valid(2)
                        }
               ACCESS   read-write
               STATUS   mandatory
               DESCRIPTION
                     " Writing 'invalid' deletes the filter table entry."
               ::= { accAtForwardFilterEntry 9 }
--  AppleTalk Route Filter
--	AppleTalk Route Filters are of the form:
--
--	if an update is received from someone in the range
--		router-address-range
--	and it advertises an address range
--		address-range
--	then
--		{ ACCEPT | REJECT } the range
--
--	it is expected that neighboring routers may advertise
--	ranges that don't exactly overlap.  It is expected that
--	advertised ranges that include both rejected and accepted
--	subranges will be treated as a succession of more limited
--	advertisements, each entirely accepted or rejected.
     accAtRouteFilterTable OBJECT-TYPE
         SYNTAX   SEQUENCE OF AccAtRouteFilterEntry
         ACCESS   not-accessible
         STATUS   mandatory
         DESCRIPTION
             "  A list of Route Filters."
         ::= { accAt 18 }
        accAtRouteFilterEntry OBJECT-TYPE
            SYNTAX   AccAtRouteFilterEntry
            ACCESS   not-accessible
            STATUS   mandatory
            DESCRIPTION
                 " A single Route Filter."
            INDEX { accAtRouteFilterRouterMin, 
                accAtRouteFilterRouterMax,
	        accAtRouteFilterRangeMin, 
                accAtRouteFilterRangeMax }
            ::= { accAtRouteFilterTable 1 }
        AccAtRouteFilterEntry ::=
            SEQUENCE {
                accAtRouteFilterRouterMin
                    OCTET STRING,
                accAtRouteFilterRouterMax
                    OCTET STRING,
                accAtRouteFilterRangeMin
                    OCTET STRING,
                accAtRouteFilterRangeMax
                    OCTET STRING,
                accAtRouteFilterDisposition
                    INTEGER,
                accAtRouteFilterStatus
                    INTEGER
	        }
           accAtRouteFilterRouterMin OBJECT-TYPE
               SYNTAX   OCTET STRING  -- (SIZE(2))
               ACCESS   read-write
               STATUS   mandatory
               DESCRIPTION
                    " The least affected Router's Network Address."
               ::= { accAtRouteFilterEntry 1 }
           accAtRouteFilterRouterMax OBJECT-TYPE
               SYNTAX   OCTET STRING  -- (SIZE(2))
               ACCESS   read-write
               STATUS   mandatory
               DESCRIPTION
                 " The greatest affected Router's Network Address."
               ::= { accAtRouteFilterEntry 2 }
           accAtRouteFilterRangeMin OBJECT-TYPE
               SYNTAX   OCTET STRING  -- (SIZE(2))
               ACCESS   read-write
               STATUS   mandatory
               DESCRIPTION
                  " The least Network Address in this range."
               ::= { accAtRouteFilterEntry 3 }
           accAtRouteFilterRangeMax OBJECT-TYPE
               SYNTAX   OCTET STRING  -- (SIZE(2))
               ACCESS   read-write
               STATUS   mandatory
               DESCRIPTION
                    " The greatest Network Address in this range."
               ::= { accAtRouteFilterEntry 4 }
           accAtRouteFilterDisposition OBJECT-TYPE
               SYNTAX   INTEGER {
                           accept(1),
                           reject(2)
                        }
               ACCESS   read-write
               STATUS   mandatory
               DESCRIPTION
                     " What is to be done with matching advertisements."
               ::= { accAtRouteFilterEntry 5 }
           accAtRouteFilterStatus OBJECT-TYPE
               SYNTAX   INTEGER {
                           invalid(1),
                           valid(2)
                        }
               ACCESS   read-write
               STATUS   mandatory
               DESCRIPTION
                   " Writing 'invalid' has the effect of deleting the filter."
               ::= { accAtRouteFilterEntry 6 }

END
