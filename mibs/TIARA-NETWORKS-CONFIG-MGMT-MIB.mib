-- *****************************************************************
-- tiaranet-config.mib:  Configuration Management MIB
--
-- April,1st 1998, Shyla
--
--
-- Copyright (c) 1998-2005 by Tiara Networks, Inc.
-- All rights reserved.
-- 
-- *****************************************************************

TIARA-NETWORKS-CONFIG-MGMT-MIB DEFINITIONS ::= BEGIN

IMPORTS
        OBJECT-TYPE,
        IpAddress, TimeTicks,
        MODULE-IDENTITY,
        Integer32
                FROM SNMPv2-SMI
        DisplayString, TEXTUAL-CONVENTION,TruthValue
                FROM SNMPv2-TC
        TRAP-TYPE
                FROM RFC-1215
	tiaraMgmt
	        FROM TIARA-NETWORKS-SMI;

tiaraConfigMgmtMib MODULE-IDENTITY 
  	LAST-UPDATED	"0008160000Z"
  	ORGANIZATION	"Tiara Networks"
  	CONTACT-INFO
                "       Tiara Networks
                        Customer Service

                		525 Race Street, Suite 100,
                        San Jose, CA 95126
                        USA

                   	Tel: +1 408-216-4700
                   	Fax: +1 408-216-4701

                		Email: support@tiaranetworks.com"

  	DESCRIPTION
  		"Configuration management MIB.
  
  		This MIB represents a model of configuration data that
  		exists in various locations:
  
  		current		In use by the running system.
  		local			Saved locally in NVRAM or flash.
  		remote		Saved to some server on the network.
  
  		The purpose of this MIB is to track changes and saves of the 
  		current configuration."
  	REVISION	"0008160000Z"
  	DESCRIPTION
  		"Initial version of this MIB module."
               ::= { tiaraMgmt 4 }



cfgOperations		OBJECT IDENTIFIER ::= { tiaraConfigMgmtMib 1 }
cfgMgmtEvents		OBJECT IDENTIFIER ::= { tiaraConfigMgmtMib 2 }
cfgNotificationEnables	OBJECT IDENTIFIER ::= { tiaraConfigMgmtMib 3 }
cfgMgmtNotifications	OBJECT IDENTIFIER ::= { tiaraConfigMgmtMib 4 }

--
-- Configuration operation group. This group allows network management
-- software to save the configuration and configure from the 
-- network file.
--


cfgNetOperTable  OBJECT-TYPE
	SYNTAX	SEQUENCE OF CfgNetOperEntry
	MAX-ACCESS	not-accessible
	STATUS	current
	DESCRIPTION  
		"A table of configuration from network operation entries. 
		Each entry represents a separate operation to configure the
		system from a file located on a server on the network. The
		management station should create an entry with a random number
		as an index to perform the operation. The management station 
		should then retrieve the entry with the same random number as 
		an index and examine the value of the cfgNetOperStatus variable 
		to get the status of the operation.
		"
	::= { cfgOperations 1 }

cfgNetOperEntry  OBJECT-TYPE
	SYNTAX	CfgNetOperEntry
	MAX-ACCESS	not-accessible
	STATUS	current
	DESCRIPTION
		"Entry to initiate an operation. Each entry consists  
		of a command and required parameters. Once the operation
		completes, the management station should retrieve the 
		value of the status object and delete the entry from 
		the table."

	INDEX	{ cfgNetOperRandomNumber }
	::= { cfgNetOperTable 1 }

CfgNetOperEntry ::=
	SEQUENCE {
		cfgNetOperRandomNumber	Integer32, 
		cfgNetOperCommand 	INTEGER,
		cfgNetOperAddress	IpAddress,
		cfgNetOperFileName	DisplayString,
		cfgNetOperStatus	INTEGER
	}

cfgNetOperRandomNumber OBJECT-TYPE
	SYNTAX  Integer32
	MAX-ACCESS	not-accessible
	STATUS	current
	DESCRIPTION
		"Object specifying a unique entry in the table.  
		A management station wishing to initiate a 
		configuration operation should use a pseudo-random
		value for this object when creating a cfgNetOperEntry.
		"
	::=   { cfgNetOperEntry 1 }

cfgNetOperCommand OBJECT-TYPE
	SYNTAX	INTEGER
		{
		config(1),
		save(2)
		}
	MAX-ACCESS	read-write
	STATUS	current
	DESCRIPTION
		"The commands to be executed configure from the network 
		or save the configuration to the network.

		Command		Remarks.
		config		Configure from network.
		save		      Save configuration to network.
		"
	::= { cfgNetOperEntry 2 }

cfgNetOperAddress OBJECT-TYPE
	SYNTAX     IpAddress
	MAX-ACCESS 	   read-write
	STATUS     current
	DESCRIPTION
		"The Internet address of the server."
	::= { cfgNetOperEntry 3 }

	
cfgNetOperFileName OBJECT-TYPE
	SYNTAX	DisplayString (SIZE (1..64))
	MAX-ACCESS	read-write
	STATUS	current
	DESCRIPTION
		"The destination or source file name on the network server.
		"
	::= { cfgNetOperEntry 4 }

cfgNetOperStatus OBJECT-TYPE
	SYNTAX	INTEGER
		{  
		idle(0),
		inProgress(1),
		operationSuccess (2),
		networkError (3),
		fileAccessError (4),
		serverAccessError (5),
		fileOpenError (6),
		notEnoughMemory (7),
		unknownFailure(8)
		}
	MAX-ACCESS	read-only
	STATUS	current
	DESCRIPTION
		"Represents the status of the operation. If the operation 
		 has not started or an operation is not being performed, 
		 then the value of this object would be idle(0)."
                
	::= { cfgNetOperEntry 5 }

--
-- Configuration operation group. This group allows network management 
-- software to save a configuration or configure from the local 
-- flash-file system.
--
cfgFlashOperTable  OBJECT-TYPE
	SYNTAX	SEQUENCE OF CfgFlashOperEntry
	MAX-ACCESS	not-accessible
	STATUS	current
	DESCRIPTION  
		"A table of config/save from/to flash operation entries. 
		Each entry represents a separate operation to configure the
		system from a file located on a local flash-file system. 
		The management station should create an entry with a random 
		number as an index to perform the operation. The management 
		station should then retrive the entry with the same random 
		number as an index and examine the value of the
		cfgFlashOperStatus variable to get the status of the 
		operation.
		"
	::= { cfgOperations 2 }

cfgFlashOperEntry  OBJECT-TYPE
	SYNTAX	CfgFlashOperEntry
	MAX-ACCESS	not-accessible
	STATUS	current
	DESCRIPTION
		"Entry to initiate an operation. Each entry consists  
		of a command and required parameters. Once the operation
		completes, the management station should retrieve the
		value of the status object and delete the entry from the 
		table.
		"
	INDEX	{ cfgFlashOperRandomNumber }
	::= { cfgFlashOperTable 1 }

CfgFlashOperEntry ::=
	SEQUENCE {
		cfgFlashOperRandomNumber	Integer32,
		cfgFlashOperCommand 	INTEGER,
		cfgFlashOperFileName	DisplayString,
		cfgFlashOperStatus	INTEGER
	}

cfgFlashOperRandomNumber OBJECT-TYPE
	SYNTAX	Integer32
	MAX-ACCESS	not-accessible
	STATUS	current
	DESCRIPTION
		"Object specifying a unique entry in the table. A 
		management station wishing to initiate a configuration
		operation should use a pseudo-random value for this 
		object when creating a cfgFlashOperEntry.
		"
	::=   { cfgFlashOperEntry 1 }

cfgFlashOperCommand OBJECT-TYPE
	SYNTAX	INTEGER
		{
		save(1),
        erase(2),
        config(3)
		}
	MAX-ACCESS	read-write
	STATUS	current
	DESCRIPTION
		"The commands to be executed configure from the 
		network or save the configuration to the network.

		Command		Remarks.
		config		Config from network.
		save			Save the configuration to the network.
		"
	::= { cfgFlashOperEntry 2 }
	
cfgFlashOperFileName OBJECT-TYPE
	SYNTAX	DisplayString (SIZE (1..64))
	MAX-ACCESS	read-write
	STATUS	current
	DESCRIPTION
		"The destination or source file name on the network server.
		"
	::= { cfgFlashOperEntry 3 }

cfgFlashOperStatus OBJECT-TYPE
	SYNTAX	INTEGER
		{  
		idle(0),
		inProgress(1),
		operationSuccess (2),
		networkError (3),
		fileAccessError (4),
		serverAccessError (5),
		fileOpenError (6),
		notEnoughMemory (7),
		unknownFailure(8)
		}
	MAX-ACCESS	read-only
	STATUS	current
	DESCRIPTION
		"The status of the operation. If the operation has not 
		started or an operation is not being performed, then 
		the value of this	object would be idle(0).
                "
	::= { cfgFlashOperEntry 4 }

--
-- Textual Convention to define the enumeration
--
CfgMedium ::= TEXTUAL-CONVENTION 
  	STATUS     current
  	DESCRIPTION
  		"The source or destination of a configuration change,
  		save, or copy.
  
  		commandSource	The source of the command.
  		current		Live operational data from RAM.
  		flash			Local flash.
  		network		Network host.
  		"
       SYNTAX INTEGER 
               { 
                commandSource(1), 
		current(2), 
		flash(3),
		erase-flash(4),
		network(5) 
               }

--
-- Configuration event history group. This group allows network 
-- management software to monitor configuration changes and saves.
-- All the objects in this group are saved to flash when the 
-- operation "save to flash" is executed.
--
cfgCurrentLastChanged OBJECT-TYPE
	SYNTAX     TimeTicks
	MAX-ACCESS read-only
	STATUS     current
	DESCRIPTION
		"The last time the current configuration was changed."
	::= { cfgMgmtEvents 1 }

cfgCurrentLastSaved OBJECT-TYPE
	SYNTAX     TimeTicks
	MAX-ACCESS read-only
	STATUS     current
	DESCRIPTION
		"The last time the current configuration was saved."
	::= { cfgMgmtEvents 2 }

cfgMaxEvents OBJECT-TYPE
	SYNTAX     INTEGER (0..20)
	MAX-ACCESS read-only
	STATUS     current
	DESCRIPTION
		"The maximum number of entries that can be held in the
		cfgEventTable. The system stores the 20 most recent 
		history events in a circular style. These events are 
		also saved to flash. Up to the last 10 entries can 
		be saved if space is available in flash."
	::= { cfgMgmtEvents 3 }

cfgEventTable OBJECT-TYPE
	SYNTAX     SEQUENCE OF CfgEventEntry
	MAX-ACCESS not-accessible
	STATUS     current
	DESCRIPTION
		"A table of configuration history events."
	::= { cfgMgmtEvents 4 }

cfgEventEntry OBJECT-TYPE
	SYNTAX     CfgEventEntry
	MAX-ACCESS not-accessible
	STATUS     current
	DESCRIPTION
		"Entry holding information about a configuration event."
	INDEX	{ cfgEventIndex }
	::= { cfgEventTable 1 }

CfgEventEntry ::=
    SEQUENCE {
	cfgEventIndex
		INTEGER,
	cfgEventTime
		TimeTicks,
	cfgEventConfigProtocol
       	INTEGER,
	cfgEventConfigSrc
       	CfgMedium,
	cfgEventConfigDst
       	CfgMedium,
	cfgEventLoginType
		INTEGER,
	cfgEventTerminalUser
		DisplayString,
	cfgEventConfigSrcAddress
		IpAddress,
	cfgEventFileName
		DisplayString
    }

cfgEventIndex OBJECT-TYPE
	SYNTAX     INTEGER (0..19)
	MAX-ACCESS not-accessible
	STATUS     current
	DESCRIPTION
		"Index in the history event table."
	::= { cfgEventEntry 1 }

cfgEventTime OBJECT-TYPE
	SYNTAX     TimeTicks
	MAX-ACCESS read-only
	STATUS     current
	DESCRIPTION
		"The time when the configuration occurred."
	::= { cfgEventEntry 2 }

cfgEventConfigProtocol OBJECT-TYPE
       	SYNTAX  INTEGER { commandLine(1), snmp(2), http(3) }
	MAX-ACCESS read-only
	STATUS     current
	DESCRIPTION
		"The source of the command that resulted in the event."
	::= { cfgEventEntry 3 }

cfgEventConfigSrc OBJECT-TYPE
       	SYNTAX  CfgMedium
	MAX-ACCESS read-only
	STATUS     current
	DESCRIPTION
		"The configuration data source for the event."
	::= { cfgEventEntry 4 }

cfgEventConfigDst OBJECT-TYPE
       	SYNTAX  CfgMedium
	MAX-ACCESS read-only
	STATUS     current
	DESCRIPTION
		"The configuration data destination for the event."
	::= { cfgEventEntry 5 }

cfgEventLoginType OBJECT-TYPE
	SYNTAX	INTEGER {
		unknown(1),
		console(2),
		telnet(3),
		rlogin(4),
		dial(5),
		other(6)
		}						
	MAX-ACCESS read-only
	STATUS     current
	DESCRIPTION
		"Configuration via telnet or rlogin, etc.
		"
	::= { cfgEventEntry 6 }

cfgEventTerminalUser OBJECT-TYPE
	SYNTAX     DisplayString (SIZE (0..15))
	MAX-ACCESS read-only
	STATUS     current
	DESCRIPTION
		"This object represents the logged in user name 
		if configuration is via the CLI. It represents 
		the community name if configuration is via SNMP. 
		Otherwise, the object string length is zero if not 
		available or not applicable."
	::= { cfgEventEntry 7 }

cfgEventConfigSrcAddress OBJECT-TYPE
	SYNTAX     IpAddress
	MAX-ACCESS read-only
	STATUS     current
	DESCRIPTION
		"The Internet address of the connected system.
		The value is 0.0.0.0 if not available or not applicable."
	::= { cfgEventEntry 8 }


cfgEventFileName OBJECT-TYPE
	SYNTAX     DisplayString (SIZE (0..64))
	MAX-ACCESS read-only
	STATUS     current
	DESCRIPTION
		"If the system is set for configuration via a network, 
		then this object represents the file name on some 
		server."
	::= { cfgEventEntry 9 }


--
-- cfgNotificationEnables group
--
cfgEnableChangeNotification OBJECT-TYPE
        SYNTAX 	    TruthValue
        MAX-ACCESS  read-write
        STATUS      current
        DESCRIPTION
               "Indicates whether the system produces the 
		cfgChangeNotification. The default is yes.
		"
        DEFVAL { true }
        ::= { cfgNotificationEnables 1 }

cfgEnableSaveNotification OBJECT-TYPE
        SYNTAX 	    TruthValue
        MAX-ACCESS  read-write
        STATUS      current
        DESCRIPTION
               "Indicates whether the system produces the 
		cfgSaveNotification. The default is yes.
		"
        DEFVAL { true }
        ::= { cfgNotificationEnables 2 }

--
-- Configuration event notification group, This group allows 
-- the agent to send either traps or info request PDU to
-- the network management software for notification of the 
-- configuration change or save event.
--
cfgEventChangeNotification TRAP-TYPE
	ENTERPRISE cfgMgmtNotifications
	VARIABLES { cfgEventConfigProtocol, 
		 cfgEventConfigSrc,
		 cfgEventConfigDst }
       	DESCRIPTION
		"Send the configuration change event via either trap or
		info request PDU"
		--#TYPE "Configuration Change Event"
		--#SUMMARY "Configuration Change Event. Command source: %s Config source: %s Config destination: %s"
		--#ARGUMENTS {0,1,2}
		--#SEVERITY NORMAL
	::= 1

cfgEventSaveNotification TRAP-TYPE
	ENTERPRISE cfgMgmtNotifications
	VARIABLES { cfgEventConfigProtocol, 
		 cfgEventConfigSrc,
		 cfgEventConfigDst }
       	DESCRIPTION
		"Send the configuration save event via either trap or
		info request PDU"
        --#TYPE "Configuration Save Event"
        --#SUMMARY "Configuration Save Event. Command source: %s Config source: %s Config destination: %s"
        --#ARGUMENTS {0,1,2}
        --#SEVERITY NORMAL

	::= 2

END
