CNTDNSEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, RowStatus
			FROM SNMPv2-TC
		apCntName, apCntOwner
			FROM CNTEXT-MIB
		cntdnsExt
			FROM APENT-MIB;

--CNTDNSEXT MIB

    apCntdnsExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  content rule dns names table"
      ::= { cntdnsExt 1}


apCntdnsTable OBJECT-TYPE
	SYNTAX          SEQUENCE OF APCntdnsEntry
	MAX-ACCESS      not-accessible
	STATUS          current
	DESCRIPTION
		"A list of content rule dns entries."
	::= { cntdnsExt 2 }

apCntdnsEntry OBJECT-TYPE
	SYNTAX          APCntdnsEntry
	MAX-ACCESS      not-accessible
	STATUS          current
	DESCRIPTION
		"A group of information to uniquely identify a content providing 
		dns name."
	INDEX   { apCntOwner, apCntName, apCntdnsName }
	::= { apCntdnsTable 1 }

APCntdnsEntry ::= SEQUENCE {
		apCntdnsName              DisplayString,
		apCntdnsNameLen           Integer32,
		apCntdnsHits              Integer32,
		apCntdnsLoad              Integer32,
                apCntdnsTtl               Integer32,
		apCntdnsStatus            RowStatus
}

apCntdnsName OBJECT-TYPE
	SYNTAX          DisplayString (SIZE(1..31))
	MAX-ACCESS      read-create
	STATUS          current
	DESCRIPTION     
			"The dns name."
	::= {apCntdnsEntry 1}

apCntdnsNameLen OBJECT-TYPE
	SYNTAX          Integer32
	MAX-ACCESS      read-create
	STATUS  		current
	DESCRIPTION     
		"Length of DNS name in bytes."
	DEFVAL { 0 }
	::= {apCntdnsEntry 2}

apCntdnsHits OBJECT-TYPE
	SYNTAX          Integer32
	MAX-ACCESS      read-create
	STATUS  		current
	DESCRIPTION     
		"Total number lookups made for this content rule dns name."
	DEFVAL { 0 }
	::= {apCntdnsEntry 3}

apCntdnsLoad OBJECT-TYPE
	SYNTAX          Integer32
	MAX-ACCESS      read-create
	STATUS  		current
	DESCRIPTION     
		"The last calculated load for this dns name."
	DEFVAL { 0 }
	::= {apCntdnsEntry 4}

apCntdnsTtl OBJECT-TYPE
	SYNTAX          Integer32
	MAX-ACCESS      read-create
	STATUS  		current
	DESCRIPTION
	       "The Time to Live Value returned in DNS Responses"
	DEFVAL { 0 }
	::= {apCntdnsEntry 5}

apCntdnsStatus OBJECT-TYPE
	SYNTAX          RowStatus
	MAX-ACCESS      read-create
	STATUS          current
	DESCRIPTION      
		"Status entry for this row "
	::= {apCntdnsEntry 6}
END
