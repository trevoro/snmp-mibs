--              Isolan House
--              Brindley Way
--              London Road
--              Hemel Hempstead
--              Hertfordshire
--              HP3 9XJ
--              England
--              (0442) 231000

--              Jan 30, 1992

--              This document defines the OBJECTS in the BICC terminal server
--              linecard private MIB.


    BICC-TrmSvr DEFINITIONS ::= BEGIN

    IMPORTS
      enterprises, Counter, IpAddress, TimeTicks
    FROM RFC1155-SMI
      OBJECT-TYPE
    FROM RFC-1212
      DisplayString
    FROM RFC1213-MIB;


      -- Object Identifiers

           bicc               OBJECT IDENTIFIER ::= { enterprises 170 }
           bdn                OBJECT IDENTIFIER ::= { bicc 1 }
           devices            OBJECT IDENTIFIER ::= { bdn 1 }
           terminal-server    OBJECT IDENTIFIER ::= { devices 2 }

           -- the following 4 entire subtrees are deprecated

           port               OBJECT IDENTIFIER ::= { terminal-server 1 }
           server             OBJECT IDENTIFIER ::= { terminal-server 2 }
           service            OBJECT IDENTIFIER ::= { terminal-server 3 }
           slot               OBJECT IDENTIFIER ::= { terminal-server 4 }

           -- the non-deprecated OBJECTs

           serverAdmin        OBJECT IDENTIFIER ::= { terminal-server 5 }

           serverMibs         OBJECT IDENTIFIER ::= { terminal-server 6 }

           -- serverDevice defines OBJECT IDENTIFIERs for different products

           serverDevice       OBJECT IDENTIFIER ::= { serverAdmin 1 }

           vcpServerDevice    OBJECT IDENTIFIER ::= { serverDevice 1 }

           -- serverProtocol defines OBJECT IDENTIFIERs for different
           -- communications protocols.

           serverProtocol     OBJECT IDENTIFIER ::= { serverAdmin 2 }

           protNone            OBJECT IDENTIFIER ::= { serverProtocol 1 }
           protTelnet          OBJECT IDENTIFIER ::= { serverProtocol 2 }
           protRlogin          OBJECT IDENTIFIER ::= { serverProtocol 3 }
           protLt              OBJECT IDENTIFIER ::= { serverProtocol 4 }


           -- vcpServerMib defines MIB for the VCP terminal-server device

           vcpServerMib       OBJECT IDENTIFIER ::= { serverMibs 1 }


           -- groups in vcpServerMib

           vcpSystem          OBJECT IDENTIFIER ::= { vcpServerMib 1 }
           vcpPort            OBJECT IDENTIFIER ::= { vcpServerMib 2 }
           vcpService         OBJECT IDENTIFIER ::= { vcpServerMib 3 }
           vcpProfile         OBJECT IDENTIFIER ::= { vcpServerMib 4 }
           vcpIpSecurity      OBJECT IDENTIFIER ::= { vcpServerMib 5 }
           vcpHostname        OBJECT IDENTIFIER ::= { vcpServerMib 6 }
           vcpNameserver      OBJECT IDENTIFIER ::= { vcpServerMib 7 }
           vcpTacacs          OBJECT IDENTIFIER ::= { vcpServerMib 8 }
           vcpIp              OBJECT IDENTIFIER ::= { vcpServerMib 9 }
           vcpArp             OBJECT IDENTIFIER ::= { vcpServerMib 10 }
           vcpTcp             OBJECT IDENTIFIER ::= { vcpServerMib 11 }
           vcpTelnet          OBJECT IDENTIFIER ::= { vcpServerMib 12 }
           vcpRlogin          OBJECT IDENTIFIER ::= { vcpServerMib 13 }
           vcpLt              OBJECT IDENTIFIER ::= { vcpServerMib 14 }
           vcpQueue           OBJECT IDENTIFIER ::= { vcpServerMib 15 }
           vcpSnmp            OBJECT IDENTIFIER ::= { vcpServerMib 16 }

           -- new types for convenience

           Character      ::=
                INTEGER (0..255)

           DisplayChar    ::=
                INTEGER (32..126)

-- LtGroupList is an OCTET STRING which represents a set of LAT-compatible
-- groups (0-255).  Each LAT-compatible group is represented by one octet of
-- the string, the value of which is the LAT-compatible group number.  For
-- example, the value '0,1,35,124,255' would represent the set of LAT-
-- compatible groups 0, 1, 35, 124 and 255.  A zero-length string represents 
-- an empty set.  Objects of type LtGroupList must have a length which is less
-- than or equal to 256 octets.

           LtGroupList          ::=
                OCTET STRING


           -- the vcpSystem group

           vSysIdentifier OBJECT-TYPE
             SYNTAX  OBJECT IDENTIFIER
             ACCESS  read-only
             STATUS  mandatory
             DESCRIPTION
                     "A unique identifier of the server type.  The OID is
                     one of those found under { serverDevice }, such as
                     { vcpServerDevice }."
             ::= { vcpSystem 1 }

           vSysReboot OBJECT-TYPE
             SYNTAX  INTEGER {
                         ready(1),
                         execute(2)
                     }
             ACCESS  read-write
             STATUS  mandatory
             DESCRIPTION
                     "A control to reinitialize the server.  In response to a
                     get-request or get-next-request, the agent always 
                     returns 'ready(1)' as the value.  Setting the value to 
                     'execute(2)' causes the server to reboot."
             ::= { vcpSystem 2 }

           vSysLtGroupStatus OBJECT-TYPE
             SYNTAX  INTEGER {
                         present(1),
                         absent(2)
                     }
             ACCESS  read-only
             STATUS  mandatory
             DESCRIPTION
                     "An integer indicating whether the vcpLt group is
                     implemented on this particular unit.  That entire group
                     has a status of optional, as some software configurations
                     executing in a server unit may not implement the
                     group.  For example, the group is not implemented in a
                     unit which is configured without the Lat-compatible
                     protocol, and in this case the value of vSysLtGroupStatus
                     is absent(2).  This variable gives management stations an
                     easy way to determine whether the group is implemented in
                     the particular unit being managed."
             ::= { vcpSystem 3 }

           vSysPrimaryBoot OBJECT-TYPE
             SYNTAX  INTEGER {
                         rom(1),
                         mop(2),
                         bootp(3),
                         tftp(4),
                         card(5)
                     }
             ACCESS  read-write
             STATUS  mandatory
             DESCRIPTION
                     "The primary boot method of the server.  This boot method
                     is attempted first on system re-initialization."
             ::= { vcpSystem 4 }

           vSysSecondaryBoot OBJECT-TYPE
             SYNTAX  INTEGER {
                         rom(1),
                         mop(2),
                         bootp(3),
                         tftp(4),
                         card(5),
                         none(6)
                     }
             ACCESS  read-write
             STATUS  mandatory
             DESCRIPTION
                     "The secondary boot method of the server.  This boot
                     method is attempted on system re-initialization when the
                     primary boot method fails."
             ::= { vcpSystem 5 }

           vSysBootFilePath OBJECT-TYPE
             SYNTAX  DisplayString (SIZE (0..16))
             ACCESS  read-write
             STATUS  mandatory
             DESCRIPTION
                     "The pathname on the remote boot host of the server's
                     boot file for boot through TFTP."
             ::= { vcpSystem 6 }

           vSysBootFileName OBJECT-TYPE
             SYNTAX  DisplayString (SIZE (0..9))
             ACCESS  read-write
             STATUS  mandatory
             DESCRIPTION
                     "The filename of the server's boot file for boot through
                     MOP, TFTP, or Card."
             ::= { vcpSystem 7 }

           vSysBootServer OBJECT-TYPE
             SYNTAX  IpAddress
             ACCESS  read-write
             STATUS  mandatory
             DESCRIPTION
                     "The IP address of the boot server for boot through
                     TFTP or BOOTP.  A value of '0.0.0.0' (on read or write)
                     indicates that no boot server is defined."
             ::= { vcpSystem 8 }

           vSysRemoteBoot OBJECT-TYPE
             SYNTAX  INTEGER {
                         enabled(1),
                         disabled(2)
                     }
             ACCESS  read-write
             STATUS  mandatory
             DESCRIPTION
                     "Indicates whether this server will supply system
                     software as a boot image for remote servers when they
                     request a network boot."
             ::= { vcpSystem 9 }

           vSysEtherType OBJECT-TYPE
             SYNTAX  INTEGER {
                         autoSelect(1),
                         thinWire(2),
                         thickWire(3),
                         tenBaseT(4)
                     }
             ACCESS  read-write
             STATUS  mandatory
             DESCRIPTION
                     "Selects the operating ethernet interface.
                     'autoSelect(1)' indicates that the server will
                     automatically select an interface by identifying that
                     interface showing network activity.  Note that the
                     server must be rebooted before a change in the value of
                     this variable actually takes effect."
             ::= { vcpSystem 10 }

           vSysBroadband OBJECT-TYPE
             SYNTAX  INTEGER {
                         enabled(1),
                         disabled(2)
                     }
             ACCESS  read-write
             STATUS  mandatory
             DESCRIPTION
                     "Determines whether or not the server is configured to
                     interface with with broadband network tranceivers.  Note
                     that the server must be rebooted before a change in the
                     value of this variable actually takes effect."
             ::= { vcpSystem 11 }

           vSysPasswordLimit OBJECT-TYPE
             SYNTAX  INTEGER (0..250)
             ACCESS  read-write
             STATUS  mandatory
             DESCRIPTION
                     "Determines the number of times the server will allow a
                     user to mistype a local password, either to login to
                     a port or connect to a local service, before refusing
                     the login attempt.  The value 0 indicates infinite
                     password attempts."
             ::= { vcpSystem 12 }

           vSysPrivPassword OBJECT-TYPE
             SYNTAX  DisplayString (SIZE (1..6))
             ACCESS  read-write
             STATUS  mandatory
             DESCRIPTION
                     "The password required for users to enter privileged
                     mode, and have access to privileged commands.  Note that
                     on a set-request, the new value is automatically
                     converted to upper-case, as is the user password input."
             ::= { vcpSystem 13 }

           vSysMaintenancePassword OBJECT-TYPE
             SYNTAX  OCTET STRING (SIZE (8))
             ACCESS  read-write
             STATUS  mandatory
             DESCRIPTION
                     "The password required for access to the server remote
                     console port through the MOP network protocol."
             ::= { vcpSystem 14 }


           -- the vcpPort group

--            A port is an abstraction to represent an entity capable of
--            supporting one or more sessions.  Physical ports have a
--            one-to-one correspondence with hardware ports.  The hardware
--            port carries the character transmissions from each side of the
--            session.  Virtual ports are software entities analogous to
--            physical ports, but with no hardware connector.  A virtual port
--            is a channel through which sessions may be established.  For
--            example, virtual ports may permit session establishment from an
--            X.25 protocol stack to/from an IP protocol stack.  The movement
--            of data 'through' the virtual port is in the form of raw data
--            octets, these octets being packaged and transmitted on either
--            side of the virtual port by the protocol involved, and on an
--            appropriate interface.

--            This group defines status variables and configuration
--            parameters for each port.  See the user manual for complete
--            description of how each parameter functions.
            
           vPortBroadcast OBJECT-TYPE
             SYNTAX  INTEGER {
                         enabled(1),
                         disabled(2)
                     }
             ACCESS  read-write
             STATUS  mandatory
             DESCRIPTION
                     "Determines whether or not port users may broadcast
                     text directly to other ports, using the local
                     'BROADCAST' command."
             ::= { vcpPort 1 }

           vPortInactivityTimer OBJECT-TYPE
             SYNTAX  INTEGER (1..120)
             ACCESS  read-write
             STATUS  mandatory
             DESCRIPTION
                     "The number of minutes that may pass with no port
                     activity before that port is automatically logged out,
                     if the port's inactivity logout feature is enabled."
             ::= { vcpPort 2 }

           vPortAbsoluteTimer OBJECT-TYPE
             SYNTAX  INTEGER (1..1439)
             ACCESS  read-write
             STATUS  mandatory
             DESCRIPTION
                     "The number of minutes that may pass with no port
                     activity before that port is automatically logged out,
                     if the port's absolute logout feature is enabled."
             ::= { vcpPort 3 }

           vPortLock OBJECT-TYPE
             SYNTAX  INTEGER {
                         enabled(1),
                         disabled(2)
                     }
             ACCESS  read-write
             STATUS  mandatory
             DESCRIPTION
                     "Determines whether or not the server will allow a user
                     to lock a port using the local 'LOCK' command."
             ::= { vcpPort 4 }

           vPortLoginPassword OBJECT-TYPE
             SYNTAX  DisplayString (SIZE (1..6))
             ACCESS  read-write
             STATUS  mandatory
             DESCRIPTION
                     "The password required for users to login ports with
                     vPortPasswordEnable = 'enabled(1)'.  On a set-request
                     the agent converts lower case ASCII characters to upper
                     case for this object, because the user's password input
                     is also converted before comparison."
             ::= { vcpPort 5 }

           vPortConsoleIndex OBJECT-TYPE
             SYNTAX  INTEGER
             ACCESS  read-write
             STATUS  mandatory
             DESCRIPTION
                     "The value of vPortIndex for the port which is serving
                     as the local console port.  Abnormal event messages are
                     automatically directed to the local console port.  A
                     value of 0 indicates that console messages are disabled."
             ::= { vcpPort 6 }

           vPortFailover OBJECT-TYPE
             SYNTAX  INTEGER {
                         enabled(1),
                         disabled(2)
                     }
             ACCESS  read-write
             STATUS  mandatory
             DESCRIPTION
                     "Determines whether or not the port failover feature is
                     enabled."
             ::= { vcpPort 7 }

           vPortSignalCheck OBJECT-TYPE
             SYNTAX  INTEGER {
                         enabled(1),
                         disabled(2)
                     }
             ACCESS  read-write
             STATUS  mandatory
             DESCRIPTION
                     "Determines whether or not the port signal check
                     feature can be enabled for individual ports."
             ::= { vcpPort 8 }

           vPortLoginMsgEnable OBJECT-TYPE
             SYNTAX  INTEGER {
                         enabled(1),
                         disabled(2)
                     }
             ACCESS  read-write
             STATUS  mandatory
             DESCRIPTION
                     "Determines whether or not the server prints an
                     introductory login message to the user when the user
                     completes a login to a port."
             ::= { vcpPort 9 }

           vPortBreakDuration OBJECT-TYPE
             SYNTAX  INTEGER (10..200)
             ACCESS  read-write
             STATUS  mandatory
             DESCRIPTION
                     "Determines the length, in milliseconds, of a BREAK
                     when transmitted from a physical port."
             ::= { vcpPort 10 }

           vPortXoffMark OBJECT-TYPE
             SYNTAX  INTEGER (2..510)
             ACCESS  read-write
             STATUS  mandatory
             DESCRIPTION
                     "Determines the number of free bytes in a port input
                     buffer at which point the port will XOFF the attached
                     device.  When set, the new value will not take effect
                     until the server is re-initialized."
             ::= { vcpPort 11 }

           vPortXonMark OBJECT-TYPE
             SYNTAX  INTEGER (2..510)
             ACCESS  read-write
             STATUS  mandatory
             DESCRIPTION
                     "Determines the number of used bytes in a port input
                     buffer at which point the port will XON the attached
                     device.  When set, the new value will not take effect
                     until the server is re-initialized."
             ::= { vcpPort 12 }

           vPortNumber OBJECT-TYPE
             SYNTAX  INTEGER
             ACCESS  read-only
             STATUS  mandatory
             DESCRIPTION
                     "An integer indicating the number of entries in
                     vPortTable.  This value cannot change from one
                     re-initialization of the unit to the next
                     re-initialization."
             ::= { vcpPort 13 }

           vPortTable OBJECT-TYPE
             SYNTAX  SEQUENCE OF VPortEntry
             ACCESS  not-accessible
             STATUS  mandatory
             DESCRIPTION
                     "A list of port entries.  The number of entries is given
                     by the value of vPortNumber."
             ::= { vcpPort 14 }

           vPortEntry OBJECT-TYPE
             SYNTAX  VPortEntry
             ACCESS  not-accessible
             STATUS  mandatory
             DESCRIPTION
                     "Status and parameter values for a port."
             INDEX   { vPortIndex }
             ::= { vPortTable 1 }

          VPortEntry ::=
              SEQUENCE {
                  vPortIndex
                      INTEGER,
                  vPortType
                      INTEGER,
                  vPortName
                      DisplayString,
                  vPortUserName
                      DisplayString,
                  vPortState
                      INTEGER,
                  vPortLogout
                      INTEGER,
                  vPortActiveSessions
                      INTEGER,
                  vPortCurrSessNumber
                      INTEGER,
                  vPortCurrSessProt
                      OBJECT IDENTIFIER,
                  vPortAccess
                      INTEGER,
                  vPortVirtualEnable
                      INTEGER,
                  vPortVirtualString
                      OCTET STRING,
                  vPortSessionLimit
                      INTEGER,
                  vPortProfile
                      DisplayString,
                  vPortQueueing
                      INTEGER,
                  vPortPasswordEnable
                      INTEGER,
                  vPortTacacsEnable
                      INTEGER,
                  vPortSecurity
                      INTEGER,
                  vPortGroups
                      LtGroupList,
                  vPortBreakMode
                      INTEGER,
                  vPortBackSwitch
                      Character,
                  vPortForwSwitch
                      Character,
                  vPortLocalSwitch
                      Character,
                  vPortPrefSvc
                      DisplayString,
                  vPortPrefNode
                      DisplayString,
                  vPortPrefPort
                      DisplayString,
                  vPortPrefMode
                      INTEGER,
                  vPortAutoConnect
                      INTEGER,
                  vPortPrompt
                      DisplayString,
                  vPortInactiveLogout
                      INTEGER,
                  vPortAutoPrompt
                      INTEGER,
                  vPortBroadcastEnable
                      INTEGER,
                  vPortInterrupts
                      INTEGER,
                  vPortMessageCodes
                      INTEGER,
                  vPortVerification
                      INTEGER,
                  vPortDialup
                      INTEGER,
                  vPortRemoteModify
                      INTEGER,
                  vPortAbsoluteLogout
                      INTEGER,
                  vPortIOflush
                      INTEGER,
                  vPortLogoutMsgEnable
                      INTEGER,
                  vPortScreenType
                      INTEGER,
                  vPortFlowType
                      INTEGER,
                  vPortInFlowState
                      INTEGER,
                  vPortOutFlowState
                      INTEGER,
                  vPortCTSstate
                      INTEGER,
                  vPortDSRstate
                      INTEGER,
                  vPortDCDstate
                      INTEGER,
                  vPortDTRstate
                      INTEGER,
                  vPortRIstate
                      INTEGER,
                  vPortRTSstate
                      INTEGER,
                  vPortSpeed
                      INTEGER,
                  vPortCharSize
                      INTEGER,
                  vPortParityType
                      INTEGER,
                  vPortAutobaud
                      INTEGER,
                  vPortModemControl
                      INTEGER,
                  vPortDSRlogout
                      INTEGER,
                  vPortRing
                      INTEGER,
                  vPortDTRwait
                      INTEGER,
                  vPortSignalCheckEnable
                      INTEGER,
                  vPortHandshake
                      INTEGER,
                  vPortRcvChars
                      Counter,
                  vPortTrnChars
                      Counter,
                  vPortFrameErrs
                      Counter,
                  vPortOverrunErrs
                      Counter,
                  vPortParityErrs
                      Counter,
                  vPortCharsDropped
                      Counter
              }

           vPortIndex OBJECT-TYPE
             SYNTAX  INTEGER
             ACCESS  read-only
             STATUS  mandatory
             DESCRIPTION
                     "A unique value for each port.  Its value ranges between
                     1 and the value of vPortNumber.  The value for each port
                     will remain constant at least from one re-initialization
                     of the unit's network management system to the next
                     re-initialization."
             ::= { vPortEntry 1 }

           vPortType OBJECT-TYPE
             SYNTAX  INTEGER {
                         unknown(1),
                         physicalRS-232(2),
                         physicalRS-423(3),
                         physicalModem(4),
                         physicalLCDPanel(5),
                         virtualConsole(6),
                         virtualNPT(7),
                         virtualX25(8),
                         virtual3270(9)
                     }
             ACCESS  read-only
             STATUS  mandatory
             DESCRIPTION
                     "An integer indicating the type of the port.  Virtual
                     ports should be considered communication channels to
                     their particular interface.  For example, a virtualX25(7)
                     port is a channel to an X.25 interface for establishing
                     connections to/from that interface."
             ::= { vPortEntry 2 }

           vPortName OBJECT-TYPE
             SYNTAX  DisplayString (SIZE (1..16))
             ACCESS  read-write
             STATUS  mandatory
             DESCRIPTION
                     "A textual name for the port.  This name is used in
                     LAT-compatible session start requests, where a device can
                     request to be connected to a port with a given name.  On
                     a set-request the agent converts lower case ASCII
                     characters to upper case for this object.  Note that for
                     ports with vPortType = 'physicalLCDPanel(5)' or vPortType
                     = 'virtualConsole(6)' this object is not modifiable.  The
                     agent will accept any valid value on a set-request for
                     such ports."
             ::= { vPortEntry 3 }

           vPortUserName OBJECT-TYPE
             SYNTAX  DisplayString (SIZE (0..16))
             ACCESS  read-only
             STATUS  mandatory
             DESCRIPTION
                     "The textual username typed in by the user who logged
                     into the port."
             ::= { vPortEntry 4 }

           vPortState OBJECT-TYPE
             SYNTAX  INTEGER {
                         unknown(1),
                         idle(2),
                         local(3),
                         connecting(4),
                         connected(5),
                         locked(6),
                         serial-interface(7)
                     }
             ACCESS  read-only
             STATUS  mandatory
             DESCRIPTION
                     "The current operational state of the port.  'idle(2)'
                     indicates that the port has no sessions and is logged
                     out.  'local(3)' indicates that the port is currently
                     in local server mode, although suspended sessions may
                     exist on the port.  'connecting(4)' indicates that the
                     server is attempting to connect the port to a session.
                     'connected(5) indicates that the port is currently
                     connected to a protocol session.  'locked(6)' indicates
                     that the port has been locked by a local LOCK command and
                     is awaiting the unlock password.  'serial-interface(7)'
                     indicates that the port is acting as an interface for
                     a serial link controlled by SLIP, PPP, etc."
             ::= { vPortEntry 5 }

           vPortLogout OBJECT-TYPE
             SYNTAX  INTEGER {
                         ready(1),
                         execute(2)
                     }
             ACCESS  read-write
             STATUS  mandatory
             DESCRIPTION
                     "A control to logout a port.  In response to a
                     get-request or get-next-request, the agent always 
                     returns 'ready(1)' as the value.  Setting the value to 
                     'execute(2)' causes all sessions on the port to be
                     disconnected and the port is returned to idle state."
             ::= { vPortEntry 6 }

           vPortActiveSessions OBJECT-TYPE
             SYNTAX  INTEGER
             ACCESS  read-only
             STATUS  mandatory
             DESCRIPTION
                     "The number of presently active sessions on the port,
                     whether current or suspended."
             ::= { vPortEntry 7 }

           vPortCurrSessNumber OBJECT-TYPE
             SYNTAX  INTEGER
             ACCESS  read-only
             STATUS  mandatory
             DESCRIPTION
                     "The reference number of the port's current session.
                     There is a unique non-zero reference number for each
                     session on a port.  The reference number stays constant
                     for the life of the session.  It can be used in
                     conjunction with vPortIndex to index into the appropriate
                     session table for retrieval of session information
                     (vTelSessTable, vLtSessTable, or vRlogSessTable).  If
                     there are no sessions on the port, or if none of them is
                     current, this object will have the value 0."
             ::= { vPortEntry 8 }

           vPortCurrSessProt OBJECT-TYPE
             SYNTAX  OBJECT IDENTIFIER
             ACCESS  read-only
             STATUS  mandatory
             DESCRIPTION
                     "An identifier of which higher-level protocol the current
                     port session is running over.  The possibilities are
                     { protNone } (for no current session, or unknown),
                     { protTelnet }, { protRlogin }, or { protLt }."
             ::= { vPortEntry 9 }

           vPortAccess OBJECT-TYPE
             SYNTAX  INTEGER {
                         local(1),
                         remote(2),
                         dynamic(3),
                         none(4)
                     }
             ACCESS  read-write
             STATUS  mandatory
             DESCRIPTION
                     "An indication of the allowed types of access to the
                     port.  'local(1)' indicates that the port can only carry
                     sessions initiated by it.  'remote(2)' indicates that the
                     port can only accept connections initiated by another
                     entity.  'dynamic(3)' indicates that the port can both
                     initiate sessions and accept connections initiated by
                     another entity.  'none(4)' indicates that the port can
                     not pass any characters, and can neither initiate nor
                     accept connections.  Note that for ports with vPortType =
                     'physicalLCDPanel(5)' or vPortType = 'virtualConsole(6)'
                     this object is not modifiable.  The agent will accept any
                     valid value on a set-request for such ports."
             ::= { vPortEntry 10 }

           vPortVirtualEnable OBJECT-TYPE
             SYNTAX  INTEGER {
                         enabled(1),
                         disabled(2)
                     }
             ACCESS  read-write
             STATUS  mandatory
             DESCRIPTION
                     "An indication of the current setting of the port's
                     virtual characteristic.  This parameter affects the
                     port's actions when connections are established.  Refer
                     to the user manual for a complete description of this
                     parameter.  Note that for ports with vPortType =
                     'physicalLCDPanel(5)' or vPortType = 'virtualConsole(6)'
                     this object is not modifiable.  The agent will accept any
                     valid value on a set-request for such ports."
             ::= { vPortEntry 11 }

           vPortVirtualString OBJECT-TYPE
             SYNTAX  OCTET STRING (SIZE (0..112))
             ACCESS  read-write
             STATUS  mandatory
             DESCRIPTION
                     "An indication of the current setting of the port's
                     virtual text string.  This parameter affects the
                     port's actions when connections are established.  Refer
                     to the user manual for a complete description of this
                     parameter.  Note that for ports with vPortType =
                     'physicalLCDPanel(5)' or vPortType = 'virtualConsole(6)'
                     this object is not modifiable.  The agent will accept any
                     valid value on a set-request for such ports."
             ::= { vPortEntry 12 }

           vPortSessionLimit OBJECT-TYPE
             SYNTAX  INTEGER (0..10)
             ACCESS  read-write
             STATUS  mandatory
             DESCRIPTION
                     "The maximum number of simultaneous sessions allowed on
                     the port.  Note that for ports with vPortType =
                     'physicalLCDPanel(5)' or vPortType = 'virtualConsole(6)'
                     this object is not modifiable.  The agent will accept
                     any valid value on a set-request for such ports."
             ::= { vPortEntry 13 }

           vPortProfile OBJECT-TYPE
             SYNTAX  DisplayString (SIZE (0..16))
             ACCESS  read-write
             STATUS  mandatory
             DESCRIPTION
                     "The name of the profile in use for the port.  The
                     profile contains session parameter information for Telnet
                     and Rlogin.  When the port initiates a Telnet or Rlogin
                     session, the parameters to be used for that session are
                     taken from the port's profile.  vPortProfilename can be
                     used to index into the profile table and retrieve/modify
                     the relevant parameters.  Note that for ports with
                     vPortType = 'physicalLCDPanel(5)' or vPortType =
                     'virtualConsole(6)' this object is not modifiable.  The
                     agent will accept any valid value on a set-request for
                     such ports."
             ::= { vPortEntry 14 }

           vPortQueueing OBJECT-TYPE
             SYNTAX  INTEGER {
                         enabled(1),
                         disabled(2)
                     }
             ACCESS  read-write
             STATUS  mandatory
             DESCRIPTION
                     "An indication of whether the LAT-compatible protocol
                     will request session queueing when attempting to
                     establish a session initiated at this port.  If queueing
                     is requested, a remote node will queue the connection
                     request in the case of resource failures and accept the
                     session when it is able.  Note that for ports with
                     vPortType = 'physicalLCDPanel(5)' or vPortType =
                     'virtualConsole(6)' this object is not modifiable.  The
                     agent will accept any valid value on a set-request for
                     such ports."
             ::= { vPortEntry 15 }

           vPortPasswordEnable OBJECT-TYPE
             SYNTAX  INTEGER {
                         enabled(1),
                         disabled(2)
                     }
             ACCESS  read-write
             STATUS  mandatory
             DESCRIPTION
                     "An indication of whether the system password must be
                     entered to login to the port.  Note that for ports with
                     vPortType = 'physicalLCDPanel(5)' or vPortType =
                     'virtualConsole(6)' this object is not modifiable.  The
                     agent will accept any valid value on a set-request for
                     such ports."
             ::= { vPortEntry 16 }

           vPortTacacsEnable OBJECT-TYPE
             SYNTAX  INTEGER {
                         enabled(1),
                         disabled(2)
                     }
             ACCESS  read-write
             STATUS  mandatory
             DESCRIPTION
                     "An indication of whether the username and password
                     entered at login must be verified by a Tacacs server
                     before port access is permitted.  Note for ports with
                     vPortType = 'physicalLCDPanel(5)' or vPortType =
                     'virtualConsole(6)' this object is not modifiable.  The
                     agent will accept any valid value on a set-request for
                     such ports."
             ::= { vPortEntry 17 }

           vPortSecurityEnable OBJECT-TYPE
             SYNTAX  INTEGER {
                         enabled(1),
                         disabled(2)
                     }
             ACCESS  read-write
             STATUS  mandatory
             DESCRIPTION
                     "An indication of whether the port security feature
                     is enabled.  Ports for which security is enabled are
                     allowed to execute only a limited subset of the
                     available local commands.  Note that for ports with
                     vPortType = 'physicalLCDPanel(5)' or vPortType =
                     'virtualConsole(6)' this object is not modifiable.  The
                     agent will accept any valid value on a set-request for
                     such ports."
             ::= { vPortEntry 18 }

           vPortGroups OBJECT-TYPE
             SYNTAX  LtGroupList
             ACCESS  read-write
             STATUS  mandatory
             DESCRIPTION
                     "Indicates which LAT-compatible groups are authorized
                     and currently enabled on the port.  There are 256
                     possible LAT-compatible groups (0-255).  Note that for
                     ports with vPortType = 'physicalLCDPanel(5)' or vPortType
                     = 'virtualConsole(6)' this object is not modifiable.  The
                     agent will accept any valid value on a set-request for
                     such ports."
             ::= { vPortEntry 19 }

           vPortBreakMode OBJECT-TYPE
             SYNTAX  INTEGER {
                         local(1),
                         remote(2),
                         disabled(3)
                     }
             ACCESS  read-write
             STATUS  mandatory
             DESCRIPTION
                     "An indication of how a BREAK is interpreted when
                     received at the port as input.  'local(1)' indicates that
                     a received BREAK causes any current session to be
                     suspended and the port returned to local mode.  If there
                     is no current session, the BREAK causes any port output
                     in progress to be aborted.  'remote(2)' indicates that a
                     received BREAK is passed through the current session to
                     the other side via a protocol-specific mechanism.  If
                     there is no current session, the BREAK causes any port
                     output in progress to be aborted.  'disabled(3)'
                     indicates that all received BREAKs are ignored.  Note
                     that for ports with vPortType = 'physicalLCDPanel(5)' or
                     vPortType = 'virtualConsole(6)' this object is not
                     modifiable.  The agent will accept any valid value on
                     a set-request for such ports."
             ::= { vPortEntry 20 }

           vPortBackSwitch OBJECT-TYPE
             SYNTAX  Character
             ACCESS  read-write
             STATUS  mandatory
             DESCRIPTION
                     "A 'hot' key which, when received at the port's input,
                     causes the current session to be changed to the
                     immediately preceding session (from session 3 to session
                     2, for example).  A value of 0 means that no backwards
                     switch is in effect.  Note for ports with vPortType =
                     'physicalLCDPanel(5)' or vPortType = 'virtualConsole(6)'
                     this object is not modifiable.  The agent will accept
                     any valid value on a set-request for such ports."
             ::= { vPortEntry 21 }

           vPortForwSwitch OBJECT-TYPE
             SYNTAX  Character
             ACCESS  read-write
             STATUS  mandatory
             DESCRIPTION
                     "A 'hot' key which, when received at the port's input,
                     causes the current session to be changed to the
                     next numerical session (from session 3 to session
                     4, for example).  A value of 0 means that no forwards
                     switch is in effect.  Note for ports with vPortType =
                     'physicalLCDPanel(5)' or vPortType = 'virtualConsole(6)'
                     this object is not modifiable.  The agent will accept
                     any valid value on a set-request for such ports."
             ::= { vPortEntry 22 }

           vPortLocalSwitch OBJECT-TYPE
             SYNTAX  Character
             ACCESS  read-write
             STATUS  mandatory
             DESCRIPTION
                     "A 'hot' key which, when received at the port's input,
                     forces the port to suspend any current session and return
                     to local mode.  If no current session exists, any port
                     output currently in progress is aborted.  A value of 0
                     means that no local switch is in effect.  Note for ports
                     with vPortType = 'physicalLCDPanel(5)' or vPortType =
                     'virtualConsole(6)' this object is not modifiable.  The
                     agent will accept any valid value on a set-request for
                     such ports."
             ::= { vPortEntry 23 }

           vPortPrefSvc OBJECT-TYPE
             SYNTAX  DisplayString (SIZE (0..16))
             ACCESS  read-write
             STATUS  mandatory
             DESCRIPTION
                     "A string defining the port's preferred service. A user
                     at the port does not need to specify the service name (or
                     node address) to connect to the service, he simply
                     executes the connect command.  Alternately, the port may
                     connect to this service immediately upon being logged in
                     from an idle state.  The exact mode of operation depends
                     on the setting of vPortPrefMode.  A zero-length value for
                     this object means that no preferred service is in
                     effect.  Note that for ports with vPortType =
                     'physicalLCDPanel(5)' or vPortType = 'virtualConsole(6)'
                     this object is not modifiable.  The agent will accept any
                     valid value on a set-request for such ports."
             ::= { vPortEntry 24 }

           vPortPrefNode OBJECT-TYPE
             SYNTAX  DisplayString (SIZE (0..16))
             ACCESS  read-write
             STATUS  mandatory
             DESCRIPTION
                     "A string defining the node name for the port's preferred
                     service.  Multiple LAT-compatible nodes may offer the
                     same service name.  This object defines which node is the
                     preferred choice for the port.  A zero-length value for
                     this object means that no preferred node is in effect.
                     Note that for ports with vPortType =
                     'physicalLCDPanel(5)' or vPortType = 'virtualConsole(6)'
                     this object is not modifiable.  The agent will accept any
                     valid value on a set-request for such ports."
             ::= { vPortEntry 25 }

           vPortPrefPort OBJECT-TYPE
             SYNTAX  DisplayString (SIZE (0..16))
             ACCESS  read-write
             STATUS  mandatory
             DESCRIPTION
                     "A string defining the port name for the port's preferred
                     service.  For LAT-compatible services this string
                     identifies the LAT-compatible port name of the desired
                     destination.  For IP hosts this string defines the
                     desired TCP port number.  A zero-length value means that
                     no preferred port is in effect.  Note that for ports with
                     vPortType = 'physicalLCDPanel(5)' or vPortType =
                     'virtualConsole(6)' this object is not modifiable.  The
                     agent will accept any valid value on a set-request for
                     such ports."
             ::= { vPortEntry 26 }

           vPortPrefMode OBJECT-TYPE
             SYNTAX  INTEGER {
                         dedicated(1),
                         preferred(2)
                     }
             ACCESS  read-write
             STATUS  mandatory
             DESCRIPTION
                     "An indication of the mode of preferred service
                     connection.  'preferred(2)' indicates the 'preferred'
                     mode of connection.  In this mode users may break back to
                     local mode by means of the BREAK key or a defined local
                     switch.  'dedicated(3)' indicates that the port cannot
                     function in local mode at all.  It is dedicated to the
                     specified service.  Once the service connection is
                     broken, the port is logged out.  When the port is logged
                     in, it immediately connects to the dedicated service.
                     Note that for ports with vPortType =
                     'physicalLCDPanel(5)' or vPortType = 'virtualConsole(6)'
                     this object is not modifiable.  The agent will accept any
                     valid value on a set-request for such ports."
             ::= { vPortEntry 27 }

           vPortAutoConnect OBJECT-TYPE
             SYNTAX  INTEGER {
                         enabled(1),
                         disabled(2)
                     }
             ACCESS  read-write
             STATUS  mandatory
             DESCRIPTION
                     "A port characteristic which, when enabled, causes the
                     port to automatically attempt to re-establish any
                     connection which is abnormally terminated, such as by
                     network media failure.  If a preferred service is also
                     defined, the port will automatically attempt connection
                     to the preferred service upon login.  Note for ports with
                     vPortType = 'physicalLCDPanel(5)' or vPortType =
                     'virtualConsole(6)' this object is not modifiable.  The
                     agent will accept any valid value on a set-request for
                     such ports."
             ::= { vPortEntry 28 }

           vPortPrompt OBJECT-TYPE
             SYNTAX  DisplayString (SIZE(0..11))
             ACCESS  read-write
             STATUS  mandatory
             DESCRIPTION
                     "The prompt string for the port when it is in local
                     mode.  Note for ports with vPortType =
                     'physicalLCDPanel(5)' or vPortType = 'virtualConsole(6)'
                     this object is not modifiable.  The agent will accept any
                     valid value on a set-request for such ports."
             ::= { vPortEntry 29 }

           vPortInactiveLogout OBJECT-TYPE
             SYNTAX  INTEGER {
                         enabled(1),
                         disabled(2)
                     }
             ACCESS  read-write
             STATUS  mandatory
             DESCRIPTION
                     "A port characteristic which, when enabled, causes the
                     port to automatically become logged out if it has no
                     active sessions and no data has been received or
                     transmitted at the port for the duration of the
                     vSysInactivityTimer.  Note for ports with vPortType =
                     'physicalLCDPanel(5)' or vPortType = 'virtualConsole(6)'
                     this object is not modifiable.  The agent will accept any
                     valid value on a set-request for such ports."
             ::= { vPortEntry 30 }

           vPortAutoPrompt OBJECT-TYPE
             SYNTAX  INTEGER {
                         enabled(1),
                         disabled(2)
                     }
             ACCESS  read-write
             STATUS  mandatory
             DESCRIPTION
                     "A port characteristic which, when enabled, causes the
                     LAT-compatible service prompt to appear at the port
                     immediately upon connecting to a LAT-compatible service.
                     Many LAT-compatible services do not supply a prompt until
                     a carriage return is encountered.  Note that for ports
                     with vPortType = 'physicalLCDPanel(5)' or vPortType =
                     'virtualConsole(6)' this object is not modifiable.  The
                     agent will accept any valid value on a set-request for
                     such ports."
             ::= { vPortEntry 31 }

           vPortBroadcastEnable OBJECT-TYPE
             SYNTAX  INTEGER {
                         enabled(1),
                         disabled(2)
                     }
             ACCESS  read-write
             STATUS  mandatory
             DESCRIPTION
                     "A port characteristic which, when enabled, allows
                     characters broadcast from other server ports to appear
                     at the port.  If disabled, such broadcasts are not
                     permitted to the particular port.  Note for ports with
                     vPortType = 'physicalLCDPanel(5)' or vPortType =
                     'virtualConsole(6)' this object is not modifiable.  The
                     agent will accept any valid value on a set-request for
                     such ports."
             ::= { vPortEntry 32 }

           vPortInterrupts OBJECT-TYPE
             SYNTAX  INTEGER {
                         enabled(1),
                         disabled(2)
                     }
             ACCESS  read-write
             STATUS  mandatory
             DESCRIPTION
                     "A port characteristic which, when enabled, allows
                     a remote connection to the port to be interrupted by a
                     local user by means of the BREAK key.  Note for ports
                     with vPortType = 'physicalLCDPanel(5)' or vPortType =
                     'virtualConsole(6)' this object is not modifiable.  The
                     agent will accept any valid value on a set-request for
                     such ports."
             ::= { vPortEntry 33 }

           vPortMessageCodes OBJECT-TYPE
             SYNTAX  INTEGER {
                         enabled(1),
                         disabled(2)
                     }
             ACCESS  read-write
             STATUS  mandatory
             DESCRIPTION
                     "A port characteristic which, when enabled, causes
                     a message code reference number to be generated along
                     with any port status or error messages.  Note for ports
                     with vPortType = 'physicalLCDPanel(5)' or vPortType =
                     'virtualConsole(6)' this object is not modifiable.  The
                     agent will accept any valid value on a set-request for
                     such ports."
             ::= { vPortEntry 34 }

           vPortVerification OBJECT-TYPE
             SYNTAX  INTEGER {
                         enabled(1),
                         disabled(2)
                     }
             ACCESS  read-write
             STATUS  mandatory
             DESCRIPTION
                     "A port characteristic which, when enabled, causes
                     a status message to appear on each connection attempt by
                     the port.  The status message indicates success or
                     failure of the connection and provides the session number
                     of the newly established session.  Note for ports
                     with vPortType = 'physicalLCDPanel(5)' or vPortType =
                     'virtualConsole(6)' this object is not modifiable.  The
                     agent will accept any valid value on a set-request for
                     such ports."
             ::= { vPortEntry 35 }

           vPortDialup OBJECT-TYPE
             SYNTAX  INTEGER {
                         enabled(1),
                         disabled(2)
                     }
             ACCESS  read-write
             STATUS  mandatory
             DESCRIPTION
                     "A port characteristic which, when enabled, causes the
                     server to identify that the port is configured for modem
                     dial-in service when it connects to a LAT-compatible
                     service.  This may cause the service to initiate any
                     security features it chooses to verify the authority or
                     source of the connecting user.  Note for ports
                     with vPortType = 'physicalLCDPanel(5)' or vPortType =
                     'virtualConsole(6)' this object is not modifiable.  The
                     agent will accept any valid value on a set-request for
                     such ports."
             ::= { vPortEntry 36 }

           vPortRemoteModify OBJECT-TYPE
             SYNTAX  INTEGER {
                         enabled(1),
                         disabled(2)
                     }
             ACCESS  read-write
             STATUS  mandatory
             DESCRIPTION
                     "A port characteristic which, when enabled, causes the
                     server to allow modification of local port parameters
                     (speed, character size, parity, etc.) from the remote
                     end of the connection through protocol-specific means.
                     Note for ports with vPortType = 'physicalLCDPanel(5)' or
                     vPortType = 'virtualConsole(6)' this object is not
                     modifiable.  The agent will accept any valid value on a
                     set-request for such ports."
             ::= { vPortEntry 37 }

           vPortAbsoluteLogout OBJECT-TYPE
             SYNTAX  INTEGER {
                         enabled(1),
                         disabled(2)
                     }
             ACCESS  read-write
             STATUS  mandatory
             DESCRIPTION
                     "A port characteristic which, when enabled, causes the
                     port to automatically become logged out if no data has
                     been received or transmitted at the port for the duration
                     of the vSysAbsoluteTimer, regardless of the presence of
                     suspended sessions on the port.  Note for ports
                     with vPortType = 'physicalLCDPanel(5)' or vPortType =
                     'virtualConsole(6)' this object is not modifiable.  The
                     agent will accept any valid value on a set-request for
                     such ports."
             ::= { vPortEntry 38 }

           vPortIOflush OBJECT-TYPE
             SYNTAX  INTEGER {
                         enabled(1),
                         disabled(2)
                     }
             ACCESS  read-write
             STATUS  mandatory
             DESCRIPTION
                     "A port characteristic which, when enabled, causes the
                     server to automatically flush the port's output buffer
                     when the port becomes logged out.  Note for ports
                     with vPortType = 'physicalLCDPanel(5)' or vPortType =
                     'virtualConsole(6)' this object is not modifiable.  The
                     agent will accept any valid value on a set-request for
                     such ports."
             ::= { vPortEntry 39 }

           vPortLogoutMsgEnable OBJECT-TYPE
             SYNTAX  INTEGER {
                         enabled(1),
                         disabled(2)
                     }
             ACCESS  read-write
             STATUS  mandatory
             DESCRIPTION
                     "A port characteristic which, when enabled, causes the
                     port to print a message whenever it becomes logged out.
                     Note for ports with vPortType = 'physicalLCDPanel(5)' or
                     vPortType = 'virtualConsole(6)' this object is not
                     modifiable.  The agent will accept any valid value on a
                     set-request for such ports."
             ::= { vPortEntry 40 }

           vPortScreenType OBJECT-TYPE
             SYNTAX  INTEGER {
                         ansi(1),
                         softcopy(2),
                         hardcopy(3)
                     }
             ACCESS  read-write
             STATUS  mandatory
             DESCRIPTION
                     "A port characteristic which determines the type of
                     output device connected to the port, and therefore
                     determines the output data formatting used for server
                     configuration and statistics screens.  'ansi(1)'
                     indicates that ANSI-compatible screen formatting
                     sequences may be used.  'softcopy(2)' specifies that
                     VT-100 screen formatting sequences may be used.
                     'hardcopy(3)' indicates that no screen-formatting
                     sequences may be used.  Note that for ports
                     with vPortType = 'physicalLCDPanel(5)' or vPortType =
                     'virtualConsole(6)' this object is not modifiable.  The
                     agent will accept any valid value on a set-request for
                     such ports."
             ::= { vPortEntry 41 }

           vPortFlowType OBJECT-TYPE
             SYNTAX  INTEGER {
                         none(1),
                         xonXoff(2),
                         hardware(3),
                         ctsRts(4),
                         dsrDtr(5)
                     }
             ACCESS  read-write
             STATUS  mandatory
             DESCRIPTION
                     "The port's type of flow control.  'none(1)' indicates
                     that no flow control is in effect.  'xonXoff(2)'
                     indicates software flow control by recognizing XON and
                     XOFF characters.  'hardware(3)' indicates flow control
                     delegated to the lower level, for example a parallel
                     port. 'ctsRts(4)' and 'dsrDtr(5)' are specific to ports
                     with vPortType = 'physicalRS-232(2) or
                     'physicalRS-423(3)'."
             ::= { vPortEntry 42 }

           vPortInFlowState OBJECT-TYPE
             SYNTAX  INTEGER {
                         none(1),
                         unknown(2),
                         stop(3),
                         go(4)
                     }
             ACCESS  read-only
             STATUS  mandatory
             DESCRIPTION
                     "The current operational state of input flow control on
                     the port.  'none' indicates not applicable.  'unknown'
                     indicates this level does not know.  'stop' indicates
                     flow not allowed.  'go' indicates flow allowed."
             ::= { vPortEntry 43 }

           vPortOutFlowState OBJECT-TYPE
             SYNTAX  INTEGER {
                         none(1),
                         unknown(2),
                         stop(3),
                         go(4)
                     }
             ACCESS  read-only
             STATUS  mandatory
             DESCRIPTION
                     "The current operational state of output flow control on
                     the port.  'none' indicates not applicable.  'unknown'
                     indicates this level does not know.  'stop' indicates
                     flow not allowed.  'go' indicates flow allowed."
             ::= { vPortEntry 44 }

           vPortCTSstate OBJECT-TYPE
             SYNTAX  INTEGER {
                         none(1),
                         on(2),
                         off(3),
                         unknown(4)
                     }
             ACCESS  read-only
             STATUS  mandatory
             DESCRIPTION
                     "The current state of the port's CLEAR-TO-SEND input.
                     'none(1)' indicates that the port has no CTS input.
                     'unknown(4)' indicates that the state of the input signal
                     is unavailable to this software level."
             ::= { vPortEntry 45 }

           vPortDSRstate OBJECT-TYPE
             SYNTAX  INTEGER {
                         none(1),
                         on(2),
                         off(3),
                         unknown(4)
                     }
             ACCESS  read-only
             STATUS  mandatory
             DESCRIPTION
                     "The current state of the port's DATA-SET-READY input.
                     'none(1)' indicates that the port has no DSR input.
                     'unknown(4)' indicates that the state of the input signal
                     is unavailable to this software level."
             ::= { vPortEntry 46 }

           vPortDCDstate OBJECT-TYPE
             SYNTAX  INTEGER {
                         none(1),
                         on(2),
                         off(3),
                         unknown(4)
                     }
             ACCESS  read-only
             STATUS  mandatory
             DESCRIPTION
                     "The current state of the port's DATA-CARRIER-DETECT
                     input.  'none(1)' indicates that the port has no DCD
                     input.  'unknown(4)' indicates that the state of the
                     input signal is unavailable to this software level."
             ::= { vPortEntry 47 }

           vPortDTRstate OBJECT-TYPE
             SYNTAX  INTEGER {
                         none(1),
                         on(2),
                         off(3),
                         unknown(4)
                     }
             ACCESS  read-only
             STATUS  mandatory
             DESCRIPTION
                     "The current state of the port's DATA-TERMINAL-READY
                     output.  'none(1)' indicates that the port has no DTR
                     output.  'unknown(4)' indicates that the state of the
                     output signal is unavailable to this software level."
             ::= { vPortEntry 48 }

           vPortRIstate OBJECT-TYPE
             SYNTAX  INTEGER {
                         none(1),
                         on(2),
                         off(3),
                         unknown(4)
                     }
             ACCESS  read-only
             STATUS  mandatory
             DESCRIPTION
                     "The current state of the port's RING-INDICATOR
                     input.  'none(1)' indicates that the port has no RI
                     input.  'unknown(4)' indicates that the state of the
                     input signal is unavailable to this software level."
             ::= { vPortEntry 49 }

           vPortRTSstate OBJECT-TYPE
             SYNTAX  INTEGER {
                         none(1),
                         on(2),
                         off(3),
                         unknown(4)
                     }
             ACCESS  read-only
             STATUS  mandatory
             DESCRIPTION
                     "The current state of the port's REQUEST-TO-SEND
                     output.  'none(1)' indicates that the port has no RTS
                     output.  'unknown(4)' indicates that the state of the
                     output signal is unavailable to this software level."
             ::= { vPortEntry 50 }

           vPortSpeed OBJECT-TYPE
             SYNTAX  INTEGER {
                         none(1),
                         baud110(2),
                         baud300(3),
                         baud600(4),
                         baud1200(5),
                         baud2400(6),
                         baud4800(7),
                         baud9600(8),
                         baud14400(9),
                         baud19200(10),
                         baud28800(11),
                         baud38400(12),
                         baud57600(13)
                     }
             ACCESS  read-write
             STATUS  mandatory
             DESCRIPTION
                     "The serial baud rate of the port.  'none(1)' indicates
                     that the port is not a physical serial port.  The agent
                     will accept any valid value on a set-request for such
                     ports."
             ::= { vPortEntry 51 }

           vPortCharSize OBJECT-TYPE
             SYNTAX  INTEGER {
                         none(1),
                         seven-bits(2),
                         eight-bits(3)
                     }
             ACCESS  read-write
             STATUS  mandatory
             DESCRIPTION
                     "The size of serial characters transmitted/received at
                     the port, excluding parity and stop bits.  'none(1)'
                     indicates that the port is not a physical serial port.
                     The agent will accept any valid value on a set-request
                     for such ports."
             ::= { vPortEntry 52 }

           vPortParityType OBJECT-TYPE
             SYNTAX  INTEGER {
                         not-applicable(1),
                         none(2),
                         even(3),
                         odd(4),
                         mark(5),
                         space(6)
                     }
             ACCESS  read-write
             STATUS  mandatory
             DESCRIPTION
                     "The type of parity used for serial transmission and
                     reception of characters at the port.  'not-applicable(1)'
                     indicates that the port is not a physical serial port.
                     The agent will accept any valid value on a set-request
                     for such ports."
             ::= { vPortEntry 53 }

           vPortAutobaud OBJECT-TYPE
             SYNTAX  INTEGER {
                         enabled(1),
                         disabled(2),
                         not-applicable(3)
                     }
             ACCESS  read-write
             STATUS  mandatory
             DESCRIPTION
                     "Indicates whether the port will automatically attempt
                     to autobaud to an external serial device after being
                     logged out.  'not-applicable(3)' indicates that the port
                     is not a physical serial port.  The agent will accept any
                     valid value on a set-request for such ports."
             ::= { vPortEntry 54 }

           vPortModemControl OBJECT-TYPE
             SYNTAX  INTEGER {
                         enabled(1),
                         disabled(2),
                         not-applicable(3)
                     }
             ACCESS  read-write
             STATUS  mandatory
             DESCRIPTION
                     "Indicates whether the port modem control characteristic
                     is enabled.  When enabled, a physical serial port will
                     not function unless modem signals are asserted, and the
                     port's DTR output is dropped for 5 seconds each time the
                     port gets logged out.  'not-applicable(3)' indicates that
                     the port is not a physical serial port.  The agent will
                     accept any valid value on a set-request for such ports."
             ::= { vPortEntry 55 }

           vPortDSRlogout OBJECT-TYPE
             SYNTAX  INTEGER {
                         enabled(1),
                         disabled(2),
                         not-applicable(3)
                     }
             ACCESS  read-write
             STATUS  mandatory
             DESCRIPTION
                     "Indicates whether the port DSRlogout characteristic
                     is enabled.  When enabled, a physical serial port will
                     automatically be logged out when the DSR input is
                     dropped.  'not-applicable(3)' indicates that the port is
                     not a physical serial port.  The agent will accept any
                     valid value on a set-request for such ports."
             ::= { vPortEntry 56 }

           vPortRing OBJECT-TYPE
             SYNTAX  INTEGER {
                         enabled(1),
                         disabled(2),
                         not-applicable(3)
                     }
             ACCESS  read-write
             STATUS  mandatory
             DESCRIPTION
                     "Indicates whether the port ring characteristic is
                     enabled.  When enabled, a physical serial port will
                     raise and lower its RTS output and wait for the DSR input
                     to be raised before accepting a remote connection
                     request.  'not-applicable(3)' indicates that the port is
                     not a physical serial port.  The agent will accept any
                     valid value on a set-request for such ports."
             ::= { vPortEntry 57 }

           vPortDTRwait OBJECT-TYPE
             SYNTAX  INTEGER {
                         enabled(1),
                         disabled(2),
                         not-applicable(3)
                     }
             ACCESS  read-write
             STATUS  mandatory
             DESCRIPTION
                     "Indicates whether the port DTRwait characteristic is
                     enabled.  When enabled, a physical serial port will
                     delay asserting its DTR and RTS outputs until the RI
                     input signal is asserted.  'not-applicable(3)' indicates
                     that the port is not a physical serial port.  The agent
                     will accept any valid value on a set-request for such
                     ports."
             ::= { vPortEntry 58 }

           vPortSignalCheckEnable OBJECT-TYPE
             SYNTAX  INTEGER {
                         enabled(1),
                         disabled(2),
                         not-applicable(3)
                     }
             ACCESS  read-write
             STATUS  mandatory
             DESCRIPTION
                     "Indicates whether the port signal check characteristic
                     is enabled.  When enabled, a physical serial port will
                     check for the assertion of the DSR input signal before
                     accepting a remote connection request.
                     'not-applicable(3)' indicates that the port is not a
                     physical serial port.  The agent will accept any valid
                     value on a set-request for such ports."
             ::= { vPortEntry 59 }

           vPortHandshake OBJECT-TYPE
             SYNTAX  INTEGER {
                         signalCTS(1),
                         signalRI(2),
                         not-applicable(3)
                     }
             ACCESS  read-write
             STATUS  mandatory
             DESCRIPTION
                     "On some server units the physical serial ports have
                     connectors which do not allow both the CTS and RI
                     input signals.  This object indicates how the input
                     signal is to be interpreted.  'not-applicable(3)'
                     indicates that the port is not a physical serial port, or
                     that the serial port can accept both the CTS and RI input
                     signals.  The agent will accept any valid value on a
                     set-request for such ports."
             ::= { vPortEntry 60 }

           vPortRcvChars OBJECT-TYPE
             SYNTAX  Counter
             ACCESS  read-only
             STATUS  mandatory
             DESCRIPTION
                     "Total number of characters detected as input from 
                    the port since system re-initialization, including
                    locally-processed input, and input sent to all sessions."
             ::= { vPortEntry 61 }

           vPortTrnChars OBJECT-TYPE
             SYNTAX  Counter
             ACCESS  read-only
             STATUS  mandatory
             DESCRIPTION
                     "Total number of characters detected as output from 
                    the port since system re-initialization, including
                    locally-creating output, and output received from all
                    sessions."
             ::= { vPortEntry 62 }

           vPortFrameErrs OBJECT-TYPE
             SYNTAX  Counter
             ACCESS  read-only
             STATUS  mandatory
             DESCRIPTION
                     "Total number of received characters which were rejected
                     because a framing error was detected.  This counter only
                     applies to physical serial ports.  The value 0 will be
                     returned for all other ports."
             ::= { vPortEntry 63 }

           vPortOverrunErrs OBJECT-TYPE
             SYNTAX  Counter
             ACCESS  read-only
             STATUS  mandatory
             DESCRIPTION
                     "Total number of received characters which were rejected
                     for lack of character FIFO space on the serial
                     communication controller.  This counter only applies to
                     physical serial ports.  The value 0 will be returned for
                     all other ports."
             ::= { vPortEntry 64 }

           vPortParityErrs OBJECT-TYPE
             SYNTAX  Counter
             ACCESS  read-only
             STATUS  mandatory
             DESCRIPTION
                     "Total number of received characters which were rejected
                     because a parity error was detected.  This counter only
                     applies to physical serial ports.  The value 0 will be
                     returned for all other ports."
             ::= { vPortEntry 65 }

           vPortCharsDropped OBJECT-TYPE
             SYNTAX  Counter
             ACCESS  read-only
             STATUS  mandatory
             DESCRIPTION
                     "Total number of received characters which were rejected
                     for any reason not covered in other objects, for example
                     lack of input buffer space.  This counter only applies
                     to physical serial ports.  The value 0 will be returned
                     for all other ports."
             ::= { vPortEntry 66 }


           -- the vcpService group

--            A service is the means by which a port or a groups of ports is
--            configured to accept connections from a given network
--            protocol(s).  The service listens for connection requests on the
--            network interface(s), and subsequently establishes the sessions
--            between a requesting entity and one of the ports allocated for
--            that service.  If the port is a physical port, the requesting
--            entity is then connected with whatever device is connected to
--            the hardware port.  If the port is a virtual port, the
--            requesting entity is connected to an internal server channel
--            from which he may gain local server access, or connection
--            capability through a different network protocol/interface.

--            This group defines status variables and configuration
--            parameters for each service.  See the user manual for complete
--            description of how each parameter functions.

           vSvcRatingMode OBJECT-TYPE
             SYNTAX  INTEGER {
                         scaled(1),
                         unScaled(2)
                     }
             ACCESS  read-write
             STATUS  mandatory
             DESCRIPTION
                     "Determines the method of computation for the rating
                     of local services.  'scaled(2)' indicates that an
                     algorithm is used where the rating is scaled to be
                     between 0 and 255.  'unScaled(1)' indicates that the
                     service rating is equal to the number of available 
                     service ports."
             ::= { vcpService 1 }

           vSvcCurrNumber OBJECT-TYPE
             SYNTAX  INTEGER
             ACCESS  read-only
             STATUS  mandatory
             DESCRIPTION
                     "An integer indicating the current number of entries in
                     vSvcTable.  This object is not constant."
             ::= { vcpService 2 }

           vSvcTable OBJECT-TYPE
             SYNTAX  SEQUENCE OF VSvcEntry
             ACCESS  not-accessible
             STATUS  mandatory
             DESCRIPTION
                     "A list of service entries.  The number of entries is
                     given by the value of vSvcCurrNumber."
             ::= { vcpService 3 }

           vSvcEntry OBJECT-TYPE
             SYNTAX  VSvcEntry
             ACCESS  not-accessible
             STATUS  mandatory
             DESCRIPTION
                     "Status and parameter values for a service."
             INDEX   { vSvcName }
             ::= { vSvcTable 1 }

          VSvcEntry ::=
              SEQUENCE {
                  vSvcName
                      DisplayString,
                  vSvcPorts
                      OCTET STRING,
                  vSvcIdent
                      DisplayString,
                  vSvcRating
                      INTEGER,
                  vSvcLtEnable
                      INTEGER,
                  vSvcTelEnable
                      INTEGER,
                  vSvcLprEnable
                      INTEGER,
                  vSvcRawEnable
                      INTEGER,
                  vSvcVirtualEnable
                      INTEGER,
                  vSvcVirtualText
                      OCTET STRING,
                  vSvcConnectEnable
                      INTEGER,
                  vSvcPassword
                      DisplayString,
                  vSvcQueueEnable
                      INTEGER,
                  vSvcIpAddr
                      IpAddress,
                  vSvcTcpPort
                      INTEGER,
                  vSvcProfile
                      DisplayString,
                  vSvcStatus
                      INTEGER
              }

           vSvcName OBJECT-TYPE
             SYNTAX  DisplayString (SIZE (1..16))
             ACCESS  read-write
             STATUS  mandatory
             DESCRIPTION
                     "A string which identifies the service uniquely among
                     all other local services configured in the unit.  This
                     name is transmitted as part of the unit's LAT-compatible
                     multicast messages.  On a set-request the string is
                     automatically converted to upper-case, as lower-case
                     service names are not allowed on the server."
             ::= { vSvcEntry 1 }

           vSvcPorts OBJECT-TYPE
             SYNTAX  OCTET STRING (SIZE (32))
             ACCESS  read-write
             STATUS  mandatory
             DESCRIPTION
                     "A 32-byte string which represents a bit map of which
                     server ports are enabled for the service.  Each server
                     port is represented by one bit in the 32 bytes.  If the
                     bit is turned on, the corresponding server port is
                     enabled for the service.  The least significant bit of
                     each byte represents the lowest of the ports for that
                     byte.  For example, port 1 (port with vPortIndex = 1) is
                     represented by the least significant bit of the first
                     byte, and port 16 (port with vPortIndex = 16) is
                     represented by the most significant bit of the second
                     byte, etc.  Note that 32 bytes allows for up to 256
                     ports.  For servers configured with less than 256 ports,
                     all bits above the highest port number must always be
                     zero.  Note also that ports with vPortType =
                     'physicalLCDPanel(5)' or vPortType = 'virtualConsole(6)'
                     cannot be enabled on a service."
             ::= { vSvcEntry 2 }

           vSvcIdent OBJECT-TYPE
             SYNTAX  DisplayString (SIZE (0..40))
             ACCESS  read-write
             STATUS  mandatory
             DESCRIPTION
                     "A locally-administered identification string which is
                     associated with the service and is transmitted as part of
                     the unit's LAT-compatible multicast messages."
             ::= { vSvcEntry 3 }

           vSvcRating OBJECT-TYPE
             SYNTAX  INTEGER (0..255)
             ACCESS  read-only
             STATUS  mandatory
             DESCRIPTION
                     "An integer indicating the ability for connections to
                     this service to be accepted by the server.  The higher
                     the value, the more able the server is to accept
                     connections to this service.  A very low value indicates
                     that the resources for this service are close to
                     exhausted.  The most dominant factor for determining the
                     service rating is the number of idle ports which are
                     enabled for the service.  If a service has no idle ports
                     enabled, its rating is zero.  This number is transmitted
                     as part of the unit's LAT-compatible multicast messages."
             ::= { vSvcEntry 4 }

           vSvcLtEnable OBJECT-TYPE
             SYNTAX  INTEGER {
                         enabled(1),
                         disabled(2)
                     }
             ACCESS  read-write
             STATUS  mandatory
             DESCRIPTION
                     "Indicates whether the server will accept connections to
                     this service over the LAT-compatible protocol.
                     'disabled(2)' indicates that LAT-compatible connections
                     will not be accepted."
             ::= { vSvcEntry 5 }

           vSvcTelEnable OBJECT-TYPE
             SYNTAX  INTEGER {
                         enabled(1),
                         disabled(2)
                     }
             ACCESS  read-write
             STATUS  mandatory
             DESCRIPTION
                     "Indicates whether the server will accept connections to
                     this service over the Telnet protocol.  'disabled(2)'
                     indicates that Telnet connections will not be accepted."
             ::= { vSvcEntry 6 }

           vSvcLprEnable OBJECT-TYPE
             SYNTAX  INTEGER {
                         enabled(1),
                         disabled(2)
                     }
             ACCESS  read-write
             STATUS  mandatory
             DESCRIPTION
                     "Indicates whether the server will accept connections to
                     this service over the LPR line printer protocol.
                     'disabled(2)' indicates that LPR connections will not be
                     accepted."
             ::= { vSvcEntry 7 }

           vSvcRawEnable OBJECT-TYPE
             SYNTAX  INTEGER {
                         enabled(1),
                         disabled(2)
                     }
             ACCESS  read-write
             STATUS  mandatory
             DESCRIPTION
                     "If enabled(1), indicates that the server will not
                     interpret Telnet interesting characters when a Telnet
                     connection is established to the service."
             ::= { vSvcEntry 8 }

           vSvcVirtualEnable OBJECT-TYPE
             SYNTAX  INTEGER {
                         enabled(1),
                         disabled(2)
                     }
             ACCESS  read-write
             STATUS  mandatory
             DESCRIPTION
                     "Indicates whether the virtual characteristic is enabled
                     or not on this service.  Refer to the user manual for
                     more information on the service virtual characteristic."
             ::= { vSvcEntry 9 }

           vSvcVirtualText OBJECT-TYPE
             SYNTAX  OCTET STRING (SIZE (0..112))
             ACCESS  read-write
             STATUS  mandatory
             DESCRIPTION
                     "Defines the virtual text string for this service.  Refer
                     to the user manual for more information on the function
                     of the service virtual text string."
             ::= { vSvcEntry 10 }

           vSvcConnectEnable OBJECT-TYPE
             SYNTAX  INTEGER {
                         enabled(1),
                         disabled(2)
                     }
             ACCESS  read-write
             STATUS  mandatory
             DESCRIPTION
                     "Indicates whether connections are presently being
                     accepted for this service or not.  It is a way of
                     temporarily turning off the service without deleting it
                     from the table."
             ::= { vSvcEntry 11 }

           vSvcPassword OBJECT-TYPE
             SYNTAX  DisplayString (SIZE (0..6))
             ACCESS  read-write
             STATUS  mandatory
             DESCRIPTION
                     "Defines the password that must be correctly supplied
                     before a session to this service can be established.  a
                     zero-length value indicates that no password must be
                     supplied.  Note that on a set-request, the new value is
                     automatically converted to upper-case, as is the user
                     password input."
             ::= { vSvcEntry 12 }

           vSvcQueueEnable OBJECT-TYPE
             SYNTAX  INTEGER {
                         enabled(1),
                         disabled(2)
                     }
             ACCESS  read-write
             STATUS  mandatory
             DESCRIPTION
                     "Indicates whether or not the server will queue
                     connection requests to the service if it is unavailable."
             ::= { vSvcEntry 13 }

           vSvcIpAddr OBJECT-TYPE
             SYNTAX  IpAddress
             ACCESS  read-write
             STATUS  mandatory
             DESCRIPTION
                     "Indicates the only IP address upon which the service
                     will carry TCP sessions.  This is used when the server
                     has multiple IP addresses and it is desired that the
                     service only respond to connection requests on one of
                     those addresses.  A value of 0.0.0.0 indicates that any
                     of the server's IP addresses can be used to connect to
                     this service."
             ::= { vSvcEntry 14 }

           vSvcTcpPort OBJECT-TYPE
             SYNTAX  INTEGER (1..65535)
             ACCESS  read-write
             STATUS  mandatory
             DESCRIPTION
                     "Indicates the TCP port on which this service accepts
                     TCP connections.  A value of zero normally means that
                     no TCP port has been assigned."
             ::= { vSvcEntry 15 }

           vSvcProfile OBJECT-TYPE
             SYNTAX  DisplayString (SIZE (0..16))
             ACCESS  read-write
             STATUS  mandatory
             DESCRIPTION
                     "Indicates the profile entry in the vProfTable which is
                     used to determine Telnet parameters when a Telnet
                     connection is accepted to the service.  A zero-length
                     value indicates that only default profile parameter
                     values will be used."
             ::= { vSvcEntry 16 }

           vSvcStatus OBJECT-TYPE
             SYNTAX  INTEGER {
                         valid(1),
                         invalid(2)
                     }
             ACCESS  read-write
             STATUS  mandatory
             DESCRIPTION
                     "The current status of this service entry.  Setting this
                     object to the value invalid(2) has the effect of deleting
                     the entry from the service table."
             ::= { vSvcEntry 17 }


           -- the vcpProfile group

--            This group defines the table of available profiles.  Profiles
--            are sets of parameters pertaining to Telnet/Rlogin sessions
--            over TCP/IP.  Each port and each service can be assigned a
--            particular profile from this table (see vPortProfile and
--            vSvcProfile).  Whenever the port initates a Telnet/Rlogin
--            session (or the service accepts a Telnet/Rlogin session), the
--            parameters for that session are taken from the port/service
--            profile entry.

           vProfCurrNumber OBJECT-TYPE
             SYNTAX  INTEGER
             ACCESS  read-only
             STATUS  mandatory
             DESCRIPTION
                     "An integer indicating the current number of entries in
                     vProfTable.  This object is not constant."
             ::= { vcpProfile 1 }

           vProfTable OBJECT-TYPE
             SYNTAX  SEQUENCE OF VProfEntry
             ACCESS  not-accessible
             STATUS  mandatory
             DESCRIPTION
                     "A list of profile entries.  The number of entries is
                     given by the value of vProfCurrNumber."
             ::= { vcpProfile 2 }

           vProfEntry OBJECT-TYPE
             SYNTAX  VProfEntry
             ACCESS  not-accessible
             STATUS  mandatory
             DESCRIPTION
                     "Parameter values for a profile entry."
             INDEX   { vProfName }
             ::= { vProfTable 1 }

          VProfEntry ::=
              SEQUENCE {
                  vProfName
                      DisplayString,
                  vProfDomain
                      DisplayString,
                  vProfConcatenate
                      INTEGER,
                  vProfPermHostOnly
                      INTEGER,
                  vProfTcpPort
                      INTEGER,
                  vProfTcpTimeout
                      INTEGER,
                  vProfTcpKeepalive
                      INTEGER,
                  vProfIpTTL
                      INTEGER,
                  vProfIpPrecedence
                      INTEGER,
                  vProfTermType
                      DisplayString,
                  vProfCrToNet
                      OCTET STRING,
                  vProfCrFromTerm
                      OCTET STRING,
                  vProfPadChar
                      Character,
                  vProfPadLength
                      INTEGER,
                  vProfEndRecord
                      Character,
                  vProfNop
                      Character,
                  vProfDataMark
                      Character,
                  vProfBreak
                      Character,
                  vProfIntProcess
                      Character,
                  vProfAbortOutput
                      Character,
                  vProfAttention
                      Character,
                  vProfEraseChar
                      Character,
                  vProfEraseLine
                      Character,
                  vProfGoAhead
                      Character,
                  vProfNullPass
                      INTEGER,
                  vProfLocalEcho
                      INTEGER,
                  vProfRemoteEcho
                      INTEGER,
                  vProfLocalBinary
                      INTEGER,
                  vProfRemoteBinary
                      INTEGER,
                  vProfStatus
                      INTEGER
              }

           vProfName OBJECT-TYPE
             SYNTAX  DisplayString (SIZE (1..16))
             ACCESS  read-write
             STATUS  mandatory
             DESCRIPTION
                     "A unique string value for each profile."
             ::= { vProfEntry 1 }

           vProfDomain OBJECT-TYPE
             SYNTAX  DisplayString (SIZE (0..63))
             ACCESS  read-write
             STATUS  mandatory
             DESCRIPTION
                     "A domain name extension that may be appended to a
                     user-specified hostname with which the user wishes to
                     start a session.  For example, if the user's port profile
                     has a vProfDomain of 'dss.com', and the user attempts to
                     start a session to the specified host 'pluto,' the server
                     will first attempt to resolve the hostname 'pluto,' and
                     if this is unsuccessful it will then attempt to resolve
                     the hostname 'pluto.dss.com.'  This automatic appending
                     of domain extension is only attempted if the value of
                     vProfConcatenate is 'enabled(1).'  A zero-length value
                     indicates that no extension is used."
             ::= { vProfEntry 2 }

           vProfConcatenate OBJECT-TYPE
             SYNTAX  INTEGER {
                         enabled(1),
                         disabled(2)
                     }
             ACCESS  read-write
             STATUS  mandatory
             DESCRIPTION
                     "An indication of whether the server will append the
                     value of vProfDomain to a user-specified hostname when
                     the user wishes to start a session to the host (see
                     vProfDomain).  'enabled(1)' indicates that the server
                     will attempt to resolve the concatenated hostname if the
                     unconcatenated hostname cannot be resolved to an IP
                     address.  'disabled(2)' indicates that the server will
                     not attempt the hostname concatenization."
             ::= { vProfEntry 3 }

           vProfPermHostOnly OBJECT-TYPE
             SYNTAX  INTEGER {
                         enabled(1),
                         disabled(2)
                     }
             ACCESS  read-write
             STATUS  mandatory
             DESCRIPTION
                     "An indication of whether the server will attempt to
                     resolve a user-specified hostname through the network
                     nameserver protocol for ports with this profile.
                     'disabled(1)' indicates that the server will
                     automatically attempt to resolve an unknown
                     user-specified hostname.  'enabled(2)' indicates that if
                     the user-specified hostname is not already in the
                     hostname table, the server will not attempt to resolve it
                     through the nameserver protocol."
             ::= { vProfEntry 4 }

           vProfTcpPort OBJECT-TYPE
             SYNTAX  INTEGER (0..65535)
             ACCESS  read-write
             STATUS  mandatory
             DESCRIPTION
                     "The default remote TCP port to which the server will
                     attempt to connect when a user starts a Telnet/Rlogin
                     session on a port with this profile."
             ::= { vProfEntry 5 }

           vProfTcpTimeout OBJECT-TYPE
             SYNTAX  INTEGER (0..65535)
             ACCESS  read-write
             STATUS  mandatory
             DESCRIPTION
                     "The maximum number of seconds TCP will wait for an
                     acknowledgement before terminating the session."
             ::= { vProfEntry 6 }

           vProfTcpKeepalive OBJECT-TYPE
             SYNTAX  INTEGER (0..65535)
             ACCESS  read-write
             STATUS  mandatory
             DESCRIPTION
                     "The number of seconds that the sessions intiated with
                     this profile may remain idle (no characters transmitted
                     or recieved) before a TCP keepalive message is generated.
                     A value of 0 indicates that keepalive messages are never
                     generated."
             ::= { vProfEntry 7 }

           vProfIpTTL OBJECT-TYPE
             SYNTAX  INTEGER (1..255)
             ACCESS  read-write
             STATUS  mandatory
             DESCRIPTION
                     "The value of the IP time to live on packets transmitted
                     for sessions initiated with this profile."
             ::= { vProfEntry 8 }

           vProfIpPrecedence OBJECT-TYPE
             SYNTAX  INTEGER (1..255)
             ACCESS  read-write
             STATUS  mandatory
             DESCRIPTION
                     "The value of the IP precedence on packets transmitted
                     for sessions initiated with this profile."
             ::= { vProfEntry 9 }

           vProfTermType OBJECT-TYPE
             SYNTAX  DisplayString (SIZE (0..16))
             ACCESS  read-write
             STATUS  mandatory
             DESCRIPTION
                     "The terminal type that Telnet/Rlogin will attempt to
                     negotiate with the remote node for sessions initiated
                     with this profile.  A zero-length value indicates that
                     no terminal type is negotiated."
             ::= { vProfEntry 10 }

           vProfCrToNet OBJECT-TYPE
             SYNTAX  OCTET STRING (SIZE (1..2))
             ACCESS  read-write
             STATUS  mandatory
             DESCRIPTION
                     "The character sequence which is sent by Telnet to the
                     remote node to indicate a carriage return in the data
                     stream for sessions initiated with this profile."
             ::= { vProfEntry 11 }

           vProfCrFromTerm OBJECT-TYPE
             SYNTAX  OCTET STRING (SIZE (1..2))
             ACCESS  read-write
             STATUS  mandatory
             DESCRIPTION
                     "The local character sequence which, when delivered to
                     Telnet for transmission, is interpreted as a carriage
                     return and translated to the sequence indicated by
                     vProfCrToNet for sessions initiated with this profile."
             ::= { vProfEntry 12 }

           vProfPadChar OBJECT-TYPE
             SYNTAX  Character
             ACCESS  read-write
             STATUS  mandatory
             DESCRIPTION
                     "The character used by the local Telnet implementation
                     to pad transmitted data immediately following a carriage
                     return for sessions initiated with this profile.  A value
                     of 0 indicates that the character is disabled."
             ::= { vProfEntry 13 }

           vProfPadLength OBJECT-TYPE
             SYNTAX  INTEGER (0..255)
             ACCESS  read-write
             STATUS  mandatory
             DESCRIPTION
                     "The number of pad characters inserted into the data
                     stream by the local Telnet implementation immediately
                     following a carriage return for sessions initiated with
                     this profile."
             ::= { vProfEntry 14 }

           vProfEndRecord OBJECT-TYPE
             SYNTAX  Character
             ACCESS  read-write
             STATUS  mandatory
             DESCRIPTION
                     "The local character which, when delivered to Telnet for
                     transmission, is interpreted as an end-of-record
                     character and translated to the appropriate Telnet
                     control function for sessions initiated with this
                     profile.  A value of 255 indicates that the character is
                     disabled."
             ::= { vProfEntry 15 }

           vProfNop OBJECT-TYPE
             SYNTAX  Character
             ACCESS  read-write
             STATUS  mandatory
             DESCRIPTION
                     "The local character which, when delivered to Telnet for
                     transmission, is interpreted as a no-op character and
                     translated to the appropriate Telnet control function for
                     sessions initiated with this profile.  A value of 255
                     indicates that the character is disabled."
             ::= { vProfEntry 16 }

           vProfDataMark OBJECT-TYPE
             SYNTAX  Character
             ACCESS  read-write
             STATUS  mandatory
             DESCRIPTION
                     "The local character which, when delivered to Telnet for
                     transmission, is interpreted as a data mark character and
                     translated to the appropriate Telnet control function for
                     sessions initiated with this profile.  A value of 255
                     indicates that the character is disabled."
             ::= { vProfEntry 17 }

           vProfBreak OBJECT-TYPE
             SYNTAX  Character
             ACCESS  read-write
             STATUS  mandatory
             DESCRIPTION
                     "The local character which, when delivered to Telnet for
                     transmission, is interpreted as a break character and
                     translated to the appropriate Telnet control function for
                     sessions initiated with this profile.  A value of 255
                     indicates that the character is disabled."
             ::= { vProfEntry 18 }

           vProfIntProcess OBJECT-TYPE
             SYNTAX  Character
             ACCESS  read-write
             STATUS  mandatory
             DESCRIPTION
                     "The local character which, when delivered to Telnet for
                     transmission, is interpreted as the interrupt process
                     character and translated to the appropriate Telnet
                     control function for sessions initiated with this
                     profile.  A value of 255 indicates that the character is
                     disabled."
             ::= { vProfEntry 19 }

           vProfAbortOutput OBJECT-TYPE
             SYNTAX  Character
             ACCESS  read-write
             STATUS  mandatory
             DESCRIPTION
                     "The local character which, when delivered to Telnet for
                     transmission, is interpreted as the abort output
                     character and translated to the appropriate Telnet
                     control function for sessions initiated with this
                     profile.  A value of 255 indicates that the character is
                     disabled."
             ::= { vProfEntry 20 }

           vProfAttention OBJECT-TYPE
             SYNTAX  Character
             ACCESS  read-write
             STATUS  mandatory
             DESCRIPTION
                     "The local character which, when delivered to Telnet for
                     transmission, is interpreted as the attention character
                     and translated to the appropriate Telnet control
                     function for sessions initiated with this profile.  A
                     value of 255 indicates that the character is disabled."
             ::= { vProfEntry 21 }

           vProfEraseChar OBJECT-TYPE
             SYNTAX  Character
             ACCESS  read-write
             STATUS  mandatory
             DESCRIPTION
                     "The local character which, when delivered to Telnet for
                     transmission, is interpreted as the backspace character
                     and translated to the appropriate Telnet control
                     function for sessions initiated with this profile.  A
                     value of 255 indicates that the character is disabled."
             ::= { vProfEntry 22 }

           vProfEraseLine OBJECT-TYPE
             SYNTAX  Character
             ACCESS  read-write
             STATUS  mandatory
             DESCRIPTION
                     "The local character which, when delivered to Telnet for
                     transmission, is interpreted as the erase line character
                     and translated to the appropriate Telnet control function
                     for sessions initiated with this profile.  A value of 255
                     indicates that the character is disabled."
             ::= { vProfEntry 23 }

           vProfGoAhead OBJECT-TYPE
             SYNTAX  Character
             ACCESS  read-write
             STATUS  mandatory
             DESCRIPTION
                     "The local character which, when delivered to Telnet for
                     transmission, is interpreted as the go ahead character
                     and translated to the appropriate Telnet control function
                     for sessions initiated with this profile.  A value of 255
                     indicates that the character is disabled."
             ::= { vProfEntry 24 }

           vProfNullPass OBJECT-TYPE
             SYNTAX  INTEGER {
                         enabled(1),
                         disabled(2)
                     }
             ACCESS  read-write
             STATUS  mandatory
             DESCRIPTION
                     "When enabled, null characters received by Telnet
                     immediately following carriage return characters are
                     passed through the data stream untouched.  When disabled,
                     these padding null characters are removed from the
                     received data stream.  This applies to sessions initiated
                     with this profile."
             ::= { vProfEntry 25 }

           vProfLocalEcho OBJECT-TYPE
             SYNTAX  INTEGER {
                         attempt(1),
                         refuse(2),
                         allow(3)
                     }
             ACCESS  read-write
             STATUS  mandatory
             DESCRIPTION
                     "Determines how the local Telnet entity negotiates the
                     local echo option with the remote Telnet entity for
                     sessions initiated with this profile.  'attempt(1)'
                     indicates the the local Telnet entity actively attempts
                     to enable the option.  'refuse(2)' indicates that the
                     local Telnet entity will refuse to enable the option
                     even when requested by the remote entity.  'allow(3)
                     indicates that the local Telnet entity will not actively
                     attempt to enable the option, but will enable the option
                     when requested by the remote entity."
             ::= { vProfEntry 26 }

           vProfRemoteEcho OBJECT-TYPE
             SYNTAX  INTEGER {
                         attempt(1),
                         refuse(2),
                         allow(3)
                     }
             ACCESS  read-write
             STATUS  mandatory
             DESCRIPTION
                     "Determines how the local Telnet entity negotiates the
                     remote echo option with the remote Telnet entity for
                     sessions initiated with this profile.  'attempt(1)'
                     indicates the the local Telnet entity actively attempts
                     to enable the option.  'refuse(2)' indicates that the
                     local Telnet entity will refuse to enable the option
                     even when requested by the remote entity.  'allow(3)
                     indicates that the local Telnet entity will not actively
                     attempt to enable the option, but will enable the option
                     when requested by the remote entity."
             ::= { vProfEntry 27 }

           vProfLocalBinary OBJECT-TYPE
             SYNTAX  INTEGER {
                         attempt(1),
                         refuse(2),
                         allow(3)
                     }
             ACCESS  read-write
             STATUS  mandatory
             DESCRIPTION
                     "Determines how the local Telnet entity negotiates the
                     local binary option with the remote Telnet entity for
                     sessions initiated with this profile.  'attempt(1)'
                     indicates the the local Telnet entity actively attempts
                     to enable the option.  'refuse(2)' indicates that the
                     local Telnet entity will refuse to enable the option
                     even when requested by the remote entity.  'allow(3)
                     indicates that the local Telnet entity will not actively
                     attempt to enable the option, but will enable the option
                     when requested by the remote entity."
             ::= { vProfEntry 28 }

           vProfRemoteBinary OBJECT-TYPE
             SYNTAX  INTEGER {
                         attempt(1),
                         refuse(2),
                         allow(3)
                     }
             ACCESS  read-write
             STATUS  mandatory
             DESCRIPTION
                     "Determines how the local Telnet entity negotiates the
                     remote binary option with the remote Telnet entity for
                     sessions initiated with this profile.  'attempt(1)'
                     indicates the the local Telnet entity actively attempts
                     to enable the option.  'refuse(2)' indicates that the
                     local Telnet entity will refuse to enable the option
                     even when requested by the remote entity.  'allow(3)
                     indicates that the local Telnet entity will not actively
                     attempt to enable the option, but will enable the option
                     when requested by the remote entity."
             ::= { vProfEntry 29 }

           vProfStatus OBJECT-TYPE
             SYNTAX  INTEGER {
                         valid(1),
                         invalid(2)
                     }
             ACCESS  read-write
             STATUS  mandatory
             DESCRIPTION
                     "The current status of this profile entry.  Setting this
                     object to the value invalid(2) has the effect of deleting
                     the entry from the profile table."
             ::= { vProfEntry 30 }


           -- the vcpIpSecurity group

--            This group defines the table of IP security structures to be
--            referenced by the server when deciding whether to allow or
--            refuse a connection to a given IP address.  See the user manual
--            for complete description of how each parameter functions.

           vSecEnable OBJECT-TYPE
             SYNTAX  INTEGER {
                         enabled(1),
                         disabled(2)
                     }
             ACCESS  read-write
             STATUS  mandatory
             DESCRIPTION
                     "Determines whether or not the server's IP security
                     feature is enabled."
             ::= { vcpIpSecurity 1 }

           vSecCurrNumber OBJECT-TYPE
             SYNTAX  INTEGER
             ACCESS  read-only
             STATUS  mandatory
             DESCRIPTION
                     "An integer indicating the current number of entries in
                     vSecTable.  This object is not constant."
             ::= { vcpIpSecurity 2 }

           vSecTable OBJECT-TYPE
             SYNTAX  SEQUENCE OF VSecEntry
             ACCESS  not-accessible
             STATUS  mandatory
             DESCRIPTION
                     "A list of security entries.  The number of entries is
                     given by the value of vSecCurrNumber."
             ::= { vcpIpSecurity 3 }

           vSecEntry OBJECT-TYPE
             SYNTAX  VSecEntry
             ACCESS  not-accessible
             STATUS  mandatory
             DESCRIPTION
                     "Parameter values for a security entry."
             INDEX   { vSecIndex }
             ::= { vSecTable 1 }

          VSecEntry ::=
              SEQUENCE {
                  vSecIndex
                      INTEGER,
                  vSecAddress
                      IpAddress,
                  vSecMask
                      IpAddress,
                  vSecGroups
                      LtGroupList,
                  vSecStatus
                      INTEGER
              }

           vSecIndex OBJECT-TYPE
             SYNTAX  INTEGER (0..32)
             ACCESS  read-write
             STATUS  mandatory
             DESCRIPTION
                     "A unique value for each security entry."
             ::= { vSecEntry 1 }

           vSecAddress OBJECT-TYPE
             SYNTAX  IpAddress
             ACCESS  read-write
             STATUS  mandatory
             DESCRIPTION
                     "The target address of the IP security entry."
             ::= { vSecEntry 2 }

           vSecMask OBJECT-TYPE
             SYNTAX  IpAddress
             ACCESS  read-write
             STATUS  mandatory
             DESCRIPTION
                     "A mask which is applied to vSecAddress to determine its
                     significant bits."
             ::= { vSecEntry 3 }

           vSecGroups OBJECT-TYPE
             SYNTAX  LtGroupList
             ACCESS  read-write
             STATUS  mandatory
             DESCRIPTION
                     "A set of group numbers which determines which security
                     entries are in use on which ports."
             ::= { vSecEntry 4 }

           vSecStatus OBJECT-TYPE
             SYNTAX  INTEGER {
                         valid(1),
                         invalid(2)
                     }
             ACCESS  read-write
             STATUS  mandatory
             DESCRIPTION
                     "The current status of this security entry.  Setting this
                     object to the value invalid(2) has the effect of deleting
                     the entry from the security table."
             ::= { vSecEntry 5 }


           -- the vcpHostname group

--            The vHostTable associates hostnames with IP addresses.

           vHostCurrNumber OBJECT-TYPE
             SYNTAX  INTEGER
             ACCESS  read-only
             STATUS  mandatory
             DESCRIPTION
                     "An integer indicating the current number of entries in
                     vHostTable.  This object is not constant."
             ::= { vcpHostname 1 }

           vHostTable OBJECT-TYPE
             SYNTAX  SEQUENCE OF VHostEntry
             ACCESS  not-accessible
             STATUS  mandatory
             DESCRIPTION
                     "A list of hostname entries.  The number of entries is
                     given by the value of vHostCurrNumber."
             ::= { vcpHostname 2 }

           vHostEntry OBJECT-TYPE
             SYNTAX  VHostEntry
             ACCESS  not-accessible
             STATUS  mandatory
             DESCRIPTION
                     "Parameter and status values for a hostname entry."
             INDEX   { vHostHostname }
             ::= { vHostTable 1 }

          VHostEntry ::=
              SEQUENCE {
                  vHostHostname
                      DisplayString,
                  vHostAddress
                      IpAddress,
                  vHostTTL
                      INTEGER,
                  vHostStatus
                      INTEGER
              }

           vHostHostname OBJECT-TYPE
             SYNTAX  OCTET STRING (SIZE (1..64))
             ACCESS  read-write
             STATUS  mandatory
             DESCRIPTION
                     "The hostname of the host.  Note that if the value of
                     vNsAllowLowerCase is 'disabled(2)', then on a set-request
                     the specified hostname is automatically converted to
                     upper case."
             ::= { vHostEntry 1 }

           vHostAddress OBJECT-TYPE
             SYNTAX  IpAddress
             ACCESS  read-write
             STATUS  mandatory
             DESCRIPTION
                     "The IP address of the host."
             ::= { vHostEntry 2 }

           vHostTTL OBJECT-TYPE
             SYNTAX  INTEGER
             ACCESS  read-only
             STATUS  mandatory
             DESCRIPTION
                     "The time to live (in seconds) of this entry in the host
                     table.  If the entry has been dynamically created by the
                     nameserver protocol, the TTL will be a non-zero value
                     indicating its remaining lifetime.  Upon expiration of
                     the TTL the entry is automatically deleted from the
                     table.  If the entry was created by a network
                     administrator, the entry is considered 'permanent' and
                     the value of its vHostTTL will be 0."
             ::= { vHostEntry 3 }

           vHostStatus OBJECT-TYPE
             SYNTAX  INTEGER {
                         valid(1),
                         invalid(2)
                     }
             ACCESS  read-write
             STATUS  mandatory
             DESCRIPTION
                     "The desired status of this host entry.  Setting this
                     object to the value 'invalid(2)' indicates that the
                     entry is desired to be deleted from the host table.  Only
                     permanent entries will be deleted (entries for which the
                     value of vHostTTL is 0).  Dynamic entries are only
                     deleted upon expiration of their vHostTTL or upon system
                     re-initialization."
             ::= { vHostEntry 4 }


           -- the vcpNameserver group

--            The VCP-x servers can perform dynamic hostname resolution by
--            communicating with known nameserver hosts.  The vNsTable
--            specifies those nameserver hosts with which the server may
--            attempt to communicate in order to resolve hostnames into IP
--            addresses.

           vNsRequestMode OBJECT-TYPE
             SYNTAX  INTEGER {
                         recursive(1),
                         nonRecursive(2)
                     }
             ACCESS  read-write
             STATUS  mandatory
             DESCRIPTION
                     "The current mode of network hostname resolution.
                     'recursive(1)' indicates that the server sends
                     recursive-type requests to network nameservers.
                     'nonRecursive(2)' indicates that the server does not
                     send recursive-type nameserver requests."
             ::= { vcpNameserver 1 }

           vNsAllowLowerCase OBJECT-TYPE
             SYNTAX  INTEGER {
                         enabled(1),
                         disabled(2)
                     }
             ACCESS  read-write
             STATUS  mandatory
             DESCRIPTION
                     "Determines whether the nameserver resolver will
                     automatically convert user-specified hostnames to upper
                     case before attempting to resolve them.  'disabled(2)'
                     indicates that automatic conversion to upper case will
                     take place."
             ::= { vcpNameserver 2 }

           vNsCurrNumber OBJECT-TYPE
             SYNTAX  INTEGER
             ACCESS  read-only
             STATUS  mandatory
             DESCRIPTION
                     "An integer indicating the current number of entries in
                     vNsTable.  This object is not constant."
             ::= { vcpNameserver 3 }

           vNsTable OBJECT-TYPE
             SYNTAX  SEQUENCE OF VNsEntry
             ACCESS  not-accessible
             STATUS  mandatory
             DESCRIPTION
                     "A list of nameserver entries.  The number of entries is
                     given by the value of vNsCurrNumber."
             ::= { vcpNameserver 4 }

           vNsEntry OBJECT-TYPE
             SYNTAX  VNsEntry
             ACCESS  not-accessible
             STATUS  mandatory
             DESCRIPTION
                     "Parameter values for a nameserver entry."
             INDEX   { vNsAddress }
             ::= { vNsTable 1 }

          VNsEntry ::=
              SEQUENCE {
                  vNsAddress
                      IpAddress,
                  vNsHostname
                      DisplayString,
                  vNsTTL
                      TimeTicks,
                  vNsStatus
                      INTEGER
              }

           vNsAddress OBJECT-TYPE
             SYNTAX  IpAddress
             ACCESS  read-write
             STATUS  mandatory
             DESCRIPTION
                     "The IP address of the nameserver host."
             ::= { vNsEntry 1 }

           vNsHostname OBJECT-TYPE
             SYNTAX  OCTET STRING (SIZE (1..64))
             ACCESS  read-only
             STATUS  mandatory
             DESCRIPTION
                     "The resolved hostname of the nameserver host  A zero-
                     length value indicates that the hostname is unknown
                     at the present time."
             ::= { vNsEntry 2 }

           vNsTTL OBJECT-TYPE
             SYNTAX  INTEGER
             ACCESS  read-only
             STATUS  mandatory
             DESCRIPTION
                     "The time to live (in seconds) of this entry in the
                     nameserver table.  If the entry has been dynamically
                     created by the nameserver protocol, the TTL will be a
                     non-zero value indicating its remaining lifetime.  Upon
                     expiration of the TTL the entry is automatically deleted
                     from the table.  If the entry was created by a network
                     administrator, the entry is considered 'permanent' and
                     the value of its vNsTTL will be 0."
             ::= { vNsEntry 3 }

           vNsStatus OBJECT-TYPE
             SYNTAX  INTEGER {
                         valid(1),
                         invalid(2)
                     }
             ACCESS  read-write
             STATUS  mandatory
             DESCRIPTION
                     "The status of this nameserver entry.  Setting this
                     object to the value 'invalid(2)' has the effect of
                     deleting the entry from the nameserver table.  Dynamic
                     entries are also automatically deleted upon expiration of
                     their vNsTTL or upon system re-initialization."
             ::= { vNsEntry 4 }


           -- the vcpTacacs group

--            The VCP-x servers are capable using a network Tacacs server(s)
--            to maintain a username-password association.  A user may then
--            be required to type his correct username-password combination
--            in order to login to a server port which is so configured.
--            The vTacTable specifies those Tacacs server hosts with which the
--            server may attempt to communicate in order to verify a user's
--            password.

           vTacServerCurrNumber OBJECT-TYPE
             SYNTAX  INTEGER
             ACCESS  read-only
             STATUS  mandatory
             DESCRIPTION
                     "An integer indicating the current number of entries in
                     vTacTable.  This object is not constant."
             ::= { vcpTacacs 1 }

           vTacTable OBJECT-TYPE
             SYNTAX  SEQUENCE OF VTacEntry
             ACCESS  not-accessible
             STATUS  mandatory
             DESCRIPTION
                     "A list of Tacacs server entries.  The number of entries
                     is given by the value of vTacServerCurrNumber."
             ::= { vcpTacacs 2 }

           vTacEntry OBJECT-TYPE
             SYNTAX  VTacEntry
             ACCESS  not-accessible
             STATUS  mandatory
             DESCRIPTION
                     "Parameter values for a Tacacs server entry."
             INDEX   { vTacAddress }
             ::= { vTacTable 1 }

          VTacEntry ::=
              SEQUENCE {
                  vTacAddress
                      IpAddress,
                  vTacHostname
                      DisplayString,
                  vTacStatus
                      INTEGER
              }

           vTacAddress OBJECT-TYPE
             SYNTAX  IpAddress
             ACCESS  read-write
             STATUS  mandatory
             DESCRIPTION
                     "The IP address of the Tacacs server host."
             ::= { vTacEntry 1 }

           vTacHostname OBJECT-TYPE
             SYNTAX  OCTET STRING (SIZE (0..63))
             ACCESS  read-only
             STATUS  mandatory
             DESCRIPTION
                     "The resolved hostname of the Tacacs server host.  If the
                     hostname is currently unknown, a zero-length value is
                     returned."
             ::= { vTacEntry 2 }

           vTacStatus OBJECT-TYPE
             SYNTAX  INTEGER {
                         valid(1),
                         invalid(2)
                     }
             ACCESS  read-write
             STATUS  mandatory
             DESCRIPTION
                     "The current status of this Tacacs server entry.  Setting
                     this object to the value invalid(2) has the effect of
                     deleting the entry from the Tacacs server table."
             ::= { vTacEntry 3 }


           -- the vcpIp group

--            This group defines IP objects which are not accessible through
--            MIB II.

           vIpBcastAddr OBJECT-TYPE
             SYNTAX  IpAddress
             ACCESS  read-write
             STATUS  mandatory
             DESCRIPTION
                     "The IP address to be used for IP limited broadcasts
                     originating from this unit."
             ::= { vcpIp 1 }

           vIpMaxAddr OBJECT-TYPE
             SYNTAX  INTEGER (8..64)
             ACCESS  read-write
             STATUS  mandatory
             DESCRIPTION
                     "An integer indicating the maximum number of IP addresses
                     that can be simultaneously assigned to this unit,
                     totaling over all interfaces.  Note that the server must
                     be rebooted before a change in the value of this variable
                     actually takes effect."
             ::= { vcpIp 2 }

           vIpMaxHostHashEntries OBJECT-TYPE
             SYNTAX  INTEGER {
                         size-11(1),
                         size-13(2),
                         size-17(3),
                         size-19(4),
                         size-23(5),
                         size-29(6),
                         size-31(7),
                         size-37(8),
                         size-41(9),
                         size-43(10),
                         size-47(11),
                         size-49(12),
                         size-53(13),
                         size-59(14),
                         size-61(15),
                         size-67(16)
                     }
             ACCESS  read-write
             STATUS  mandatory
             DESCRIPTION
                     "An integer indicating the number of buckets in the host
                     route hash table.  Note that the server must be rebooted
                     before a change in the value of this variable actually
                     takes effect."
             ::= { vcpIp 3 }

           vIpMaxNetHashEntries OBJECT-TYPE
             SYNTAX  INTEGER {
                         size-11(1),
                         size-13(2),
                         size-17(3),
                         size-19(4),
                         size-23(5),
                         size-29(6),
                         size-31(7),
                         size-37(8),
                         size-41(9),
                         size-43(10),
                         size-47(11),
                         size-49(12),
                         size-53(13),
                         size-59(14),
                         size-61(15),
                         size-67(16)
                     }
             ACCESS  read-write
             STATUS  mandatory
             DESCRIPTION
                     "An integer indicating the number of buckets in the
                     network route hash table.  Note that the server must be
                     rebooted before a change in the value of this variable
                     actually takes effect."
             ::= { vcpIp 4 }

           vIpMaxInterfaces OBJECT-TYPE
             SYNTAX  INTEGER (2..128)
             ACCESS  read-write
             STATUS  mandatory
             DESCRIPTION
                     "An integer indicating the maximum number of IP
                     interfaces of all types that can be configured on the
                     unit.  Note that the server must be rebooted before a
                     change in the value of this variable actually takes
                     effect."
             ::= { vcpIp 5 }

           vIpMaxRoutes OBJECT-TYPE
             SYNTAX  INTEGER (16..128)
             ACCESS  read-write
             STATUS  mandatory
             DESCRIPTION
                     "An integer indicating the maximum number of entries in
                     the unit's route table.  Note that the server must be
                     rebooted before a change in the value of this variable
                     actually takes effect."
             ::= { vcpIp 6 }


           -- the vcpArp group

--            This group defines ARP objects which are not accessible through
--            MIB II.

           vArpMaxEntries OBJECT-TYPE
             SYNTAX  INTEGER (16..128)
             ACCESS  read-write
             STATUS  mandatory
             DESCRIPTION
                     "An integer indicating the maximum number of entries in
                     the unit's ARP table.  Note that the server must be
                     rebooted before a change in the value of this variable
                     actually takes effect."
             ::= { vcpArp 1 }

           vArpRetryTimeout OBJECT-TYPE
             SYNTAX  INTEGER (1..30)
             ACCESS  read-write
             STATUS  mandatory
             DESCRIPTION
                     "An integer indicating the number of seconds between
                     ARP retransmit attempts."
             ::= { vcpArp 2 }

           vArpRetryMax OBJECT-TYPE
             SYNTAX  INTEGER (2..10)
             ACCESS  read-write
             STATUS  mandatory
             DESCRIPTION
                     "An integer indicating the maximum number of ARP
                     retransmit attempts."
             ::= { vcpArp 3 }

           vArpConfirmTimer OBJECT-TYPE
             SYNTAX  INTEGER (1..300)
             ACCESS  read-write
             STATUS  mandatory
             DESCRIPTION
                     "An integer indicating the number of seconds between
                     confirmations of an ARP entry."
             ::= { vcpArp 4 }

           vArpIdleTimeout OBJECT-TYPE
             SYNTAX  INTEGER (60..1800)
             ACCESS  read-write
             STATUS  mandatory
             DESCRIPTION
                     "An integer indicating the number of seconds that a
                     non-permanent ARP entry can go unused before it is
                     deleted from the table.  A non-permanent entry is one
                     which was entered into the table by the ARP protocol
                     rather than manually entered by a network administrator."
             ::= { vcpArp 5 }


           -- the vcpTcp group

--            This group defines TCP objects which are not accessible through
--            MIB II.

           vTcpIpPrecedence OBJECT-TYPE
             SYNTAX  INTEGER (0..255)
             ACCESS  read-write
             STATUS  mandatory
             DESCRIPTION
                     "An integer indicating the value of the IP precedence
                     that the TCP layer will request."
             ::= { vcpTcp 1 }

           vTcpSendQSize OBJECT-TYPE
             SYNTAX  INTEGER (128..8192)
             ACCESS  read-write
             STATUS  mandatory
             DESCRIPTION
                     "An integer indicating the maximum number of data bytes
                     that will be queued for transmission by the TCP protocol
                     layer."
             ::= { vcpTcp 2 }

           vTcpRcvWinSize OBJECT-TYPE
             SYNTAX  INTEGER (128..8192)
             ACCESS  read-write
             STATUS  mandatory
             DESCRIPTION
                     "An integer indicating the TCP receive window size in
                     bytes."
             ::= { vcpTcp 3 }

           vTcpSegSize OBJECT-TYPE
             SYNTAX  INTEGER (64..511)
             ACCESS  read-write
             STATUS  mandatory
             DESCRIPTION
                     "An integer indicating the TCP segment size in bytes."
             ::= { vcpTcp 4 }

           vTcpTimerInterval OBJECT-TYPE
             SYNTAX  INTEGER (1..200)
             ACCESS  read-write
             STATUS  mandatory
             DESCRIPTION
                     "An integer indicating the resolution (in 1/100 s) of all
                     timer values used by TCP."
             ::= { vcpTcp 5 }

           vTcpChecksumEnable OBJECT-TYPE
             SYNTAX  INTEGER {
                         enabled(1),
                         disabled(2)
                     }
             ACCESS  read-write
             STATUS  mandatory
             DESCRIPTION
                     "An integer indicating whether TCP checksums are enabled
                     for all TCP connections."
             ::= { vcpTcp 6 }


           -- the vcpTelnet group

--            This group defines objects relevant to the Telnet protocol.

           vTelCourierEnable OBJECT-TYPE
             SYNTAX  INTEGER {
                         enabled(1),
                         disabled(2)
                     }
             ACCESS  read-write
             STATUS  mandatory
             DESCRIPTION
                     "Determines whether or not the Telnet courier feature is
                     enabled."
             ::= { vcpTelnet 1 }

           vTelCourierText OBJECT-TYPE
             SYNTAX  OCTET STRING (SIZE (0..16))
             ACCESS  read-write
             STATUS  mandatory
             DESCRIPTION
                     "Defines the text which is tranmsitted for the Telnet
                     courier feature."
             ::= { vcpTelnet 2 }

           vTelSessCurrNumber OBJECT-TYPE
             SYNTAX  INTEGER
             ACCESS  read-only
             STATUS  mandatory
             DESCRIPTION
                     "An integer indicating the current number of entries in
                     vTelSessTable.  This object is not constant."
             ::= { vcpTelnet 3 }

           vTelSessTable OBJECT-TYPE
             SYNTAX  SEQUENCE OF VTelSessEntry
             ACCESS  not-accessible
             STATUS  mandatory
             DESCRIPTION
                     "A list of Telnet session entries.  The number of entries
                     is given by the value of vTelSessCurrNumber."
             ::= { vcpTelnet 4 }

           vTelSessEntry OBJECT-TYPE
             SYNTAX  VTelSessEntry
             ACCESS  not-accessible
             STATUS  mandatory
             DESCRIPTION
                     "Parameter and status values for a Telnet session entry."
             INDEX   { vTelSessPortIndex, vTelSessIndex }
             ::= { vTelSessTable 1 }

          VTelSessEntry ::=
              SEQUENCE {
                  vTelSessPortIndex
                      INTEGER,
                  vTelSessIndex
                      INTEGER,
                  vTelSessOrigin
                      INTEGER,
                  vTelSessState
                      INTEGER,
                  vTelSessDisconnect
                      INTEGER,
                  vTelSessLocalAddr
                      IpAddress,
                  vTelSessLocalTcpPort
                      INTEGER,
                  vTelSessRemAddr
                      IpAddress,
                  vTelSessRemTcpPort
                      INTEGER,
                  vTelSessCrToNet
                      OCTET STRING,
                  vTelSessCrFromTerm
                      OCTET STRING,
                  vTelSessPadChar
                      Character,
                  vTelSessPadLength
                      INTEGER,
                  vTelSessUserTimeout
                      INTEGER,
                  vTelSessKeepalive
                      INTEGER,
                  vTelSessIpTTL
                      INTEGER,
                  vTelSessIpPrecedence
                      INTEGER,
                  vTelSessEndRecord
                      Character,
                  vTelSessNop
                      Character,
                  vTelSessDataMark
                      Character,
                  vTelSessBreak
                      Character,
                  vTelSessIntProcess
                      Character,
                  vTelSessAbortOutput
                      Character,
                  vTelSessAttention
                      Character,
                  vTelSessEraseChar
                      Character,
                  vTelSessEraseLine
                      Character,
                  vTelSessGoAhead
                      Character,
                  vTelSessNullPass
                      INTEGER,
                  vTelSessTermType
                      DisplayString,
                  vTelSessLocalEcho
                      INTEGER,
                  vTelSessRemoteEcho
                      INTEGER,
                  vTelSessLocalBinary
                      INTEGER,
                  vTelSessRemoteBinary
                      INTEGER
              }

           vTelSessPortIndex OBJECT-TYPE
             SYNTAX  INTEGER
             ACCESS  read-only
             STATUS  mandatory
             DESCRIPTION
                     "The value of vPortIndex for the port to which this
                     session belongs."
             ::= { vTelSessEntry 1 }

           vTelSessIndex OBJECT-TYPE
             SYNTAX  INTEGER
             ACCESS  read-only
             STATUS  mandatory
             DESCRIPTION
                     "The session index in the context of the port, a 
                     non-zero positive integer.  Session indexes within a 
                     port need not be sequential.  Session indexes may be 
                     reused for different ports.  For example, port 1 and 
                     port 3 may both have a session 2 at the same time."
             ::= { vTelSessEntry 2 }

           vTelSessOrigin OBJECT-TYPE
             SYNTAX  INTEGER {
                         unknown(1),
                         network(2),
                         local(3)
                     }
             ACCESS  read-only
             STATUS  mandatory
             DESCRIPTION
                     "The session's source of establishment."
             ::= { vTelSessEntry 3 }

           vTelSessState OBJECT-TYPE
             SYNTAX  INTEGER {
                         starting(1),
                         running(2),
                         stopping(3)
                     }
             ACCESS  read-only
             STATUS  mandatory
             DESCRIPTION
                     "The current state of the session."
             ::= { vTelSessEntry 4 }

           vTelSessDisconnect OBJECT-TYPE
             SYNTAX  INTEGER {
                         ready(1),
                         execute(2)
                     }
             ACCESS  read-write
             STATUS  mandatory
             DESCRIPTION
                     "A control to terminate the session.  In response to 
                     a get-request or get-next-request, the agent always 
                     returns 'ready(1)' as the value.  Setting the value to 
                     'execute(2)' causes termination."
             ::= { vTelSessEntry 5 }

           vTelSessLocalAddr OBJECT-TYPE
             SYNTAX  IpAddress
             ACCESS  read-only
             STATUS  mandatory
             DESCRIPTION
                     "The local IP address for this session.  This object
                     supplies part of the necessary index information to
                     locate the corresponding session in the MIB II
                     TcpConnTable."
             ::= { vTelSessEntry 6 }

           vTelSessLocalTcpPort OBJECT-TYPE
             SYNTAX  INTEGER (1..65535)
             ACCESS  read-only
             STATUS  mandatory
             DESCRIPTION
                     "The local TCP port number for this session.  This object
                     supplies part of the necessary index information to
                     locate the corresponding session in the MIB II
                     TcpConnTable."
             ::= { vTelSessEntry 7 }

           vTelSessRemAddr OBJECT-TYPE
             SYNTAX  IpAddress
             ACCESS  read-only
             STATUS  mandatory
             DESCRIPTION
                     "The remote IP address for this session.  This object
                     supplies part of the necessary index information to
                     locate the corresponding session in the MIB II
                     TcpConnTable."
             ::= { vTelSessEntry 8 }

           vTelSessRemTcpPort OBJECT-TYPE
             SYNTAX  INTEGER (1..65535)
             ACCESS  read-only
             STATUS  mandatory
             DESCRIPTION
                     "The remote TCP port number for this session.  This
                     object supplies part of the necessary index information
                     to locate the corresponding session in the MIB II
                     TcpConnTable."
             ::= { vTelSessEntry 9 }

           vTelSessCrToNet OBJECT-TYPE
             SYNTAX  OCTET STRING (SIZE (1..2))
             ACCESS  read-write
             STATUS  mandatory
             DESCRIPTION
                     "The character sequence which is sent to the remote node
                     of the session to indicate a carriage return in the data
                     stream."
             ::= { vTelSessEntry 10 }

           vTelSessCrFromTerm OBJECT-TYPE
             SYNTAX  OCTET STRING (SIZE (1..2))
             ACCESS  read-write
             STATUS  mandatory
             DESCRIPTION
                     "The local character sequence which, when delivered to
                     Telnet for transmission, is interpreted as a carriage
                     return and translated to the sequence indicated by
                     vTelSessCrToNet."
             ::= { vTelSessEntry 11 }

           vTelSessPadChar OBJECT-TYPE
             SYNTAX  Character
             ACCESS  read-write
             STATUS  mandatory
             DESCRIPTION
                     "The character used by the local Telnet implementation
                     to pad transmitted data immediately following a carriage
                     return.  A value of 0 indicates that the character is
                     disabled."
             ::= { vTelSessEntry 12 }

           vTelSessPadLength OBJECT-TYPE
             SYNTAX  INTEGER (0..255)
             ACCESS  read-write
             STATUS  mandatory
             DESCRIPTION
                     "The number of pad characters inserted into the data
                     stream by the local Telnet implementation immediately
                     following a carriage return."
             ::= { vTelSessEntry 13 }

           vTelSessUserTimeout OBJECT-TYPE
             SYNTAX  INTEGER (0..65535)
             ACCESS  read-only
             STATUS  mandatory
             DESCRIPTION
                     "The maximum number of seconds Telnet instructs TCP to
                     wait for an acknowledgement before terminating the
                     session."
             ::= { vTelSessEntry 14 }

           vTelSessKeepalive OBJECT-TYPE
             SYNTAX  INTEGER (0..65535)
             ACCESS  read-only
             STATUS  mandatory
             DESCRIPTION
                     "The number of seconds that the session may remain idle
                     (no characters transmitted or recieved) before a TCP
                     keepalive message is generated.  A value of 0 indicates
                     that keepalive messages are never generated."
             ::= { vTelSessEntry 15 }

           vTelSessIpTTL OBJECT-TYPE
             SYNTAX  INTEGER (1..255)
             ACCESS  read-only
             STATUS  mandatory
             DESCRIPTION
                     "The value of the IP time to live on packets transmitted
                     for this session."
             ::= { vTelSessEntry 16 }

           vTelSessIpPrecedence OBJECT-TYPE
             SYNTAX  INTEGER (1..255)
             ACCESS  read-only
             STATUS  mandatory
             DESCRIPTION
                     "The value of the IP precedence on packets transmitted
                     for this session."
             ::= { vTelSessEntry 17 }

           vTelSessEndRecord OBJECT-TYPE
             SYNTAX  Character
             ACCESS  read-write
             STATUS  mandatory
             DESCRIPTION
                     "The local character which, when delivered to Telnet for
                     transmission, is interpreted as an end-of-record
                     character and translated to the appropriate Telnet
                     control function.  A value of 255 indicates that the
                     character is disabled."
             ::= { vTelSessEntry 18 }

           vTelSessNop OBJECT-TYPE
             SYNTAX  Character
             ACCESS  read-write
             STATUS  mandatory
             DESCRIPTION
                     "The local character which, when delivered to Telnet for
                     transmission, is interpreted as a no-op character and
                     translated to the appropriate Telnet control function.  A
                     value of 255 indicates that the character is disabled."
             ::= { vTelSessEntry 19 }

           vTelSessDataMark OBJECT-TYPE
             SYNTAX  Character
             ACCESS  read-write
             STATUS  mandatory
             DESCRIPTION
                     "The local character which, when delivered to Telnet for
                     transmission, is interpreted as a data mark character and
                     translated to the appropriate Telnet control function.  A
                     value of 255 indicates that the character is disabled."
             ::= { vTelSessEntry 20 }

           vTelSessBreak OBJECT-TYPE
             SYNTAX  Character
             ACCESS  read-write
             STATUS  mandatory
             DESCRIPTION
                     "The local character which, when delivered to Telnet for
                     transmission, is interpreted as a break character and
                     translated to the appropriate Telnet control function.  A
                     value of 255 indicates that the character is disabled."
             ::= { vTelSessEntry 21 }

           vTelSessIntProcess OBJECT-TYPE
             SYNTAX  Character
             ACCESS  read-write
             STATUS  mandatory
             DESCRIPTION
                     "The local character which, when delivered to Telnet for
                     transmission, is interpreted as the interrupt process
                     character and translated to the appropriate Telnet
                     control function.  A value of 255 indicates that the
                     character is disabled."
             ::= { vTelSessEntry 22 }

           vTelSessAbortOutput OBJECT-TYPE
             SYNTAX  Character
             ACCESS  read-write
             STATUS  mandatory
             DESCRIPTION
                     "The local character which, when delivered to Telnet for
                     transmission, is interpreted as the abort output
                     character and translated to the appropriate Telnet
                     control function.  A value of 255 indicates that the
                     character is disabled."
             ::= { vTelSessEntry 23 }

           vTelSessAttention OBJECT-TYPE
             SYNTAX  Character
             ACCESS  read-write
             STATUS  mandatory
             DESCRIPTION
                     "The local character which, when delivered to Telnet for
                     transmission, is interpreted as the attention character
                     and translated to the appropriate Telnet control
                     function.  A value of 255 indicates that the character is
                     disabled."
             ::= { vTelSessEntry 24 }

           vTelSessEraseChar OBJECT-TYPE
             SYNTAX  Character
             ACCESS  read-write
             STATUS  mandatory
             DESCRIPTION
                     "The local character which, when delivered to Telnet for
                     transmission, is interpreted as the backspace character
                     and translated to the appropriate Telnet control
                     function.  A value of 255 indicates that the character is
                     disabled."
             ::= { vTelSessEntry 25 }

           vTelSessEraseLine OBJECT-TYPE
             SYNTAX  Character
             ACCESS  read-write
             STATUS  mandatory
             DESCRIPTION
                     "The local character which, when delivered to Telnet for
                     transmission, is interpreted as the erase line character
                     and translated to the appropriate Telnet control
                     function.  A value of 255 indicates that the character is
                     disabled."
             ::= { vTelSessEntry 26 }

           vTelSessGoAhead OBJECT-TYPE
             SYNTAX  Character
             ACCESS  read-write
             STATUS  mandatory
             DESCRIPTION
                     "The local character which, when delivered to Telnet for
                     transmission, is interpreted as the go ahead character
                     and translated to the appropriate Telnet control
                     function.  A value of 255 indicates that the character is
                     disabled."
             ::= { vTelSessEntry 27 }

           vTelSessNullPass OBJECT-TYPE
             SYNTAX  INTEGER {
                         enabled(1),
                         disabled(2)
                     }
             ACCESS  read-write
             STATUS  mandatory
             DESCRIPTION
                     "When enabled, null characters received by Telnet
                     immediately following carriage return characters are
                     passed through the data stream untouched.  When disabled,
                     these padding null characters are removed from the
                     received data stream."
             ::= { vTelSessEntry 28 }

           vTelSessTermType OBJECT-TYPE
             SYNTAX  OCTET STRING (SIZE (0..16))
             ACCESS  read-only
             STATUS  mandatory
             DESCRIPTION
                     "A text string indicating the currently negotiated
                     terminal type for the session.  A zero-length value
                     indicates no terminal type has been negotiated."
             ::= { vTelSessEntry 29 }

           vTelSessLocalEcho OBJECT-TYPE
             SYNTAX  INTEGER {
                         enabled(1),
                         disabled(2)
                     }
             ACCESS  read-only
             STATUS  mandatory
             DESCRIPTION
                     "When enabled, the local Telnet will perform local
                     echoing of all data delivered to it for transmission."
             ::= { vTelSessEntry 30 }

           vTelSessRemoteEcho OBJECT-TYPE
             SYNTAX  INTEGER {
                         enabled(1),
                         disabled(2)
                     }
             ACCESS  read-only
             STATUS  mandatory
             DESCRIPTION
                     "When enabled, the remote Telnet will perform echoing of
                     all received network data."
             ::= { vTelSessEntry 31 }

           vTelSessLocalBinary OBJECT-TYPE
             SYNTAX  INTEGER {
                         enabled(1),
                         disabled(2)
                     }
             ACCESS  read-only
             STATUS  mandatory
             DESCRIPTION
                     "When enabled, the local Telnet will transmit data in
                     binary mode."
             ::= { vTelSessEntry 32 }

           vTelSessRemoteBinary OBJECT-TYPE
             SYNTAX  INTEGER {
                         enabled(1),
                         disabled(2)
                     }
             ACCESS  read-only
             STATUS  mandatory
             DESCRIPTION
                     "When enabled, the remote Telnet will transmit data in
                     binary mode."
             ::= { vTelSessEntry 33 }


           -- the vcpRlogin group

--            This group defines objects relevant to the Rlogin protocol.

           vRlogSessCurrNumber OBJECT-TYPE
             SYNTAX  INTEGER
             ACCESS  read-only
             STATUS  mandatory
             DESCRIPTION
                     "An integer indicating the current number of entries in
                     vRlogSessTable.  This object is not constant."
             ::= { vcpRlogin 1 }

           vRlogSessTable OBJECT-TYPE
             SYNTAX  SEQUENCE OF VRlogSessEntry
             ACCESS  not-accessible
             STATUS  mandatory
             DESCRIPTION
                     "A list of Rlogin session entries.  The number of entries
                     is given by the value of vRlogSessCurrNumber."
             ::= { vcpRlogin 2 }

           vRlogSessEntry OBJECT-TYPE
             SYNTAX  VRlogSessEntry
             ACCESS  not-accessible
             STATUS  mandatory
             DESCRIPTION
                     "Parameter and status values for a Rlogin session entry."
             INDEX   { vRlogSessPortIndex, vRlogSessIndex }
             ::= { vRlogSessTable 1 }

          VRlogSessEntry ::=
              SEQUENCE {
                  vRlogSessPortIndex
                      INTEGER,
                  vRlogSessIndex
                      INTEGER,
                  vRlogSessOrigin
                      INTEGER,
                  vRlogSessState
                      INTEGER,
                  vRlogSessDisconnect
                      INTEGER,
                  vRlogSessLocalAddr
                      IpAddress,
                  vRlogSessLocalTcpPort
                      INTEGER,
                  vRlogSessRemAddr
                      IpAddress,
                  vRlogSessRemTcpPort
                      INTEGER,
                  vRlogSessTermType
                      DisplayString
              }

           vRlogSessPortIndex OBJECT-TYPE
             SYNTAX  INTEGER
             ACCESS  read-only
             STATUS  mandatory
             DESCRIPTION
                     "The value of vPortIndex for the port to which this
                     session belongs."
             ::= { vRlogSessEntry 1 }

           vRlogSessIndex OBJECT-TYPE
             SYNTAX  INTEGER
             ACCESS  read-only
             STATUS  mandatory
             DESCRIPTION
                     "The session index in the context of the port, a 
                     non-zero positive integer.  Session indexes within a 
                     port need not be sequential.  Session indexes may be 
                     reused for different ports.  For example, port 1 and 
                     port 3 may both have a session 2 at the same time."
             ::= { vRlogSessEntry 2 }

           vRlogSessOrigin OBJECT-TYPE
             SYNTAX  INTEGER {
                         unknown(1),
                         network(2),
                         local(3)
                     }
             ACCESS  read-only
             STATUS  mandatory
             DESCRIPTION
                     "The session's source of establishment."
             ::= { vRlogSessEntry 3 }

           vRlogSessState OBJECT-TYPE
             SYNTAX  INTEGER {
                         starting(1),
                         running(2),
                         stopping(3)
                     }
             ACCESS  read-only
             STATUS  mandatory
             DESCRIPTION
                     "The current state of the session."
             ::= { vRlogSessEntry 4 }

           vRlogSessDisconnect OBJECT-TYPE
             SYNTAX  INTEGER {
                         ready(1),
                         execute(2)
                     }
             ACCESS  read-write
             STATUS  mandatory
             DESCRIPTION
                     "A control to terminate the session.  In response to 
                     a get-request or get-next-request, the agent always 
                     returns 'ready(1)' as the value.  Setting the value to 
                     'execute(2)' causes termination."
             ::= { vRlogSessEntry 5 }

           vRlogSessLocalAddr OBJECT-TYPE
             SYNTAX  IpAddress
             ACCESS  read-only
             STATUS  mandatory
             DESCRIPTION
                     "The local IP address for this session.  This object
                     supplies part of the necessary index information to
                     locate the corresponding session in the MIB II
                     TcpConnTable."
             ::= { vRlogSessEntry 6 }

           vRlogSessLocalTcpPort OBJECT-TYPE
             SYNTAX  INTEGER (1..65535)
             ACCESS  read-only
             STATUS  mandatory
             DESCRIPTION
                     "The local TCP port number for this session.  This object
                     supplies part of the necessary index information to
                     locate the corresponding session in the MIB II
                     TcpConnTable."
             ::= { vRlogSessEntry 7 }

           vRlogSessRemAddr OBJECT-TYPE
             SYNTAX  IpAddress
             ACCESS  read-only
             STATUS  mandatory
             DESCRIPTION
                     "The remote IP address for this session.  This object
                     supplies part of the necessary index information to
                     locate the corresponding session in the MIB II
                     TcpConnTable."
             ::= { vRlogSessEntry 8 }

           vRlogSessRemTcpPort OBJECT-TYPE
             SYNTAX  INTEGER (1..65535)
             ACCESS  read-only
             STATUS  mandatory
             DESCRIPTION
                     "The remote TCP port number for this session.  This
                     object supplies part of the necessary index information
                     to locate the corresponding session in the MIB II
                     TcpConnTable."
             ::= { vRlogSessEntry 9 }

           vRlogSessTermType OBJECT-TYPE
             SYNTAX  OCTET STRING (SIZE (0..16))
             ACCESS  read-only
             STATUS  mandatory
             DESCRIPTION
                     "A text string indicating the currently negotiated
                     terminal type for the session.  A zero-length value
                     indicates no terminal type has been negotiated."
             ::= { vRlogSessEntry 10 }


           -- the vcpLt group

--            This group defines objects relevant to the LAT-compatible
--            protocol.  Note that this group is OPTIONAL.  Some units
--            are not configured to implement the LAT-compatible protocol,
--            and accordingly none of the objects in this group are present
--            in those units' MIB.

           vLtNodeName OBJECT-TYPE
             SYNTAX  DisplayString (SIZE (1..16))
             ACCESS  read-write
             STATUS  optional
             DESCRIPTION
                     "The LAT-compatible node name for this unit.  This name
                     is transmitted as part of the node's LAT-compatible
                     multicast messages."
             ::= { vcpLt 1 }

           vLtNodeID OBJECT-TYPE
             SYNTAX  DisplayString (SIZE (0..40))
             ACCESS  read-write
             STATUS  optional
             DESCRIPTION
                     "The LAT-compatible identification string for this
                     server.  This string is transmitted as part of the
                     agent's LAT-compatible multicast messages."
             ::= { vcpLt 2 }

           vLtNodeGroups OBJECT-TYPE
             SYNTAX  LtGroupList
             ACCESS  read-write
             STATUS  optional
             DESCRIPTION
                     "A bit string indicating the LAT-compatible groups which
                     are transmitted as part of the node's LAT-compatible
                     multicast messages."
             ::= { vcpLt 3 }

           vLtNumber OBJECT-TYPE
             SYNTAX  INTEGER (0..65535)
             ACCESS  read-write
             STATUS  optional
             DESCRIPTION
                     "An integer indicating the LAT-compatible number that is
                     tranmsitted as part of the node's LAT-compatible
                     multicast messages."
             ::= { vcpLt 4 }

           vLtMcastEnable OBJECT-TYPE
             SYNTAX  INTEGER {
                         enabled(1),
                         disabled(2)
                     }
             ACCESS  read-write
             STATUS  optional
             DESCRIPTION
                     "An integer indicating whether the unit's LAT-compatible
                     periodic multicast is enabled or not.  If enabled, the
                     unit will transmit one LAT-compatible multicast message
                     every vLtMcastTimer seconds if it has any local services
                     to announce."
             ::= { vcpLt 5 }

           vLtMcastTimer OBJECT-TYPE
             SYNTAX  INTEGER (10..180)
             ACCESS  read-write
             STATUS  optional
             DESCRIPTION
                     "An integer indicating the unit's multicast timer value
                     in seconds.  If multicasts are enabled, the unit will
                     transmit one LAT-compatible multicast message every
                     vLtMcastTimer seconds if it has any local services to
                     announce."
             ::= { vcpLt 6 }

           vLtCktTimer OBJECT-TYPE
             SYNTAX  INTEGER (1..200)
             ACCESS  read-write
             STATUS  optional
             DESCRIPTION
                     "An integer indicating the unit's circuit timer value in
                     milliseconds.  For circuits on which the unit is the
                     master, circuit data is collected for transmission once
                     every circuit timer interval."
             ::= { vcpLt 7 }

           vLtKeepaliveTimer OBJECT-TYPE
             SYNTAX  INTEGER (10..180)
             ACCESS  read-write
             STATUS  optional
             DESCRIPTION
                     "An integer indicating the unit's keepalive timer value
                     in seconds.  For circuits on which the unit is the
                     master, a keepalive message is transmitted once every
                     keepalive timer interval if the circuit is otherwise
                     idle."
             ::= { vcpLt 8 }

           vLtMaxRetran OBJECT-TYPE
             SYNTAX  INTEGER (4..120)
             ACCESS  read-write
             STATUS  optional
             DESCRIPTION
                     "An integer indicating the maximum number of times the
                     unit will attempt to retransmit LAT-compatible messages."
             ::= { vcpLt 9 }

           vLtSlotPerCkt OBJECT-TYPE
             SYNTAX  INTEGER (0..255)
             ACCESS  read-write
             STATUS  optional
             DESCRIPTION
                     "An integer indicating the maximum number of slots per
                     circuit that the unit can support.  This effectively
                     limits the number of sessions the unit can maintain with
                     any other node on a single circuit."
             ::= { vcpLt 10 }

           vLtMaxNodes OBJECT-TYPE
             SYNTAX  INTEGER (16..1024)
             ACCESS  read-write
             STATUS  optional
             DESCRIPTION
                     "An integer indicating the maximum number of
                     LAT-compatible nodes about which the unit will maintain
                     information necessary for session establishment.  When
                     the unit receives LAT-compatible multicasts, it enters
                     the pertinent information into its internal node table.
                     This object indicates the maximum number of entries in
                     the node table."
             ::= { vcpLt 11 }

           vLtMaxSvcs OBJECT-TYPE
             SYNTAX  INTEGER (16..2048)
             ACCESS  read-write
             STATUS  optional
             DESCRIPTION
                     "An integer indicating the maximum number of
                     LAT-compatible services about which the unit will
                     maintain information necessary for session establishment.
                     When the unit receives LAT-compatible multicasts, it
                     enters the pertinent information into its internal
                     service table.  This object indicates the size of the
                     service table."
             ::= { vcpLt 12 }

           vLtMaxCkts OBJECT-TYPE
             SYNTAX  INTEGER (4..128)
             ACCESS  read-write
             STATUS  optional
             DESCRIPTION
                     "An integer indicating the maximum number of simultaneous
                     active LAT-compatible circuits.  In effect this object
                     governs the maximum number of LAT-compatible nodes with
                     which the unit can maintain simultaneous connections."
             ::= { vcpLt 13 }

           vLtSessCurrNumber OBJECT-TYPE
             SYNTAX  INTEGER
             ACCESS  read-only
             STATUS  optional
             DESCRIPTION
                     "An integer indicating the current number of entries in
                     vLtSessTable.  This object is not constant."
             ::= { vcpLt 14 }

           vLtSessTable OBJECT-TYPE
             SYNTAX  SEQUENCE OF VLtSessEntry
             ACCESS  not-accessible
             STATUS  optional
             DESCRIPTION
                     "A list of LAT-compatible session entries.  The number of
                     entries is given by the value of vLtSessCurrNumber."
             ::= { vcpLt 15 }

           vLtSessEntry OBJECT-TYPE
             SYNTAX  VLtSessEntry
             ACCESS  not-accessible
             STATUS  optional
             DESCRIPTION
                     "Parameter and status values for a LAT-compatible session
                     entry."
             INDEX   { vLtSessIndex }
             ::= { vLtSessTable 1 }

          VLtSessEntry ::=
              SEQUENCE {
                  vLtSessPortIndex
                      INTEGER,
                  vLtSessIndex
                      INTEGER,
                  vLtSessOrigin
                      INTEGER,
                  vLtSessState
                      INTEGER,
                  vLtSessDisconnect
                      INTEGER,
                  vLtSessSvcName
                      DisplayString,
                  vLtSessNodeName
                      DisplayString,
                  vLtSessDestName
                      DisplayString
              }

           vLtSessPortIndex OBJECT-TYPE
             SYNTAX  INTEGER
             ACCESS  read-only
             STATUS  optional
             DESCRIPTION
                     "The value of vPortIndex for the port to which this
                     session belongs."
             ::= { vLtSessEntry 1 }

           vLtSessIndex OBJECT-TYPE
             SYNTAX  INTEGER
             ACCESS  read-only
             STATUS  optional
             DESCRIPTION
                     "The session index in the context of the port, a 
                     non-zero positive integer.  Session indexes within a 
                     port need not be sequential.  Session indexes may be 
                     reused for different ports.  For example, port 1 and 
                     port 3 may both have a session 2 at the same time."
             ::= { vLtSessEntry 2 }

           vLtSessOrigin OBJECT-TYPE
             SYNTAX  INTEGER {
                         unknown(1),
                         network(2),
                         local(3),
                         remote-port(4)
                     }
             ACCESS  read-only
             STATUS  optional
             DESCRIPTION
                     "The session's source of establishment.  'network(2)'
                     indicates that a remote node has started this session.
                     'local(3)' indicates that the session was started by the
                     agent port given by vLtSessPortIndex.  'remote-port(4)'
                     indicates that the session is local between two server
                     ports, and the port given by vLtSessPortIndex was not
                     the initiator of the session."
             ::= { vLtSessEntry 3 }

           vLtSessState OBJECT-TYPE
             SYNTAX  INTEGER {
                         starting(1),
                         running(2),
                         stopping(3)
                     }
             ACCESS  read-only
             STATUS  optional
             DESCRIPTION
                     "The current state of the session."
             ::= { vLtSessEntry 4 }

           vLtSessDisconnect OBJECT-TYPE
             SYNTAX  INTEGER {
                         ready(1),
                         execute(2)
                     }
             ACCESS  read-write
             STATUS  optional
             DESCRIPTION
                     "A control to terminate the session.  In response to 
                     a get-request or get-next-request, the agent always 
                     returns 'ready(1)' as the value.  Setting the value to 
                     'execute(2)' causes termination."
             ::= { vLtSessEntry 5 }

           vLtSessSvcName OBJECT-TYPE
             SYNTAX  DisplayString
             ACCESS  read-only
             STATUS  optional
             DESCRIPTION
                     "A (readable) text string indicating the name of the
                     LAT-compatible remote service.  A zero-length value
                     indicates that the remote service for this session is
                     unknown."
             ::= { vLtSessEntry 6 }

           vLtSessNodeName OBJECT-TYPE
             SYNTAX  DisplayString
             ACCESS  read-only
             STATUS  optional
             DESCRIPTION
                     "A (readable) text string indicating the name of the
                     LAT-compatible remote node.  A zero-length value
                     indicates that the remote node for this session is
                     unknown."
             ::= { vLtSessEntry 7 }

           vLtSessDestName OBJECT-TYPE
             SYNTAX  DisplayString
             ACCESS  read-only
             STATUS  optional
             DESCRIPTION
                     "A (readable) text string indicating the name of the
                     LAT-compatible remote destination port.  A zero-length
                     value indicates that the remote port name for this
                     session is unknown."
             ::= { vLtSessEntry 8 }

           vLtTotalRcvPkts OBJECT-TYPE
             SYNTAX  Counter
             ACCESS  read-only
             STATUS  optional
             DESCRIPTION
                     "A count of the total number of LAT-compatible messages
                     received and processed by the unit."
             ::= { vcpLt 16 }

           vLtTotalTrnPkts OBJECT-TYPE
             SYNTAX  Counter
             ACCESS  read-only
             STATUS  optional
             DESCRIPTION
                     "A count of the total number of LAT-compatible messages
                     transmitted by the unit."
             ::= { vcpLt 17 }

           vLtTotalRetranPkts OBJECT-TYPE
             SYNTAX  Counter
             ACCESS  read-only
             STATUS  optional
             DESCRIPTION
                     "A count of the total number of LAT-compatible messages
                     retransmited."
             ::= { vcpLt 18 }

           vLtRcvCorruptPkts OBJECT-TYPE
             SYNTAX  Counter
             ACCESS  read-only
             STATUS  optional
             DESCRIPTION
                     "A count of the total number of LAT-compatible station
                     packets recieved which were found to be invalid or
                     corrupted."
             ::= { vcpLt 19 }

           vLtRcvCorruptMcasts OBJECT-TYPE
             SYNTAX  Counter
             ACCESS  read-only
             STATUS  optional
             DESCRIPTION
                     "A count of the total number of LAT-compatible multicast
                     packets recieved which were found to be invalid or
                     corrupted."
             ::= { vcpLt 20 }

           vLtRcvDuplicatePkts OBJECT-TYPE
             SYNTAX  Counter
             ACCESS  read-only
             STATUS  optional
             DESCRIPTION
                     "A count of the total number of LAT-compatible messages
                     received which had already been acknowledged by the
                     unit."
             ::= { vcpLt 21 }

           vLtReqAccepted OBJECT-TYPE
             SYNTAX  Counter
             ACCESS  read-only
             STATUS  optional
             DESCRIPTION
                     "A count of the total number of remote connection
                     requests which were received and accepted by the unit."
             ::= { vcpLt 22 }

           vLtReqRejected OBJECT-TYPE
             SYNTAX  Counter
             ACCESS  read-only
             STATUS  optional
             DESCRIPTION
                     "A count of the total number of remote connection
                     requests which were received and rejected by the unit."
             ::= { vcpLt 23 }

           vLtTotalNodeDiscards OBJECT-TYPE
             SYNTAX  Counter
             ACCESS  read-only
             STATUS  optional
             DESCRIPTION
                     "A count of the total number of LAT-compatible nodes that
                     the unit has not been able to insert into its internal
                     node table, due to resource failures."
             ::= { vcpLt 24 }


           -- the vcpQueue group

--            This group defines objects relevant to the server internal
--            session queue.  When connection attempts to/from the server
--            fail because of busy resources, under some conditions these
--            sessions may be queued until the resource is freed.

           vQueMaxEntries OBJECT-TYPE
             SYNTAX  INTEGER (4..128)
             ACCESS  read-write
             STATUS  mandatory
             DESCRIPTION
                     "An integer indicating the maximum number of queued
                     connection requests.  This governs the maximum value that
                     vQueCurrNumber can take."
             ::= { vcpQueue 1 }

           vQueCurrNumber OBJECT-TYPE
             SYNTAX  INTEGER
             ACCESS  read-only
             STATUS  mandatory
             DESCRIPTION
                     "An integer indicating the current number of entries in
                     vQueTable.  This object is not constant."
             ::= { vcpQueue 2 }

           vQueTable OBJECT-TYPE
             SYNTAX  SEQUENCE OF VQueEntry
             ACCESS  not-accessible
             STATUS  mandatory
             DESCRIPTION
                     "A list of queue entries.  The number of entries is given
                     by the value of vQueCurrNumber."
             ::= { vcpQueue 3 }

           vQueEntry OBJECT-TYPE
             SYNTAX  VQueEntry
             ACCESS  not-accessible
             STATUS  mandatory
             DESCRIPTION
                     "Parameter and status values for a queue entry."
             INDEX   { vQueEntryNumber }
             ::= { vQueTable 1 }

          VQueEntry ::=
              SEQUENCE {
                  vQueEntryNumber
                      INTEGER,
                  vQueSvcName
                      DisplayString,
                  vQueNodeName
                      DisplayString,
                  vQuePortName
                      DisplayString,
                  vQueStatus
                      INTEGER
              }

           vQueEntryNumber OBJECT-TYPE
             SYNTAX  INTEGER (0..65535)
             ACCESS  read-only
             STATUS  mandatory
             DESCRIPTION
                     "A unique identifier for the queue entry.  Entry numbers
                     may be re-used, but there will never be two simultaneous
                     queue entries with the same value of vQueEntryNumber."
             ::= { vQueEntry 1 }

           vQueSvcName OBJECT-TYPE
             SYNTAX  OCTET STRING
             ACCESS  read-only
             STATUS  mandatory
             DESCRIPTION
                     "The name of the service for which this queue entry is
                     awating connection."
             ::= { vQueEntry 2 }

           vQueNodeName OBJECT-TYPE
             SYNTAX  OCTET STRING
             ACCESS  read-only
             STATUS  mandatory
             DESCRIPTION
                     "The name of the remote node with which the connection
                     will take place."
             ::= { vQueEntry 3 }

           vQuePortName OBJECT-TYPE
             SYNTAX  OCTET STRING
             ACCESS  read-only
             STATUS  mandatory
             DESCRIPTION
                     "The name of the port with which the connection will take
                     place."
             ::= { vQueEntry 4 }

           vQueStatus OBJECT-TYPE
             SYNTAX  INTEGER {
                         valid(1),
                         invalid(2)
                     }
             ACCESS  read-write
             STATUS  mandatory
             DESCRIPTION
                     "The current status of the queue entry.  Setting the
                     value of this object to 'invalid(2)' has the effect of
                     deleting the queue entry."
             ::= { vQueEntry 5 }


           -- the vcpSnmp group

--            This group defines SNMP objects which are not accessible through
--            MIB II.

           vSnmpReadCommunity OBJECT-TYPE
             SYNTAX  OCTET STRING (SIZE (1..10))
             ACCESS  read-write
             STATUS  mandatory
             DESCRIPTION
                     "A current community name in use by the agent for which
                     get-requests and getnext-requests are permitted."
             ::= { vcpSnmp 1 }

           vSnmpWriteCommunity OBJECT-TYPE
             SYNTAX  OCTET STRING (SIZE (1..10))
             ACCESS  read-write
             STATUS  mandatory
             DESCRIPTION
                     "A current community name in use by the agent for which
                     the set-request is permitted."
             ::= { vcpSnmp 2 }

           vSnmpReadWriteCommunity OBJECT-TYPE
             SYNTAX  OCTET STRING (SIZE (1..10))
             ACCESS  read-write
             STATUS  mandatory
             DESCRIPTION
                     "A current community name in use by the agent for which
                     set-requests, get-requests, and getnext-requests are
                     permitted."
             ::= { vcpSnmp 3 }

           vSnmpWriteEnable OBJECT-TYPE
             SYNTAX  INTEGER {
                         enabled(1),
                         disabled(2)
                     }
             ACCESS  read-write
             STATUS  mandatory
             DESCRIPTION
                     "An integer which indicates whether SET requests are
                     permitted from any management station.  This flag
                     overrides use of the WRITE or READWRITE community names.
                     Thus, if this object has the value disabled(2), no SET
                     requests are permitted regardless of community name."
             ::= { vcpSnmp 4 }

           vSnmpTrapDestCurrNumber OBJECT-TYPE
             SYNTAX  INTEGER
             ACCESS  read-only
             STATUS  mandatory
             DESCRIPTION
                     "An integer indicating the current number of entries in
                     vSnmpTrapDestTable.  This object is not constant."
             ::= { vcpSnmp 5 }

           vSnmpTrapDestTable OBJECT-TYPE
             SYNTAX  SEQUENCE OF VSnmpTrapDestEntry
             ACCESS  not-accessible
             STATUS  mandatory
             DESCRIPTION
                     "A list of destination management stations to which this
                     agent will address certain generated trap messages.  The
                     number of entries is given by the value of
                     vSnmpTrapDestCurrNumber."
             ::= { vcpSnmp 6 }

           vSnmpTrapDestEntry OBJECT-TYPE
             SYNTAX  VSnmpTrapDestEntry
             ACCESS  not-accessible
             STATUS  mandatory
             DESCRIPTION
                     "Parameter and status values for a SNMP trap destination
                     entry."
             INDEX   { vSnmpTrapDestAddr }
             ::= { vSnmpTrapDestTable 1 }

          VSnmpTrapDestEntry ::=
              SEQUENCE {
                  vSnmpTrapDestAddr
                      IpAddress,
                  vSnmpTrapDestCommunity
                      INTEGER,
                  vSnmpTrapDestColdEnable
                      INTEGER,
                  vSnmpTrapDestAuthEnable
                      INTEGER,
                  vSnmpTrapDestStatus
                      INTEGER
              }

           vSnmpTrapDestAddr OBJECT-TYPE
             SYNTAX  IpAddress
             ACCESS  read-write
             STATUS  mandatory
             DESCRIPTION
                     "The IP address of this trap destination node."
             ::= { vSnmpTrapDestEntry 1 }

           vSnmpTrapDestCommunity OBJECT-TYPE
             SYNTAX  INTEGER {
                         read(1),
                         write(2),
                         readwrite(3)
                     }
             ACCESS  read-write
             STATUS  mandatory
             DESCRIPTION
                     "Indication of which of the three locally maintained
                     community names will be used in trap messages addressed
                     to this trap destination."
             ::= { vSnmpTrapDestEntry 2 }

           vSnmpTrapDestColdEnable OBJECT-TYPE
             SYNTAX  INTEGER {
                         enabled(1),
                         disabled(2)
                     }
             ACCESS  read-write
             STATUS  mandatory
             DESCRIPTION
                     "An indication of whether trap messages of the
                     'cold-start' type will be sent to this trap destination."
             ::= { vSnmpTrapDestEntry 3 }

           vSnmpTrapDestAuthEnable OBJECT-TYPE
             SYNTAX  INTEGER {
                         enabled(1),
                         disabled(2)
                     }
             ACCESS  read-write
             STATUS  mandatory
             DESCRIPTION
                     "An indication of whether trap messages of the
                     'authentication-failure' type will be sent to this trap
                     destination."
             ::= { vSnmpTrapDestEntry 4 }

           vSnmpTrapDestStatus OBJECT-TYPE
             SYNTAX  INTEGER {
                         valid(1),
                         invalid(2)
                     }
             ACCESS  read-write
             STATUS  mandatory
             DESCRIPTION
                     "The current status of the trap destination entry.
                     Setting this object to the value 'invalid(2)' has the
                     effect of deleting the entry."
             ::= { vSnmpTrapDestEntry 5 }

    END
