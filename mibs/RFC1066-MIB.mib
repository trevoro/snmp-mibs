-- WinAgents MIB Extraction Wizard
-- Extracted from rfc1066.txt 16.03.2005 20:16:09

RFC1066-MIB --{ iso org(3) dod(6) internet(1) mgmt(2) 1 }

DEFINITIONS ::= BEGIN

IMPORTS
        OBJECT-TYPE FROM RFC-1212
		  mgmt, NetworkAddress, IpAddress,
        Counter, Gauge, TimeTicks
            FROM RFC1065-SMI;

  mib        OBJECT IDENTIFIER ::= { mgmt 1 }

  system     OBJECT IDENTIFIER ::= { mib 1 }
  interfaces OBJECT IDENTIFIER ::= { mib 2 }
  at         OBJECT IDENTIFIER ::= { mib 3 }
  ip         OBJECT IDENTIFIER ::= { mib 4 }
  icmp       OBJECT IDENTIFIER ::= { mib 5 }
  tcp        OBJECT IDENTIFIER ::= { mib 6 }
  udp        OBJECT IDENTIFIER ::= { mib 7 }
  egp        OBJECT IDENTIFIER ::= { mib 8 }

  -- object types

  -- the System group

  sysDescr OBJECT-TYPE
          SYNTAX  OCTET STRING
          ACCESS  read-only
          STATUS  mandatory
          ::= { system 1 }

  sysObjectID OBJECT-TYPE
          SYNTAX  OBJECT IDENTIFIER
          ACCESS  read-only
          STATUS  mandatory
          ::= { system 2 }

  sysUpTime OBJECT-TYPE
          SYNTAX  TimeTicks
          ACCESS  read-only
          STATUS  mandatory
          ::= { system 3 }

  -- the Interfaces group

  ifNumber OBJECT-TYPE
          SYNTAX  INTEGER

          ACCESS  read-only
          STATUS  mandatory
          ::= { interfaces 1 }

  -- the Interfaces table

  ifTable OBJECT-TYPE
          SYNTAX  SEQUENCE OF IfEntry
          ACCESS  read-write
          STATUS  mandatory
          ::= { interfaces 2 }

  ifEntry OBJECT-TYPE
          SYNTAX  IfEntry
          ACCESS  read-write
          STATUS  mandatory
          ::= { ifTable 1 }

  IfEntry ::= SEQUENCE {
      ifIndex
          INTEGER,
      ifDescr
          OCTET STRING,
      ifType
          INTEGER,
      ifMtu
          INTEGER,
      ifSpeed
          Gauge,
      ifPhysAddress
          OCTET STRING,
      ifAdminStatus
          INTEGER,
      ifOperStatus
          INTEGER,
      ifLastChange
          TimeTicks,
      ifInOctets
          Counter,
      ifInUcastPkts
          Counter,
      ifInNUcastPkts
          Counter,
      ifInDiscards
          Counter,
      ifInErrors
          Counter,
      ifInUnknownProtos

          Counter,
      ifOutOctets
          Counter,
      ifOutUcastPkts
          Counter,
      ifOutNUcastPkts
          Counter,
      ifOutDiscards
          Counter,
      ifOutErrors
          Counter,
      ifOutQLen
          Gauge
  }

  ifIndex OBJECT-TYPE
          SYNTAX  INTEGER
          ACCESS  read-only
          STATUS  mandatory
          ::= { ifEntry 1 }

  ifDescr OBJECT-TYPE
          SYNTAX  OCTET STRING
          ACCESS  read-only
          STATUS  mandatory
          ::= { ifEntry 2 }

  ifType OBJECT-TYPE
          SYNTAX  INTEGER {
                  other(1),     -- none of the following
                  regular1822(2),
                  hdh1822(3),
                  ddn-x25(4),
                  rfc877-x25(5),
                  ethernet-csmacd(6),
                  iso88023-csmacd(7),
                  iso88024-tokenBus(8),
                  iso88025-tokenRing(9),
                  iso88026-man(10),
                  starLan(11),
                  proteon-10MBit(12),
                  proteon-80MBit(13),
                  hyperchannel(14),
                  fddi(15),
                  lapb(16),
                  sdlc(17),
                  t1-carrier(18),
                  cept(19),

                  basicIsdn(20),
                  primaryIsdn(21),
                                   -- proprietary serial
                  propPointToPointSerial(22)
              }
          ACCESS  read-only
          STATUS  mandatory
          ::= { ifEntry 3 }

  ifMtu OBJECT-TYPE
          SYNTAX  INTEGER
          ACCESS  read-only
          STATUS  mandatory
          ::= { ifEntry 4 }

  ifSpeed OBJECT-TYPE
          SYNTAX  Gauge
          ACCESS  read-only
          STATUS  mandatory
          ::= { ifEntry 5 }

  ifPhysAddress OBJECT-TYPE
          SYNTAX  OCTET STRING
          ACCESS  read-only
          STATUS  mandatory
          ::= { ifEntry 6 }

  ifAdminStatus OBJECT-TYPE
          SYNTAX  INTEGER {
                  up(1),        -- ready to pass packets
                  down(2),
                  testing(3)    -- in some test mode
                  }
          ACCESS  read-write
          STATUS  mandatory
          ::= { ifEntry 7 }

  ifOperStatus OBJECT-TYPE
          SYNTAX  INTEGER {
                  up(1),        -- ready to pass packets
                  down(2),
                  testing(3)    -- in some test mode
                  }
          ACCESS  read-only
          STATUS  mandatory
          ::= { ifEntry 8 }

  ifLastChange OBJECT-TYPE

          SYNTAX  TimeTicks
          ACCESS  read-only
          STATUS  mandatory
          ::= { ifEntry 9 }

  ifInOctets OBJECT-TYPE
          SYNTAX  Counter
          ACCESS  read-only
          STATUS  mandatory
          ::= { ifEntry 10 }

  ifInUcastPkts OBJECT-TYPE
          SYNTAX  Counter
          ACCESS  read-only
          STATUS  mandatory
          ::=  { ifEntry 11 }

  ifInNUcastPkts OBJECT-TYPE
          SYNTAX  Counter
          ACCESS  read-only
          STATUS  mandatory
          ::= { ifEntry 12 }

  ifInDiscards OBJECT-TYPE
          SYNTAX  Counter
          ACCESS  read-only
          STATUS  mandatory
          ::= { ifEntry 13 }

  ifInErrors OBJECT-TYPE
          SYNTAX  Counter
          ACCESS  read-only
          STATUS  mandatory
          ::= { ifEntry 14 }

  ifInUnknownProtos OBJECT-TYPE
          SYNTAX  Counter
          ACCESS  read-only
          STATUS  mandatory
          ::= { ifEntry 15 }

  ifOutOctets OBJECT-TYPE
          SYNTAX  Counter
          ACCESS  read-only
          STATUS  mandatory
          ::= { ifEntry 16 }

  ifOutUcastPkts OBJECT-TYPE

          SYNTAX  Counter
          ACCESS  read-only
          STATUS  mandatory
          ::= { ifEntry 17 }

  ifOutNUcastPkts OBJECT-TYPE
          SYNTAX  Counter
          ACCESS  read-only
          STATUS  mandatory
          ::= { ifEntry 18 }

  ifOutDiscards OBJECT-TYPE
          SYNTAX  Counter
          ACCESS  read-only
          STATUS  mandatory
          ::= { ifEntry 19 }

  ifOutErrors OBJECT-TYPE
          SYNTAX  Counter
          ACCESS  read-only
          STATUS  mandatory
          ::= { ifEntry 20 }

  ifOutQLen OBJECT-TYPE
          SYNTAX  Gauge
          ACCESS  read-only
          STATUS  mandatory
          ::= { ifEntry 21 }

  -- the Address Translation group

  atTable OBJECT-TYPE
          SYNTAX  SEQUENCE OF AtEntry
          ACCESS  read-write
          STATUS  mandatory
          ::= { at 1 }

  atEntry OBJECT-TYPE
          SYNTAX  AtEntry
          ACCESS  read-write
          STATUS  mandatory
          ::= { atTable 1 }

  AtEntry ::= SEQUENCE {
      atIfIndex
          INTEGER,
      atPhysAddress
          OCTET STRING,

      atNetAddress
          NetworkAddress
  }

  atIfIndex OBJECT-TYPE
          SYNTAX  INTEGER
          ACCESS  read-write
          STATUS  mandatory
          ::= { atEntry 1 }

  atPhysAddress OBJECT-TYPE
          SYNTAX  OCTET STRING
          ACCESS  read-write
          STATUS  mandatory
          ::= { atEntry 2 }

  atNetAddress OBJECT-TYPE
          SYNTAX  NetworkAddress
          ACCESS  read-write
          STATUS  mandatory
          ::= { atEntry 3 }

  -- the IP group

  ipForwarding OBJECT-TYPE
          SYNTAX  INTEGER {
        gateway(1), -- entity forwards datagrams
        host(2)     -- entity does NOT forward datagrams
                  }
          ACCESS  read-only
          STATUS  mandatory
          ::= { ip 1 }

  ipDefaultTTL OBJECT-TYPE
          SYNTAX  INTEGER
          ACCESS  read-write
          STATUS  mandatory
          ::= { ip 2 }

  ipInReceives OBJECT-TYPE
          SYNTAX  Counter
          ACCESS  read-only
          STATUS  mandatory
          ::= { ip 3 }

  ipInHdrErrors OBJECT-TYPE
          SYNTAX  Counter
          ACCESS  read-only

          STATUS  mandatory
          ::= { ip 4 }

  ipInAddrErrors OBJECT-TYPE
          SYNTAX  Counter
          ACCESS  read-only
          STATUS  mandatory
          ::= { ip 5 }

  ipForwDatagrams OBJECT-TYPE
          SYNTAX  Counter
          ACCESS  read-only
          STATUS  mandatory
          ::= { ip 6 }

  ipInUnknownProtos OBJECT-TYPE
          SYNTAX  Counter
          ACCESS  read-only
          STATUS  mandatory
          ::= { ip 7 }

  ipInDiscards OBJECT-TYPE
          SYNTAX  Counter
          ACCESS  read-only
          STATUS  mandatory
          ::= { ip 8 }

  ipInDelivers OBJECT-TYPE
          SYNTAX  Counter
          ACCESS  read-only
          STATUS  mandatory
          ::= { ip 9 }

  ipOutRequests OBJECT-TYPE
          SYNTAX  Counter
          ACCESS  read-only
          STATUS  mandatory
          ::= { ip 10 }

  ipOutDiscards OBJECT-TYPE
          SYNTAX  Counter
          ACCESS  read-only
          STATUS  mandatory
          ::= { ip 11 }

  ipOutNoRoutes OBJECT-TYPE
          SYNTAX  Counter
          ACCESS  read-only

          STATUS  mandatory
          ::= { ip 12 }

  ipReasmTimeout OBJECT-TYPE
          SYNTAX  INTEGER
          ACCESS  read-only
          STATUS  mandatory
          ::= { ip 13 }

  ipReasmReqds OBJECT-TYPE
          SYNTAX  Counter
          ACCESS  read-only
          STATUS  mandatory
          ::= { ip 14 }

  ipReasmOKs OBJECT-TYPE
          SYNTAX  Counter
          ACCESS  read-only
          STATUS  mandatory
          ::= { ip 15 }

  ipReasmFails OBJECT-TYPE
          SYNTAX  Counter
          ACCESS  read-only
          STATUS  mandatory
          ::= { ip 16 }

  ipFragOKs OBJECT-TYPE
          SYNTAX  Counter
          ACCESS  read-only
          STATUS  mandatory
          ::= { ip 17 }

  ipFragFails OBJECT-TYPE
          SYNTAX  Counter
          ACCESS  read-only
          STATUS  mandatory
          ::= { ip 18 }

  ipFragCreates OBJECT-TYPE
          SYNTAX  Counter
          ACCESS  read-only
          STATUS  mandatory
          ::= { ip 19 }

  -- the IP Interface table

  ipAddrTable OBJECT-TYPE

          SYNTAX  SEQUENCE OF IpAddrEntry
          ACCESS  read-only
          STATUS  mandatory
          ::= { ip 20 }

  ipAddrEntry OBJECT-TYPE
          SYNTAX  IpAddrEntry
          ACCESS  read-only
          STATUS  mandatory
          ::= { ipAddrTable 1 }

  IpAddrEntry ::= SEQUENCE {
      ipAdEntAddr
          IpAddress,
      ipAdEntIfIndex
          INTEGER,
      ipAdEntNetMask
          IpAddress,
      ipAdEntBcastAddr
          INTEGER
  }

  ipAdEntAddr OBJECT-TYPE
          SYNTAX  IpAddress
          ACCESS  read-only
          STATUS  mandatory
          ::=  { ipAddrEntry 1 }

  ipAdEntIfIndex OBJECT-TYPE
          SYNTAX  INTEGER
          ACCESS  read-only
          STATUS  mandatory
          ::=  { ipAddrEntry 2 }

  ipAdEntNetMask OBJECT-TYPE
          SYNTAX  IpAddress
          ACCESS  read-only
          STATUS  mandatory
          ::=  { ipAddrEntry 3 }

  ipAdEntBcastAddr OBJECT-TYPE
          SYNTAX  INTEGER
          ACCESS  read-only
          STATUS  mandatory
          ::= { ipAddrEntry 4 }

  -- the IP Routing table


  ipRoutingTable OBJECT-TYPE
          SYNTAX  SEQUENCE OF IpRouteEntry
          ACCESS  read-write
          STATUS  mandatory
          ::= { ip 21 }

  ipRouteEntry OBJECT-TYPE
          SYNTAX  IpRouteEntry
          ACCESS  read-write
          STATUS  mandatory
          ::= { ipRoutingTable 1 }

  IpRouteEntry ::= SEQUENCE {
      ipRouteDest
          IpAddress,
      ipRouteIfIndex
          INTEGER,
      ipRouteMetric1
          INTEGER,
      ipRouteMetric2
          INTEGER,
      ipRouteMetric3
          INTEGER,
      ipRouteMetric4
          INTEGER,
      ipRouteNextHop
          IpAddress,
      ipRouteType
          INTEGER,
      ipRouteProto
          INTEGER,
      ipRouteAge
          INTEGER
  }

  ipRouteDest OBJECT-TYPE
          SYNTAX  IpAddress
          ACCESS  read-write
          STATUS  mandatory
          ::= { ipRouteEntry 1 }

  ipRouteIfIndex  OBJECT-TYPE
          SYNTAX  INTEGER
          ACCESS  read-write
          STATUS  mandatory
          ::= { ipRouteEntry 2 }

  ipRouteMetric1 OBJECT-TYPE

          SYNTAX  INTEGER
          ACCESS  read-write
          STATUS  mandatory
          ::= { ipRouteEntry 3 }

  ipRouteMetric2 OBJECT-TYPE
          SYNTAX  INTEGER
          ACCESS  read-write
          STATUS  mandatory
          ::= { ipRouteEntry 4 }

  ipRouteMetric3 OBJECT-TYPE
          SYNTAX  INTEGER
          ACCESS  read-write
          STATUS  mandatory
          ::= { ipRouteEntry 5 }

  ipRouteMetric4 OBJECT-TYPE
          SYNTAX  INTEGER
          ACCESS  read-write
          STATUS  mandatory
          ::= { ipRouteEntry 6 }

  ipRouteNextHop OBJECT-TYPE
          SYNTAX  IpAddress
          ACCESS  read-write
          STATUS  mandatory
          ::= { ipRouteEntry 7 }

  ipRouteType OBJECT-TYPE
          SYNTAX  INTEGER {
            other(1),      -- none of the following

            invalid(2),    -- an invalidated route

                           -- route to directly
            direct(3),     -- connected (sub-)network

                           -- route to a non-local
            remote(4)     -- host/network/sub-network
              }
          ACCESS  read-write
          STATUS  mandatory
          ::= { ipRouteEntry 8 }

  ipRouteProto OBJECT-TYPE
          SYNTAX  INTEGER {
            other(1),     -- none of the following

                          -- non-protocol information
                          --   e.g., manually
            local(2),     --   configured entries

                          -- set via a network
            netmgmt(3),   --   management protocol

                          -- obtained via ICMP,
            icmp(4),      --   e.g., Redirect

                          -- the following are
                          -- gateway routing protocols
            egp(5),
            ggp(6),
            hello(7),
            rip(8),
            is-is(9),
            es-is(10),
            ciscoIgrp(11),
            bbnSpfIgp(12),
            oigp(13)
              }
          ACCESS  read-only
          STATUS  mandatory
          ::= { ipRouteEntry 9 }

  ipRouteAge OBJECT-TYPE
          SYNTAX  INTEGER
          ACCESS  read-write
          STATUS  mandatory
          ::= { ipRouteEntry 10 }

  -- the ICMP group

  icmpInMsgs OBJECT-TYPE
          SYNTAX  Counter
          ACCESS  read-only
          STATUS  mandatory
          ::= { icmp 1 }

  icmpInErrors OBJECT-TYPE
          SYNTAX  Counter
          ACCESS  read-only
          STATUS  mandatory
          ::= { icmp 2 }

  icmpInDestUnreachs OBJECT-TYPE
          SYNTAX  Counter

          ACCESS  read-only
          STATUS  mandatory
          ::= { icmp 3 }

  icmpInTimeExcds OBJECT-TYPE
          SYNTAX  Counter
          ACCESS  read-only
          STATUS  mandatory
          ::= { icmp 4 }

  icmpInParmProbs OBJECT-TYPE
          SYNTAX  Counter
          ACCESS  read-only
          STATUS  mandatory
          ::= { icmp 5 }

  icmpInSrcQuenchs OBJECT-TYPE
          SYNTAX  Counter
          ACCESS  read-only
          STATUS  mandatory
          ::= { icmp 6 }

  icmpInRedirects OBJECT-TYPE
          SYNTAX  Counter
          ACCESS  read-only
          STATUS  mandatory
          ::= { icmp 7 }

  icmpInEchos OBJECT-TYPE
          SYNTAX  Counter
          ACCESS  read-only
          STATUS  mandatory
          ::= { icmp 8 }

  icmpInEchoReps OBJECT-TYPE
          SYNTAX  Counter
          ACCESS  read-only
          STATUS  mandatory
          ::= { icmp 9 }

  icmpInTimestamps OBJECT-TYPE
          SYNTAX  Counter
          ACCESS  read-only
          STATUS  mandatory
          ::= { icmp 10 }

  icmpInTimestampReps OBJECT-TYPE
          SYNTAX  Counter

          ACCESS  read-only
          STATUS  mandatory
          ::= { icmp 11 }

  icmpInAddrMasks OBJECT-TYPE
          SYNTAX  Counter
          ACCESS  read-only
          STATUS  mandatory
          ::= { icmp 12 }

  icmpInAddrMaskReps OBJECT-TYPE
          SYNTAX  Counter
          ACCESS  read-only
          STATUS  mandatory
          ::= { icmp 13 }

  icmpOutMsgs OBJECT-TYPE
          SYNTAX  Counter
          ACCESS  read-only
          STATUS  mandatory
          ::= { icmp 14 }

  icmpOutErrors OBJECT-TYPE
          SYNTAX  Counter
          ACCESS  read-only
          STATUS  mandatory
          ::= { icmp 15 }

  icmpOutDestUnreachs OBJECT-TYPE
          SYNTAX  Counter
          ACCESS  read-only
          STATUS  mandatory
          ::= { icmp 16 }

  icmpOutTimeExcds OBJECT-TYPE
          SYNTAX  Counter
          ACCESS  read-only
          STATUS  mandatory
          ::= { icmp 17 }

  icmpOutParmProbs OBJECT-TYPE
          SYNTAX  Counter
          ACCESS  read-only
          STATUS  mandatory
          ::= { icmp 18 }

  icmpOutSrcQuenchs OBJECT-TYPE
          SYNTAX  Counter

          ACCESS  read-only
          STATUS  mandatory
          ::= { icmp 19 }

  icmpOutRedirects OBJECT-TYPE
          SYNTAX  Counter
          ACCESS  read-only
          STATUS  mandatory
          ::= { icmp 20 }

  icmpOutEchos OBJECT-TYPE
          SYNTAX  Counter
          ACCESS  read-only
          STATUS  mandatory
          ::= { icmp 21 }

  icmpOutEchoReps OBJECT-TYPE
          SYNTAX  Counter
          ACCESS  read-only
          STATUS  mandatory
          ::= { icmp 22 }

  icmpOutTimestamps OBJECT-TYPE
          SYNTAX  Counter
          ACCESS  read-only
          STATUS  mandatory
          ::= { icmp 23 }

  icmpOutTimestampReps OBJECT-TYPE
          SYNTAX  Counter
          ACCESS  read-only
          STATUS  mandatory
          ::= { icmp 24 }

  icmpOutAddrMasks OBJECT-TYPE
          SYNTAX  Counter
          ACCESS  read-only
          STATUS  mandatory
          ::= { icmp 25 }

  icmpOutAddrMaskReps OBJECT-TYPE
          SYNTAX  Counter
          ACCESS  read-only
          STATUS  mandatory
          ::= { icmp 26 }

  -- the TCP group


  tcpRtoAlgorithm OBJECT-TYPE
          SYNTAX  INTEGER {
          other(1),    -- none of the following
          constant(2), -- a constant rto
          rsre(3),     -- MIL-STD-1778, Appendix B
          vanj(4)      -- Van Jacobson's algorithm [11]
                  }
          ACCESS  read-only
          STATUS  mandatory
          ::= { tcp 1 }

  tcpRtoMin OBJECT-TYPE
          SYNTAX  INTEGER
          ACCESS  read-only
          STATUS  mandatory
          ::= { tcp 2 }

  tcpRtoMax OBJECT-TYPE
          SYNTAX  INTEGER
          ACCESS  read-only
          STATUS  mandatory
          ::= { tcp 3 }

  tcpMaxConn OBJECT-TYPE
          SYNTAX  INTEGER
          ACCESS  read-only
          STATUS  mandatory
          ::= { tcp 4 }

  tcpActiveOpens OBJECT-TYPE
          SYNTAX  Counter
          ACCESS  read-only
          STATUS  mandatory
          ::= { tcp 5 }

  tcpPassiveOpens OBJECT-TYPE
          SYNTAX  Counter
          ACCESS  read-only
          STATUS  mandatory
          ::= { tcp 6 }

  tcpAttemptFails OBJECT-TYPE
          SYNTAX  Counter
          ACCESS  read-only
          STATUS  mandatory
          ::= { tcp 7 }

  tcpEstabResets OBJECT-TYPE

          SYNTAX  Counter
          ACCESS  read-only
          STATUS  mandatory
          ::= { tcp 8 }

  tcpCurrEstab OBJECT-TYPE
          SYNTAX  Gauge
          ACCESS  read-only
          STATUS  mandatory
          ::= { tcp 9 }

  tcpInSegs OBJECT-TYPE
          SYNTAX  Counter
          ACCESS  read-only
          STATUS  mandatory
          ::= { tcp 10 }

  tcpOutSegs OBJECT-TYPE
          SYNTAX  Counter
          ACCESS  read-only
          STATUS  mandatory
          ::= { tcp 11 }

  tcpRetransSegs OBJECT-TYPE
          SYNTAX  Counter
          ACCESS  read-only
          STATUS  mandatory
          ::= { tcp 12 }

  -- the TCP connections table

  tcpConnTable OBJECT-TYPE
          SYNTAX  SEQUENCE OF TcpConnEntry
          ACCESS  read-only
          STATUS  mandatory
          ::= { tcp 13 }

  tcpConnEntry OBJECT-TYPE
          SYNTAX  TcpConnEntry
          ACCESS  read-only
          STATUS  mandatory
          ::= { tcpConnTable 1 }

  TcpConnEntry ::= SEQUENCE {
      tcpConnState
          INTEGER,
      tcpConnLocalAddress
          IpAddress,

      tcpConnLocalPort
          INTEGER (0..65535),
      tcpConnRemAddress
          IpAddress,
      tcpConnRemPort
          INTEGER (0..65535)
  }

  tcpConnState OBJECT-TYPE
          SYNTAX  INTEGER {
                      closed(1),
                      listen(2),
                      synSent(3),
                      synReceived(4),
                      established(5),
                      finWait1(6),
                      finWait2(7),
                      closeWait(8),
                      lastAck(9),
                      closing(10),
                      timeWait(11)
                  }
          ACCESS  read-only
          STATUS  mandatory
          ::= { tcpConnEntry 1 }

  tcpConnLocalAddress OBJECT-TYPE
          SYNTAX  IpAddress
          ACCESS  read-only
          STATUS  mandatory
          ::= { tcpConnEntry 2 }

  tcpConnLocalPort OBJECT-TYPE
          SYNTAX  INTEGER (0..65535)
          ACCESS  read-only
          STATUS  mandatory
          ::= { tcpConnEntry 3 }

  tcpConnRemAddress OBJECT-TYPE
          SYNTAX  IpAddress
          ACCESS  read-only
          STATUS  mandatory
          ::= { tcpConnEntry 4 }

  tcpConnRemPort OBJECT-TYPE
          SYNTAX  INTEGER (0..65535)
          ACCESS  read-only
          STATUS  mandatory

          ::= { tcpConnEntry 5 }

  -- the UDP group

  udpInDatagrams OBJECT-TYPE
          SYNTAX  Counter
          ACCESS  read-only
          STATUS  mandatory
          ::= { udp 1 }

  udpNoPorts OBJECT-TYPE
          SYNTAX  Counter
          ACCESS  read-only
          STATUS  mandatory
          ::= { udp 2 }

  udpInErrors OBJECT-TYPE
          SYNTAX  Counter
          ACCESS  read-only
          STATUS  mandatory
          ::= { udp 3 }

  udpOutDatagrams OBJECT-TYPE
          SYNTAX  Counter
          ACCESS  read-only
          STATUS  mandatory
          ::= { udp 4 }

  -- the EGP group

  egpInMsgs OBJECT-TYPE
          SYNTAX  Counter
          ACCESS  read-only
          STATUS  mandatory
          ::= { egp 1 }

  egpInErrors OBJECT-TYPE
          SYNTAX  Counter
          ACCESS  read-only
          STATUS  mandatory
          ::= { egp 2 }

  egpOutMsgs OBJECT-TYPE
          SYNTAX  Counter
          ACCESS  read-only
          STATUS  mandatory
          ::= { egp 3 }


  egpOutErrors OBJECT-TYPE
          SYNTAX  Counter
          ACCESS  read-only
          STATUS  mandatory
          ::= { egp 4 }

  -- the EGP Neighbor table

  egpNeighTable OBJECT-TYPE
          SYNTAX  SEQUENCE OF EgpNeighEntry
          ACCESS  read-only
          STATUS  mandatory
          ::= { egp 5 }

  egpNeighEntry OBJECT-TYPE
          SYNTAX  EgpNeighEntry
          ACCESS  read-only
          STATUS  mandatory
          ::= { egpNeighTable 1 }

  EgpNeighEntry ::= SEQUENCE {
      egpNeighState
          INTEGER,
      egpNeighAddr
          IpAddress
  }

  egpNeighState OBJECT-TYPE
          SYNTAX  INTEGER {
                      idle(1),
                      acquisition(2),
                      down(3),
                      up(4),
                      cease(5)
                  }
          ACCESS  read-only
          STATUS  mandatory
          ::= { egpNeighEntry 1 }

  egpNeighAddr OBJECT-TYPE
          SYNTAX  IpAddress
          ACCESS  read-only
          STATUS  mandatory
          ::= { egpNeighEntry 2 }

  END
