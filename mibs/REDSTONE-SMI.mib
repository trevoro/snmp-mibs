-- *****************************************************************
-- REDSTONE-SMI
--
-- Redstone Communications Inc. Enterprise
-- Structure of Management Information (SMI)
--
-- Copyright 1998 Redstone Communications, Incorporated.
-- All Rights Reserved.
-- *****************************************************************

REDSTONE-SMI DEFINITIONS ::= BEGIN

IMPORTS
	MODULE-IDENTITY,
	OBJECT-IDENTITY,
	enterprises
		FROM SNMPv2-SMI;

redstone   MODULE-IDENTITY
	LAST-UPDATED "9801010000Z"
	ORGANIZATION "Redstone Communications, Inc."
	CONTACT-INFO
        "
		Redstone Communications, Inc.
        5 Carlisle Road
        Westford MA 01886
        USA

		Tel:    +1-978-692-1999
		Email:  mib@redstonecom.com
        "
	DESCRIPTION
		"The Structure of Management Information for the
		Redstone Communications Inc. enterprise."
	REVISION      "9801010000Z"
	DESCRIPTION
		"Initial version of this MIB module."
	::= { enterprises 2773 } -- assigned by IANA

-- +++++++++++++++++++++++++++++++++++++++++++++++++++++++++++++++++++++++++++++
-- Object Identifier Assignment Name Space
--
-- This section of the MIB tree is used for object identifier
-- name assignments for various purposes.
--+++++++++++++++++++++++++++++++++++++++++++++++++++++++++++++++++++++++++++++
rsRegistration OBJECT-IDENTITY
	STATUS	current
	DESCRIPTION
		"The root OBJECT IDENTIFIER under which administratively 
		assigned OBJECT IDENTIFIERS are registered, for example, 
        sysObjectIDs, hardware components, chip sets, etc."
	::= { redstone 1 }

rsRegGeneric OBJECT-IDENTITY
	STATUS	current
	DESCRIPTION
		"The root OBJECT IDENTIFIER under which identifiers of 
		generic significance are assigned."
	::= { rsRegistration 1 }

    rsRegGenericOther      OBJECT IDENTIFIER ::= { rsRegGeneric 1 }
    rsRegGenericNone       OBJECT IDENTIFIER ::= { rsRegGeneric 2 }
    rsRegGenericUnknown    OBJECT IDENTIFIER ::= { rsRegGeneric 3 }


rsRegHardware OBJECT-IDENTITY
	STATUS	current
	DESCRIPTION
		"The root OBJECT IDENTIFIER under which identifiers
        for hardware components are assigned."
	::= { rsRegistration 2 }

rsRegHwPlatform OBJECT-IDENTITY
	STATUS	current
	DESCRIPTION
		"The root OBJECT IDENTIFIER under which identifiers for
        platforms are assigned. These identifiers are typically
        used as sysObjectID values."
	::= { rsRegHardware 1 }

rsRegHwPlatformRX1400   OBJECT IDENTIFIER ::= { rsRegHwPlatform 1 }
rsRegHwPlatformRX700    OBJECT IDENTIFIER ::= { rsRegHwPlatform 2 }

rsRegHwModule OBJECT-IDENTITY
	STATUS	current
	DESCRIPTION
		"The root OBJECT IDENTIFIER under which identifiers for
        platform modules are assigned."
	::= { rsRegHardware 2 }

rsRegHwChip OBJECT-IDENTITY
	STATUS	current
	DESCRIPTION
		"The root OBJECT IDENTIFIER under which identifiers for
        chip sets are assigned."
	::= { rsRegHardware 3 }


-- +++++++++++++++++++++++++++++++++++++++++++++++++++++++++++++++++++++++++++++
-- MIB Object Definitions
--
-- Definitions of all enterprise MIB objects are contained in this
-- this section of the MIB. In most cases, MIB object names will 
-- be allocated beneath a MIB's MODULE-IDENTITY node.
-- +++++++++++++++++++++++++++++++++++++++++++++++++++++++++++++++++++++++++++++
rsMgmt OBJECT-IDENTITY
	STATUS	current
	DESCRIPTION
		"The root OBJECT IDENTIFIER under which enterprise MIB
		modules are defined."
--      
--      1   REDSTONE-TC                         Textual Conventions
--      2   REDSTONE-SYSTEM-MIB                 System (reserved)
--      3   REDSTONE-IF-MIB                     Generic Interfaces 
--      4   REDSTONE-DS3-MIB                    DS3/E3
--      5   REDSTONE-DS1-MIB                    DS1/E1
--      6   REDSTONE-FRACTIONAL-T1-MIB          Fractional T1 arrangements
--      7   REDSTONE-SONET-MIB                  SONET
--      8   REDSTONE-ATM-MIB                    ATM
--      9   REDSTONE-HDLC-MIB                   HDLC 
--     10   REDSTONE-FRAME-RELAY-MIB            Frame Relay
--     11   REDSTONE-PPP-MIB                    PPP
--     12   REDSTONE-IP-MIB                     IP Protocol, Interfaces, Forwarding
--     13   REDSTONE-IP-POLICY-MIB              IP Access Lists, Route Maps
--     14   REDSTONE-OSPF-MIB                   OSPF
--     15   REDSTONE-BGP-MIB                    BGP
--     16   REDSTONE-SNMP-MIB                   SNMP
--     17   REDSTONE-RXSYS-MIB                  System MIB specific to RX1400/RX700
--     18   REDSTONE-PPPOE-MIB                  PPP-over-Ethernet MIB
--     19   REDSTONE-RADIUS-CLIENT-MIB          RADIUS Client MIB
--     20   REDSTONE-NAME-SERVER-MIB            Name Server MIB
--     21   REDSTONE-ADDRESS-POOL-MIB           Address Pool MIB
--     22   REDSTONE-DHCP-MIB                   DHCP MIB
--     23   REDSTONE-FILE-XFER-MIB              FILE TRANSFER MIB
--     24   REDSTONE-ACCOUNTING-MIB             BULK STATS 
--     25   REDSTONE-TEMPLATE-MIB               Name/identifier mapping of configuration templates.
--
	::= { redstone 2 }


-- +++++++++++++++++++++++++++++++++++++++++++++++++++++++++++++++++++++++++++++
-- MIB Agent Capabilities Statements
--
-- Specifications of agent capabilities for SNMP agents in Redstone products.
-- +++++++++++++++++++++++++++++++++++++++++++++++++++++++++++++++++++++++++++++
rsRegAgentCapabilities OBJECT-IDENTITY
	STATUS	current
	DESCRIPTION
		"The root OBJECT IDENTIFIER under which AGENT-CAPABILITIES 
		identifiers are assigned."
	::= { redstone 3 }

-- +++++++++++++++++++++++++++++++++++++++++++++++++++++++++++++++++++++++++++++
-- MIB Experimental Object Definitions
--
-- Temporary MIB object definitions for development purposes.
-- +++++++++++++++++++++++++++++++++++++++++++++++++++++++++++++++++++++++++++++
rsExperiment OBJECT-IDENTITY
	STATUS	current
	DESCRIPTION
		"The root OBJECT IDENTIFIER under which experimental 
		MIBs may be temporarily	located for development purposes.
		Support for MIBs in the rsExperiment subtree will be 
		deleted when a permanent object	identifier is assigned."
	::= { redstone 4 }

END
