INTERCARRIER-FR-MIB DEFINITIONS ::= BEGIN
 IMPORTS
    MODULE-IDENTITY, OBJECT-TYPE, Counter32, enterprises  FROM SNMPv2-SMI
    ifIndex                                  FROM RFC-1213;

 bellcore         OBJECT IDENTIFIER ::= { enterprises 148 }
 requirements     OBJECT IDENTIFIER ::= { bellcore 1 }


 gr1430 MODULE-IDENTITY
      LAST-UPDATED "9409301200Z"
      ORGANIZATION "Bellcore"
      CONTACT-INFO
            "   Andrew J. Mayer
                Bellcore
                331 Newman Springs Rd.
                Red Bank, NJ 07701 USA

                Tel: 1-908-758-2148
                Fax: 1-908-758-4177
                E-mail: ajm2@cc.bellcore.com

                Robert M. Davenport
                Bellcore
                331 Newman Springs Rd.
                Red Bank, NJ 07701 USA

                Tel: 1-908-758-2194
                Fax: 1-908-758-4177
                E-mail: rmd2@cc.bellcore.com."

      DESCRIPTION
               "The MIB module to describe generic objects for
               Intercarrier Frame Relay Network Service."
      ::= { requirements 9 }

              friciObjects  OBJECT IDENTIFIER ::= { gr1430 1 }

 -- The Frame Relay ICI Group

 friciTable OBJECT-TYPE
    SYNTAX  SEQUENCE OF FrIciEntry
    MAX-ACCESS  not-accessible
    STATUS  current
    DESCRIPTION
       "The Frame Relay ICI table."
    ::= { friciObjects 1 }





 friciEntry OBJECT-TYPE
    SYNTAX  FrIciEntry
    MAX-ACCESS  not-accessible
    STATUS  current
    DESCRIPTION
       "An entry in the Frame Relay ICI table."
    INDEX   { ifIndex }
    ::= { friciTable 1 }

 FrIciEntry ::=
    SEQUENCE {
       friciLevel2ErrorDiscards
           Counter32,
       friciLevel3ErrorDiscards
           Counter32,
       friciSigUserInvalidEvents
           Counter32,
       friciSigUserIncorrectEvents
           Counter32,
       friciSigNetInvalidEvents
           Counter32,
       friciSigNetIncorrectEvents
           Counter32,
       friciCongestionDiscards
           Counter32,
       friciDisagreementsDiscards
           Counter32
 }

 friciLevel2ErrorDiscards OBJECT-TYPE
    SYNTAX  Counter32
    MAX-ACCESS  read-only
    STATUS  current
    DESCRIPTION
       "The number of frames discarded per FR_ICI 
        transmission path in the ingress direction
        due to Level 2 errors.  The specific Level 2
        errors that contributed to the discard of frames
        are described in Section 5.4.3, R 5-31 of
        GR-1327-CORE"
 ::= { friciEntry 1 }













 friciLevel3ErrorDiscards OBJECT-TYPE
    SYNTAX  Counter32
    MAX-ACCESS  read-only
    STATUS  current
    DESCRIPTION
       "The number of frames discarded per FR_ICI 
        transmission path in the ingress direction
        due to Level 3 errors.  The specific Level 3
        errors that contributed to the discard of frames
        are described in Section 5.4.3, R 5-31 of
        GR-1327-CORE"
 ::= { friciEntry 2 }

 friciSigUserInvalidEvents OBJECT-TYPE
    SYNTAX  Counter32
    MAX-ACCESS  read-only
    STATUS  current
    DESCRIPTION
       "The number of frames discarded per FR_ICI 
        transmission path in the ingress direction
        because of user side status signaling invalid
        fields.  The specific status signaling invalid field
        errors that contributed to the discard of frames
        are described in Section 5.4.3, R 5-31 of
        GR-1327-CORE"
 ::= { friciEntry 3 }

 friciSigUserIncorrectEvents OBJECT-TYPE
    SYNTAX  Counter32
    MAX-ACCESS  read-only
    STATUS  current
    DESCRIPTION
       "The number of frames discarded per FR_ICI 
        transmission path in the ingress direction
        because of user side status signaling incorrect
        fields.  The specific status signaling incorrect field
        errors that contributed to the discard of frames
        are described in Section 5.4.3, R 5-31 of
        GR-1327-CORE"
 ::= { friciEntry 4 }














 friciSigNetInvalidEvents OBJECT-TYPE
    SYNTAX  Counter32
    MAX-ACCESS  read-only
    STATUS  current
    DESCRIPTION
       "The number of frames discarded per FR_ICI 
        transmission path in the ingress direction
        because of network side status signaling invalid
        fields.  The specific status signaling invalid field
        errors that contributed to the discard of frames
        are described in Section 5.4.3, R 5-31 of
        GR-1327-CORE"
 ::= { friciEntry 5 }

 friciSigNetIncorrectEvents OBJECT-TYPE
    SYNTAX  Counter32
    MAX-ACCESS  read-only
    STATUS  current
    DESCRIPTION
       "The number of frames discarded per FR_ICI 
        transmission path in the ingress direction
        because of user side status signaling incorrect
        fields.  The specific status signaling incorrect field
        errors that contributed to the discard of frames
        are described in Section 5.4.3, R 5-31 of
        GR-1327-CORE"
 ::= { friciEntry 6 }

 friciCongestionDiscards OBJECT-TYPE
    SYNTAX  Counter32
    MAX-ACCESS  read-only
    STATUS  current
    DESCRIPTION
       "The number of frames discarded per FR_ICI 
        transmission path due to congestion.  This count
        includes frames with and without the DE bit set
        discarded due to congestion.  The specific reasons
        for discarding frames at a congestable resource
        are described in Section 7.2.1, R 7-8, Items #5, #6,
        and #7 in GR-1327-CORE"
 ::= { friciEntry 7 }













 friciDisagreementsDiscards OBJECT-TYPE
    SYNTAX  Counter32
    MAX-ACCESS  read-only
    STATUS  current
    DESCRIPTION
       "The number of frames discarded per FR_ICI 
        transmission path because of service disagreements
        The specific service disagreements that contribute
        to the discard of frames are described in Section 5.5
        R 5-42 of GR-1327-CORE"
 ::= { friciEntry 8 }


 END
