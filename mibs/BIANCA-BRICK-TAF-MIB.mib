-- This file is corresponding to Release 6.1.2.100 from 2001/09/26 00:00:00
-- (C)opyright 1991-1999 BinTec Communications AG, All Rights Reserved
--  $RCSfile: mibtaf,v $ 
-- $Revision: 1.4 $ 

BIANCA-BRICK-TAF-MIB DEFINITIONS ::= BEGIN
 
        IMPORTS
            IpAddress, Counter
                FROM RFC1155-SMI
 
            OBJECT-TYPE
                FROM RFC-1212
			Date FROM BIANCA-BRICK-PPP-MIB;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bintecsec 	OBJECT IDENTIFIER ::= { bintec 254 }
    taf	OBJECT IDENTIFIER
		::= { bintecsec  9 } 

	tafServerTable OBJECT-TYPE
	    SYNTAX  SEQUENCE OF TafServerEntry
	    ACCESS  not-accessible
	    STATUS  mandatory
	    DESCRIPTION
		"The tafServerTable contains information about the 
		 servers that are used for the token authentication 
		 firewall."
	::= { taf 1 }

	tafServerEntry OBJECT-TYPE
	    SYNTAX  TafServerEntry
	    ACCESS  not-accessible
	    STATUS  mandatory
	    DESCRIPTION
		""
	    INDEX { tafServerType }
	::= { tafServerTable 1 }

	TafServerEntry ::=
	    SEQUENCE {
		tafServerType			INTEGER,
		tafServerNodeSecret		OCTET STRING,
		tafServerVersion		INTEGER,
		tafServerRetries		INTEGER,
		tafServerTimeout		INTEGER,
		tafServerEncryption		INTEGER,
		tafServerAddress		INTEGER,
		tafServerPort			INTEGER,
		tafServerClientPort		INTEGER,
		tafServerPriority		INTEGER,
		tafServerState			INTEGER,
		tafServerCheckInterface		INTEGER
	    }

	tafServerType OBJECT-TYPE
	    SYNTAX  INTEGER { ace(1), none(2) } 
	    ACCESS  read-write
	    STATUS  mandatory

	    DESCRIPTION
		"Type of authentication server."
	::= { tafServerEntry 1 }

	tafServerNodeSecret OBJECT-TYPE
	    SYNTAX  OCTET STRING
	    ACCESS  read-write
	    STATUS  mandatory

	    DESCRIPTION
		"The shared secret between TAF server and Brick."
	::= { tafServerEntry 2 }

	tafServerVersion OBJECT-TYPE
	    SYNTAX  INTEGER  
	    ACCESS  read-write
	    STATUS  mandatory

	    DESCRIPTION
		"Version of the protocol between TAF server and Brick."
	::= { tafServerEntry 3 }

	tafServerRetries OBJECT-TYPE
	    SYNTAX  INTEGER  (1..6)
	    ACCESS  read-write
	    STATUS  mandatory

	    DESCRIPTION
		"The number of retries sent for each request"
	::= { tafServerEntry 4 }

	tafServerTimeout OBJECT-TYPE
	    SYNTAX  INTEGER  (1..20)
	    ACCESS  read-write
	    STATUS  mandatory

	    DESCRIPTION
		"The amount of seconds  waiting for an
		 outstanding request."
	::= { tafServerEntry 5 }

	tafServerEncryption OBJECT-TYPE
	    SYNTAX  INTEGER  { sdi(1), des(2) }
	    ACCESS  read-write
	    STATUS  mandatory

	    DESCRIPTION
		"The encryption algorithm that is used for the 
		 communication between ACE server and Brick"
	::= { tafServerEntry 6 }

	tafServerAddress OBJECT-TYPE
	    SYNTAX  IpAddress 
	    ACCESS  read-write
	    STATUS  mandatory

	    DESCRIPTION
		"The IP Address of the TAF server ."
	::= { tafServerEntry 7 }

	tafServerPort OBJECT-TYPE
	    SYNTAX  INTEGER 
	    ACCESS  read-write
	    STATUS  mandatory

	    DESCRIPTION
		"The TAF server UDP port."
	::= { tafServerEntry 8 }

	tafServerClientPort OBJECT-TYPE
	    SYNTAX  INTEGER 
	    ACCESS  read-write
	    STATUS  mandatory

	    DESCRIPTION
		"The TAF client UDP port."
	::= { tafServerEntry 9 }

	tafServerPriority OBJECT-TYPE
	    SYNTAX  INTEGER (0..7) 
	    ACCESS  read-write
	    STATUS  mandatory

	    DESCRIPTION
		"The TAF server with the lowest priority is the first
		 used for request. Use the value 0 for the master server
		 and the value 1 for the slave server."
	::= { tafServerEntry 10 }

	tafServerState OBJECT-TYPE
	    SYNTAX  INTEGER { active(1), disabled(2), delete(3) }
	    ACCESS  read-write
	    STATUS  mandatory

	    DESCRIPTION
		"The entry is ignored, if the value of this field is 
		`disabled'. Set this field to `delete' to delete
		this entry"
	::= { tafServerEntry 11 }

	tafServerCheckInterface OBJECT-TYPE
	    SYNTAX  INTEGER  { dont-verify(1), verify(2) }
	    ACCESS  read-write
	    STATUS  mandatory

	    DESCRIPTION
		""
	::= { tafServerEntry 12 }





    bibo        OBJECT IDENTIFIER ::= { bintec 4 }
    biboip      OBJECT IDENTIFIER 
	::= { bibo 5 }

        ipTafTable OBJECT-TYPE
            SYNTAX  SEQUENCE OF IpTafEntry
            ACCESS  not-accessible
            STATUS  mandatory
            DESCRIPTION
		"The ipTafTable contains information about IP partners that
		 sent packets to an interface that has authentication
		 enabled."
	::= { biboip 17}

	ipTafEntry OBJECT-TYPE
            SYNTAX  IpTafEntry
            ACCESS  not-accessible
            STATUS  mandatory
            DESCRIPTION
		""
	    INDEX   {
		ipTafIfIndex
	    }
            ::= { ipTafTable 1 }

	IpTafEntry ::=
            SEQUENCE {
		ipTafIfIndex		INTEGER,
		ipTafAddress    	IpAddress,
		ipTafState		INTEGER,
		ipTafAuthTime		Date,
		ipTafTimeout           INTEGER
            }

	ipTafIfIndex OBJECT-TYPE
	    SYNTAX INTEGER 
            ACCESS  read-only
            STATUS  mandatory
            DESCRIPTION
		 "Interface Index."
	::= { ipTafEntry 1 }

	ipTafAddress OBJECT-TYPE
	    SYNTAX  IpAddress
            ACCESS  read-only
            STATUS  mandatory
            DESCRIPTION
		 "IP address of the partner"
	::= { ipTafEntry 2 }

	ipTafState OBJECT-TYPE
	    SYNTAX INTEGER {
		idle(1),
		authenticating(2),
		xfer(3)
	    }
            ACCESS  read-only
            STATUS  mandatory
            DESCRIPTION
		"This object shows the authentication state of the partner.
		 Packets are only routed if the state is xfer. If the state
		 is authenticating a response from an authentication 
		 server is expected. Entries in state idle are deleted
		 automatically after a timeout."
	::= { ipTafEntry 3 }

	ipTafAuthTime OBJECT-TYPE
	    SYNTAX  Date
            ACCESS  read-only
            STATUS  mandatory
            DESCRIPTION
		 "Time of the last successful authentication."
	::= { ipTafEntry 4 }

	ipTafTimeout OBJECT-TYPE
	    SYNTAX  INTEGER
            ACCESS  read-write
            STATUS  mandatory
            DESCRIPTION
		 "This object gives the number of seconds till the 
		  authentication expires."
	::= { ipTafEntry 5 }

END
