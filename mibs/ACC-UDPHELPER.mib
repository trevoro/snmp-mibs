ACC-UDPHELPER DEFINITIONS ::= BEGIN

    IMPORTS
		OBJECT-TYPE, IpAddress, TimeTicks, Gauge, Counter FROM RFC1155-SMI
		TRAP-TYPE FROM RFC-1215
	accTrapLogSeqNum FROM ACC-SYSTEM
	accBRG, DisplayString, RowStatus, IfIndex, SmdsAddress
             FROM ACC-MIB;

-- UDP Helper Group
accUDPHelper         OBJECT IDENTIFIER ::= { accBRG 48 }
	accUdpHelperStatus	OBJECT-TYPE
			SYNTAX	 INTEGER {
				enabled(1),
				disabled(2)
				}
			 ACCESS  read-only
			 STATUS  mandatory
			 DESCRIPTION
		" Status of UDP Helper 
		  enabled - The UDP helper functionality is enabled
		  disabled - The UDP helper functionality is disbled"
			::= { accUDPHelper 1 }
        accUdpHelperPortTable 	OBJECT-TYPE
                        SYNTAX  SEQUENCE OF AccUdpHelperPortEntry
                        ACCESS  not-accessible
                        STATUS  mandatory
                        DESCRIPTION
                " A table of UDP Helper ports and IP addresses to which
                 UDP Helper will forward UDP requests to."
                        ::= { accUDPHelper 2 }
        accUdpHelperPortEntry		OBJECT-TYPE
                        SYNTAX  AccUdpHelperPortEntry
                        ACCESS  not-accessible
                        STATUS  mandatory
                        DESCRIPTION
			" It is the entry for UDP Helper port table"
                       INDEX {  accUdpHelperPortNo,
    			        accUDPHelperIpAddr}
                        ::= { accUdpHelperPortTable 1 }
     AccUdpHelperPortEntry ::= SEQUENCE {
	accUdpHelperPortNo	INTEGER,
	accUDPHelperIpAddr	IpAddress,
	accUdpHelperTtlOverride	INTEGER
                                }
	accUdpHelperPortNo	OBJECT-TYPE
                        SYNTAX  INTEGER (1..65535)
                        ACCESS  read-only
                        STATUS  mandatory
                        DESCRIPTION
                         " The UDP port number for which the UDP helper
                           is being turned on."
                        ::= { accUdpHelperPortEntry 1 }
	accUDPHelperIpAddr	OBJECT-TYPE
			SYNTAX IpAddress
			ACCESS	read-only
			STATUS	mandatory
			DESCRIPTION
		" The address to which UDP Helper packets need to be 
		forwarded"
			 ::= { accUdpHelperPortEntry 2 }
	accUdpHelperTtlOverride	OBJECT-TYPE
                        SYNTAX  INTEGER (0..255)
                        ACCESS  read-only
                        STATUS  mandatory
                        DESCRIPTION
                         " The TTL value specified by the user"
                        ::= { accUdpHelperPortEntry 3 }
        accUdpHelperStatsTable 	OBJECT-TYPE
                        SYNTAX  SEQUENCE OF AccUdpHelperStatsEntry
                        ACCESS  not-accessible
                        STATUS  mandatory
                        DESCRIPTION
                " This displays the UDP Helper statistics "
                        ::= { accUDPHelper 3 }
        accUdpHelperStatsEntry		OBJECT-TYPE
                        SYNTAX  AccUdpHelperStatsEntry
                        ACCESS  not-accessible
                        STATUS  mandatory
                        DESCRIPTION
			" An entry in the UDP Helper stats table"
                       INDEX {  accUdpHelperStPortNo}
                        ::= { accUdpHelperStatsTable 1 }
     AccUdpHelperStatsEntry ::= SEQUENCE {
	accUdpHelperStPortNo		INTEGER,
	accUDPHelperReceivedPkts	Counter,
	accUDPHelperForwardedPkts	Counter,
	accUDPHelperRebroadcastedPkts	Counter,
	accUDPHelperDiscardedPkts	Counter
                                }
	accUdpHelperStPortNo	OBJECT-TYPE
                        SYNTAX  INTEGER (1..65535)
                        ACCESS  read-only
                        STATUS  mandatory
                        DESCRIPTION
                         " The UDP port number for which the UDP helper
                           is turned on."
                        ::= { accUdpHelperStatsEntry 1 }
	accUDPHelperReceivedPkts	OBJECT-TYPE
			SYNTAX	Counter
			ACCESS	read-only
			STATUS	mandatory
			DESCRIPTION
		"The number of UDP Helper packets received."
			 ::= { accUdpHelperStatsEntry 2 }
	accUDPHelperForwardedPkts	OBJECT-TYPE
			SYNTAX	Counter
			ACCESS	read-only
			STATUS	mandatory
			DESCRIPTION
		"The number of UDP Helper packets Forwarded."
			 ::= { accUdpHelperStatsEntry 3 }
	accUDPHelperRebroadcastedPkts	OBJECT-TYPE
			SYNTAX	Counter
			ACCESS	read-only
			STATUS	mandatory
			DESCRIPTION
		"The number of UDP Helper packets Rebroadcasted."
			 ::= { accUdpHelperStatsEntry 4 }
	accUDPHelperDiscardedPkts	OBJECT-TYPE
			SYNTAX	Counter
			ACCESS	read-only
			STATUS	mandatory
			DESCRIPTION
		"The number of UDP Helper packets Discarded."
			 ::= { accUdpHelperStatsEntry 5 }
	accUdpHelperPrAction	OBJECT-TYPE
			SYNTAX	 INTEGER {
				add (1),
				delete (2)
				}
			 ACCESS  read-only
			 STATUS  mandatory
			 DESCRIPTION
		" Action in Add/Delete UDP Helper command "
			::= { accUDPHelper 4 }

END
