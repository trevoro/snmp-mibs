Nortel-MsCarrier-MscPassport-NetSentryMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Integer32
   FROM Nortel-MsCarrier-MscPassport-StandardTextualConventionsMIB

      AsciiString,
      NonReplicated,
      AsciiStringIndex
   FROM Nortel-MsCarrier-MscPassport-TextualConventionsMIB

      mscVrIndex,
      mscVr
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     NetSentry Enterprise MIB."

netSentryMIB OBJECT IDENTIFIER ::= { mscPassportMIBs 31 }










-- Vr/<string> NetSentry
-- This is the top-level component for NetSentry. It exists to hold global 
-- NetSentry data, and the subcomponents.

mscVrNs OBJECT IDENTIFIER ::= { mscVr 4 }



mscVrNsRowStatusTable OBJECT-TYPE
   SYNTAX     SEQUENCE OF MscVrNsRowStatusEntry
   ACCESS     not-accessible
   STATUS     mandatory
   DESCRIPTION
     "This entry controls the addition and deletion of 
      mscVrNs components."
::= { mscVrNs 1 }

mscVrNsRowStatusEntry OBJECT-TYPE
   SYNTAX     MscVrNsRowStatusEntry
   ACCESS     not-accessible
   STATUS     mandatory
   DESCRIPTION
     "A single entry in the table represents a single 
      mscVrNs component."
   INDEX {
      mscVrIndex,
      mscVrNsIndex }
::= { mscVrNsRowStatusTable 1 }

MscVrNsRowStatusEntry ::= SEQUENCE {
   mscVrNsRowStatus
      RowStatus,
   mscVrNsComponentName
      DisplayString,
   mscVrNsStorageType
      StorageType,
   mscVrNsIndex
      NonReplicated }

mscVrNsRowStatus OBJECT-TYPE
   SYNTAX     RowStatus 
   ACCESS     read-write
   STATUS     mandatory
   DESCRIPTION
     "This variable is used as the basis for SNMP naming of
      mscVrNs components.
      These components can be added and deleted."
::= { mscVrNsRowStatusEntry 1 }

mscVrNsComponentName OBJECT-TYPE
   SYNTAX     DisplayString 
   ACCESS     read-only
   STATUS     mandatory
   DESCRIPTION
     "This variable provides the component's string name for
      use with the ASCII Console Interface"
::= { mscVrNsRowStatusEntry 2 }

mscVrNsStorageType OBJECT-TYPE
   SYNTAX     StorageType 
   ACCESS     read-only
   STATUS     mandatory
   DESCRIPTION
     "This variable represents the storage type value for the
      mscVrNs tables."
::= { mscVrNsRowStatusEntry 4 }

mscVrNsIndex OBJECT-TYPE
   SYNTAX     NonReplicated 
   ACCESS     not-accessible
   STATUS     mandatory
   DESCRIPTION
     "This variable represents the index for the mscVrNs tables."
::= { mscVrNsRowStatusEntry 10 }

mscVrNsProvTable OBJECT-TYPE
   SYNTAX     SEQUENCE OF MscVrNsProvEntry
   ACCESS     not-accessible
   STATUS     mandatory
   DESCRIPTION
     "This contains the global NetSentry control flags."
::= { mscVrNs 100 }

mscVrNsProvEntry OBJECT-TYPE
   SYNTAX     MscVrNsProvEntry
   ACCESS     not-accessible
   STATUS     mandatory
   DESCRIPTION
     "An entry in the mscVrNsProvTable."
   INDEX {
      mscVrIndex,
      mscVrNsIndex }
::= { mscVrNsProvTable 1 }

MscVrNsProvEntry ::= SEQUENCE {
   mscVrNsDropConditions
      OCTET STRING }

mscVrNsDropConditions OBJECT-TYPE
   SYNTAX     OCTET STRING (SIZE (1))
   ACCESS     read-write
   STATUS     mandatory
   DESCRIPTION
     "This attribute controls under what circumstances NetSentry drops 
      packets. It is possible for NetSentry to drop packets when:
      There is no memory to contain statistics for this packet (statsNoMem), it 
      is for whatever reason impossible to clone, copy, or log a copy of the 
      packet via the clone_to copy_to or log_to actions respectively 
      (cantCloneTo, cantCopyTo and cantLogTo), and if the packet encounters 
      a filter which is provisioned at a filter point within a protocol 
      component, but not defined in any of the files defined by File 
      components within NetSentry (this is a Null filter).

      Description of bits:
      statsNoMem(0)
      cantCloneTo(1)
      cantLogTo(2)
      cantCopyTo(3)
      cantMacCloneTo(4)
      nullFilter(5)"
::= { mscVrNsProvEntry 1 }

mscVrNsStatsTable OBJECT-TYPE
   SYNTAX     SEQUENCE OF MscVrNsStatsEntry
   ACCESS     not-accessible
   STATUS     mandatory
   DESCRIPTION
     "This contains the global NetSentry (in particular, non-protocol specific) 
      statistics."
::= { mscVrNs 101 }

mscVrNsStatsEntry OBJECT-TYPE
   SYNTAX     MscVrNsStatsEntry
   ACCESS     not-accessible
   STATUS     mandatory
   DESCRIPTION
     "An entry in the mscVrNsStatsTable."
   INDEX {
      mscVrIndex,
      mscVrNsIndex }
::= { mscVrNsStatsTable 1 }

MscVrNsStatsEntry ::= SEQUENCE {
   mscVrNsPacketsProcessed
      Counter32,
   mscVrNsPacketsFailed
      Counter32,
   mscVrNsStatsNoMem
      Counter32,
   mscVrNsHsaOkayFailed
      Counter32,
   mscVrNsDepthExceeded
      Counter32,
   mscVrNsDroppedStatsNoMem
      Counter32,
   mscVrNsDroppedCantCloneTo
      Counter32,
   mscVrNsDroppedCantLogTo
      Counter32,
   mscVrNsDroppedCantCopyTo
      Counter32,
   mscVrNsDroppedNullFilter
      Counter32 }

mscVrNsPacketsProcessed OBJECT-TYPE
   SYNTAX     Counter32 
   ACCESS     read-only
   STATUS     mandatory
   DESCRIPTION
     "This attribute counts the total number of packets processed through 
      NetSentry. This counter will wrap around to zero when it exceeds its 
      maximum value, 4294967295."
::= { mscVrNsStatsEntry 1 }

mscVrNsPacketsFailed OBJECT-TYPE
   SYNTAX     Counter32 
   ACCESS     read-only
   STATUS     mandatory
   DESCRIPTION
     "This attribute counts the total number of packets processed through 
      NetSentry which ended with a fail disposition. This counter will wrap 
      around to zero when it exceeds its maximum value, 4294967295."
::= { mscVrNsStatsEntry 2 }

mscVrNsStatsNoMem OBJECT-TYPE
   SYNTAX     Counter32 
   ACCESS     read-only
   STATUS     mandatory
   DESCRIPTION
     "This attribute counts the total number of packets processed through 
      NetSentry for which statistic should have been gathered, but for which 
      statistics were not gathered due to a failure to allocate memory. Such 
      packets may or may not be dropped according to the values provisioned 
      in dropConditions under the NetSentry component. If this attribute is 
      being incremented, the system is suffering from memory shortfalls, and 
      some operator action is advised. Perhaps memory allocations should be 
      re-provisioned, NetSentry statistics gathering should be reduced, or 
      NetSentry statistics tables should be cleared to temporarily free memory. 
      This counter will wrap around to zero when it exceeds its maximum 
      value, 4294967295."
::= { mscVrNsStatsEntry 3 }

mscVrNsHsaOkayFailed OBJECT-TYPE
   SYNTAX     Counter32 
   ACCESS     read-only
   STATUS     mandatory
   DESCRIPTION
     "This attribute counts the total number of packets processed through 
      NetSentry which encountered, and did not match, an hsa_okay pattern. 
      Such packets are likely to be generated from misconfigured hosts. Some 
      operator action to track down these hosts is advised. This counter will 
      wrap around to zero should it ever exceed its maximum value, 
      4294967295."
::= { mscVrNsStatsEntry 4 }

mscVrNsDepthExceeded OBJECT-TYPE
   SYNTAX     Counter32 
   ACCESS     read-only
   STATUS     mandatory
   DESCRIPTION
     "This attribute counts the total number of times a NetSentry filter was 
      executed which referenced too many layers of indirect filters. If this 
      count is non-zero, the filter definitions the unit is using are incorrect, and 
      some operator action to track down the erroneous filter definitions is 
      advised. Filters will not be behaving correctly if this counter is 
      increasing, and security could be compromised. This count should 
      always be zero, and it will wrap around to zero should it ever exceed its 
      maximum value of 4294967295."
::= { mscVrNsStatsEntry 5 }

mscVrNsDroppedStatsNoMem OBJECT-TYPE
   SYNTAX     Counter32 
   ACCESS     read-only
   STATUS     mandatory
   DESCRIPTION
     "This counts the total number of packets that were actually dropped due 
      to an inability to allocate memory to hold statistics for the packet. Such 
      a packet must have had a NetSentry statistics gathering action applied to 
      it, in order for the attempt to gather statistics to be made, and the 
      dropConditions attribute must include the statsNoMem value."
::= { mscVrNsStatsEntry 6 }

mscVrNsDroppedCantCloneTo OBJECT-TYPE
   SYNTAX     Counter32 
   ACCESS     read-only
   STATUS     mandatory
   DESCRIPTION
     "This counts the total number of packets that were dropped due to the 
      failure of a clone_to action applied to the packet. This counter will only 
      increment if the dropConditions attribute includes the cantCloneTo 
      value."
::= { mscVrNsStatsEntry 7 }

mscVrNsDroppedCantLogTo OBJECT-TYPE
   SYNTAX     Counter32 
   ACCESS     read-only
   STATUS     mandatory
   DESCRIPTION
     "This counts the total number of packets that 
      were dropped due to the failure of a log_to 
      action applied to the packet. This counter 
      will only increment if the dropConditions 
      attribute includes the cantLogTo value."
::= { mscVrNsStatsEntry 8 }

mscVrNsDroppedCantCopyTo OBJECT-TYPE
   SYNTAX     Counter32 
   ACCESS     read-only
   STATUS     mandatory
   DESCRIPTION
     "This counts the total number of packets that 
      were dropped due to the failure of a copy_to 
      action applied to the packet. This counter 
      will only increment if the dropConditions 
      attribute includes the cantCopyTo value."
::= { mscVrNsStatsEntry 9 }

mscVrNsDroppedNullFilter OBJECT-TYPE
   SYNTAX     Counter32 
   ACCESS     read-only
   STATUS     mandatory
   DESCRIPTION
     "This counts the total number of packets that 
      were dropped because the packet passed through a filter point into which 
      was provisioned a filter which was never defined in a file loaded into 
      NetSentry. Such filter points have atached to the the so-call Null Filter, 
      which will either succeed or fail all packets passing through it, 
      depending on whether or not the dropConditions attribute includes the 
      nullFilter value."
::= { mscVrNsStatsEntry 10 }


-- Vr/<string> NetSentry File/<filename>
-- This component's instance value is a single filename to be compiled. 
-- The file must reside in
-- /provisioning/netsentry/prov
-- in order to be compiled at provisioning activate time, but in
-- /provisioning/netsentry/oper
-- to be recompiled with the ReLoad verb. This is to provide the same sort 
-- of protections that the provisioning system gives with its activate-
-- confirm-commit sequence.

mscVrNsFile OBJECT IDENTIFIER ::= { mscVrNs 2 }



mscVrNsFileRowStatusTable OBJECT-TYPE
   SYNTAX     SEQUENCE OF MscVrNsFileRowStatusEntry
   ACCESS     not-accessible
   STATUS     mandatory
   DESCRIPTION
     "This entry controls the addition and deletion of 
      mscVrNsFile components."
::= { mscVrNsFile 1 }

mscVrNsFileRowStatusEntry OBJECT-TYPE
   SYNTAX     MscVrNsFileRowStatusEntry
   ACCESS     not-accessible
   STATUS     mandatory
   DESCRIPTION
     "A single entry in the table represents a single 
      mscVrNsFile component."
   INDEX {
      mscVrIndex,
      mscVrNsIndex,
      mscVrNsFileIndex }
::= { mscVrNsFileRowStatusTable 1 }

MscVrNsFileRowStatusEntry ::= SEQUENCE {
   mscVrNsFileRowStatus
      RowStatus,
   mscVrNsFileComponentName
      DisplayString,
   mscVrNsFileStorageType
      StorageType,
   mscVrNsFileIndex
      AsciiStringIndex }

mscVrNsFileRowStatus OBJECT-TYPE
   SYNTAX     RowStatus 
   ACCESS     read-write
   STATUS     mandatory
   DESCRIPTION
     "This variable is used as the basis for SNMP naming of
      mscVrNsFile components.
      These components can be added and deleted."
::= { mscVrNsFileRowStatusEntry 1 }

mscVrNsFileComponentName OBJECT-TYPE
   SYNTAX     DisplayString 
   ACCESS     read-only
   STATUS     mandatory
   DESCRIPTION
     "This variable provides the component's string name for
      use with the ASCII Console Interface"
::= { mscVrNsFileRowStatusEntry 2 }

mscVrNsFileStorageType OBJECT-TYPE
   SYNTAX     StorageType 
   ACCESS     read-only
   STATUS     mandatory
   DESCRIPTION
     "This variable represents the storage type value for the
      mscVrNsFile tables."
::= { mscVrNsFileRowStatusEntry 4 }

mscVrNsFileIndex OBJECT-TYPE
   SYNTAX     AsciiStringIndex (SIZE (1..64))
   ACCESS     not-accessible
   STATUS     mandatory
   DESCRIPTION
     "This variable represents the index for the mscVrNsFile tables."
::= { mscVrNsFileRowStatusEntry 10 }

mscVrNsFileOperTable OBJECT-TYPE
   SYNTAX     SEQUENCE OF MscVrNsFileOperEntry
   ACCESS     not-accessible
   STATUS     mandatory
   DESCRIPTION
     "This holds hold a single compiler error message."
::= { mscVrNsFile 10 }

mscVrNsFileOperEntry OBJECT-TYPE
   SYNTAX     MscVrNsFileOperEntry
   ACCESS     not-accessible
   STATUS     mandatory
   DESCRIPTION
     "An entry in the mscVrNsFileOperTable."
   INDEX {
      mscVrIndex,
      mscVrNsIndex,
      mscVrNsFileIndex }
::= { mscVrNsFileOperTable 1 }

MscVrNsFileOperEntry ::= SEQUENCE {
   mscVrNsFileCompilerErrorMsg
      AsciiString }

mscVrNsFileCompilerErrorMsg OBJECT-TYPE
   SYNTAX     AsciiString (SIZE (1..80))
   ACCESS     read-only
   STATUS     mandatory
   DESCRIPTION
     "This attribute contains a single string holding the compiler error which 
      caused the compile to fail. In the event that the file is recompiled (using 
      the RELoad verb), the value of this will change, to reflect the new error, 
      if any was encountered, or no error, if the compile was successful."
   DEFVAL     { '4e6f204572726f72'H }  -- "No Error"
::= { mscVrNsFileOperEntry 1 }


-- Vr/<string> NetSentry Engine/n
-- The existence of this component represents the presence of NetSentry on 
-- a particular Logical Processor. Each Engine component must correspond 
-- to a matching Lp component. If NetSentry filtering is needed on some 
-- Lp, a corresponding Engine must be provisioned.

mscVrNsEngine OBJECT IDENTIFIER ::= { mscVrNs 3 }



mscVrNsEngineRowStatusTable OBJECT-TYPE
   SYNTAX     SEQUENCE OF MscVrNsEngineRowStatusEntry
   ACCESS     not-accessible
   STATUS     mandatory
   DESCRIPTION
     "This entry controls the addition and deletion of 
      mscVrNsEngine components."
::= { mscVrNsEngine 1 }

mscVrNsEngineRowStatusEntry OBJECT-TYPE
   SYNTAX     MscVrNsEngineRowStatusEntry
   ACCESS     not-accessible
   STATUS     mandatory
   DESCRIPTION
     "A single entry in the table represents a single 
      mscVrNsEngine component."
   INDEX {
      mscVrIndex,
      mscVrNsIndex,
      mscVrNsEngineIndex }
::= { mscVrNsEngineRowStatusTable 1 }

MscVrNsEngineRowStatusEntry ::= SEQUENCE {
   mscVrNsEngineRowStatus
      RowStatus,
   mscVrNsEngineComponentName
      DisplayString,
   mscVrNsEngineStorageType
      StorageType,
   mscVrNsEngineIndex
      Integer32 }

mscVrNsEngineRowStatus OBJECT-TYPE
   SYNTAX     RowStatus 
   ACCESS     read-write
   STATUS     mandatory
   DESCRIPTION
     "This variable is used as the basis for SNMP naming of
      mscVrNsEngine components.
      These components can be added and deleted."
::= { mscVrNsEngineRowStatusEntry 1 }

mscVrNsEngineComponentName OBJECT-TYPE
   SYNTAX     DisplayString 
   ACCESS     read-only
   STATUS     mandatory
   DESCRIPTION
     "This variable provides the component's string name for
      use with the ASCII Console Interface"
::= { mscVrNsEngineRowStatusEntry 2 }

mscVrNsEngineStorageType OBJECT-TYPE
   SYNTAX     StorageType 
   ACCESS     read-only
   STATUS     mandatory
   DESCRIPTION
     "This variable represents the storage type value for the
      mscVrNsEngine tables."
::= { mscVrNsEngineRowStatusEntry 4 }

mscVrNsEngineIndex OBJECT-TYPE
   SYNTAX     Integer32 (0..15)
   ACCESS     not-accessible
   STATUS     mandatory
   DESCRIPTION
     "This variable represents the index for the mscVrNsEngine tables."
::= { mscVrNsEngineRowStatusEntry 10 }


-- Vr/<string> NetSentry IPStats
-- This component holds all the statistics gathered for the IP protocol. If 
-- IPStatistics is provisioned, NetSentry statistics gathering actions will 
-- gather statistics for all IP packets to which they apply.

mscVrNsIPStats OBJECT IDENTIFIER ::= { mscVrNs 4 }



mscVrNsIPStatsRowStatusTable OBJECT-TYPE
   SYNTAX     SEQUENCE OF MscVrNsIPStatsRowStatusEntry
   ACCESS     not-accessible
   STATUS     mandatory
   DESCRIPTION
     "This entry controls the addition and deletion of 
      mscVrNsIPStats components."
::= { mscVrNsIPStats 1 }

mscVrNsIPStatsRowStatusEntry OBJECT-TYPE
   SYNTAX     MscVrNsIPStatsRowStatusEntry
   ACCESS     not-accessible
   STATUS     mandatory
   DESCRIPTION
     "A single entry in the table represents a single 
      mscVrNsIPStats component."
   INDEX {
      mscVrIndex,
      mscVrNsIndex,
      mscVrNsIPStatsIndex }
::= { mscVrNsIPStatsRowStatusTable 1 }

MscVrNsIPStatsRowStatusEntry ::= SEQUENCE {
   mscVrNsIPStatsRowStatus
      RowStatus,
   mscVrNsIPStatsComponentName
      DisplayString,
   mscVrNsIPStatsStorageType
      StorageType,
   mscVrNsIPStatsIndex
      NonReplicated }

mscVrNsIPStatsRowStatus OBJECT-TYPE
   SYNTAX     RowStatus 
   ACCESS     read-write
   STATUS     mandatory
   DESCRIPTION
     "This variable is used as the basis for SNMP naming of
      mscVrNsIPStats components.
      These components can be added and deleted."
::= { mscVrNsIPStatsRowStatusEntry 1 }

mscVrNsIPStatsComponentName OBJECT-TYPE
   SYNTAX     DisplayString 
   ACCESS     read-only
   STATUS     mandatory
   DESCRIPTION
     "This variable provides the component's string name for
      use with the ASCII Console Interface"
::= { mscVrNsIPStatsRowStatusEntry 2 }

mscVrNsIPStatsStorageType OBJECT-TYPE
   SYNTAX     StorageType 
   ACCESS     read-only
   STATUS     mandatory
   DESCRIPTION
     "This variable represents the storage type value for the
      mscVrNsIPStats tables."
::= { mscVrNsIPStatsRowStatusEntry 4 }

mscVrNsIPStatsIndex OBJECT-TYPE
   SYNTAX     NonReplicated 
   ACCESS     not-accessible
   STATUS     mandatory
   DESCRIPTION
     "This variable represents the index for the mscVrNsIPStats tables."
::= { mscVrNsIPStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

mscVrNsIPStatsAddrStat OBJECT IDENTIFIER ::= { mscVrNsIPStats 2 }



mscVrNsIPStatsAddrStatRowStatusTable OBJECT-TYPE
   SYNTAX     SEQUENCE OF MscVrNsIPStatsAddrStatRowStatusEntry
   ACCESS     not-accessible
   STATUS     mandatory
   DESCRIPTION
     "*** THIS TABLE CURRENTLY NOT IMPLEMENTED ***

      This entry controls the addition and deletion of 
      mscVrNsIPStatsAddrStat components."
::= { mscVrNsIPStatsAddrStat 1 }

mscVrNsIPStatsAddrStatRowStatusEntry OBJECT-TYPE
   SYNTAX     MscVrNsIPStatsAddrStatRowStatusEntry
   ACCESS     not-accessible
   STATUS     mandatory
   DESCRIPTION
     "A single entry in the table represents a single 
      mscVrNsIPStatsAddrStat component."
   INDEX {
      mscVrIndex,
      mscVrNsIndex,
      mscVrNsIPStatsIndex,
      mscVrNsIPStatsAddrStatSourceAddressIndex,
      mscVrNsIPStatsAddrStatDestinationAddressIndex }
::= { mscVrNsIPStatsAddrStatRowStatusTable 1 }

MscVrNsIPStatsAddrStatRowStatusEntry ::= SEQUENCE {
   mscVrNsIPStatsAddrStatRowStatus
      RowStatus,
   mscVrNsIPStatsAddrStatComponentName
      DisplayString,
   mscVrNsIPStatsAddrStatStorageType
      StorageType,
   mscVrNsIPStatsAddrStatSourceAddressIndex
      AsciiStringIndex,
   mscVrNsIPStatsAddrStatDestinationAddressIndex
      AsciiStringIndex }

mscVrNsIPStatsAddrStatRowStatus OBJECT-TYPE
   SYNTAX     RowStatus 
   ACCESS     read-only
   STATUS     mandatory
   DESCRIPTION
     "This variable is used as the basis for SNMP naming of
      mscVrNsIPStatsAddrStat components.
      These components cannot be added nor deleted."
::= { mscVrNsIPStatsAddrStatRowStatusEntry 1 }

mscVrNsIPStatsAddrStatComponentName OBJECT-TYPE
   SYNTAX     DisplayString 
   ACCESS     read-only
   STATUS     mandatory
   DESCRIPTION
     "This variable provides the component's string name for
      use with the ASCII Console Interface"
::= { mscVrNsIPStatsAddrStatRowStatusEntry 2 }

mscVrNsIPStatsAddrStatStorageType OBJECT-TYPE
   SYNTAX     StorageType 
   ACCESS     read-only
   STATUS     mandatory
   DESCRIPTION
     "This variable represents the storage type value for the
      mscVrNsIPStatsAddrStat tables."
::= { mscVrNsIPStatsAddrStatRowStatusEntry 4 }

mscVrNsIPStatsAddrStatSourceAddressIndex OBJECT-TYPE
   SYNTAX     AsciiStringIndex (SIZE (1..32))
   ACCESS     not-accessible
   STATUS     mandatory
   DESCRIPTION
     "This variable represents an index for the mscVrNsIPStatsAddrStat tables."
::= { mscVrNsIPStatsAddrStatRowStatusEntry 10 }

mscVrNsIPStatsAddrStatDestinationAddressIndex OBJECT-TYPE
   SYNTAX     AsciiStringIndex (SIZE (1..32))
   ACCESS     not-accessible
   STATUS     mandatory
   DESCRIPTION
     "This variable represents an index for the mscVrNsIPStatsAddrStat tables."
::= { mscVrNsIPStatsAddrStatRowStatusEntry 11 }

mscVrNsIPStatsAddrStatStatsTable OBJECT-TYPE
   SYNTAX     SEQUENCE OF MscVrNsIPStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { mscVrNsIPStatsAddrStat 10 }

mscVrNsIPStatsAddrStatStatsEntry OBJECT-TYPE
   SYNTAX     MscVrNsIPStatsAddrStatStatsEntry
   ACCESS     not-accessible
   STATUS     mandatory
   DESCRIPTION
     "An entry in the mscVrNsIPStatsAddrStatStatsTable."
   INDEX {
      mscVrIndex,
      mscVrNsIndex,
      mscVrNsIPStatsIndex,
      mscVrNsIPStatsAddrStatSourceAddressIndex,
      mscVrNsIPStatsAddrStatDestinationAddressIndex }
::= { mscVrNsIPStatsAddrStatStatsTable 1 }

MscVrNsIPStatsAddrStatStatsEntry ::= SEQUENCE {
   mscVrNsIPStatsAddrStatPacketCount
      Counter32,
   mscVrNsIPStatsAddrStatByteCount
      Counter32,
   mscVrNsIPStatsAddrStatCounter1
      Counter32,
   mscVrNsIPStatsAddrStatCounter2
      Counter32 }

mscVrNsIPStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { mscVrNsIPStatsAddrStatStatsEntry 1 }

mscVrNsIPStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { mscVrNsIPStatsAddrStatStatsEntry 2 }

mscVrNsIPStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { mscVrNsIPStatsAddrStatStatsEntry 3 }

mscVrNsIPStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { mscVrNsIPStatsAddrStatStatsEntry 4 }


-- Vr/<string> NetSentry IPXStats
-- This component holds all the statistics gathered for the IPX protocol. If 
-- IPXStatistics is provisioned, NetSentry statistics gathering actions will 
-- gather statistics for all IPX packets to which they apply.

mscVrNsIPXStats OBJECT IDENTIFIER ::= { mscVrNs 5 }



mscVrNsIPXStatsRowStatusTable OBJECT-TYPE
   SYNTAX     SEQUENCE OF MscVrNsIPXStatsRowStatusEntry
   ACCESS     not-accessible
   STATUS     mandatory
   DESCRIPTION
     "This entry controls the addition and deletion of 
      mscVrNsIPXStats components."
::= { mscVrNsIPXStats 1 }

mscVrNsIPXStatsRowStatusEntry OBJECT-TYPE
   SYNTAX     MscVrNsIPXStatsRowStatusEntry
   ACCESS     not-accessible
   STATUS     mandatory
   DESCRIPTION
     "A single entry in the table represents a single 
      mscVrNsIPXStats component."
   INDEX {
      mscVrIndex,
      mscVrNsIndex,
      mscVrNsIPXStatsIndex }
::= { mscVrNsIPXStatsRowStatusTable 1 }

MscVrNsIPXStatsRowStatusEntry ::= SEQUENCE {
   mscVrNsIPXStatsRowStatus
      RowStatus,
   mscVrNsIPXStatsComponentName
      DisplayString,
   mscVrNsIPXStatsStorageType
      StorageType,
   mscVrNsIPXStatsIndex
      NonReplicated }

mscVrNsIPXStatsRowStatus OBJECT-TYPE
   SYNTAX     RowStatus 
   ACCESS     read-write
   STATUS     mandatory
   DESCRIPTION
     "This variable is used as the basis for SNMP naming of
      mscVrNsIPXStats components.
      These components can be added and deleted."
::= { mscVrNsIPXStatsRowStatusEntry 1 }

mscVrNsIPXStatsComponentName OBJECT-TYPE
   SYNTAX     DisplayString 
   ACCESS     read-only
   STATUS     mandatory
   DESCRIPTION
     "This variable provides the component's string name for
      use with the ASCII Console Interface"
::= { mscVrNsIPXStatsRowStatusEntry 2 }

mscVrNsIPXStatsStorageType OBJECT-TYPE
   SYNTAX     StorageType 
   ACCESS     read-only
   STATUS     mandatory
   DESCRIPTION
     "This variable represents the storage type value for the
      mscVrNsIPXStats tables."
::= { mscVrNsIPXStatsRowStatusEntry 4 }

mscVrNsIPXStatsIndex OBJECT-TYPE
   SYNTAX     NonReplicated 
   ACCESS     not-accessible
   STATUS     mandatory
   DESCRIPTION
     "This variable represents the index for the mscVrNsIPXStats tables."
::= { mscVrNsIPXStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

mscVrNsIPXStatsAddrStat OBJECT IDENTIFIER ::= { mscVrNsIPXStats 2 }



mscVrNsIPXStatsAddrStatRowStatusTable OBJECT-TYPE
   SYNTAX     SEQUENCE OF MscVrNsIPXStatsAddrStatRowStatusEntry
   ACCESS     not-accessible
   STATUS     mandatory
   DESCRIPTION
     "*** THIS TABLE CURRENTLY NOT IMPLEMENTED ***

      This entry controls the addition and deletion of 
      mscVrNsIPXStatsAddrStat components."
::= { mscVrNsIPXStatsAddrStat 1 }

mscVrNsIPXStatsAddrStatRowStatusEntry OBJECT-TYPE
   SYNTAX     MscVrNsIPXStatsAddrStatRowStatusEntry
   ACCESS     not-accessible
   STATUS     mandatory
   DESCRIPTION
     "A single entry in the table represents a single 
      mscVrNsIPXStatsAddrStat component."
   INDEX {
      mscVrIndex,
      mscVrNsIndex,
      mscVrNsIPXStatsIndex,
      mscVrNsIPXStatsAddrStatSourceAddressIndex,
      mscVrNsIPXStatsAddrStatDestinationAddressIndex }
::= { mscVrNsIPXStatsAddrStatRowStatusTable 1 }

MscVrNsIPXStatsAddrStatRowStatusEntry ::= SEQUENCE {
   mscVrNsIPXStatsAddrStatRowStatus
      RowStatus,
   mscVrNsIPXStatsAddrStatComponentName
      DisplayString,
   mscVrNsIPXStatsAddrStatStorageType
      StorageType,
   mscVrNsIPXStatsAddrStatSourceAddressIndex
      AsciiStringIndex,
   mscVrNsIPXStatsAddrStatDestinationAddressIndex
      AsciiStringIndex }

mscVrNsIPXStatsAddrStatRowStatus OBJECT-TYPE
   SYNTAX     RowStatus 
   ACCESS     read-only
   STATUS     mandatory
   DESCRIPTION
     "This variable is used as the basis for SNMP naming of
      mscVrNsIPXStatsAddrStat components.
      These components cannot be added nor deleted."
::= { mscVrNsIPXStatsAddrStatRowStatusEntry 1 }

mscVrNsIPXStatsAddrStatComponentName OBJECT-TYPE
   SYNTAX     DisplayString 
   ACCESS     read-only
   STATUS     mandatory
   DESCRIPTION
     "This variable provides the component's string name for
      use with the ASCII Console Interface"
::= { mscVrNsIPXStatsAddrStatRowStatusEntry 2 }

mscVrNsIPXStatsAddrStatStorageType OBJECT-TYPE
   SYNTAX     StorageType 
   ACCESS     read-only
   STATUS     mandatory
   DESCRIPTION
     "This variable represents the storage type value for the
      mscVrNsIPXStatsAddrStat tables."
::= { mscVrNsIPXStatsAddrStatRowStatusEntry 4 }

mscVrNsIPXStatsAddrStatSourceAddressIndex OBJECT-TYPE
   SYNTAX     AsciiStringIndex (SIZE (1..32))
   ACCESS     not-accessible
   STATUS     mandatory
   DESCRIPTION
     "This variable represents an index for the mscVrNsIPXStatsAddrStat tables."
::= { mscVrNsIPXStatsAddrStatRowStatusEntry 10 }

mscVrNsIPXStatsAddrStatDestinationAddressIndex OBJECT-TYPE
   SYNTAX     AsciiStringIndex (SIZE (1..32))
   ACCESS     not-accessible
   STATUS     mandatory
   DESCRIPTION
     "This variable represents an index for the mscVrNsIPXStatsAddrStat tables."
::= { mscVrNsIPXStatsAddrStatRowStatusEntry 11 }

mscVrNsIPXStatsAddrStatStatsTable OBJECT-TYPE
   SYNTAX     SEQUENCE OF MscVrNsIPXStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { mscVrNsIPXStatsAddrStat 10 }

mscVrNsIPXStatsAddrStatStatsEntry OBJECT-TYPE
   SYNTAX     MscVrNsIPXStatsAddrStatStatsEntry
   ACCESS     not-accessible
   STATUS     mandatory
   DESCRIPTION
     "An entry in the mscVrNsIPXStatsAddrStatStatsTable."
   INDEX {
      mscVrIndex,
      mscVrNsIndex,
      mscVrNsIPXStatsIndex,
      mscVrNsIPXStatsAddrStatSourceAddressIndex,
      mscVrNsIPXStatsAddrStatDestinationAddressIndex }
::= { mscVrNsIPXStatsAddrStatStatsTable 1 }

MscVrNsIPXStatsAddrStatStatsEntry ::= SEQUENCE {
   mscVrNsIPXStatsAddrStatPacketCount
      Counter32,
   mscVrNsIPXStatsAddrStatByteCount
      Counter32,
   mscVrNsIPXStatsAddrStatCounter1
      Counter32,
   mscVrNsIPXStatsAddrStatCounter2
      Counter32 }

mscVrNsIPXStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { mscVrNsIPXStatsAddrStatStatsEntry 1 }

mscVrNsIPXStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { mscVrNsIPXStatsAddrStatStatsEntry 2 }

mscVrNsIPXStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { mscVrNsIPXStatsAddrStatStatsEntry 3 }

mscVrNsIPXStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { mscVrNsIPXStatsAddrStatStatsEntry 4 }


-- Vr/<string> NetSentry ATStats
-- This component holds all the statistics gathered for the AppleTalk 
-- protocol. If AppleTalkStatistics is provisioned, NetSentry statistics 
-- gathering actions will gather statistics for AppleTalk packets to which 
-- they apply.

mscVrNsATStats OBJECT IDENTIFIER ::= { mscVrNs 6 }



mscVrNsATStatsRowStatusTable OBJECT-TYPE
   SYNTAX     SEQUENCE OF MscVrNsATStatsRowStatusEntry
   ACCESS     not-accessible
   STATUS     mandatory
   DESCRIPTION
     "This entry controls the addition and deletion of 
      mscVrNsATStats components."
::= { mscVrNsATStats 1 }

mscVrNsATStatsRowStatusEntry OBJECT-TYPE
   SYNTAX     MscVrNsATStatsRowStatusEntry
   ACCESS     not-accessible
   STATUS     mandatory
   DESCRIPTION
     "A single entry in the table represents a single 
      mscVrNsATStats component."
   INDEX {
      mscVrIndex,
      mscVrNsIndex,
      mscVrNsATStatsIndex }
::= { mscVrNsATStatsRowStatusTable 1 }

MscVrNsATStatsRowStatusEntry ::= SEQUENCE {
   mscVrNsATStatsRowStatus
      RowStatus,
   mscVrNsATStatsComponentName
      DisplayString,
   mscVrNsATStatsStorageType
      StorageType,
   mscVrNsATStatsIndex
      NonReplicated }

mscVrNsATStatsRowStatus OBJECT-TYPE
   SYNTAX     RowStatus 
   ACCESS     read-write
   STATUS     mandatory
   DESCRIPTION
     "This variable is used as the basis for SNMP naming of
      mscVrNsATStats components.
      These components can be added and deleted."
::= { mscVrNsATStatsRowStatusEntry 1 }

mscVrNsATStatsComponentName OBJECT-TYPE
   SYNTAX     DisplayString 
   ACCESS     read-only
   STATUS     mandatory
   DESCRIPTION
     "This variable provides the component's string name for
      use with the ASCII Console Interface"
::= { mscVrNsATStatsRowStatusEntry 2 }

mscVrNsATStatsStorageType OBJECT-TYPE
   SYNTAX     StorageType 
   ACCESS     read-only
   STATUS     mandatory
   DESCRIPTION
     "This variable represents the storage type value for the
      mscVrNsATStats tables."
::= { mscVrNsATStatsRowStatusEntry 4 }

mscVrNsATStatsIndex OBJECT-TYPE
   SYNTAX     NonReplicated 
   ACCESS     not-accessible
   STATUS     mandatory
   DESCRIPTION
     "This variable represents the index for the mscVrNsATStats tables."
::= { mscVrNsATStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

mscVrNsATStatsAddrStat OBJECT IDENTIFIER ::= { mscVrNsATStats 2 }



mscVrNsATStatsAddrStatRowStatusTable OBJECT-TYPE
   SYNTAX     SEQUENCE OF MscVrNsATStatsAddrStatRowStatusEntry
   ACCESS     not-accessible
   STATUS     mandatory
   DESCRIPTION
     "*** THIS TABLE CURRENTLY NOT IMPLEMENTED ***

      This entry controls the addition and deletion of 
      mscVrNsATStatsAddrStat components."
::= { mscVrNsATStatsAddrStat 1 }

mscVrNsATStatsAddrStatRowStatusEntry OBJECT-TYPE
   SYNTAX     MscVrNsATStatsAddrStatRowStatusEntry
   ACCESS     not-accessible
   STATUS     mandatory
   DESCRIPTION
     "A single entry in the table represents a single 
      mscVrNsATStatsAddrStat component."
   INDEX {
      mscVrIndex,
      mscVrNsIndex,
      mscVrNsATStatsIndex,
      mscVrNsATStatsAddrStatSourceAddressIndex,
      mscVrNsATStatsAddrStatDestinationAddressIndex }
::= { mscVrNsATStatsAddrStatRowStatusTable 1 }

MscVrNsATStatsAddrStatRowStatusEntry ::= SEQUENCE {
   mscVrNsATStatsAddrStatRowStatus
      RowStatus,
   mscVrNsATStatsAddrStatComponentName
      DisplayString,
   mscVrNsATStatsAddrStatStorageType
      StorageType,
   mscVrNsATStatsAddrStatSourceAddressIndex
      AsciiStringIndex,
   mscVrNsATStatsAddrStatDestinationAddressIndex
      AsciiStringIndex }

mscVrNsATStatsAddrStatRowStatus OBJECT-TYPE
   SYNTAX     RowStatus 
   ACCESS     read-only
   STATUS     mandatory
   DESCRIPTION
     "This variable is used as the basis for SNMP naming of
      mscVrNsATStatsAddrStat components.
      These components cannot be added nor deleted."
::= { mscVrNsATStatsAddrStatRowStatusEntry 1 }

mscVrNsATStatsAddrStatComponentName OBJECT-TYPE
   SYNTAX     DisplayString 
   ACCESS     read-only
   STATUS     mandatory
   DESCRIPTION
     "This variable provides the component's string name for
      use with the ASCII Console Interface"
::= { mscVrNsATStatsAddrStatRowStatusEntry 2 }

mscVrNsATStatsAddrStatStorageType OBJECT-TYPE
   SYNTAX     StorageType 
   ACCESS     read-only
   STATUS     mandatory
   DESCRIPTION
     "This variable represents the storage type value for the
      mscVrNsATStatsAddrStat tables."
::= { mscVrNsATStatsAddrStatRowStatusEntry 4 }

mscVrNsATStatsAddrStatSourceAddressIndex OBJECT-TYPE
   SYNTAX     AsciiStringIndex (SIZE (1..32))
   ACCESS     not-accessible
   STATUS     mandatory
   DESCRIPTION
     "This variable represents an index for the mscVrNsATStatsAddrStat tables."
::= { mscVrNsATStatsAddrStatRowStatusEntry 10 }

mscVrNsATStatsAddrStatDestinationAddressIndex OBJECT-TYPE
   SYNTAX     AsciiStringIndex (SIZE (1..32))
   ACCESS     not-accessible
   STATUS     mandatory
   DESCRIPTION
     "This variable represents an index for the mscVrNsATStatsAddrStat tables."
::= { mscVrNsATStatsAddrStatRowStatusEntry 11 }

mscVrNsATStatsAddrStatStatsTable OBJECT-TYPE
   SYNTAX     SEQUENCE OF MscVrNsATStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { mscVrNsATStatsAddrStat 10 }

mscVrNsATStatsAddrStatStatsEntry OBJECT-TYPE
   SYNTAX     MscVrNsATStatsAddrStatStatsEntry
   ACCESS     not-accessible
   STATUS     mandatory
   DESCRIPTION
     "An entry in the mscVrNsATStatsAddrStatStatsTable."
   INDEX {
      mscVrIndex,
      mscVrNsIndex,
      mscVrNsATStatsIndex,
      mscVrNsATStatsAddrStatSourceAddressIndex,
      mscVrNsATStatsAddrStatDestinationAddressIndex }
::= { mscVrNsATStatsAddrStatStatsTable 1 }

MscVrNsATStatsAddrStatStatsEntry ::= SEQUENCE {
   mscVrNsATStatsAddrStatPacketCount
      Counter32,
   mscVrNsATStatsAddrStatByteCount
      Counter32,
   mscVrNsATStatsAddrStatCounter1
      Counter32,
   mscVrNsATStatsAddrStatCounter2
      Counter32 }

mscVrNsATStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { mscVrNsATStatsAddrStatStatsEntry 1 }

mscVrNsATStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { mscVrNsATStatsAddrStatStatsEntry 2 }

mscVrNsATStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { mscVrNsATStatsAddrStatStatsEntry 3 }

mscVrNsATStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { mscVrNsATStatsAddrStatStatsEntry 4 }


-- Vr/<string> NetSentry DNStats
-- This component holds all the statistics gathered for the DECnet 
-- protocol. If DECnetStatistics is provisioned, NetSentry statistics 
-- gathering actions will gather statistics for DECnet packets to which they 
-- apply.

mscVrNsDNStats OBJECT IDENTIFIER ::= { mscVrNs 7 }



mscVrNsDNStatsRowStatusTable OBJECT-TYPE
   SYNTAX     SEQUENCE OF MscVrNsDNStatsRowStatusEntry
   ACCESS     not-accessible
   STATUS     mandatory
   DESCRIPTION
     "This entry controls the addition and deletion of 
      mscVrNsDNStats components."
::= { mscVrNsDNStats 1 }

mscVrNsDNStatsRowStatusEntry OBJECT-TYPE
   SYNTAX     MscVrNsDNStatsRowStatusEntry
   ACCESS     not-accessible
   STATUS     mandatory
   DESCRIPTION
     "A single entry in the table represents a single 
      mscVrNsDNStats component."
   INDEX {
      mscVrIndex,
      mscVrNsIndex,
      mscVrNsDNStatsIndex }
::= { mscVrNsDNStatsRowStatusTable 1 }

MscVrNsDNStatsRowStatusEntry ::= SEQUENCE {
   mscVrNsDNStatsRowStatus
      RowStatus,
   mscVrNsDNStatsComponentName
      DisplayString,
   mscVrNsDNStatsStorageType
      StorageType,
   mscVrNsDNStatsIndex
      NonReplicated }

mscVrNsDNStatsRowStatus OBJECT-TYPE
   SYNTAX     RowStatus 
   ACCESS     read-write
   STATUS     mandatory
   DESCRIPTION
     "This variable is used as the basis for SNMP naming of
      mscVrNsDNStats components.
      These components can be added and deleted."
::= { mscVrNsDNStatsRowStatusEntry 1 }

mscVrNsDNStatsComponentName OBJECT-TYPE
   SYNTAX     DisplayString 
   ACCESS     read-only
   STATUS     mandatory
   DESCRIPTION
     "This variable provides the component's string name for
      use with the ASCII Console Interface"
::= { mscVrNsDNStatsRowStatusEntry 2 }

mscVrNsDNStatsStorageType OBJECT-TYPE
   SYNTAX     StorageType 
   ACCESS     read-only
   STATUS     mandatory
   DESCRIPTION
     "This variable represents the storage type value for the
      mscVrNsDNStats tables."
::= { mscVrNsDNStatsRowStatusEntry 4 }

mscVrNsDNStatsIndex OBJECT-TYPE
   SYNTAX     NonReplicated 
   ACCESS     not-accessible
   STATUS     mandatory
   DESCRIPTION
     "This variable represents the index for the mscVrNsDNStats tables."
::= { mscVrNsDNStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

mscVrNsDNStatsAddrStat OBJECT IDENTIFIER ::= { mscVrNsDNStats 2 }



mscVrNsDNStatsAddrStatRowStatusTable OBJECT-TYPE
   SYNTAX     SEQUENCE OF MscVrNsDNStatsAddrStatRowStatusEntry
   ACCESS     not-accessible
   STATUS     mandatory
   DESCRIPTION
     "*** THIS TABLE CURRENTLY NOT IMPLEMENTED ***

      This entry controls the addition and deletion of 
      mscVrNsDNStatsAddrStat components."
::= { mscVrNsDNStatsAddrStat 1 }

mscVrNsDNStatsAddrStatRowStatusEntry OBJECT-TYPE
   SYNTAX     MscVrNsDNStatsAddrStatRowStatusEntry
   ACCESS     not-accessible
   STATUS     mandatory
   DESCRIPTION
     "A single entry in the table represents a single 
      mscVrNsDNStatsAddrStat component."
   INDEX {
      mscVrIndex,
      mscVrNsIndex,
      mscVrNsDNStatsIndex,
      mscVrNsDNStatsAddrStatSourceAddressIndex,
      mscVrNsDNStatsAddrStatDestinationAddressIndex }
::= { mscVrNsDNStatsAddrStatRowStatusTable 1 }

MscVrNsDNStatsAddrStatRowStatusEntry ::= SEQUENCE {
   mscVrNsDNStatsAddrStatRowStatus
      RowStatus,
   mscVrNsDNStatsAddrStatComponentName
      DisplayString,
   mscVrNsDNStatsAddrStatStorageType
      StorageType,
   mscVrNsDNStatsAddrStatSourceAddressIndex
      AsciiStringIndex,
   mscVrNsDNStatsAddrStatDestinationAddressIndex
      AsciiStringIndex }

mscVrNsDNStatsAddrStatRowStatus OBJECT-TYPE
   SYNTAX     RowStatus 
   ACCESS     read-only
   STATUS     mandatory
   DESCRIPTION
     "This variable is used as the basis for SNMP naming of
      mscVrNsDNStatsAddrStat components.
      These components cannot be added nor deleted."
::= { mscVrNsDNStatsAddrStatRowStatusEntry 1 }

mscVrNsDNStatsAddrStatComponentName OBJECT-TYPE
   SYNTAX     DisplayString 
   ACCESS     read-only
   STATUS     mandatory
   DESCRIPTION
     "This variable provides the component's string name for
      use with the ASCII Console Interface"
::= { mscVrNsDNStatsAddrStatRowStatusEntry 2 }

mscVrNsDNStatsAddrStatStorageType OBJECT-TYPE
   SYNTAX     StorageType 
   ACCESS     read-only
   STATUS     mandatory
   DESCRIPTION
     "This variable represents the storage type value for the
      mscVrNsDNStatsAddrStat tables."
::= { mscVrNsDNStatsAddrStatRowStatusEntry 4 }

mscVrNsDNStatsAddrStatSourceAddressIndex OBJECT-TYPE
   SYNTAX     AsciiStringIndex (SIZE (1..32))
   ACCESS     not-accessible
   STATUS     mandatory
   DESCRIPTION
     "This variable represents an index for the mscVrNsDNStatsAddrStat tables."
::= { mscVrNsDNStatsAddrStatRowStatusEntry 10 }

mscVrNsDNStatsAddrStatDestinationAddressIndex OBJECT-TYPE
   SYNTAX     AsciiStringIndex (SIZE (1..32))
   ACCESS     not-accessible
   STATUS     mandatory
   DESCRIPTION
     "This variable represents an index for the mscVrNsDNStatsAddrStat tables."
::= { mscVrNsDNStatsAddrStatRowStatusEntry 11 }

mscVrNsDNStatsAddrStatStatsTable OBJECT-TYPE
   SYNTAX     SEQUENCE OF MscVrNsDNStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { mscVrNsDNStatsAddrStat 10 }

mscVrNsDNStatsAddrStatStatsEntry OBJECT-TYPE
   SYNTAX     MscVrNsDNStatsAddrStatStatsEntry
   ACCESS     not-accessible
   STATUS     mandatory
   DESCRIPTION
     "An entry in the mscVrNsDNStatsAddrStatStatsTable."
   INDEX {
      mscVrIndex,
      mscVrNsIndex,
      mscVrNsDNStatsIndex,
      mscVrNsDNStatsAddrStatSourceAddressIndex,
      mscVrNsDNStatsAddrStatDestinationAddressIndex }
::= { mscVrNsDNStatsAddrStatStatsTable 1 }

MscVrNsDNStatsAddrStatStatsEntry ::= SEQUENCE {
   mscVrNsDNStatsAddrStatPacketCount
      Counter32,
   mscVrNsDNStatsAddrStatByteCount
      Counter32,
   mscVrNsDNStatsAddrStatCounter1
      Counter32,
   mscVrNsDNStatsAddrStatCounter2
      Counter32 }

mscVrNsDNStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { mscVrNsDNStatsAddrStatStatsEntry 1 }

mscVrNsDNStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { mscVrNsDNStatsAddrStatStatsEntry 2 }

mscVrNsDNStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { mscVrNsDNStatsAddrStatStatsEntry 3 }

mscVrNsDNStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { mscVrNsDNStatsAddrStatStatsEntry 4 }


-- Vr/<string> NetSentry BrStats
-- This component holds all the statistics gathered for Bridged packets. If 
-- BridgingStatistics is provisioned, NetSentry statistics gathering actions 
-- will gather statistics for Bridged packets to which they apply.

mscVrNsBrStats OBJECT IDENTIFIER ::= { mscVrNs 8 }



mscVrNsBrStatsRowStatusTable OBJECT-TYPE
   SYNTAX     SEQUENCE OF MscVrNsBrStatsRowStatusEntry
   ACCESS     not-accessible
   STATUS     mandatory
   DESCRIPTION
     "This entry controls the addition and deletion of 
      mscVrNsBrStats components."
::= { mscVrNsBrStats 1 }

mscVrNsBrStatsRowStatusEntry OBJECT-TYPE
   SYNTAX     MscVrNsBrStatsRowStatusEntry
   ACCESS     not-accessible
   STATUS     mandatory
   DESCRIPTION
     "A single entry in the table represents a single 
      mscVrNsBrStats component."
   INDEX {
      mscVrIndex,
      mscVrNsIndex,
      mscVrNsBrStatsIndex }
::= { mscVrNsBrStatsRowStatusTable 1 }

MscVrNsBrStatsRowStatusEntry ::= SEQUENCE {
   mscVrNsBrStatsRowStatus
      RowStatus,
   mscVrNsBrStatsComponentName
      DisplayString,
   mscVrNsBrStatsStorageType
      StorageType,
   mscVrNsBrStatsIndex
      NonReplicated }

mscVrNsBrStatsRowStatus OBJECT-TYPE
   SYNTAX     RowStatus 
   ACCESS     read-write
   STATUS     mandatory
   DESCRIPTION
     "This variable is used as the basis for SNMP naming of
      mscVrNsBrStats components.
      These components can be added and deleted."
::= { mscVrNsBrStatsRowStatusEntry 1 }

mscVrNsBrStatsComponentName OBJECT-TYPE
   SYNTAX     DisplayString 
   ACCESS     read-only
   STATUS     mandatory
   DESCRIPTION
     "This variable provides the component's string name for
      use with the ASCII Console Interface"
::= { mscVrNsBrStatsRowStatusEntry 2 }

mscVrNsBrStatsStorageType OBJECT-TYPE
   SYNTAX     StorageType 
   ACCESS     read-only
   STATUS     mandatory
   DESCRIPTION
     "This variable represents the storage type value for the
      mscVrNsBrStats tables."
::= { mscVrNsBrStatsRowStatusEntry 4 }

mscVrNsBrStatsIndex OBJECT-TYPE
   SYNTAX     NonReplicated 
   ACCESS     not-accessible
   STATUS     mandatory
   DESCRIPTION
     "This variable represents the index for the mscVrNsBrStats tables."
::= { mscVrNsBrStatsRowStatusEntry 10 }

-- 
-- *** THIS SUBTREE CURRENTLY NOT IMPLEMENTED ***
-- 

-- Vr/<string> NetSentry IPStats AddrStat/128.12.3.7,-
-- This component holds statistics for a source address, a destination 
-- address, or a source address/destination address pair. This component 
-- may reside in one of a variety of by-protocol tables, each with a double 
-- index for rows. One index is the source address, one is the destination 
-- address. One of the indices may be a "-", which indicates that the other 
-- index is the relevent one. That is, a statistic referred to with source 
-- address "128.12.3.7" and destination address "-" is a statistic for packets 
-- originating from 128.12.3.7 alone.

mscVrNsBrStatsAddrStat OBJECT IDENTIFIER ::= { mscVrNsBrStats 2 }



mscVrNsBrStatsAddrStatRowStatusTable OBJECT-TYPE
   SYNTAX     SEQUENCE OF MscVrNsBrStatsAddrStatRowStatusEntry
   ACCESS     not-accessible
   STATUS     mandatory
   DESCRIPTION
     "*** THIS TABLE CURRENTLY NOT IMPLEMENTED ***

      This entry controls the addition and deletion of 
      mscVrNsBrStatsAddrStat components."
::= { mscVrNsBrStatsAddrStat 1 }

mscVrNsBrStatsAddrStatRowStatusEntry OBJECT-TYPE
   SYNTAX     MscVrNsBrStatsAddrStatRowStatusEntry
   ACCESS     not-accessible
   STATUS     mandatory
   DESCRIPTION
     "A single entry in the table represents a single 
      mscVrNsBrStatsAddrStat component."
   INDEX {
      mscVrIndex,
      mscVrNsIndex,
      mscVrNsBrStatsIndex,
      mscVrNsBrStatsAddrStatSourceAddressIndex,
      mscVrNsBrStatsAddrStatDestinationAddressIndex }
::= { mscVrNsBrStatsAddrStatRowStatusTable 1 }

MscVrNsBrStatsAddrStatRowStatusEntry ::= SEQUENCE {
   mscVrNsBrStatsAddrStatRowStatus
      RowStatus,
   mscVrNsBrStatsAddrStatComponentName
      DisplayString,
   mscVrNsBrStatsAddrStatStorageType
      StorageType,
   mscVrNsBrStatsAddrStatSourceAddressIndex
      AsciiStringIndex,
   mscVrNsBrStatsAddrStatDestinationAddressIndex
      AsciiStringIndex }

mscVrNsBrStatsAddrStatRowStatus OBJECT-TYPE
   SYNTAX     RowStatus 
   ACCESS     read-only
   STATUS     mandatory
   DESCRIPTION
     "This variable is used as the basis for SNMP naming of
      mscVrNsBrStatsAddrStat components.
      These components cannot be added nor deleted."
::= { mscVrNsBrStatsAddrStatRowStatusEntry 1 }

mscVrNsBrStatsAddrStatComponentName OBJECT-TYPE
   SYNTAX     DisplayString 
   ACCESS     read-only
   STATUS     mandatory
   DESCRIPTION
     "This variable provides the component's string name for
      use with the ASCII Console Interface"
::= { mscVrNsBrStatsAddrStatRowStatusEntry 2 }

mscVrNsBrStatsAddrStatStorageType OBJECT-TYPE
   SYNTAX     StorageType 
   ACCESS     read-only
   STATUS     mandatory
   DESCRIPTION
     "This variable represents the storage type value for the
      mscVrNsBrStatsAddrStat tables."
::= { mscVrNsBrStatsAddrStatRowStatusEntry 4 }

mscVrNsBrStatsAddrStatSourceAddressIndex OBJECT-TYPE
   SYNTAX     AsciiStringIndex (SIZE (1..32))
   ACCESS     not-accessible
   STATUS     mandatory
   DESCRIPTION
     "This variable represents an index for the mscVrNsBrStatsAddrStat tables."
::= { mscVrNsBrStatsAddrStatRowStatusEntry 10 }

mscVrNsBrStatsAddrStatDestinationAddressIndex OBJECT-TYPE
   SYNTAX     AsciiStringIndex (SIZE (1..32))
   ACCESS     not-accessible
   STATUS     mandatory
   DESCRIPTION
     "This variable represents an index for the mscVrNsBrStatsAddrStat tables."
::= { mscVrNsBrStatsAddrStatRowStatusEntry 11 }

mscVrNsBrStatsAddrStatStatsTable OBJECT-TYPE
   SYNTAX     SEQUENCE OF MscVrNsBrStatsAddrStatStatsEntry
   ACCESS     not-accessible
   STATUS     mandatory
   DESCRIPTION
     "*** THIS TABLE CURRENTLY NOT IMPLEMENTED ***

      This is the basic statistic used throughout NetSentry by-protocol 
      statistics gathering. It contains counters for total packets, total octets in 
      packets, and two user counters, counter_1 and counter_2."
::= { mscVrNsBrStatsAddrStat 10 }

mscVrNsBrStatsAddrStatStatsEntry OBJECT-TYPE
   SYNTAX     MscVrNsBrStatsAddrStatStatsEntry
   ACCESS     not-accessible
   STATUS     mandatory
   DESCRIPTION
     "An entry in the mscVrNsBrStatsAddrStatStatsTable."
   INDEX {
      mscVrIndex,
      mscVrNsIndex,
      mscVrNsBrStatsIndex,
      mscVrNsBrStatsAddrStatSourceAddressIndex,
      mscVrNsBrStatsAddrStatDestinationAddressIndex }
::= { mscVrNsBrStatsAddrStatStatsTable 1 }

MscVrNsBrStatsAddrStatStatsEntry ::= SEQUENCE {
   mscVrNsBrStatsAddrStatPacketCount
      Counter32,
   mscVrNsBrStatsAddrStatByteCount
      Counter32,
   mscVrNsBrStatsAddrStatCounter1
      Counter32,
   mscVrNsBrStatsAddrStatCounter2
      Counter32 }

mscVrNsBrStatsAddrStatPacketCount OBJECT-TYPE
   SYNTAX     Counter32 
   ACCESS     read-only
   STATUS     mandatory
   DESCRIPTION
     "This is the number of packets which caused the enclosing Statistics 
      group to to be incremented. This counter will wrap around to zero when 
      it exceeds its maximum value, 4294967295."
::= { mscVrNsBrStatsAddrStatStatsEntry 1 }

mscVrNsBrStatsAddrStatByteCount OBJECT-TYPE
   SYNTAX     Counter32 
   ACCESS     read-only
   STATUS     mandatory
   DESCRIPTION
     "This is the number of bytes in all the packets which caused the enclosing 
      Statistics group to be incremented. This counter will wrap around to 
      zero when it exceeds its maximum value, 4294967295."
::= { mscVrNsBrStatsAddrStatStatsEntry 2 }

mscVrNsBrStatsAddrStatCounter1 OBJECT-TYPE
   SYNTAX     Counter32 
   ACCESS     read-only
   STATUS     mandatory
   DESCRIPTION
     "This is the number of times a packet caused a counter_1 action to be 
      applied with reference to the enclosing Statistics group. This counter 
      will wrap around to zero when it exceeds its maximum value, 
      4294967295."
::= { mscVrNsBrStatsAddrStatStatsEntry 3 }

mscVrNsBrStatsAddrStatCounter2 OBJECT-TYPE
   SYNTAX     Counter32 
   ACCESS     read-only
   STATUS     mandatory
   DESCRIPTION
     "This is the number of times a packet caused a counter_2 action to be 
      applied with reference to the enclosing Statistics group. This counter 
      will wrap around to zero when it exceeds its maximum value, 
      4294967295."
::= { mscVrNsBrStatsAddrStatStatsEntry 4 }

-- 
-- *** THIS SUBTREE CURRENTLY NOT IMPLEMENTED ***
-- 

-- Vr/<string> NetSentry Filter/not_tcp,Filter
-- Each instance of this component names a single NetSentry Filter or other 
-- NetSentry data object.

mscVrNsFilter OBJECT IDENTIFIER ::= { mscVrNs 9 }



mscVrNsFilterRowStatusTable OBJECT-TYPE
   SYNTAX     SEQUENCE OF MscVrNsFilterRowStatusEntry
   ACCESS     not-accessible
   STATUS     mandatory
   DESCRIPTION
     "*** THIS TABLE CURRENTLY NOT IMPLEMENTED ***

      This entry controls the addition and deletion of 
      mscVrNsFilter components."
::= { mscVrNsFilter 1 }

mscVrNsFilterRowStatusEntry OBJECT-TYPE
   SYNTAX     MscVrNsFilterRowStatusEntry
   ACCESS     not-accessible
   STATUS     mandatory
   DESCRIPTION
     "A single entry in the table represents a single 
      mscVrNsFilter component."
   INDEX {
      mscVrIndex,
      mscVrNsIndex,
      mscVrNsFilterNameIndex,
      mscVrNsFilterKindIndex }
::= { mscVrNsFilterRowStatusTable 1 }

MscVrNsFilterRowStatusEntry ::= SEQUENCE {
   mscVrNsFilterRowStatus
      RowStatus,
   mscVrNsFilterComponentName
      DisplayString,
   mscVrNsFilterStorageType
      StorageType,
   mscVrNsFilterNameIndex
      AsciiStringIndex,
   mscVrNsFilterKindIndex
      INTEGER }

mscVrNsFilterRowStatus OBJECT-TYPE
   SYNTAX     RowStatus 
   ACCESS     read-only
   STATUS     mandatory
   DESCRIPTION
     "This variable is used as the basis for SNMP naming of
      mscVrNsFilter components.
      These components cannot be added nor deleted."
::= { mscVrNsFilterRowStatusEntry 1 }

mscVrNsFilterComponentName OBJECT-TYPE
   SYNTAX     DisplayString 
   ACCESS     read-only
   STATUS     mandatory
   DESCRIPTION
     "This variable provides the component's string name for
      use with the ASCII Console Interface"
::= { mscVrNsFilterRowStatusEntry 2 }

mscVrNsFilterStorageType OBJECT-TYPE
   SYNTAX     StorageType 
   ACCESS     read-only
   STATUS     mandatory
   DESCRIPTION
     "This variable represents the storage type value for the
      mscVrNsFilter tables."
::= { mscVrNsFilterRowStatusEntry 4 }

mscVrNsFilterNameIndex OBJECT-TYPE
   SYNTAX     AsciiStringIndex (SIZE (1..32))
   ACCESS     not-accessible
   STATUS     mandatory
   DESCRIPTION
     "This variable represents an index for the mscVrNsFilter tables."
::= { mscVrNsFilterRowStatusEntry 10 }

mscVrNsFilterKindIndex OBJECT-TYPE
   SYNTAX     INTEGER  {
                 filter(0),
                 pafSet(1),
                 compartment(2),
                 aesoData(3),
                 nleso(4),
                 aeso(5),
                 accreditTable(6),
                 setData(7),
                 metaFilter(8) }
   ACCESS     not-accessible
   STATUS     mandatory
   DESCRIPTION
     "This variable represents an index for the mscVrNsFilter tables."
::= { mscVrNsFilterRowStatusEntry 11 }

mscVrNsFilterStatsTable OBJECT-TYPE
   SYNTAX     SEQUENCE OF MscVrNsFilterStatsEntry
   ACCESS     not-accessible
   STATUS     mandatory
   DESCRIPTION
     "*** THIS TABLE CURRENTLY NOT IMPLEMENTED ***

      This group contains the various counters associated with a particular 
      filter definition. A packet being processed through a NetSentry filter will 
      encounter zero or more dispositions according to which elements of the 
      filter have patterns which match the packet. This group counts, for the 
      enclosing Filter, how many packets encountered each sort of disposition 
      while being processed through the filter."
::= { mscVrNsFilter 10 }

mscVrNsFilterStatsEntry OBJECT-TYPE
   SYNTAX     MscVrNsFilterStatsEntry
   ACCESS     not-accessible
   STATUS     mandatory
   DESCRIPTION
     "An entry in the mscVrNsFilterStatsTable."
   INDEX {
      mscVrIndex,
      mscVrNsIndex,
      mscVrNsFilterNameIndex,
      mscVrNsFilterKindIndex }
::= { mscVrNsFilterStatsTable 1 }

MscVrNsFilterStatsEntry ::= SEQUENCE {
   mscVrNsFilterPacketsSucceeded
      Counter32,
   mscVrNsFilterBytesSucceeded
      Counter32,
   mscVrNsFilterPacketsFailed
      Counter32,
   mscVrNsFilterBytesFailed
      Counter32,
   mscVrNsFilterPacketsBreaked
      Counter32,
   mscVrNsFilterBytesBreaked
      Counter32,
   mscVrNsFilterPacketsContinued
      Counter32,
   mscVrNsFilterBytesContinued
      Counter32 }

mscVrNsFilterPacketsSucceeded OBJECT-TYPE
   SYNTAX     Counter32 
   ACCESS     read-only
   STATUS     mandatory
   DESCRIPTION
     "This counter contains the number of packets which passed through 
      NetSentry, which happen to have been matched against an element of the 
      enclosing Filter component which had a succeed disposition."
::= { mscVrNsFilterStatsEntry 1 }

mscVrNsFilterBytesSucceeded OBJECT-TYPE
   SYNTAX     Counter32 
   ACCESS     read-only
   STATUS     mandatory
   DESCRIPTION
     "This counter counts the number of bytes in the packets counted in the 
      packetsSucceeded."
::= { mscVrNsFilterStatsEntry 2 }

mscVrNsFilterPacketsFailed OBJECT-TYPE
   SYNTAX     Counter32 
   ACCESS     read-only
   STATUS     mandatory
   DESCRIPTION
     "This counter contains the number of packets which passed through 
      NetSentry, which happen to have been matched against an element of the 
      enclosing Filter which had a fail disposition."
::= { mscVrNsFilterStatsEntry 3 }

mscVrNsFilterBytesFailed OBJECT-TYPE
   SYNTAX     Counter32 
   ACCESS     read-only
   STATUS     mandatory
   DESCRIPTION
     "This counter counts the number of bytes in the packets counted in the 
      packetsFailed counter."
::= { mscVrNsFilterStatsEntry 4 }

mscVrNsFilterPacketsBreaked OBJECT-TYPE
   SYNTAX     Counter32 
   ACCESS     read-only
   STATUS     mandatory
   DESCRIPTION
     "This counter contains the number of packets which passed through 
      NetSentry, which happen to have been matched against an element of the 
      enclosing Filter which had a break disposition."
::= { mscVrNsFilterStatsEntry 5 }

mscVrNsFilterBytesBreaked OBJECT-TYPE
   SYNTAX     Counter32 
   ACCESS     read-only
   STATUS     mandatory
   DESCRIPTION
     "This counter counts the number of bytes in the packets counted in the 
      packetsBreaked counter."
::= { mscVrNsFilterStatsEntry 6 }

mscVrNsFilterPacketsContinued OBJECT-TYPE
   SYNTAX     Counter32 
   ACCESS     read-only
   STATUS     mandatory
   DESCRIPTION
     "This counter contains the number of packets which passed through 
      NetSentry, which happen to have been matched against at least one 
      element of the enclosing Filter which had a continue disposition. Such a 
      packet may also have been counted in one of the packetsSucceeded 
      packetsFailed or packetsBreaked counters, since a continue disposition 
      does not exit a NetSentry filter unless it is the disposition in the last 
      element of the filter."
::= { mscVrNsFilterStatsEntry 7 }

mscVrNsFilterBytesContinued OBJECT-TYPE
   SYNTAX     Counter32 
   ACCESS     read-only
   STATUS     mandatory
   DESCRIPTION
     "This counter counts the number of bytes in the packets counted in the 
      packetsContinued counter."
::= { mscVrNsFilterStatsEntry 8 }




-- 
-- Version and Compliance statements
-- 



-- Object-Group Statement:
-- A list of all current accessible leaf objects.

-- OBJECTS { mscVrNsComponentName,
--           mscVrNsDroppedCantLogTo,
--           mscVrNsPacketsProcessed,
--           mscVrNsFilterBytesSucceeded,
--           mscVrNsIPStatsComponentName,
--           mscVrNsFilterPacketsContinued,
--           mscVrNsIPXStatsAddrStatComponentName,
--           mscVrNsBrStatsAddrStatByteCount,
--           mscVrNsDNStatsComponentName,
--           mscVrNsFilterPacketsBreaked,
--           mscVrNsIPXStatsAddrStatCounter2,
--           mscVrNsIPStatsAddrStatComponentName,
--           mscVrNsATStatsAddrStatByteCount,
--           mscVrNsBrStatsAddrStatRowStatus,
--           mscVrNsDNStatsAddrStatComponentName,
--           mscVrNsIPStatsAddrStatCounter2,
--           mscVrNsBrStatsAddrStatCounter2,
--           mscVrNsATStatsStorageType,
--           mscVrNsBrStatsComponentName,
--           mscVrNsFilterPacketsSucceeded,
--           mscVrNsDNStatsAddrStatCounter2,
--           mscVrNsDroppedNullFilter,
--           mscVrNsFileComponentName,
--           mscVrNsIPXStatsAddrStatCounter1,
--           mscVrNsATStatsAddrStatStorageType,
--           mscVrNsRowStatus,
--           mscVrNsBrStatsAddrStatCounter1,
--           mscVrNsFilterStorageType,
--           mscVrNsPacketsFailed,
--           mscVrNsBrStatsStorageType,
--           mscVrNsFilterBytesContinued,
--           mscVrNsATStatsAddrStatRowStatus,
--           mscVrNsDNStatsAddrStatCounter1,
--           mscVrNsDNStatsAddrStatByteCount,
--           mscVrNsFilterRowStatus,
--           mscVrNsFileCompilerErrorMsg,
--           mscVrNsBrStatsAddrStatStorageType,
--           mscVrNsDNStatsAddrStatRowStatus,
--           mscVrNsATStatsRowStatus,
--           mscVrNsDropConditions,
--           mscVrNsIPXStatsAddrStatByteCount,
--           mscVrNsATStatsAddrStatPacketCount,
--           mscVrNsIPXStatsComponentName,
--           mscVrNsEngineStorageType,
--           mscVrNsFilterBytesFailed,
--           mscVrNsStorageType,
--           mscVrNsIPStatsAddrStatByteCount,
--           mscVrNsATStatsAddrStatCounter1,
--           mscVrNsHsaOkayFailed,
--           mscVrNsFilterComponentName,
--           mscVrNsIPStatsStorageType,
--           mscVrNsIPXStatsAddrStatStorageType,
--           mscVrNsATStatsComponentName,
--           mscVrNsDNStatsAddrStatStorageType,
--           mscVrNsDepthExceeded,
--           mscVrNsFilterBytesBreaked,
--           mscVrNsIPStatsAddrStatStorageType,
--           mscVrNsBrStatsAddrStatPacketCount,
--           mscVrNsATStatsAddrStatComponentName,
--           mscVrNsBrStatsRowStatus,
--           mscVrNsDroppedStatsNoMem,
--           mscVrNsDroppedCantCloneTo,
--           mscVrNsATStatsAddrStatCounter2,
--           mscVrNsDroppedCantCopyTo,
--           mscVrNsFileStorageType,
--           mscVrNsIPXStatsRowStatus,
--           mscVrNsEngineRowStatus,
--           mscVrNsStatsNoMem,
--           mscVrNsDNStatsAddrStatPacketCount,
--           mscVrNsIPStatsRowStatus,
--           mscVrNsFileRowStatus,
--           mscVrNsBrStatsAddrStatComponentName,
--           mscVrNsIPXStatsAddrStatRowStatus,
--           mscVrNsIPXStatsAddrStatPacketCount,
--           mscVrNsDNStatsRowStatus,
--           mscVrNsDNStatsStorageType,
--           mscVrNsIPXStatsStorageType,
--           mscVrNsFilterPacketsFailed,
--           mscVrNsIPStatsAddrStatRowStatus,
--           mscVrNsIPStatsAddrStatPacketCount,
--           mscVrNsIPStatsAddrStatCounter1,
--           mscVrNsEngineComponentName }
-- STATUS  mandatory
-- DESCRIPTION
--   "A list of all current accessible leaf objects."

netSentryGroup OBJECT IDENTIFIER ::= { netSentryMIB 1 }
netSentryGroupCA OBJECT IDENTIFIER ::= { netSentryGroup 1 }
netSentryGroupCA02 OBJECT IDENTIFIER ::= { netSentryGroupCA 3 }
netSentryGroupCA02A OBJECT IDENTIFIER ::= { netSentryGroupCA02 2 }



-- Agent-Capabilities Statement:

-- PRODUCT-RELEASE "MscPassport Release 1.2 NetSentry."
-- STATUS          mandatory
-- DESCRIPTION     "Carrier Passport NetSentry MIB: MIB Version CA02A,
--                  Software Version CA02S9C."
-- SUPPORTS        Nortel-MsCarrier-MscPassport-NetSentryMIB
--    INCLUDES     { netSentryGroupCA02A }

netSentryCapabilities OBJECT IDENTIFIER ::= { netSentryMIB 3 }
netSentryCapabilitiesCA OBJECT IDENTIFIER ::= { netSentryCapabilities 1 }
netSentryCapabilitiesCA02 OBJECT IDENTIFIER ::= { netSentryCapabilitiesCA 3 }
netSentryCapabilitiesCA02A OBJECT IDENTIFIER ::= { netSentryCapabilitiesCA02 2 }





END
