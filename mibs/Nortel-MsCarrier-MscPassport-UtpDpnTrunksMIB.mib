Nortel-MsCarrier-MscPassport-UtpDpnTrunksMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Unsigned32
   FROM Nortel-MsCarrier-MscPassport-StandardTextualConventionsMIB

      NonReplicated,
      PassportCounter64,
      Link
   FROM Nortel-MsCarrier-MscPassport-TextualConventionsMIB

      mscDpnGateIndex,
      mscDpnGate
   FROM Nortel-MsCarrier-MscPassport-DpnTrunksMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     UtpDpnTrunks Enterprise MIB."

utpDpnTrunksMIB OBJECT IDENTIFIER ::= { mscPassportMIBs 67 }










-- DpnGateway/n Utp
-- The Utp component provides the Utp Level2 link protocol, an 
-- acknowledged protocol that provides selective retransmission of 
-- frames. A Framer subcomponent is automatically added providing 
-- the underlying HDLC framing and associated hardware that the Utp 
-- component will use.

mscDpnGateUtp OBJECT IDENTIFIER ::= { mscDpnGate 2 }



mscDpnGateUtpRowStatusTable OBJECT-TYPE
   SYNTAX     SEQUENCE OF MscDpnGateUtpRowStatusEntry
   ACCESS     not-accessible
   STATUS     mandatory
   DESCRIPTION
     "This entry controls the addition and deletion of 
      mscDpnGateUtp components."
::= { mscDpnGateUtp 1 }

mscDpnGateUtpRowStatusEntry OBJECT-TYPE
   SYNTAX     MscDpnGateUtpRowStatusEntry
   ACCESS     not-accessible
   STATUS     mandatory
   DESCRIPTION
     "A single entry in the table represents a single 
      mscDpnGateUtp component."
   INDEX {
      mscDpnGateIndex,
      mscDpnGateUtpIndex }
::= { mscDpnGateUtpRowStatusTable 1 }

MscDpnGateUtpRowStatusEntry ::= SEQUENCE {
   mscDpnGateUtpRowStatus
      RowStatus,
   mscDpnGateUtpComponentName
      DisplayString,
   mscDpnGateUtpStorageType
      StorageType,
   mscDpnGateUtpIndex
      NonReplicated }

mscDpnGateUtpRowStatus OBJECT-TYPE
   SYNTAX     RowStatus 
   ACCESS     read-write
   STATUS     mandatory
   DESCRIPTION
     "This variable is used as the basis for SNMP naming of
      mscDpnGateUtp components.
      These components can be added and deleted."
::= { mscDpnGateUtpRowStatusEntry 1 }

mscDpnGateUtpComponentName OBJECT-TYPE
   SYNTAX     DisplayString 
   ACCESS     read-only
   STATUS     mandatory
   DESCRIPTION
     "This variable provides the component's string name for
      use with the ASCII Console Interface"
::= { mscDpnGateUtpRowStatusEntry 2 }

mscDpnGateUtpStorageType OBJECT-TYPE
   SYNTAX     StorageType 
   ACCESS     read-only
   STATUS     mandatory
   DESCRIPTION
     "This variable represents the storage type value for the
      mscDpnGateUtp tables."
::= { mscDpnGateUtpRowStatusEntry 4 }

mscDpnGateUtpIndex OBJECT-TYPE
   SYNTAX     NonReplicated 
   ACCESS     not-accessible
   STATUS     mandatory
   DESCRIPTION
     "This variable represents the index for the mscDpnGateUtp tables."
::= { mscDpnGateUtpRowStatusEntry 10 }

mscDpnGateUtpProvTable OBJECT-TYPE
   SYNTAX     SEQUENCE OF MscDpnGateUtpProvEntry
   ACCESS     not-accessible
   STATUS     mandatory
   DESCRIPTION
     "This group of provisionable attributes contains the parameters used 
      by Unacknowledged, Utp, and FrAccess for monitoring link quality."
::= { mscDpnGateUtp 10 }

mscDpnGateUtpProvEntry OBJECT-TYPE
   SYNTAX     MscDpnGateUtpProvEntry
   ACCESS     not-accessible
   STATUS     mandatory
   DESCRIPTION
     "An entry in the mscDpnGateUtpProvTable."
   INDEX {
      mscDpnGateIndex,
      mscDpnGateUtpIndex }
::= { mscDpnGateUtpProvTable 1 }

MscDpnGateUtpProvEntry ::= SEQUENCE {
   mscDpnGateUtpMaximumErroredInterval
      Unsigned32,
   mscDpnGateUtpReceiveErrorSensitivity
      Unsigned32 }

mscDpnGateUtpMaximumErroredInterval OBJECT-TYPE
   SYNTAX     Unsigned32 (0 | 1..15)
   ACCESS     read-write
   STATUS     mandatory
   DESCRIPTION
     "This attribute specifies the interval time over which the error 
      threshold (as specified by receiveErrorSensitivity) must be 
      continuously exceeded before the Unacknowledged, Utp, or 
      FrAccess component can be degraded. Once the error interval count 
      exceeds the provisioned value, the Unacknowledged, Utp, or 
      FrAccess component issues an alarm indicating that link quality has 
      degraded, and it disables its parent component. The exception to 
      this is a value of zero, the default, which indicates that the 
      mechanism is completely disabled."
   DEFVAL     { 0 }
::= { mscDpnGateUtpProvEntry 1 }

mscDpnGateUtpReceiveErrorSensitivity OBJECT-TYPE
   SYNTAX     Unsigned32 (0 | 1..10)
   ACCESS     read-write
   STATUS     mandatory
   DESCRIPTION
     "This attribute is the allowable error rate beyond which the 
      Unacknowledged, Utp, or FrAccess component can be degraded if it 
      persists for a duration longer than the maximumErrorInterval. The 
      threshold is expressed as a percentage of number of errored frames 
      in the last interval per number of frames received in the last interval. 
      The exception to this is a value of zero, which indicates that the 
      mechanism is completely disabled. The configurable values are:
      0 = the mechanism is completely disabled
      1 = 1/(2**1)
      2 = 1/(2**2)
      3 = 1/(2**3)
      :
      10 = 1/(2**10)"
   DEFVAL     { 3 }
::= { mscDpnGateUtpProvEntry 2 }

mscDpnGateUtpStateTable OBJECT-TYPE
   SYNTAX     SEQUENCE OF MscDpnGateUtpStateEntry
   ACCESS     not-accessible
   STATUS     mandatory
   DESCRIPTION
     "This group contains the three OSI State attributes and the six OSI 
      Status attributes. The descriptions generically indicate what each 
      attribute implies about the component. Note that not all the values 
      and state combinations described here are supported by every 
      component which reuses this group. For component-specific 
      information and the valid state combinations, refer to the 
      appropriate NTP."
::= { mscDpnGateUtp 11 }

mscDpnGateUtpStateEntry OBJECT-TYPE
   SYNTAX     MscDpnGateUtpStateEntry
   ACCESS     not-accessible
   STATUS     mandatory
   DESCRIPTION
     "An entry in the mscDpnGateUtpStateTable."
   INDEX {
      mscDpnGateIndex,
      mscDpnGateUtpIndex }
::= { mscDpnGateUtpStateTable 1 }

MscDpnGateUtpStateEntry ::= SEQUENCE {
   mscDpnGateUtpAdminState
      INTEGER,
   mscDpnGateUtpOperationalState
      INTEGER,
   mscDpnGateUtpUsageState
      INTEGER,
   mscDpnGateUtpAvailabilityStatus
      OCTET STRING,
   mscDpnGateUtpProceduralStatus
      OCTET STRING,
   mscDpnGateUtpControlStatus
      OCTET STRING,
   mscDpnGateUtpAlarmStatus
      OCTET STRING,
   mscDpnGateUtpStandbyStatus
      INTEGER,
   mscDpnGateUtpUnknownStatus
      INTEGER }

mscDpnGateUtpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscDpnGateUtpStateEntry 1 }

mscDpnGateUtpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscDpnGateUtpStateEntry 2 }

mscDpnGateUtpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscDpnGateUtpStateEntry 3 }

mscDpnGateUtpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below is present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. Usually, the resource remains available for service. The 
      operationalState is almost always enabled. There is one exception 
      where an operationalState of disabled is used in conjunction with 
      degraded for a component which represents a rolled up view of a 
      set of other components.
      
      The value notInstalled indicates the resource is not present. The 
      operationalState is disabled.
      
      The value logFull is not used.
      
      The value migrating indicates that a software migration activation 
      is in progress, making the component unavailable for other 
      activities until the migration is complete.

      Description of bits:
      inTest(0)
      failed(1)
      powerOff(2)
      offLine(3)
      offDuty(4)
      dependency(5)
      degraded(6)
      notInstalled(7)
      logFull(8)
      migrating(9)"
::= { mscDpnGateUtpStateEntry 4 }

mscDpnGateUtpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below is present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscDpnGateUtpStateEntry 5 }

mscDpnGateUtpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below is present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscDpnGateUtpStateEntry 6 }

mscDpnGateUtpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below is present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscDpnGateUtpStateEntry 7 }

mscDpnGateUtpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below is present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscDpnGateUtpStateEntry 8 }

mscDpnGateUtpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscDpnGateUtpStateEntry 9 }

mscDpnGateUtpOpTable OBJECT-TYPE
   SYNTAX     SEQUENCE OF MscDpnGateUtpOpEntry
   ACCESS     not-accessible
   STATUS     mandatory
   DESCRIPTION
     "This group of attributes contains the set of UTP operational 
      parameters measured and maintained by this component."
::= { mscDpnGateUtp 12 }

mscDpnGateUtpOpEntry OBJECT-TYPE
   SYNTAX     MscDpnGateUtpOpEntry
   ACCESS     not-accessible
   STATUS     mandatory
   DESCRIPTION
     "An entry in the mscDpnGateUtpOpTable."
   INDEX {
      mscDpnGateIndex,
      mscDpnGateUtpIndex }
::= { mscDpnGateUtpOpTable 1 }

MscDpnGateUtpOpEntry ::= SEQUENCE {
   mscDpnGateUtpRoundTripDelay
      Gauge32 }

mscDpnGateUtpRoundTripDelay OBJECT-TYPE
   SYNTAX     Gauge32 (0..1500)
   ACCESS     read-only
   STATUS     mandatory
   DESCRIPTION
     "This is the measured Round Trip Delay (ms) discovered with the 
      remote through the UTP staging protocol. The value includes 
      emission, propagation, and queuing delays. A 2 byte control frame 
      is used to perform the measurement. A value of zero is displayed 
      when the link is disabled or the measured Round Trip Delay is 
      unknown."
::= { mscDpnGateUtpOpEntry 1 }

mscDpnGateUtpStatsTable OBJECT-TYPE
   SYNTAX     SEQUENCE OF MscDpnGateUtpStatsEntry
   ACCESS     not-accessible
   STATUS     mandatory
   DESCRIPTION
     "This group of attributes contains the set of Utp frame counters 
      collected by this component."
::= { mscDpnGateUtp 13 }

mscDpnGateUtpStatsEntry OBJECT-TYPE
   SYNTAX     MscDpnGateUtpStatsEntry
   ACCESS     not-accessible
   STATUS     mandatory
   DESCRIPTION
     "An entry in the mscDpnGateUtpStatsTable."
   INDEX {
      mscDpnGateIndex,
      mscDpnGateUtpIndex }
::= { mscDpnGateUtpStatsTable 1 }

MscDpnGateUtpStatsEntry ::= SEQUENCE {
   mscDpnGateUtpDiscardBadFromIf
      Counter32,
   mscDpnGateUtpDiscardExcessToIf
      Counter32,
   mscDpnGateUtpFrmRexmtToIf
      Counter32,
   mscDpnGateUtpAreYouThereModeEntries
      Counter32,
   mscDpnGateUtpWindowClosures
      Counter32 }

mscDpnGateUtpDiscardBadFromIf OBJECT-TYPE
   SYNTAX     Counter32 
   ACCESS     read-only
   STATUS     mandatory
   DESCRIPTION
     "This attribute is the number of received frames discarded by the Utp 
      component. UTP discards any received frame that is unknown to its 
      protocol. This counter wraps around to zero when the maximum 
      value is reached."
::= { mscDpnGateUtpStatsEntry 1 }

mscDpnGateUtpDiscardExcessToIf OBJECT-TYPE
   SYNTAX     Counter32 
   ACCESS     read-only
   STATUS     mandatory
   DESCRIPTION
     "This attribute is the number of transmitted frames discarded by the 
      Utp component. Transmitted frames are discarded if the wait for 
      transmission queue is congested. This counter wraps around to zero 
      when the maximum value is reached."
::= { mscDpnGateUtpStatsEntry 2 }

mscDpnGateUtpFrmRexmtToIf OBJECT-TYPE
   SYNTAX     Counter32 
   ACCESS     read-only
   STATUS     mandatory
   DESCRIPTION
     "This attribute is the number of frames retransmitted by the Utp 
      component. This counter wraps around to zero when the maximum 
      value is reached."
::= { mscDpnGateUtpStatsEntry 3 }

mscDpnGateUtpAreYouThereModeEntries OBJECT-TYPE
   SYNTAX     Counter32 
   ACCESS     read-only
   STATUS     mandatory
   DESCRIPTION
     "This attribute is the number of times the Utp component entered the 
      AreYouThere mode. UTP enters this mode whenever the 
      acknowledgment for the last transmitted frame has not been 
      received within a certain time interval. In this mode UTP verifies 
      that the remote end is still active. If so, it will retransmit all frames 
      that were waiting to be acknowledged. This counter wraps around 
      to zero when the maximum value is reached."
::= { mscDpnGateUtpStatsEntry 4 }

mscDpnGateUtpWindowClosures OBJECT-TYPE
   SYNTAX     Counter32 
   ACCESS     read-only
   STATUS     mandatory
   DESCRIPTION
     "This attribute is the number of times the Utp component closed its 
      frame window. The frame window determines the maximum 
      number of unacknowledged frames allowed. Typically, the frame 
      window closes when the remote end cannot keep up with the frame 
      arrival rate. This counter wraps around to zero when the maximum 
      value is reached."
::= { mscDpnGateUtpStatsEntry 5 }


-- 
-- Trunk/n Utp Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscDpnGateUtpFramer OBJECT IDENTIFIER ::= { mscDpnGateUtp 2 }



mscDpnGateUtpFramerRowStatusTable OBJECT-TYPE
   SYNTAX     SEQUENCE OF MscDpnGateUtpFramerRowStatusEntry
   ACCESS     not-accessible
   STATUS     mandatory
   DESCRIPTION
     "This entry controls the addition and deletion of 
      mscDpnGateUtpFramer components."
::= { mscDpnGateUtpFramer 1 }

mscDpnGateUtpFramerRowStatusEntry OBJECT-TYPE
   SYNTAX     MscDpnGateUtpFramerRowStatusEntry
   ACCESS     not-accessible
   STATUS     mandatory
   DESCRIPTION
     "A single entry in the table represents a single 
      mscDpnGateUtpFramer component."
   INDEX {
      mscDpnGateIndex,
      mscDpnGateUtpIndex,
      mscDpnGateUtpFramerIndex }
::= { mscDpnGateUtpFramerRowStatusTable 1 }

MscDpnGateUtpFramerRowStatusEntry ::= SEQUENCE {
   mscDpnGateUtpFramerRowStatus
      RowStatus,
   mscDpnGateUtpFramerComponentName
      DisplayString,
   mscDpnGateUtpFramerStorageType
      StorageType,
   mscDpnGateUtpFramerIndex
      NonReplicated }

mscDpnGateUtpFramerRowStatus OBJECT-TYPE
   SYNTAX     RowStatus 
   ACCESS     read-only
   STATUS     mandatory
   DESCRIPTION
     "This variable is used as the basis for SNMP naming of
      mscDpnGateUtpFramer components.
      These components cannot be added nor deleted."
::= { mscDpnGateUtpFramerRowStatusEntry 1 }

mscDpnGateUtpFramerComponentName OBJECT-TYPE
   SYNTAX     DisplayString 
   ACCESS     read-only
   STATUS     mandatory
   DESCRIPTION
     "This variable provides the component's string name for
      use with the ASCII Console Interface"
::= { mscDpnGateUtpFramerRowStatusEntry 2 }

mscDpnGateUtpFramerStorageType OBJECT-TYPE
   SYNTAX     StorageType 
   ACCESS     read-only
   STATUS     mandatory
   DESCRIPTION
     "This variable represents the storage type value for the
      mscDpnGateUtpFramer tables."
::= { mscDpnGateUtpFramerRowStatusEntry 4 }

mscDpnGateUtpFramerIndex OBJECT-TYPE
   SYNTAX     NonReplicated 
   ACCESS     not-accessible
   STATUS     mandatory
   DESCRIPTION
     "This variable represents the index for the mscDpnGateUtpFramer tables."
::= { mscDpnGateUtpFramerRowStatusEntry 10 }

mscDpnGateUtpFramerProvTable OBJECT-TYPE
   SYNTAX     SEQUENCE OF MscDpnGateUtpFramerProvEntry
   ACCESS     not-accessible
   STATUS     mandatory
   DESCRIPTION
     "This group contains the base provisioning data for the Framer 
      component. Application or hardware interface specific provisioning 
      data is contained in other provisionable Framer groups."
::= { mscDpnGateUtpFramer 10 }

mscDpnGateUtpFramerProvEntry OBJECT-TYPE
   SYNTAX     MscDpnGateUtpFramerProvEntry
   ACCESS     not-accessible
   STATUS     mandatory
   DESCRIPTION
     "An entry in the mscDpnGateUtpFramerProvTable."
   INDEX {
      mscDpnGateIndex,
      mscDpnGateUtpIndex,
      mscDpnGateUtpFramerIndex }
::= { mscDpnGateUtpFramerProvTable 1 }

MscDpnGateUtpFramerProvEntry ::= SEQUENCE {
   mscDpnGateUtpFramerInterfaceName
      Link }

mscDpnGateUtpFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDpnGateUtpFramerProvEntry 1 }

mscDpnGateUtpFramerLinkTable OBJECT-TYPE
   SYNTAX     SEQUENCE OF MscDpnGateUtpFramerLinkEntry
   ACCESS     not-accessible
   STATUS     mandatory
   DESCRIPTION
     "This group contains attributes defining the framing of data on the 
      link interface."
::= { mscDpnGateUtpFramer 11 }

mscDpnGateUtpFramerLinkEntry OBJECT-TYPE
   SYNTAX     MscDpnGateUtpFramerLinkEntry
   ACCESS     not-accessible
   STATUS     mandatory
   DESCRIPTION
     "An entry in the mscDpnGateUtpFramerLinkTable."
   INDEX {
      mscDpnGateIndex,
      mscDpnGateUtpIndex,
      mscDpnGateUtpFramerIndex }
::= { mscDpnGateUtpFramerLinkTable 1 }

MscDpnGateUtpFramerLinkEntry ::= SEQUENCE {
   mscDpnGateUtpFramerFramingType
      INTEGER,
   mscDpnGateUtpFramerDataInversion
      INTEGER,
   mscDpnGateUtpFramerFrameCrcType
      INTEGER,
   mscDpnGateUtpFramerFlagsBetweenFrames
      Unsigned32 }

mscDpnGateUtpFramerFramingType OBJECT-TYPE
   SYNTAX     INTEGER  {
                 hdlc(0) }
   ACCESS     read-write
   STATUS     mandatory
   DESCRIPTION
     "This attribute defines the type of framing on the link."
   DEFVAL     { hdlc }
::= { mscDpnGateUtpFramerLinkEntry 1 }

mscDpnGateUtpFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted."
   DEFVAL     { off }
::= { mscDpnGateUtpFramerLinkEntry 2 }

mscDpnGateUtpFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used."
   DEFVAL     { crc16 }
::= { mscDpnGateUtpFramerLinkEntry 3 }

mscDpnGateUtpFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscDpnGateUtpFramerLinkEntry 4 }

mscDpnGateUtpFramerStateTable OBJECT-TYPE
   SYNTAX     SEQUENCE OF MscDpnGateUtpFramerStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscDpnGateUtpFramer 12 }

mscDpnGateUtpFramerStateEntry OBJECT-TYPE
   SYNTAX     MscDpnGateUtpFramerStateEntry
   ACCESS     not-accessible
   STATUS     mandatory
   DESCRIPTION
     "An entry in the mscDpnGateUtpFramerStateTable."
   INDEX {
      mscDpnGateIndex,
      mscDpnGateUtpIndex,
      mscDpnGateUtpFramerIndex }
::= { mscDpnGateUtpFramerStateTable 1 }

MscDpnGateUtpFramerStateEntry ::= SEQUENCE {
   mscDpnGateUtpFramerAdminState
      INTEGER,
   mscDpnGateUtpFramerOperationalState
      INTEGER,
   mscDpnGateUtpFramerUsageState
      INTEGER }

mscDpnGateUtpFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDpnGateUtpFramerStateEntry 1 }

mscDpnGateUtpFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDpnGateUtpFramerStateEntry 2 }

mscDpnGateUtpFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDpnGateUtpFramerStateEntry 3 }

mscDpnGateUtpFramerStatsTable OBJECT-TYPE
   SYNTAX     SEQUENCE OF MscDpnGateUtpFramerStatsEntry
   ACCESS     not-accessible
   STATUS     mandatory
   DESCRIPTION
     "This group contains the operational statistics data for a UTP Framer 
      component."
::= { mscDpnGateUtpFramer 13 }

mscDpnGateUtpFramerStatsEntry OBJECT-TYPE
   SYNTAX     MscDpnGateUtpFramerStatsEntry
   ACCESS     not-accessible
   STATUS     mandatory
   DESCRIPTION
     "An entry in the mscDpnGateUtpFramerStatsTable."
   INDEX {
      mscDpnGateIndex,
      mscDpnGateUtpIndex,
      mscDpnGateUtpFramerIndex }
::= { mscDpnGateUtpFramerStatsTable 1 }

MscDpnGateUtpFramerStatsEntry ::= SEQUENCE {
   mscDpnGateUtpFramerFrmToIf
      Counter32,
   mscDpnGateUtpFramerFrmFromIf
      Counter32,
   mscDpnGateUtpFramerOctetFromIf
      Counter32,
   mscDpnGateUtpFramerAborts
      Counter32,
   mscDpnGateUtpFramerCrcErrors
      Counter32,
   mscDpnGateUtpFramerLrcErrors
      Counter32,
   mscDpnGateUtpFramerNonOctetErrors
      Counter32,
   mscDpnGateUtpFramerOverruns
      Counter32,
   mscDpnGateUtpFramerUnderruns
      Counter32,
   mscDpnGateUtpFramerLargeFrmErrors
      Counter32,
   mscDpnGateUtpFramerFrmModeErrors
      Counter32,
   mscDpnGateUtpFramerOutOfSequenceFrm
      Counter32,
   mscDpnGateUtpFramerRepeatedFrm
      Counter32,
   mscDpnGateUtpFramerFrmToIf64
      PassportCounter64,
   mscDpnGateUtpFramerFrmFromIf64
      PassportCounter64,
   mscDpnGateUtpFramerOctetFromIf64
      PassportCounter64 }

mscDpnGateUtpFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscDpnGateUtpFramerStatsEntry 1 }

mscDpnGateUtpFramerFrmFromIf OBJECT-TYPE
   SYNTAX     Counter32 
   ACCESS     read-only
   STATUS     obsolete
   DESCRIPTION
     "The number of frames received from the link interface by Framer."
::= { mscDpnGateUtpFramerStatsEntry 2 }

mscDpnGateUtpFramerOctetFromIf OBJECT-TYPE
   SYNTAX     Counter32 
   ACCESS     read-only
   STATUS     obsolete
   DESCRIPTION
     "The number of bytes received from the link interface by Framer."
::= { mscDpnGateUtpFramerStatsEntry 3 }

mscDpnGateUtpFramerAborts OBJECT-TYPE
   SYNTAX     Counter32 
   ACCESS     read-only
   STATUS     mandatory
   DESCRIPTION
     "This attribute is the total number of aborts received."
::= { mscDpnGateUtpFramerStatsEntry 4 }

mscDpnGateUtpFramerCrcErrors OBJECT-TYPE
   SYNTAX     Counter32 
   ACCESS     read-only
   STATUS     mandatory
   DESCRIPTION
     "This attribute is the total number of frames with CRC errors, 
      occurring in the receive direction from the link."
::= { mscDpnGateUtpFramerStatsEntry 5 }

mscDpnGateUtpFramerLrcErrors OBJECT-TYPE
   SYNTAX     Counter32 
   ACCESS     read-only
   STATUS     mandatory
   DESCRIPTION
     "This attribute is the total number of frames with LRC errors, 
      occurring in the Tx link prior to transmission onto the link."
::= { mscDpnGateUtpFramerStatsEntry 6 }

mscDpnGateUtpFramerNonOctetErrors OBJECT-TYPE
   SYNTAX     Counter32 
   ACCESS     read-only
   STATUS     mandatory
   DESCRIPTION
     "This attribute is the total number of frames that were non octet 
      aligned."
::= { mscDpnGateUtpFramerStatsEntry 7 }

mscDpnGateUtpFramerOverruns OBJECT-TYPE
   SYNTAX     Counter32 
   ACCESS     read-only
   STATUS     mandatory
   DESCRIPTION
     "This attribute is the total number of frames received from the link 
      for which overruns occurred."
::= { mscDpnGateUtpFramerStatsEntry 8 }

mscDpnGateUtpFramerUnderruns OBJECT-TYPE
   SYNTAX     Counter32 
   ACCESS     read-only
   STATUS     mandatory
   DESCRIPTION
     "This attribute is the total number of frames transmitted to the link 
      for which underruns occurred."
::= { mscDpnGateUtpFramerStatsEntry 9 }

mscDpnGateUtpFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mscDpnGateUtpFramerStatsEntry 10 }

mscDpnGateUtpFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mscDpnGateUtpFramerStatsEntry 11 }

mscDpnGateUtpFramerOutOfSequenceFrm OBJECT-TYPE
   SYNTAX     Counter32 
   ACCESS     read-only
   STATUS     mandatory
   DESCRIPTION
     "This attribute is the total number of out of sequence frames in 
      interrupting mode that have been received from the link."
::= { mscDpnGateUtpFramerStatsEntry 12 }

mscDpnGateUtpFramerRepeatedFrm OBJECT-TYPE
   SYNTAX     Counter32 
   ACCESS     read-only
   STATUS     mandatory
   DESCRIPTION
     "This attribute is the total number of repeated frames (frames with 
      the same sequence number) in interrupting mode that have been 
      received from the link."
::= { mscDpnGateUtpFramerStatsEntry 13 }

mscDpnGateUtpFramerFrmToIf64 OBJECT-TYPE
   SYNTAX     PassportCounter64 
   ACCESS     read-only
   STATUS     mandatory
   DESCRIPTION
     "The number of frames transmitted to the link interface by Framer.
      
      Note: This does not include the number of frames transmitted 
      directly to the hardware queue, thus bypassing the Framer 
      component."
::= { mscDpnGateUtpFramerStatsEntry 14 }

mscDpnGateUtpFramerFrmFromIf64 OBJECT-TYPE
   SYNTAX     PassportCounter64 
   ACCESS     read-only
   STATUS     mandatory
   DESCRIPTION
     "The number of frames received from the link interface by Framer."
::= { mscDpnGateUtpFramerStatsEntry 15 }

mscDpnGateUtpFramerOctetFromIf64 OBJECT-TYPE
   SYNTAX     PassportCounter64 
   ACCESS     read-only
   STATUS     mandatory
   DESCRIPTION
     "The number of bytes received from the link interface by Framer."
::= { mscDpnGateUtpFramerStatsEntry 16 }

mscDpnGateUtpFramerUtilTable OBJECT-TYPE
   SYNTAX     SEQUENCE OF MscDpnGateUtpFramerUtilEntry
   ACCESS     not-accessible
   STATUS     mandatory
   DESCRIPTION
     "This group contains the link utilization operational data for a 
      Framer component."
::= { mscDpnGateUtpFramer 14 }

mscDpnGateUtpFramerUtilEntry OBJECT-TYPE
   SYNTAX     MscDpnGateUtpFramerUtilEntry
   ACCESS     not-accessible
   STATUS     mandatory
   DESCRIPTION
     "An entry in the mscDpnGateUtpFramerUtilTable."
   INDEX {
      mscDpnGateIndex,
      mscDpnGateUtpIndex,
      mscDpnGateUtpFramerIndex }
::= { mscDpnGateUtpFramerUtilTable 1 }

MscDpnGateUtpFramerUtilEntry ::= SEQUENCE {
   mscDpnGateUtpFramerNormPrioLinkUtilToIf
      Gauge32,
   mscDpnGateUtpFramerHighPrioLinkUtilToIf
      Gauge32,
   mscDpnGateUtpFramerNormPrioLinkUtilFromIf
      Gauge32,
   mscDpnGateUtpFramerHighPrioLinkUtilFromIf
      Gauge32 }

mscDpnGateUtpFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { mscDpnGateUtpFramerUtilEntry 1 }

mscDpnGateUtpFramerHighPrioLinkUtilToIf OBJECT-TYPE
   SYNTAX     Gauge32 (0..100)
   ACCESS     read-only
   STATUS     mandatory
   DESCRIPTION
     "This attribute is the utilization of the interrupting data traffic sent to 
      the link as a percentage of the available bandwidth on the link. Note 
      that this includes traffic with a Transfer Priority (TP) of 11 and/or 
      Emission Priority of 1. The utilization is the average for the last 
      minute."
   DEFVAL     { 0 }
::= { mscDpnGateUtpFramerUtilEntry 2 }

mscDpnGateUtpFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mscDpnGateUtpFramerUtilEntry 3 }

mscDpnGateUtpFramerHighPrioLinkUtilFromIf OBJECT-TYPE
   SYNTAX     Gauge32 (0..100)
   ACCESS     read-only
   STATUS     mandatory
   DESCRIPTION
     "This attribute is the utilization of the interrupting data traffic 
      received from the link as a percentage of the available bandwidth on 
      the link. Note that this includes traffic with a Transfer Priority (TP) 
      of 11 and/or Emission Priority of 1. The utilization is the average 
      for the last minute."
   DEFVAL     { 0 }
::= { mscDpnGateUtpFramerUtilEntry 4 }

mscDpnGateUtpFramerUtilThresholdTable OBJECT-TYPE
   SYNTAX     SEQUENCE OF MscDpnGateUtpFramerUtilThresholdEntry
   ACCESS     not-accessible
   STATUS     mandatory
   DESCRIPTION
     "This group contains all of the provisioning data required to set the 
      link utilization alarm thresholds. All thresholds are percentages 
      which can take on any value in the range of 0% through 100%. The 
      value 100% is used to disable an individual threshold. For values 
      other than 100%, a semantic check ensures that the minor alarm 
      threshold is less than the other thresholds and that the major alarm 
      threshold is less than the critical alarm threshold."
::= { mscDpnGateUtpFramer 15 }

mscDpnGateUtpFramerUtilThresholdEntry OBJECT-TYPE
   SYNTAX     MscDpnGateUtpFramerUtilThresholdEntry
   ACCESS     not-accessible
   STATUS     mandatory
   DESCRIPTION
     "An entry in the mscDpnGateUtpFramerUtilThresholdTable."
   INDEX {
      mscDpnGateIndex,
      mscDpnGateUtpIndex,
      mscDpnGateUtpFramerIndex }
::= { mscDpnGateUtpFramerUtilThresholdTable 1 }

MscDpnGateUtpFramerUtilThresholdEntry ::= SEQUENCE {
   mscDpnGateUtpFramerMinorLinkUtilAlarmThreshold
      Unsigned32,
   mscDpnGateUtpFramerMajorLinkUtilAlarmThreshold
      Unsigned32,
   mscDpnGateUtpFramerCriticalLinkUtilAlarmThreshold
      Unsigned32,
   mscDpnGateUtpFramerLinkUtilAlarmStatus
      INTEGER }

mscDpnGateUtpFramerMinorLinkUtilAlarmThreshold OBJECT-TYPE
   SYNTAX     Unsigned32 (0..100)
   ACCESS     read-write
   STATUS     mandatory
   DESCRIPTION
     "This attribute provides the threshold value which defines when a 
      minor alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the minor 
      alarm threshold is less than the other thresholds."
   DEFVAL     { 75 }
::= { mscDpnGateUtpFramerUtilThresholdEntry 1 }

mscDpnGateUtpFramerMajorLinkUtilAlarmThreshold OBJECT-TYPE
   SYNTAX     Unsigned32 (0..100)
   ACCESS     read-write
   STATUS     mandatory
   DESCRIPTION
     "This attribute provides the threshold value which defines when a 
      major alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the major 
      alarm threshold is greater than the minor threshold and less than the 
      critical threshold."
   DEFVAL     { 85 }
::= { mscDpnGateUtpFramerUtilThresholdEntry 2 }

mscDpnGateUtpFramerCriticalLinkUtilAlarmThreshold OBJECT-TYPE
   SYNTAX     Unsigned32 (0..100)
   ACCESS     read-write
   STATUS     mandatory
   DESCRIPTION
     "This attribute provides the threshold value which defines when a 
      critical alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the critical 
      alarm threshold is greater than the other thresholds."
   DEFVAL     { 95 }
::= { mscDpnGateUtpFramerUtilThresholdEntry 3 }

mscDpnGateUtpFramerLinkUtilAlarmStatus OBJECT-TYPE
   SYNTAX     INTEGER  {
                 disabled(0),
                 enabled(1) }
   ACCESS     read-write
   STATUS     mandatory
   DESCRIPTION
     "This attribute provides control of the generation of link utilization 
      alarms. If the value is disabled, none of the alarms are generated 
      (this is equivalent to setting all of the thresholds to 100%). If the 
      value is enabled, the individual thresholds are handled."
   DEFVAL     { disabled }
::= { mscDpnGateUtpFramerUtilThresholdEntry 4 }




-- 
-- Version and Compliance statements
-- 



-- Object-Group Statement:
-- A list of all current accessible leaf objects.

-- OBJECTS { mscDpnGateUtpComponentName,
--           mscDpnGateUtpFramerAborts,
--           mscDpnGateUtpFramerHighPrioLinkUtilToIf,
--           mscDpnGateUtpOperationalState,
--           mscDpnGateUtpFramerFrmModeErrors,
--           mscDpnGateUtpFramerHighPrioLinkUtilFromIf,
--           mscDpnGateUtpFramerOverruns,
--           mscDpnGateUtpFramerMajorLinkUtilAlarmThreshold,
--           mscDpnGateUtpReceiveErrorSensitivity,
--           mscDpnGateUtpFramerRepeatedFrm,
--           mscDpnGateUtpFramerFrameCrcType,
--           mscDpnGateUtpFrmRexmtToIf,
--           mscDpnGateUtpAreYouThereModeEntries,
--           mscDpnGateUtpMaximumErroredInterval,
--           mscDpnGateUtpFramerLrcErrors,
--           mscDpnGateUtpAlarmStatus,
--           mscDpnGateUtpUnknownStatus,
--           mscDpnGateUtpAdminState,
--           mscDpnGateUtpFramerNonOctetErrors,
--           mscDpnGateUtpFramerFrmFromIf64,
--           mscDpnGateUtpRoundTripDelay,
--           mscDpnGateUtpFramerFrmToIf64,
--           mscDpnGateUtpFramerRowStatus,
--           mscDpnGateUtpWindowClosures,
--           mscDpnGateUtpDiscardExcessToIf,
--           mscDpnGateUtpRowStatus,
--           mscDpnGateUtpFramerStorageType,
--           mscDpnGateUtpFramerAdminState,
--           mscDpnGateUtpProceduralStatus,
--           mscDpnGateUtpFramerLinkUtilAlarmStatus,
--           mscDpnGateUtpAvailabilityStatus,
--           mscDpnGateUtpDiscardBadFromIf,
--           mscDpnGateUtpFramerOctetFromIf64,
--           mscDpnGateUtpFramerNormPrioLinkUtilToIf,
--           mscDpnGateUtpFramerUsageState,
--           mscDpnGateUtpControlStatus,
--           mscDpnGateUtpFramerNormPrioLinkUtilFromIf,
--           mscDpnGateUtpFramerCrcErrors,
--           mscDpnGateUtpFramerComponentName,
--           mscDpnGateUtpUsageState,
--           mscDpnGateUtpFramerOutOfSequenceFrm,
--           mscDpnGateUtpFramerUnderruns,
--           mscDpnGateUtpFramerMinorLinkUtilAlarmThreshold,
--           mscDpnGateUtpFramerInterfaceName,
--           mscDpnGateUtpFramerDataInversion,
--           mscDpnGateUtpStandbyStatus,
--           mscDpnGateUtpFramerFramingType,
--           mscDpnGateUtpFramerCriticalLinkUtilAlarmThreshold,
--           mscDpnGateUtpFramerLargeFrmErrors,
--           mscDpnGateUtpFramerFlagsBetweenFrames,
--           mscDpnGateUtpStorageType,
--           mscDpnGateUtpFramerOperationalState }
-- STATUS  mandatory
-- DESCRIPTION
--   "A list of all current accessible leaf objects."

utpDpnTrunksGroup OBJECT IDENTIFIER ::= { utpDpnTrunksMIB 1 }
utpDpnTrunksGroupCA OBJECT IDENTIFIER ::= { utpDpnTrunksGroup 1 }
utpDpnTrunksGroupCA02 OBJECT IDENTIFIER ::= { utpDpnTrunksGroupCA 3 }
utpDpnTrunksGroupCA02A OBJECT IDENTIFIER ::= { utpDpnTrunksGroupCA02 2 }



-- Agent-Capabilities Statement:

-- PRODUCT-RELEASE "MscPassport Release 2.2 UtpDpnTrunks."
-- STATUS          mandatory
-- DESCRIPTION     "Carrier Passport UtpDpnTrunks MIB: MIB Version CA02A,
--                  Software Version CB02S1B."
-- SUPPORTS        Nortel-MsCarrier-MscPassport-UtpDpnTrunksMIB
--    INCLUDES     { utpDpnTrunksGroupCA02A }

utpDpnTrunksCapabilities OBJECT IDENTIFIER ::= { utpDpnTrunksMIB 3 }
utpDpnTrunksCapabilitiesCA OBJECT IDENTIFIER ::= { utpDpnTrunksCapabilities 1 }
utpDpnTrunksCapabilitiesCA02 OBJECT IDENTIFIER ::= { utpDpnTrunksCapabilitiesCA 3 }
utpDpnTrunksCapabilitiesCA02A OBJECT IDENTIFIER ::= { utpDpnTrunksCapabilitiesCA02 2 }





END
