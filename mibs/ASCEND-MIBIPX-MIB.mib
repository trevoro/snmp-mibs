--			Ascend mibipx MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIPX-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibipxGlobalProfile  OBJECT IDENTIFIER ::= { configuration 87}
    mibipxInterfaceProfile  OBJECT IDENTIFIER ::= { configuration 86}

	-- The mibipxGlobalProfile table
	--
	-- This table contains parameters for the mibipxGlobalProfile profile
	--

    mibipxGlobalProfileTable	OBJECT-TYPE
	SYNTAX		SEQUENCE OF MibipxGlobalProfileEntry
	ACCESS		not-accessible
	STATUS		mandatory
	DESCRIPTION	"A list of mibipxGlobalProfile profile entries."
	::= { mibipxGlobalProfile 1 }

    mibipxGlobalProfileEntry	OBJECT-TYPE
	SYNTAX		MibipxGlobalProfileEntry
	ACCESS		not-accessible
	STATUS		mandatory
	DESCRIPTION	"A mibipxGlobalProfile entry containing objects that
			 maps to the parameters of mibipxGlobalProfile profile."
	INDEX		{ ipxGlobalProfile-Index-o }
	::= { mibipxGlobalProfileTable 1 }

    MibipxGlobalProfileEntry ::=
	SEQUENCE {
	    ipxGlobalProfile-Index-o
		INTEGER,
	    ipxGlobalProfile-InterfaceAddress-PhysicalAddress-Shelf
		INTEGER,
	    ipxGlobalProfile-InterfaceAddress-PhysicalAddress-Slot
		INTEGER,
	    ipxGlobalProfile-InterfaceAddress-PhysicalAddress-ItemNumber
		INTEGER,
	    ipxGlobalProfile-InterfaceAddress-LogicalItem
		INTEGER,
	    ipxGlobalProfile-IpxRoutingEnabled
		INTEGER,
	    ipxGlobalProfile-IpxDialinPool
		DisplayString,
	    ipxGlobalProfile-GlobalVrouter
		DisplayString,
	    ipxGlobalProfile-Action-o
		INTEGER
	}

    ipxGlobalProfile-Index-o	OBJECT-TYPE
	SYNTAX	INTEGER
	ACCESS	read-only
	STATUS	mandatory
	DESCRIPTION	""
	::= { mibipxGlobalProfileEntry 1 }

    ipxGlobalProfile-InterfaceAddress-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibipxGlobalProfileEntry 2 }

    ipxGlobalProfile-InterfaceAddress-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibipxGlobalProfileEntry 3 }

    ipxGlobalProfile-InterfaceAddress-PhysicalAddress-ItemNumber	OBJECT-TYPE
	SYNTAX	INTEGER
	ACCESS	read-write
	STATUS	mandatory
	DESCRIPTION	"A number that specifies an addressable entity within the context of shelf and slot."
	::= { mibipxGlobalProfileEntry 4 }

    ipxGlobalProfile-InterfaceAddress-LogicalItem	OBJECT-TYPE
	SYNTAX	INTEGER
	ACCESS	read-write
	STATUS	mandatory
	DESCRIPTION	"A number that specifies an addressable logical entity within the context of a physical address."
	::= { mibipxGlobalProfileEntry 5 }

    ipxGlobalProfile-IpxRoutingEnabled	OBJECT-TYPE
	SYNTAX	INTEGER {
		    no (1),
		    yes (2)
		}
	ACCESS	read-write
	STATUS	mandatory
	DESCRIPTION	"TRUE if this box is currently routing IPX. We don't do IPX routing protocols or packet forwarding if FALSE. Spoofing is independent, not affected by this."
	::= { mibipxGlobalProfileEntry 6 }

    ipxGlobalProfile-IpxDialinPool	OBJECT-TYPE
	SYNTAX	DisplayString
	ACCESS	read-write
	STATUS	mandatory
	DESCRIPTION	"Dialin Pool Numbers to be shared by the ipx wan interfaces"
	::= { mibipxGlobalProfileEntry 7 }

    ipxGlobalProfile-GlobalVrouter	OBJECT-TYPE
	SYNTAX	DisplayString
	ACCESS	read-write
	STATUS	mandatory
	DESCRIPTION	"Specifies the global VRouter."
	::= { mibipxGlobalProfileEntry 8 }

    ipxGlobalProfile-Action-o	OBJECT-TYPE
	SYNTAX	INTEGER {
		    noAction (1),
		    createProfile (2),
		    deleteProfile (3)
		}
	ACCESS	read-write
	STATUS	mandatory
	DESCRIPTION	""
	::= { mibipxGlobalProfileEntry 9 }


	-- The mibipxInterfaceProfile table
	--
	-- This table contains parameters for the mibipxInterfaceProfile profile
	--

    mibipxInterfaceProfileTable	OBJECT-TYPE
	SYNTAX		SEQUENCE OF MibipxInterfaceProfileEntry
	ACCESS		not-accessible
	STATUS		mandatory
	DESCRIPTION	"A list of mibipxInterfaceProfile profile entries."
	::= { mibipxInterfaceProfile 1 }

    mibipxInterfaceProfileEntry	OBJECT-TYPE
	SYNTAX		MibipxInterfaceProfileEntry
	ACCESS		not-accessible
	STATUS		mandatory
	DESCRIPTION	"A mibipxInterfaceProfile entry containing objects that
			 maps to the parameters of mibipxInterfaceProfile profile."
	INDEX		{ ipxInterfaceProfile-Shelf-o, ipxInterfaceProfile-Slot-o, ipxInterfaceProfile-Item-o, ipxInterfaceProfile-LogicalItem-o }
	::= { mibipxInterfaceProfileTable 1 }

    MibipxInterfaceProfileEntry ::=
	SEQUENCE {
	    ipxInterfaceProfile-Shelf-o
		INTEGER,
	    ipxInterfaceProfile-Slot-o
		INTEGER,
	    ipxInterfaceProfile-Item-o
		INTEGER,
	    ipxInterfaceProfile-LogicalItem-o
		INTEGER,
	    ipxInterfaceProfile-InterfaceAddress-PhysicalAddress-Shelf
		INTEGER,
	    ipxInterfaceProfile-InterfaceAddress-PhysicalAddress-Slot
		INTEGER,
	    ipxInterfaceProfile-InterfaceAddress-PhysicalAddress-ItemNumber
		INTEGER,
	    ipxInterfaceProfile-InterfaceAddress-LogicalItem
		INTEGER,
	    ipxInterfaceProfile-IpxRoutingEnabled
		INTEGER,
	    ipxInterfaceProfile-IpxFrame
		INTEGER,
	    ipxInterfaceProfile-IpxNetNumber
		DisplayString,
	    ipxInterfaceProfile-IpxType20
		INTEGER,
	    ipxInterfaceProfile-IpxSapFilterName
		DisplayString,
	    ipxInterfaceProfile-oIPXSAPFilter
		INTEGER,
	    ipxInterfaceProfile-IpxSapProxy
		INTEGER,
	    ipxInterfaceProfile-Vrouter
		DisplayString,
	    ipxInterfaceProfile-Action-o
		INTEGER
	}

    ipxInterfaceProfile-Shelf-o	OBJECT-TYPE
	SYNTAX	INTEGER
	ACCESS	read-only
	STATUS	mandatory
	DESCRIPTION	""
	::= { mibipxInterfaceProfileEntry 1 }

    ipxInterfaceProfile-Slot-o	OBJECT-TYPE
	SYNTAX	INTEGER
	ACCESS	read-only
	STATUS	mandatory
	DESCRIPTION	""
	::= { mibipxInterfaceProfileEntry 2 }

    ipxInterfaceProfile-Item-o	OBJECT-TYPE
	SYNTAX	INTEGER
	ACCESS	read-only
	STATUS	mandatory
	DESCRIPTION	""
	::= { mibipxInterfaceProfileEntry 3 }

    ipxInterfaceProfile-LogicalItem-o	OBJECT-TYPE
	SYNTAX	INTEGER
	ACCESS	read-only
	STATUS	mandatory
	DESCRIPTION	""
	::= { mibipxInterfaceProfileEntry 4 }

    ipxInterfaceProfile-InterfaceAddress-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibipxInterfaceProfileEntry 5 }

    ipxInterfaceProfile-InterfaceAddress-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibipxInterfaceProfileEntry 6 }

    ipxInterfaceProfile-InterfaceAddress-PhysicalAddress-ItemNumber	OBJECT-TYPE
	SYNTAX	INTEGER
	ACCESS	read-write
	STATUS	mandatory
	DESCRIPTION	"A number that specifies an addressable entity within the context of shelf and slot."
	::= { mibipxInterfaceProfileEntry 7 }

    ipxInterfaceProfile-InterfaceAddress-LogicalItem	OBJECT-TYPE
	SYNTAX	INTEGER
	ACCESS	read-write
	STATUS	mandatory
	DESCRIPTION	"A number that specifies an addressable logical entity within the context of a physical address."
	::= { mibipxInterfaceProfileEntry 8 }

    ipxInterfaceProfile-IpxRoutingEnabled	OBJECT-TYPE
	SYNTAX	INTEGER {
		    no (1),
		    yes (2)
		}
	ACCESS	read-write
	STATUS	mandatory
	DESCRIPTION	"TRUE if this box is currently routing IPX. We don't do IPX routing protocols or packet forwarding if FALSE. Spoofing is not affected by this."
	::= { mibipxInterfaceProfileEntry 9 }

    ipxInterfaceProfile-IpxFrame	OBJECT-TYPE
	SYNTAX	INTEGER {
		    none (1),
		    n-8023 (2),
		    n-8022 (3),
		    sNAP (4),
		    enetII (5)
		}
	ACCESS	read-write
	STATUS	mandatory
	DESCRIPTION	"The IPX Frame Type supported in this interface."
	::= { mibipxInterfaceProfileEntry 10 }

    ipxInterfaceProfile-IpxNetNumber	OBJECT-TYPE
	SYNTAX	DisplayString
	ACCESS	read-write
	STATUS	mandatory
	DESCRIPTION	"The network number of the ipx router."
	::= { mibipxInterfaceProfileEntry 11 }

    ipxInterfaceProfile-IpxType20	OBJECT-TYPE
	SYNTAX	INTEGER {
		    no (1),
		    yes (2)
		}
	ACCESS	read-write
	STATUS	mandatory
	DESCRIPTION	"Propogate IPX Type 20 packets (NetBIOS)."
	::= { mibipxInterfaceProfileEntry 12 }

    ipxInterfaceProfile-IpxSapFilterName	OBJECT-TYPE
	SYNTAX	DisplayString
	ACCESS	read-write
	STATUS	mandatory
	DESCRIPTION	"The name of this filter. All filters are referenced by name so a name must be assigned to active filters."
	::= { mibipxInterfaceProfileEntry 13 }

    ipxInterfaceProfile-oIPXSAPFilter	OBJECT-TYPE
	SYNTAX	INTEGER
	ACCESS	read-write
	STATUS	mandatory
	DESCRIPTION	"The number of the IPX SAP Filter assigned to this interface."
	::= { mibipxInterfaceProfileEntry 14 }

    ipxInterfaceProfile-IpxSapProxy	OBJECT-TYPE
	SYNTAX	INTEGER {
		    no (1),
		    yes (2)
		}
	ACCESS	read-write
	STATUS	mandatory
	DESCRIPTION	"Use IPX SAP Proxy."
	::= { mibipxInterfaceProfileEntry 15 }

    ipxInterfaceProfile-Vrouter	OBJECT-TYPE
	SYNTAX	DisplayString
	ACCESS	read-write
	STATUS	mandatory
	DESCRIPTION	"Specifies the VRouter in which this IPX interface profile belongs."
	::= { mibipxInterfaceProfileEntry 16 }

    ipxInterfaceProfile-Action-o	OBJECT-TYPE
	SYNTAX	INTEGER {
		    noAction (1),
		    createProfile (2),
		    deleteProfile (3)
		}
	ACCESS	read-write
	STATUS	mandatory
	DESCRIPTION	""
	::= { mibipxInterfaceProfileEntry 17 }


	-- The mibipxInterfaceProfile__ipx_sap_proxy_net table
	--
	-- This table contains parameters for the mibipxInterfaceProfile__ipx_sap_proxy_net profile
	--

    mibipxInterfaceProfile-IpxSapProxyNetTable	OBJECT-TYPE
	SYNTAX		SEQUENCE OF MibipxInterfaceProfile-IpxSapProxyNetEntry
	ACCESS		not-accessible
	STATUS		mandatory
	DESCRIPTION	"A list of mibipxInterfaceProfile__ipx_sap_proxy_net profile entries."
	::= { mibipxInterfaceProfile 2 }

    mibipxInterfaceProfile-IpxSapProxyNetEntry	OBJECT-TYPE
	SYNTAX		MibipxInterfaceProfile-IpxSapProxyNetEntry
	ACCESS		not-accessible
	STATUS		mandatory
	DESCRIPTION	"A mibipxInterfaceProfile__ipx_sap_proxy_net entry containing objects that
			 maps to the parameters of mibipxInterfaceProfile__ipx_sap_proxy_net profile."
	INDEX		{ ipxInterfaceProfile-IpxSapProxyNet-Shelf-o, ipxInterfaceProfile-IpxSapProxyNet-Slot-o, ipxInterfaceProfile-IpxSapProxyNet-Item-o, ipxInterfaceProfile-IpxSapProxyNet-LogicalItem-o, ipxInterfaceProfile-IpxSapProxyNet-Index-o }
	::= { mibipxInterfaceProfile-IpxSapProxyNetTable 1 }

    MibipxInterfaceProfile-IpxSapProxyNetEntry ::=
	SEQUENCE {
	    ipxInterfaceProfile-IpxSapProxyNet-Shelf-o
		INTEGER,
	    ipxInterfaceProfile-IpxSapProxyNet-Slot-o
		INTEGER,
	    ipxInterfaceProfile-IpxSapProxyNet-Item-o
		INTEGER,
	    ipxInterfaceProfile-IpxSapProxyNet-LogicalItem-o
		INTEGER,
	    ipxInterfaceProfile-IpxSapProxyNet-Index-o
		INTEGER,
	    ipxInterfaceProfile-IpxSapProxyNet
		INTEGER
	}

    ipxInterfaceProfile-IpxSapProxyNet-Shelf-o	OBJECT-TYPE
	SYNTAX	INTEGER
	ACCESS	read-only
	STATUS	mandatory
	DESCRIPTION	""
	::= { mibipxInterfaceProfile-IpxSapProxyNetEntry 1 }

    ipxInterfaceProfile-IpxSapProxyNet-Slot-o	OBJECT-TYPE
	SYNTAX	INTEGER
	ACCESS	read-only
	STATUS	mandatory
	DESCRIPTION	""
	::= { mibipxInterfaceProfile-IpxSapProxyNetEntry 2 }

    ipxInterfaceProfile-IpxSapProxyNet-Item-o	OBJECT-TYPE
	SYNTAX	INTEGER
	ACCESS	read-only
	STATUS	mandatory
	DESCRIPTION	""
	::= { mibipxInterfaceProfile-IpxSapProxyNetEntry 3 }

    ipxInterfaceProfile-IpxSapProxyNet-LogicalItem-o	OBJECT-TYPE
	SYNTAX	INTEGER
	ACCESS	read-only
	STATUS	mandatory
	DESCRIPTION	""
	::= { mibipxInterfaceProfile-IpxSapProxyNetEntry 4 }

    ipxInterfaceProfile-IpxSapProxyNet-Index-o	OBJECT-TYPE
	SYNTAX	INTEGER
	ACCESS	read-only
	STATUS	mandatory
	DESCRIPTION	""
	::= { mibipxInterfaceProfile-IpxSapProxyNetEntry 5 }

    ipxInterfaceProfile-IpxSapProxyNet	OBJECT-TYPE
	SYNTAX	INTEGER
	ACCESS	read-write
	STATUS	mandatory
	DESCRIPTION	"The Network# for IPX SAP Proxy."
	::= { mibipxInterfaceProfile-IpxSapProxyNetEntry 6 }

END
