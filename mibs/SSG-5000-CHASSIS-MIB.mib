-- $Id: SSG-5000-CHASSIS-MIB.my,v 1.14.2.1.2.1 2000/05/26 01:54:40 stevea Exp $ 
SSG-5000-CHASSIS-MIB DEFINITIONS ::= BEGIN

IMPORTS
	TEXTUAL-CONVENTION FROM SNMPv2-TC
	MODULE-IDENTITY,
	OBJECT-TYPE,
	NOTIFICATION-TYPE,
	Counter32,
	Counter64,
	Gauge32,
	Integer32, 
	IpAddress
		FROM SNMPv2-SMI
	DisplayString,
	TruthValue
		FROM SNMPv2-TC
	MODULE-COMPLIANCE,
	OBJECT-GROUP
		FROM SNMPv2-CONF
        ifIndex
                FROM IF-MIB
	shastaExperiment
		FROM SHASTA-MIB;

ssg5000ChassisMIB MODULE-IDENTITY
	LAST-UPDATED	"9907140000Z"
	ORGANIZATION	"Nortel Networks
			 Shasta IP Services Business Unit"
	CONTACT-INFO	"
			 Nortel Networks
			 Shasta IP Services Business Unit
			 Customer Service

		 Postal: 2305 Mission College Boulevard
		 	 Mailstop SC9-C1200
                         Santa Clara, CA 94054
                         USA
 
                 Tel: +1 408 855-3800

		 E-mail: support@shastanets.com"

	DESCRIPTION
		"This MIB provides a means to monitor the status of a SSG
	system's health."

	::= { shastaExperiment 28 }


--
-- This MIB gives you the health status of the SSG system.
-- The health monitoring MIB allows you to monitor health status of the 
-- following items:
--
-- 1. System & CMC configuration, status
-- 2. Slot, configuration, status of all card types
-- 3. SSM, related connections, packet statistics information
-- 4. ALC, related connections, atm cell statistics information
-- 5. Sonet line alarm
--

    PSOperStatus ::= TEXTUAL-CONVENTION
        STATUS    current
        DESCRIPTION
        "Operational status of an SSG-5000 chassis component.
	 A partialFault(5) indicates a partial failure in redundant components.
         A fault(3) value indicates failure in non-redundant component or a
         total failure in redundant component."
        SYNTAX	INTEGER {
			unknown(1),      -- none of the following
                        empty(2),        -- not present
                        ok(3),           -- status ok
                        fault(4),        -- major problem
                        partialFault(5), -- partial failure
			diagFault(6)	 -- diagnostic fault
                        }

    AdminStatus ::= TEXTUAL-CONVENTION
        STATUS    current
        DESCRIPTION
        "Administrative status."
        SYNTAX	INTEGER {
			adminStateDisabled(0),
                        adminStateEnabled(1),
                        adminStateAbsent(2),
			adminStateStandby(3)
                        }

    OperStatus ::= TEXTUAL-CONVENTION
        STATUS    current
        DESCRIPTION
        "Operational status."
        SYNTAX	INTEGER {
			operStateDown(0),
                        operStateUP(1),
                        operStateAbsent(2),
			operStateStandby(3)
                        }

    PsType ::= TEXTUAL-CONVENTION
        STATUS    current
        DESCRIPTION "Power Supply type"
        SYNTAX     INTEGER {    ac264(1),
                                dc48V(2),
                                empty(3)
                                }

    CardType ::= TEXTUAL-CONVENTION
        STATUS    current
        DESCRIPTION "Card type"
        SYNTAX     INTEGER {
                                cardAbsent(0),
                                controlManagementCard(1),
                                subscriberServiceCard(2),
                                switchFabricCard(3),
                                oc3AtmLineCard(4),
                                ds3AtmLineCard(5),
                                hsiLineCard(6),
                                e3AtmLineCard(7),	
				oc12SAtmLineCard(8),
				oc12DAtmLineCard(9),
                                cardTypeUnknown(10),
				ds3ChannelizedFrameCard(11),
				ethnetLineCard(12) 
                                }

    SystemAlarmType ::= TEXTUAL-CONVENTION
        STATUS    current
        DESCRIPTION "System alarm type,
			nodeReboot is an informational event reported when the
			system is administratively rebooted by command.
			PCMCIA card inserted/removed events are only significant
			when user is doing software upgrade with PCMCIA. 
			sysSSMsAreUp is an informational event for sussessful 
			state of complete system hardware startup."
        SYNTAX     INTEGER {
                                nodeDead(1),
                                nodeReboot(2),
                                fanDead(3),
				fanFailure(4),
				temperatureOverheat(5),
				dcPowerFailure(6),
				acDcShelfFailure(7),
				acDcShelfOverheat(8),
				batteryFailure(9),
				batteryOverheat(10),
				pcmciaCardInserted(11),
				pcmciaCardRemoved(12),
				sysSSMsAreUp(13)
				}

    CardAlarmType ::= TEXTUAL-CONVENTION
        STATUS    current
        DESCRIPTION "Card alarm type,
				cardInserted is an positive event of card is up
				in service. 
				cardSwitchToActive is a redundant card event, 
				indicate the card by TrapSlotId is now in the 
				active role.
				cardStandbyNotInRedundant is a redundant card
				event, inidicate if the standby card is in the
				redundant mode or not by TrapOccurClearTag.
				cardStandbyNotInRedundant/SET indicate the card
				is not ready in redundant, may due to it's
				configuration not sync up by any reason." 
        SYNTAX     INTEGER {
                                cardMissing(1),
                                cardInserted(2),
                                cardRemoved(3),
				cardMismatch(4),
				cardBoot(5),
				cardReboot(6),
				cardRevMismatch(7),
				cardFailed(8),
				cardMalfunction(9),
				cardFailDiag(10),
				cardDead(11),
				cardSwitchToActive(12),
				cardStandbyNotInRedundant(13)
				}

    ALCPortAlarmType ::= TEXTUAL-CONVENTION
        STATUS    current
        DESCRIPTION "Port alarm type, an id for port specific alarm,
			Up/Down, indicates port's operational state,
			following are acronyms for ATM interfaces,
			Loop: in loop back state, 
			LOS:  in Lost of Signal state,
			LOF:  in Lost of Frame state,
			LAIS: Line Alarm Indication Signal occurs,
			LRDI: Line Remote Defect Indicator occurs,
			LOP:  in Lost of Pointer occurs,
			PAIS: Path Alarm Indication Signal occurs,
			PRDI: Path Remote Defect Indicator occurs,
			LCD:  in Lost of Cell Delineation state,	 	
			Note, portUp alarm clear port's previous alarms."   
        SYNTAX     INTEGER {
                                portUp(1),
                                portDown(2),
                                portLoop(3),
				portLOS(4),
				portLOF(5),
				portLAIS(6),
				portLRDI(7),
				portLOP(8),
				portPAIS(9),
				portPRDI(10),
				portLCD(11)
				}

    SSMAlarmType ::= TEXTUAL-CONVENTION
        STATUS    current
        DESCRIPTION "SSM alarm type,
				ssmUp indicate SSM is Up and in service, which 
				clear ssm existing alarms."
        SYNTAX     INTEGER {
                                ssmFailed(1),
                                ssmReset(2),
                                ssmUp(3),
				ssmDead(4),
				ssmDown(5)
				}

    CT3PortAlarmType ::= TEXTUAL-CONVENTION
        STATUS    current
        DESCRIPTION "Channelized DS3 port alarm type,
				ct3Up alarm clear previous alarms."
        SYNTAX     INTEGER {
				ct3Failed(1),
				ct3Reset(2),
				ct3Up(3),
				ct3Dead(4),
				ct3Down(5),
				ct3DS3LOS(6),
				ct3DS3OOF(7),
				ct3DS3AIS(8),
				ct3DS3FERF(9),
				ct3DS3RED(10)
				}

    CT3DS2AlarmType ::= TEXTUAL-CONVENTION
        STATUS    current
        DESCRIPTION "Channelized CT3 DS2 channel alarm type"
        SYNTAX     INTEGER {
				ds2OOF(1),
				ds2AIS(2),
				ds2RAI(3)
				}

    CT3DS1AlarmType ::= TEXTUAL-CONVENTION
        STATUS    current
        DESCRIPTION "Channelized CT3 DS1 channel alarm type"
        SYNTAX     INTEGER {
				ds1OOF(1),
				ds1AIS(2),
				ds1RAI(3)
				}

    ServiceAlarmSeverityType ::= TEXTUAL-CONVENTION
        STATUS    current
        DESCRIPTION "Service Level Alarm severity level type"
        SYNTAX     INTEGER {
				infomational(1),
				warning(2),
				critical(3)
				}

    ETHPortAlarmType ::= TEXTUAL-CONVENTION
        STATUS    current
        DESCRIPTION "ETHERNET port alarm type"
        SYNTAX     INTEGER {
				ethLinkDown(1)
				}

    ALARMStateType ::= TEXTUAL-CONVENTION
        STATUS    current
        DESCRIPTION "Alarm state type,
				alarmClear is reverting this alarm's alarm
				state,
				alarmOccur normally indicate the alarm 
				conditions, excepte events of nodeReboot,
				cardBoot, cardRebooted, cardInserted, alcPortUp,				ssmUp, ct3Up." 
        SYNTAX     INTEGER {
                                alarmOccur(1),
                                alarmClear(2)
				}
 
    PVCAlarmType ::= TEXTUAL-CONVENTION
        STATUS    current
        DESCRIPTION "PVC connection alarm type"
        SYNTAX     INTEGER {
                                connectionDown(1)
				}

ssg5000ChassisMIBObjects OBJECT IDENTIFIER ::= { ssg5000ChassisMIB 1 }
ssg5000ChassisGroup OBJECT IDENTIFIER ::= { ssg5000ChassisMIBObjects 1 }
ssg5000SysHealthGroup OBJECT IDENTIFIER ::= { ssg5000ChassisMIBObjects 2 }
ssg5000TrapIndexGroup OBJECT IDENTIFIER ::= { ssg5000ChassisMIBObjects 3 }

-- the SSG5000 chassis group

ssg5000SysStatus OBJECT-TYPE
	SYNTAX		Integer32
	MAX-ACCESS	read-only
	STATUS		current
	DESCRIPTION	"This is a bitmask value that indicates the system 
			 alarms:

			 Bit		Alarm
			 1		NODE_DEAD_ALARM
			 2		NODE_REBOOT_ALARM
			 3		FAN_DEAD_ALARM
			 4		FAN_FAILURE_ALARM
			 5		OVERTEMP_ALARM
			 6		DC_POWER_FAILURE_ALARM
			 7		AC_DC_SHELF_FAILURE_ALARM
			 8		AC_DC_SHELF_OVERTEMP_ALARM
			 9		BATTERY_FAILURE_ALARM
			10		BATTERY_OVERTEMP_ALARM
			11		PCMCIA_CARD_INSERTED_ALARM
			12		PCMCIA_CARD_REMOVED_ALARM
			13		SYS_SSMS_ARE_UP
			"
	::= { ssg5000ChassisGroup 1 }

-- the SSG5000 system health group

ssg5000SysFanStatus OBJECT-TYPE
	SYNTAX		PSOperStatus
	MAX-ACCESS	read-only
	STATUS		current
	DESCRIPTION	"Status of fan."
	::= { ssg5000SysHealthGroup 1 }

ssg5000SysTempStatus OBJECT-TYPE
	SYNTAX		INTEGER {
				ok(1),
				overTemperature(2),
				underTemperature(3)
				}
	MAX-ACCESS	read-only
	STATUS		current
	DESCRIPTION	"ok(1): 	10C <= temperature  <= 40C
			 overTemperature(2): 	temperature > 40C
			 underTemperature(3): 	temperature < 10C."
	::= { ssg5000SysHealthGroup 2 }

ssg5000SysFabricCellsDropped OBJECT-TYPE
	SYNTAX          Counter64
        MAX-ACCESS      read-only
        STATUS          current
        DESCRIPTION     "Number of ATM cells dropped at system fabric."
	::= { ssg5000SysHealthGroup 3 }

ssg5000SysFabricMemUtilization OBJECT-TYPE
	SYNTAX          Integer32
        MAX-ACCESS      read-only
        STATUS          current
        DESCRIPTION     "Memory utilization of system fabric."
	::= { ssg5000SysHealthGroup 4 }

ssg5000SysActiveAccessConn OBJECT-TYPE
	SYNTAX          Integer32
        MAX-ACCESS      read-only
        STATUS          current
        DESCRIPTION     "Number of active connections of access ports."
	::= { ssg5000SysHealthGroup 5 }

ssg5000SysActiveTrunkConn OBJECT-TYPE
	SYNTAX          Integer32
        MAX-ACCESS      read-only
        STATUS          current
        DESCRIPTION     "Number of active connections of trunk ports."
	::= { ssg5000SysHealthGroup 6 }

ssg5000SysPacketsDropped OBJECT-TYPE
	SYNTAX          Integer32
        MAX-ACCESS      read-only
        STATUS          current
        DESCRIPTION     "Number of IP packets dropped of the system."
	::= { ssg5000SysHealthGroup 7 }

ssg5000SysCellsDropped OBJECT-TYPE
	SYNTAX          Counter64
        MAX-ACCESS      read-only
        STATUS          current
        DESCRIPTION     "Number of ATM cells dropped of the system."
	::= { ssg5000SysHealthGroup 8 }

ssg5000CmcCPUIdleTics5Sec OBJECT-TYPE
        SYNTAX          Integer32
        MAX-ACCESS      read-only
        STATUS          current
        DESCRIPTION     "CMC's CPU Idle Tics over 5 seconds duration."
        ::= { ssg5000SysHealthGroup 9 }
 
ssg5000CmcCPUTotalTics5Sec OBJECT-TYPE
        SYNTAX          Integer32
        MAX-ACCESS      read-only
        STATUS          current
        DESCRIPTION     "CMC's CPU Tics over 5 seconds duration."
        ::= { ssg5000SysHealthGroup 10 }
 
ssg5000CmcCPUIdleTicsReboot OBJECT-TYPE
        SYNTAX          Integer32
        MAX-ACCESS      read-only
        STATUS          current
        DESCRIPTION     "CMC's CPU Idle Tics since system reboot."
        ::= { ssg5000SysHealthGroup 11 }
 
ssg5000CmcCPUTotalTicsReboot OBJECT-TYPE
        SYNTAX          Integer32
        MAX-ACCESS      read-only
        STATUS          current
        DESCRIPTION     "CMC's CPU Tics since system reboot."
        ::= { ssg5000SysHealthGroup 12 }
 
ssg5000CmcCPUMemHeapFree OBJECT-TYPE
        SYNTAX          Integer32
        MAX-ACCESS      read-only
        STATUS          current
        DESCRIPTION     "CMC's free memory Heap measurement."
        ::= { ssg5000SysHealthGroup 13 }
 
ssg5000CmcCPUMemHeapTotal OBJECT-TYPE
        SYNTAX          Integer32
        MAX-ACCESS      read-only
        STATUS          current
        DESCRIPTION     "CMC's total memory Heap measurement."
        ::= { ssg5000SysHealthGroup 14 }

ssg5000CmcCPUMBufClusterFree OBJECT-TYPE
        SYNTAX          Integer32
        MAX-ACCESS      read-only
        STATUS          current
        DESCRIPTION     "CMC's free MBuf Cluster."
        ::= { ssg5000SysHealthGroup 15 }
 
ssg5000CmcCPUMBufClusterTotal OBJECT-TYPE
        SYNTAX          Integer32
        MAX-ACCESS      read-only
        STATUS          current
        DESCRIPTION     "CMC's total MBuf Cluster."
        ::= { ssg5000SysHealthGroup 16 }

ssg5000CmcCPUAverageLoad OBJECT-TYPE
        SYNTAX          Integer32
        MAX-ACCESS      read-only
        STATUS          current
        DESCRIPTION     "System CMC's average cpu load (%)."
        ::= { ssg5000SysHealthGroup 17 }

ssg5000SspCPUnoEncryptionAverageLoad OBJECT-TYPE
        SYNTAX          Integer32
        MAX-ACCESS      read-only
        STATUS          current
        DESCRIPTION     "System SSPs with no Encryption average cpu load (%)."
        ::= { ssg5000SysHealthGroup 18 }

ssg5000SspCPUwEncryptionAverageLoad OBJECT-TYPE
        SYNTAX          Integer32
        MAX-ACCESS      read-only
        STATUS          current
        DESCRIPTION     "System SSPs with Encryption average cpu load (%)."
        ::= { ssg5000SysHealthGroup 19 }


-- SSG-5000 Slot information table

ssg5000SlotTable OBJECT-TYPE
	SYNTAX		SEQUENCE OF Ssg5000SlotEntry
	MAX-ACCESS	not-accessible
	STATUS		current
	DESCRIPTION	"A list of slot entries."
	::= { ssg5000ChassisGroup 2 }

ssg5000SlotEntry OBJECT-TYPE
	SYNTAX		Ssg5000SlotEntry
	MAX-ACCESS	not-accessible
	STATUS		current
	DESCRIPTION	"Entry containing information about card status in
			 a slot of the chassis. A slot could contain no card." 
	INDEX		{ ssg5000SlotIndex }
	::= { ssg5000SlotTable 1 }

Ssg5000SlotEntry ::= 
	SEQUENCE {
		ssg5000SlotIndex
			Integer32,
		ssg5000SlotCardType
			CardType,
		ssg5000SlotCardDescr
			DisplayString,
		ssg5000SlotAdminStatus
			AdminStatus,
		ssg5000SlotOperStatus
			OperStatus,
		ssg5000SlotCardNumPorts
			Integer32,
		ssg5000SlotCardHwVersion
			DisplayString,	
		ssg5000SlotCardSerialNumber
			DisplayString,
		ssg5000SlotAlarms
			Integer32
		}

ssg5000SlotIndex OBJECT-TYPE
	SYNTAX		Integer32 (1..14)
	MAX-ACCESS	read-only
	STATUS		current
	DESCRIPTION	"Unique index for indexing the slots."
	::= { ssg5000SlotEntry 1 }

ssg5000SlotCardType	OBJECT-TYPE
	SYNTAX		CardType
	MAX-ACCESS	read-only
	STATUS		current
	DESCRIPTION	"The type of card in the slot."
	::= { ssg5000SlotEntry 2 }
				
ssg5000SlotCardDescr	OBJECT-TYPE
	SYNTAX		DisplayString
	MAX-ACCESS	read-only
	STATUS		current
	DESCRIPTION	"A Description of the card in the slot." 
	::= { ssg5000SlotEntry 3 }

ssg5000SlotAdminStatus OBJECT-TYPE
        SYNTAX		AdminStatus
	MAX-ACCESS	read-only
	STATUS		current
	DESCRIPTION	"The Administrative status of the card."
	::= { ssg5000SlotEntry 4 }

ssg5000SlotOperStatus OBJECT-TYPE
        SYNTAX		OperStatus
	MAX-ACCESS	read-only
	STATUS		current
	DESCRIPTION	"The Operational status of the card."
	::= { ssg5000SlotEntry 5 }

ssg5000SlotCardNumPorts OBJECT-TYPE
	SYNTAX		Integer32
	MAX-ACCESS	read-only
	STATUS		current
	DESCRIPTION	"The number of ports equipped in this card."
	::= { ssg5000SlotEntry 6 }

ssg5000SlotCardHwVersion OBJECT-TYPE
	SYNTAX		DisplayString
	MAX-ACCESS	read-only
	STATUS		current
	DESCRIPTION	"The hardware version fo the card."
	::= { ssg5000SlotEntry 7 }

ssg5000SlotCardSerialNumber OBJECT-TYPE
	SYNTAX		DisplayString
	MAX-ACCESS	read-only
	STATUS		current
	DESCRIPTION	"The serial number of the card."
	::= { ssg5000SlotEntry 8 }

ssg5000SlotAlarms OBJECT-TYPE
	SYNTAX		Integer32
	MAX-ACCESS	read-only
	STATUS		current
	DESCRIPTION	"The bitmask value that carry card's alarms,
                         Bit            Alarm
                         1              CARD_MISSING_ALARM
                         2              CARD_INSERTED_ALARM
                         3              CARD_REMOVED_ALARM
                         4              CARD_MISMATCH_ALARM
                         5              CARD_BOOT_ALARM
                         6              CARD_REBOOT_ALARM
                         7              CARD_REV_MISMATCH_ALARM
                         8              CARD_FAILED_ALARM
                         9              CARD_MALFUNCTION_ALARM
                        10              CARD_FAILED_DIAG_ALARM
                        11              CARD_DEAD_ALARM
			12		CARD_SWITCH_TO_ACTIVE
			13		CARD_STANDBY_NOT_IN_REDUNDANT
                        "
	::= { ssg5000SlotEntry 9 }

-- SSM group statistic table

ssg5000SSMStatTable OBJECT-TYPE
	SYNTAX		SEQUENCE OF Ssg5000SSMStatEntry
	MAX-ACCESS	not-accessible
	STATUS		current
	DESCRIPTION	"Table of SSM port statistics information."
	::= { ssg5000ChassisGroup 3 }

ssg5000SSMStatEntry OBJECT-TYPE
	SYNTAX		Ssg5000SSMStatEntry
	MAX-ACCESS	not-accessible
	STATUS		current
	DESCRIPTION	"An entry in the table, containing information
			 about a SSM port."
	INDEX	{ ssg5000SlotIndex,
		  ssg5000SSMIndex }
	::= { ssg5000SSMStatTable 1 }

Ssg5000SSMStatEntry ::= 
	SEQUENCE {
		ssg5000SSMIndex
			Integer32,
		ssg5000SSMAdminStatus
			AdminStatus,
		ssg5000SSMOperStatus
			OperStatus,
		ssg5000SSMCPUIdleTics5Sec
			Integer32,
		ssg5000SSMCPUTics5Sec
			Integer32,
		ssg5000SSMCPUIdleTicsReboot
			Integer32,
		ssg5000SSMCPUTicsReboot
			Integer32,
		ssg5000SSMCPUMemHeapFree
			Integer32,
		ssg5000SSMCPUMemHeapTotal
			Integer32,
		ssg5000SSMCPUMBufClusterFree
			Integer32,
		ssg5000SSMCPUMBufClusterTotal
			Integer32,
		ssg5000SSMActiveAccessConn
			Integer32,
		ssg5000SSMActiveSubscribers
			Integer32,
		ssg5000SSMPacketsDropped
			Integer32,
		ssg5000SSMPacketsForwarded
			Integer32,
		ssg5000SSMAlarms
			Integer32
		}

ssg5000SSMIndex OBJECT-TYPE
	SYNTAX		Integer32
        MAX-ACCESS      read-only
        STATUS          current
        DESCRIPTION     "An arbitrary integer value to uniquely identify
                         a SSM module/port entry in a SSC card."
        ::= { ssg5000SSMStatEntry 1 }

ssg5000SSMAdminStatus	OBJECT-TYPE
	SYNTAX		AdminStatus
	MAX-ACCESS	read-only
	STATUS		current
	DESCRIPTION	"A Administrative status of the SSM."
	::= { ssg5000SSMStatEntry 2 }

ssg5000SSMOperStatus	OBJECT-TYPE
	SYNTAX		OperStatus
	MAX-ACCESS	read-only
	STATUS		current
	DESCRIPTION	"A Operational status of the SSM."
	::= { ssg5000SSMStatEntry 3 }

ssg5000SSMCPUIdleTics5Sec OBJECT-TYPE
	SYNTAX	    	Integer32
	MAX-ACCESS  	read-only
	STATUS	    	current
	DESCRIPTION	"CPU Idle Tics over 5 seconds duration of the SSM." 
	::= { ssg5000SSMStatEntry 4 }

ssg5000SSMCPUTics5Sec OBJECT-TYPE
	SYNTAX          Integer32
        MAX-ACCESS      read-only
        STATUS          current
	DESCRIPTION	"CPU Tics over 5 seconds duration of the SSM." 
	::= { ssg5000SSMStatEntry 5 }

ssg5000SSMCPUIdleTicsReboot OBJECT-TYPE
	SYNTAX	    	Integer32
	MAX-ACCESS  	read-only
	STATUS	    	current
	DESCRIPTION	"CPU Idle Tics since reboot of the SSM." 
	::= { ssg5000SSMStatEntry 6 }

ssg5000SSMCPUTicsReboot OBJECT-TYPE
	SYNTAX          Integer32
        MAX-ACCESS      read-only
        STATUS          current
	DESCRIPTION	"CPU Tics since reboot of the SSM." 
	::= { ssg5000SSMStatEntry 7 }

ssg5000SSMCPUMemHeapFree OBJECT-TYPE
	SYNTAX		Integer32
	MAX-ACCESS	read-only
	STATUS		current
	DESCRIPTION	"Free Memory in the Heap of the the SSM."
	::= { ssg5000SSMStatEntry 8 }

ssg5000SSMCPUMemHeapTotal OBJECT-TYPE
	SYNTAX          Integer32
        MAX-ACCESS      read-only
        STATUS          current
	DESCRIPTION	"Total Memory in the Heap of the the SSM."
	::= { ssg5000SSMStatEntry 9 }

ssg5000SSMCPUMBufClusterFree OBJECT-TYPE
	SYNTAX		Integer32
	MAX-ACCESS	read-only
	STATUS		current
	DESCRIPTION	"Free MBuf cluster in the CPU of the SSM."
	::= { ssg5000SSMStatEntry 10 }

ssg5000SSMCPUMBufClusterTotal OBJECT-TYPE
	SYNTAX          Integer32
	MAX-ACCESS      read-only
        STATUS          current
	DESCRIPTION	"Total MBuf cluster in the CPU of the SSM."
	::= { ssg5000SSMStatEntry 11 }

ssg5000SSMActiveAccessConn OBJECT-TYPE
	SYNTAX		Integer32
	MAX-ACCESS      read-only
        STATUS          current
        DESCRIPTION     "Number of Active Access connection on this SSM."
	::= { ssg5000SSMStatEntry 12 }

ssg5000SSMActiveSubscribers OBJECT-TYPE
	SYNTAX          Integer32
        MAX-ACCESS      read-only
        STATUS          current
        DESCRIPTION     "Number of Active subscribers on this SSM."
	::= { ssg5000SSMStatEntry 13 }

ssg5000SSMPacketsDropped OBJECT-TYPE
	SYNTAX		Integer32
	MAX-ACCESS	read-only
	STATUS		current
	DESCRIPTION	"Number of packets been dropped from this SSM."
	::= { ssg5000SSMStatEntry 14 }

ssg5000SSMPacketsForwarded OBJECT-TYPE
	SYNTAX		Integer32
	MAX-ACCESS	read-only
	STATUS		current
	DESCRIPTION	"Number of packets been forwarded from this SSM."
	::= { ssg5000SSMStatEntry 15 }

ssg5000SSMAlarms OBJECT-TYPE
	SYNTAX		Integer32
	MAX-ACCESS	read-only
	STATUS		current
	DESCRIPTION	"The bitmask value that carry SSM's alarms,
			Bit            Alarm
                         1              SSM_FAILED_ALARM
                         2              SSM_RESET_ALARM
                         3              SSM_UP_ALARM
                         4              SSM_DIED_ALARM
                         5              SSM_DOWN_ALARM
                        "
	::= { ssg5000SSMStatEntry 16 }

-- ALC Port statistic table

ssg5000ALCPortStatTable OBJECT-TYPE
	SYNTAX		SEQUENCE OF Ssg5000ALCPortStatEntry
	MAX-ACCESS	not-accessible
	STATUS		current
	DESCRIPTION	"Table of port (ATM Line Card) statistics information,
			table will list instances of OC3, DS3/E3 not ETH, CT3"
	::= { ssg5000ChassisGroup 4 }

ssg5000ALCPortStatEntry OBJECT-TYPE
	SYNTAX		Ssg5000ALCPortStatEntry
	MAX-ACCESS	not-accessible
	STATUS		current
	DESCRIPTION	"An entry in the table, containing information
			about an ATM access or trunk port."
	INDEX { ssg5000SlotIndex,
		ssg5000ALCPortIndex}
	::= { ssg5000ALCPortStatTable 1 }

Ssg5000ALCPortStatEntry ::= 
	SEQUENCE {
		ssg5000ALCPortIndex
			Integer32,
		ssg5000ALCPortIfIndex
			Integer32,
		ssg5000ALCPortAdminStatus
			AdminStatus,
		ssg5000ALCPortOperStatus
			OperStatus,
		ssg5000ALCPortActiveAccessConn
			Integer32,
		ssg5000ALCPortActiveTrunkConn
			Integer32,
		ssg5000ALCPortCellsReceived
			Counter64,
		ssg5000ALCPortCellsTransmitted
			Counter64,
		ssg5000ALCPortCellsDropped
			Counter64,
		ssg5000ALCPortAlarms
			Integer32
		}

ssg5000ALCPortIndex OBJECT-TYPE
	SYNTAX		Integer32
	MAX-ACCESS	read-only
	STATUS		current
	DESCRIPTION	"The ALC port index of an ALC card." 
	::= { ssg5000ALCPortStatEntry 1 }

ssg5000ALCPortIfIndex OBJECT-TYPE
	SYNTAX		Integer32
	MAX-ACCESS	read-only
	STATUS		current
	DESCRIPTION	"The MIBII ifIndex value assigned to this port."
	::= { ssg5000ALCPortStatEntry 2 }

ssg5000ALCPortAdminStatus OBJECT-TYPE
	SYNTAX		AdminStatus
	MAX-ACCESS      read-only
	STATUS          current
	DESCRIPTION     "The Administrative status of the ALC port."
	::= { ssg5000ALCPortStatEntry 3 }

ssg5000ALCPortOperStatus OBJECT-TYPE
	SYNTAX		OperStatus
	MAX-ACCESS      read-only
	STATUS          current
	DESCRIPTION     "The Operational status of the ALC port."
	::= { ssg5000ALCPortStatEntry 4 }

ssg5000ALCPortActiveAccessConn OBJECT-TYPE
	SYNTAX	    	Integer32
	MAX-ACCESS  	read-only
	STATUS	    	current
	DESCRIPTION	"The Active Access connections on the ALC port."
	::= { ssg5000ALCPortStatEntry 5 }

ssg5000ALCPortActiveTrunkConn OBJECT-TYPE
	SYNTAX	    	Integer32
	MAX-ACCESS  	read-only
	STATUS	    	current
	DESCRIPTION	"The Active Trunk connections on the ALC port."
	::= { ssg5000ALCPortStatEntry 6 }

ssg5000ALCPortCellsReceived OBJECT-TYPE
	SYNTAX		Counter64
	MAX-ACCESS      read-only
        STATUS          current
	DESCRIPTION	"The ATM cells received on this ALC port."
	::= { ssg5000ALCPortStatEntry 7 }

ssg5000ALCPortCellsTransmitted OBJECT-TYPE
	SYNTAX		Counter64
	MAX-ACCESS	read-only
	STATUS		current
	DESCRIPTION	"The ATM cells transmitted on this ALC port."
	::= { ssg5000ALCPortStatEntry 8 }

ssg5000ALCPortCellsDropped OBJECT-TYPE
	SYNTAX          Counter64
	MAX-ACCESS	read-only
	STATUS		current
	DESCRIPTION	"The ATM cells dropped on this ALC port."
	::= { ssg5000ALCPortStatEntry 9 }

ssg5000ALCPortAlarms OBJECT-TYPE
	SYNTAX          Integer32
	MAX-ACCESS	read-only
	STATUS		current
	DESCRIPTION	"The bitmask value that carry port's alarms,
			bitmap [32,...          ,9,8,7,6,5,4,3,2,1],
			refer ALCPortAlarmType for ATM interface alarm acronyms.      	 
                         Bit            Alarm
                         1              ALC_PORT_UP_ALARM
                         2              ALC_PORT_DOWN_ALARM
                         3              ALC_PORT_LOOP_ALARM
                         4              ALC_PORT_LOS_ALARM
                         5              ALC_PORT_LOF_ALARM
                         6              ALC_PORT_LAIS_ALARM
                         7              ALC_PORT_LRDI_ALARM
                         8              ALC_PORT_LOP_ALARM
                         9              ALC_PORT_PAIS_ALARM
                        10              ALC_PORT_PRDI_ALARM
                        11              ALC_PORT_LCD_ALARM
                        "
	::= { ssg5000ALCPortStatEntry 10 }

-- ETH Port statistic table

ssg5000ETHPortStatTable OBJECT-TYPE
	SYNTAX		SEQUENCE OF Ssg5000ETHPortStatEntry
	MAX-ACCESS	not-accessible
	STATUS		current
	DESCRIPTION	"Table of ETH port information,
			table will list instances of ETH port."
	::= { ssg5000ChassisGroup 5 }

ssg5000ETHPortStatEntry OBJECT-TYPE
	SYNTAX		Ssg5000ETHPortStatEntry
	MAX-ACCESS	not-accessible
	STATUS		current
	DESCRIPTION	"An entry in the table, containing information
			about an Ethernet port."
	INDEX { ssg5000SlotIndex,
		ssg5000ETHPortIndex}
	::= { ssg5000ETHPortStatTable 1 }

Ssg5000ETHPortStatEntry ::= 
	SEQUENCE {
		ssg5000ETHPortIndex
			Integer32,
		ssg5000ETHPortAdminStatus
			AdminStatus,
		ssg5000ETHPortOperStatus
			OperStatus,
		ssg5000ETHPortAlarms
			Integer32
	}

ssg5000ETHPortIndex OBJECT-TYPE
	SYNTAX		Integer32
	MAX-ACCESS	read-only
	STATUS		current
	DESCRIPTION	"The ETH port index." 
	::= { ssg5000ETHPortStatEntry 1 }

ssg5000ETHPortAdminStatus OBJECT-TYPE
	SYNTAX		AdminStatus
	MAX-ACCESS      read-only
	STATUS          current
	DESCRIPTION     "The Administrative status of the ETH port."
	::= { ssg5000ETHPortStatEntry 2 }

ssg5000ETHPortOperStatus OBJECT-TYPE
	SYNTAX		OperStatus
	MAX-ACCESS      read-only
	STATUS          current
	DESCRIPTION     "The Operational status of the ETH port."
	::= { ssg5000ETHPortStatEntry 3 }

ssg5000ETHPortAlarms OBJECT-TYPE
	SYNTAX          Integer32
	MAX-ACCESS	read-only
	STATUS		current
	DESCRIPTION	"The bitmask value that ETH port's alarms,
			bitmap [32,...          ,9,8,7,6,5,4,3,2,1],
			refer ETHPortAlarmType for alarm acronyms.      	 
                         Bit            Alarm
                         1              ETH_LINK_DOWN_ALARM
                         2              ETH_LINK_UP_ALARM
                        "
	::= { ssg5000ETHPortStatEntry 4 }

-- CT3 Port statistic table

ssg5000CT3PortStatTable OBJECT-TYPE
	SYNTAX		SEQUENCE OF Ssg5000CT3PortStatEntry
	MAX-ACCESS	not-accessible
	STATUS		current
	DESCRIPTION	"Table of CT3 port information,
			table will list instances of CT3 port."
	::= { ssg5000ChassisGroup 6 }

ssg5000CT3PortStatEntry OBJECT-TYPE
	SYNTAX		Ssg5000CT3PortStatEntry
	MAX-ACCESS	not-accessible
	STATUS		current
	DESCRIPTION	"An entry in the table, containing information
			about an CT3 port."
	INDEX { ssg5000SlotIndex,
		ssg5000CT3PortIndex}
	::= { ssg5000CT3PortStatTable 1 }

Ssg5000CT3PortStatEntry ::= 
	SEQUENCE {
		ssg5000CT3PortIndex
			Integer32,
		ssg5000CT3PortAdminStatus
			AdminStatus,
		ssg5000CT3PortOperStatus
			OperStatus,
		ssg5000CT3PortAlarms
			Integer32
	}

ssg5000CT3PortIndex OBJECT-TYPE
	SYNTAX		Integer32
	MAX-ACCESS	read-only
	STATUS		current
	DESCRIPTION	"The CT3 port index." 
	::= { ssg5000CT3PortStatEntry 1 }

ssg5000CT3PortAdminStatus OBJECT-TYPE
	SYNTAX		AdminStatus
	MAX-ACCESS      read-only
	STATUS          current
	DESCRIPTION     "The Administrative status of the CT3 port."
	::= { ssg5000CT3PortStatEntry 2 }

ssg5000CT3PortOperStatus OBJECT-TYPE
	SYNTAX		OperStatus
	MAX-ACCESS      read-only
	STATUS          current
	DESCRIPTION     "The Operational status of the CT3 port."
	::= { ssg5000CT3PortStatEntry 3 }

ssg5000CT3PortAlarms OBJECT-TYPE
	SYNTAX          Integer32
	MAX-ACCESS	read-only
	STATUS		current
	DESCRIPTION	"The bitmask value that CT3 port's alarms,
			bitmap [32,...          ,9,8,7,6,5,4,3,2,1],
			refer CT3PortAlarmType for alarm acronyms.      	 
                         Bit            Alarm
                         1              CT3_FAILED_ALARM
                         2              CT3_RESET_ALARM
                         3              CT3_UP_ALARM
                         4              CT3_DIED_ALARM
                         5              CT3_DOWN_ALARM
                         6              CT3_DS3_LOS_ALARM
                         7              CT3_DS3_OOF_ALARM
                         8              CT3_DS3_AIS_ALARM
                         9              CT3_DS3_RERF_ALARM
                         10             CT3_DS3_RED_ALARM
                        "
	::= { ssg5000CT3PortStatEntry 4 }

-- the following are place holder objects used by Notifications
-- ssg5000TrapIndexGroup
ssg5000TrapSystemAlarmId OBJECT-TYPE
	SYNTAX		SystemAlarmType
	MAX-ACCESS	not-accessible
	STATUS		current
	DESCRIPTION	"A trap ID object for system alarm."
	::= { ssg5000TrapIndexGroup 1 }

ssg5000TrapCardAlarmId OBJECT-TYPE
	SYNTAX		CardAlarmType
	MAX-ACCESS	not-accessible
	STATUS		current
	DESCRIPTION	"A trap ID object for card alarm."
	::= { ssg5000TrapIndexGroup 2 }

ssg5000TrapALCPortAlarmId OBJECT-TYPE
	SYNTAX		ALCPortAlarmType
	MAX-ACCESS	not-accessible
	STATUS		current
	DESCRIPTION	"A trap ID object for (ALC) port alarm."
	::= { ssg5000TrapIndexGroup 3 }

ssg5000TrapSSMAlarmId OBJECT-TYPE
	SYNTAX		SSMAlarmType
	MAX-ACCESS	not-accessible
	STATUS		current
	DESCRIPTION	"A trap ID object for ssm alarm."
	::= { ssg5000TrapIndexGroup 4 }

ssg5000TrapSlotId OBJECT-TYPE
	SYNTAX		Integer32
	MAX-ACCESS	not-accessible
	STATUS		current
	DESCRIPTION	"A trap slot ID for slot number."
	::= { ssg5000TrapIndexGroup 5 }

ssg5000TrapCardType OBJECT-TYPE
	SYNTAX		CardType
	MAX-ACCESS	not-accessible
	STATUS		current
	DESCRIPTION	"A trap card ID for slot card type."
	::= { ssg5000TrapIndexGroup 6 }

ssg5000TrapPortId OBJECT-TYPE
	SYNTAX		Integer32
	MAX-ACCESS	not-accessible
	STATUS		current
	DESCRIPTION	"A trap port ID for port number."
	::= { ssg5000TrapIndexGroup 7 }

ssg5000TrapOccurClearTag OBJECT-TYPE
	SYNTAX		ALARMStateType
	MAX-ACCESS	not-accessible
	STATUS		current
	DESCRIPTION	"A trap state indicating occur or clear."
	::= { ssg5000TrapIndexGroup 8 }

ssg5000TrapPVCAlarmId OBJECT-TYPE
	SYNTAX		PVCAlarmType
	MAX-ACCESS	not-accessible
	STATUS		current
	DESCRIPTION	"A trap connection alarm ID for PVC connection alarm."
	::= { ssg5000TrapIndexGroup 9 }

ssg5000TrapInterfaceNumber OBJECT-TYPE
	SYNTAX		Integer32
	MAX-ACCESS	not-accessible
	STATUS		current
	DESCRIPTION	"A trap interface ID for connection alarm."
	::= { ssg5000TrapIndexGroup 10 }

ssg5000TrapVPINumber OBJECT-TYPE
	SYNTAX		Integer32
	MAX-ACCESS	not-accessible
	STATUS		current
	DESCRIPTION	"A trap variable object for Connection VPI number."
	::= { ssg5000TrapIndexGroup 11 }

ssg5000TrapVCINumber OBJECT-TYPE
	SYNTAX		Integer32
	MAX-ACCESS	not-accessible
	STATUS		current
	DESCRIPTION	"A trap variable object for Connection VCI number."
	::= { ssg5000TrapIndexGroup 12 }

ssg5000TrapCT3PortAlarmId OBJECT-TYPE
	SYNTAX		CT3PortAlarmType
	MAX-ACCESS	not-accessible
	STATUS		current
	DESCRIPTION	"A trap ID object for CT3 port alarm."
	::= { ssg5000TrapIndexGroup 13 }

ssg5000TrapETHPortAlarmId OBJECT-TYPE
	SYNTAX		ETHPortAlarmType
	MAX-ACCESS	not-accessible
	STATUS		current
	DESCRIPTION	"A trap ID object for ETH port alarm."
	::= { ssg5000TrapIndexGroup 14 }

ssg5000TrapSSGHostAddress OBJECT-TYPE
	SYNTAX		IpAddress
	MAX-ACCESS	not-accessible
	STATUS		current
	DESCRIPTION	"A trap ID object indicating the SSG this trap
			is origionated, this is needed and informational
			when the trap is forwarded by Nortel-Shasta's  
			Service Creation System manager to 3rd Party NMS."
	::= { ssg5000TrapIndexGroup 15 }

ssg5000TrapCT3DS2AlarmId OBJECT-TYPE
	SYNTAX		CT3DS2AlarmType
	MAX-ACCESS	not-accessible
	STATUS		current
	DESCRIPTION	"A trap ID object for CT3 DS2 alarm."  
	::= { ssg5000TrapIndexGroup 16 }

ssg5000TrapCT3DS1AlarmId OBJECT-TYPE
	SYNTAX		CT3DS1AlarmType
	MAX-ACCESS	not-accessible
	STATUS		current
	DESCRIPTION	"A trap ID object for CT3 DS1 alarm."  
	::= { ssg5000TrapIndexGroup 17 }

ssg5000TrapDS2ChannelId OBJECT-TYPE
	SYNTAX		Integer32
	MAX-ACCESS	not-accessible
	STATUS		current
	DESCRIPTION	"A trap ID object for indicating a DS2 channel." 
	::= { ssg5000TrapIndexGroup 18 }

ssg5000TrapDS1ChannelId OBJECT-TYPE
	SYNTAX		Integer32
	MAX-ACCESS	not-accessible
	STATUS		current
	DESCRIPTION	"A trap ID object for indicating a DS1 channel." 
	::= { ssg5000TrapIndexGroup 19 }

ssg5000TrapServiceModuleAlarm OBJECT-TYPE
	SYNTAX		DisplayString
	MAX-ACCESS	not-accessible
	STATUS		current
	DESCRIPTION	"A trap object for showing a SSG Service Module." 
	::= { ssg5000TrapIndexGroup 20 }

ssg5000TrapServiceAlarmSeverity OBJECT-TYPE
	SYNTAX		ServiceAlarmSeverityType
	MAX-ACCESS	not-accessible
	STATUS		current
	DESCRIPTION	"A trap object for indicating Service Alarm Severity." 
	::= { ssg5000TrapIndexGroup 21 }

ssg5000TrapServiceAlarmDescription OBJECT-TYPE
	SYNTAX		DisplayString
	MAX-ACCESS	not-accessible
	STATUS		current
	DESCRIPTION	"A trap object for describing a Service Alarm." 
	::= { ssg5000TrapIndexGroup 22 }


-- the following two OBJECT IDENTIFIERS are used to define SNMPv2 Notifications
-- that are backward compatable with SNMPv1 Traps.

ssg5000MIBNotificationPrefix OBJECT IDENTIFIER ::= { ssg5000ChassisMIB 2 }
ssg5000MIBNotification OBJECT IDENTIFIER ::= { ssg5000MIBNotificationPrefix 0 }

ssg5000ChassisFailureNotification NOTIFICATION-TYPE
        OBJECTS {
		ssg5000SysFanStatus,
		ssg5000SysTempStatus,
		ssg5000TrapSSGHostAddress
		}
	STATUS  current
        DESCRIPTION
		"The notification signifies that the agent detects a change in
		 the status of ps1, ps2, fan, chassis temperature."
	::= { ssg5000MIBNotification 1 }

ssg5000SysAlarmNotification NOTIFICATION-TYPE
	OBJECTS {
		ssg5000TrapSystemAlarmId,
		ssg5000TrapOccurClearTag,
		ssg5000TrapSSGHostAddress
		}
	STATUS  current
        DESCRIPTION
		"The notification signal the agenet detects an alarm status
		 in the system."
	::= { ssg5000MIBNotification 2 }

ssg5000CardAlarmNotification NOTIFICATION-TYPE
	OBJECTS {
		ssg5000TrapCardAlarmId,
		ssg5000TrapSlotId,
		ssg5000TrapCardType,
		ssg5000TrapOccurClearTag,
		ssg5000TrapSSGHostAddress
		}
	STATUS  current
        DESCRIPTION
		"The notification signal the agenet detects an alarm status 
		 in the card."
	::= { ssg5000MIBNotification 3 }

ssg5000PortAlarmNotification NOTIFICATION-TYPE
	OBJECTS {
		ssg5000TrapALCPortAlarmId,
		ssg5000TrapSlotId,
		ssg5000TrapCardType,
		ssg5000TrapPortId,
		ssg5000TrapOccurClearTag,
		ssg5000TrapSSGHostAddress
		}
	STATUS  current
        DESCRIPTION
		"The notification signal the agenet detects an alarm status
		 in the port."
	::= { ssg5000MIBNotification 4 }

ssg5000SSMAlarmNotification NOTIFICATION-TYPE
	OBJECTS {
		ssg5000TrapSSMAlarmId,
		ssg5000TrapSlotId,
		ssg5000TrapCardType,
		ssg5000TrapPortId,
		ssg5000TrapOccurClearTag,
		ssg5000TrapSSGHostAddress
		}
	STATUS  current
        DESCRIPTION
		"The notification signal the agenet detects an alarm status
		 in the SSM."
	::= { ssg5000MIBNotification 5 }

ssg5000PVCAlarmNotification NOTIFICATION-TYPE
	OBJECTS {
		ssg5000TrapPVCAlarmId,
		ssg5000TrapSlotId,
		ssg5000TrapCardType,
		ssg5000TrapPortId,
		ssg5000TrapInterfaceNumber,
		ssg5000TrapVPINumber,
		ssg5000TrapVCINumber,
		ssg5000TrapOccurClearTag,
		ssg5000TrapSSGHostAddress
		}
	STATUS  current
        DESCRIPTION
		"The notification signifies that the agenet detects an alarm
		 status in a PVC."
	::= { ssg5000MIBNotification 6 }

ssg5000CT3PortAlarmNotification NOTIFICATION-TYPE
	OBJECTS {
		ssg5000TrapCT3PortAlarmId,
		ssg5000TrapSlotId,
		ssg5000TrapCardType,
		ssg5000TrapPortId,
		ssg5000TrapOccurClearTag,
		ssg5000TrapSSGHostAddress
		}
	STATUS  current
        DESCRIPTION
		"The notification signal the agenet detects an alarm status
		 in the CT3 port."
	::= { ssg5000MIBNotification 7 }

ssg5000ETHPortAlarmNotification NOTIFICATION-TYPE
	OBJECTS {
		ssg5000TrapETHPortAlarmId,
		ssg5000TrapSlotId,
		ssg5000TrapCardType,
		ssg5000TrapPortId,
		ssg5000TrapOccurClearTag,
		ssg5000TrapSSGHostAddress
		}
	STATUS  current
        DESCRIPTION
		"The notification signal the agenet detects an alarm status
		 in the ETHERNET port."
	::= { ssg5000MIBNotification 8 }

ssg5000CT3DS2AlarmNotification NOTIFICATION-TYPE
	OBJECTS {
		ssg5000TrapCT3DS2AlarmId,
		ssg5000TrapSlotId,
		ssg5000TrapCardType,
		ssg5000TrapPortId,
		ssg5000TrapDS2ChannelId,
		ssg5000TrapOccurClearTag,
		ssg5000TrapSSGHostAddress
		}
	STATUS  current
        DESCRIPTION
		"The notification signal the agenet detects an DS2 alarm status
		 in the CT3 port."
	::= { ssg5000MIBNotification 9 }

ssg5000CT3DS1AlarmNotification NOTIFICATION-TYPE
	OBJECTS {
		ssg5000TrapCT3DS1AlarmId,
		ssg5000TrapSlotId,
		ssg5000TrapCardType,
		ssg5000TrapPortId,
		ssg5000TrapDS1ChannelId,
		ssg5000TrapOccurClearTag,
		ssg5000TrapSSGHostAddress
		}
	STATUS  current
        DESCRIPTION
		"The notification signal the agenet detects an DS1 alarm status
		 in the CT3 port."
	::= { ssg5000MIBNotification 10 }

ssg5000ServiceAlarmNotification NOTIFICATION-TYPE
	OBJECTS {
		ssg5000TrapServiceModuleAlarm,
		ssg5000TrapServiceAlarmSeverity,
		ssg5000TrapServiceAlarmDescription,
		ssg5000TrapSSGHostAddress
		}
	STATUS  current
        DESCRIPTION
		"The notification signal the agenet detects an alarm 
		 in SSG Service related modules."
	::= { ssg5000MIBNotification 11 }

-- Conformance Information

ssg5000ChassisMIBConformance		OBJECT IDENTIFIER ::= { ssg5000ChassisMIB 3 }
ssg5000ChassisMIBCompliances		OBJECT IDENTIFIER ::= { ssg5000ChassisMIBConformance 1 }
ssg5000ChassisMIBGroups		OBJECT IDENTIFIER ::= { ssg5000ChassisMIBConformance 2 }

-- compliance statements

ssg5000ChassisMIBCompliance MODULE-COMPLIANCE
        STATUS  current
        DESCRIPTION
                "The compliance statement for the SSG-5000, used in the CMC, 
		 which implements the SSG-5000 chassis MIB."
	MODULE  -- this module
	MANDATORY-GROUPS {
		ssg5000ChassisMIBGroup,
		ssg5000SysHealthMIBGroup
		}
	::= { ssg5000ChassisMIBCompliances 1 }

-- units of conformance

ssg5000ChassisMIBGroup OBJECT-GROUP
	OBJECTS {
		ssg5000SysStatus,
		ssg5000SlotIndex,
		ssg5000SlotCardType,
		ssg5000SlotCardDescr,
		ssg5000SlotAdminStatus,
		ssg5000SlotOperStatus,
		ssg5000SlotCardNumPorts,
		ssg5000SlotCardHwVersion,
		ssg5000SlotCardSerialNumber,
		ssg5000SlotAlarms,
		ssg5000SSMIndex,
                ssg5000SSMAdminStatus,
                ssg5000SSMOperStatus,
                ssg5000SSMCPUIdleTics5Sec,
                ssg5000SSMCPUTics5Sec,
                ssg5000SSMCPUIdleTicsReboot,
                ssg5000SSMCPUTicsReboot,
		ssg5000SSMCPUMemHeapFree,
		ssg5000SSMCPUMemHeapTotal,
		ssg5000SSMCPUMBufClusterFree,
		ssg5000SSMCPUMBufClusterTotal,
		ssg5000SSMActiveAccessConn,
		ssg5000SSMActiveSubscribers,
		ssg5000SSMPacketsDropped,
		ssg5000SSMPacketsForwarded,
		ssg5000SSMAlarms,
                ssg5000ALCPortIndex,
                ssg5000ALCPortIfIndex,
                ssg5000ALCPortAdminStatus,
                ssg5000ALCPortOperStatus,
		ssg5000ALCPortActiveAccessConn,
		ssg5000ALCPortActiveTrunkConn,
		ssg5000ALCPortCellsReceived,
		ssg5000ALCPortCellsTransmitted,
		ssg5000ALCPortCellsDropped,
		ssg5000ALCPortAlarms
	}
	STATUS	current
	DESCRIPTION
		"A collection of objects providing SSG-5000 chassis 
		 information."
	::= { ssg5000ChassisMIBGroups 1 }

ssg5000SysHealthMIBGroup OBJECT-GROUP
        OBJECTS {
		ssg5000SysFanStatus,
		ssg5000SysTempStatus,
		ssg5000SysFabricCellsDropped,
		ssg5000SysFabricMemUtilization,
		ssg5000SysActiveAccessConn,
		ssg5000SysActiveTrunkConn,
		ssg5000SysPacketsDropped,
		ssg5000SysCellsDropped,
		ssg5000CmcCPUIdleTics5Sec,
		ssg5000CmcCPUTotalTics5Sec,
		ssg5000CmcCPUIdleTicsReboot,
		ssg5000CmcCPUTotalTicsReboot,
		ssg5000CmcCPUMemHeapFree,
		ssg5000CmcCPUMemHeapTotal,
		ssg5000CmcCPUMBufClusterFree,
		ssg5000CmcCPUMBufClusterTotal,
		ssg5000CmcCPUAverageLoad,
		ssg5000SspCPUnoEncryptionAverageLoad,
		ssg5000SspCPUwEncryptionAverageLoad
        }
        STATUS  current
        DESCRIPTION
                "A collection of objects providing SSG-5000 health
                 information."
        ::= { ssg5000ChassisMIBGroups 2 }
END
