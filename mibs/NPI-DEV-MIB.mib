--
--
-- NOTE:
--
--
-- This is the generic NPI MIB, modified for the DS24+ by XACT Inc.
--
--
-- February 9, 1998
--
--
--
-- ==================================================================
-- FILE : NUCOM  v 1.00.03

-- ==================================================================
-- ENTERPRISE MIB OF ALL NPI DEVICEs.


NPI-DEV-MIB DEFINITIONS ::= BEGIN

IMPORTS
     mgmt, NetworkAddress, IpAddress, Counter, Gauge,
     TimeTicks, enterprises                            FROM RFC1155-SMI
     DisplayString                                     FROM RFC1213-MIB
     TRAP-TYPE                                         FROM RFC-1215
     OBJECT-TYPE                                       FROM RFC-1212;

-- mgmt         OBJECT IDENTIFIER ::= { iso org(3) dod(6) internet(1) mgmt(2) }
-- directory    OBJECT IDENTIFIER ::= { internet 1 }
-- experimental OBJECT IDENTIFIER ::= { internet 3 }
-- private      OBJECT IDENTIFIER ::= { internet 4 }
-- enterprises  OBJECT IDENTIFIER ::= { private  1 }


   MacAddress ::= OCTET STRING (SIZE (6))    -- a 6 octet address in
                                             -- the "canonical" order

-- ==================================================================


npi   OBJECT IDENTIFIER ::= { enterprises 1101 }

common OBJECT IDENTIFIER ::= { npi 1 }

devDeviceInfo   OBJECT IDENTIFIER ::= { common 1 }
devMonitorInfo  OBJECT IDENTIFIER ::= { common 2 }
devActionInfo   OBJECT IDENTIFIER ::= { common 3 }

--
-- NPI common MIB v 1.00.03 DEFINITIONS
-- Define common partion MIB of all NPI intelligent devices

-- device Information

   devDeviceName   OBJECT-TYPE
         SYNTAX    DisplayString( SIZE(0..64))
         ACCESS    read-only
         STATUS    mandatory
         DESCRIPTION
              " Full model number of this device,
                e.g. NPI NuWave DS24+ 24 port 10/100 Managed Ethernet Switch\n."
         ::= { devDeviceInfo 1 }

   devDeviceType   OBJECT-TYPE
         SYNTAX    INTEGER {
               hub(1),
               bridge(2),
               switch(3),                --XACT
               router(4)                --XACT
              }
         ACCESS    read-only
         STATUS    mandatory
         DESCRIPTION
              "The value indicates the type of this device. "
         ::= { devDeviceInfo 2 }

   devDeviceModel  OBJECT-TYPE
         SYNTAX    DisplayString( SIZE(0..32))
         ACCESS    read-only
         STATUS    mandatory
         DESCRIPTION
              "DW24+"
         ::= { devDeviceInfo 3 }

   devDeviceHardwareVersion   OBJECT-TYPE
         SYNTAX    DisplayString( SIZE(0..8))
         ACCESS    read-only
         STATUS    mandatory
         DESCRIPTION
              "  ASCII string to specify device hardware verion,
                 e.g. 0A.01"
         ::= { devDeviceInfo 4 }

   devDeviceSoftwareVersion   OBJECT-TYPE
         SYNTAX    INTEGER
         ACCESS    read-only
         STATUS    mandatory
         DESCRIPTION
              " The current software/firmware version implemented in this
                device represented in non-zero integer.
                e.g. 10000 means version 1.00.00"
         ::= { devDeviceInfo 5 }

   devDeviceSNMPVersion       OBJECT-TYPE
         SYNTAX     INTEGER {
                v1(1),                --XACT
                v2(2),                --XACT
                v3(3)                --XACT
               }              
         ACCESS     read-only
         STATUS     mandatory
         DESCRIPTION
             " Current version of SNMP protocol used in device,
               e.g. 1 means SNMPV1, 2 means SNMPV2, 3 means SNMPV3." --XACT
         ::= { devDeviceInfo 6 }

   devDeviceNPIMIBVersion      OBJECT-TYPE
         SYNTAX     INTEGER
         ACCESS     read-only
         STATUS     mandatory
         DESCRIPTION
              " Current version of NPI common MIB this device
                supports.
                e.g. the value 10000 indicates version 1.00.00"
         ::= { devDeviceInfo 7 }

   devDeviceTrapLevel            OBJECT-TYPE
         SYNTAX    INTEGER (1..7)
         ACCESS    read-write
         STATUS    mandatory
         DESCRIPTION
              " Trap reporting level for occasional event. The events are
                categorized into 7 levels based on severity. For example,
                if the value set to 3, the Trap will be sent to manager while
                level 1, 2, or 3 event arises, but not for level 4-7 event."
         ::= { devDeviceInfo 8 }


   devDeviceSubnetControl   OBJECT-TYPE
         SYNTAX     INTEGER {
                    on(1),
                    off(2)
                    }
         ACCESS     read-only
         STATUS     mandatory
         DESCRIPTION
              "  The entity indicates whether the firmware of the device
                 implements internet subnet addressing."
         ::= { devDeviceInfo 9 }

   devDeviceIfMAX           OBJECT-TYPE
         SYNTAX     INTEGER( 1..32)
         ACCESS     read-only
         STATUS     mandatory
         DESCRIPTION
              "  This object defines the maximum number of interfaces
                 this device contains. "
         ::= { devDeviceInfo 10 }

-- --


   devDeviceIfTable         OBJECT-TYPE
         SYNTAX    SEQUENCE OF DevDeviceIfEntry
         ACCESS    not-accessible
         STATUS    mandatory
         DESCRIPTION
              " This table contains addressing information relevant
                to this interface corresponding to IfEntry table.
                The number of entries is given by the value of ifNumber."
         ::= { devDeviceInfo 11 }

   devDeviceIfEntry         OBJECT-TYPE
         SYNTAX    DevDeviceIfEntry
         ACCESS    not-accessible
         STATUS    mandatory
         ::= { devDeviceIfTable 1}

   DevDeviceIfEntry  ::=
          SEQUENCE {
                devDeviceIfIndex
                     INTEGER,
                devDeviceIfOperation
                     INTEGER,
                devDeviceIfMacAddr
                     MacAddress,
                devDeviceIfIpAddr
                     IpAddress,
                devDeviceIfSNetMask
                     IpAddress,
                devDeviceIfDfGateway        -- 1.00.03
                     IpAddress
--XACT          devDeviceIfIpxFunc
--XACT               INTEGER,
--XACT          devDeviceIfIpxEnable
--XACT               INTEGER,
--XACT          devDeviceIfIpxAddr
--XACT               OCTET STRING,
--XACT          devDeviceIfIpxFrameType
--XACT               INTEGER
          }

   devDeviceIfIndex         OBJECT-TYPE
           SYNTAX    INTEGER( 1..32)
           ACCESS    read-only
           STATUS    mandatory
           DESCRIPTION
              " This index value uniquely identifies the interface
                to which this entry is applicable."
           ::= { devDeviceIfEntry 1 }

   devDeviceIfOperation    OBJECT-TYPE
           SYNTAX    INTEGER  {
                          ok(1),
                          failure(2)
                     }
           ACCESS    read-only
           STATUS    mandatory
           DESCRIPTION
              " This object indicates the operational status of this
                device. "
           ::= { devDeviceIfEntry 2 }

   devDeviceIfMacAddr       OBJECT-TYPE
           SYNTAX    MacAddress
           ACCESS    read-only
           STATUS    mandatory
           DESCRIPTION
              " The MAC address of the specified interface of the
                device."
           ::= { devDeviceIfEntry 3 }

   devDeviceIfIpAddr        OBJECT-TYPE
           SYNTAX    IpAddress
           ACCESS    read-write
           STATUS    mandatory
           DESCRIPTION
              " The Internet address of the specified interface of the
                device."
           ::= { devDeviceIfEntry 4 }

   devDeviceIfSNetMask      OBJECT-TYPE
           SYNTAX    IpAddress
           ACCESS    read-write
           STATUS    mandatory
           DESCRIPTION
              " The internet address subnet mask of the specified interface
                of the device."
           ::= { devDeviceIfEntry 5 }

   devDeviceIfDfGateway          OBJECT-TYPE
           SYNTAX    IpAddress
           ACCESS    read-write
           STATUS    mandatory
           DESCRIPTION
              " The default gateway address which the routed packets are
                delivered to."
           ::= { devDeviceIfEntry 6 }


-- devDeviceIfIpxFunc      OBJECT-TYPE
--XACT    SYNTAX    INTEGER  {
--XACT                   support(1),
--XACT                   nosupport(2)
--XACT              }
--XACT    ACCESS    read-only
--XACT    STATUS    mandatory
--XACT    DESCRIPTION
--XACT       " This object indicates that, is this device support snmp
--XACT         over ipx funtion. "
--XACT    ::= { devDeviceIfEntry 7 }
--XACT
-- devDeviceIfIpxEnable    OBJECT-TYPE
--XACT    SYNTAX    INTEGER  {
--XACT                   enable(1),
--XACT                   disable(2)
--XACT              }
--XACT    ACCESS    read-write
--XACT    STATUS    mandatory
--XACT    DESCRIPTION
--XACT       " The current Ipxfunction status."
--XACT    ::= { devDeviceIfEntry 8 }
--XACT
--XACT
-- devDeviceIfIpxAddr          OBJECT-TYPE
--XACT    SYNTAX    OCTET STRING( SIZE(10))
--XACT    ACCESS    read-write
--XACT    STATUS    mandatory
--XACT    DESCRIPTION
--XACT       " The IPX address of the specific interface of this device."
--XACT    ::= { devDeviceIfEntry 9 }
--XACT
-- devDeviceIfIpxFrameType          OBJECT-TYPE
--XACT    SYNTAX    INTEGER  {
--XACT                   ethernet-802-2(1),
--XACT                   ethernet-802-3(2),
--XACT                   ethernet-ii(3),
--XACT                   ethernet-snap(4)
--XACT              }
--XACT    ACCESS    read-write
--XACT    STATUS    mandatory
--XACT    DESCRIPTION
--XACT       " The IPX address of the specific interface of this device."
--XACT    ::= { devDeviceIfEntry 10 }


-- --


   devDeviceSpecificOIDTable    OBJECT-TYPE
           SYNTAX    SEQUENCE OF DevDeviceSpecificOIDEntry    -- 1.00.03
           ACCESS    not-accessible
           STATUS    mandatory
           DESCRIPTION
              " A list of SNMP MIB groups that the device supports"
         ::= { devDeviceInfo 12 }

   devDeviceSpecificOIDEntry     OBJECT-TYPE
           SYNTAX    DevDeviceSpecificOIDEntry
           ACCESS    not-accessible
           STATUS    mandatory
           INDEX     { devDeviceSpecificOIDIndex }    -- 1.00.03
           ::= { devDeviceSpecificOIDTable 1 }

   DevDeviceSpecificOIDEntry  ::=
          SEQUENCE {
                devDeviceSpecificOIDIndex
                   INTEGER,
                devDeviceSpecificOIDPtr
                   OBJECT IDENTIFIER,
                devDeviceSpecificOIDDescription       -- 1.00.03
                   DisplayString,
                devDeviceSpecificOIDVersion           -- 1.00.03
                   INTEGER
          }

   devDeviceSpecificOIDIndex    OBJECT-TYPE
           SYNTAX    INTEGER
           ACCESS    read-only
           STATUS    mandatory
           ::= { devDeviceSpecificOIDEntry 1 }

   devDeviceSpecificOIDPtr      OBJECT-TYPE           -- 1.00.03
           SYNTAX    OBJECT IDENTIFIER
           ACCESS    read-only
           STATUS    mandatory
           DESCRIPTION
              " The Object ID for the SMI enterprises subtree that
                the device did implement."
           ::= { devDeviceSpecificOIDEntry 2 }

   devDeviceSpecificOIDDescription     OBJECT-TYPE
           SYNTAX    DisplayString (SIZE(1..128))
           ACCESS    read-only
           STATUS    mandatory
           DESCRIPTION
              " The description of this MIB group"
           ::= { devDeviceSpecificOIDEntry 3 }

   devDeviceSpecificOIDVersion         OBJECT-TYPE
           SYNTAX    INTEGER
           ACCESS    read-only
           STATUS    mandatory
           DESCRIPTION
              " The version of this MIB group, e.g., 10000 means
                version 1.00.00"
           ::= { devDeviceSpecificOIDEntry 4 }

-- --

   devDeviceTrapManagerTable         OBJECT-TYPE
          SYNTAX    SEQUENCE OF DevDeviceTrapManagerEntry     --1.00.03
          ACCESS    not-accessible
          STATUS    mandatory
          DESCRIPTION
              " This table contains the information needed
                for sending traps."
          ::= { devDeviceInfo 13 }

   devDeviceTrapManagerEntry         OBJECT-TYPE
          SYNTAX    DevDeviceTrapManagerEntry
          ACCESS    not-accessible
          STATUS    mandatory
          ::=  { devDeviceTrapManagerTable 1}

   DevDeviceTrapManagerEntry  ::=
        SEQUENCE {
            devDeviceTrapManagerIndex
                  INTEGER,
            devDeviceTrapManagerMacAddr
                  OCTET STRING,
            devDeviceTrapManagerIpAddr
                  IpAddress,
            devDeviceTrapManagerAttribute
                  INTEGER,
            devDeviceTrapManagerProtocol
                  INTEGER,
            devDeviceTrapManagerComm
                  DisplayString
--XACT     devDeviceTrapManagerIPX
--XACT           OCTET STRING
       }

   devDeviceTrapManagerIndex     OBJECT-TYPE
          SYNTAX    INTEGER
          ACCESS    read-only
          STATUS    mandatory
          ::= { devDeviceTrapManagerEntry 1}

   devDeviceTrapManagerMacAddr   OBJECT-TYPE
          SYNTAX    OCTET STRING (SIZE(6))
          ACCESS    read-only                      -- 1.00.03
          STATUS    mandatory
          DESCRIPTION
               " The MAC address of the management station which
                 trap is sent to ."
          ::= { devDeviceTrapManagerEntry 2}

   devDeviceTrapManagerIpAddr     OBJECT-TYPE
          SYNTAX    IpAddress
          ACCESS    read-write
          STATUS    mandatory
          DESCRIPTION
               " The Internet address of the management station which
                 trap is sent to ."
          ::= { devDeviceTrapManagerEntry 3}

   devDeviceTrapManagerAttribute     OBJECT-TYPE
          SYNTAX    INTEGER {
                        dynamic(1),
                        permanent(2)
                    }
          ACCESS    read-write
          STATUS    mandatory
          DESCRIPTION
              "  The dynamic attribute of the station address
                 indicates whether the address is learned from the
                 and the permanent entries means specified by user."
          ::=  { devDeviceTrapManagerEntry 4}

   devDeviceTrapManagerProtocol      OBJECT-TYPE
          SYNTAX    INTEGER {
                        unknown(1),
                        ip(2),
                 ipx(3),
                 ip-and-ipx(4)
                    }
          ACCESS    read-write
          STATUS    mandatory
          DESCRIPTION
              "  Indicate the frame format used in the management station"
          ::= { devDeviceTrapManagerEntry 5}

   devDeviceTrapManagerComm          OBJECT-TYPE
          SYNTAX    DisplayString (SIZE(1..16))
          ACCESS    read-write
          STATUS    mandatory
          DESCRIPTION
              "  Community name used for sending the trap to this management
                 station"
           ::= { devDeviceTrapManagerEntry 6 }

-- devDeviceTrapManagerIPX           OBJECT-TYPE
--XACT   SYNTAX    OCTET STRING ( SIZE(10))
--XACT   ACCESS    read-write
--XACT   STATUS    mandatory
--XACT   DESCRIPTION
--XACT        " The IPX address of the management station which
--XACT          trap is sent to ."
--XACT   ::= { devDeviceTrapManagerEntry 7}

-- --

    devMonTrapReportNumber OBJECT-TYPE
           SYNTAX    INTEGER
           ACCESS    read-only
           STATUS    mandatory
           DESCRIPTION
              " The specific number of the latest trap event"
           ::= { devMonitorInfo 1 }

    devMonTrapReportLevel  OBJECT-TYPE
           SYNTAX    INTEGER
           ACCESS    read-only
           STATUS    mandatory
           DESCRIPTION
              " The trap level of the latest trap event"
           ::= { devMonitorInfo 2 }

    devMonTrapReportString  OBJECT-TYPE
           SYNTAX    DisplayString (SIZE(0..127))
           ACCESS    read-only
           STATUS    mandatory
           DESCRIPTION
              " The trap message to describe the latest trap event."
           ::= { devMonitorInfo 3 }

    devMonTrapReportTimestamp  OBJECT-TYPE
           SYNTAX    TimeTicks
           ACCESS    read-only
           STATUS    mandatory
           DESCRIPTION
              " the value of sysUpTime at the time the latest trap event
                arises."
           ::= { devMonitorInfo 4 }

    devMonTrapReportPortNumber  OBJECT-TYPE
           SYNTAX    INTEGER
           ACCESS    read-only
           STATUS    mandatory
           DESCRIPTION
              " the port number binding with this event"
           ::= { devMonitorInfo 5 }

-- --

   devActReset          OBJECT-TYPE
           SYNTAX    INTEGER {
                        reset (1),
                        noReset(2)
                     }
           ACCESS    read-write
           STATUS    mandatory
           DESCRIPTION
              " Request system to perform reset in short time"
           ::= { devActionInfo 1 }

   devActFactoryReset   OBJECT-TYPE
           SYNTAX     INTEGER {
                         factoryReset(1),
                         noFactoryReset(2)
                      }
           ACCESS    read-write
           STATUS    mandatory
           DESCRIPTION
              " Request the system to perform factory reset in short
                time, all the setting will be changed to default ones,
                after this action."
           ::= { devActionInfo 2 }

   devActTest          OBJECT-TYPE
           SYNTAX     INTEGER {
                          test(1),
                          noTest(2)
                      }
           ACCESS     read-write
           STATUS     mandatory
           DESCRIPTION
               " Request the system to perform a internal test which
                 does not require resetting the system."
           ::= { devActionInfo 3}

   devActTestResult     OBJECT-TYPE
           SYNTAX     INTEGER {
                           ok(1),
                           fail(2)
                      }
           ACCESS     read-only
           STATUS     mandatory
           DESCRIPTION
              "  This object shows the result of the test activated
                 by setting devActTest"
           ::= { devActionInfo 4}

-- ==================================================================

END

-- EOF
