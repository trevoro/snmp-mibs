-- 
-- Copyright 1999 by Fore Systems, Inc. 
-- Converted to SMIv2 rfc 2578,2579,2580 - STD 58
--

-- Copyright 1996 by Fore Systems, Inc.  All rights reserved.
--
-- This file contains definitions for management information for
-- Trap Events on a device.
------------------------------------------------------------------

Fore-TrapLog-MIB DEFINITIONS ::= BEGIN

IMPORTS
          OBJECT-TYPE,
          MODULE-IDENTITY,
	  Integer32,
	  Counter32			  FROM SNMPv2-SMI
          TimeStamp,
          TimeInterval                    FROM SNMPv2-TC
          snmpTrapLog,
	  TrapNumber			  FROM Fore-Common-MIB;

 foreTrapLogModule MODULE-IDENTITY
	LAST-UPDATED	"9610010000Z"
	ORGANIZATION	"FORE"
	CONTACT-INFO	"
		Postal:	FORE Systems Inc.
			1000 FORE Drive
			Warrendale, PA 15086-7502
		Tel:	+1 724 742 6900
		Email:	nm_mibs@fore.com
		Web:	http://www.fore.com"
	DESCRIPTION
		"This MIB module defines the FORE Systems specific
                 Log information for Traps. It provides
                 for a Log table, Var table and Threshold table.  
		 Each Log table entry contains general information
                 on the traps that occured, number of times and the
		 last time they occured.
		 The Var table contains information on the trap
		 variables reported with specific traps.
		 The Threshold table is a fully populated table which 
		 has the thresholds & timeperiods defined for all the traps."
	::= { snmpTrapLog 1}

--------------------------------------------------------------------------------
-- Table 1 is the trapLogTable

trapLogTable OBJECT-TYPE
	SYNTAX	SEQUENCE OF TrapLogEntry
	MAX-ACCESS  not-accessible
	STATUS  current
	DESCRIPTION 
		"A table consisting of entries with trap information"
        ::= { snmpTrapLog 2 }

trapLogEntry OBJECT-TYPE
	SYNTAX	TrapLogEntry
	MAX-ACCESS	not-accessible
	STATUS	current
	DESCRIPTION
		"A table entry containing a trap number, and some information on
		 the trap."
	INDEX	{ trapLogIndex }  
	::= { trapLogTable 1 }

TrapLogEntry ::=
	SEQUENCE {
		trapLogIndex	 	Integer32,
		trapLogEnterprise	OBJECT IDENTIFIER,
		trapLogGenericId	TrapNumber,
		trapLogId	 	TrapNumber,	
		trapLogXmits	 	Counter32,
		trapLogLastXmit	 	TimeStamp,
		trapLogEvents	 	Counter32,
		trapLogLastEvent 	TimeStamp
	}
 
trapLogIndex OBJECT-TYPE
	SYNTAX	Integer32
	MAX-ACCESS  read-only
	STATUS  current
	DESCRIPTION
		"The sequence number of this trap occurence. This
		entry uniquely identifies an entry in the trapLogTable"
	::= { trapLogEntry 1 }

trapLogEnterprise OBJECT-TYPE
	SYNTAX	OBJECT IDENTIFIER
	MAX-ACCESS	read-only
	STATUS	current
	DESCRIPTION
		"The enterprise oid of this trap.  This used 
		 with the trapLogGenericId and trapLogId uniquely 
		 identifies the trap type which occured."
	::= { trapLogEntry 2 }

trapLogGenericId OBJECT-TYPE
	SYNTAX  TrapNumber
	MAX-ACCESS  read-only
	STATUS  current
	DESCRIPTION
		"The value of this object identifies the generic trap type that
		 occured."
	::= { trapLogEntry 3 }

trapLogId  OBJECT-TYPE
	SYNTAX	TrapNumber
	MAX-ACCESS	read-only
	STATUS	current
	DESCRIPTION         
		"The value of this object identifies the specific trap type that
		 occured."
	::= { trapLogEntry  4 }

trapLogXmits   OBJECT-TYPE
	SYNTAX	Counter32
	MAX-ACCESS	read-only
	STATUS  current
	DESCRIPTION
		"The number of times this trap was transmitted out on
		the network to trap destinations."
	::= { trapLogEntry 5 }

trapLogLastXmit OBJECT-TYPE
	SYNTAX	TimeStamp
	MAX-ACCESS  read-only
	STATUS  current
	DESCRIPTION
		"The sysUptime at which this trap was last transmitted
		to trap destinations."
	::= { trapLogEntry 6 }

trapLogEvents  OBJECT-TYPE
	SYNTAX	Counter32
	MAX-ACCESS	read-only
	STATUS  current
	DESCRIPTION
		"The number of times this trap event occured."
	::= { trapLogEntry 7 }

trapLogLastEvent OBJECT-TYPE
	SYNTAX	TimeStamp
	MAX-ACCESS	read-only
	STATUS	current
	DESCRIPTION
		"The sysUptime at which this trap event last occured."
	::= { trapLogEntry 8 }


-- Table 2 is the trapLogVarTable

trapLogVarTable OBJECT-TYPE
	SYNTAX SEQUENCE OF TrapLogVarEntry
	MAX-ACCESS not-accessible
	STATUS current
	DESCRIPTION
		"A table of trap variables corresponding to trap occurences."
	::= { snmpTrapLog 3 }

trapLogVarEntry OBJECT-TYPE
	SYNTAX TrapLogVarEntry
	MAX-ACCESS not-accessible
	STATUS current
	DESCRIPTION
		"A table entry containing informaiton about a trap
		 variable reported for one of the trap occurences."
	INDEX { trapLogIndex, trapLogVarIndex }
	::= { trapLogVarTable 1 }

TrapLogVarEntry ::=
	SEQUENCE {
		trapLogVarIndex	Integer32,
		trapLogVarOID	OBJECT IDENTIFIER,
		trapLogVarValue	OCTET STRING
	}

trapLogVarIndex OBJECT-TYPE
	SYNTAX Integer32
	MAX-ACCESS not-accessible
	STATUS current
	DESCRIPTION
		"The Variable index. This number identifies the index
		of this variable in a list of variables reported with
		one trap occurence. The list of variables are in the
		order of the variables given in the TRAP definition
		for this trap."
	::= { trapLogVarEntry 1 }

trapLogVarOID OBJECT-TYPE
	SYNTAX OBJECT IDENTIFIER
	MAX-ACCESS read-only
	STATUS current
	DESCRIPTION 
		"This is the OID of the trap variable."
	::= { trapLogVarEntry 2 }

trapLogVarValue OBJECT-TYPE
	SYNTAX OCTET STRING
	MAX-ACCESS read-only
	STATUS current	
	DESCRIPTION 
		"This is the value of the trap variable."
	::= { trapLogVarEntry 3 }


--  Table 3 is the trapThresholdTable

trapThresholdTable  OBJECT-TYPE
	SYNTAX SEQUENCE OF TrapThresholdEntry
	MAX-ACCESS not-accessible
	STATUS current
	DESCRIPTION
		"A table of thresholds and time periods for the switch
		traps, which determine when a trap is transmitted to
		the trap destinations"
	::= { snmpTrapLog 4 }

trapThresholdEntry  OBJECT-TYPE
	SYNTAX TrapThresholdEntry
	MAX-ACCESS not-accessible
	STATUS current
	DESCRIPTION
                "A table entry containing the trap type and the threshold value 
		and the time period for the trap."
	INDEX { trapThresholdTrapEnterprise, trapThresholdGenericTrapId,
		trapThresholdTrapId }
	::= { trapThresholdTable  1 }

TrapThresholdEntry ::=
	SEQUENCE {
		trapThresholdTrapEnterprise	OBJECT IDENTIFIER,
		trapThresholdGenericTrapId	TrapNumber,
		trapThresholdTrapId		TrapNumber,
		trapThresholdValue		Integer32,
		trapThresholdTimePeriod		TimeInterval 
	}

-- This table has no EntryStatus Object as it is supposed to be a fully 
-- populated table. The table initially holds default values.
-- User has no access to create a new entry, but can only modify an existing 
-- entry.

trapThresholdTrapEnterprise  OBJECT-TYPE
	SYNTAX OBJECT IDENTIFIER
	MAX-ACCESS not-accessible
	STATUS current
	DESCRIPTION
		"The enterprise OID of this trap."
	::= { trapThresholdEntry 1 }

trapThresholdGenericTrapId  OBJECT-TYPE
	SYNTAX TrapNumber
	MAX-ACCESS not-accessible
	STATUS current
	DESCRIPTION
		"A generic trap type."
	::= { trapThresholdEntry  2 }

trapThresholdTrapId  OBJECT-TYPE
	SYNTAX TrapNumber
	MAX-ACCESS not-accessible
	STATUS current
	DESCRIPTION
		"An enterprise specific trap type."
	::= { trapThresholdEntry  3 }

trapThresholdValue  OBJECT-TYPE
	SYNTAX Integer32
	MAX-ACCESS read-write	-- user configurable thresholds.
	STATUS current
	DESCRIPTION  
		"The value of the threshold for the number of trap occurences 
		 after which the trap gets sent to the destinations."
	::= { trapThresholdEntry  4 }

trapThresholdTimePeriod OBJECT-TYPE
	SYNTAX TimeInterval
	MAX-ACCESS read-write 
	STATUS current
	DESCRIPTION
		"This value has to be used in conjuntion with the 
		trapThresholdValue. It gives the time period over 
		which the threshold is valid. i.e if trapThresholdValue
		trap events occur, Or if the time since the last transmission 
		is greater than this object's value, the trap gets transmitted
		out."
	::= { trapThresholdEntry 5 }

trapThresholdTableReset OBJECT-TYPE
	SYNTAX INTEGER {
		enable(1),
		disable(2)
	}
	MAX-ACCESS read-write
	STATUS current
	DESCRIPTION
		"When user sets this object to enable(1), all the threshold
		table values are reset to default values. The value of
		this object would be disable(2), after the
		reconfiguration."
	::= { trapThresholdTable 3 }

--------------------------------------------------------------------------------
END
