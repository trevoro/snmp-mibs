IPV4HOST-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress
			FROM SNMPv2-SMI
		RowStatus, DisplayString
			FROM SNMPv2-TC
		apIpv4Host
			FROM APENT-MIB;


    apIpv4HostMib MODULE-IDENTITY
	   LAST-UPDATED "9801282000Z" -- Wed January 28 20:00:00 EST 1998
	   ORGANIZATION "ArrowPoint Communications Inc."
	   CONTACT-INFO
	   "PPostal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for IPv4 Host table"
      ::= { apIpv4Host 1}

--arrowpoint
-- apmgmt
--  ipv4Ext
--   apIpv4Host
--     apIpv4HostTable

-- IPv4 Host Table configuration information

-- Host table

apIpv4HostTable OBJECT-TYPE
	SYNTAX      SEQUENCE OF ApIpv4HostEntry
	MAX-ACCESS  not-accessible
	STATUS      current
	DESCRIPTION
		"A table of Host table entries."
	::= {apIpv4Host 2}

apIpv4HostEntry OBJECT-TYPE
	SYNTAX      ApIpv4HostEntry
	MAX-ACCESS  not-accessible
	STATUS      current
	DESCRIPTION
	       "ArrowPoint Host Table entries"
	INDEX  { apIpv4HostName}
	::= {apIpv4HostTable 1}

ApIpv4HostEntry ::=
	SEQUENCE {
	       apIpv4HostName               DisplayString,
	       apIpv4HostIpAddress          IpAddress,
	       apIpv4HostStatus             RowStatus
		 }

apIpv4HostName OBJECT-TYPE
	SYNTAX      DisplayString (SIZE(1..16))
	MAX-ACCESS  read-create
	STATUS      current
	DESCRIPTION
	       "The host name"
	::= {apIpv4HostEntry 1}

apIpv4HostIpAddress OBJECT-TYPE
	SYNTAX      IpAddress
	MAX-ACCESS  read-create
	STATUS      current
	DESCRIPTION
	       "The IP Address associated with the host name."
	::= {apIpv4HostEntry 2}

apIpv4HostStatus OBJECT-TYPE
	SYNTAX      RowStatus
	MAX-ACCESS  read-create
	STATUS      current
	DESCRIPTION
	       "Status object for this row"
	::= {apIpv4HostEntry 3}

END
