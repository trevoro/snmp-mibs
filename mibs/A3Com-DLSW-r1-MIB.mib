A3Com-DLSW-r1-MIB DEFINITIONS ::= BEGIN

  IMPORTS

            enterprises, Counter,
            Gauge, TimeTicks
                 FROM RFC1155-SMI

            DisplayString
                 FROM RFC1213-MIB

            OBJECT-TYPE
	         FROM RFC-1212

            TRAP-TYPE
                 FROM RFC-1215;

-- *******************************************************************
-- *                                                                 *
-- *                       Textual Conventions                       *
-- *                                                                 *
-- *******************************************************************

-- Represents a single qualified NetBIOS name, which can include -don-t 
-- care- and -wildcard' characters to represent a number of real NetBIOS 
-- names.  If an individual character position in the qualified name 
-- contains a -?-, the corresponding character position in a real 
-- NetBIOS name is a -don-t care'.  If the qualified name ends in `*', 
-- the remainder of a real NetBIOS name is a -don-t care'. `*' is only 
-- considered a wildcard if it appears at the end of a name.
--
   NBName ::= OCTET STRING (SIZE (0..16))

--
-- Represents an 802 MAC address represented in non-canonical format.  
-- That is, the most significant bit will be transmitted first.
--
   MacAddress ::= OCTET STRING (SIZE (6)) 

--
-- Denotes a transport service address. For dlswTCPDomain, a TAddress 
-- is 4 octets long, containing the IP-address in network-byte order.
--
   TAddress ::= OCTET STRING (SIZE (4))

--
-- The value of dlwsUpTime when the event of interest occurred.
--
   DlswTimeStamp ::= TimeTicks

--
-- Representing the location of an end station related to the managed 
-- DLSw node.
-- 
   EndStationLocation ::= INTEGER
             {
                other          (1),
                internal       (2),  -- local virtual MAC address
                remote         (3),  -- DLSw partner
                local          (4)   -- locally attached
             }

--
-- Representing the type of DLC of an end station, if applicable.
--
   DlcType    ::= INTEGER
	     {
                other          (1),  -- not assigned yet
                na             (2),  -- not applicable
                llc            (3),  -- 802.2 Logical Link Control
                sdlc           (4)   -- SDLC
             }

--
-- The largest size of the INFO field. This is an enumerated value
-- in the AIW version of the MIB.
--
   LFSize    ::= INTEGER

--
-- Declared for SNMP V2 compatability.
--
   Truthvalue ::= INTEGER
             {
                false          (1),
                true           (2)
             }

-- This data type, which has the same semantics as the RowStatus
-- textual convention used in SNMPv2, is used to add and 
-- delete entries from a table.

-- The tables in this MIB allow a subset of the functionality
-- provided by the RowStatus textual convention.  In particular
-- row creation is allowed using only the createAndGo method.

-- That is, when adding entries to this table, this object
-- must be set to createAndGo(4).  The instance identifier
-- for this object will define the values of the columns 
-- that make up the index.  

-- In the same PDU, the appropriate remaining columns
-- of that row must be set as well.  The agent
-- will immediately set the value of this object to
-- active(1) if the row is correct.  If not, the agent
-- will refuse the SET request and return an
-- error code.

-- To modify an existing entry, it must be removed
-- an another entry with the desired changes added. 
                       
-- To remove an entry, set the value of this object
-- to destroy(6).

   RowStatus ::= INTEGER 
	     {
             -- the following two values are states
             -- these values can be read or written

                active(1),
                notInService(2),

             -- the following value is a state:         
             -- this value may be read, but not written 

                notReady(3),                               

             -- the following three values are actions
             -- these values can be written, but are never read

                createAndGo(4),
                createAndWait(5),
                destroy(6)
              }

          --This data type, which has the same semantics as the RowStatus
          --textual convention used in SNMPv2, is used to add and 
          --delete entries from a table.

          --The tables in this MIB allow a subset of the functionality
          --provided by the RowStatus textual convention.  In particular
          --row creation is allowed using only the createAndGo method.

          --That is, when adding entries to this table, this object
          --must be set to createAndGo(4).  The instance identifier
          --for this object will define the values of the columns 
          --that make up the index.  

          --In the same PDU, the appropriate remaining columns
          --of that row must be set as well.  The agent
          --will immediately set the value of this object to
          --active(1) if the row is correct.  If not, the agent
          --will refuse the SET request and return an
          --error code.

          --To modify an existing entry, it must be removed
          --an another entry with the desired changes added. 
                       
          --To remove an entry, set the value of this object
          --to destroy(6).

--
-- Declared for SNMP V2 compatability.
--
   Instancepointer ::= INTEGER


-- *******************************************************************
-- *                                                                 *
-- *                         DLSw GROUPS                             *
-- *                                                                 *
-- *******************************************************************

--a3Com           OBJECT IDENTIFIER ::= { 1 3 6 1 4 1 43 }
  a3Com           OBJECT IDENTIFIER ::= { enterprises 43 }
  brouterMIB      OBJECT IDENTIFIER ::= { a3Com 2 }
  dlswMIB-3Com    OBJECT IDENTIFIER ::= { brouterMIB 24 }

  dlswNode        OBJECT IDENTIFIER ::= { dlswMIB-3Com 1 }
  dlswTConn       OBJECT IDENTIFIER ::= { dlswMIB-3Com 2 }
  dlswInterface   OBJECT IDENTIFIER ::= { dlswMIB-3Com 3 }
  dlswDirectory   OBJECT IDENTIFIER ::= { dlswMIB-3Com 4 }
  dlswCircuit     OBJECT IDENTIFIER ::= { dlswMIB-3Com 5 }
  dlswSdlc        OBJECT IDENTIFIER ::= { dlswMIB-3Com 6 }


-- *******************************************************************
-- *                                                                 *
-- *                            NODE GROUP                           *
-- *                                                                 *
-- *******************************************************************

dlswVersion  OBJECT-TYPE
    SYNTAX     OCTET STRING (SIZE (2))
    ACCESS     read-only
    STATUS     mandatory
    DESCRIPTION
       "This value identifies the particular version of the
        DLSw standard supported by this DLSw.  The first hexdecimal
        value represents the DLSw standard Version number of
        this DLSw, the second hexdecimal value represents the
        DLSw standard Release number. This information
        is exchanged in DLSw Capabilities Exchange."
    ::= { dlswNode 1 }
 
dlswVendorID  OBJECT-TYPE
    SYNTAX     OCTET STRING (SIZE (3))
    ACCESS     read-only
    STATUS     mandatory
    DESCRIPTION
       "The value identifies the manufacturer-s IEEE assigned
        organizationally Unique Identifier (OUI) of this DLSw.
        This information is exchanged in DLSw Capabilities
        Exchange."
    ::= { dlswNode 2 }
 
dlswVersionString  OBJECT-TYPE
    SYNTAX     DisplayString (SIZE (0..255))
    ACCESS     read-only
    STATUS     mandatory
    DESCRIPTION
       "This value identifies the particular version number
        of this DLSw.  The format of the actual version
        string is vendor-specific.  This flows in Capabilities
        Exchange messages."
    ::= { dlswNode 3 }
 
dlswStdPacingSupport  OBJECT-TYPE
    SYNTAX     INTEGER  {
       none              (1),  -- does not support DLSw
                               -- Standard adaptive scheme
       adaptiveRcvWindow (2),  -- the receive window size
                               -- varies
       fixedRcvWindow    (3)   -- the receive window size
                               -- remains constant
    }
    ACCESS     read-only
    STATUS     mandatory
    DESCRIPTION
       "Adaptive pacing defined in the DLSw Standard allows the
        receiving end of the DLSw node to control the amount of
        data that can flow over the DLSw cloud.  none (1) means
        this DLSw node does not support the adaptive pacing
        scheme as defined in the DLSw Standard, possibly a
        proprietary pacing scheme is used. adaptiveRcvWindow
        (2) means this DLSw node supports the DLSw Standard
        pacing scheme.  This DLSw node must be capable to
        adjust its sending window size as instructed by the
        partner DLSw and also will adjust its receive window
        size accordingly to its resource situation.  However,
        implementation may choose not to adjust the receive window
        size.  That is, the only Flow Control Operator will
        be sent by this node is the Repeat Window Operator.
        fixedRcvWindow (3) indicates this capability."
    ::= { dlswNode 4 }
 
dlswStatus  OBJECT-TYPE
    SYNTAX     INTEGER  {
        active        (1),
        inactive      (2)
    }
    ACCESS     read-write
    STATUS     mandatory
    DESCRIPTION
       "The status of DLSw part of the system.  Changing the
        value from active to inactive causes DLSw to take
        the following actions: (1) disconnect all circuits
        through all DLSw partners, (2) disconnect all
        transport connections to all DLSw partners, (3)
        disconnect all local DLC connections, and (4) stop
        processing all DLC connection set-up traffic.
        Since these are destructive actions, the user should
        query the circuit and transport connection tables in
        advance to understand the effect this action will have.
        Changing the value from inactive to active causes DLSw
        to come up in its initial state, i.e., transport
        connection established and ready to bring up circuits."
    ::= { dlswNode 5 }
 
dlswUpTime  OBJECT-TYPE
    SYNTAX     TimeTicks
    ACCESS     read-only
    STATUS     mandatory
    DESCRIPTION
       "The time (in hundredths of a second) since the DLSw
        portion of the system was last re-initialized.
        That is, if dlswState is in the active state,
        the time the dlswState entered the active state.
        It will remain zero, if the dlswState is in the
        inactive state."
    ::= { dlswNode 6 }
 
dlswVirtualSegmentLFSize  OBJECT-TYPE
    SYNTAX     INTEGER
    ACCESS     read-write
    STATUS     mandatory
    DESCRIPTION
       "The largest size of the INFO field (LLC and above)
        that virtual segment can send/receive.  It does
        not include any MAC level (framing) octets.
        This value will affect the LF size of circuits
        in creation.  LF size of an existing circuit
        can be found in RIF (Routing Information Field)."
    ::= { dlswNode 7 }
 
dlswResourceNBExclusivity  OBJECT-TYPE
    SYNTAX     Truthvalue
    ACCESS     read-write
    STATUS     mandatory
    DESCRIPTION
       "The value of true identifies the NETBIOS Names that
        are configured in the dlswDirNBTable are the only
        ones accessible via this DLSw.  Changes to this object
        take effect for runtime Capabilities Exchange messages
        is implementation choice."
    ::= { dlswNode 8 }
 
dlswResourceMacExclusivity  OBJECT-TYPE
    SYNTAX     Truthvalue
    ACCESS     read-write
    STATUS     mandatory
    DESCRIPTION
       "The value of true identifies the MAC addresses that
        are configured in the dlswDirMacTable are the only
        ones accessible via this DLSw.  Changes to this object
        take effect for runtime Capabilities Exchange messages
        is implementation choice."
    ::= { dlswNode 9 }

 
-- *******************************************************************
-- *                                                                 *
-- *                   TRANSPORT CONNECTION GROUP                    *
-- *                                                                 *
-- *                        (Partner DLSw)                           *
-- *                                                                 *
-- *******************************************************************
 
dlswTConnStat    OBJECT IDENTIFIER ::= { dlswTConn 1 }
 

dlswTConnStatActiveConnections  OBJECT-TYPE
    SYNTAX     Gauge
    ACCESS     read-only
    STATUS     mandatory
    DESCRIPTION
       "The number of transport connections are not in
        -disconnected- state."
    ::= { dlswTConnStat 1 }
 
dlswTConnStatCloseIdles  OBJECT-TYPE
    SYNTAX     Counter
    ACCESS     read-only
    STATUS     mandatory
    DESCRIPTION
       "The number of DLSw connections exited connected state
        with all circuits disconnected gracefully.  That is,
        the transport connection was brought down, by either
        this DLSw node or its partner DLSw node, with no
        active circuits."
    ::= { dlswTConnStat 2 }
 
dlswTConnStatCloseBusys  OBJECT-TYPE
    SYNTAX     Counter
    ACCESS     read-only
    STATUS     mandatory
    DESCRIPTION
       "The number of DLSw connections exited connected state
        without all circuits disconnected gracefully.  That is,
        the transport connection was brought down, by either
        this DLSw node or its partner DLSw node, with some
        active circuits.  For instance, transport connection,
        e.g, TCP connection, failed."
    ::= { dlswTConnStat 3 }
 
-- 
-- Transport Connection Configuration Table (TConnConfig)
-- 

dlswTConnConfigTable  OBJECT-TYPE
    SYNTAX     SEQUENCE OF DlswTConnConfigEntry
    ACCESS     not-accessible
    STATUS     mandatory
    DESCRIPTION
       "This table defines the transport connections
        that will be initiated or accepted by this
        DLSw.  Structure of masks allows wildcard
        definition for a collection of transport
        connections by a conceptual row.  For a
        specific transport connection, there may
        be multiple of conceptual rows match the
        transport address.  The -best- match will
        the one to determine the characteristics
        of the transport connection."
    ::= { dlswTConn 2 }
 
dlswTConnConfigEntry  OBJECT-TYPE
    SYNTAX     DlswTConnConfigEntry
    ACCESS     not-accessible
    STATUS     mandatory
    DESCRIPTION
       "Each conceptual row defines a collection of
        transport connections."
    INDEX   { dlswTConnConfigIndex }
    ::= { dlswTConnConfigTable 1 }
 
DlswTConnConfigEntry ::= SEQUENCE {
    dlswTConnConfigIndex              INTEGER,
    dlswTConnConfigTDomain            OBJECT IDENTIFIER,
    dlswTConnConfigLocalTAddr         TAddress,
    dlswTConnConfigRemoteTAddr        TAddress,
    dlswTConnConfigLastModifyTime     DlswTimeStamp,
    dlswTConnConfigEntryType          INTEGER,
    dlswTConnConfigGroupDefinition    Instancepointer,
    dlswTConnConfigSetupType          INTEGER,
    dlswTConnConfigSapList            OCTET STRING,
    dlswTConnConfigAdvertiseMacNB     Truthvalue,
    dlswTConnConfigInitCirRecvWndw    INTEGER,
    dlswTConnConfigOpens              Counter,
    dlswTConnConfigRowStatus          RowStatus
    }
 
dlswTConnConfigIndex  OBJECT-TYPE
    SYNTAX     INTEGER
    ACCESS     read-only
    STATUS     mandatory
    DESCRIPTION
       "The index to the conceptual row of the table.
        Non-positive numbers are not allowed.  There
        are objects defined that point to conceptual
        rows of this table with this index value.
        Zero is used to denote that no corresponding
        row exists.
 
        Index values are assigned by the managed station,
        and should not be reused but should continue to
        increase in value until they wrap."
    ::= { dlswTConnConfigEntry 1 }
 
dlswTConnConfigTDomain  OBJECT-TYPE
    SYNTAX     OBJECT IDENTIFIER
    ACCESS     read-write
    STATUS     mandatory
    DESCRIPTION
       "The object identifier which indicates the transport
        domain of this conceptual row."
    ::= { dlswTConnConfigEntry 2 }
 
dlswTConnConfigLocalTAddr  OBJECT-TYPE
    SYNTAX     TAddress
    ACCESS     read-write
    STATUS     mandatory
    DESCRIPTION
       "The local transport address for this conceptual row
        of the transport connection definition."
    ::= { dlswTConnConfigEntry 3 }
 
dlswTConnConfigRemoteTAddr  OBJECT-TYPE
    SYNTAX     TAddress
    ACCESS     read-write
    STATUS     mandatory
    DESCRIPTION
       "The remote transport address.  Together with the
        dlswTConnConfigRemoteTAddrMask, the object instance
        of this conceptual row identifies a collection of
        the transport connections that will be either
        initiated by this DLSw or initiated by partner
        DLSw and accepted by this DLSw."
    ::= { dlswTConnConfigEntry 4 }
 
dlswTConnConfigLastModifyTime  OBJECT-TYPE
    SYNTAX     DlswTimeStamp
    ACCESS     read-write
    STATUS     mandatory
    DESCRIPTION
       "The value of dlswUpTime when the value of any object in
        this conceptual row was last changed.  This value may
        be compared to dlswTConnOperConnectTime to determine
        whether values in this row are completely valid for a
        tranport connection created using this row definition."
    ::= { dlswTConnConfigEntry 5 }
 
dlswTConnConfigEntryType  OBJECT-TYPE
    SYNTAX     INTEGER  {
        individual     (1),
        global         (2),
        group          (3)
    }
    ACCESS     read-write
    STATUS     mandatory
    DESCRIPTION
       "The object instance signifies the type of entry in the
        associated conceptual row.  The value of -individual-
        means that the entry applies to a specific partner DLSw
        node as identified by dlswTConnConfigRemoteTAddr and
        dlswTConnConfigTDomain.  The value of -global-
        means that the entry applies to all partner DLSw nodes
        of the TDomain.  The value of -group' means that the entry
        applies to a specific set of DLSw nodes in the TDomain.
        Any group definitions are enterprise-specific and are pointed
        to by dlswTConnConfigGroupDefinition.  In the cases of
        -global- and `group', the value in dlswTConnConfigRemoteTAddr
        may not have any significance."
    ::= { dlswTConnConfigEntry 6 }
 
dlswTConnConfigGroupDefinition OBJECT-TYPE
    SYNTAX     Instancepointer
    ACCESS     read-write
    STATUS     mandatory
    DESCRIPTION
       "For conceptual rows of -individual- and `global' as
        specified in dlswTConnConfigEntryType, the instance
        of this object is  -0.0-.  For conceptual rows of
        -group-, the instance points to the specific
        group definition."
    ::= { dlswTConnConfigEntry 7 }
 
dlswTConnConfigSetupType  OBJECT-TYPE
    SYNTAX     INTEGER  {
        other              (1),
        activePersistent   (2),
        activeOnDemand     (3),
        passive            (4),
        excluded           (5)
    }
    ACCESS     read-write
    STATUS     mandatory
    DESCRIPTION
       "This value of the instance of a conceptual row
        identifies the behavior of the collection of
        transport connections that this conceptual row
        defines.  The value of activePersistent, activeOnDemand
        and passive means this DLSw will accept any transport
        connections, initiated by partner DLSw nodes, which
        are defined by this conceptual row.  The value of
        activePersistent means this DLSw will also initiate
        the transport connections of this conceptual row and
        retry periodically if necessary.  The value of
        activeOnDemand means this DLSw will initiate a
        transport connection of this conceptual row, if
        there is a directory cache hits.  The value of
        other is implementation specific.  The value of exclude
        means that the specified node is not allowed to be
        a partner to this DLSw node.  To take a certain
        conceptual row definition out of service, a value of
        notInService for dlswTConnConfigRowStatus should be
        used."
    DEFVAL  { passive }
    ::= { dlswTConnConfigEntry 8 }
 
dlswTConnConfigSapList  OBJECT-TYPE
    SYNTAX     OCTET STRING  (SIZE(16))
    ACCESS     read-write
    STATUS     mandatory
    DESCRIPTION
       "The SAP list indicates which SAPs are advertised to
        the transport connection defined by this conceptual
        row.  Only SAPs with even numbers are represented,
        in the form of the most significant bit of the first
        octet representing the SAP 0, the next most significant
        bit representing the SAP 2, to the least significant
        bit of the last octet representing the SAP 254.  Data
        link switching is allowed for those SAPs which have
        one in its corresponding bit, not allowed otherwise.
        The whole SAP list has to be changed together.  Changing
        the SAP list affects only new circuit establishments
        and has no effect on established circuits.
 
        This list can be used to restrict specific partners
        from knowing about all the SAPs used by DLSw on all its
        interfaces (these are represented in dlswIfSapList for
        each interface).  For instance, one may want to run NetBIOS
        with some partners but not others.
 
        If a node supports sending run-time capabilities exchange
        messages, changes to this object should cause that action.
        It is up to the implementation exactly when to start the
        run-time capabilities exchange."
    ::= { dlswTConnConfigEntry 9 }
 
dlswTConnConfigAdvertiseMacNB  OBJECT-TYPE
    SYNTAX     Truthvalue
    ACCESS     read-write
    STATUS     mandatory
    DESCRIPTION
       "The value of true indicates that defined local MAC
       addresses and NetBIOS names will be advertised to a
        partner node via initial and (if supported) run-time
        capabilities exchange messages."
    DEFVAL  { true }
    ::= { dlswTConnConfigEntry 10 }
 
dlswTConnConfigInitCirRecvWndw  OBJECT-TYPE
    SYNTAX     INTEGER (0..65535)
--  UNITS      "SSP messages"
    ACCESS     read-write
    STATUS     mandatory
    DESCRIPTION
       "The initial circuit receive pacing window size, in the unit
        of SSP messages, to be used for future transport connections
        activated using this table row.  The managed node sends this
        value as its initial receive pacing window in its initial
        capabilities exchange message.  Changing this value does not
        affect the initial circuit receive pacing window size of
        currently active transport connections.  If the standard window
        pacing scheme is not supported, the value is zero.
 
        A larger receive window value may be appropriate for partners
        that are reachable only via physical paths that have longer
        network delays."
    DEFVAL  { 1 }
    ::= { dlswTConnConfigEntry 11 }
 
dlswTConnConfigOpens  OBJECT-TYPE
    SYNTAX     Counter
    ACCESS     read-only
    STATUS     mandatory
    DESCRIPTION
       "Number of times transport connections entered
        connected state according to the definition of
        this conceptual row."
    ::= { dlswTConnConfigEntry 12 }
 
dlswTConnConfigRowStatus  OBJECT-TYPE
    SYNTAX     RowStatus
    ACCESS     read-write
    STATUS     mandatory
    DESCRIPTION
       "This object is used by a Management Station to create
        or delete the row entry in the dlswTConnConfigTable
        following the RowStatus textual convention.  The value
        of notInService will be used to take a conceptual
        row definition out of use."
    ::= { dlswTConnConfigEntry 13 }
 
-- 
-- Transport Connection Operation Table (TConnOper)
-- 
-- 
-- (1) At most one transport connection can be connected between
--     this DLSw and one of its DLSw partners at a given time.
-- (2) Multiple transport types are supported.
-- (3) Since the entries may be reused, dlswTConnOperEntryTime
--     needs to be consulted for the possibility of counter reset.
-- 
 
dlswTConnOperTable  OBJECT-TYPE
    SYNTAX     SEQUENCE OF DlswTConnOperEntry
    ACCESS     not-accessible
    STATUS     mandatory
    DESCRIPTION
       "A list of transport connections.   It is optional but
        desirable for an implementation to keep an entry for
        some period of time after the transport connection is
        disconnected.  This allows a network management station
        to capture additional useful information about the connection,
        in particular, statistical information and the cause of the
        disconnection."
    ::= { dlswTConn 3 }
 
dlswTConnOperEntry  OBJECT-TYPE
    SYNTAX     DlswTConnOperEntry
    ACCESS     not-accessible
    STATUS     mandatory
    DESCRIPTION
       ""
    INDEX   { dlswTConnOperTDomain, dlswTConnOperRemoteTAddr }
    ::= { dlswTConnOperTable 1 }
 
DlswTConnOperEntry ::= SEQUENCE {
    dlswTConnOperTDomain                  OBJECT IDENTIFIER,
    dlswTConnOperLocalTAddr               TAddress,
    dlswTConnOperRemoteTAddr              TAddress,
    dlswTConnOperEntryTime                DlswTimeStamp,
    dlswTConnOperConnectTime              DlswTimeStamp,
    dlswTConnOperState                    INTEGER,
    dlswTConnOperConfigIndex              INTEGER,
    dlswTConnOperFlowCntlMode             INTEGER,
    dlswTConnOperPartnerVersion           OCTET STRING,
    dlswTConnOperPartnerVendorID          OCTET STRING,
    dlswTConnOperPartnerVersionStr        DisplayString,
    dlswTConnOperPartnerInitPacingWndw    INTEGER,
    dlswTConnOperPartnerSapList           OCTET STRING,
    dlswTConnOperPartnerNBExcl            Truthvalue,
    dlswTConnOperPartnerMacExcl           Truthvalue,
    dlswTConnOperPartnerNBInfo            INTEGER,
    dlswTConnOperPartnerMacInfo           INTEGER,
    dlswTConnOperDiscTime                 DlswTimeStamp,
    dlswTConnOperDiscReason               INTEGER,
    dlswTConnOperDiscActiveCir            INTEGER,
    dlswTConnOperInDataPkts               Counter,
    dlswTConnOperOutDataPkts              Counter,
    dlswTConnOperInDataOctets             Counter,
    dlswTConnOperOutDataOctets            Counter,
    dlswTConnOperInCntlPkts               Counter,
    dlswTConnOperOutCntlPkts              Counter,
    dlswTConnOperCURexSents               Counter,
    dlswTConnOperICRexRcvds               Counter,
    dlswTConnOperCURexRcvds               Counter,
    dlswTConnOperICRexSents               Counter,
    dlswTConnOperNQexSents                Counter,
    dlswTConnOperNRexRcvds                Counter,
    dlswTConnOperNQexRcvds                Counter,
    dlswTConnOperNRexSents                Counter,
    dlswTConnOperCirCreates               Counter,
    dlswTConnOperCircuits                 Gauge
    }
 
dlswTConnOperTDomain  OBJECT-TYPE
    SYNTAX     OBJECT IDENTIFIER
    ACCESS     read-only
    STATUS     mandatory
    DESCRIPTION
       "The object identifier indicates the transport domain
        of this transport connection."
    ::= { dlswTConnOperEntry 1 }
 
dlswTConnOperLocalTAddr  OBJECT-TYPE
    SYNTAX     TAddress
    ACCESS     read-only
    STATUS     mandatory
    DESCRIPTION
       "The local transport address for this transport connection.
        This value could be different from dlswTConnConfigLocalAddr,
        if the value of the latter were changed after this transport
        connection was established."
    ::= { dlswTConnOperEntry 2 }
 
dlswTConnOperRemoteTAddr  OBJECT-TYPE
    SYNTAX     TAddress
    ACCESS     read-only
    STATUS     mandatory
    DESCRIPTION
       "The remote transport address of this transport connection."
    ::= { dlswTConnOperEntry 3 }
 
dlswTConnOperEntryTime  OBJECT-TYPE
    SYNTAX     DlswTimeStamp
    ACCESS     read-only
    STATUS     mandatory
    DESCRIPTION
       "The value of dlswUpTime when this transport connection
        conceptual row was created."
    ::= { dlswTConnOperEntry 4 }
 
-- ...................................................................
-- DLSw Transport Connection Operational Objects
-- ...................................................................
 
dlswTConnOperConnectTime  OBJECT-TYPE
    SYNTAX     DlswTimeStamp
    ACCESS     read-only
    STATUS     mandatory
    DESCRIPTION
       "The value of dlswUpTime when this transport connection
        last entered the -connected- state.  A value of zero means
        this transport connection has never been established."
    ::= { dlswTConnOperEntry 5 }
 
dlswTConnOperState  OBJECT-TYPE
    SYNTAX     INTEGER  {
        connecting         (1),
        initCapExchange    (2),
        connected          (3),
        quiescing          (4),
        disconnecting      (5),
        disconnected       (6)
    }
    ACCESS     read-write
    STATUS     mandatory
    DESCRIPTION
       "The state of this transport connection.  The transport
        connection enters -connecting- state when DLSw makes
        a connection request to the transport layer.  Once initial
        Capabilities Exchange is sent, the transport connection enters
        enters -initCapExchange- state.  When partner capabilities have been
        determined and the transport connection is ready for sending
        CanUReach (CUR) messages, it moves to the -connected- state.
        When DLSw is in the process of bringing down the connection,
        it is in the -disconnecting- state.  When the transport layer
        indicates one of its connections is disconnected, the transport
        connection moves to the -disconnected- state.
 
        Whereas all of the values will be returned in response to a
        management protocol retrieval operation, only two values may
        be specified in a management protocol set operation, -quiescing-
        and -disconnecting-.  Changing the value to -quiescing- prevents
        new circuits from being established, and will cause a transport
        disconnect when the last circuit on the connection goes away.
        Changing the value to -disconnecting- will force off all circuits
        immediately and bring the connection to -disconnected- state."
    ::= { dlswTConnOperEntry 6 }
 
dlswTConnOperConfigIndex  OBJECT-TYPE
    SYNTAX     INTEGER
    ACCESS     read-only
    STATUS     mandatory
    DESCRIPTION
       "The value of dlswTConnConfigIndex of the dlswTConnConfigEntry
        that governs the configuration information used by this
        dlswTConnOperEntry.  A management station can therefore
        normally examine both configured and operational information
        for this transport connection.
 
        This value is zero if the corresponding dlswTConnConfigEntry
        was deleted after the creation of this dlswTConnOperEntry.
        If some fields in the former were changed but the conceptual
        row was not deleted, some configuration information may not
        be valid for this operational transport connection.  A network
        management application can compare dlswTConnOperConnectTime and
        dlswTConnConfigLastModifyTime to determine if this condition
        exists."
    ::= { dlswTConnOperEntry 7 }
 
-- ...................................................................
-- Transport Connection Characteristics
-- ...................................................................
 
dlswTConnOperFlowCntlMode  OBJECT-TYPE
    SYNTAX     INTEGER  {
       undetermined   (1),
       pacing         (2),   -- DLSw standard flow control
       other          (3)    -- non-DLSw standard flow control
    }
    ACCESS     read-only
    STATUS     mandatory
    DESCRIPTION
       "The flow control mechanism in use on this transport connection.
        This value is undetermined (1) before the mode of flow control
        can be established on a new tranport connection (i.e., after
        CapEx is sent but before Capex or other SSP control messages
        have been received).  Pacing (2) indicates that the standard
        RFC 1795 pacing mechanism is in use.  Other (3) may be either
        the RFC 1434+ xBusy mechanism operating to a back-level DLSw,
        or a vendor-specific flow control method.  Whether it is xBusy
        or not can be inferred from dlswTConnOperPartnerVersion."
    ::= { dlswTConnOperEntry 8 }
 
dlswTConnOperPartnerVersion  OBJECT-TYPE
    SYNTAX     OCTET STRING (SIZE (0..2))
    ACCESS     read-only
    STATUS     mandatory
    DESCRIPTION
       "This value identifies which version (first octet) and release
        (second octect) of the DLSw standard is supported by this
        partner DLSw. This information is obtained from a DLSw
        capabilities exchange message received from the partner DLSw.
        A string of zero length is returned before a Capabilities
        Exchange message is received, or if one is never received.
        A conceptual row with a dlswTConnOperState of -connected- but
        a zero length partner version indicates that the partner is
        a non-standard DLSw partner.
 
        If an implementation chooses to keep dlswTConnOperEntrys in
        the -disconnected- state, this value should remain unchanged."
    ::= { dlswTConnOperEntry 9 }
 
dlswTConnOperPartnerVendorID  OBJECT-TYPE
    SYNTAX     OCTET STRING (SIZE (0..3))
    ACCESS     read-only
    STATUS     mandatory
    DESCRIPTION
       "This value identifies the IEEE-assigned organizationally
        Unique Identifier (OUI) of the maker of this partner
        DLSw.  This information is obtained from a DLSw
        capabilities exchange message received from the partner DLSw.
        A string of zero length is returned before a Capabilities
        Exchange message is received, or if one is never received.
 
        If an implementation chooses to keep dlswTConnOperEntrys in
        the -disconnected- state, this value should remain unchanged."
    ::= { dlswTConnOperEntry 10 }
 
dlswTConnOperPartnerVersionStr  OBJECT-TYPE
    SYNTAX     DisplayString (SIZE (0..253))
    ACCESS     read-only
    STATUS     mandatory
    DESCRIPTION
       "This value identifies the particular product version (e.g.,
        product name, code level, fix level) of this partner DLSw.
        The format of the actual version string is vendor-specific.
        This information is obtained from a DLSw capabilities exchange
        message received from the partner DLSw.
        A string of zero length is returned before a Capabilities
        Exchange message is received, if one is never received, or
        if one is received but it does not contain a version string.
 
        If an implementation chooses to keep dlswTConnOperEntrys in
        the -disconnected- state, this value should remain unchanged."
    ::= { dlswTConnOperEntry 11 }
 
dlswTConnOperPartnerInitPacingWndw  OBJECT-TYPE
    SYNTAX     INTEGER (0..65535)
    ACCESS     read-only
    STATUS     mandatory
    DESCRIPTION
       "The value of the partner initial receive pacing window.  This
        is our initial send pacing window for all new circuits on this
        transport connection, as modified and granted by the first flow
        control indication the partner sends on each circuit.
        This information is obtained from a DLSw capabilities exchange
        message received from the partner DLSw.
        A value of zero is returned before a Capabilities
        Exchange message is received, or if one is never received.
 
        If an implementation chooses to keep dlswTConnOperEntrys in
        the -disconnected- state, this value should remain unchanged."
    ::= { dlswTConnOperEntry 12 }
 
dlswTConnOperPartnerSapList  OBJECT-TYPE
    SYNTAX     OCTET STRING (SIZE (0..16))
    ACCESS     read-write
    STATUS     mandatory
    DESCRIPTION
       "The Supported SAP List received in the capabilities
        exchange message from the partner DLSw.  This list has
        the same format described for dlswTConnConfigSapList.
        A string of zero length is returned before a Capabilities
        Exchange message is received, or if one is never received.
 
        If an implementation chooses to keep dlswTConnOperEntrys in
        the -disconnected- state, this value should remain unchanged."
    ::= { dlswTConnOperEntry 13 }
 
dlswTConnOperPartnerNBExcl  OBJECT-TYPE
    SYNTAX     Truthvalue
    ACCESS     read-only
    STATUS     mandatory
    DESCRIPTION
       "The value of true signifies that the NetBIOS names received
        from this partner in the NetBIOS name list in its capabilities
        exchange message are the only NetBIOS names reachable by
        that partner.  -False- indicates that other NetBIOS names may
        be reachable.  -False- should be returned before a Capabilities
        Exchange message is received, if one is never received, or if
        one is received without a NB Name Exclusivity CV.
 
        If an implementation chooses to keep dlswTConnOperEntrys in
        the -disconnected- state, this value should remain unchanged."
    ::= { dlswTConnOperEntry 14 }
 
dlswTConnOperPartnerMacExcl  OBJECT-TYPE
    SYNTAX     Truthvalue
    ACCESS     read-only
    STATUS     mandatory
    DESCRIPTION
       "The value of true signifies that the MAC addresses received
        from this partner in the MAC address list in its capabilities
        exchange message are the only MAC addresses reachable by
        that partner.  -False- indicates that other MAC addresses may
        be reachable.  -False- should be returned before a Capabilities
        Exchange message is received, if one is never received, or if
        one is received without a MAC Address Exclusivity CV.
 
        If an implementation chooses to keep dlswTConnOperEntrys in
        the -disconnected- state, this value should remain unchanged."
    ::= { dlswTConnOperEntry 15 }
 
dlswTConnOperPartnerNBInfo  OBJECT-TYPE
    SYNTAX     INTEGER  {
       none           (1),  -- none is kept
       partial        (2),  -- partial list is kept
       complete       (3),  -- complete list is kept
       notApplicable  (4)
    }
    ACCESS     read-only
    STATUS     mandatory
    DESCRIPTION
       "It is up to this DSLw whether to keep either none, some,
        or all of the NetBIOS name list that was received in
        the capabilities exchange message sent by this partner DLSw.
        This object identifies how much information was kept by
        this DLSw.  These names are stored as userConfigured
        remote entries in dlswDirNBTable.
        A value of (4), notApplicable, should be returned before
        a Capabilities Exchange message is received, or if one is
        never received.
 
        If an implementation chooses to keep dlswTConnOperEntrys in
        the -disconnected- state, this value should remain unchanged."
    ::= { dlswTConnOperEntry 16 }
 
dlswTConnOperPartnerMacInfo  OBJECT-TYPE
    SYNTAX     INTEGER  {
       none           (1),  -- none is kept
       partial        (2),  -- partial list is kept
       complete       (3),  -- complete list is kept
       notApplicable  (4)
    }
    ACCESS     read-only
    STATUS     mandatory
    DESCRIPTION
       "It is up to this DLSw whether to keep either none, some,
        or all of the MAC address list that was received in the
        capabilities exchange message sent by this partner DLSw.
        This object identifies how much information was kept by
        this DLSw.  These names are stored as userConfigured
        remote entries in dlswDirMACTable.
        A value of (4), notApplicable, should be returned before
        a Capabilities Exchange message is received, or if one is
        never received.
 
        If an implementation chooses to keep dlswTConnOperEntrys in
        the -disconnected- state, this value should remain unchanged."
    ::= { dlswTConnOperEntry 17 }
 
-- ...................................................................
-- Information about the last disconnect of this transport connection.
--   These objects make sense only for implementations that keep
--   transport connection information around after disconnection.
-- ...................................................................

dlswTConnOperDiscTime  OBJECT-TYPE
    SYNTAX     DlswTimeStamp
    ACCESS     read-only
    STATUS     mandatory
    DESCRIPTION
       "The value of dlswUpTime when dlswTConnOperState last
        entered -disconnected- state."
    ::= { dlswTConnOperEntry 18 }
 
dlswTConnOperDiscReason  OBJECT-TYPE
    SYNTAX     INTEGER  {
        other              (1),
        capExFailed        (2),
        transportLayerDisc (3),
        operatorCommand    (4),
        lastCircuitDiscd   (5),
        protocolError      (6)
    }
    ACCESS     read-only
    STATUS     mandatory
    DESCRIPTION
       "This object signifies the reason that either prevented the
        transport connection from entering the connected state, or
        caused the transport connection to enter the disconnected state."
    ::= { dlswTConnOperEntry 19 }
 
dlswTConnOperDiscActiveCir  OBJECT-TYPE
    SYNTAX     INTEGER
    ACCESS     read-only
    STATUS     mandatory
    DESCRIPTION
       "The number of circuits active (not in DISCONNECTED state)
        at the time the transport connection was last disconnected.
        This value is zero if the transport connection has never
        been connected."
    ::= { dlswTConnOperEntry 20 }
 
-- ...................................................................
-- Transport Connection Statistics
-- (1) Traffic counts
-- ...................................................................

dlswTConnOperInDataPkts  OBJECT-TYPE
    SYNTAX     Counter
--  UNITS      "SSP messages"
    ACCESS     read-only
    STATUS     mandatory
    DESCRIPTION
       "The number of Switch-to-Switch Protocol (SSP) messages of
        type DGRMFRAME, DATAFRAME, or INFOFRAME received on this
        transport connection."
    ::= { dlswTConnOperEntry 21 }
 
dlswTConnOperOutDataPkts  OBJECT-TYPE
    SYNTAX     Counter
--  UNITS      "SSP messages"
    ACCESS     read-only
    STATUS     mandatory
    DESCRIPTION
       "The number of Switch-to-Switch Protocol (SSP) messages of
        type DGRMFRAME, DATAFRAME, or INFOFRAME transmitted on this
        transport connection."
    ::= { dlswTConnOperEntry 22 }
 
dlswTConnOperInDataOctets  OBJECT-TYPE
    SYNTAX     Counter
--  UNITS      "octets"
    ACCESS     read-only
    STATUS     mandatory
    DESCRIPTION
       "The number octets in Switch-to-Switch Protocol (SSP) messages
        of type DGRMFRAME, DATAFRAME, or INFOFRAME received on this
        transport connection.  Each message is counted starting with
        the first octet following the SSP message header."
    ::= { dlswTConnOperEntry 23 }
 
dlswTConnOperOutDataOctets  OBJECT-TYPE
    SYNTAX     Counter
--  UNITS      "octets"
    ACCESS     read-only
    STATUS     mandatory
    DESCRIPTION
       "The number octets in Switch-to-Switch Protocol (SSP) messages
        of type DGRMFRAME, DATAFRAME, or INFOFRAME transmitted on this
        transport connection.  Each message is counted starting with
        the first octet following the SSP message header."
    ::= { dlswTConnOperEntry 24 }
 
dlswTConnOperInCntlPkts  OBJECT-TYPE
    SYNTAX     Counter
--  UNITS      "SSP messages"
    ACCESS     read-only
    STATUS     mandatory
    DESCRIPTION
       "The number of Switch-to-Switch Protocol (SSP) messages
        received on this transport connection which were not of
        type DGRMFRAME, DATAFRAME, or INFOFRAME."
    ::= { dlswTConnOperEntry 25 }
 
dlswTConnOperOutCntlPkts  OBJECT-TYPE
    SYNTAX     Counter
--  UNITS      "SSP messages"
    ACCESS     read-only
    STATUS     mandatory
    DESCRIPTION
       "The number of Switch-to-Switch Protocol (SSP) messages of
        transmitted on this transport connection which were not of
        type DGRMFRAME, DATAFRAME, or INFOFRAME."
    ::= { dlswTConnOperEntry 26 }
 
-- ...................................................................
-- (2) Directory activities (Explorer messages)
-- ...................................................................
 
dlswTConnOperCURexSents  OBJECT-TYPE
    SYNTAX     Counter
    ACCESS     read-only
    STATUS     mandatory
    DESCRIPTION
       "The number of CanUReach_ex messages sent on this transport
        connection."
    ::= { dlswTConnOperEntry 27 }
 
dlswTConnOperICRexRcvds  OBJECT-TYPE
    SYNTAX     Counter
    ACCESS     read-only
    STATUS     mandatory
    DESCRIPTION
       "The number of ICanReach_ex messages received on this transport
        connection."
    ::= { dlswTConnOperEntry 28 }
 
dlswTConnOperCURexRcvds  OBJECT-TYPE
    SYNTAX     Counter
    ACCESS     read-only
    STATUS     mandatory
    DESCRIPTION
       "The number of CanUReach_ex messages received on this transport
        connection."
    ::= { dlswTConnOperEntry 29 }
 
dlswTConnOperICRexSents  OBJECT-TYPE
    SYNTAX     Counter
    ACCESS     read-only
    STATUS     mandatory
    DESCRIPTION
       "The number of ICanReach_ex messages sent on this transport
        connection."
    ::= { dlswTConnOperEntry 30 }
 
dlswTConnOperNQexSents  OBJECT-TYPE
    SYNTAX     Counter
    ACCESS     read-only
    STATUS     mandatory
    DESCRIPTION
       "The number of NetBIOS_NQ_ex (NetBIOS Name Query-explorer) messages
        sent on this transport connection."
    ::= { dlswTConnOperEntry 31 }
 
dlswTConnOperNRexRcvds  OBJECT-TYPE
    SYNTAX     Counter
    ACCESS     read-only
    STATUS     mandatory
    DESCRIPTION
       "The number of NETBIOS_NR_ex (NetBIOS Name Recognized-explorer)
        messages received on this transport connection."
    ::= { dlswTConnOperEntry 32 }
 
dlswTConnOperNQexRcvds  OBJECT-TYPE
    SYNTAX     Counter
    ACCESS     read-only
    STATUS     mandatory
    DESCRIPTION
       "The number of NETBIOS_NQ_ex messages received on this
        transport connection."
    ::= { dlswTConnOperEntry 33 }
 
dlswTConnOperNRexSents  OBJECT-TYPE
    SYNTAX     Counter
    ACCESS     read-only
    STATUS     mandatory
    DESCRIPTION
       "The number of NETBIOS_NR_ex messages sent on this transport
        connection."
    ::= { dlswTConnOperEntry 34 }
 
-- ...................................................................
-- (3) Circuit activities on each transport connection
-- ...................................................................

dlswTConnOperCirCreates  OBJECT-TYPE
    SYNTAX     Counter
    ACCESS     read-only
    STATUS     mandatory
    DESCRIPTION
       "The number of times that circuits entered -circuit_established-
        state (not counting transitions from -circuit_restart-)."
    ::= { dlswTConnOperEntry 35 }
 
dlswTConnOperCircuits  OBJECT-TYPE
    SYNTAX     Gauge
    ACCESS     read-only
    STATUS     mandatory
    DESCRIPTION
       "The number of currently active circuits on this transport
        connection, where -active- means not in -disconnected- state."
    ::= { dlswTConnOperEntry 36 }
 
 
-- *******************************************************************
-- *                                                                 *
-- *                        DIRECTORY GROUP                          *
-- *                                                                 *
-- *******************************************************************

-- Directory Related Statistical Objects

dlswDirStat     OBJECT IDENTIFIER ::= { dlswDirectory 1 }
 
dlswDirMacEntries  OBJECT-TYPE
    SYNTAX     Gauge
    ACCESS     read-only
    STATUS     mandatory
    DESCRIPTION
       "The current total number of entries in the dlswDirMacTable."
    ::= { dlswDirStat 1 }
 
dlswDirNBEntries  OBJECT-TYPE
    SYNTAX     Gauge
    ACCESS     read-only
    STATUS     mandatory
    DESCRIPTION
       "The current total number of entries in the dlswDirNBTable."
    ::= { dlswDirStat 4 }
 
-- Directory Cache

dlswDirCache     OBJECT IDENTIFIER ::= { dlswDirectory 2 }
 
 
dlswDirMacTable  OBJECT-TYPE
    SYNTAX     SEQUENCE OF DlswDirMacEntry
    ACCESS     not-accessible
    STATUS     mandatory
    DESCRIPTION
       "This table contains locations of MAC addresses.
        They could be either verified or not verified,
        local or remote, and configured locally or learned
        from either Capabilities Exchange messages or
        directory searches."
    ::= { dlswDirCache 1 }
 
dlswDirMacEntry  OBJECT-TYPE
    SYNTAX     DlswDirMacEntry
    ACCESS     not-accessible
    STATUS     mandatory
    DESCRIPTION
       "Indexed by dlswDirMacIndex."
    INDEX   { dlswDirMacIndex }
    ::= { dlswDirMacTable 1 }
 
DlswDirMacEntry ::= SEQUENCE {
    dlswDirMacIndex          INTEGER,
    dlswDirMacMac            MacAddress,
    dlswDirMacMask           MacAddress,
    dlswDirMacEntryType      INTEGER,
    dlswDirMacLocationType   INTEGER,
    dlswDirMacLocation       Instancepointer,
    dlswDirMacStatus         INTEGER,
    dlswDirMacLFSize         LFSize,
    dlswDirMacRowStatus      RowStatus
    }
 
dlswDirMacIndex  OBJECT-TYPE
    SYNTAX     INTEGER
    ACCESS     read-only
    STATUS     mandatory
    DESCRIPTION
       "Uniquely identifies a conceptual row of this table."
    ::= { dlswDirMacEntry 1 }
 
dlswDirMacMac  OBJECT-TYPE
    SYNTAX     MacAddress
    ACCESS     read-only
    STATUS     mandatory
    DESCRIPTION
       "The MAC address, together with the dlswDirMacMask,
        specifies a set of MAC addresses that are defined or
        discovered through an interface or partner DLSw nodes."
    ::= { dlswDirMacEntry 2 }
 
dlswDirMacMask  OBJECT-TYPE
    SYNTAX     MacAddress
    ACCESS     read-only
    STATUS     mandatory
    DESCRIPTION
       "The MAC address mask, together with the dlswDirMacMac,
        specifies a set of MAC addresses that are defined or
        discovered through an interface or partner DLSw nodes."
    DEFVAL { 'FFFFFFFFFFFF'H }
    ::= { dlswDirMacEntry 3 }
 
dlswDirMacEntryType  OBJECT-TYPE
    SYNTAX     INTEGER  {
        other                    (1),
        userConfiguredPublic     (2),
        userConfiguredPrivate    (3),
        partnerCapExMsg          (4),
        dynamic                  (5)
    }
    ACCESS     read-only
    STATUS     mandatory
    DESCRIPTION
       "The cause of the creation of this conceptual row.
        It could be one of the three methods: (1) user
        configured, including via management protocol
        set operations, configuration file, command line
        or equivalent methods; (2) learned from the
        partner DLSw Capabilities Exchange messages;
        and (3) dynamic, e.g., learned from ICanReach
        messages, or LAN explorer frames.  Since only
        individual MAC addresses can be dynamically learned,
        dynamic entries will all have a mask of all FFs.
 
        The public versus private distinction for user-
        configured resources applies only to local resources
        (UC remote resources are private), and indicates
        whether that resource should be advertised in
        capabilities exchange messages sent by this node."
    DEFVAL { userConfiguredPublic }
    ::= { dlswDirMacEntry 4 }
 
dlswDirMacLocationType  OBJECT-TYPE
    SYNTAX     INTEGER  {
        other                 (1),
        local                 (2),
        remote                (3)
    }
    ACCESS     read-only
    STATUS     mandatory
    DESCRIPTION
       "The location of the resource (or a collection of
        resources using a mask) of this conceptual row
        is either (1) local - the resource is reachable
        via an interface, or (2) remote - the resource
        is reachable via a partner DLSw node (or a set
        of partner DLSw nodes)."
    DEFVAL { local }
    ::= { dlswDirMacEntry 5 }
 
dlswDirMacLocation  OBJECT-TYPE
    SYNTAX     Instancepointer
    ACCESS     read-only
    STATUS     mandatory
    DESCRIPTION
       "Points to either the ifEntry, dlswTConnConfigEntry,
        dlswTConnOperEntry, 0.0, or something that is implementation
        specific.  It identifies the location of the MAC address
        (or the collection of MAC addresses.)"
    ::= { dlswDirMacEntry 6 }
 
dlswDirMacStatus  OBJECT-TYPE
    SYNTAX     INTEGER  {
        unknown               (1),
        reachable             (2),
        notReachable          (3)
    }
    ACCESS     read-only
    STATUS     mandatory
    DESCRIPTION
       "This object specifies whether DLSw currently believes
        the MAC address to be accessible at the specified location.
        The value `notReachable' allows a configured resource
        definition to be taken out of service when a search to
        that resource fails (avoiding a repeat of the search)."
    DEFVAL { unknown }
    ::= { dlswDirMacEntry 7 }
 
dlswDirMacLFSize  OBJECT-TYPE
    SYNTAX     LFSize
    ACCESS     read-only
    STATUS     mandatory
    DESCRIPTION
       "The largest size of the MAC INFO field (LLC header and data)
        that a circuit to the MAC address can carry through this path."
    ::= { dlswDirMacEntry 8 }
 
dlswDirMacRowStatus  OBJECT-TYPE
    SYNTAX     RowStatus
    ACCESS     read-only
    STATUS     mandatory
    DESCRIPTION
       "This object is used by a Management Station to create
        or delete the row entry in the dlswDirMacTable
        following the RowStatus textual convention."
    ::= { dlswDirMacEntry 9 }
 
-- ...................................................................
-- Directory for NetBIOS Names
-- ...................................................................

dlswDirNBTable  OBJECT-TYPE
    SYNTAX     SEQUENCE OF DlswDirNBEntry
    ACCESS     not-accessible
    STATUS     mandatory
    DESCRIPTION
       "This table contains locations of NetBIOS names.
        They could be either verified or not verified,
        local or remote, and configured locally or learned
        from either Capabilities Exchange messages or
        directory searches."
    ::= { dlswDirCache 2 }
 
dlswDirNBEntry  OBJECT-TYPE
    SYNTAX     DlswDirNBEntry
    ACCESS     not-accessible
    STATUS     mandatory
    DESCRIPTION
       "Indexed by dlswDirNBIndex."
    INDEX   { dlswDirNBIndex }
    ::= { dlswDirNBTable 1 }
 
DlswDirNBEntry ::= SEQUENCE {
    dlswDirNBIndex           INTEGER,
    dlswDirNBName            NBName,
    dlswDirNBNameType        INTEGER,
    dlswDirNBEntryType       INTEGER,
    dlswDirNBLocationType    INTEGER,
    dlswDirNBLocation        Instancepointer,
    dlswDirNBStatus          INTEGER,
    dlswDirNBLFSize          LFSize,
    dlswDirNBRowStatus       RowStatus
    }
 
dlswDirNBIndex  OBJECT-TYPE
    SYNTAX     INTEGER
    ACCESS     read-only
    STATUS     mandatory
    DESCRIPTION
       "Uniquely identifies a conceptual row of this table."
    ::= { dlswDirNBEntry 1 }
 
dlswDirNBName  OBJECT-TYPE
    SYNTAX     NBName
    ACCESS     read-only
    STATUS     mandatory
    DESCRIPTION
       "The NetBIOS name (including `any char' and `wildcard' characters)
        specifies a set of NetBIOS names that are defined or discovered
        through an interface or partner DLSw nodes."
    ::= { dlswDirNBEntry 2 }
 
dlswDirNBNameType  OBJECT-TYPE
    SYNTAX     INTEGER  {
        unknown       (1),
        individual    (2),
        group         (3)
    }
    ACCESS     read-only
    STATUS     mandatory
    DESCRIPTION
       "Whether dlswDirNBName represents an (or a set of) individual
        or group NetBIOS name(s)."
    DEFVAL { unknown }
    ::= { dlswDirNBEntry 3 }
 
dlswDirNBEntryType  OBJECT-TYPE
    SYNTAX     INTEGER  {
        other                    (1),
        userConfiguredPublic     (2),
        userConfiguredPrivate    (3),
        partnerCapExMsg          (4),
        dynamic                  (5)
    }
    ACCESS     read-only
    STATUS     mandatory
    DESCRIPTION
       "The cause of the creation of this conceptual row.
        It could be one of the three methods: (1) user
        configured, including via management protocol
        set operations, configuration file, command line,
        or equivalent methods; (2) learned from the
        partner DLSw Capabilities Exchange messages;
        and (3) dynamic, e.g., learned from ICanReach
        messages, or test frames.  Since only actual
        NetBIOS names can be dynamically learned, dynamic
        entries will not contain any char or wildcard
        characters.
 
        The public versus private distinction for user-
        configured resources applies only to local resources
        (UC remote resources are private), and indicates
        whether that resource should be advertised in
        capabilities exchange messages sent by this node."
    DEFVAL { userConfiguredPublic }
    ::= { dlswDirNBEntry 4 }
 
dlswDirNBLocationType  OBJECT-TYPE
    SYNTAX     INTEGER  {
        other                 (1),
        local                 (2),
        remote                (3)
    }
    ACCESS     read-only
    STATUS     mandatory
    DESCRIPTION
       "The location of the resource (or a collection of resources
        using any char/wildcard characters) of this conceptual row
        is either (1) local - the resource is reachable via an
        interface, or (2) remote - the resource is reachable via a
        a partner DLSw node (or a set of partner DLSw nodes)."
    DEFVAL { local }
    ::= { dlswDirNBEntry 5 }
 
dlswDirNBLocation  OBJECT-TYPE
    SYNTAX     Instancepointer
    ACCESS     read-only
    STATUS     mandatory
    DESCRIPTION
       "Points to either the ifEntry, dlswTConnConfigEntry,
        dlswTConnOperEntry, 0.0, or something that is implementation
        specific.  It identifies the location of the NetBIOS name
        or the set of NetBIOS names."
    ::= { dlswDirNBEntry 6 }
 
dlswDirNBStatus  OBJECT-TYPE
    SYNTAX     INTEGER  {
        unknown               (1),
        reachable             (2),
        notReachable          (3)
    }
    ACCESS     read-only
    STATUS     mandatory
    DESCRIPTION
       "This object specifies whether DLSw currently believes
        the NetBIOS name to be accessible at the specified location.
        The value `notReachable' allows a configured resource
        definition to be taken out of service when a search to
        that resource fails (avoiding a repeat of the search)."
    DEFVAL { unknown }
    ::= { dlswDirNBEntry 7 }
 
dlswDirNBLFSize  OBJECT-TYPE
    SYNTAX     LFSize
    ACCESS     read-only
    STATUS     mandatory
    DESCRIPTION
       "The largest size of the MAC INFO field (LLC header and data)
        that a circuit to the NB name can carry through this path."
    ::= { dlswDirNBEntry 8 }
 
dlswDirNBRowStatus  OBJECT-TYPE
    SYNTAX     RowStatus
    ACCESS     read-only
    STATUS     mandatory
    DESCRIPTION
       "This object is used by a Management Station to create
        or delete the row entry in the dlswDirNBTable
        following the RowStatus textual convention."
    ::= { dlswDirNBEntry 9 }
 


-- *******************************************************************
-- *                                                                 *
-- *                          CIRCUIT GROUP                          *
-- *                                                                 *
-- *******************************************************************
--
-- A circuit is the end-to-end association of two DLS entities
-- through one or two DLSw nodes.  It is the concatenation of
-- two "data links", optionally with an intervening transport
-- connection. Origin of the circuit is the end station which
-- initiates the circuit.  Target of the circuit is the end
-- station which receives the initiation.
--
 
dlswCircuitStat      OBJECT IDENTIFIER ::= { dlswCircuit 1 }

dlswActiveCircuits  OBJECT-TYPE
    SYNTAX     Gauge
    ACCESS     read-only
    STATUS     mandatory
    DESCRIPTION
       "The number of entries in dlswCircuitTable which are
        not in the disconnected state."
    ::= { dlswCircuitStat 1 }
 
dlswCircuitCreates  OBJECT-TYPE
    SYNTAX     Counter
    ACCESS     read-only
    STATUS     mandatory
    DESCRIPTION
       "The total number of entries ever added to dlswCircuitTable, 
	or reactivated upon exiting -disconnected- state."
    ::= { dlswCircuitStat 2 }
 
--
-- Circuit Table (dlswCircuit)
--
-- This table is the DLSw entity-s view of circuits.  There will be
-- a conceptual row in the table associated with each data link.
--
-- The chart below lists the various possible combinations of
-- origin and target MAC locations and the number of entries in
-- this Circuit Table:
--
--           number of       |    Origin End Station Location
--         entries in the    |--------------------------------------
--         Circuit Table     |  internal     local       remote
--     Target    |  internal |     NA          2           1
--     End       |  local    |     2           2           1
--     Station   |  remote   |     1           1           NA
--     Location  |           |
--
--     NA: Not applicable
--
--  Note:
--  (a) IfIndex and RouteInfo are applied only if location is local.
--  (b) TDomain and TAddr are applied only if location is remote.
--
-- Most of statistics related to circuits can be collected
-- from LLC-2 Link Station Table.
--

dlswCircuitTable  OBJECT-TYPE
    SYNTAX     SEQUENCE OF DlswCircuitEntry
    ACCESS     not-accessible
    STATUS     mandatory
    DESCRIPTION
       "This table is the circuit representation in the DLSw
        entity. Virtual data links are used to represent any internal
        end stations.  There is a conceptual row associated with
        each data link.  Thus, for circuits without an intervening
        transport connection, there are two conceptual rows
        for each circuit.
 
        The table consists of the circuits being established,
        established, and as an implementation option, circuits that
        have been disconnected.  For circuits carried over
        transport connections, an entry is created after
        the CUR_cs was sent or received.  For circuits between
        two locally attached devices, or internal virtual MAC
        addresses, an entry is created when the equivalent of
        CUR_cs sent/received status is reached.
 
        End station 1 (S1) and End station 2 (S2) are used to
        represent the two end stations of the circuit.
        S1 is always an end station which is locally attached.
        S2 may be locally attached or remote.  If it is locally
        attached, the circuit will be represented by two rows indexed
        by (A, B) and (B, A) where A & B are the relevant MACs/SAPs.
 
        The table may be used to store the causes of disconnection of
        circuits.  It is recommended that the oldest disconnected
        circuit entry be removed from this table when the memory
        space of disconnected circuits is needed."
    ::= { dlswCircuit 2 }
 
dlswCircuitEntry  OBJECT-TYPE
    SYNTAX     DlswCircuitEntry
    ACCESS     not-accessible
    STATUS     mandatory
    DESCRIPTION
       ""
    INDEX   { dlswCircuitS1Mac,
              dlswCircuitS1Sap,
              dlswCircuitS2Mac,
              dlswCircuitS2Sap }
    ::= { dlswCircuitTable 1 }
 
DlswCircuitEntry ::= SEQUENCE {
    dlswCircuitS1Mac                MacAddress,
    dlswCircuitS1Sap                OCTET STRING,
    dlswCircuitS1IfIndex            INTEGER,
    dlswCircuitS1DlcType            DlcType,
    dlswCircuitS1RouteInfo          OCTET STRING,
    dlswCircuitS1CircuitId          OCTET STRING,
    dlswCircuitS1Dlc                Instancepointer,
    dlswCircuitS2Mac                MacAddress,
    dlswCircuitS2Sap                OCTET STRING,
    dlswCircuitS2Location           EndStationLocation,
    dlswCircuitS2TDomain            OBJECT IDENTIFIER,
    dlswCircuitS2TAddress           TAddress,
    dlswCircuitS2CircuitId          OCTET STRING,
    dlswCircuitOrigin               INTEGER,
    dlswCircuitEntryTime            DlswTimeStamp,
    dlswCircuitStateTime            DlswTimeStamp,
    dlswCircuitState                INTEGER,
    dlswCircuitPriority             INTEGER,
    dlswCircuitFCSendGrantedUnits   INTEGER,
    dlswCircuitFCSendCurrentWndw    INTEGER,
    dlswCircuitFCRecvGrantedUnits   INTEGER,
    dlswCircuitFCRecvCurrentWndw    INTEGER,
    dlswCircuitFCLargestRecvGranted Gauge,
    dlswCircuitFCLargestSendGranted Gauge,
    dlswCircuitFCHalveWndwSents     Counter,
    dlswCircuitFCResetOpSents       Counter,
    dlswCircuitFCHalveWndwRcvds     Counter,
    dlswCircuitFCResetOpRcvds       Counter,
    dlswCircuitDiscReasonLocal      INTEGER,
    dlswCircuitDiscReasonRemote     INTEGER,
    dlswCircuitDiscReasonRemoteData OCTET STRING
    }
 
-- ...................................................................
-- Information related to the End Station 1 (S1).
-- ...................................................................

dlswCircuitS1Mac  OBJECT-TYPE
    SYNTAX     MacAddress
    ACCESS     read-only
    STATUS     mandatory
    DESCRIPTION
       "The MAC Address of End Station 1 (S1) used for this circuit."
    ::= { dlswCircuitEntry 1 }
 
dlswCircuitS1Sap  OBJECT-TYPE
    SYNTAX     OCTET STRING (SIZE(1))
    ACCESS     read-only
    STATUS     mandatory
    DESCRIPTION
       "The SAP at End Station 1 (S1) used for this circuit."
    ::= { dlswCircuitEntry 2 }
 
dlswCircuitS1IfIndex  OBJECT-TYPE
    SYNTAX     INTEGER
    ACCESS     read-only
    STATUS     mandatory
    DESCRIPTION
       "The IfEntry index of the local interface through which S1
        can be reached."
    ::= { dlswCircuitEntry 3 }
 
dlswCircuitS1DlcType  OBJECT-TYPE
    SYNTAX     DlcType
    ACCESS     read-only
    STATUS     mandatory
    DESCRIPTION
       "The DLC protocol in use between the DLSw node and S1."
    ::= { dlswCircuitEntry 4 }
 
dlswCircuitS1RouteInfo  OBJECT-TYPE
    SYNTAX     OCTET STRING (SIZE (0..30))
    ACCESS     read-only
    STATUS     mandatory
    DESCRIPTION
       "If source-route bridging is in use between the DLSw
        node and S1, this is the routing information field
        describing the path between the two devices.
        Otherwise the value will be an OCTET STRING of
        zero length."
    ::= { dlswCircuitEntry 5 }
 
dlswCircuitS1CircuitId  OBJECT-TYPE
    SYNTAX     OCTET STRING (SIZE (0..8))
    ACCESS     read-only
    STATUS     mandatory
    DESCRIPTION
       "The Circuit ID assigned by this DLSw node to this circuit.
        The first four octets are the DLC port Id, and
        the second four octets are the Data Link Correlator.
        If the DLSw SSP was not used to establish this circuit,
        the value will be a string of zero length."
    ::= { dlswCircuitEntry 6 }
 
dlswCircuitS1Dlc  OBJECT-TYPE
    SYNTAX     Instancepointer
    ACCESS     read-only
    STATUS     mandatory
    DESCRIPTION
       "Points to a conceptual row of the underlying DLC MIB,
        which could either be the standard SDLC or LLC MIBs, or an
        enterprise-specific DLC MIB."
    ::= { dlswCircuitEntry 7 }
 
-- ...................................................................
-- Information related to the End Station 2 (S2).
-- ...................................................................

dlswCircuitS2Mac  OBJECT-TYPE
    SYNTAX     MacAddress
    ACCESS     read-only
    STATUS     mandatory
    DESCRIPTION
       "The MAC Address of End Station 2 (S2) used for this circuit."
    ::= { dlswCircuitEntry 8 }
 
dlswCircuitS2Sap  OBJECT-TYPE
    SYNTAX     OCTET STRING (SIZE(1))
    ACCESS     read-only
    STATUS     mandatory
    DESCRIPTION
       "The SAP at End Station 2 (S2) used for this circuit."
    ::= { dlswCircuitEntry 9 }
 
dlswCircuitS2Location  OBJECT-TYPE
    SYNTAX     EndStationLocation
    ACCESS     read-only
    STATUS     mandatory
    DESCRIPTION
       "The location of End Station 2 (S2).
        If the location of End Station 2 is local, the
        interface information will be available in the
        conceptual row whose S1 and S2 are the S2 and
        the S1 of this conceptual row, respectively."
    ::= { dlswCircuitEntry 10 }
 
dlswCircuitS2TDomain  OBJECT-TYPE
    SYNTAX     OBJECT IDENTIFIER
    ACCESS     read-only
    STATUS     mandatory
    DESCRIPTION
       "If the location of End Station 2 is remote,
        this value is the transport domain of the
        transport protocol the circuit is running
        over.  Otherwise, the value is 0.0."
    ::= { dlswCircuitEntry 11 }
 
dlswCircuitS2TAddress  OBJECT-TYPE
    SYNTAX     TAddress
    ACCESS     read-only
    STATUS     mandatory
    DESCRIPTION
       "If the location of End Station 2 is remote,
        this object contains the address of the partner
        DLSw, else it will be an OCTET STRING of zero length."
    ::= { dlswCircuitEntry 12 }
 
dlswCircuitS2CircuitId  OBJECT-TYPE
    SYNTAX     OCTET STRING (SIZE (0..8))
    ACCESS     read-only
    STATUS     mandatory
    DESCRIPTION
       "The Circuit ID assigned to this circuit by the partner
        DLSw node.  The first four octets are the DLC port Id, and
        the second four octets are the Data Link Correlator.
        If the DLSw SSP was not used to establish this circuit,
        the value will be a string of zero length."
    ::= { dlswCircuitEntry 13 }
 
dlswCircuitOrigin  OBJECT-TYPE
    SYNTAX     INTEGER  {
        s1             (1),
        s2             (2)
    }
    ACCESS     read-only
    STATUS     mandatory
    DESCRIPTION
       "This object specifies which of the two end stations
        initiated the establishment of this circuit."
    ::= { dlswCircuitEntry 14 }
 
-- ...................................................................
-- Operational information related to this circuit.
-- ...................................................................
dlswCircuitEntryTime  OBJECT-TYPE
    SYNTAX     DlswTimeStamp
    ACCESS     read-only
    STATUS     mandatory
    DESCRIPTION
       "The value of dlswUpTime when this circuit table
        conceptual row was created."
    ::= { dlswCircuitEntry 15 }
 
dlswCircuitStateTime  OBJECT-TYPE
    SYNTAX     DlswTimeStamp
    ACCESS     read-only
    STATUS     mandatory
    DESCRIPTION
       "The value of dlswUpTime when this circuit entered the
        current state."
    ::= { dlswCircuitEntry 16 }
 
dlswCircuitState  OBJECT-TYPE
    SYNTAX     INTEGER  {
        disconnected           (1),
        circuitStart           (2),
        resolvePending         (3),
        circuitPending         (4),
        circuitEstablished     (5),
        connectPending         (6),
        contactPending         (7),
        connected              (8),
        disconnectPending      (9),
        haltPending            (10),
        haltPendingNoack       (11),
        circuitRestart         (12),
        restartPending         (13)
    }
    ACCESS     read-write
    STATUS     mandatory
    DESCRIPTION
       "The current state of this circuit.  The implementation
        may choose to keep entries for some period of time after
        circuit disconnect, so the network management station can
        gather the time and cause of disconnection.
 
        While all of the specified values may be returned from a GET
        operation, the only SETable value is -disconnectPending-.
        When this value is set, DLSw should perform the appropriate
        action given its previous state (e.g., send HALT_DL if the
        state was -connected-) to bring the circuit down to the
        -disconnected- state.  Both the partner DLSw and local end
        station(s) should be notified as appropriate.
 
        This MIB provides no facility to re-establish a disconnected
        circuit, because in DLSw this should be an end station-driven
        function."
    ::= { dlswCircuitEntry 17 }
 
dlswCircuitPriority  OBJECT-TYPE
    SYNTAX     INTEGER  {
        unsupported     (0),
        low             (1),
        medium          (2),
        high            (3),
        highest         (4)
    }
    ACCESS     read-only
    STATUS     mandatory
    DESCRIPTION
       "The transmission priority of this circuit as understood by
        this DLSw node.  This value is determined by the two DLSw
        nodes at circuit startup time.  If this DLSw node does not
        support DLSw circuit priority, the value -unsupported- should
        be returned."
    ::= { dlswCircuitEntry 18 }
 
-- ...................................................................
-- Pacing Objects:
-- These objects are applicable if DLSw is using the SSP circuit
-- pacing protocol to control the flow between the two data links
-- in this circuit.
-- ...................................................................

dlswCircuitFCSendGrantedUnits  OBJECT-TYPE
    SYNTAX     INTEGER (0..65535)
    ACCESS     read-only
    STATUS     mandatory
    DESCRIPTION
       "The number of paced SSP messages that this DLSw is currently
        authorized to send on this circuit before it must stop and
        wait for an additional flow control indication from the
        partner DLSw.
 
        The value zero should be returned if this circuit is not
        running the DLSw pacing protocol."
    ::= { dlswCircuitEntry 19 }
 
dlswCircuitFCSendCurrentWndw  OBJECT-TYPE
    SYNTAX     INTEGER (0..65535)
    ACCESS     read-only
    STATUS     mandatory
    DESCRIPTION
       "The current window size that this DLSw is using in its role
        as a data sender.  This is the value by which this DLSw would
        increase the number of messages it is authorized to send, if
        it were to receive a flow control indication with the bits
        specifying -repeat window-.
 
        The value zero should be returned if this circuit is not
        running the DLSw pacing protocol."
    ::= { dlswCircuitEntry 20 }
 
dlswCircuitFCRecvGrantedUnits  OBJECT-TYPE
    SYNTAX     INTEGER (0..65535)
    ACCESS     read-only
    STATUS     mandatory
    DESCRIPTION
       "The current number of paced SSP messages that this DLSw has
        authorized the partner DLSw to send on this circuit before
        the partner DLSw must stop and wait for an additional flow
        control indication from this DLSw.
 
        The value zero should be returned if this circuit is not
        running the DLSw pacing protocol."
    ::= { dlswCircuitEntry 21 }
 
dlswCircuitFCRecvCurrentWndw  OBJECT-TYPE
    SYNTAX     INTEGER (0..65535)
    ACCESS     read-only
    STATUS     mandatory
    DESCRIPTION
       "The current window size that this DLSw is using in its role
        as a data receiver.  This is the number of additional paced
        SSP messages that this DLSw would be authorizing its DLSw
        partner to send, if this DLSw were to send a flow control
        indication with the bits specifying -repeat window-.
 
        The value zero should be returned if this circuit is not
        running the DLSw pacing protocol."
    ::= { dlswCircuitEntry 22 }
 
dlswCircuitFCLargestRecvGranted  OBJECT-TYPE
    SYNTAX     Gauge
    ACCESS     read-only
    STATUS     mandatory
    DESCRIPTION
       "The largest receive window size granted by this DLSw during
        the current activation of this circuit.  This is not the
        largest number of messages granted at any time, but the
        largest window size as represented by FCIND operator bits.
 
        The value zero should be returned if this circuit is not
        running the DLSw pacing protocol."
    ::= { dlswCircuitEntry 23 }
 
dlswCircuitFCLargestSendGranted  OBJECT-TYPE
    SYNTAX     Gauge
    ACCESS     read-only
    STATUS     mandatory
    DESCRIPTION
       "The largest send (with respect to this DLSw) window size
        granted by the partner DLSw during the current activation of
        this circuit.
 
        The value zero should be returned if this circuit is not
        running the DLSw pacing protocol."
    ::= { dlswCircuitEntry 24 }
 
dlswCircuitFCHalveWndwSents  OBJECT-TYPE
    SYNTAX     Counter
    ACCESS     read-only
    STATUS     mandatory
    DESCRIPTION
       "The number of Halve Window operations this DLSw has sent on
        this circuit, in its role as a data receiver.
 
        The value zero should be returned if this circuit is not
        running the DLSw pacing protocol."
    ::= { dlswCircuitEntry 25 }
 
dlswCircuitFCResetOpSents  OBJECT-TYPE
    SYNTAX     Counter
    ACCESS     read-only
    STATUS     mandatory
    DESCRIPTION
       "The number of Reset Window operations this DLSw has sent on
        this circuit, in its role as a data receiver.
 
        The value zero should be returned if this circuit is not
        running the DLSw pacing protocol."
    ::= { dlswCircuitEntry 26 }
 
dlswCircuitFCHalveWndwRcvds  OBJECT-TYPE
    SYNTAX     Counter
    ACCESS     read-only
    STATUS     mandatory
    DESCRIPTION
       "The number of Halve Window operations this DLSw has received on
        this circuit, in its role as a data sender.
 
        The value zero should be returned if this circuit is not
        running the DLSw pacing protocol."
    ::= { dlswCircuitEntry 27 }
 
dlswCircuitFCResetOpRcvds  OBJECT-TYPE
    SYNTAX     Counter
    ACCESS     read-only
    STATUS     mandatory
    DESCRIPTION
       "The number of Reset Window operations this DLSw has received on
        this circuit, in its role as a data sender.
 
        The value zero should be returned if this circuit is not
        running the DLSw pacing protocol."
    ::= { dlswCircuitEntry 28 }
 
-- ...................................................................
-- Information about the circuit disconnection
-- ...................................................................
dlswCircuitDiscReasonLocal  OBJECT-TYPE
    SYNTAX     INTEGER  {
        endStationDiscRcvd           (1),
        endStationDlcError           (2),
        protocolError                (3),
        operatorCommand              (4),
        haltDlRcvd                   (5),
        haltDlNoAckRcvd              (6),
        transportConnClosed          (7)
    }
    ACCESS     read-only
    STATUS     mandatory
    DESCRIPTION
       "The reason why this circuit was last disconnected, as seen
        by this DLSw node.
 
        This object is present only if the implementation keeps circuit
        table entries around for some period after circuit disconnect."
    ::= { dlswCircuitEntry 29 }
 
dlswCircuitDiscReasonRemote  OBJECT-TYPE
    SYNTAX     INTEGER  {
        unknown                      (0),
        endStationDiscRcvd           (1),
        endStationDlcError           (2),
        protocolError                (3),
        operatorCommand              (4)
    }
    ACCESS     read-only
    STATUS     mandatory
    DESCRIPTION
       "The generic reason code why this circuit was last disconnected,
        as reported by the DLSw partner in a HALT_DL or HALT_DL_NOACK.
        If the partner does not send a reason code in these messages, or
        the DLSw implementation does not report receiving one, the value
        -unknown- is returned.
 
        This object is present only if the implementation keeps circuit
        table entries around for some period after circuit disconnect."
    ::= { dlswCircuitEntry 30 }
 
dlswCircuitDiscReasonRemoteData  OBJECT-TYPE
    SYNTAX     OCTET STRING (SIZE (0..4))
    ACCESS     read-only
    STATUS     mandatory
    DESCRIPTION
       "Implementation-specific data reported by the DLSw partner in a
        HALT_DL or HALT_DL_NOACK, to help specify how and why this
        circuit was last disconnected.  If the partner does not send
        this data in these messages, or the DLSw implementation does
        not report receiving it, a string of zero length is returned.
 
        This object is present only if the implementation keeps circuit
        table entries around for some period after circuit disconnect."
    ::= { dlswCircuitEntry 31 }
 
 

-- *******************************************************************
-- *                                                                 *
-- *                      PROPRIETARY EXTENSIONS                     *
-- *                                                                 *
-- *******************************************************************

-- dlswCircuitAdjNodeType  OBJECT-TYPE
--     SYNTAX     OCTET STRING (SIZE (2))
--     ACCESS     read-only
--     STATUS     mandatory
--     DESCRIPTION
--        "SNA Adjacent Node Type???"
--     ::= { dlswCircuitEntry 40 }

-- dlswCircuitAdjCpName  OBJECT-TYPE
--     SYNTAX     OCTET STRING (SIZE (8))
--     ACCESS     read-only
--     STATUS     mandatory
--     DESCRIPTION
--        "Name of SNA Adjacent Control Point."
--     ::= { dlswCircuitEntry 41 }



-- *******************************************************************
-- *                                                                 *
-- *                          DLSW TRAPS                             *
-- *                                                                 *
-- *******************************************************************
--

dlswTrapControl OBJECT IDENTIFIER  ::= { dlswNode 10}

-- ...................................................................
-- Trap Generation Control
-- ...................................................................
 
dlswTrapCntlTConn  OBJECT-TYPE
    SYNTAX     INTEGER {
        enabled     (1),
        disabled    (2)
    }
    ACCESS     read-write
    STATUS     mandatory
    DESCRIPTION
       "Indicates whether the DLSw is permitted to emit transport
        connection up and down traps.  With the value of `enabled'
        the DLSw will emit traps when connections enter `connected'
        and `disconnected' states.  With the value of `disabled'
        the DLSw will not emit traps when connections enter of
        `connected' and `disconnected' states.  With the value
        of `partial' the DLSw will only emits transport connection
        down traps when the connection is closed with busy.
        The changes take effect immediately."
    ::= { dlswTrapControl 3 }
 
dlswTrapCntlCircuit  OBJECT-TYPE
    SYNTAX     INTEGER {
        enabled     (1),
        disabled    (2)
    }
    ACCESS     read-write
    STATUS     mandatory
    DESCRIPTION
       "Indicates whether the DLSw is permitted to generate
        circuit up and down traps.  With the value of `enabled'
        the DLSw will emit traps when circuits enter `connected'
        and `disconnected' states.  With the value of `disabled'
        the DLSw will not emit traps when circuits enter of
        `connected' and `disconnected' states.  With the value
        of `partial' the DLSw will emit traps only for those
        circuits that are initiated by this DLSw, e.g.,
        originating the CUR_CS message.  The changes take effect
        immediately."
    ::= { dlswTrapControl 4 }
 
 
-- ...................................................................
-- Trap Definitions       
-- ...................................................................
-- *******************************************************************
 
dlswTraps  OBJECT IDENTIFIER ::= { dlswMIB-3Com 7 }
 
dlswTrapTConnUp TRAP-TYPE
    ENTERPRISE  dlswMIB-3Com
    VARIABLES   { dlswTConnOperTDomain, dlswTConnOperRemoteTAddr }
    DESCRIPTION
       "This trap is sent each time a transport connection
        enters `connected' state."
    ::= 1
 
dlswTrapTConnDown TRAP-TYPE
    ENTERPRISE  dlswMIB-3Com
    VARIABLES   { dlswTConnOperTDomain, dlswTConnOperRemoteTAddr }
    DESCRIPTION
       "This trap is sent each time a transport connection
        enters `disconnected' state."
    ::= 2
 
dlswTrapCircuitUp TRAP-TYPE
    ENTERPRISE  dlswMIB-3Com
    VARIABLES   { dlswCircuitS1Mac, dlswCircuitS1Sap,
                       dlswCircuitS2Mac, dlswCircuitS2Sap }
    DESCRIPTION
       "This trap is sent each time a circuit enters
        `connected' state."
    ::= 3
 
dlswTrapCircuitDown TRAP-TYPE
    ENTERPRISE  dlswMIB-3Com
    VARIABLES   { dlswCircuitS1Mac, dlswCircuitS1Sap,
                        dlswCircuitS2Mac, dlswCircuitS2Sap }
    DESCRIPTION
       "This trap is sent each time a circuit enters
        `disconnected' state."
    ::= 4 
 
 
--
--
--
END
