ODS-MIB DEFINITIONS ::= BEGIN

-- Title:	Optical Data Systems MIB
-- Date:	September 19, 1990
-- By:		Ernie Tascik <ods@utdallas.edu>


          IMPORTS
               NetworkAddress, IpAddress, Counter, Gauge, TimeTicks, enterprises, OBJECT-TYPE
               FROM RFC1155-SMI;

          ods            OBJECT IDENTIFIER ::= { enterprises 50 }

          enc            OBJECT IDENTIFIER ::= { ods 1 }
          enBridge       OBJECT IDENTIFIER ::= { ods 2 }
          tokenRing      OBJECT IDENTIFIER ::= { ods 3 }
          trBridge       OBJECT IDENTIFIER ::= { ods 4 }

          encMib1        OBJECT IDENTIFIER ::= { enc 1 }
          e1Interface    OBJECT IDENTIFIER ::= { encMib1 1 }
          e1AddressGroup OBJECT IDENTIFIER ::= { encMib1 2 }

          encMib2        OBJECT IDENTIFIER ::= { enc 2 }
          encInterfaces  OBJECT IDENTIFIER ::= { encMib2 1 }
          encBox         OBJECT IDENTIFIER ::= { encInterfaces 1 }
          encCards       OBJECT IDENTIFIER ::= { encInterfaces 2 }
          encPorts       OBJECT IDENTIFIER ::= { encInterfaces 3 }
          encAdmin       OBJECT IDENTIFIER ::= { encMib2 2 }

          e1TotalCRC OBJECT-TYPE
               SYNTAX  Counter
               ACCESS  read-only
               STATUS  obsolete
               ::= { e1Interface 1 }

          e1CRCSec OBJECT-TYPE
               SYNTAX  Gauge
               ACCESS  read-write
               STATUS  obsolete
               ::= { e1Interface 2 }

          e1TotalFAE OBJECT-TYPE
               SYNTAX  Counter
               ACCESS  read-only
               STATUS  obsolete
               ::= { e1Interface 3 }

          e1FAESec OBJECT-TYPE
               SYNTAX  Gauge
               ACCESS  read-write
               STATUS  obsolete
               ::= { e1Interface 4 }

          e1PortMask OBJECT-TYPE












               SYNTAX  INTEGER
               ACCESS  read-write
               STATUS  obsolete
               ::= { e1Interface 5 }

          e1Index OBJECT-TYPE
               SYNTAX  INTEGER
               ACCESS  read-write
               STATUS  obsolete
               ::= { e1Interface 6 }

          e1BoxCode OBJECT-TYPE
               SYNTAX  INTEGER
               ACCESS  read-only
               STATUS  obsolete
               ::= { e1Interface 7 }

          e1SystemTime OBJECT-TYPE
               SYNTAX  TimeTicks
               ACCESS  read-only
               STATUS  obsolete
               ::= { e1Interface 8 }

          e1SoftwareVersion OBJECT-TYPE
               SYNTAX  INTEGER
               ACCESS  read-only
               STATUS  obsolete
               ::= { e1Interface 9 }

          e1MgrFlag OBJECT-TYPE
               SYNTAX  INTEGER
               ACCESS  read-write
               STATUS  obsolete
               ::= { e1Interface 10 }

          e1AddrTrapFlag OBJECT-TYPE
               SYNTAX  INTEGER
               ACCESS  read-write
               STATUS  obsolete
               ::= { e1Interface 11 }


          e1AddressTable OBJECT-TYPE
               SYNTAX  E1AddressTable
               ACCESS  read-write
               STATUS  obsolete
               ::= { e1AddressGroup 1 }

          E1AddressTable ::= SEQUENCE {
               e1PhysicalAddress        OCTET STRING,
               e1PortNumber             INTEGER,
               e1FirstPacketTime        TimeTicks,
               e1LastPacketTime         TimeTicks,
               e1Packets                Counter,












               e1Frags                  Counter,
               e1FragsSec               Gauge,
               e1PcktsSec               Gauge
          }

          e1PhysicalAddress OBJECT-TYPE
               SYNTAX  OCTET STRING
               ACCESS  read-only
               STATUS  obsolete
               ::= { e1AddressTable 1 }

          e1PortNumber OBJECT-TYPE
               SYNTAX  INTEGER
               ACCESS  read-only
               STATUS  obsolete
               ::= { e1AddressTable 2 }

          e1FirstPacketTime OBJECT-TYPE
               SYNTAX  TimeTicks
               ACCESS  read-only
               STATUS  obsolete
               ::= { e1AddressTable 3 }

          e1LastPacketTime OBJECT-TYPE
               SYNTAX  TimeTicks
               ACCESS  read-only
               STATUS  obsolete
               ::= { e1AddressTable 4 }

          e1Packets OBJECT-TYPE
               SYNTAX  Counter
               ACCESS  read-only
               STATUS  obsolete
               ::= { e1AddressTable 5 }

          e1Frags OBJECT-TYPE
               SYNTAX  Counter
               ACCESS  read-only
               STATUS  obsolete
               ::= { e1AddressTable 6 }

          e1FragsSec OBJECT-TYPE
               SYNTAX  Gauge
               ACCESS  read-write
               STATUS  obsolete
               ::= { e1AddressTable 7 }

          e1PcktsSec OBJECT-TYPE
               SYNTAX  Gauge
               ACCESS  read-write
               STATUS  obsolete
               ::= { e1AddressTable 8 }















          boxId OBJECT-TYPE
               SYNTAX  INTEGER {
                    ods241(1),     -- 16-port fiber optic card
                    ods251(2),     -- 16-port AUI card
                    ods261(3),     -- 16-port twisted pair card
                    ods243(4),     --  8-port fiber optic card
                    ods263(5),     --  8-port twisted pair card
                    ods290(6)      -- multi-card system
               }
               ACCESS  read-only
               STATUS  mandatory
               ::= { encBox 1 }

          boxDescr OBJECT-TYPE
               SYNTAX  OCTET STRING
               ACCESS  read-only
               STATUS  mandatory
               ::= { encBox 2 }

          boxMode OBJECT-TYPE
               SYNTAX  INTEGER {
                    local(1),
                    network(2)
               }
               ACCESS  read-only
               STATUS  mandatory
               ::= { encBox 3 }

          boxHashSelect OBJECT-TYPE
               SYNTAX  INTEGER
               ACCESS  read-write
               STATUS  mandatory
               ::= { encBox 4 }

          boxPktsThru OBJECT-TYPE
               SYNTAX  Counter
               ACCESS  read-only
               STATUS  mandatory
               ::= { encBox 5 }

          boxOctetsThru OBJECT-TYPE
               SYNTAX  Counter
               ACCESS  read-only
               STATUS  mandatory
               ::= { encBox 6 }

          boxAddrsThru OBJECT-TYPE
               SYNTAX  Counter
               ACCESS  read-only
               STATUS  mandatory
               ::= { encBox 7 }

          boxPktsLost OBJECT-TYPE












               SYNTAX  Counter
               ACCESS  read-only
               STATUS  mandatory
               ::= { encBox 8 }

          boxPktsMissed OBJECT-TYPE
               SYNTAX  Counter
               ACCESS  read-only
               STATUS  mandatory
               ::= { encBox 9 }

          boxCrcs OBJECT-TYPE
               SYNTAX  Counter
               ACCESS  read-only
               STATUS  mandatory
               ::= { encBox 10 }

          boxFaes OBJECT-TYPE
               SYNTAX  Counter
               ACCESS  read-only
               STATUS  mandatory
               ::= { encBox 11 }

          boxFrags OBJECT-TYPE
               SYNTAX  Counter
               ACCESS  read-only
               STATUS  mandatory
               ::= { encBox 12 }

          boxPktThresh OBJECT-TYPE
               SYNTAX  Gauge
               ACCESS  read-write
               STATUS  mandatory
               ::= { encBox 13 }

          boxCrcThresh OBJECT-TYPE
               SYNTAX  Gauge
               ACCESS  read-write
               STATUS  mandatory
               ::= { encBox 14 }

          boxFaeThresh OBJECT-TYPE
               SYNTAX  Gauge
               ACCESS  read-write
               STATUS  mandatory
               ::= { encBox 15 }

          boxFragThresh OBJECT-TYPE
               SYNTAX  Gauge
               ACCESS  read-write
               STATUS  mandatory
               ::= { encBox 16 }

          boxAddressCapacity OBJECT-TYPE












               SYNTAX  INTEGER
               ACCESS  read-only
               STATUS  mandatory
               ::= { encBox 17 }

          boxAddressTable OBJECT-TYPE
               SYNTAX  SEQUENCE OF BoxatEntry
               ACCESS  read-write
               STATUS  mandatory
               ::= { encBox 18 }

          boxatEntry OBJECT-TYPE
               SYNTAX  BoxatEntry
               ACCESS  read-write
               STATUS  mandatory
               ::= { boxAddressTable 1 }

          BoxatEntry ::= SEQUENCE {
               boxatPhysAddr       OCTET STRING,
               boxatOldest         TimeTicks,
               boxatNewest         TimeTicks,
               boxatPkts           Counter,
               boxatOctets         Counter,
               boxatSlot           INTEGER,
               boxatPort           INTEGER
          }

          boxatPhysAddr OBJECT-TYPE
               SYNTAX  OCTET STRING
               ACCESS  read-only
               STATUS  mandatory
               ::= { boxatEntry 1 }

          boxatOldest OBJECT-TYPE
               SYNTAX  TimeTicks
               ACCESS  read-only
               STATUS  mandatory
               ::= { boxatEntry 2 }

          boxatNewest OBJECT-TYPE
               SYNTAX  TimeTicks
               ACCESS  read-only
               STATUS  mandatory
               ::= { boxatEntry 3 }

          boxatPkts OBJECT-TYPE
               SYNTAX  Counter
               ACCESS  read-only
               STATUS  mandatory
               ::= { boxatEntry 4 }

          boxatOctets OBJECT-TYPE
               SYNTAX  Counter
               ACCESS  read-only












               STATUS  mandatory
               ::= { boxatEntry 5 }

          boxatSlot OBJECT-TYPE
               SYNTAX  INTEGER
               ACCESS  read-only
               STATUS  mandatory
               ::= { boxatEntry 6 }

          boxatPort OBJECT-TYPE
               SYNTAX  INTEGER
               ACCESS  read-only
               STATUS  mandatory
               ::= { boxatEntry 7 }



          cardCapacity OBJECT-TYPE
               SYNTAX  INTEGER
               ACCESS  read-only
               STATUS  mandatory
               ::= { encCards 1 }

          cardIOCount OBJECT-TYPE
               SYNTAX  INTEGER
               ACCESS  read-only
               STATUS  mandatory
               ::= { encCards 2 }

          cardTable OBJECT-TYPE
               SYNTAX  SEQUENCE OF CardtEntry
               ACCESS  read-write
               STATUS  mandatory
               ::= { encCards 3 }

          cardtEntry OBJECT-TYPE
               SYNTAX  CardtEntry
               ACCESS  read-write
               STATUS  mandatory
               ::= { cardTable 1 }

          CardtEntry ::= SEQUENCE {
               cardIndex           INTEGER,
               cardId              INTEGER,
               cardDescr           OCTET STRING,
               cardOperStatus      INTEGER,
               cardAdminStatus     INTEGER,
               cardPktsThru        Counter,
               cardOctetsThru      Counter,
               cardAddrsThru       Counter,
               cardCrcs            Counter,
               cardFaes            Counter,
               cardFrags           Counter,
               cardPktThresh       Gauge,












               cardCrcThresh       Gauge,
               cardFaeThresh       Gauge,
               cardFragThresh      Gauge,
               cardPortCount       INTEGER
          }

          cardIndex OBJECT-TYPE
               SYNTAX  INTEGER
               ACCESS  read-only
               STATUS  mandatory
               ::= { cardtEntry 1 }

          cardId OBJECT-TYPE
               SYNTAX  INTEGER
               ACCESS  read-only
               STATUS  mandatory
               ::= { cardtEntry 2 }

          cardDescr OBJECT-TYPE
               SYNTAX  OCTET STRING
               ACCESS  read-only
               STATUS  mandatory
               ::= { cardtEntry 3 }

          cardOperStatus OBJECT-TYPE
               SYNTAX  INTEGER
               ACCESS  read-only
               STATUS  mandatory
               ::= { cardtEntry 4 }

          cardAdminStatus OBJECT-TYPE
               SYNTAX  INTEGER
               ACCESS  read-write
               STATUS  mandatory
               ::= { cardtEntry 5 }

          cardPktsThru OBJECT-TYPE
               SYNTAX  Counter
               ACCESS  read-only
               STATUS  mandatory
               ::= { cardtEntry 6 }

          cardOctetsThru OBJECT-TYPE
               SYNTAX  Counter
               ACCESS  read-only
               STATUS  mandatory
               ::= { cardtEntry 7 }

          cardAddrsThru OBJECT-TYPE
               SYNTAX  Counter
               ACCESS  read-only
               STATUS  mandatory
               ::= { cardtEntry 8 }













          cardCrcs OBJECT-TYPE
               SYNTAX  Counter
               ACCESS  read-only
               STATUS  mandatory
               ::= { cardtEntry 9 }

          cardFaes OBJECT-TYPE
               SYNTAX  Counter
               ACCESS  read-only
               STATUS  mandatory
               ::= { cardtEntry 10 }

          cardFrags OBJECT-TYPE
               SYNTAX  Counter
               ACCESS  read-only
               STATUS  mandatory
               ::= { cardtEntry 11 }

          cardPktThresh OBJECT-TYPE
               SYNTAX  Gauge
               ACCESS  read-only
               STATUS  mandatory
               ::= { cardtEntry 12 }

          cardCrcThresh OBJECT-TYPE
               SYNTAX  Gauge
               ACCESS  read-only
               STATUS  mandatory
               ::= { cardtEntry 13 }

          cardFaeThresh OBJECT-TYPE
               SYNTAX  Gauge
               ACCESS  read-only
               STATUS  mandatory
               ::= { cardtEntry 14 }

          cardFragThresh OBJECT-TYPE
               SYNTAX  Gauge
               ACCESS  read-only
               STATUS  mandatory
               ::= { cardtEntry 15 }

          cardPortCount OBJECT-TYPE
               SYNTAX  INTEGER
               ACCESS  read-only
               STATUS  mandatory
               ::= { cardtEntry 16 }



          portTable OBJECT-TYPE
               SYNTAX  SEQUENCE OF PorttEntry
               ACCESS  read-write
               STATUS  mandatory












               ::= { encPorts 1 }

          porttEntry OBJECT-TYPE
               SYNTAX  PorttEntry
               ACCESS  read-write
               STATUS  mandatory
               ::= { portTable 1 }

          PorttEntry ::= SEQUENCE {
               portSlot            INTEGER,
               portIndex           INTEGER,
               portOperStatus      INTEGER,
               portAdminStatus     INTEGER,
               portPktsThru        Counter,
               portOctetsThru      Counter,
               portAddrsThru       Counter,
               portCrcs            Counter,
               portFaes            Counter,
               portFrags           Counter,
               portPktThresh       Gauge,
               portCrcThresh       Gauge,
               portFaeThresh       Gauge,
               portFragThresh      Gauge
          }

          portSlot OBJECT-TYPE
               SYNTAX  INTEGER
               ACCESS  read-only
               STATUS  mandatory
               ::= { porttEntry 1 }

          portIndex OBJECT-TYPE
               SYNTAX  INTEGER
               ACCESS  read-only
               STATUS  mandatory
               ::= { porttEntry 2 }

          portOperStatus OBJECT-TYPE
               SYNTAX  INTEGER
               ACCESS  read-only
               STATUS  mandatory
               ::= { porttEntry 3 }

          portAdminStatus OBJECT-TYPE
               SYNTAX  INTEGER
               ACCESS  read-write
               STATUS  mandatory
               ::= { porttEntry 4 }

          portPktsThru OBJECT-TYPE
               SYNTAX  Counter
               ACCESS  read-only
               STATUS  mandatory
               ::= { porttEntry 5 }













          portOctetsThru OBJECT-TYPE
               SYNTAX  Counter
               ACCESS  read-only
               STATUS  mandatory
               ::= { porttEntry 6 }

          portAddrsThru OBJECT-TYPE
               SYNTAX  Counter
               ACCESS  read-only
               STATUS  mandatory
               ::= { porttEntry 7 }

          portCrcs OBJECT-TYPE
               SYNTAX  Counter
               ACCESS  read-only
               STATUS  mandatory
               ::= { porttEntry 8 }

          portFaes OBJECT-TYPE
               SYNTAX  Counter
               ACCESS  read-only
               STATUS  mandatory
               ::= { porttEntry 9 }

          portFrags OBJECT-TYPE
               SYNTAX  Counter
               ACCESS  read-only
               STATUS  mandatory
               ::= { porttEntry 10 }

          portPktThresh OBJECT-TYPE
               SYNTAX  Gauge
               ACCESS  read-only
               STATUS  mandatory
               ::= { porttEntry 11 }

          portCrcThresh OBJECT-TYPE
               SYNTAX  Gauge
               ACCESS  read-only
               STATUS  mandatory
               ::= { porttEntry 12 }

          portFaeThresh OBJECT-TYPE
               SYNTAX  Gauge
               ACCESS  read-only
               STATUS  mandatory
               ::= { porttEntry 13 }

          portFragThresh OBJECT-TYPE
               SYNTAX  Gauge
               ACCESS  read-only
               STATUS  mandatory
               ::= { porttEntry 14 }













          portAddressTable OBJECT-TYPE
               SYNTAX  SEQUENCE OF PortatEntry
               ACCESS  read-write
               STATUS  mandatory
               ::= { encPorts 2 }

          portatEntry OBJECT-TYPE
               SYNTAX  PortatEntry
               ACCESS  read-write
               STATUS  mandatory
               ::= { portAddressTable 1 }

          PortatEntry ::= SEQUENCE {
               portatPhysAddr      OCTET STRING,
               portatOldest        TimeTicks,
               portatNewest        TimeTicks,
               portatPkts          Counter,
               portatOctets        Counter,
               portatSlot          INTEGER,
               portatPort          INTEGER
          }

          portatPhysAddr OBJECT-TYPE
               SYNTAX  OCTET STRING
               ACCESS  read-only
               STATUS  mandatory
               ::= { portatEntry 1 }

          portatOldest OBJECT-TYPE
               SYNTAX  TimeTicks
               ACCESS  read-only
               STATUS  mandatory
               ::= { portatEntry 2 }

          portatNewest OBJECT-TYPE
               SYNTAX  TimeTicks
               ACCESS  read-only
               STATUS  mandatory
               ::= { portatEntry 3 }

          portatPkts OBJECT-TYPE
               SYNTAX  Counter
               ACCESS  read-only
               STATUS  mandatory
               ::= { portatEntry 4 }

          portatOctets OBJECT-TYPE
               SYNTAX  Counter
               ACCESS  read-only
               STATUS  mandatory
               ::= { portatEntry 5 }

          portatSlot OBJECT-TYPE












               SYNTAX  INTEGER
               ACCESS  read-only
               STATUS  mandatory
               ::= { portatEntry 6 }

          portatPort OBJECT-TYPE
               SYNTAX  INTEGER
               ACCESS  read-only
               STATUS  mandatory
               ::= { portatEntry 7 }




          adminTime OBJECT-TYPE
               SYNTAX  OCTET STRING
               ACCESS  read-write
               STATUS  mandatory
               ::= { encAdmin 1 }

          adminDate OBJECT-TYPE
               SYNTAX  OCTET STRING
               ACCESS  read-write
               STATUS  mandatory
               ::= { encAdmin 2 }

          adminSerialBaud OBJECT-TYPE
               SYNTAX  INTEGER {
                         b9600(1)
               }
               ACCESS  read-write
               STATUS  mandatory
               ::= { encAdmin 3 }

          adminSerialPerson OBJECT-TYPE
               SYNTAX  INTEGER {
                         vt100(1)
               }
               ACCESS  read-write
               STATUS  mandatory
               ::= { encAdmin 4 }

          adminCommTable OBJECT-TYPE
               SYNTAX  SEQUENCE OF AdctEntry
               ACCESS  read-write
               STATUS  mandatory
               ::= { encAdmin 5 }

          adctEntry OBJECT-TYPE
               SYNTAX  AdctEntry
               ACCESS  read-write
               STATUS  mandatory
               ::= { adminCommTable 1 }













          AdctEntry ::= SEQUENCE {
               ctIndex        INTEGER,
               ctCommStr      OCTET STRING,
               ctPrivelege    INTEGER
          }

          ctIndex OBJECT-TYPE
               SYNTAX  INTEGER
               ACCESS  read-write
               STATUS  mandatory
               ::= { adctEntry 1 }

          ctCommStr OBJECT-TYPE
               SYNTAX  OCTET STRING
               ACCESS  read-write
               STATUS  mandatory
               ::= { adctEntry 2 }

          ctPrivelege OBJECT-TYPE
               SYNTAX  INTEGER
               ACCESS  read-write
               STATUS  mandatory
               ::= { adctEntry 3 }

          adminTrapTable OBJECT-TYPE
               SYNTAX  SEQUENCE OF AdttEntry
               ACCESS  read-write
               STATUS  mandatory
               ::= { encAdmin 6 }

          adttEntry OBJECT-TYPE
               SYNTAX  AdttEntry
               ACCESS  read-write
               STATUS  mandatory
               ::= { adminTrapTable 1 }

          AdttEntry ::= SEQUENCE {
               ttIndex        INTEGER,
               ttCommStr      OCTET STRING,
               ttMgrAddr      IpAddress,
               ttTrapEnBox    INTEGER,
               ttTrapEnCard   INTEGER,
               ttTrapEnPort   INTEGER,
               ttTrapEnAddr   INTEGER
          }

          ttIndex OBJECT-TYPE
               SYNTAX  INTEGER
               ACCESS  read-write
               STATUS  mandatory
               ::= { adttEntry 1 }

          ttCommStr OBJECT-TYPE
               SYNTAX  OCTET STRING












               ACCESS  read-write
               STATUS  mandatory
               ::= { adttEntry 2 }

          ttMgrAddr OBJECT-TYPE
               SYNTAX  IpAddress
               ACCESS  read-write
               STATUS  mandatory
               ::= { adttEntry 3 }

          ttTrapEnBox OBJECT-TYPE
               SYNTAX  INTEGER
               ACCESS  read-write
               STATUS  mandatory
               ::= { adttEntry 4 }

          ttTrapEnCard OBJECT-TYPE
               SYNTAX  INTEGER
               ACCESS  read-write
               STATUS  mandatory
               ::= { adttEntry 5 }

          ttTrapEnPort OBJECT-TYPE
               SYNTAX  INTEGER
               ACCESS  read-write
               STATUS  mandatory
               ::= { adttEntry 6 }

          ttTrapEnAddr OBJECT-TYPE
               SYNTAX  INTEGER
               ACCESS  read-write
               STATUS  mandatory
               ::= { adttEntry 7 }

          END
