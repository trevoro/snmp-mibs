Wellfleet-HWF-MIB DEFINITIONS ::= BEGIN

-- Created by mdl2asn version 3.1
-- Creation date: Wed Aug 30 16:42:27 EDT 1995


    IMPORTS

      OBJECT-TYPE
        FROM RFC-1212
      wfHwFGroup
        FROM Wellfleet-COMMON-MIB;


    wfHwfTable OBJECT-TYPE
        SYNTAX	SEQUENCE OF WfHwfEntry
        ACCESS	not-accessible
        STATUS	mandatory
        DESCRIPTION
                "The following table will contain information about a collection of
                Hardware Filter (HWF) driver records.

                Only one HWF driver may be spawned, by the loader, on a given slot.
                Hence, only the slot number is used as the instance identifier into
                the table."
        ::= { wfHwFGroup 1 }

    wfHwfEntry OBJECT-TYPE
        SYNTAX	WfHwfEntry
        ACCESS	not-accessible
        STATUS	mandatory
        DESCRIPTION
                "Slot number used as instance identifier."
        INDEX	{ wfHwfSlot }
        ::= { wfHwfTable 1 }

    WfHwfEntry ::= SEQUENCE {
    	    wfHwfDelete
    		INTEGER,
    	    wfHwfEnable
    		INTEGER,
    	    wfHwfState
    		INTEGER,
    	    wfHwfSlot
    		INTEGER,
    	    wfHwfAvailableLines
    		INTEGER
        }

    wfHwfDelete OBJECT-TYPE
        SYNTAX	INTEGER {
    		    created(1),
    		    deleted(2)
    		}
        ACCESS	read-write
        STATUS	mandatory
        DESCRIPTION
                "Create/delete parameter."
        DEFVAL	{ created }
        ::= { wfHwfEntry 1 }

    wfHwfEnable OBJECT-TYPE
        SYNTAX	INTEGER {
    		    enabled(1),
    		    disabled(2)
    		}
        ACCESS	read-write
        STATUS	mandatory
        DESCRIPTION
                "Enable/disable parameter."
        DEFVAL	{ enabled }
        ::= { wfHwfEntry 2 }

    wfHwfState OBJECT-TYPE
        SYNTAX	INTEGER {
    		    up(1),
    		    down(2),
    		    init(3),
    		    notpresent(4)
    		}
        ACCESS	read-only
        STATUS	mandatory
        DESCRIPTION
                "Driver state variable."
        DEFVAL	{ notpresent }
        ::= { wfHwfEntry 3 }

    wfHwfSlot OBJECT-TYPE
        SYNTAX	INTEGER(1..14)
        ACCESS	read-only
        STATUS	mandatory
        DESCRIPTION
                "Slot number -- instance ID."
        ::= { wfHwfEntry 4 }

    wfHwfAvailableLines OBJECT-TYPE
        SYNTAX	INTEGER
        ACCESS	read-only
        STATUS	mandatory
        DESCRIPTION
                "Number of available lines on module."
        ::= { wfHwfEntry 5 }

    wfHwfLineTable OBJECT-TYPE
        SYNTAX	SEQUENCE OF WfHwfLineEntry
        ACCESS	not-accessible
        STATUS	mandatory
        DESCRIPTION
                "The following table will contain information about a collection of
                Hardware Filter (HWF) line records."
        ::= { wfHwFGroup 2 }

    wfHwfLineEntry OBJECT-TYPE
        SYNTAX	WfHwfLineEntry
        ACCESS	not-accessible
        STATUS	mandatory
        DESCRIPTION
                "Slot number and line number used as instance identifier."
        INDEX	{ wfHwfLineSlot,
    		  wfHwfLineNumber }
        ::= { wfHwfLineTable 1 }

    WfHwfLineEntry ::= SEQUENCE {
    	    wfHwfLineState
    		INTEGER,
    	    wfHwfLineSlot
    		INTEGER,
    	    wfHwfLineNumber
    		INTEGER,
    	    wfHwfLineCct
    		INTEGER,
    	    wfHwfLineCapableMaxTblSize
    		INTEGER,
    	    wfHwfLineCurrentTblSize
    		INTEGER,
    	    wfHwfLineCurrentUsedEntries
    		INTEGER,
    	    wfHwfLineDroppedFrames
    		INTEGER
        }

    wfHwfLineState OBJECT-TYPE
        SYNTAX	INTEGER {
    		    operational(1),
    		    disabled(2),
    		    full(3)
    		}
        ACCESS	read-only
        STATUS	mandatory
        DESCRIPTION
                "State of filtering hardware on a per line basis."
        DEFVAL	{ disabled }
        ::= { wfHwfLineEntry 1 }

    wfHwfLineSlot OBJECT-TYPE
        SYNTAX	INTEGER
        ACCESS	read-only
        STATUS	mandatory
        DESCRIPTION
                "Slot number -- instance ID."
        ::= { wfHwfLineEntry 2 }

    wfHwfLineNumber OBJECT-TYPE
        SYNTAX	INTEGER {
    		    one(1),
    		    two(2),
    		    three(3),
    		    four(4),
    		    five(5)
    		}
        ACCESS	read-only
        STATUS	mandatory
        DESCRIPTION
                "Line number -- instance ID."
        ::= { wfHwfLineEntry 3 }

    wfHwfLineCct OBJECT-TYPE
        SYNTAX	INTEGER
        ACCESS	read-only
        STATUS	mandatory
        DESCRIPTION
                "Circuit number associated with a line."
        ::= { wfHwfLineEntry 4 }

    wfHwfLineCapableMaxTblSize OBJECT-TYPE
        SYNTAX	INTEGER
        ACCESS	read-only
        STATUS	mandatory
        DESCRIPTION
                "This attribute specifies the maximum number of table entries
                capable of being used by a line based upon actual hardware
                filter devices present and available."
        ::= { wfHwfLineEntry 5 }

    wfHwfLineCurrentTblSize OBJECT-TYPE
        SYNTAX	INTEGER
        ACCESS	read-only
        STATUS	mandatory
        DESCRIPTION
                "Current capacity of the hardware filter table. Hardware filter
                table resources are dynamically allocated (in increments of 256)
                on an as-needed basis up to the available table size."
        ::= { wfHwfLineEntry 6 }

    wfHwfLineCurrentUsedEntries OBJECT-TYPE
        SYNTAX	INTEGER
        ACCESS	read-only
        STATUS	mandatory
        DESCRIPTION
                "Number of hardware filter table entries used."
        ::= { wfHwfLineEntry 7 }

    wfHwfLineDroppedFrames OBJECT-TYPE
        SYNTAX	INTEGER
        ACCESS	read-only
        STATUS	mandatory
        DESCRIPTION
                "Number of frames dropped because of hardware filter match."
        ::= { wfHwfLineEntry 8 }

    END  -- Wellfleet-HWF-MIB
