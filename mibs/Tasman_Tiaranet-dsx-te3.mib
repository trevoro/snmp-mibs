-- *********************************************************************
-- Copyright (c) 1998-2005 Tiara Networks Inc.
-- All rights reserved.
--
-- April,1st 1998, kumar 
-- 
--  MIB Tree Overview:
-- 
--tiaraMgmt
--  |_dsxMIB
--     |_dsxT3E3MIB
--         |_dsxT3E3IfGroup
--         |   |_dsxT3E3IfConfigGroup
--         |   |   |_dsxT3E3IfConfigLineTable
--         |   |   |_dsxT3E3IfConfigMdlTable
--         |   |   |_dsxT3E3IfAlarmConfigGroup
--         |   |   |   |_dsxT3E3IfAlarmThresholdConfigTable {te3IfIndex, conigIndex}
--         |   |   |_dsxT3E3IfTestConfigTable
--         |   |_dsxT3E3IfStatusGroup
--         |   |   |_dsxT3E3IfStatusTable
--         |   |   |_dsxT3E3IfAlarmStatusTable
--         |   |   |_dsxT3E3IfTestStatusTable
--         |   |   |_dsxT3E3IfLastTestResultTable
--         |   |_dsxT3E3IfStatsGroup
--         |   |   |_dsxT3E3IfArchiveStatsValidIntervalsTable
--         |   |   |_dsxT3E3IfErrorEventStatsTable
--         |   |   |_dsxT3E3IfAnsiStatsGroup
--         |   |   |   |_dsxT3E3IfAnsiCurrentStatsTable
--         |   |   |   |_dsxT3E3IfAnsiTotalStatsTable
--         |   |   |   |_dsxT3E3IfAnsiArchiveIntervalStatsTable {te3IfIndex, interval number }
--         |   |   |_dsxT3E3IfIetfStatsGroup   
--         |   |   |   |_dsxT3E3IfIetfCurrentStatsTable 
--         |   |   |   |_dsxT3E3IfIetfTotalStatsTable   
--         |   |   |   |_dsxT3E3IfIetfArchiveStatsTable { te3IfIndex,interval number }
--         |   |   |_dsxT3E3IfUserStatsGroup   
--         |   |   |   |_dsxT3E3IfUserCurrentStatsTable 
--         |   |   |   |_dsxT3E3IfUserTotalStatsTable { te3IfIndex, day }
--         |   |   |   |_dsxT3E3IfUserLifetimeStatsTable
--         |   |   |   |_dsxT3E3IfUserArchiveStatsTable { te3IfIndex,interval number }
--      
-- ***************************************************************************
TIARA-NETWORKS-DSX-TE3-MIB 

DEFINITIONS ::= BEGIN


IMPORTS
    MODULE-IDENTITY, 
    OBJECT-TYPE, 
    Unsigned32
        FROM SNMPv2-SMI
    LEDState ,
    dsxT3E3IfGroup
        FROM TIARA-NETWORKS-DSX-TC-MIB
    TruthValue
        FROM SNMPv2-TC;
     
dsxT3E3MIB MODULE-IDENTITY
    LAST-UPDATED "0008180000Z"
    ORGANIZATION "Tiara Networks Inc."
    CONTACT-INFO
                "       Tiara Networks
                        Customer Support

                 		525 Race Street, Suite 100,
                        San Jose, CA 95126
                        USA

                   	Tel: +1 408-216-4700
                   	Fax: +1 408-216-4701

                		Email: support@tiaranetworks.com"

    DESCRIPTION
            "Interface MIB definitions for Tiara T3/E3 
		interface modules."
    REVISION "0008180000Z"
    DESCRIPTION
            "Initial revision."
    ::= { dsxT3E3IfGroup 1 }
    
-- TE3 interface group. 
dsxT3E3Traps  OBJECT IDENTIFIER ::= { dsxT3E3IfGroup 2}

dsxT3E3TrapVariables OBJECT IDENTIFIER  ::= { dsxT3E3Traps 1}

-- TE3 Interface sub-group definitions.
 
dsxT3E3IfConfigGroup     OBJECT IDENTIFIER ::= { dsxT3E3MIB 1 }
dsxT3E3IfStatusGroup     OBJECT IDENTIFIER ::= { dsxT3E3MIB 2 }
dsxT3E3IfStatsGroup      OBJECT IDENTIFIER ::= { dsxT3E3MIB 3 }

-- DSX TE3 interface configuration group definitions.

-- DSX TE3 interface line configuration table.

dsxT3E3IfConfigLineTable OBJECT-TYPE
    SYNTAX      		 SEQUENCE OF DsxT3E3IfConfigLineEntry
    MAX-ACCESS  		 not-accessible
    STATUS      		 current
    DESCRIPTION
     	"A list of T3/E3 interfaces currently configured."
    ::= { dsxT3E3IfConfigGroup 1 }

dsxT3E3IfConfigLineEntry OBJECT-TYPE
    SYNTAX      		 DsxT3E3IfConfigLineEntry
    MAX-ACCESS  		 not-accessible
    STATUS      		 current
    DESCRIPTION
     	"An entry containing configuration information for each 
	currently active T3/E3 interface."
    INDEX   		 { dsxT3E3IfIndex }
    ::= { dsxT3E3IfConfigLineTable 1 }

DsxT3E3IfConfigLineEntry ::=
    SEQUENCE {
      dsxT3E3IfIndex                        INTEGER,
      dsxT3E3IfConfigLineType               INTEGER,
      dsxT3E3IfConfigLineCode               INTEGER,
      dsxT3E3IfConfigCableLength            INTEGER,
      dsxT3E3IfConfigTransmitClock          INTEGER,
	dsxT3E3IfConfigDS3ScramblingMode      INTEGER,
	dsxT3E3IfConfigDS3ScramblingEnable    TruthValue
    }
dsxT3E3IfIndex 	OBJECT-TYPE
    SYNTAX      	INTEGER
    MAX-ACCESS  	not-accessible
    STATUS      	current
    DESCRIPTION
    	"An integer value that is an index to the entries of
      ifTable (MIB-II) whose interface type is ds3." 
    ::= { dsxT3E3IfConfigLineEntry 1 }
    
dsxT3E3IfConfigLineType OBJECT-TYPE
    SYNTAX      	INTEGER 
                	{
                    linetype-m13        (2),
                    linetype-cbitparity (4)
                	}
    MAX-ACCESS  	read-write
    STATUS      	current
    DESCRIPTION
    	"This variable indicates the variety of T3/E3 
	C-bit or E3 application implementing this 
	interface. The type of interface affects the 
	interpretation of the usage and error 
	statistics. The rate of T3/E3 is 44.736 Mbps
      and E3 is 34.368 Mbps. 
               
	The values, in sequence, describe:
		linetype-m13            ANSI T1.107-1988
      linetype-cbitparity     ANSI T1.107a-1990"

   
    ::= { dsxT3E3IfConfigLineEntry 2 }
    
dsxT3E3IfConfigLineCode OBJECT-TYPE
    SYNTAX      	INTEGER 
                	{
                    linecode-b3zs (2),
                    linecode-hdb3 (3)
                	}
    MAX-ACCESS  	read-only
    STATUS      	current
    DESCRIPTION
      "This variable describes the variety of zero 
	code suppression used on this interface, which 
	in turn affects a number of its characteristics.

      linecode-B3ZS and linecode-HDB3 refer to the use 
	of specified patterns of normal bits and bipolar 
	violations that are used to replace sequences 
	of zero bits of a specified length."
    ::= { dsxT3E3IfConfigLineEntry 3 }

dsxT3E3IfConfigCableLength 	OBJECT-TYPE
    SYNTAX      	INTEGER 
                	{
                    cable-length-0-to-225  (1),
                    cable-length-225-to-450(2)
                	}
    MAX-ACCESS  	read-write
    STATUS      	current
    DESCRIPTION
	"The length of the T3/E3 line in feet. This
      object provides information for line build out
      circuitry if it exists and can use this object to
      adjust the line build out."
    ::= { dsxT3E3IfConfigLineEntry 4 }
    
dsxT3E3IfConfigTransmitClock 	OBJECT-TYPE
    SYNTAX      	INTEGER
                	{
                    timing-line     (1),
                    timing-internal (2)
                	}
    MAX-ACCESS  	read-write
    STATUS      	current
    DESCRIPTION
     	"The source of transmit clock. It is derived  
	from the recovered receive clock of another 
      T3/E3 interface."
    ::= { dsxT3E3IfConfigLineEntry 5 } 

dsxT3E3IfConfigDS3ScramblingMode OBJECT-TYPE
    SYNTAX      INTEGER
                {
                  mode-0  (1),
                  mode-1  (2),
		      mode-2  (3)
                }
    MAX-ACCESS  read-write
    STATUS      current
    DESCRIPTION
     	"Scrambling mode."
    ::= { dsxT3E3IfConfigLineEntry 6 } 

dsxT3E3IfConfigDS3ScramblingEnable 	OBJECT-TYPE
    SYNTAX      	TruthValue
    MAX-ACCESS  	read-write
    STATUS      	current
    DESCRIPTION
     	"To enable or disable scrambling. This is applicable
	only to clear channel TE3."
    ::= { dsxT3E3IfConfigLineEntry 7 } 

-- DSX TE3 interface MDL configuration table.

-- This table is applicable only for those interfaces whose
-- LineType is cbitparity.


dsxT3E3IfConfigMdlTable OBJECT-TYPE
    SYNTAX      		SEQUENCE OF DsxT3E3IfConfigMdlEntry
    MAX-ACCESS  		not-accessible
    STATUS      		current
    DESCRIPTION
     	"A list of T3/E3 interfaces currently configured."
    ::= { dsxT3E3IfConfigGroup 2 }

dsxT3E3IfConfigMdlEntry OBJECT-TYPE
    SYNTAX      		DsxT3E3IfConfigMdlEntry
    MAX-ACCESS  		not-accessible
    STATUS     		current
    DESCRIPTION
    	"An entry containing configuration for each currently
	active T3/E3 interface."
    AUGMENTS { dsxT3E3IfConfigLineEntry }
    ::= { dsxT3E3IfConfigMdlTable 1 }

DsxT3E3IfConfigMdlEntry ::=
    SEQUENCE {
        dsxT3E3IfConfigMdlEIC                OCTET STRING,
        dsxT3E3IfConfigMdlLIC                OCTET STRING,
        dsxT3E3IfConfigMdlFIC                OCTET STRING,
        dsxT3E3IfConfigMdlUIC                OCTET STRING,
        dsxT3E3IfConfigMdlPFI                OCTET STRING,
        dsxT3E3IfConfigMdlPort               OCTET STRING,
        dsxT3E3IfConfigMdlGenerator          OCTET STRING
    }

dsxT3E3IfConfigMdlEIC 	OBJECT-TYPE
    SYNTAX      		OCTET STRING (SIZE(10))
    MAX-ACCESS  		read-write
    STATUS      		current
    DESCRIPTION 
	"The equipment identification code (up to 10
	characters) describes a specific piece of
	equipment."
    ::= { dsxT3E3IfConfigMdlEntry 1 }

dsxT3E3IfConfigMdlLIC 	OBJECT-TYPE
    SYNTAX      		OCTET STRING (SIZE(11))
    MAX-ACCESS  		read-write
    STATUS      		current
    DESCRIPTION 
	"The location identification code (up to 11
	characters) describes a specific location."
    ::= { dsxT3E3IfConfigMdlEntry 2 }

dsxT3E3IfConfigMdlFIC 	OBJECT-TYPE
    SYNTAX      		OCTET STRING (SIZE(10))
    MAX-ACCESS  		read-write
    STATUS      		current
    DESCRIPTION 
	"The frame identification code (up to 10
	charaters) identifies where the equipment 
	is located within a building at a given location."
    ::= { dsxT3E3IfConfigMdlEntry 3 }

dsxT3E3IfConfigMdlUIC 	OBJECT-TYPE
    SYNTAX      		OCTET STRING (SIZE(6))
    MAX-ACCESS  		read-write
    STATUS      		current
    DESCRIPTION 
	"A code (up to 6 characters) that identifies the
	equipment location within a bay."
    ::= { dsxT3E3IfConfigMdlEntry 4 }

dsxT3E3IfConfigMdlPFI 	OBJECT-TYPE
    SYNTAX      		OCTET STRING (SIZE(38))
    MAX-ACCESS  		read-write
    STATUS     		 current
    DESCRIPTION 
	"The facility identification code (up to 38
	characters) identifies a specific T3/E3 path."
    ::= { dsxT3E3IfConfigMdlEntry 5 }

dsxT3E3IfConfigMdlPort 	OBJECT-TYPE
    SYNTAX      		OCTET STRING (SIZE(38))
    MAX-ACCESS  		read-write
    STATUS      		current
    DESCRIPTION 
	"The Port number is the designation of equipment,
	port that initiates the idle signal."
    ::= { dsxT3E3IfConfigMdlEntry 6 }

dsxT3E3IfConfigMdlGenerator 	OBJECT-TYPE
    SYNTAX      			OCTET STRING (SIZE(38))
    MAX-ACCESS  			read-write
    STATUS      			current
    DESCRIPTION 
	"Gen No. is the number of the signal generator 
	that initiates the test signal."
    ::= { dsxT3E3IfConfigMdlEntry 7 }


-- DSX TE3 interface alarm configuration table.

dsxT3E3IfAlarmConfigGroup OBJECT IDENTIFIER ::= {dsxT3E3IfConfigGroup 3 }

-- DSX TE3 alarm threshold congiguration table.
-- In order to configure a alarm threshold, all the columns 
-- are mandatory and failure to proide all the columns will
-- result in badValue error.


dsxT3E3IfAlarmThresholdConfigTable 	OBJECT-TYPE
    SYNTAX      		SEQUENCE OF DsxT3E3IfAlarmThresholdConfigEntry
    MAX-ACCESS  		not-accessible
    STATUS      		current
    DESCRIPTION
     	"A list of TE3 interface alarm threshold configuration."
    ::= { dsxT3E3IfAlarmConfigGroup 1 }

dsxT3E3IfAlarmThresholdConfigEntry 	OBJECT-TYPE
    SYNTAX      		DsxT3E3IfAlarmThresholdConfigEntry
    MAX-ACCESS  		not-accessible
    STATUS      		current
    DESCRIPTION
    	"An entry containing alarm configuration information 
	for each currently active TE3 interface."
    INDEX 			{ dsxT3E3IfIndex, dsxT3E3IfAlarmThresholdConfigIndex }
    ::= { dsxT3E3IfAlarmThresholdConfigTable 1 }

DsxT3E3IfAlarmThresholdConfigEntry ::=
    SEQUENCE {
        dsxT3E3IfAlarmThresholdConfigIndex             INTEGER,
        dsxT3E3IfAlarmThresholdConfigObject            INTEGER,
        dsxT3E3IfAlarmThresholdConfigSamplingInterval  INTEGER,
        dsxT3E3IfAlarmThresholdConfigSampleType        INTEGER,
        dsxT3E3IfAlarmThresholdConfigStartupType       TruthValue,
        dsxT3E3IfAlarmThresholdConfigRisingThreshold   INTEGER,
        dsxT3E3IfAlarmThresholdConfigFallingThreshold  INTEGER
    }

dsxT3E3IfAlarmThresholdConfigIndex 	OBJECT-TYPE
    SYNTAX      				INTEGER
    MAX-ACCESS  				not-accessible
    STATUS      				current
    DESCRIPTION
   	"Index value of the threshold configuration."
    ::= { dsxT3E3IfAlarmThresholdConfigEntry 1 }

dsxT3E3IfAlarmThresholdConfigObject OBJECT-TYPE
    SYNTAX      	INTEGER
               	{
                 	  te3-object-lcv  (1),
                 	  te3-object-fbe  (2),
                 	  te3-object-pbe  (3),
                    te3-object-cpbe (4),
                    te3-object-febe (5),
                    te3-object-exz  (6),
                    te3-object-cofa (7)
                	}
    MAX-ACCESS  	read-write
    STATUS      	current
    DESCRIPTION
  	"Configurable variables for the threshold alarm configuration."
    ::= { dsxT3E3IfAlarmThresholdConfigEntry 2 }

dsxT3E3IfAlarmThresholdConfigSamplingInterval	OBJECT-TYPE
    SYNTAX      	INTEGER (1..65535)
    MAX-ACCESS  	read-write
    STATUS      	current
    DESCRIPTION
 	 "Sampling interval for the threshold alarm."
    ::= { dsxT3E3IfAlarmThresholdConfigEntry 3 }

dsxT3E3IfAlarmThresholdConfigSampleType OBJECT-TYPE
    SYNTAX      	INTEGER
                	{
                    sample-absolute  (1),
                    sample-delta   (2)
                	}
    MAX-ACCESS  	read-write
    STATUS      	current
    DESCRIPTION
    	"Sampling type for the threshold alarm."
    ::= { dsxT3E3IfAlarmThresholdConfigEntry 4 }

dsxT3E3IfAlarmThresholdConfigStartupType OBJECT-TYPE
    SYNTAX      	TruthValue
    MAX-ACCESS  	read-write
    STATUS     	 current
    DESCRIPTION
     	"Startup Type for the threashold alarm."
    ::= { dsxT3E3IfAlarmThresholdConfigEntry 5 }

dsxT3E3IfAlarmThresholdConfigRisingThreshold OBJECT-TYPE
    SYNTAX      	INTEGER
    MAX-ACCESS  	read-write
    STATUS      	current
    DESCRIPTION
   	"Rising threshold."
    ::= { dsxT3E3IfAlarmThresholdConfigEntry 6 }

dsxT3E3IfAlarmThresholdConfigFallingThreshold OBJECT-TYPE
    SYNTAX      	INTEGER
    MAX-ACCESS  	read-write
    STATUS      	current
    DESCRIPTION
   	"Falling threshold."
    ::= { dsxT3E3IfAlarmThresholdConfigEntry 7 }

-- DSX TE3 interface Test configuration table.

dsxT3E3IfTestConfigTable 	OBJECT-TYPE
    SYNTAX      			SEQUENCE OF DsxT3E3IfTestConfigEntry
    MAX-ACCESS  			not-accessible
    STATUS      			current
    DESCRIPTION
     	"A list of TE3 interface test configuration."
    ::= { dsxT3E3IfConfigGroup 4 }

dsxT3E3IfTestConfigEntry 	OBJECT-TYPE
    SYNTAX      			DsxT3E3IfTestConfigEntry
    MAX-ACCESS  			not-accessible
    STATUS      			current
    DESCRIPTION
    	"An entry containing test configuration for each currently 
       active TE3 interface."
    AUGMENTS 			{ dsxT3E3IfConfigLineEntry }
    ::= { dsxT3E3IfTestConfigTable 1 }

DsxT3E3IfTestConfigEntry ::=
    SEQUENCE {
        dsxT3E3IfTestConfigType       INTEGER,
        dsxT3E3IfTestConfigLoopCode   INTEGER
    }

dsxT3E3IfTestConfigType OBJECT-TYPE
    SYNTAX       INTEGER
                 {
                    no-test            (1),
                    line-loopback-test (3),
                    remote-lpup-test   (8),
                 	  remote-lpdn-test   (9)
                	}
    MAX-ACCESS  	read-write
    STATUS      	current
    DESCRIPTION
   	"Test type for the TE3 interface. Only TestType is 
	mandatory to perform no-test, payload-loopback-test, 
	or line-loopback-test.
             
	ConfigLoopCode is mandatory to perform 
	remote-lpup-test and remote-lpdn-test."
    ::= { dsxT3E3IfTestConfigEntry 1 }
    
dsxT3E3IfTestConfigLoopCode 	OBJECT-TYPE
    SYNTAX      	INTEGER
                	{
                    loopcode-none    (1),
                    loopcode-feac    (2)
                	}
    MAX-ACCESS  	read-write
    STATUS      	current
    DESCRIPTION
   	"Loopback code."
    ::= { dsxT3E3IfTestConfigEntry 2 }
    
    
-- DSX TE3 interface status group definitions.

dsxT3E3IfStatusTable 	OBJECT-TYPE
    SYNTAX      	SEQUENCE OF DsxT3E3IfStatusEntry
    MAX-ACCESS  	not-accessible
    STATUS      	current
    DESCRIPTION
   	"A list of TE3 interface status entries."
    ::= { dsxT3E3IfStatusGroup 1 }

dsxT3E3IfStatusEntry 	OBJECT-TYPE
    SYNTAX      		DsxT3E3IfStatusEntry
    MAX-ACCESS  		not-accessible
    STATUS      		current
    DESCRIPTION
     	"An entry containing the status entry for each 
	currently active TE3 interface."
    AUGMENTS 		{ dsxT3E3IfConfigLineEntry }
    ::= { dsxT3E3IfStatusTable 1 }

DsxT3E3IfStatusEntry ::=
    SEQUENCE {
        dsxT3E3IfStatusLineStatus     BITS,
        dsxT3E3IfStatusTransmitClock  INTEGER,
        dsxT3E3IfStatusTestLED        LEDState,
        dsxT3E3IfStatusErrorLED       LEDState,
        dsxT3E3IfStatusAisLED         LEDState,
        dsxT3E3IfStatusSignalLED      LEDState,
        dsxT3E3IfStatusFrameLED       LEDState,
        dsxT3E3IfStatusYellowLED      LEDState
    }

dsxT3E3IfStatusLineStatus OBJECT-TYPE
    SYNTAX      BITS
                {
                    reserved           (0),
                    reserved1          (1),
                    reserved2          (2),
                    reserved3          (3),
                    reserved4          (4),
                    reserved5          (5),
                    reserved6          (6),
                    reserved7          (7),
                    sendPattern        (8),
                    sendTE3Code        (9),
                    sendResetCode      (10),
                    sendPayloadCode    (11),
                    sendLineCode       (12),
                    reserved8          (13),
                    febeStatus         (14),
                    pdeStatus          (15),
                    lorcStatus         (16),
                    reserved9          (17),
                    reserved10         (18),
                    rfebeStatus        (19),
                    risStatus          (20),
                    rexzStatus         (21),
                    reserved11         (22),
                    rcvTestCode        (23),
                    loopbackStatus     (24),
                    rlosStatus         (25),
                    rlofStatus         (26),
                    taisStatus         (27),
                    raisStatus         (28),
                    traiStatus         (29),
                    rraiStatus         (30),
                    no-alarm           (31)
                }
    MAX-ACCESS  read-only
    STATUS      current
    DESCRIPTION
    	"Line  Status of the T3/E3 interface.
		sendPattern     - TRUE if the line transmiting bit pattern,
		sendTE3Code     - sending T3/E3 code,
		sendResetCode   - transmits Reset Code if it is TRUE,
		sendPayloadcode - transmits the payload code,
		sendLinecode    - transmitts the line code,
		febe	-  Far End Block Error,
		pde   -  pulse Density code transmission,
		lorc  -  loss of recieve clock,
		rfebe -  recieve far end block error,
		ris   -  recieve Idle signal,
		rexz	-  recieve exessive zeros,
		rcvTestCode - recieve test code,
		loopback    - loopback status ,
		rlos		- recieve loss of signal,
		rlof		- recieve loss of frame,
		tais		- transmit alarm indication signal,
		rais		- recieve alarm indication signal,
		trai		- transmit remote alarm indication,
		rrai		- recieve remote alarm indication,
		"
    ::= { dsxT3E3IfStatusEntry 1 }

dsxT3E3IfStatusTransmitClock 	OBJECT-TYPE
    SYNTAX      	INTEGER
                	{
                    timing-line     (1),
                    timing-internal (2)
                	}
    MAX-ACCESS  	read-only 
    STATUS      	current
    DESCRIPTION
 	"The source of tranmit clock.
   
      'timing-line' indicates that the recovered 
      receive clock is used as the transmit clock.

      'timing-internal' indicates that a local clock
      source is used."

    ::= { dsxT3E3IfStatusEntry 2 }
    
dsxT3E3IfStatusTestLED 	OBJECT-TYPE
    SYNTAX      		LEDState
    MAX-ACCESS  		read-only
    STATUS      		current
    DESCRIPTION
    	"Status of TEST LED. "
    ::= { dsxT3E3IfStatusEntry 3 }
    

dsxT3E3IfStatusErrorLED 	OBJECT-TYPE
    SYNTAX      			LEDState
    MAX-ACCESS  			read-only
    STATUS      			current
    DESCRIPTION
    	"Status of the Error LED. "
    ::= { dsxT3E3IfStatusEntry 4 }
    
dsxT3E3IfStatusAisLED 	OBJECT-TYPE
    SYNTAX      		LEDState
    MAX-ACCESS  		read-only
    STATUS      		current
    DESCRIPTION
	"Status of AIS LED. "
    ::= { dsxT3E3IfStatusEntry 5 }
    
dsxT3E3IfStatusSignalLED 	OBJECT-TYPE
    SYNTAX      			LEDState
    MAX-ACCESS  			read-only
    STATUS      			current
    DESCRIPTION
    	"Status of the Signal LED. "
    ::= { dsxT3E3IfStatusEntry 6 }
    
dsxT3E3IfStatusFrameLED 	OBJECT-TYPE
    SYNTAX      			LEDState
    MAX-ACCESS  			read-only
    STATUS      			current
    DESCRIPTION
  	"Status of the Frame LED. "
    ::= { dsxT3E3IfStatusEntry 7 }
    
dsxT3E3IfStatusYellowLED 	OBJECT-TYPE
    SYNTAX      			LEDState
    MAX-ACCESS  			read-only
    STATUS      			current
    DESCRIPTION
   	"Status of the Yellow Alarm LED. "
    ::= { dsxT3E3IfStatusEntry 8 }
    
-- DSX T3/E3 interface alarm status group definitions.

dsxT3E3IfAlarmStatusTable 	OBJECT-TYPE
    SYNTAX      			SEQUENCE OF DsxT3E3IfAlarmStatusEntry
    MAX-ACCESS  			not-accessible
    STATUS      			current
    DESCRIPTION
   	"A list of T3/E3 interface status entries."
    ::= { dsxT3E3IfStatusGroup 2 }

dsxT3E3IfAlarmStatusEntry 	OBJECT-TYPE
    SYNTAX      			DsxT3E3IfAlarmStatusEntry
    MAX-ACCESS  			not-accessible
    STATUS      			current
    DESCRIPTION
   	"An entry containing the status entry for each 
	currently active T3/E3 interface."
    AUGMENTS { dsxT3E3IfConfigLineEntry }
    ::= { dsxT3E3IfAlarmStatusTable 1 }

DsxT3E3IfAlarmStatusEntry ::=
    SEQUENCE {
        dsxT3E3IfAlarmStatusAlarmStatus       BITS,
        dsxT3E3IfAlarmStatusThresholdStatus   BITS
    }

dsxT3E3IfAlarmStatusAlarmStatus OBJECT-TYPE
    SYNTAX      			BITS
                			{
                    		  noAlarm             (0),
                    		  rraiAlarm           (1),
                    		  traiAlarm           (2),
                    		  taisAlarm           (3),
                    		  rlofAlarm           (4),
                    		  rlosAlarm           (5),
                    		  loopbackStateAlarm  (6),
                    		  rcvTestCode         (7),
                    		  rbluAlarm           (8),
                    		  risAlarm            (9),
                    		  rexzAlarm           (10),
                    		  rfbeAlarm           (11),
                    		  rpeAlarm            (12),
                    		  rcpeAlarm           (13),
                    		  lorcAlarm           (14),
                    		  tpdeAlarm           (15),
                    		  tfebeAlarm          (16)
                			}
    MAX-ACCESS  			read-only
    STATUS      			current
    DESCRIPTION
    	"Current status of all the T3/E3 interface alarms.
			RRAI 		- Recieve Remote Alarm Indication,
			TRAI		- Transmit Remote Alarm Indication,
			TAIS		- Transmit Alarm Indication Siganl, 
			RLOF		- Recieve Loss Of Frame,
			RLOS		- Recieve Loss Of Sync,
			Loopback	- Status of Loop back,
			rcvTestCode - Recieve Test Code,
			rblu		- Recieve Blue Alarm,
			RIS			- Recieve Idle Signal,
			REXZ		- Recieve Excessive Zeros,
			RFBE		- Recieve Frame Bit Error,
			RPE			- Recieve Parity Error,
			RCPE		- Recieve C-Parity Error,
			LORC		- Loss Of Recive Clock (LORC),
			TPDE		- transmit pulse density,
			RAIS		- Recieve Alarm Indication Signal,
			TFEBE		- Transmit Far End Block Alarm."
    ::= { dsxT3E3IfAlarmStatusEntry 1 }

dsxT3E3IfAlarmStatusThresholdStatus OBJECT-TYPE
    SYNTAX      		BITS
                		{
                    	  threshold1  (0),
                    	  threshold2  (1),
                          threshold3  (2),
                    	  threshold4  (3),
                    	  threshold5  (4),
                    	  threshold6  (5),
                    	  threshold7  (6),
                    	  threshold8  (7),
                    	  threshold9  (8),
                    	  threshold10 (9)
               		 }
    MAX-ACCESS  read-only
    STATUS      current
    DESCRIPTION
   	"Current status of all the configured threshold alarms."
    ::= { dsxT3E3IfAlarmStatusEntry 2 }

-- DSX T3/E3 interface test status group definitions.

dsxT3E3IfTestStatusTable	OBJECT-TYPE
    SYNTAX      			SEQUENCE OF DsxT3E3IfTestStatusEntry
    MAX-ACCESS  			not-accessible
    STATUS      			current
    DESCRIPTION
	"A list of T3/E3 interface test status entries."
    ::= { dsxT3E3IfStatusGroup 3 }

dsxT3E3IfTestStatusEntry 	OBJECT-TYPE
    SYNTAX      			DsxT3E3IfTestStatusEntry
    MAX-ACCESS  			not-accessible
    STATUS      			current
    DESCRIPTION
    	"An entry containing the status entry for each 
	currently active T3/E3 interface."
    AUGMENTS { dsxT3E3IfConfigLineEntry }
    ::= { dsxT3E3IfTestStatusTable 1 }

DsxT3E3IfTestStatusEntry ::=
    SEQUENCE {
        dsxT3E3IfTestStatusTestType           INTEGER,
        dsxT3E3IfTestStatusTestState          INTEGER,
        dsxT3E3IfTestStatusLoopCode           INTEGER
    }
    
dsxT3E3IfTestStatusTestType 	OBJECT-TYPE
    SYNTAX      	INTEGER 
                	{
                    no-test        (1),
                    line-loopback  (3),
                    other-loopback (4),
                    remote-lpup    (6),
                    remote-lpdn    (7)
                   }
    MAX-ACCESS  	read-only
    STATUS      	current
    DESCRIPTION
   	"The test type."
    ::= { dsxT3E3IfTestStatusEntry 1 }

dsxT3E3IfTestStatusTestState 	OBJECT-TYPE
    SYNTAX      	INTEGER
                	{
                    state-idle       (1),
                   state-searching   (2),
                   state-locked      (3),
                   state-relocked    (4),
                   state-in-progress (5),
                   state-passed      (6),
                   state-failed      (7)
                	}
    MAX-ACCESS  	read-only
    STATUS      	current
    DESCRIPTION
    	"State of the test invoked."
    ::= { dsxT3E3IfTestStatusEntry 2 }

dsxT3E3IfTestStatusLoopCode 	OBJECT-TYPE
    SYNTAX      	INTEGER
                	{
                   loopcode-feac   (1)
               	}
    MAX-ACCESS  	read-only
    STATUS      	current
    DESCRIPTION
    	"Line code for loop back test."
    ::= { dsxT3E3IfTestStatusEntry 3 }
    
-- T3/E3 last test result table.

dsxT3E3IfLastTestResultTable 	OBJECT-TYPE
    SYNTAX      	SEQUENCE OF DsxT3E3IfLastTestResultEntry
    MAX-ACCESS  	not-accessible
    STATUS      	current
    DESCRIPTION
    	"A list of T3/E3 interface test status entries."
    ::= { dsxT3E3IfStatusGroup 4 }

dsxT3E3IfLastTestResultEntry 	OBJECT-TYPE
    SYNTAX      	DsxT3E3IfLastTestResultEntry
    MAX-ACCESS  	not-accessible
    STATUS      	current
    DESCRIPTION
    	"An entry containing the status entry for each 
	currently active T3/E3 interface."
    AUGMENTS { dsxT3E3IfConfigLineEntry }
    ::= { dsxT3E3IfLastTestResultTable 1 }

DsxT3E3IfLastTestResultEntry ::=
    SEQUENCE {
        dsxT3E3IfLastTestResultTestType       INTEGER,
        dsxT3E3IfLastTestResultTestState      INTEGER,
        dsxT3E3IfLastTestResultLoopCode       INTEGER
    }
    
dsxT3E3IfLastTestResultTestType 	OBJECT-TYPE
    SYNTAX      	INTEGER 
                	{
                    no-test        (1),
                    line-loopback  (3),
                    other-loopback (4),
                    remote-lpup    (6),
                    remote-lpdn    (7)
                  }
    MAX-ACCESS  	read-only
    STATUS      	current
    DESCRIPTION
   	"The test type."
    ::= { dsxT3E3IfLastTestResultEntry 1 }

dsxT3E3IfLastTestResultTestState 	OBJECT-TYPE
    SYNTAX      	INTEGER
                	{
                    state-idle        (1),
                    state-searching   (2),
       		    state-locked      (3),
                    state-relocked    (4),
                    state-in-progress (5),
                    state-passed      (6),
                    state-failed      (7)
                	}
    MAX-ACCESS  	read-only
    STATUS      	current
    DESCRIPTION
   	"State of the test invoked."
    ::= { dsxT3E3IfLastTestResultEntry 2 }

dsxT3E3IfLastTestResultLoopCode 	OBJECT-TYPE
    SYNTAX      	INTEGER
                	{
                    loopcode-none (1),
                    loopcode-feac (2)
                	}
    MAX-ACCESS  	read-only
    STATUS      	current
    DESCRIPTION
    	"The loopcode used to loopback the T3/E3 interface 
	in previous test."
    ::= { dsxT3E3IfLastTestResultEntry 3 }
    
-- DSX T3/E3 stats group definitions.

-- Table to store the valid intervals of archive stats tables.

dsxT3E3IfArchiveStatsValidIntervalsTable OBJECT-TYPE
    SYNTAX      	SEQUENCE OF DsxT3E3IfArchiveStatsValidIntervalsEntry
    MAX-ACCESS  	not-accessible
    STATUS      	current
    DESCRIPTION
    	"A list of T3/E3 interface ValidIntervals entries."
    ::= { dsxT3E3IfStatsGroup 1 }

dsxT3E3IfArchiveStatsValidIntervalsEntry  OBJECT-TYPE
    SYNTAX      	DsxT3E3IfArchiveStatsValidIntervalsEntry
    MAX-ACCESS  	not-accessible
    STATUS      	current
    DESCRIPTION
   	"An entry containing a valid intervals entry for each currently 
	active T3/E3 interface."
    AUGMENTS 	{ dsxT3E3IfConfigLineEntry }
    ::= { dsxT3E3IfArchiveStatsValidIntervalsTable 1 }

DsxT3E3IfArchiveStatsValidIntervalsEntry ::=
    SEQUENCE {
        dsxT3E3IfAnsiArchiveStatsValidIntervals        Unsigned32, 
        dsxT3E3IfIetfArchiveStatsValidIntervals        Unsigned32, 
        dsxT3E3IfUserTotalStatsValidDays               Unsigned32, 
        dsxT3E3IfUserArchiveStatsValidIntervals        INTEGER
    }
    
dsxT3E3IfAnsiArchiveStatsValidIntervals OBJECT-TYPE
    SYNTAX   	Unsigned32
    MAX-ACCESS  	read-only
    STATUS      	current
    DESCRIPTION
    	"Archive Stats Valid Interval for ANSI."
    ::= { dsxT3E3IfArchiveStatsValidIntervalsEntry 1 }
    
dsxT3E3IfIetfArchiveStatsValidIntervals OBJECT-TYPE
    SYNTAX   	Unsigned32
    MAX-ACCESS  	read-only
    STATUS      	current
    DESCRIPTION
    	"Archive stats valid interval for IETF."
    ::= { dsxT3E3IfArchiveStatsValidIntervalsEntry 2 }
    
dsxT3E3IfUserTotalStatsValidDays OBJECT-TYPE
    SYNTAX   	Unsigned32
    MAX-ACCESS  	read-only
    STATUS      	current
    DESCRIPTION
   	"User total stats valid days."
    ::= { dsxT3E3IfArchiveStatsValidIntervalsEntry 3 }
    
dsxT3E3IfUserArchiveStatsValidIntervals OBJECT-TYPE
    SYNTAX   	INTEGER
    MAX-ACCESS  	read-write
    STATUS      	current
    DESCRIPTION
    	"User archive stats valid interval. Setting this 
	variable to 0 will clear the user statistics tables."
    ::= { dsxT3E3IfArchiveStatsValidIntervalsEntry 4 }


-- Error event statistics table.

dsxT3E3IfErrorEventStatsTable OBJECT-TYPE
    SYNTAX      SEQUENCE OF DsxT3E3IfErrorEventStatsEntry
    MAX-ACCESS  not-accessible
    STATUS      current
    DESCRIPTION
     	"A list of T3/E3 interface error events entries."
    ::= { dsxT3E3IfStatsGroup 2 }

dsxT3E3IfErrorEventStatsEntry  OBJECT-TYPE
    SYNTAX      DsxT3E3IfErrorEventStatsEntry
    MAX-ACCESS  not-accessible
    STATUS      current
    DESCRIPTION
   	"An entry containing error events that occured on 
	the T3/E3 interface."
    AUGMENTS { dsxT3E3IfConfigLineEntry }
    ::= { dsxT3E3IfErrorEventStatsTable 1 }

DsxT3E3IfErrorEventStatsEntry ::=
    SEQUENCE {
        dsxT3E3IfErrorEventStatsEXZ     Unsigned32,
        dsxT3E3IfErrorEventStatsPBE     Unsigned32,
        dsxT3E3IfErrorEventStatsFEBE    Unsigned32
    }
    
dsxT3E3IfErrorEventStatsEXZ OBJECT-TYPE
    SYNTAX      Unsigned32
    MAX-ACCESS  read-only
    STATUS      current
    DESCRIPTION
  	"Excessive zeros (EXZ) error event count."
    ::= { dsxT3E3IfErrorEventStatsEntry 1 }

dsxT3E3IfErrorEventStatsPBE OBJECT-TYPE
    SYNTAX      	Unsigned32
    MAX-ACCESS  	read-only
    STATUS      	current
    DESCRIPTION 
	"Parity bit error events count."
    ::= { dsxT3E3IfErrorEventStatsEntry 2 }

dsxT3E3IfErrorEventStatsFEBE OBJECT-TYPE
    SYNTAX      Unsigned32
    MAX-ACCESS  read-only
    STATUS      current
    DESCRIPTION
    	"Far end block error (FEBE) event count."
    ::= { dsxT3E3IfErrorEventStatsEntry 3 }

-- DSX T3/E3 stats group definitions.

dsxT3E3IfAnsiStatsGroup   OBJECT IDENTIFIER   ::= { dsxT3E3IfStatsGroup 3 }
dsxT3E3IfIetfStatsGroup   OBJECT IDENTIFIER   ::= { dsxT3E3IfStatsGroup 4 }
dsxT3E3IfUserStatsGroup   OBJECT IDENTIFIER   ::= { dsxT3E3IfStatsGroup 5 }


-- DSX T3/E3 ANSI statistics group definitions.

-- ANSI current stats table.

dsxT3E3IfAnsiCurrentStatsTable OBJECT-TYPE
    SYNTAX      	SEQUENCE OF DsxT3E3IfAnsiCurrentStatsEntry
    MAX-ACCESS  	not-accessible
    STATUS      	current
    DESCRIPTION
   	"A list of T3/E3 interface current 15-minute interval 
	statistics entries."
    ::= { dsxT3E3IfAnsiStatsGroup 1 }

dsxT3E3IfAnsiCurrentStatsEntry  OBJECT-TYPE
    SYNTAX      	DsxT3E3IfAnsiCurrentStatsEntry
    MAX-ACCESS  	not-accessible
    STATUS      	current
    DESCRIPTION
   	"An entry containing status entry for each currently 
	active T3/E3 interface."
    AUGMENTS 	{ dsxT3E3IfConfigLineEntry }
    ::= { dsxT3E3IfAnsiCurrentStatsTable 1 }

DsxT3E3IfAnsiCurrentStatsEntry ::=
    SEQUENCE {
        dsxT3E3IfAnsiCurrentStatsUASState       TruthValue,
        dsxT3E3IfAnsiCurrentStatsTimeInCurrent  Unsigned32,
        dsxT3E3IfAnsiCurrentPathStatsCV         Unsigned32,
        dsxT3E3IfAnsiCurrentPathStatsES         Unsigned32,
        dsxT3E3IfAnsiCurrentPathStatsSES        Unsigned32,
        dsxT3E3IfAnsiCurrentPathStatsSAS        Unsigned32,
        dsxT3E3IfAnsiCurrentPathStatsUAS        Unsigned32,
        dsxT3E3IfAnsiCurrentLineStatsCV         Unsigned32,
        dsxT3E3IfAnsiCurrentLineStatsES         Unsigned32,
        dsxT3E3IfAnsiCurrentLineStatsSES        Unsigned32
    }
    
dsxT3E3IfAnsiCurrentStatsUASState 	OBJECT-TYPE
    SYNTAX      	TruthValue
    MAX-ACCESS  	read-only
    STATUS      	current
    DESCRIPTION
    	"Current state of availablity of the T3/E3 line."
    ::= { dsxT3E3IfAnsiCurrentStatsEntry 1 }

dsxT3E3IfAnsiCurrentStatsTimeInCurrent 	OBJECT-TYPE
    SYNTAX      	Unsigned32
    MAX-ACCESS  	read-only
    STATUS      	current
    DESCRIPTION
    	"Current time for statistics."
    ::= { dsxT3E3IfAnsiCurrentStatsEntry 2 }

dsxT3E3IfAnsiCurrentPathStatsCV OBJECT-TYPE
    SYNTAX      	Unsigned32
    MAX-ACCESS  	read-only
    STATUS      	current
    DESCRIPTION
   	"The number of path coding violations encountered 
	by a T3/E3 interface in the current 15-minute
	interval."
    ::= { dsxT3E3IfAnsiCurrentStatsEntry 3 }

dsxT3E3IfAnsiCurrentPathStatsES 	OBJECT-TYPE
    SYNTAX      	Unsigned32
    MAX-ACCESS  	read-only
    STATUS      	current
    DESCRIPTION
   	"The number of errored seconds encountered  by
	a T3/E3 interface in the current 15-minute 
	interval."
    ::= { dsxT3E3IfAnsiCurrentStatsEntry 4 }

dsxT3E3IfAnsiCurrentPathStatsSES 	OBJECT-TYPE
    SYNTAX      	Unsigned32
    MAX-ACCESS  	read-only
    STATUS      	current
    DESCRIPTION
    	"The number of severely errored seconds 
	encountered by a T3/E3 interface in 
	the current 15-minute interval."
    ::= { dsxT3E3IfAnsiCurrentStatsEntry 5 }

dsxT3E3IfAnsiCurrentPathStatsSAS 	OBJECT-TYPE
    SYNTAX      	Unsigned32
    MAX-ACCESS  	read-only
    STATUS      	current
    DESCRIPTION
    	"The number of severely errored framing seconds
      encountered by a T3/E3 interface in the current
      15-minute interval."
    ::= { dsxT3E3IfAnsiCurrentStatsEntry 6 }

dsxT3E3IfAnsiCurrentPathStatsUAS OBJECT-TYPE
    SYNTAX      	Unsigned32
    MAX-ACCESS  	read-only
    STATUS      	current
    DESCRIPTION
    	"The number of unavailable seconds encountered
      by a T3/E3 interface in the current 15-minute 
	interval."
                
    ::= { dsxT3E3IfAnsiCurrentStatsEntry 7 }

    
dsxT3E3IfAnsiCurrentLineStatsCV 	OBJECT-TYPE
    SYNTAX   	Unsigned32
    MAX-ACCESS  	read-only
    STATUS      	current
    DESCRIPTION
  	"The number of path coding violations encountered
      by a T3/E3 interface in the current 15-minute 
      interval."
    ::= { dsxT3E3IfAnsiCurrentStatsEntry 8 }

dsxT3E3IfAnsiCurrentLineStatsES 	OBJECT-TYPE
    SYNTAX   	Unsigned32
    MAX-ACCESS  	read-only
    STATUS      	current
    DESCRIPTION
	"The number of errored seconds encountered by
      a T3/E3 interface in the current 15-minute 
      interval."
    ::= { dsxT3E3IfAnsiCurrentStatsEntry 9 }

dsxT3E3IfAnsiCurrentLineStatsSES 	OBJECT-TYPE
    SYNTAX   	Unsigned32
    MAX-ACCESS  	read-only
    STATUS      	current
    DESCRIPTION
    	"The number of severely errored seconds encountered  
      by a T3/E3 interface in the current 15-minute 
      interval."
    ::= { dsxT3E3IfAnsiCurrentStatsEntry 10 }

-- ANSI total stats table.

dsxT3E3IfAnsiTotalStatsTable 	OBJECT-TYPE
    SYNTAX      	SEQUENCE OF DsxT3E3IfAnsiTotalStatsEntry
    MAX-ACCESS  	not-accessible
    STATUS      	current
    DESCRIPTION
    	"Entries of total statistics collected over past 
	24 hours on a T3/E3 interface."
    ::= { dsxT3E3IfAnsiStatsGroup 2 }

dsxT3E3IfAnsiTotalStatsEntry  OBJECT-TYPE
    SYNTAX      	DsxT3E3IfAnsiTotalStatsEntry
    MAX-ACCESS  	not-accessible
    STATUS      	current
    DESCRIPTION
    	"An entry containing the status entry for each 
	currently active T3/E3 interface."
    AUGMENTS { dsxT3E3IfConfigLineEntry }
    ::= { dsxT3E3IfAnsiTotalStatsTable 1 }

DsxT3E3IfAnsiTotalStatsEntry ::=
    SEQUENCE {
        dsxT3E3IfAnsiTotalPathStatsCV     Unsigned32,
        dsxT3E3IfAnsiTotalPathStatsES     Unsigned32,
        dsxT3E3IfAnsiTotalPathStatsSES    Unsigned32,
        dsxT3E3IfAnsiTotalPathStatsSAS  	Unsigned32,
        dsxT3E3IfAnsiTotalPathStatsUAS    Unsigned32,
        dsxT3E3IfAnsiTotalLineStatsCV     Unsigned32,
        dsxT3E3IfAnsiTotalLineStatsES     Unsigned32,
        dsxT3E3IfAnsiTotalLineStatsSES    Unsigned32
    }
    
dsxT3E3IfAnsiTotalPathStatsCV 	OBJECT-TYPE
    SYNTAX   	Unsigned32
    MAX-ACCESS  	read-only
    STATUS      	current
    DESCRIPTION
    	"The number of path coding violations encountered  
      by a T3/E3 interface in the previous 24-hour 
	interval."
    ::= { dsxT3E3IfAnsiTotalStatsEntry 1 }

dsxT3E3IfAnsiTotalPathStatsES OBJECT-TYPE
    SYNTAX   	Unsigned32
    MAX-ACCESS  	read-only
    STATUS      	current
    DESCRIPTION
    	"The number of errored seconds encountered by a
      T3/E3 interface in the previous 24-hour interval."
    ::= { dsxT3E3IfAnsiTotalStatsEntry 2 }

dsxT3E3IfAnsiTotalPathStatsSES 	OBJECT-TYPE
    SYNTAX   	Unsigned32
    MAX-ACCESS  	read-only
    STATUS      	current
    DESCRIPTION
    	"The number of severely errored seconds encountered  
      by a T3/E3 interface in the previous 24-hour 
      interval."
    ::= { dsxT3E3IfAnsiTotalStatsEntry 3 }

dsxT3E3IfAnsiTotalPathStatsSAS 	OBJECT-TYPE
    SYNTAX   	Unsigned32
    MAX-ACCESS  	read-only
    STATUS      	current
    DESCRIPTION
    	"The number of severely alarm aeconds encountered  
      by a T3/E3 interface in the previous 24-hour 
      interval."
    ::= { dsxT3E3IfAnsiTotalStatsEntry 4 }

dsxT3E3IfAnsiTotalPathStatsUAS 	OBJECT-TYPE
    SYNTAX   	Unsigned32
    MAX-ACCESS  	read-only
    STATUS      	current
    DESCRIPTION
   	"The number of unavailable seconds encountered
      by a T3/E3 interface in the previous 24-hour 
	interval."
                
    ::= { dsxT3E3IfAnsiTotalStatsEntry 5 }

dsxT3E3IfAnsiTotalLineStatsCV OBJECT-TYPE
    SYNTAX   	Unsigned32
    MAX-ACCESS  	read-only
    STATUS      	current
    DESCRIPTION
    	"The number of path coding violations encountered  
      by a T3/E3 interface in the previous 24-hour 
      interval. "
    ::= { dsxT3E3IfAnsiTotalStatsEntry 6 }

dsxT3E3IfAnsiTotalLineStatsES OBJECT-TYPE
    SYNTAX   	Unsigned32
    MAX-ACCESS  	read-only
    STATUS      	current
    DESCRIPTION
    	"The number of errored seconds encountered 
	by a T3/E3 interface in the previous 24-hour 
	interval."
    ::= { dsxT3E3IfAnsiTotalStatsEntry 7 }

dsxT3E3IfAnsiTotalLineStatsSES 	OBJECT-TYPE
    SYNTAX   	Unsigned32
    MAX-ACCESS  	read-only
    STATUS      	current
    DESCRIPTION
    	"The number of severely errored seconds encountered  
      by a T3/E3 interface in the previous 24-hour 
	interval."
    ::= { dsxT3E3IfAnsiTotalStatsEntry 8 }


-- ANSI ARCHIVE INTERVAL STATISTICS TABLE

dsxT3E3IfAnsiArchiveIntervalStatsTable OBJECT-TYPE
    SYNTAX      	SEQUENCE OF DsxT3E3IfAnsiArchiveIntervalStatsEntry
    MAX-ACCESS  	not-accessible
    STATUS      	current
    DESCRIPTION
     	"A list of T3/E3 interface archive statistics entries."
    ::= { dsxT3E3IfAnsiStatsGroup 3 }

dsxT3E3IfAnsiArchiveIntervalStatsEntry  OBJECT-TYPE
    SYNTAX      	DsxT3E3IfAnsiArchiveIntervalStatsEntry
    MAX-ACCESS  	not-accessible
    STATUS      	current
    DESCRIPTION
     	"An entry containing the status entry for each currently active 
      T3/E3 interface."
    INDEX { dsxT3E3IfIndex, dsxT3E3IfAnsiArchiveStatsInterval }
    ::= { dsxT3E3IfAnsiArchiveIntervalStatsTable 1 }

DsxT3E3IfAnsiArchiveIntervalStatsEntry ::=
    SEQUENCE {
        dsxT3E3IfAnsiArchiveStatsInterval            Unsigned32,
        dsxT3E3IfAnsiArchiveIntervalPathStatsCV      Unsigned32,
        dsxT3E3IfAnsiArchiveIntervalPathStatsES      Unsigned32,
        dsxT3E3IfAnsiArchiveIntervalPathStatsSES     Unsigned32,
        dsxT3E3IfAnsiArchiveIntervalPathStatsSAS     Unsigned32,
        dsxT3E3IfAnsiArchiveIntervalPathStatsUAS     Unsigned32,
        dsxT3E3IfAnsiArchiveIntervalLineStatsCV      Unsigned32,
        dsxT3E3IfAnsiArchiveIntervalLineStatsES      Unsigned32,
        dsxT3E3IfAnsiArchiveIntervalLineStatsSES     Unsigned32
    }

dsxT3E3IfAnsiArchiveStatsInterval 	OBJECT-TYPE
    SYNTAX      	Unsigned32
    MAX-ACCESS  	not-accessible
    STATUS      	current
    DESCRIPTION
    	"Entries of the ANSI archive statistics collected 
	for T3/E3 a interface."
    ::= { dsxT3E3IfAnsiArchiveIntervalStatsEntry 1 }
    
dsxT3E3IfAnsiArchiveIntervalPathStatsCV 	OBJECT-TYPE
    SYNTAX   	Unsigned32
    MAX-ACCESS  	read-only
    STATUS      	current
    DESCRIPTION
    	"The number of path coding violations encountered  
      by a T3/E3 interface in the current interval."
            
    ::= { dsxT3E3IfAnsiArchiveIntervalStatsEntry 2 }

dsxT3E3IfAnsiArchiveIntervalPathStatsES OBJECT-TYPE
    SYNTAX   	Unsigned32
    MAX-ACCESS  	read-only
    STATUS      	current
    DESCRIPTION
     	"The number of errored seconds encountered by
      a T3/E3 interface in the current interval."
    ::= { dsxT3E3IfAnsiArchiveIntervalStatsEntry 3 }

dsxT3E3IfAnsiArchiveIntervalPathStatsSES OBJECT-TYPE
    SYNTAX   	Unsigned32
    MAX-ACCESS  	read-only
    STATUS      	current
    DESCRIPTION
   	"The number of severely errored seconds encountered 
      by a T3/E3 interface in the current interval."
    ::= { dsxT3E3IfAnsiArchiveIntervalStatsEntry 4 }

dsxT3E3IfAnsiArchiveIntervalPathStatsSAS OBJECT-TYPE
    SYNTAX   	Unsigned32
    MAX-ACCESS  	read-only
    STATUS      	current
    DESCRIPTION
    	"The number of severely errored framing seconds
      encountered by a T3/E3 interface in the current
      interval."
    ::= { dsxT3E3IfAnsiArchiveIntervalStatsEntry 5 }

dsxT3E3IfAnsiArchiveIntervalPathStatsUAS OBJECT-TYPE
    SYNTAX   	Unsigned32
    MAX-ACCESS  	read-only
    STATUS      	current
    DESCRIPTION
    	"The number of unavailable seconds encountered
      by a T3/E3 interface in the current interval."
    ::= { dsxT3E3IfAnsiArchiveIntervalStatsEntry 6 }

dsxT3E3IfAnsiArchiveIntervalLineStatsCV OBJECT-TYPE
    SYNTAX   	Unsigned32
    MAX-ACCESS  	read-only
    STATUS      	current
    DESCRIPTION
     	"The number of path coding violations encountered  
      by a T3/E3 interface in the current interval."
             
    ::= { dsxT3E3IfAnsiArchiveIntervalStatsEntry 7 }

dsxT3E3IfAnsiArchiveIntervalLineStatsES OBJECT-TYPE
    SYNTAX   	Unsigned32
    MAX-ACCESS  	read-only
    STATUS      	current
    DESCRIPTION
     	"The number of errored seconds encountered by
      a T3/E3 interface in the current interval."
    ::= { dsxT3E3IfAnsiArchiveIntervalStatsEntry 8 }

dsxT3E3IfAnsiArchiveIntervalLineStatsSES OBJECT-TYPE
    SYNTAX   	Unsigned32
    MAX-ACCESS  	read-only
    STATUS      	current
    DESCRIPTION
    	"The number of severely errored seconds encountered  
      by a T3/E3 interface in the current interval."  
                
    ::= { dsxT3E3IfAnsiArchiveIntervalStatsEntry 9 }


-- IETF stats group.

-- IETF current stats table.
dsxT3E3IfIetfCurrentStatsTable OBJECT-TYPE
    SYNTAX      	SEQUENCE OF DsxT3E3IfIetfCurrentStatsEntry
    MAX-ACCESS  	not-accessible
    STATUS      	current
    DESCRIPTION
    	"A list of the current 15-minute IETF-based statistics
	collected for T3/E3 interface."
    ::= { dsxT3E3IfIetfStatsGroup 1 }

dsxT3E3IfIetfCurrentStatsEntry  OBJECT-TYPE
    SYNTAX      	DsxT3E3IfIetfCurrentStatsEntry
    MAX-ACCESS  	not-accessible
    STATUS      	current
    DESCRIPTION
     	"An entry containing the status entry for each 
	currently active T3/E3 interface."
    AUGMENTS { dsxT3E3IfConfigLineEntry }
    ::= { dsxT3E3IfIetfCurrentStatsTable 1 }

DsxT3E3IfIetfCurrentStatsEntry ::=
    SEQUENCE {
        dsxT3E3IfIetfCurrentStatsUASState        TruthValue,
        dsxT3E3IfIetfCurrentStatsTimeInCurrent   Unsigned32,
        dsxT3E3IfIetfCurrentStatsPES             Unsigned32,
        dsxT3E3IfIetfCurrentStatsPSES            Unsigned32,
        dsxT3E3IfIetfCurrentStatsSEFS            Unsigned32,
        dsxT3E3IfIetfCurrentStatsUAS             Unsigned32,
        dsxT3E3IfIetfCurrentStatsLCV             Unsigned32,
        dsxT3E3IfIetfCurrentStatsPCV             Unsigned32,
        dsxT3E3IfIetfCurrentStatsLES             Unsigned32,
        dsxT3E3IfIetfCurrentStatsCCV             Unsigned32,
        dsxT3E3IfIetfCurrentStatsCES             Unsigned32,
        dsxT3E3IfIetfCurrentStatsCSES            Unsigned32        
    }
    
dsxT3E3IfIetfCurrentStatsUASState OBJECT-TYPE
    SYNTAX   	TruthValue
    MAX-ACCESS  	read-only
    STATUS      	current
    DESCRIPTION
    	"Current state of availablity of the interface."
    ::= { dsxT3E3IfIetfCurrentStatsEntry 1 }
    
dsxT3E3IfIetfCurrentStatsTimeInCurrent OBJECT-TYPE
    SYNTAX   	Unsigned32
    MAX-ACCESS  	read-only
    STATUS     	current
    DESCRIPTION
     	"The number of seconds that have elapsed since 
      the beginning of the current IETF 
	error-measurement period. "
    ::= { dsxT3E3IfIetfCurrentStatsEntry 2 }
    
dsxT3E3IfIetfCurrentStatsPES OBJECT-TYPE
    SYNTAX   	Unsigned32
    MAX-ACCESS  	read-only
    STATUS      	current
    DESCRIPTION
   	"The number of IETF parity errored seconds encountered  
      by a T3/E3 interface."
    ::= { dsxT3E3IfIetfCurrentStatsEntry 3 }

dsxT3E3IfIetfCurrentStatsPSES OBJECT-TYPE
    SYNTAX   	Unsigned32
    MAX-ACCESS  	read-only
    STATUS      	current
    DESCRIPTION
    	"The number of parity severely errored seconds
      encountered by a T3/E3 interface."
    ::= { dsxT3E3IfIetfCurrentStatsEntry 4 }

dsxT3E3IfIetfCurrentStatsSEFS OBJECT-TYPE
    SYNTAX   	Unsigned32
    MAX-ACCESS  	read-only
    STATUS      	current
    DESCRIPTION
    	"The number of IETF severely errored framing
      seconds encountered by a T3/E3 interface."
    ::= { dsxT3E3IfIetfCurrentStatsEntry 5 }

dsxT3E3IfIetfCurrentStatsUAS OBJECT-TYPE
    SYNTAX   	Unsigned32
    MAX-ACCESS  	read-only
    STATUS      	current
    DESCRIPTION
    	"The number of unavailable seconds encountered
      by a T3/E3 interface."
    ::= { dsxT3E3IfIetfCurrentStatsEntry 6 }

dsxT3E3IfIetfCurrentStatsLCV OBJECT-TYPE
    SYNTAX   	Unsigned32
    MAX-ACCESS  	read-only
    STATUS      	current
    DESCRIPTION
    	"The number of line code violations encountered
      by a T3/E3 interface."
    ::= { dsxT3E3IfIetfCurrentStatsEntry 7 }

dsxT3E3IfIetfCurrentStatsPCV OBJECT-TYPE
    SYNTAX   	Unsigned32
    MAX-ACCESS  	read-only
    STATUS      	current
    DESCRIPTION
    	"The number of IETF path coding violations,
      encountered by a T3/E3 interface that are 
	reported via the far-end block-error count."
    ::= { dsxT3E3IfIetfCurrentStatsEntry 8 }


dsxT3E3IfIetfCurrentStatsLES OBJECT-TYPE
    SYNTAX   	Unsigned32
    MAX-ACCESS  	read-only
    STATUS      	current
    DESCRIPTION
   	"The number of IETF line errored seconds 
	encountered by a T3/E3 interface."
   ::= { dsxT3E3IfIetfCurrentStatsEntry 9 }

dsxT3E3IfIetfCurrentStatsCCV OBJECT-TYPE
    SYNTAX   	Unsigned32
    MAX-ACCESS  	read-only
    STATUS      	current
    DESCRIPTION
   	"The number of IETF C-bit coding violations
      encountered by a T3/E3 interface."
   ::= { dsxT3E3IfIetfCurrentStatsEntry 10 }
    
dsxT3E3IfIetfCurrentStatsCES OBJECT-TYPE
    SYNTAX   	Unsigned32
    MAX-ACCESS  	read-only
    STATUS      	current
    DESCRIPTION
    	"The number of IETF C-bit errored seconds  
      encountered by a T3/E3 interface."
   ::= { dsxT3E3IfIetfCurrentStatsEntry 11 }
    
dsxT3E3IfIetfCurrentStatsCSES OBJECT-TYPE
    SYNTAX   	Unsigned32
    MAX-ACCESS  	read-only
    STATUS      	current
    DESCRIPTION
    	"The number of IETF C-Bit severely errored seconds."
   ::= { dsxT3E3IfIetfCurrentStatsEntry 12 }

 
-- IETF total stats table.

dsxT3E3IfIetfTotalStatsTable OBJECT-TYPE
    SYNTAX      	SEQUENCE OF DsxT3E3IfIetfTotalStatsEntry
    MAX-ACCESS  	not-accessible
    STATUS      	current
    DESCRIPTION
    	"A list of entries for statistics collected over 
	24 hours."
    ::= { dsxT3E3IfIetfStatsGroup 2 }

dsxT3E3IfIetfTotalStatsEntry  OBJECT-TYPE
    SYNTAX      	DsxT3E3IfIetfTotalStatsEntry
    MAX-ACCESS  	not-accessible
    STATUS      	current
    DESCRIPTION
    	"An entry containing the status entry for each 
	currently active T3/E3 interface."
    AUGMENTS { dsxT3E3IfConfigLineEntry }
    ::= { dsxT3E3IfIetfTotalStatsTable 1 }

DsxT3E3IfIetfTotalStatsEntry ::=
    SEQUENCE {
        dsxT3E3IfIetfTotalStatsPES        Unsigned32,
        dsxT3E3IfIetfTotalStatsPSES       Unsigned32,
        dsxT3E3IfIetfTotalStatsSEFS       Unsigned32,
        dsxT3E3IfIetfTotalStatsUAS        Unsigned32,
        dsxT3E3IfIetfTotalStatsLCV        Unsigned32,
        dsxT3E3IfIetfTotalStatsPCV        Unsigned32,
        dsxT3E3IfIetfTotalStatsLES        Unsigned32,
        dsxT3E3IfIetfTotalStatsCCV        Unsigned32,
        dsxT3E3IfIetfTotalStatsCES        Unsigned32,
        dsxT3E3IfIetfTotalStatsCSES       Unsigned32        
    }
    
dsxT3E3IfIetfTotalStatsPES OBJECT-TYPE
    SYNTAX      	Unsigned32
    MAX-ACCESS  	read-only
    STATUS      	current
    DESCRIPTION
    	"Total number of IETF errored seconds encountered  
      by a T3/E3 interface during past 24 hours."
    ::= { dsxT3E3IfIetfTotalStatsEntry 1 }

dsxT3E3IfIetfTotalStatsPSES OBJECT-TYPE
    SYNTAX      	Unsigned32
    MAX-ACCESS  	read-only
    STATUS      	current
    DESCRIPTION
    	"Total number of IETF severely errored seconds
      encountered by a T3/E3 interface during past 
	24 hours."
    ::= { dsxT3E3IfIetfTotalStatsEntry 2 }

dsxT3E3IfIetfTotalStatsSEFS OBJECT-TYPE
    SYNTAX      	Unsigned32
    MAX-ACCESS  	read-only
    STATUS      	current
    DESCRIPTION
    	"Total number of IETF severely errored framing
      seconds encountered by a T3/E3 interface during
	the past 24 hours."
    ::= { dsxT3E3IfIetfTotalStatsEntry 3 }

dsxT3E3IfIetfTotalStatsUAS OBJECT-TYPE
    SYNTAX      	Unsigned32
    MAX-ACCESS  	read-only
    STATUS      	current
    DESCRIPTION
     	"Total number of unavailable seconds encountered
	by a T3/E3 interface during past 24 hours."
    ::= { dsxT3E3IfIetfTotalStatsEntry 4 }

dsxT3E3IfIetfTotalStatsLCV OBJECT-TYPE
    SYNTAX      	Unsigned32
    MAX-ACCESS  	read-only
    STATUS     	 current
    DESCRIPTION
    	"Total number of line code violations encountered 
	by a T3/E3 interface during past 24 hours."
    ::= { dsxT3E3IfIetfTotalStatsEntry 5 }

dsxT3E3IfIetfTotalStatsPCV OBJECT-TYPE
    SYNTAX      	Unsigned32
    MAX-ACCESS  	read-only
    STATUS      	current
    DESCRIPTION
   	"Total number of IETF path coding violations 
	encountered by a T3/E3 interface during past 
	24 hours."
    ::= { dsxT3E3IfIetfTotalStatsEntry 6 }


dsxT3E3IfIetfTotalStatsLES OBJECT-TYPE
    SYNTAX      	Unsigned32
    MAX-ACCESS  	read-only
    STATUS      	current
    DESCRIPTION
    	"Total number of IETF line errored seconds 
	encountered by a T3/E3 interface during past 
	24 hours."
   ::= { dsxT3E3IfIetfTotalStatsEntry 7 }

dsxT3E3IfIetfTotalStatsCCV OBJECT-TYPE
    SYNTAX      	Unsigned32
    MAX-ACCESS  	read-only
    STATUS      	current
    DESCRIPTION
    	"Total number of IETF C-bit parity code violation
	encountered by a T3/E3 interface during past 
	24 hours."
   ::= { dsxT3E3IfIetfTotalStatsEntry 8 }
    
dsxT3E3IfIetfTotalStatsCES OBJECT-TYPE
    SYNTAX      	Unsigned32
    MAX-ACCESS  	read-only
    STATUS      	current
    DESCRIPTION
    	"Total number of IETF C-bit parity errored seconds
	encountered by a T3/E3 interface during past 
	24 hours."
   ::= { dsxT3E3IfIetfTotalStatsEntry 9 }
    
dsxT3E3IfIetfTotalStatsCSES OBJECT-TYPE
    SYNTAX      	Unsigned32
    MAX-ACCESS  	read-only
    STATUS      	current
    DESCRIPTION
    	"Total number of IETF C-bit parity severely errored 
	seconds encountered by a T3/E3 interface during past 
	24 hours."
   ::= { dsxT3E3IfIetfTotalStatsEntry 10 }


--  IETF archive stats table.

dsxT3E3IfIetfArchiveStatsTable OBJECT-TYPE
    SYNTAX      	SEQUENCE OF DsxT3E3IfIetfArchiveStatsEntry
    MAX-ACCESS  	not-accessible
    STATUS      	current
    DESCRIPTION
    	"A list of T3/E3 interface IETF archive statistics entries."
    ::= { dsxT3E3IfIetfStatsGroup 3 }

dsxT3E3IfIetfArchiveStatsEntry  OBJECT-TYPE
    SYNTAX      	DsxT3E3IfIetfArchiveStatsEntry
    MAX-ACCESS  	not-accessible
    STATUS      	current
    DESCRIPTION
    	"An entry containing status entry for each currently active 
      T3/E3 interface."
    INDEX { dsxT3E3IfIndex, dsxT3E3IfIetfArchiveStatsInterval }
    ::= { dsxT3E3IfIetfArchiveStatsTable 1 }

DsxT3E3IfIetfArchiveStatsEntry ::=
    SEQUENCE {
        dsxT3E3IfIetfArchiveStatsInterval  Unsigned32, 
        dsxT3E3IfIetfArchiveStatsPES       Unsigned32,
        dsxT3E3IfIetfArchiveStatsPSES      Unsigned32,
        dsxT3E3IfIetfArchiveStatsSEFS      Unsigned32,
        dsxT3E3IfIetfArchiveStatsUAS       Unsigned32,
        dsxT3E3IfIetfArchiveStatsLCV       Unsigned32,
        dsxT3E3IfIetfArchiveStatsPCV       Unsigned32,
        dsxT3E3IfIetfArchiveStatsLES       Unsigned32,
        dsxT3E3IfIetfArchiveStatsCCV       Unsigned32,
        dsxT3E3IfIetfArchiveStatsCES       Unsigned32,
        dsxT3E3IfIetfArchiveStatsCSES      Unsigned32        
    }
    
dsxT3E3IfIetfArchiveStatsInterval OBJECT-TYPE
    SYNTAX      	Unsigned32
    MAX-ACCESS  	not-accessible
    STATUS      	current
    DESCRIPTION
    	"The total number of intervals for which statistics
      would be collected."
    ::= { dsxT3E3IfIetfArchiveStatsEntry 1 }
    
dsxT3E3IfIetfArchiveStatsPES OBJECT-TYPE
    SYNTAX      	Unsigned32
    MAX-ACCESS  	read-only
    STATUS      	current
    DESCRIPTION
    	"The number of IETF errored seconds encountered  
      by a T3/E3 interface."
    ::= { dsxT3E3IfIetfArchiveStatsEntry 2 }

dsxT3E3IfIetfArchiveStatsPSES OBJECT-TYPE
    SYNTAX      	Unsigned32
    MAX-ACCESS  	read-only
    STATUS      	current
    DESCRIPTION
     	"The number of IETF severely errored seconds
      encountered by a T3/E3 interface."
    ::= { dsxT3E3IfIetfArchiveStatsEntry 3 }

dsxT3E3IfIetfArchiveStatsSEFS OBJECT-TYPE
    SYNTAX      	Unsigned32
    MAX-ACCESS  	read-only
    STATUS      	current
    DESCRIPTION
     	"The number of IETF severely errored framing
      seconds encountered by a T3/E3 interface."
    ::= { dsxT3E3IfIetfArchiveStatsEntry 4 }

dsxT3E3IfIetfArchiveStatsUAS OBJECT-TYPE
    SYNTAX      	Unsigned32
    MAX-ACCESS  	read-only
    STATUS      	current
    DESCRIPTION
    	"The number of unavailable seconds encountered
      by a T3/E3 interface."
    ::= { dsxT3E3IfIetfArchiveStatsEntry 5 }

dsxT3E3IfIetfArchiveStatsLCV OBJECT-TYPE
    SYNTAX      	Unsigned32
    MAX-ACCESS  	read-only
    STATUS      	current
    DESCRIPTION
    	"The number of line code violations encountered
      by a T3/E3 interface."
    ::= { dsxT3E3IfIetfArchiveStatsEntry 6 }

dsxT3E3IfIetfArchiveStatsPCV OBJECT-TYPE
    SYNTAX      	Unsigned32
    MAX-ACCESS  	read-only
    STATUS      	current
    DESCRIPTION
     	"The number of IETF path coding violations,
	encountered by a T3/E3 interface that are reported 
      via the far-end block-error count."
                
    ::= { dsxT3E3IfIetfArchiveStatsEntry 7 }


dsxT3E3IfIetfArchiveStatsLES OBJECT-TYPE
    SYNTAX      	Unsigned32
    MAX-ACCESS  	read-only
    STATUS      	current
    DESCRIPTION
    	"The number of IETF line errored seconds
      encountered by a T3/E3 interface."
   ::= { dsxT3E3IfIetfArchiveStatsEntry 8 }

dsxT3E3IfIetfArchiveStatsCCV OBJECT-TYPE
    SYNTAX      	Unsigned32
    MAX-ACCESS  	read-only
    STATUS      	current
    DESCRIPTION
    	"The number of IETF C-bit parity code violations
	encountered by a T3/E3 interface."
   ::= { dsxT3E3IfIetfArchiveStatsEntry 9 }
    
dsxT3E3IfIetfArchiveStatsCES OBJECT-TYPE
    SYNTAX      	Unsigned32
    MAX-ACCESS  	read-only
    STATUS      	current
    DESCRIPTION
    	"The number of IETF C-bit parity errored seconds
	encountered by a T3/E3 interface."
   ::= { dsxT3E3IfIetfArchiveStatsEntry 10 }
    
dsxT3E3IfIetfArchiveStatsCSES OBJECT-TYPE
    SYNTAX      	Unsigned32
    MAX-ACCESS  	read-only
    STATUS      	current
    DESCRIPTION
    	"The number of IETF C-bit parity severrly errored 
	seconds encountered by a T3/E3 interface."
   ::= { dsxT3E3IfIetfArchiveStatsEntry 11 }    
   
-- USER Stats Group

-- USER Current Stats Table

dsxT3E3IfUserCurrentStatsTable OBJECT-TYPE
    SYNTAX      	SEQUENCE OF DsxT3E3IfUserCurrentStatsEntry
    MAX-ACCESS  	not-accessible
    STATUS      	current
    DESCRIPTION
    	"A list of T3/E3 interface user current 15-minute 
	interval statistics entries."
    ::= { dsxT3E3IfUserStatsGroup 1 }

dsxT3E3IfUserCurrentStatsEntry  OBJECT-TYPE
    SYNTAX      	DsxT3E3IfUserCurrentStatsEntry
    MAX-ACCESS  	not-accessible
    STATUS      	current
    DESCRIPTION
    	"An entry containing status entry for each currently active 
      T3/E3 interface."
    AUGMENTS 	{ dsxT3E3IfConfigLineEntry }
    ::= { dsxT3E3IfUserCurrentStatsTable 1 }

DsxT3E3IfUserCurrentStatsEntry ::=
    SEQUENCE {
        dsxT3E3IfUserCurrentStatsUASState        TruthValue,
        dsxT3E3IfUserCurrentStatsTimeInCurrent   Unsigned32,
        dsxT3E3IfUserCurrentStatsLCV             Unsigned32,
        dsxT3E3IfUserCurrentStatsFBE             Unsigned32,
        dsxT3E3IfUserCurrentStatsPBE             Unsigned32,
        dsxT3E3IfUserCurrentStatsCPBE            Unsigned32,
        dsxT3E3IfUserCurrentStatsFEBE            Unsigned32,
        dsxT3E3IfUserCurrentStatsEXZ             Unsigned32,
        dsxT3E3IfUserCurrentStatsCOFA            Unsigned32
    }
     
dsxT3E3IfUserCurrentStatsUASState OBJECT-TYPE
    SYNTAX      	TruthValue
    MAX-ACCESS  	read-only
    STATUS      	current
    DESCRIPTION
    	"The current status of availablity of the T3/E3 
	interface."
    ::= { dsxT3E3IfUserCurrentStatsEntry 1 }

dsxT3E3IfUserCurrentStatsTimeInCurrent OBJECT-TYPE
    SYNTAX      	Unsigned32
    MAX-ACCESS  	read-only
    STATUS      	current
    DESCRIPTION
   	"The number of seconds that have elapsed since
             the beginning of the current error-measurement
             period."
    ::= { dsxT3E3IfUserCurrentStatsEntry 2 }

dsxT3E3IfUserCurrentStatsLCV OBJECT-TYPE
    SYNTAX      	Unsigned32
    MAX-ACCESS  	read-only
    STATUS      	current
    DESCRIPTION
     	"The number of line code violations encountered
      by a T3/E3 interface."
    ::= { dsxT3E3IfUserCurrentStatsEntry 3 }

dsxT3E3IfUserCurrentStatsFBE OBJECT-TYPE
    SYNTAX      	Unsigned32
    MAX-ACCESS  	read-only
    STATUS      	current
    DESCRIPTION
    	"The number of frame bit errors encountered
      by a T3/E3 interface."
    ::= { dsxT3E3IfUserCurrentStatsEntry 4 }

dsxT3E3IfUserCurrentStatsPBE OBJECT-TYPE
    SYNTAX      	Unsigned32
    MAX-ACCESS  	read-only
    STATUS      	current
    DESCRIPTION
    	"The number of parity bit errors encountered
      by a T3/E3 interface."
    ::= { dsxT3E3IfUserCurrentStatsEntry 5 }

dsxT3E3IfUserCurrentStatsCPBE OBJECT-TYPE
    SYNTAX      	Unsigned32
    MAX-ACCESS  	read-only
    STATUS      	current
    DESCRIPTION
    	"The number of C-parity bit errors encountered
      by a T3/E3 interface."
    ::= { dsxT3E3IfUserCurrentStatsEntry 6 }

dsxT3E3IfUserCurrentStatsFEBE OBJECT-TYPE
    SYNTAX      	Unsigned32
    MAX-ACCESS  	read-only
    STATUS      	current
    DESCRIPTION
    	"The number of far end block errors encountered
      by a T3/E3 interface."
    ::= { dsxT3E3IfUserCurrentStatsEntry 7 }


dsxT3E3IfUserCurrentStatsEXZ OBJECT-TYPE
    SYNTAX      	Unsigned32
    MAX-ACCESS  	read-only
    STATUS      	current
    DESCRIPTION
    	"The number of excessive zeros encountered
      by a T3/E3 interface."
   ::= { dsxT3E3IfUserCurrentStatsEntry 8}

dsxT3E3IfUserCurrentStatsCOFA OBJECT-TYPE
    SYNTAX      	Unsigned32
    MAX-ACCESS  	read-only
    STATUS      	current
    DESCRIPTION
    	"The number of change of frame alignment
	encountered by a T3/E3 interface."
   ::= { dsxT3E3IfUserCurrentStatsEntry 9 }
    

-- USER total stats table.

dsxT3E3IfUserTotalStatsTable OBJECT-TYPE
    SYNTAX      	SEQUENCE OF DsxT3E3IfUserTotalStatsEntry
    MAX-ACCESS  	not-accessible
    STATUS      	current
    DESCRIPTION
   	"A list of entries for statistics collected 
	over 24-hours."
    ::= { dsxT3E3IfUserStatsGroup 2 }

dsxT3E3IfUserTotalStatsEntry  OBJECT-TYPE
    SYNTAX      	DsxT3E3IfUserTotalStatsEntry
    MAX-ACCESS  	not-accessible
    STATUS      	current
    DESCRIPTION
     	"An entry containing status entry for each currently active 
      T3/E3 interface."
    INDEX { dsxT3E3IfIndex, dsxT3E3IfUserTotalStatsDay }
    ::= { dsxT3E3IfUserTotalStatsTable 1 }

DsxT3E3IfUserTotalStatsEntry ::=
    SEQUENCE {
        dsxT3E3IfUserTotalStatsDay    Unsigned32, 
        dsxT3E3IfUserTotalStatsLCV    Unsigned32,
        dsxT3E3IfUserTotalStatsFBE    Unsigned32,
        dsxT3E3IfUserTotalStatsPBE    Unsigned32,
        dsxT3E3IfUserTotalStatsCPBE   Unsigned32,
        dsxT3E3IfUserTotalStatsFEBE   Unsigned32,
        dsxT3E3IfUserTotalStatsEXZ    Unsigned32,
        dsxT3E3IfUserTotalStatsCOFA   Unsigned32
    }
    
dsxT3E3IfUserTotalStatsDay OBJECT-TYPE
    SYNTAX      	Unsigned32
    MAX-ACCESS  	not-accessible
    STATUS      	current
    DESCRIPTION
    	"The total number of days for which statistics
      would be collected."
    ::= { dsxT3E3IfUserTotalStatsEntry 1 }
    
dsxT3E3IfUserTotalStatsLCV OBJECT-TYPE
    SYNTAX      	Unsigned32
    MAX-ACCESS  	read-only
    STATUS      	current
    DESCRIPTION
    	"Total number of line code violations encountered
      by a T3/E3 interface during past 24 hours."
    ::= { dsxT3E3IfUserTotalStatsEntry 2 }

dsxT3E3IfUserTotalStatsFBE OBJECT-TYPE
    SYNTAX      	Unsigned32
    MAX-ACCESS  	read-only
    STATUS      	current
    DESCRIPTION
    	"Total number of frame bit errors encountered
      by a T3/E3 interface during past 24 hours."
    ::= { dsxT3E3IfUserTotalStatsEntry 3 }

dsxT3E3IfUserTotalStatsPBE OBJECT-TYPE
    SYNTAX      	Unsigned32
    MAX-ACCESS  	read-only
    STATUS      	current
    DESCRIPTION
    	"Total number of parity bit errors encountered
      by a T3/E3 interface during past 24 hours."
    ::= { dsxT3E3IfUserTotalStatsEntry 4 }

dsxT3E3IfUserTotalStatsCPBE OBJECT-TYPE
    SYNTAX      	Unsigned32
    MAX-ACCESS  	read-only
    STATUS      	current
    DESCRIPTION
    	"Total number of C-bit parity bit errors
	encountered by a T3/E3 interface during 
	past 24 hours."
    ::= { dsxT3E3IfUserTotalStatsEntry 5 }

dsxT3E3IfUserTotalStatsFEBE OBJECT-TYPE
    SYNTAX      	Unsigned32
    MAX-ACCESS  	read-only
    STATUS      	current
    DESCRIPTION
     	"Total number of far end block errors 
	encountered by a T3/E3 interface during past 24 hours."
    ::= { dsxT3E3IfUserTotalStatsEntry 6 }

dsxT3E3IfUserTotalStatsEXZ OBJECT-TYPE
    SYNTAX      	Unsigned32
    MAX-ACCESS  	read-only
    STATUS      	current
    DESCRIPTION
    	"Total number of excessive zeros encountered
      by a T3/E3 interface during past 24 hours."
    ::= { dsxT3E3IfUserTotalStatsEntry 7 }


dsxT3E3IfUserTotalStatsCOFA OBJECT-TYPE
    SYNTAX      	Unsigned32
    MAX-ACCESS  	read-only
    STATUS      	current
    DESCRIPTION
     	"Total number of change of frame alignment
	encountered by a T3/E3 interface during past 
	24 hours."
   ::= { dsxT3E3IfUserTotalStatsEntry 8 }
 
-- User lifetime stats table.
 
dsxT3E3IfUserLifetimeStatsTable OBJECT-TYPE
     SYNTAX      	SEQUENCE OF DsxT3E3IfUserLifetimeStatsEntry
     MAX-ACCESS  	not-accessible
     STATUS      	current
    DESCRIPTION
   	"A list of T3/E3 interface statistics entries 
	collected since the system was powered on."
    ::= { dsxT3E3IfUserStatsGroup 3 }

dsxT3E3IfUserLifetimeStatsEntry  OBJECT-TYPE
    SYNTAX      	DsxT3E3IfUserLifetimeStatsEntry
    MAX-ACCESS  	not-accessible
    STATUS      	current
    DESCRIPTION
    	"An entry containing status entry for each currently active 
      T3/E3 interface."
    AUGMENTS { dsxT3E3IfConfigLineEntry }
    ::= { dsxT3E3IfUserLifetimeStatsTable 1 }

DsxT3E3IfUserLifetimeStatsEntry ::=
    SEQUENCE {
        dsxT3E3IfUserLifetimeStatsPES    Unsigned32,
        dsxT3E3IfUserLifetimeStatsPSES   Unsigned32,
        dsxT3E3IfUserLifetimeStatsSEFS   Unsigned32,
        dsxT3E3IfUserLifetimeStatsUAS    Unsigned32,
        dsxT3E3IfUserLifetimeStatsLCV    Unsigned32,
        dsxT3E3IfUserLifetimeStatsPCV    Unsigned32,
        dsxT3E3IfUserLifetimeStatsLES    Unsigned32,
        dsxT3E3IfUserLifetimeStatsCCV    Unsigned32,
        dsxT3E3IfUserLifetimeStatsCES    Unsigned32,
        dsxT3E3IfUserLifetimeStatsFBE    Unsigned32,        
        dsxT3E3IfUserLifetimeStatsPBE    Unsigned32,        
        dsxT3E3IfUserLifetimeStatsCPBE   Unsigned32,        
        dsxT3E3IfUserLifetimeStatsFEBE   Unsigned32,        
        dsxT3E3IfUserLifetimeStatsEXZ    Unsigned32,        
        dsxT3E3IfUserLifetimeStatsCOFA   Unsigned32
    }
    
dsxT3E3IfUserLifetimeStatsPES OBJECT-TYPE
    SYNTAX      	Unsigned32
    MAX-ACCESS  	read-only
    STATUS      	current
    DESCRIPTION
    	"Total number of parity errored seconds encountered
      by a T3/E3 interface since the interface came up."
    ::= { dsxT3E3IfUserLifetimeStatsEntry 1 }

dsxT3E3IfUserLifetimeStatsPSES OBJECT-TYPE
    SYNTAX      	Unsigned32
    MAX-ACCESS  	read-only
    STATUS      	current
    DESCRIPTION
    	"Total number of parity severe errored seconds
	encountered by a T3/E3 interface since the 
	interface came up."
    ::= { dsxT3E3IfUserLifetimeStatsEntry 2 }

dsxT3E3IfUserLifetimeStatsSEFS OBJECT-TYPE
    SYNTAX      	Unsigned32
    MAX-ACCESS  	read-only
    STATUS      	current
    DESCRIPTION
    	"Total number of severly errored frame seconds
	encountered by a T3/E3 interface since the 
	interface came up."
    ::= { dsxT3E3IfUserLifetimeStatsEntry 3 }

dsxT3E3IfUserLifetimeStatsUAS OBJECT-TYPE
    SYNTAX      	Unsigned32
    MAX-ACCESS  	read-only
    STATUS      	current
    DESCRIPTION
    	"Total number of unavailable seconds encountered
      by a T3/E3 interface since the interface came up."
    ::= { dsxT3E3IfUserLifetimeStatsEntry 4 }

dsxT3E3IfUserLifetimeStatsLCV OBJECT-TYPE
    SYNTAX      	Unsigned32
    MAX-ACCESS  	read-only
    STATUS      	current
    DESCRIPTION
    	"Total number of line code violations encountered
      by a T3/E3 interface since the interface came up."
    ::= { dsxT3E3IfUserLifetimeStatsEntry 5 }

dsxT3E3IfUserLifetimeStatsPCV OBJECT-TYPE
    SYNTAX      	Unsigned32
    MAX-ACCESS  	read-only
    STATUS      	current
    DESCRIPTION
    	"Total number of path code violations encountered
      by a T3/E3 interface since the interface came up."
    ::= { dsxT3E3IfUserLifetimeStatsEntry 6 }


dsxT3E3IfUserLifetimeStatsLES OBJECT-TYPE
    SYNTAX      	Unsigned32
    MAX-ACCESS  	read-only
    STATUS      	current
    DESCRIPTION
    	"Total number of line errored seconds encountered
      by a T3/E3 interface since the interface came up."
   ::= { dsxT3E3IfUserLifetimeStatsEntry 7}

dsxT3E3IfUserLifetimeStatsCCV OBJECT-TYPE
    SYNTAX      	Unsigned32
    MAX-ACCESS  	read-only
    STATUS      	current
    DESCRIPTION
    	"Total number of C-bit code violations encountered
      by a T3/E3 interface since the interface came up."
   ::= { dsxT3E3IfUserLifetimeStatsEntry 8 }
    
dsxT3E3IfUserLifetimeStatsCES OBJECT-TYPE
    SYNTAX      	Unsigned32
    MAX-ACCESS  	read-only
    STATUS      	current
    DESCRIPTION
    	"Total number of C-bit errored seconds encountered
      by a T3/E3 interface since the interface came up."
   ::= { dsxT3E3IfUserLifetimeStatsEntry 9 }
    
dsxT3E3IfUserLifetimeStatsFBE OBJECT-TYPE
    SYNTAX      	Unsigned32
    MAX-ACCESS  	read-only
    STATUS      	current
    DESCRIPTION
    	"Total number of frame bit errors encountered
      by a T3/E3 interface since the interface came up."
   ::= { dsxT3E3IfUserLifetimeStatsEntry 10 } 

dsxT3E3IfUserLifetimeStatsPBE OBJECT-TYPE
    SYNTAX      	Unsigned32
    MAX-ACCESS  	read-only
    STATUS      	current
    DESCRIPTION
    "Total number of parity bit errors encountered
    by a T3/E3 interface since the interface came up."
   ::= { dsxT3E3IfUserLifetimeStatsEntry 11 }    
   
dsxT3E3IfUserLifetimeStatsCPBE OBJECT-TYPE
    SYNTAX      	Unsigned32
    MAX-ACCESS  	read-only
    STATUS      	current
    DESCRIPTION
    	"Total number of C-bit parity errors encountered
	by a T3/E3 interface since the interface came up."
   ::= { dsxT3E3IfUserLifetimeStatsEntry 12 }    
   
dsxT3E3IfUserLifetimeStatsFEBE OBJECT-TYPE
    SYNTAX      	Unsigned32
    MAX-ACCESS  	read-only
    STATUS      	current
    DESCRIPTION
    	"Total number of far end block errors encountered
      by a T3/E3 interface since the interface came up."
   ::= { dsxT3E3IfUserLifetimeStatsEntry 13 }    
   
dsxT3E3IfUserLifetimeStatsEXZ OBJECT-TYPE
    SYNTAX      	Unsigned32
    MAX-ACCESS  	read-only
    STATUS      	current
    DESCRIPTION
     	"Total number of excessive zeros encountered
      by a T3/E3 interface since the interface came up."
   ::= { dsxT3E3IfUserLifetimeStatsEntry 14 }    
   
dsxT3E3IfUserLifetimeStatsCOFA OBJECT-TYPE
    SYNTAX      	Unsigned32
    MAX-ACCESS  	read-only
    STATUS      	current
    DESCRIPTION
    	"Total number of frame alignment changes
	encountered by a T3/E3 interface since the 
	interface came up."
   ::= { dsxT3E3IfUserLifetimeStatsEntry 15 }    
   
-- USER archive stats table.

dsxT3E3IfUserArchiveStatsTable OBJECT-TYPE
    SYNTAX      	SEQUENCE OF DsxT3E3IfUserArchiveStatsEntry
    MAX-ACCESS  	not-accessible
    STATUS      	current
    DESCRIPTION
    	"A list of T3/E3 interface user archive statistics 
	entries."
    ::= { dsxT3E3IfUserStatsGroup 4 }

dsxT3E3IfUserArchiveStatsEntry  OBJECT-TYPE
    SYNTAX      	DsxT3E3IfUserArchiveStatsEntry
    MAX-ACCESS  	not-accessible
    STATUS      	current
    DESCRIPTION
    	"An entry containing a status entry for each 
	currently active T3/E3 interface."
    INDEX { dsxT3E3IfIndex, dsxT3E3IfUserArchiveStatsInterval }
    ::= { dsxT3E3IfUserArchiveStatsTable 1 }

DsxT3E3IfUserArchiveStatsEntry ::=
    SEQUENCE {
        dsxT3E3IfUserArchiveStatsInterval  Unsigned32, 
        dsxT3E3IfUserArchiveStatsLCV       Unsigned32,
        dsxT3E3IfUserArchiveStatsFBE       Unsigned32,
        dsxT3E3IfUserArchiveStatsPBE       Unsigned32,
        dsxT3E3IfUserArchiveStatsCPBE      Unsigned32,
        dsxT3E3IfUserArchiveStatsFEBE      Unsigned32,
        dsxT3E3IfUserArchiveStatsEXZ       Unsigned32,
        dsxT3E3IfUserArchiveStatsCOFA      Unsigned32   
    }
    
dsxT3E3IfUserArchiveStatsInterval OBJECT-TYPE
    SYNTAX      	Unsigned32
    MAX-ACCESS  	not-accessible
    STATUS      	current
    DESCRIPTION
   	"The total number of intervals for which statistics
      would be collected."
    ::= { dsxT3E3IfUserArchiveStatsEntry 1 }
    
dsxT3E3IfUserArchiveStatsLCV OBJECT-TYPE
    SYNTAX      	Unsigned32
    MAX-ACCESS  	read-only
    STATUS      	current
    DESCRIPTION
    	"The number of line code violations encountered
      by a T3/E3 interface."
    ::= { dsxT3E3IfUserArchiveStatsEntry 2 }

dsxT3E3IfUserArchiveStatsFBE OBJECT-TYPE
    SYNTAX      	Unsigned32
    MAX-ACCESS  	read-only
    STATUS      	current
    DESCRIPTION
    	"The number of frame bit errors encountered
      by  a T3/E3 interface."
    ::= { dsxT3E3IfUserArchiveStatsEntry 3 }

dsxT3E3IfUserArchiveStatsPBE OBJECT-TYPE
    SYNTAX      	Unsigned32
    MAX-ACCESS  	read-only
    STATUS      	current
    DESCRIPTION
    	"The number of parity bit errors encountered
      by  a T3/E3 interface."
    ::= { dsxT3E3IfUserArchiveStatsEntry 4 }

dsxT3E3IfUserArchiveStatsCPBE OBJECT-TYPE
    SYNTAX      	Unsigned32
    MAX-ACCESS  	read-only
    STATUS      	current
    DESCRIPTION
    	"The number of C parity bit errors encountered
      by a T3/E3 interface."
    ::= { dsxT3E3IfUserArchiveStatsEntry 5 }

dsxT3E3IfUserArchiveStatsFEBE OBJECT-TYPE
    SYNTAX      	Unsigned32
    MAX-ACCESS  	read-only
    STATUS      	current
    DESCRIPTION
    	"The number of far end block errors encountered
      by a T3/E3 interface."
    ::= { dsxT3E3IfUserArchiveStatsEntry 6 }

dsxT3E3IfUserArchiveStatsEXZ OBJECT-TYPE
    SYNTAX      	Unsigned32
    MAX-ACCESS  	read-only
    STATUS      	current
    DESCRIPTION
     	"The number of exessive zero errors encountered
      by a T3/E3 interface."
    ::= { dsxT3E3IfUserArchiveStatsEntry 7 }


dsxT3E3IfUserArchiveStatsCOFA OBJECT-TYPE
    SYNTAX      	Unsigned32
    MAX-ACCESS  	read-only
    STATUS      	current
    DESCRIPTION
    	"The number of change of frame alignment encountered
      by a T3/E3 interface."
   ::= { dsxT3E3IfUserArchiveStatsEntry 8 }

-- TRAP definition and related TRAP variable definitions for T3E3 Interface.
--
--

dsxT3E3Number   	OBJECT-TYPE
    SYNTAX  	INTEGER
    MAX-ACCESS  	not-accessible
    STATUS  	current
    DESCRIPTION
     	"This variable indicates the T3/E3 interface number from 
      where this alarm originated."
    ::= { dsxT3E3TrapVariables 1}

dsxT3E3AlarmType	OBJECT-TYPE
    SYNTAX  	INTEGER {
                	te3-alarm-rais (1),
                	te3-alarm-roof (2),
                	te3-alarm-rrai (3),
                	te3-alarm-ris  (4),
                	te3-alarm-rlos (5),
                	te3-alarm-rlof (6),
                	te3-alarm-rexz (7),
                	te3-alarm-rfebe (8),
                	te3-alarm-rpe  (9),
                	te3-alarm-rcpe (10),
                	te3-alarm-lorc (11),
                	te3-alarm-tpde (12),
                	te3-alarm-tais (13),
                	te3-alarm-trai (14),
                	te3-alarm-tfebe (15),
                	te1-alarm-threshold1 (16),
                	te1-alarm-threshold2 (17),
                	te1-alarm-threshold3 (18),
                	te1-alarm-threshold4 (19),
                	te1-alarm-threshold5 (20),
                	te1-alarm-threshold6 (21),
                	te1-alarm-threshold7 (22),
                	te1-alarm-threshold8 (23),
                	te1-alarm-threshold9 (24),
                	te1-alarm-threshold10 (25)

                	}
    MAX-ACCESS  	not-accessible
    STATUS  	current
    DESCRIPTION
    	"Alarm status T3/E3 interface
                  RRAI            - Recieve Receive Alarm Indication,
                  TRAI            - Transmit Receive Alarm Indication,
                  TAIS            - Transmit Alarm Indication Siganl,
                  RLOF            - Recieve Loss Of Frame,
                  RLOS            - Recieve Loss Of Sync,
                  Loopback        - Status of Loop back,
                  rcvTestCode     - Receive Test Code,
                  rblu            - Receive Blue Alarm,
                  RIS             - Receive Idle Signal,
                  REXZ            - Receive Excessive Zeros,
                  RFBE            - Receive Frame Bit Error,
                  RPE             - Receive Parity Error,
                  RCPE            - Receive C-Parity Error,
                  LORC            - Loss Of Receive Clock (LORC),
                  TPDE            - transmit pulse density,
                  RAIS            - Recieve Alarm Indication Signal,
                  TFEBE           - Transmit Far End Block Alarm,
                  Threshold 1-10  - TRUE if it is configured.
                                "
    ::= { dsxT3E3TrapVariables 2}

dsxT3E3AlarmOnTrap TRAP-TYPE
    ENTERPRISE dsxT3E3Traps
    VARIABLES {
                dsxT3E3IfIndex,
                dsxT3E3Number,
                dsxT3E3AlarmType }

    DESCRIPTION
  	"T3/E3 interface alarm trap for Alarm On state."
             --#TYPE "T3/E3 Alarm On state"
             --#SUMMARY "T3/E3 Alarm On trap sent from Interface index: %s T3/E3 number: %s with the Alarm type: %s"
             --#ARGUMENTS {0,1,2}
             --#SEVERITY MAJOR
    ::= 1

dsxT3E3AlarmOffTrap TRAP-TYPE
    ENTERPRISE dsxT3E3Traps
    VARIABLES {
                dsxT3E3IfIndex,
                dsxT3E3Number,
                dsxT3E3AlarmType }
                    
    DESCRIPTION
    	"T3/E3 interface alarm trap for Alarm Off state."
             --#TYPE "T3/E3 Alarm Off state"
             --#SUMMARY "T3/E3 Alarm Off trap sent from Interface index: %s T3/E3 number: %s with the Alarm type: %s"
             --#ARGUMENTS {0,1,2}
             --#SEVERITY NORMAL
    ::= 2


END
