--	3Com Switching Systems Management Information Base
--	Version 1.0.0
--	February 13, 1998
 
--	3Com Corporation
--	80 Central Street
--	Boxborough, MA 01719
--	(508) 264-1400
 
----------------------------------------------------------------------------------------
--  04/27/99 - tmeiczin   Broke apart from 3cSys.mib
----------------------------------------------------------------------------------------
 
A3COM-SWITCHING-SYSTEMS-SMT-MIB DEFINITIONS ::= BEGIN
 
IMPORTS
	enterprises, Counter, IpAddress
		 FROM RFC1155-SMI
	DisplayString
                 FROM RFC1213-MIB
	OBJECT-TYPE
                 FROM RFC-1212;

-- 
-- Object identifiers 
-- 
 
a3Com                               OBJECT IDENTIFIER ::= { enterprises 43 } 
switchingSystemsMibs                OBJECT IDENTIFIER ::= { a3Com 29 } 
a3ComSwitchingSystemsMib            OBJECT IDENTIFIER ::= { switchingSystemsMibs 4 } 
 
-- a3ComSwitchingSystemsMib groups. 
a3ComSysSmt                         OBJECT IDENTIFIER ::= { a3ComSwitchingSystemsMib 9 } 
 
-- The Switching Systems MIB SMT group.  Implementation of this group is 
-- mandatory for agents which manage SMT resources. 
 
a3ComSysSmtCount  OBJECT-TYPE 
    SYNTAX  INTEGER 
    ACCESS  read-only 
    STATUS  mandatory 
    DESCRIPTION   
            "The count of SMTs managed by this agent." 
::= { a3ComSysSmt 1 } 
 
-- The Switching Systems MIB SMT table. 
-- This table is currently unused and is reserved for future use. 
-- { a3ComSysSmt 2 } 
 
-- The Switching Systems MIB SMT FDDI MAC table. 
-- This table is currently unused and is reserved for future use. 
-- { a3ComSysSmt 3 } 

-- a3ComSysSmtFddiMacBeaconTable OBJECT-TYPE
-- Currently not supported.
-- ::= { a3ComSysSmt 4 }
   
-- The Switching Systems MIB SMT FDDI MAC rate table. 
 
a3ComSysSmtFddiMacRateTable  OBJECT-TYPE 
    SYNTAX  SEQUENCE OF A3ComSysSmtFddiMacRateEntry 
    ACCESS  not-accessible 
    STATUS  mandatory 
    DESCRIPTION   
            "A list of FDDI MAC rate entries.  A single entry exists 
            in this list for each FDDI MAC, managed by this agent, 
            which supports rate statistics." 
::= { a3ComSysSmt 5 } 
 
a3ComSysSmtFddiMacRateEntry  OBJECT-TYPE 
    SYNTAX  A3ComSysSmtFddiMacRateEntry 
    ACCESS  not-accessible 
    STATUS  mandatory 
    DESCRIPTION   
            "An FDDI MAC rate entry contains rate statistics for a 
            particular FDDI MAC managed by this agent.  Rate statistics 
            are calculated based on a one second sampling interval." 
    INDEX  { a3ComSysSmtFddiMacRateSmtIndex, 
            a3ComSysSmtFddiMacRateIndex } 
::= { a3ComSysSmtFddiMacRateTable 1 } 
 
A3ComSysSmtFddiMacRateEntry ::= 
    SEQUENCE { 
		a3ComSysSmtFddiMacRateSmtIndex 
			INTEGER, 
		a3ComSysSmtFddiMacRateIndex 
			INTEGER, 
		a3ComSysSmtFddiMacRateByteReceiveRate 
			INTEGER, 
		a3ComSysSmtFddiMacRatePeakByteReceiveRate 
			INTEGER, 
		a3ComSysSmtFddiMacRateFrameReceiveRate 
			INTEGER, 
		a3ComSysSmtFddiMacRatePeakFrameReceiveRate 
			INTEGER, 
		a3ComSysSmtFddiMacRateByteTransmitRate 
			INTEGER, 
		a3ComSysSmtFddiMacRatePeakByteTransmitRate 
			INTEGER, 
		a3ComSysSmtFddiMacRateFrameTransmitRate 
			INTEGER, 
		a3ComSysSmtFddiMacRatePeakFrameTransmitRate 
			INTEGER 
	} 
 
a3ComSysSmtFddiMacRateSmtIndex  OBJECT-TYPE 
    SYNTAX  INTEGER (1..65535) 
    ACCESS  read-only 
    STATUS  mandatory 
    DESCRIPTION   
            "The index of the SMT instance identified by this entry, 
            relative to this agent." 
::= { a3ComSysSmtFddiMacRateEntry 1 } 
 
a3ComSysSmtFddiMacRateIndex  OBJECT-TYPE 
    SYNTAX  INTEGER (1..65535) 
    ACCESS  read-only 
    STATUS  mandatory 
    DESCRIPTION   
            "The index of the FDDI MAC identified by this entry, within 
            the SMT identified by this entry." 
::= { a3ComSysSmtFddiMacRateEntry 2 } 
 
a3ComSysSmtFddiMacRateByteReceiveRate  OBJECT-TYPE 
    SYNTAX  INTEGER 
    ACCESS  read-only 
    STATUS  mandatory 
    DESCRIPTION   
            "The average number of bytes received per second by the 
            FDDI MAC identified by this entry during the most recent 
            sampling period." 
::= { a3ComSysSmtFddiMacRateEntry 3 } 
 
a3ComSysSmtFddiMacRatePeakByteReceiveRate  OBJECT-TYPE 
    SYNTAX  INTEGER 
    ACCESS  read-only 
    STATUS  mandatory 
    DESCRIPTION   
            "The peak value of a3ComSysSmtFddiMacByteReceiveRate since the 
            system was last initialized for the FDDI MAC identified by 
            this entry." 
::= { a3ComSysSmtFddiMacRateEntry 4 } 
 
a3ComSysSmtFddiMacRateFrameReceiveRate  OBJECT-TYPE 
    SYNTAX  INTEGER 
    ACCESS  read-only 
    STATUS  mandatory 
    DESCRIPTION   
            "The average number of frames received per second by the 
            FDDI MAC identified by this entry during the most recent 
            sampling period." 
::= { a3ComSysSmtFddiMacRateEntry 5 } 
 
a3ComSysSmtFddiMacRatePeakFrameReceiveRate  OBJECT-TYPE 
    SYNTAX  INTEGER 
    ACCESS  read-only 
    STATUS  mandatory 
    DESCRIPTION   
            "The peak value of a3ComSysSmtFddiMacRateFrameReceiveRate since 
            the system was last initialized for the FDDI MAC identified 
            by this entry." 
::= { a3ComSysSmtFddiMacRateEntry 6 } 
 
a3ComSysSmtFddiMacRateByteTransmitRate  OBJECT-TYPE 
    SYNTAX  INTEGER 
    ACCESS  read-only 
    STATUS  mandatory 
    DESCRIPTION   
            "The average number of bytes transmitted per second by the 
            FDDI MAC identified by this entry during the most recent 
            sampling period." 
::= { a3ComSysSmtFddiMacRateEntry 7 } 
 
a3ComSysSmtFddiMacRatePeakByteTransmitRate  OBJECT-TYPE 
    SYNTAX  INTEGER 
    ACCESS  read-only 
    STATUS  mandatory 
    DESCRIPTION   
            "The peak value of a3ComSysSmtFddiMacByteTransmitRate since the 
            system was last initialized for the FDDI MAC identified by 
            this entry." 
::= { a3ComSysSmtFddiMacRateEntry 8 } 
 
a3ComSysSmtFddiMacRateFrameTransmitRate  OBJECT-TYPE 
    SYNTAX  INTEGER 
    ACCESS  read-only 
    STATUS  mandatory 
    DESCRIPTION   
            "The average number of frames transmitted per second by 
            the FDDI MAC identified by this entry during the most 
            recent sampling period." 
::= { a3ComSysSmtFddiMacRateEntry 9 } 
 
a3ComSysSmtFddiMacRatePeakFrameTransmitRate  OBJECT-TYPE 
    SYNTAX  INTEGER 
    ACCESS  read-only 
    STATUS  mandatory 
    DESCRIPTION   
            "The peak value of a3ComSysSmtFddiMacFrameTransmitRate since the 
            system was last initialized for the FDDI MAC identified by 
            this entry." 
::= { a3ComSysSmtFddiMacRateEntry 10 } 
 
-- The Switching Systems MIB SMT FDDI port table. 
 
a3ComSysSmtFddiPortTable  OBJECT-TYPE 
    SYNTAX  SEQUENCE OF A3ComSysSmtFddiPortEntry 
    ACCESS  not-accessible 
    STATUS  mandatory 
    DESCRIPTION   
            "A list of FDDI port entries.  A single entry exists in 
            this list for each FDDI port managed by this agent." 
::= { a3ComSysSmt 6 } 
 
a3ComSysSmtFddiPortEntry  OBJECT-TYPE 
    SYNTAX  A3ComSysSmtFddiPortEntry 
    ACCESS  not-accessible 
    STATUS  mandatory 
    DESCRIPTION   
            "An FDDI port entry contains information about a particular 
            FDDI port managed by this agent." 
    INDEX  { a3ComSysSmtFddiPortSmtIndex, 
            a3ComSysSmtFddiPortIndex } 
::= { a3ComSysSmtFddiPortTable 1 } 
 
A3ComSysSmtFddiPortEntry ::= 
    SEQUENCE { 
		a3ComSysSmtFddiPortSmtIndex 
			INTEGER, 
		a3ComSysSmtFddiPortIndex 
			INTEGER, 
		a3ComSysSmtFddiPortLocationType 
			INTEGER, 
		a3ComSysSmtFddiPortLocationTypeIndex 
			INTEGER, 
		a3ComSysSmtFddiPortLocationLocalIndex 
			INTEGER, 
		a3ComSysSmtFddiPortLabel 
			DisplayString,
                a3ComSysSmtFddiPortSystemPhysicalConnectorId
                        INTEGER 
	} 
 
a3ComSysSmtFddiPortSmtIndex  OBJECT-TYPE 
    SYNTAX  INTEGER (1..65535) 
    ACCESS  read-only 
    STATUS  mandatory 
    DESCRIPTION   
            "The index of the SMT instance identified by this entry, 
            relative to this agent." 
::= { a3ComSysSmtFddiPortEntry 1 } 
 
a3ComSysSmtFddiPortIndex  OBJECT-TYPE 
    SYNTAX  INTEGER (1..65535) 
    ACCESS  read-only 
    STATUS  mandatory 
    DESCRIPTION   
            "The index of the FDDI port identified by this entry, 
            within the SMT identified by this entry." 
::= { a3ComSysSmtFddiPortEntry 2 } 
 
a3ComSysSmtFddiPortLocationType  OBJECT-TYPE 
    SYNTAX  INTEGER { 
              other(1), 
              modularSlot(2), 
              chassis(3), 
              modularCard(4) 
            } 
    ACCESS  read-only 
    STATUS  mandatory 
    DESCRIPTION   
            "The type of location where the FDDI port identified by 
            this entry is physically located." 
::= { a3ComSysSmtFddiPortEntry 3 } 
 
a3ComSysSmtFddiPortLocationTypeIndex  OBJECT-TYPE 
    SYNTAX  INTEGER 
    ACCESS  read-only 
    STATUS  mandatory 
    DESCRIPTION   
            "The index of the location identified by the corresponding 
            instance of a3ComSysSmtFddiPortLocationType where the FDDI port 
            identified by this entry is physically located." 
::= { a3ComSysSmtFddiPortEntry 4 } 
 
a3ComSysSmtFddiPortLocationLocalIndex  OBJECT-TYPE 
    SYNTAX  INTEGER 
    ACCESS  read-only 
    STATUS  mandatory 
    DESCRIPTION   
            "The local index of the FDDI port identified by this 
            entry relative to the location specified by the 
            corresponding values of a3ComSysSmtFddiPortLocationType and 
            a3ComSysSmtFddiPortLocationTypeIndex." 
::= { a3ComSysSmtFddiPortEntry 5 } 
 
a3ComSysSmtFddiPortLabel  OBJECT-TYPE 
    SYNTAX  DisplayString (SIZE (0..31)) 
    ACCESS  read-write 
    STATUS  mandatory 
    DESCRIPTION   
            "An ASCII text string describing the FDDI port identified 
            by this entry." 
::= { a3ComSysSmtFddiPortEntry 6 } 
 
a3ComSysSmtFddiPortSystemPhysicalConnectorId OBJECT-TYPE
    SYNTAX INTEGER
    ACCESS read-only
    STATUS mandatory
    DESCRIPTION
            "The actual physical connector that corresponds to the values
            of a3ComSysSmtFddiPortLocationType a3ComSysSmtFddiPortLocationTypeIndex
            a3ComSysSmtFddiPortLocationLocalIndex."
::= { a3ComSysSmtFddiPortEntry 7 } 

-- a3ComSysSmtFddiMacLocationTable OBJECT-TYPE
-- Currently reserved for future use.
-- ::= { a3ComSysSmt 7 }


-- a3ComSysSmtFddiMacStationTable OBJECT-TYPE
-- Currently reserved for future use.
-- ::= { a3ComSysSmt 8 }


-- a3ComSysSmtFddiPortStationTable OBJECT-TYPE
-- Currently reserved for future use.
-- ::= { a3ComSysSmt 9 }

-- the a3ComSysSmtFddiStationModeTable

a3ComSysSmtFddiStationModeTable OBJECT-TYPE
    SYNTAX  SEQUENCE OF A3ComSysSmtFddiStationModeEntry
    ACCESS  not-accessible
    STATUS  mandatory
    DESCRIPTION
            "An FDDI station Mode table contains information to assign
             an FDDI Station to DAS(dual attached) or SAS(single attached) mode.  
             The system must be rebooted after all changes to this table are completed 
             in order that the changes take effect. "
::= { a3ComSysSmt 10 }

a3ComSysSmtFddiStationModeEntry OBJECT-TYPE
    SYNTAX  A3ComSysSmtFddiStationModeEntry
    ACCESS  not-accessible
    STATUS  mandatory
    DESCRIPTION
            "An FDDI Port entry contains information to assign
             an FDDI Port to an FDDI Station "
    INDEX   { a3ComSysSmtFddiStationModeIndex,
              a3ComSysSmtFddiStationModePortIndex }
::= { a3ComSysSmtFddiStationModeTable 1 }

A3ComSysSmtFddiStationModeEntry ::=
    SEQUENCE {
                a3ComSysSmtFddiStationModeIndex
                        INTEGER,
                a3ComSysSmtFddiStationModePortIndex
                        INTEGER,
                a3ComSysSmtFddiStationModeSelectablePorts
                        INTEGER,
                a3ComSysSmtFddiStationModeCurrentMode
                        INTEGER,
                a3ComSysSmtFddiStationModeRequestedMode
                        INTEGER 
              }

a3ComSysSmtFddiStationModeIndex OBJECT-TYPE
    SYNTAX  INTEGER
    ACCESS  read-only
    STATUS  mandatory
    DESCRIPTION
            "The index of the SMT instance identified by this entry,
            relative to this agent "
::= { a3ComSysSmtFddiStationModeEntry 1 }
 
a3ComSysSmtFddiStationModePortIndex OBJECT-TYPE
    SYNTAX  INTEGER 
    ACCESS  read-only
    STATUS  mandatory
    DESCRIPTION
                "The index of the Port instance identified by this entry,
                relative to the SMT indentified by this entry."
::= { a3ComSysSmtFddiStationModeEntry 2 }

a3ComSysSmtFddiStationModeSelectablePorts OBJECT-TYPE
    SYNTAX  INTEGER (1..65535)
    ACCESS  read-only
    STATUS  mandatory
    DESCRIPTION
            "An implementation specific entry that corresponds to a port pair,
            based on the hardware implementation. Only ports with a value of 1
            are configurable, those with a value of 0 are not."
::= { a3ComSysSmtFddiStationModeEntry 3 }

a3ComSysSmtFddiStationModeCurrentMode OBJECT-TYPE
	SYNTAX	INTEGER {
				sas-m(1),
				sas-s(2),
				das(3)
				}
    ACCESS  read-only
    STATUS  mandatory
    DESCRIPTION
            "Indicates the current SAS or DAS mode of the port(s) instance
             relative to the SMT instance. A value of 1 indicates SAS(M).
             A value of 2 indicates SAS(S) and a value of 3 indicates DAS."
::= { a3ComSysSmtFddiStationModeEntry 4 }
                
a3ComSysSmtFddiStationModeRequestedMode OBJECT-TYPE
	SYNTAX	INTEGER {
				sas-m(1),
				sas-s(2),
				das(3)
				}
    ACCESS  read-write
    STATUS  mandatory
    DESCRIPTION
            "Indicates the requested mode for a given port pair. A value
            of 1 indicates a request for SAS(M) for the corresponding pair.
            A value of 2 indicates SAS(S) and a value of 3 indicates DAS.
            It should be noted that if requested mode is different than
            current mode a reboot is required to enable the requested mode.
            NOTE: reboot can be accomplished using a3ComSysSystemAction."
::= { a3ComSysSmtFddiStationModeEntry 5 }
 
END
