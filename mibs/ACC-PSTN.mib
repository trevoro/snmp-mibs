ACC-PSTN DEFINITIONS ::= BEGIN

    IMPORTS
	 OBJECT-TYPE, IpAddress, TimeTicks, Gauge, Counter FROM RFC1155-SMI
	 TRAP-TYPE FROM RFC-1215
	 ifIndex FROM RFC1213-MIB
        accTrapLogSeqNum FROM ACC-SYSTEM
 accBRG, DisplayString FROM ACC-MIB;

-- PSTN Group
accPstn OBJECT IDENTIFIER  ::= { accBRG 69 }
	accPstnSubTable OBJECT-TYPE
		SYNTAX SEQUENCE OF AccPstnSubTabEntry
		ACCESS not-accessible
		STATUS mandatory
		DESCRIPTION "Table of PSTN subscriber entry parameters."
		::= { accPstn 1 }
	accPstnSubTabEntry OBJECT-TYPE
		SYNTAX AccPstnSubTabEntry
		ACCESS not-accessible
		STATUS mandatory
		DESCRIPTION "PSTN subscriber entry-table parameters."
		INDEX{ oPstnSubTabDslIndex }
		::= { accPstnSubTable 1 }
	AccPstnSubTabEntry ::= SEQUENCE {
		oPstnSubTabDslIndex	INTEGER,
		oPstnSubTabSigSystem	INTEGER,
		oPstnSubTabNumChannels	INTEGER,
		oPstnSubTabAdminStatus	INTEGER,
		oPstnSubTabOperStatus	INTEGER,
		oPstnSubTabMsgLevel	INTEGER,
		oPstnSubTabLastCause	INTEGER,
		oPstnSubTabNumberGroup	INTEGER
		}
	oPstnSubTabDslIndex OBJECT-TYPE
		SYNTAX INTEGER
		ACCESS read-only
		STATUS mandatory
		DESCRIPTION "PSTN Subscriber Table Index."
		::= { accPstnSubTabEntry 1 }
	oPstnSubTabSigSystem OBJECT-TYPE
		SYNTAX INTEGER {
			rbs (1),
			p7  (2),
			r2  (3)	
			}
		ACCESS read-write
		STATUS mandatory
		DESCRIPTION "PSTN signaling system.  Either RBS, P7 or R2. "
		::= { accPstnSubTabEntry 2 }
	oPstnSubTabNumChannels OBJECT-TYPE
		SYNTAX INTEGER
		ACCESS read-write
		STATUS mandatory
		DESCRIPTION "PSTN subscriber table - number of channels."
                ::= { accPstnSubTabEntry 3 }
	oPstnSubTabAdminStatus OBJECT-TYPE
                SYNTAX INTEGER {
			enabled (1),
			disabled (2),
			drained (3)
			}
                ACCESS read-write
                STATUS mandatory
                DESCRIPTION "Administration status of PSTN."
                ::= { accPstnSubTabEntry 4 }
	oPstnSubTabOperStatus OBJECT-TYPE
		SYNTAX INTEGER {
			offline (1),
			regpend (2),
			unrpend (3),
			cfgpend (4),
			starting (5),
			stopping (6),
			online (7)		
			}
                ACCESS read-only
                STATUS mandatory
                DESCRIPTION "Operational status of PSTN."
                ::= { accPstnSubTabEntry 5 }
	oPstnSubTabMsgLevel OBJECT-TYPE
		SYNTAX INTEGER 
                ACCESS read-write
                STATUS mandatory
                DESCRIPTION "PSTN Message level."
                ::= { accPstnSubTabEntry 6 }
	oPstnSubTabLastCause OBJECT-TYPE
		SYNTAX INTEGER {
			no-error(0),
			unassigned-number(1),
			no-route-to-transit-network(2),
			no-route-to-destination(3),
			channel-unacceptable(6),
			call-awarded-being-delivered(7),
			normal-call-clearing(16),
			user-busy(17),
			no-user-responding(18),
			user-alerted-no-answer(19),
			call-rejected(21),
			number-changed(22),
			non-selected-user-clearing(26),
			destination-out-of-order(27),
			invalid-number-format(28),
			facility-rejected(29),
			response-to-status-enquiry(30),
			normal-clearing-unspecified(31),
			no-circuit-or-channel-available(34),
			network-out-of-order(38),
			temporary-failure(41),
			network-congestion(42),
			access-information-discarded(43),
			requested-channel-not-available(44),
			ciruit-or-channel-preempted(45),
			resources-unavailable(47),
			quality-of-service-unavailable(49),
			facility-not-subscribed(50),
			outgoing-call-barred(52),
			incoming-call-barred(54),
			bearer-capability-not-authorized(57),
			bearer-capability-not-available(58),
			service-not-available(63),
			bearer-capability-not-implemented(65),
			channel-not-implemented(66),
			facility-not-implemented(69),
			restricted-digital-information-only(70),
			service-not-implemented(79),
			invalid-call-reference(81),
			channel-does-not-exist(82),
			call-identity-non-existent(83),
			call-identity-in-use(84),
			no-call-suspended(85),
			suspended-call-cleared(86),
			incompatible-destination(88),
			invalid-transit-network(91),
			invalid-message-unspecified(95),
			manditory-information-element-missing(96),
			message-nonexistent-or-not-implemented(97),
			incompatible-or-nonexistent-message(98),
			information-element-not-implemented(99),
			invalid-information-element-contents(100),
			message-incompatible-with-call-state(101),
			timer-expiration(102),
			information-element-length-error(103),
			protocol-error-unspecified(111),
			interworking-unspecified(127)
		}
                ACCESS read-only
                STATUS mandatory
                DESCRIPTION "PSTN subscriber table - last cause."
                ::= { accPstnSubTabEntry 7 }
	oPstnSubTabNumberGroup OBJECT-TYPE
		SYNTAX INTEGER 
                ACCESS read-write
                STATUS mandatory
                DESCRIPTION "PSTN Subscriber table - number group."
                ::= { accPstnSubTabEntry 8 }
	accPstnStatTable OBJECT-TYPE
		SYNTAX SEQUENCE OF AccPstnStatEntry
                ACCESS not-accessible
                STATUS mandatory
                DESCRIPTION
                        " A table containing PSTN statistics."
                ::= { accPstn 2 }
	accPstnStatEntry OBJECT-TYPE
		SYNTAX AccPstnStatEntry
                ACCESS not-accessible
                STATUS mandatory
                DESCRIPTION
                        " Management information PSTN statistics."
                INDEX { oPstnStatDslIndex }
                ::= { accPstnStatTable 1 }
	AccPstnStatEntry ::= SEQUENCE {
		oPstnStatDslIndex	INTEGER,
		oPstnStatCallsOriginated	Counter,
		oPstnStatCallsOfferred	Counter,
		oPstnStatCallsRouted	Counter,
		oPstnStatCallsAccepted	Counter,
		oPstnStatCallsCompleted	Counter,
		oPstnStatCallsCleared	Counter
		}
	oPstnStatDslIndex OBJECT-TYPE
		SYNTAX INTEGER 
                ACCESS read-only
                STATUS mandatory
                DESCRIPTION "PSTN Statistics Dsl Index."
                ::= { accPstnStatEntry 1 }
	oPstnStatCallsOriginated OBJECT-TYPE
		SYNTAX Counter 
                ACCESS read-only
                STATUS mandatory
                DESCRIPTION "PSTN Statistics - Calls Originated."
                ::= { accPstnStatEntry 2 }
	oPstnStatCallsOfferred OBJECT-TYPE
		SYNTAX Counter 
                ACCESS read-only
                STATUS mandatory
                DESCRIPTION "PSTN Statistics - Calls Offered."
                ::= { accPstnStatEntry 3 }
        oPstnStatCallsRouted OBJECT-TYPE
                SYNTAX Counter
                ACCESS read-only
                STATUS mandatory
                DESCRIPTION "PSTN Statistics - Calls Routed."
                ::= { accPstnStatEntry 4 }
        oPstnStatCallsAccepted OBJECT-TYPE
                SYNTAX Counter
                ACCESS read-only
                STATUS mandatory
                DESCRIPTION "PSTN Statistics - Calls Accepted."
                ::= { accPstnStatEntry 5 }
        oPstnStatCallsCompleted OBJECT-TYPE
                SYNTAX Counter
                ACCESS read-only
                STATUS mandatory
                DESCRIPTION "PSTN Statistics - Calls Completed."
                ::= { accPstnStatEntry 6 }
        oPstnStatCallsCleared OBJECT-TYPE
                SYNTAX Counter
                ACCESS read-only
                STATUS mandatory
                DESCRIPTION "PSTN Statistics - Calls Cleared."
                ::= { accPstnStatEntry 7 }
	accPstnCallTable OBJECT-TYPE
		SYNTAX SEQUENCE OF AccPstnCallTableEntry
		ACCESS not-accessible
		STATUS mandatory
		DESCRIPTION "A list of PSTN call entries."
		::= { accPstn 3 }
	accPstnCallTableEntry OBJECT-TYPE
		SYNTAX AccPstnCallTableEntry
		ACCESS not-accessible
		STATUS mandatory
		DESCRIPTION " A table entry providing information about a 
			specific call."
		INDEX { oPstnCallTabDslIndex }
		::= { accPstnCallTable 1 }
	AccPstnCallTableEntry ::= SEQUENCE {
		oPstnCallTabDslIndex	INTEGER,
		oPstnCallTabCallId	INTEGER,
		oPstnCallTabOrigin	INTEGER,
		oPstnCallTabChannel	INTEGER,
		oPstnCallTabEndpoint	INTEGER,
		oPstnCallTabState	INTEGER,
		oPstnCallTabCause	INTEGER,
		oPstnCallTabAddress	INTEGER,
		oPstnCallTabInfoRate	INTEGER,
		oPstnCallTabInfoType	INTEGER,
		oPstnCallTabDuration	INTEGER
		}
        oPstnCallTabDslIndex OBJECT-TYPE
                SYNTAX INTEGER
                ACCESS read-only
                STATUS mandatory
                DESCRIPTION "PSTN Call Table Dsl Index."
                ::= { accPstnCallTableEntry 1 }
        oPstnCallTabCallId OBJECT-TYPE
                SYNTAX INTEGER
                ACCESS read-only
                STATUS mandatory
                DESCRIPTION "PSTN Call Table Call ID."
                ::= { accPstnCallTableEntry 2 }
        oPstnCallTabOrigin OBJECT-TYPE
                SYNTAX INTEGER {
			none(1),
			incoming(2),
			outgoing(3)
			}
                ACCESS read-only
                STATUS mandatory
                DESCRIPTION "PSTN Call Table Origin."
                ::= { accPstnCallTableEntry 3 }
        oPstnCallTabChannel OBJECT-TYPE
                SYNTAX INTEGER
                ACCESS read-only
                STATUS mandatory
                DESCRIPTION "PSTN Call Table Channel."
                ::= { accPstnCallTableEntry 4 }
        oPstnCallTabEndpoint OBJECT-TYPE
                SYNTAX INTEGER
                ACCESS read-only
                STATUS mandatory
                DESCRIPTION "PSTN Call Table Endpoint."
                ::= { accPstnCallTableEntry 5 }
	oPstnCallTabState OBJECT-TYPE
		SYNTAX INTEGER {
			idle(1),
			offered(2),
			initiated(3),
			sending(4),
			proceeding(5),
			connected(6),
			releasing(7),
			clearing(8),
			routing(9),
			ringing(10),
			delivered(11),
			answered(12),
			receiving(13),
			busy(14)
			}
                ACCESS read-only
                STATUS mandatory
                DESCRIPTION "PSTN Call Table State."
                ::= { accPstnCallTableEntry 6 }
	oPstnCallTabCause OBJECT-TYPE
		SYNTAX INTEGER {
			no-error(0),
			unassigned-number(1),
			no-route-to-transit-network(2),
			no-route-to-destination(3),
			channel-unacceptable(6),
			call-awarded-being-delivered(7),
			normal-call-clearing(16),
			user-busy(17),
			no-user-responding(18),
			user-alerted-no-answer(19),
			call-rejected(21),
			number-changed(22),
			non-selected-user-clearing(26),
			destination-out-of-order(27),
			invalid-number-format(28),
			facility-rejected(29),
			response-to-status-enquiry(30),
			normal-clearing-unspecified(31),
			no-circuit-or-channel-available(34),
			network-out-of-order(38),
			temporary-failure(41),
			network-congestion(42),
			access-information-discarded(43),
			requested-channel-not-available(44),
			ciruit-or-channel-preempted(45),
			resources-unavailable(47),
			quality-of-service-unavailable(49),
			facility-not-subscribed(50),
			outgoing-call-barred(52),
			incoming-call-barred(54),
			bearer-capability-not-authorized(57),
			bearer-capability-not-available(58),
			service-not-available(63),
			bearer-capability-not-implemented(65),
			channel-not-implemented(66),
			facility-not-implemented(69),
			restricted-digital-information-only(70),
			service-not-implemented(79),
			invalid-call-reference(81),
			channel-does-not-exist(82),
			call-identity-non-existent(83),
			call-identity-in-use(84),
			no-call-suspended(85),
			suspended-call-cleared(86),
			incompatible-destination(88),
			invalid-transit-network(91),
			invalid-message-unspecified(95),
			manditory-information-element-missing(96),
			message-nonexistent-or-not-implemented(97),
			incompatible-or-nonexistent-message(98),
			information-element-not-implemented(99),
			invalid-information-element-contents(100),
			message-incompatible-with-call-state(101),
			timer-expiration(102),
			information-element-length-error(103),
			protocol-error-unspecified(111),
			interworking-unspecified(127)
			}
                ACCESS read-only
                STATUS mandatory
                DESCRIPTION "PSTN Call Table State."
                ::= { accPstnCallTableEntry 7 }
	oPstnCallTabAddress OBJECT-TYPE
		SYNTAX INTEGER
                ACCESS read-only
                STATUS mandatory
                DESCRIPTION "PSTN Call Table Address."
                ::= { accPstnCallTableEntry 8 }
	oPstnCallTabInfoRate OBJECT-TYPE
                SYNTAX INTEGER
                ACCESS read-only
                STATUS mandatory
                DESCRIPTION "PSTN Call Table Info Rate."
                ::= { accPstnCallTableEntry 9 }
	oPstnCallTabInfoType OBJECT-TYPE
		SYNTAX INTEGER {
			cmd(1),
			cm56(2),
			cmv(3),
			cma(4),
			voice(5),
			data(6),
			data56(7),
			audio(8),
			udi(9),
			rdi(10)
			}
                ACCESS read-only
                STATUS mandatory
                DESCRIPTION "PSTN Call Table Info Type."
                ::= { accPstnCallTableEntry 10 }
	oPstnCallTabDuration OBJECT-TYPE
		SYNTAX INTEGER
                ACCESS read-only
                STATUS mandatory
                DESCRIPTION "PSTN Call Table Duration."
                ::= { accPstnCallTableEntry 11 }
	accPstnChanTable OBJECT-TYPE
		SYNTAX SEQUENCE OF AccPstnChanTableEntry
		ACCESS not-accessible
		STATUS mandatory
		DESCRIPTION "Table of PSTN channel parameters."
		::= { accPstn 4 }
	accPstnChanTableEntry OBJECT-TYPE
		SYNTAX AccPstnChanTableEntry
		ACCESS not-accessible
		STATUS mandatory
		DESCRIPTION "Entry of PSTN channel parameter table."
		INDEX { oPstnChanTabDslIndex, oPstnChanTabSlotMap }
		::= { accPstnChanTable 1 }
	AccPstnChanTableEntry ::= SEQUENCE {
		oPstnChanTabDslIndex	INTEGER,
		oPstnChanTabChannel	INTEGER,
		oPstnChanTabServState	INTEGER,
		oPstnChanTabChanState 	INTEGER,
		oPstnChanTabSlotMap	INTEGER
		}
	oPstnChanTabDslIndex OBJECT-TYPE
		SYNTAX INTEGER
                ACCESS read-only
                STATUS mandatory
                DESCRIPTION "PSTN Channel Table Dsl Index."
                ::= { accPstnChanTableEntry 1 }
	oPstnChanTabChannel OBJECT-TYPE
                SYNTAX INTEGER
                ACCESS read-only
                STATUS mandatory
                DESCRIPTION "PSTN Channel Table Channel."
                ::= { accPstnChanTableEntry 2 }
	oPstnChanTabServState OBJECT-TYPE
		SYNTAX INTEGER {
			in-service(1),
			maintenance(2),
			out-service(3)
			}
                ACCESS read-only
                STATUS mandatory
                DESCRIPTION "PSTN Channel Table Service State."
                ::= { accPstnChanTableEntry 3 }
	oPstnChanTabChanState OBJECT-TYPE
		SYNTAX INTEGER {
			idle(1),
			proposed(2),
			awarded(3),
			busy(4),
			restart(5),
			cnfgpend(6),
			cnfgerr(7),
			reserved(8)
			}
                ACCESS read-only
                STATUS mandatory
                DESCRIPTION "PSTN Channel Table Channel State."
                ::= { accPstnChanTableEntry 4 }
	oPstnChanTabSlotMap OBJECT-TYPE
		SYNTAX INTEGER
                ACCESS read-only
                STATUS mandatory
                DESCRIPTION "PSTN Channel Table Slot Map."
                ::= { accPstnChanTableEntry 5 }
	accPstnRBSParamTable OBJECT-TYPE
		SYNTAX SEQUENCE OF AccPstnRBSParamTableEntry
		ACCESS not-accessible
		STATUS mandatory
		DESCRIPTION "A table containing RBS parameters."
		::= { accPstn 5 }
	accPstnRBSParamTableEntry OBJECT-TYPE
		SYNTAX AccPstnRBSParamTableEntry
                ACCESS not-accessible
                STATUS mandatory
                DESCRIPTION "An RBS parameter-table entry."
		INDEX { oPstnRbsTabDslIndex }
                ::= { accPstnRBSParamTable 1 }
	AccPstnRBSParamTableEntry ::= SEQUENCE {
		oPstnRbsTabDslIndex	INTEGER,
		oPstnRbsTabSuprModeIn	INTEGER,
		oPstnRbsTabSuprModeOut	INTEGER,
		oPstnRbsTabRegnModeIn	INTEGER,
		oPstnRbsTabRegnModeOut	INTEGER,
		oPstnRbsTabPresModeIn	INTEGER,
		oPstnRbsTabPresModeOut	INTEGER,
		oPstnRbsTabGlareAction	INTEGER,
		oPstnRbsTabWoddDuration	INTEGER,
		oPstnRbsTabWsddDetect	INTEGER,
		oPstnRbsTabWesdDetect	INTEGER,
		oPstnRbsTabEnblocDigits INTEGER,
		oPstnRbsTabEnblocTimeout INTEGER
		}
	oPstnRbsTabDslIndex OBJECT-TYPE
		SYNTAX INTEGER
                ACCESS read-only
                STATUS mandatory
                DESCRIPTION "PSTN RBS Table Dsl Index."
                ::= { accPstnRBSParamTableEntry 1 }
	oPstnRbsTabSuprModeIn OBJECT-TYPE
		SYNTAX INTEGER {
			none(1),
			immediate(2),
			wink(3),
			ddsd(4)
			}
                ACCESS read-write
                STATUS mandatory
                DESCRIPTION "PSTN RBS Line Supervision Mode - Incoming."
                ::= { accPstnRBSParamTableEntry 2 }
	oPstnRbsTabSuprModeOut OBJECT-TYPE
		SYNTAX INTEGER {
			none(1),
			immediate(2),
			wink(3),
			ddsd(4)
			}
                ACCESS read-write
                STATUS mandatory
                DESCRIPTION "PSTN RBS Line Supervision Mode - Outgoing."
                ::= { accPstnRBSParamTableEntry 3 }
	oPstnRbsTabRegnModeIn OBJECT-TYPE
		SYNTAX INTEGER {
			suppress(1),
			pulse(2),
			mf(3),
			dtmf(4)
			}
                ACCESS read-write
                STATUS mandatory
                DESCRIPTION "PSTN RBS Table Register Signaling Mode - Incoming."
                ::= { accPstnRBSParamTableEntry 4 }
	oPstnRbsTabRegnModeOut OBJECT-TYPE
		SYNTAX INTEGER {
			suppress(1),
			pulse(2),
			mf(3),
			dtmf(4)
			}
                ACCESS read-write
                STATUS mandatory
                DESCRIPTION "PSTN RBS Table Register Signaling Mode - Outgoing."
                ::= { accPstnRBSParamTableEntry 5 }
	oPstnRbsTabPresModeIn OBJECT-TYPE
		SYNTAX INTEGER {
			none(1),
			enbloc(2),
			overlap(3)
			}
                ACCESS read-write
                STATUS mandatory
                DESCRIPTION "PSTN RBS Table Pres Mode - Incoming."
                ::= { accPstnRBSParamTableEntry 6 }
	oPstnRbsTabPresModeOut OBJECT-TYPE
		SYNTAX INTEGER {
			none(1),
			enbloc(2),
			overlap(3)
			}
                ACCESS read-write
                STATUS mandatory
                DESCRIPTION "PSTN RBS Table Pres Mode - outgoing."
                ::= { accPstnRBSParamTableEntry 7 }
	oPstnRbsTabGlareAction OBJECT-TYPE
		SYNTAX INTEGER {
			backoff(1),
			proceed(2)
			}
                ACCESS read-write
                STATUS mandatory
                DESCRIPTION "PSTN RBS Table Glare Action."
                ::= { accPstnRBSParamTableEntry 8 }
	oPstnRbsTabWoddDuration OBJECT-TYPE
		SYNTAX INTEGER 
                ACCESS read-write
                STATUS mandatory
                DESCRIPTION "PSTN RBS Table Wodd Duration."
                ::= { accPstnRBSParamTableEntry 9 }
	oPstnRbsTabWsddDetect OBJECT-TYPE
		SYNTAX INTEGER 
                ACCESS read-write
                STATUS mandatory
                DESCRIPTION "PSTN RBS Table Wsdd Detect."
                ::= { accPstnRBSParamTableEntry 10 }
	oPstnRbsTabWesdDetect OBJECT-TYPE
		SYNTAX INTEGER 
                ACCESS read-write
                STATUS mandatory
                DESCRIPTION "PSTN RBS Table Wesd Detect."
                ::= { accPstnRBSParamTableEntry 11 }
	oPstnRbsTabEnblocDigits OBJECT-TYPE
		SYNTAX INTEGER 
                ACCESS read-write
                STATUS mandatory
                DESCRIPTION "PSTN RBS Table Enbloc Digits."
                ::= { accPstnRBSParamTableEntry 12 }
	oPstnRbsTabEnblocTimeout OBJECT-TYPE
		SYNTAX INTEGER 
                ACCESS read-write
                STATUS mandatory
                DESCRIPTION "PSTN RBS Table Enbloc Timeout."
                ::= { accPstnRBSParamTableEntry 13 }
	accPstnIntCasSupvParamTable OBJECT-TYPE
		SYNTAX SEQUENCE OF AccPstnIntCasSupvParamEntry
		ACCESS not-accessible
		STATUS mandatory
		DESCRIPTION "Table of PSTN line supervision parameters."
		::= { accPstn 6 }
	accPstnIntCasSupvParamEntry OBJECT-TYPE
		SYNTAX AccPstnIntCasSupvParamEntry
                ACCESS not-accessible
                STATUS mandatory
                DESCRIPTION "PSTN line supervision parameter-table entry."
		INDEX{ oPstnCasTabDslIndex }
                ::= { accPstnIntCasSupvParamTable 1 } 
	AccPstnIntCasSupvParamEntry ::= SEQUENCE {
		oPstnCasTabDslIndex		INTEGER,
		oPstnCasTabSupvModeIn		INTEGER,
		oPstnCasTabSupvModeOut		INTEGER,
		oPstnCasTabSupvMask		INTEGER,
		oPstnCasTabSupvIdlePatt		INTEGER,
		oPstnCasTabSupvIdleTime		INTEGER,
		oPstnCasTabSupvSeizePatt	INTEGER,
		oPstnCasTabSupvSeizeTime	INTEGER,
		oPstnCasTabSupvSeizeAckPatt	INTEGER,
		oPstnCasTabSupvSeizeAckTime	INTEGER,
		oPstnCasTabSupvAnswerPatt	INTEGER,
		oPstnCasTabSupvAnswerTime	INTEGER,
		oPstnCasTabSupvClrForwPatt	INTEGER,
		oPstnCasTabSupvClrForwTime	INTEGER,
		oPstnCasTabSupvClrBackPatt	INTEGER,
		oPstnCasTabSupvClrBackTime	INTEGER,
		oPstnCasTabSupvBlockPatt	INTEGER,
		oPstnCasTabSupvBlockTime	INTEGER,
		oPstnCasTabSupvMetPatt		INTEGER,
		oPstnCasTabSupvMetTime		INTEGER,
		oPstnCasTabSupvMetDelay		INTEGER,
		oPstnCasTabSupvMetOn		INTEGER,
		oPstnCasTabSupvMetOff		INTEGER,
		oPstnCasTabSupvGlare		INTEGER,
-- Start of Register Signaling Parameters
		oPstnCasTabRegModeIn	INTEGER,
		oPstnCasTabRegModeOut	INTEGER,
		oPstnCasTabRegComp1Tone	INTEGER,
		oPstnCasTabRegComp1On	INTEGER,
		oPstnCasTabRegComp1Off	INTEGER,
		oPstnCasTabRegComp2Tone	INTEGER,
		oPstnCasTabRegComp2On	INTEGER,
		oPstnCasTabRegComp2Off	INTEGER
	}
	oPstnCasTabDslIndex OBJECT-TYPE
                SYNTAX INTEGER 
                ACCESS read-only
                STATUS mandatory
                DESCRIPTION "PSTN CAS Table Dsl Index."
		::= { accPstnIntCasSupvParamEntry 1 }
	oPstnCasTabSupvModeIn OBJECT-TYPE
                SYNTAX INTEGER {
			none(1),
			r2(2),
			p7(3)
			}  
                ACCESS read-write
                STATUS mandatory
                DESCRIPTION "PSTN CAS Table Line Supervision Mode - Incoming."
		::= { accPstnIntCasSupvParamEntry 2 }
	oPstnCasTabSupvModeOut OBJECT-TYPE
                SYNTAX INTEGER {
			none(1),
			r2(2),
			p7(3)
			}  
                ACCESS read-write
                STATUS mandatory
                DESCRIPTION "PSTN CAS Table Line Supervision Mode - Outgoing."
		::= { accPstnIntCasSupvParamEntry 3 }
	oPstnCasTabSupvMask OBJECT-TYPE
                SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}  
                ACCESS read-write
                STATUS mandatory
                DESCRIPTION "PSTN CAS Table Line Supervision Mask."
		::= { accPstnIntCasSupvParamEntry 4 }
	oPstnCasTabSupvIdlePatt OBJECT-TYPE		
                SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}  
                ACCESS read-write
                STATUS mandatory
                DESCRIPTION "PSTN CAS Table Line Supervision Idle Pattern."
		::= { accPstnIntCasSupvParamEntry 5 }
	oPstnCasTabSupvIdleTime OBJECT-TYPE
                SYNTAX INTEGER 
                ACCESS read-write
                STATUS mandatory
                DESCRIPTION "PSTN CAS Table Line Supervision Idle Time."
		::= { accPstnIntCasSupvParamEntry 6 }
	oPstnCasTabSupvSeizePatt OBJECT-TYPE
                SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}  
                ACCESS read-write
                STATUS mandatory
                DESCRIPTION "PSTN CAS Table Line Supervision Seize Pattern."
		::= { accPstnIntCasSupvParamEntry 7 }
	oPstnCasTabSupvSeizeTime OBJECT-TYPE
		SYNTAX INTEGER 
                ACCESS read-write
                STATUS mandatory
                DESCRIPTION "PSTN CAS Table Line Supervision Seize Time."
		::= { accPstnIntCasSupvParamEntry 8 }
	oPstnCasTabSupvSeizeAckPatt OBJECT-TYPE
		SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}
                ACCESS read-write
                STATUS mandatory
                DESCRIPTION "PSTN CAS Table Line Supervision Seize Ack Pattern."
		::= { accPstnIntCasSupvParamEntry 9 }
	oPstnCasTabSupvSeizeAckTime OBJECT-TYPE
		SYNTAX INTEGER 
                ACCESS read-write
                STATUS mandatory
                DESCRIPTION "PSTN CAS Table Line Supervision Seize Ack Time."
		::= { accPstnIntCasSupvParamEntry 10 }
	oPstnCasTabSupvAnswerPatt OBJECT-TYPE
		SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}  
                ACCESS read-write
                STATUS mandatory
                DESCRIPTION "PSTN CAS Table Line Supervision Answer Pattern."
		::= { accPstnIntCasSupvParamEntry 11 }
	oPstnCasTabSupvAnswerTime OBJECT-TYPE
		SYNTAX INTEGER 
                ACCESS read-write
                STATUS mandatory
                DESCRIPTION "PSTN CAS Table Line Supervision Answer Time."
		::= { accPstnIntCasSupvParamEntry 12 }
	oPstnCasTabSupvClrForwPatt OBJECT-TYPE
		SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}
                ACCESS read-write
                STATUS mandatory
                DESCRIPTION "PSTN CAS Table Line Supervision Clear Forward
				Pattern."
		::= { accPstnIntCasSupvParamEntry 13 }
	oPstnCasTabSupvClrForwTime OBJECT-TYPE
                SYNTAX INTEGER 
                ACCESS read-write
                STATUS mandatory
                DESCRIPTION "PSTN CAS Table Line Supervision Clear Forward 
				Time."
		::= { accPstnIntCasSupvParamEntry 14 }
	oPstnCasTabSupvClrBackPatt OBJECT-TYPE
		SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}
                ACCESS read-write
                STATUS mandatory
                DESCRIPTION "PSTN CAS Table Line Supervision Clear Back
			Pattern." 
		::= { accPstnIntCasSupvParamEntry 15 }
	oPstnCasTabSupvClrBackTime OBJECT-TYPE
                SYNTAX INTEGER 
                ACCESS read-write
                STATUS mandatory
                DESCRIPTION "PSTN CAS Table Line Supervision Clear Back Time."
		::= { accPstnIntCasSupvParamEntry 16 }
	oPstnCasTabSupvBlockPatt OBJECT-TYPE
                SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16)
			}
                ACCESS read-write
                STATUS mandatory
                DESCRIPTION "PSTN CAS Table Line Supervision Block Pattern."
		::= { accPstnIntCasSupvParamEntry 17 }
	oPstnCasTabSupvBlockTime OBJECT-TYPE
		SYNTAX INTEGER 
                ACCESS read-write
                STATUS mandatory
                DESCRIPTION "PSTN CAS Table Line Supervision Block Time."
		::= { accPstnIntCasSupvParamEntry 18 }
	oPstnCasTabSupvMetPatt OBJECT-TYPE
		SYNTAX INTEGER {
			b0000(1),
			b0001(2),
			b0010(3),
			b0011(4),
			b0100(5),
			b0101(6),
			b0110(7),
			b0111(8),
			b1000(9),
			b1001(10),
			b1010(11),
			b1011(12),
			b1100(13),
			b1101(14),
			b1110(15),
			b1111(16),
			disabled(17)
			}  
                ACCESS read-write
                STATUS mandatory
                DESCRIPTION "PSTN CAS Table Line Supervision Metering Pattern."
		::= { accPstnIntCasSupvParamEntry 19 }
	oPstnCasTabSupvMetTime OBJECT-TYPE
		SYNTAX INTEGER 
                ACCESS read-write
                STATUS mandatory
                DESCRIPTION "PSTN CAS Table Line Supervision Metering Time."
		::= { accPstnIntCasSupvParamEntry 20 }
	oPstnCasTabSupvMetDelay OBJECT-TYPE
		SYNTAX INTEGER 
                ACCESS read-write
                STATUS mandatory
                DESCRIPTION "PSTN CAS Table Line Supervision Metering Delay."
		::= { accPstnIntCasSupvParamEntry 21 }
	oPstnCasTabSupvMetOn OBJECT-TYPE
		SYNTAX INTEGER 
                ACCESS read-write
                STATUS mandatory
                DESCRIPTION "PSTN CAS Table Line Supervision Metering On."
		::= { accPstnIntCasSupvParamEntry 22 }
	oPstnCasTabSupvMetOff OBJECT-TYPE
		SYNTAX INTEGER 
                ACCESS read-write
                STATUS mandatory
                DESCRIPTION "PSTN CAS Table Line Supervision Metering Off."
		::= { accPstnIntCasSupvParamEntry 23 }
	oPstnCasTabSupvGlare OBJECT-TYPE
		SYNTAX INTEGER {
			backoff(1),
			proceed(2)
			}  
                ACCESS read-write
                STATUS mandatory
                DESCRIPTION "PSTN CAS Table Line Supervision Glare Behavior."
		::= { accPstnIntCasSupvParamEntry 24 }
--	accPstnIntRegSigParamTable OBJECT-TYPE
--		SYNTAX SEQUENCE OF AccPstnIntRegSigParamEntry
--		ACCESS not-accessible
--		STATUS mandatory
--		DESCRIPTION "Table of PSTN Register Signaling Parameters."
--		::= { accPstn
--
--	accPstnIntRegSigParamEntry OBJECT-TYPE
--		SYNTAX AccPstnIntRegSigParamEntry
--		ACCESS not-accessible
--               STATUS mandatory
--              DESCRIPTION "Table of PSTN Register Signaling Parameters."
--		INDEX { oPstnCasTabDslIndex }
--                ::= { accPstnIntRegSigParamTable 1 }
--
--	AccPstnIntRegSigParamEntry ::= SEQUENCE {
--		oPstnCasTabRegDslIndex	INTEGER,
--		oPstnCasTabRegModeIn	INTEGER,
--		oPstnCasTabRegModeOut	INTEGER,
--		oPstnCasTabRegComp1Tone	INTEGER,
--		oPstnCasTabRegComp1On	INTEGER,
--		oPstnCasTabRegComp1Off	INTEGER,
--		oPstnCasTabRegComp2Tone	INTEGER,
--		oPstnCasTabRegComp2On	INTEGER,
--		oPstnCasTabRegComp2Off	INTEGER
--		}
--
--	oPstnCasTabRegDslIndex OBJECT-TYPE
--              SYNTAX INTEGER 
--              ACCESS read-only
--             	STATUS mandatory
--            	DESCRIPTION "PSTN CAS Table Dsl Index."
--		::= { accPstnIntRegSigParamEntry 1 }
	oPstnCasTabRegModeIn OBJECT-TYPE
		SYNTAX INTEGER {
			suppressed(1),
			r2-mf-x(2),
			p7-dtmf(3)
			}  
                ACCESS read-write
                STATUS mandatory
                DESCRIPTION "PSTN CAS Table Register Signaling Mode - Incoming."
		::= { accPstnIntCasSupvParamEntry 25 }
	oPstnCasTabRegModeOut OBJECT-TYPE
		SYNTAX INTEGER {
			suppressed(1),
			r2-mf-x(2),
			p7-dtmf(3)
			}  
                ACCESS read-write
                STATUS mandatory
                DESCRIPTION "PSTN CAS Table Register Signaling Mode - Outgoing."
		::= { accPstnIntCasSupvParamEntry 26 }
	oPstnCasTabRegComp1Tone OBJECT-TYPE
		SYNTAX INTEGER {
			d1(1),
			d2(2),
			d3(3),
			d4(4),
			d5(5),
			d6(6),
			d7(7),
			d8(8),
			d9(9),
			d10(10),
			d11(11),
			d12(12),
			d13(13),
			d14(14),
			d15(15),
			none(16)
			}
                ACCESS read-write
                STATUS mandatory
                DESCRIPTION "PSTN CAS Table Register Signaling Completion One
			Tone."
		::= { accPstnIntCasSupvParamEntry 27 }
	oPstnCasTabRegComp1On OBJECT-TYPE
		SYNTAX INTEGER 
                ACCESS read-write
                STATUS mandatory
                DESCRIPTION "PSTN CAS Table Register Signaling Completion One
			Tone On Time."
		::= { accPstnIntCasSupvParamEntry 28 }
	oPstnCasTabRegComp1Off OBJECT-TYPE
		SYNTAX INTEGER 
                ACCESS read-write
                STATUS mandatory
                DESCRIPTION "PSTN CAS Table Register Signaling Completion One
			Tone Off Time."
		::= { accPstnIntCasSupvParamEntry 29 }
	oPstnCasTabRegComp2Tone OBJECT-TYPE
		SYNTAX INTEGER {
			d1(1),
			d2(2),
			d3(3),
			d4(4),
			d5(5),
			d6(6),
			d7(7),
			d8(8),
			d9(9),
			d10(10),
			d11(11),
			d12(12),
			d13(13),
			d14(14),
			d15(15),
			none(16)
			}
                ACCESS read-write
                STATUS mandatory
                DESCRIPTION "PSTN CAS Table Register Signaling Completion Two
			Tone."
		::= { accPstnIntCasSupvParamEntry 30 }
	oPstnCasTabRegComp2On OBJECT-TYPE
		SYNTAX INTEGER
                ACCESS read-write
                STATUS mandatory
                DESCRIPTION "PSTN CAS Table Register Signaling Completion Two
			Tone On Time."
		::= { accPstnIntCasSupvParamEntry 31 }
	oPstnCasTabRegComp2Off OBJECT-TYPE
		SYNTAX INTEGER
                ACCESS read-write
                STATUS mandatory
                DESCRIPTION "PSTN CAS Table Register Signaling Completion Two
			Tone Off Time."
		::= { accPstnIntCasSupvParamEntry 32 }
        accDsprmTraps OBJECT IDENTIFIER ::= { accPstn 7 }
        accDsprmTrapMsg OBJECT-TYPE
                SYNTAX DisplayString
                ACCESS read-write
                STATUS mandatory
                DESCRIPTION 
			" Trap message object for level-1 traps of DSPRM module"
                ::= { accDsprmTraps 1 }
-- Interface General
    accNewLiberty OBJECT IDENTIFIER ::= { accPstn 8 }
    accPstnTabSigGen	OBJECT IDENTIFIER ::= { accNewLiberty 3 }
    accPstnEtt      	OBJECT IDENTIFIER ::= { accPstnTabSigGen 3 }
        accPstnTabSigTrace OBJECT-TYPE
	    SYNTAX INTEGER
	    ACCESS read-write
	    STATUS mandatory
	    DESCRIPTION
	      " Depth of the trace level displayed in
              the trap log."
	    ::= { accPstnTabSigGen 1 }
    accPstnTabSigType OBJECT IDENTIFIER ::= { accPstnTabSigGen 2 }
        accPstnTabSigInType OBJECT-TYPE
	    SYNTAX INTEGER {
		none (1),
		dtmf (2),
		dp (3),
		r2 (4)
	    }
	    ACCESS read-write
	    STATUS mandatory
	    DESCRIPTION
	       " Inbound signaling type."
	    ::= { accPstnTabSigType 1 }
	accPstnTabSigOutType OBJECT-TYPE
	    SYNTAX INTEGER {
		none (1),
		dtmf (2),
		dp (3),
		r2 (4)
	    }
	    ACCESS read-write
	    STATUS mandatory
	    DESCRIPTION
	       " Outbound signaling type."
	    ::= { accPstnTabSigType 2 }
      accPstnTabSigGenT	OBJECT IDENTIFIER ::= { accNewLiberty 4 }
	accPstnTabLineTrace OBJECT-TYPE
	    SYNTAX INTEGER
	    ACCESS read-write
	    STATUS mandatory
	    DESCRIPTION
	      " Depth of messages to be displayed in the trace."
	    ::= { accPstnTabSigGenT 1 }
	accPstnTabSupType OBJECT-TYPE
	    SYNTAX INTEGER {
		r2 (1),
		em (2),
		none (3)
	    }
	    ACCESS read-write
	    STATUS mandatory
	    DESCRIPTION
	       " Line supervision type."
	    ::= { accPstnTabSigGenT 2 }
-- Dial Pulse Signaling
    accDPSig	OBJECT IDENTIFIER ::= { accPstnTabSigGen 5 }
    accDPSigo	OBJECT IDENTIFIER ::= { accDPSig 1 }
    accDPSigoo	OBJECT IDENTIFIER ::= { accDPSigo 1 }
	accPstnTabSigDpCpEnd OBJECT-TYPE
	    SYNTAX INTEGER {
		none (1),
		ringbackbusy (2)
	    }
	    ACCESS read-write
	    STATUS mandatory
	    DESCRIPTION
	       " Action to be performed at end of dial pulse
               callprogress signaling."
	    ::= { accDPSigoo 1 }
	accPstnTabSigDpCpSt OBJECT-TYPE
	    SYNTAX INTEGER {
		none (1),
		dial (2)
	    }
	    ACCESS read-write
	    STATUS mandatory
	    DESCRIPTION
	       " Action to be performed at start of dial pulse
               callprogress signaling."
	    ::= { accDPSigoo 2 }
	accPstnTabSigDpCpTo OBJECT-TYPE
	    SYNTAX INTEGER
	    ACCESS read-write
	    STATUS mandatory
	    DESCRIPTION
	       " Dial pulse callprogress timeout."
	    ::= { accDPSigoo 3 }
	accPstnTabSigDpDt OBJECT-TYPE
	    SYNTAX INTEGER
	    ACCESS read-write
	    STATUS mandatory
	    DESCRIPTION
	       " Timer for dial pulse digit timeout."
	    ::= { accDPSigoo 4 }
	accPstnTabSigDpPm OBJECT-TYPE
	    SYNTAX INTEGER
	    ACCESS read-write
	    STATUS mandatory
	    DESCRIPTION
	       " Parsemask for dial pulse signaling."
	    ::= { accDPSigoo 5 }
	accPstnTabSigDpPmCo OBJECT-TYPE
	    SYNTAX INTEGER
	    ACCESS read-write
	    STATUS mandatory
	    DESCRIPTION
	       " Count of digits in the dial pulse parsemask."
            ::= { accDPSigoo 6 }
	accPstnTabSigDpBrkTime OBJECT-TYPE
	    SYNTAX INTEGER
	    ACCESS read-write
	    STATUS mandatory
	    DESCRIPTION
	       " Break timer for pulse dialing."
	    ::= { accDPSigoo 7 }                                 
	accPstnTabSigDpIdTime OBJECT-TYPE
	    SYNTAX INTEGER
	    ACCESS read-write
	    STATUS mandatory
	    DESCRIPTION
	       " Idle time used for dial pulse digit timing."
	    ::= { accDPSigoo 8 }
	accPstnTabSigDpMkTime OBJECT-TYPE
	    SYNTAX INTEGER
	    ACCESS read-write
	    STATUS mandatory
	    DESCRIPTION
	       " Make time used for dial pulse digit timing."
	    ::= { accDPSigoo 9 }
	accPstnTabSigDpSt OBJECT-TYPE
	    SYNTAX INTEGER
	    ACCESS read-write
	    STATUS mandatory
	    DESCRIPTION
	       " Signal duration for use in dial pulse sigtimeout."
	    ::= { accDPSigoo 10 }
-- DTMF
accDTMF	    OBJECT IDENTIFIER ::= { accPstnTabSigGen 4 }
accDTMFo    OBJECT IDENTIFIER ::= { accDTMF 1 }
accDTMFoo    OBJECT IDENTIFIER ::= { accDTMFo 1 }
        accPstnTabSigDtCpEnd OBJECT-TYPE
	    SYNTAX INTEGER {
		none (1),
		ringbackbusy (2)
	    }
	    ACCESS read-write
	    STATUS mandatory
	    DESCRIPTION
	       " Call progress end timer for DTMF signaling."
	    ::= { accDTMFoo 1 }
	accPstnTabSigDtCpSt OBJECT-TYPE
	    SYNTAX INTEGER {
		none (1),
		dial (2)
	    }
	    ACCESS read-write
	    STATUS mandatory
	    DESCRIPTION
	       " Call progress start timer for DTMF signaling."
	    ::= { accDTMFoo 2 }
	accPstnTabSigDtCpTo OBJECT-TYPE
	    SYNTAX INTEGER
	    ACCESS read-write
	    STATUS mandatory
	    DESCRIPTION
	       " Call progress timeout timer for DTMF signaling."
	    ::= { accDTMFoo 3 }
	accPstnTabSigDtDt OBJECT-TYPE
	    SYNTAX INTEGER
	    ACCESS read-write
	    STATUS mandatory
	    DESCRIPTION
	       " Digit timeout timer for DTMF signaling."
	    ::= { accDTMFoo 4 }
	accPstnTabSigDtIbCpSt OBJECT-TYPE
	    SYNTAX INTEGER {
		none (1),
		dial (2)
	    }
	    ACCESS read-write
	    STATUS mandatory
	    DESCRIPTION
	       " If set to DIAL, ibcallprogress will wait 
               for a dial tone from the other side before 
               starting the call, when set to NONE, it won't."
            ::= { accDTMFoo 5 }
	accPstnTabSigDtIbCpTp OBJECT-TYPE
	    SYNTAX INTEGER
	    ACCESS read-write
	    STATUS mandatory
	    DESCRIPTION
	       " Tonepower setting for inbound DTMF calls, from
               zero to -12 dB."
	    ::= { accDTMFoo 6 }
	accPstnTabSigDtPm OBJECT-TYPE
	    SYNTAX INTEGER
	    ACCESS read-write
	    STATUS mandatory
	    DESCRIPTION
	       " Parsemask for DTMF signaling."
	    ::= { accDTMFoo 7 }
	accPstnTabSigDtPmCo OBJECT-TYPE
	    SYNTAX INTEGER
	    ACCESS read-write
	    STATUS mandatory
	    DESCRIPTION
	       " Number of digits in the DTMF parsemask."
	    ::= { accDTMFoo 8 }
	accPstnTabSigDtSt OBJECT-TYPE
	    SYNTAX INTEGER
	    ACCESS read-write
	    STATUS mandatory
	    DESCRIPTION
	       " DTMF (touch tone) signal timeout."
	    ::= { accDTMFoo 9 }
	accPstnTabSigDtHiPwr OBJECT-TYPE
	    SYNTAX INTEGER
	    ACCESS read-write
	    STATUS mandatory
	    DESCRIPTION
	       " Power of high frequency tone for DTMF signaling."
	    ::= { accDTMFoo 10 }
	accPstnTabSigDtLoPwr OBJECT-TYPE
	    SYNTAX INTEGER
	    ACCESS read-write
	    STATUS mandatory
	    DESCRIPTION
	       " Power of low frequency tone for DTMF signaling."
	    ::= { accDTMFoo 11 }
	accPstnTabSigDtOffTime OBJECT-TYPE
	    SYNTAX INTEGER
	    ACCESS read-write
	    STATUS mandatory
	    DESCRIPTION
	       " Off time for DTMF digit tonetiming."
	    ::= { accDTMFoo 12 }
	accPstnTabSigDtOnTime OBJECT-TYPE
	    SYNTAX INTEGER
	    ACCESS read-write
	    STATUS mandatory
	    DESCRIPTION
	       " On time for DTMF digit tonetiming."
	    ::= { accDTMFoo 13 }
-- R2 Signaling
accR2Sig   OBJECT IDENTIFIER ::= { accPstnEtt 1 }
accR2Sigo  OBJECT IDENTIFIER ::= { accR2Sig 1 }
        accPstnTabSigR2CdDig OBJECT-TYPE
	    SYNTAX INTEGER
	    ACCESS read-write
	    STATUS mandatory
	    DESCRIPTION
	       " Number of called digits to request for
               an R2 signaling call."
	    ::= { accR2Sigo 1 }
	accPstnTabSigR2CnDig OBJECT-TYPE
	    SYNTAX INTEGER
	    ACCESS read-write
	    STATUS mandatory
	    DESCRIPTION
	       " Number of calling digits to request for
               an R2 signaling call."
	    ::= { accR2Sigo 2 }
	accPstnTabSigR2ReqCpc OBJECT-TYPE
	    SYNTAX INTEGER {
		yes (1),
		no (2)
	    }
	    ACCESS read-write
	    STATUS mandatory
	    DESCRIPTION
	       " This object holds the calling party category."
	    ::= { accR2Sigo 3 }
	accPstnTabSigR2AdMo OBJECT-TYPE
	    SYNTAX INTEGER {
		groupBTable (1),
		groupATable (2)
	    }
	    ACCESS read-write
	    STATUS mandatory
	    DESCRIPTION
	      "Group table to use for address termination."
            ::= { accR2Sigo 4 }
	accPstnTabSigR2CdInMode OBJECT-TYPE
	    SYNTAX INTEGER {
		signaled (1),
		timeout (2)
	    }
	    ACCESS read-write
	    STATUS mandatory
	    DESCRIPTION
	       " Defines the method used to signal a stop 
               after receiving the called number digits."
	    ::= { accR2Sigo 5 }
	accPstnTabSigR2CdOutMode OBJECT-TYPE
	    SYNTAX INTEGER {
		signaled (1),
		timeout (2)
	    }
	    ACCESS read-write
	    STATUS mandatory
	    DESCRIPTION
	       " Defines the method used to signal a stop 
               after sending the called number digits."
	    ::= { accR2Sigo 6 }
	accPstnTabSigR2CnInMode OBJECT-TYPE
	    SYNTAX INTEGER {
		signaled (1),
		timeout (2)
	    }
	    ACCESS read-write
	    STATUS mandatory
	    DESCRIPTION
	       " Defines the method used to signal a stop 
               after receiving the calling number digits."
	    ::= { accR2Sigo 7 }
	accPstnTabSigR2CnOutMode OBJECT-TYPE
	    SYNTAX INTEGER {
		signaled (1),
		timeout (2)
	    }
	    ACCESS read-write
	    STATUS mandatory
	    DESCRIPTION
	       " Defines the mode used to stop sending the
               calling number digits."
	    ::= { accR2Sigo 8 }
	accPstnTabSigR2RspInMode OBJECT-TYPE
	    SYNTAX INTEGER {
		compelled (1),
		semicomp (2),
		noncomp (3)
	    }
	    ACCESS read-write
	    STATUS mandatory
	    DESCRIPTION
	       " Mode used for inbound call signaling  
               (compelled, semi-compelled, none)."
            ::= { accR2Sigo 9 }
	accPstnTabSigR2RspOutMode OBJECT-TYPE
	    SYNTAX INTEGER {
		compelled (1),
		semicomp (2),
		noncomp (3)
	    }
	    ACCESS read-write
	    STATUS mandatory
	    DESCRIPTION
	       " Mode used for outbound call signaling  
               (compelled, semi-compelled, none)."
            ::= { accR2Sigo 10 }
	accPstnTabSigR2ObCpc OBJECT-TYPE
	    SYNTAX INTEGER {
		operator (1),
		ordinary (2),
		priority (3),
		data (4),
		maintenance (5)
	    }
	    ACCESS read-write
	    STATUS mandatory
	    DESCRIPTION
	       " Calling party category used for
                outbound calls."
	    ::= { accR2Sigo 11 }
	accPstnTabSigR2ObDflt OBJECT-TYPE
	    SYNTAX INTEGER
	    ACCESS read-write
	    STATUS mandatory
	    DESCRIPTION
	       " Called number used for outbound calls."
	    ::= { accR2Sigo 12 }
	accPstnTabSigR2ScDur OBJECT-TYPE
	    SYNTAX INTEGER
	    ACCESS read-write
	    STATUS mandatory
	    DESCRIPTION
	      " Holds the semi-compelled tone duration, used
              in either direction (inbound, outbound). "
	    ::= { accR2Sigo 13 }
	accPstnTabSigR2RspInDur OBJECT-TYPE
	    SYNTAX INTEGER
	    ACCESS read-write
	    STATUS mandatory
	    DESCRIPTION
	      " Maximum inbound signaling response duration
                for R2 signaling."
	    ::= { accR2Sigo 14 }
	accPstnTabSigR2RspOutDur OBJECT-TYPE
	    SYNTAX INTEGER
	    ACCESS read-write
	    STATUS mandatory
	    DESCRIPTION
	       " Maximum outbound signaling response duration
               for R2 signaling."
            ::= { accR2Sigo 15 }
	accPstnTabSigR2InDur OBJECT-TYPE
	    SYNTAX INTEGER
	    ACCESS read-write
	    STATUS mandatory
	    DESCRIPTION
	       " Signaling timeout for inbound R2 calls. "
	    ::= { accR2Sigo 16 }
	accPstnTabSigR2OutDur OBJECT-TYPE
	    SYNTAX INTEGER
	    ACCESS read-write
	    STATUS mandatory
	    DESCRIPTION
	       " Signaling timeout for outbound R2 calls. "
	    ::= { accR2Sigo 17 }
	accPstnTabSigR2InHiPwr OBJECT-TYPE
	    SYNTAX INTEGER
	    ACCESS read-write
	    STATUS mandatory
	    DESCRIPTION
	       " High frequency tonepower setting for
               incoming calls."
	    ::= { accR2Sigo 18 }
	accPstnTabSigR2InLoPwr OBJECT-TYPE
	    SYNTAX INTEGER
	    ACCESS read-write
	    STATUS mandatory
	    DESCRIPTION
	       " Low frequency tonepower setting for
               incoming calls."
	    ::= { accR2Sigo 19 }
	accPstnTabSigR2OutHiPwr OBJECT-TYPE
	    SYNTAX INTEGER
	    ACCESS read-write
	    STATUS mandatory
	    DESCRIPTION
	       " High frequency tone power setting
               for outbound calls."
	    ::= { accR2Sigo 20 }
	accPstnTabSigR2OutLoPwr OBJECT-TYPE
	    SYNTAX INTEGER
	    ACCESS read-write
	    STATUS mandatory
	    DESCRIPTION
	       " Low frequency tone power setting
               for outbound calls."
	    ::= { accR2Sigo 21 }
	accPstnTableInt OBJECT-TYPE
	    SYNTAX INTEGER
	    ACCESS read-write
	    STATUS mandatory
	    DESCRIPTION
	       " TBLSET currently in use."
	    ::= { accR2Sigo 22 }
-- New Tonetable Supervision
        accPstnTTIndex OBJECT-TYPE
	    SYNTAX INTEGER
	    ACCESS read-write
	    STATUS mandatory
	    DESCRIPTION
	       " Setting default timer for tonetables"
	    ::= { accPstnEtt 3 }
--    accToneSupt   OBJECT IDENTIFIER ::= { accPstnEtt 2 }
--    accToneSupo	  OBJECT IDENTIFIER ::= { accToneSupt 1 }
---    accToneSupoo  OBJECT IDENTIFIER ::= { accToneSupo 1 }
    accToneSupoo   OBJECT IDENTIFIER ::= { accPstnEtt 2 }
        accPstnTable OBJECT-TYPE
	    SYNTAX INTEGER
	    ACCESS read-write
	    STATUS mandatory
	    DESCRIPTION
	      " Used for set tonetable command, determines 
              which TBLSET will be set."
	    ::= { accToneSupoo 1 }
	accPstnSignal OBJECT-TYPE
	    SYNTAX INTEGER
	    ACCESS read-write
	    STATUS mandatory
	    DESCRIPTION
	       " Signal currently in use (for tonetable)."
	    ::= { accToneSupoo 2 }
	accPstnFwdIntGI OBJECT-TYPE
	    SYNTAX INTEGER {
		digit1 (1),
		digit2 (2),
		digit3 (3),
		digit4 (4),
		digit5 (5),
		digit6 (6),
		digit7 (7),
		digit8 (8),
		digit9 (9),
		digit0 (10),
		incomingOperator (11),
		delayOperator (12),
		accessTestEquipment (13),
		requireHalfEchoSuppressor (14),
		endOfInformation (15),
		spare (200)
	    }
	    ACCESS read-write
	    STATUS mandatory
	    DESCRIPTION
	       " Forward interpretation GI possible token values."
	    ::= { accToneSupoo 3 }
	accPstnFwdIntGII OBJECT-TYPE
	    SYNTAX INTEGER {
		nationalSubscriber (1),
		nationalPrioritySubscriber (2),
		nationalMaintenanceEquipment (3),
		nationalOp (5),
		nationalDataTransmission (6),
		internationalSubscriber (7),
		internationalDataTrans (8),
		internationalPrioritySubscriber (9),
		internationalOp (10),
		spare (200)
	    }
	    ACCESS read-write
	    STATUS mandatory
	    DESCRIPTION
	       " Forward interpretation GII possible token values."
	    ::= { accToneSupoo 4 }
	accPstnFwdGenGI OBJECT-TYPE
	    SYNTAX INTEGER {
		digit1 (1),
		digit2 (2),
		digit3 (3),
		digit4 (4),
		digit5 (5),
		digit6 (6),
		digit7 (7),
		digit8 (8),
		digit9 (9),
		digit0 (10),
		incomingOperator (11),
		delayOperator (12),
		accessTestEquipment (13),
		requireHalfEchoSuppressor (14),
		endOfInformation (15),
		spare (200)
	    }
	    ACCESS read-write
	    STATUS mandatory
	    DESCRIPTION
	       " Forward generation GI possible token values."
	    ::= { accToneSupoo 5 }
	accPstnFwdGenGII OBJECT-TYPE
	    SYNTAX INTEGER {
		nationalSubscriber (1),
		nationalPrioritySubscriber (2),
		nationalMaintenanceEquipment (3),
		nationalOp (5),
		nationalDataTransmission (6),
		internationalSubscriber (7),
		internationalDataTrans (8),
		internationalPrioritySubscriber (9),
		internationalOp (10),
		spare (200)
	    }
	    ACCESS read-write
	    STATUS mandatory
	    DESCRIPTION
	       " Forward generation GII possible token values."
	    ::= { accToneSupoo 6 }
	accPstnBckIntGA OBJECT-TYPE
	    SYNTAX INTEGER {
		sndNextDig (17),
		sndDigN1 (18),
		addCmpltRcvB (19),
		congestNat (20),
		sndCpc (21),
		addCmpltEndSig (22),
		sndDigN2 (23),
		sndDigN3 (24),
		snd1stDig (25),
		sndCpcGoC (26),
		countryC (27),
		langDig (28),
		natureCirct-sndCallingLn (29),
		echoSup-sndSigGroup2 (30),
		congestInt-vacnt (31),
		spare (200)
	    }
	    ACCESS read-write
	    STATUS mandatory
	    DESCRIPTION
	       " Backward interpretation GA possible token values."
	    ::= { accToneSupoo 7 }
	accPstnBckIntGB OBJECT-TYPE
	    SYNTAX INTEGER {
		sendSpecialInformationTone (18),
		subscriberLineBusy (19),
		congestion (20),
		unallocatedNumber (21),
		subscriberLineFreeCharge (22),
		subscriberLineFreeNoCharge (23),
		subscriberLineOutOfService (24),
		spare (200)
	    }
	    ACCESS read-write
	    STATUS mandatory
	    DESCRIPTION
	       " Backward interpretation GB possible token values."
	    ::= { accToneSupoo 8 }
	accPstnBckIntGC OBJECT-TYPE
	    SYNTAX INTEGER {
		sendNextCallingDigit (17),
		sendFirstCalledDigit (18),
		sendGroupB (19),
		congestionC (20),
		sendNextCalledDigit (21),
		sendSameCalledDigit (22),
		spare (200)
	    }
	    ACCESS read-write
	    STATUS mandatory
	    DESCRIPTION
	       " Backward interpretation GC possible token values."
	    ::= { accToneSupoo 9 }
	accPstnBckGenGA OBJECT-TYPE
	    SYNTAX INTEGER {
		sndNextDig (17),
		sndDigN1 (18),
		addCmpltrcvB (19),
		congestNat (20),
		sndCpc (21),
		addCmpltendSig (22),
		sndDigN2 (23),
		sndDigN3 (24),
		snd1stDig (25),
		sndCpcGoC (26),
		countryC (27),
		langDig (28),
		natureCirct-sndCallingLn (29),
		echoSup-sndSigGroup2 (30),
		congestint-vacnt (31),
		spare (200)
	    }
	    ACCESS read-write
	    STATUS mandatory
	    DESCRIPTION
	       " Backward generation GA possible token values."
	    ::= { accToneSupoo 10 }
	accPstnBckGenGB OBJECT-TYPE
	    SYNTAX INTEGER {
		sendSpecialInformationTone (18),
		subscriberLineBusy (19),
		congestion (20),
		unallocatedNumber (21),
		subscriberLineFreeCharge (22),
		subscriberLineFreeNoCharge (23),
		subscriberLineOutOfService (24),
		spare (200)
	    }
	    ACCESS read-write
	    STATUS mandatory
	    DESCRIPTION
	       " Backward generation GB possible token values."
	    ::= { accToneSupoo 11 }
	accPstnBckGenGC OBJECT-TYPE
	    SYNTAX INTEGER {
		sendNextCallingDigit (17),
		sendFirstCalledDigit (18),
		sendGroupB (19),
		congestionC (20),
		sendNextCalledDigit (21),
		sendSameCalledDigit (22),
		spare (200)
	    }
	    ACCESS read-write
	    STATUS mandatory
	    DESCRIPTION
	       " Backward generation GC possible token values."
	    ::= { accToneSupoo 12 }
	accPstnTableDef OBJECT-TYPE
	    SYNTAX INTEGER
	    ACCESS read-write
	    STATUS mandatory
	    DESCRIPTION
	       " Default tonetable values.  (sets all 4 TBLSETs,
               current will be set upon system reset."
	    ::= { accToneSupoo 13 }
	accPstnDisplayFGTableSet1 OBJECT-TYPE
	    SYNTAX INTEGER
	    ACCESS read-write
	    STATUS mandatory
	    DESCRIPTION
	       " Display object for TBLSET 1, forward generation"
	    ::= { accToneSupoo 14 }
	accPstnDisplayFGTableSet2 OBJECT-TYPE
	    SYNTAX INTEGER
	    ACCESS read-write
	    STATUS mandatory
	    DESCRIPTION
	       " Display object for TBLSET 2, forward generation"
	    ::= { accToneSupoo 15 }
	accPstnDisplayFGTableSet3 OBJECT-TYPE
	    SYNTAX INTEGER
	    ACCESS read-write
	    STATUS mandatory
	    DESCRIPTION
	       " Display object for TBLSET 3, forward generation"
	    ::= { accToneSupoo 16 }
	accPstnDisplayFGTableSet4 OBJECT-TYPE
	    SYNTAX INTEGER
	    ACCESS read-write
	    STATUS mandatory
	    DESCRIPTION
	       " Display object for TBLSET 4, forward generation"
	    ::= { accToneSupoo 17 }
	accPstnDisplayFITableSet1 OBJECT-TYPE
	    SYNTAX INTEGER
	    ACCESS read-write
	    STATUS mandatory
	    DESCRIPTION
	       " Display object for TBLSET 1, forward interpretation"
	    ::= { accToneSupoo 18 }
	accPstnDisplayFITableSet2 OBJECT-TYPE
	    SYNTAX INTEGER
	    ACCESS read-write
	    STATUS mandatory
	    DESCRIPTION
	       " Display object for TBLSET 2, forward interpretation"
	    ::= { accToneSupoo 19 }
	accPstnDisplayFITableSet3 OBJECT-TYPE
	    SYNTAX INTEGER
	    ACCESS read-write
	    STATUS mandatory
	    DESCRIPTION
	       " Display object for TBLSET 3, forward interpretation"
	    ::= { accToneSupoo 20 }
	accPstnDisplayFITableSet4 OBJECT-TYPE
	    SYNTAX INTEGER
	    ACCESS read-write
	    STATUS mandatory
	    DESCRIPTION
	       " Display object for TBLSET 4, forward interpretation"
	    ::= { accToneSupoo 21 }
	accPstnDisplayBGTableSet1 OBJECT-TYPE
	    SYNTAX INTEGER
	    ACCESS read-write
	    STATUS mandatory
	    DESCRIPTION
	       " Display object for TBLSET 1, backward generation"
	    ::= { accToneSupoo 22 }
	accPstnDisplayBGTableSet2 OBJECT-TYPE
	    SYNTAX INTEGER
	    ACCESS read-write
	    STATUS mandatory
	    DESCRIPTION
	       " Display object for TBLSET 2, backward generation"
	    ::= { accToneSupoo 23 }
	accPstnDisplayBGTableSet3 OBJECT-TYPE
	    SYNTAX INTEGER
	    ACCESS read-write
	    STATUS mandatory
	    DESCRIPTION
	       " Display object for TBLSET 3, backward generation"
	    ::= { accToneSupoo 24 }
	accPstnDisplayBGTableSet4 OBJECT-TYPE
	    SYNTAX INTEGER
	    ACCESS read-write
	    STATUS mandatory
	    DESCRIPTION
	       " Display object for TBLSET 4, backward generation"
	    ::= { accToneSupoo 25 }
	accPstnDisplayBITableSet1 OBJECT-TYPE
	    SYNTAX INTEGER
	    ACCESS read-write
	    STATUS mandatory
	    DESCRIPTION
	       " Display object for TBLSET 1, backward interpretation"
	    ::= { accToneSupoo 26 }
	accPstnDisplayBITableSet2 OBJECT-TYPE
	    SYNTAX INTEGER
	    ACCESS read-write
	    STATUS mandatory
	    DESCRIPTION
	       " Display object for TBLSET 2, backward interpretation"
	    ::= { accToneSupoo 27 }
	accPstnDisplayBITableSet3 OBJECT-TYPE
	    SYNTAX INTEGER
	    ACCESS read-write
	    STATUS mandatory
	    DESCRIPTION
	       " Display object for TBLSET 3, backward interpretation"
	    ::= { accToneSupoo 28 }
	accPstnDisplayBITableSet4 OBJECT-TYPE
	    SYNTAX INTEGER
	    ACCESS read-write
	    STATUS mandatory
	    DESCRIPTION
	       " Display object for TBLSET 4, backward interpretation"
	    ::= { accToneSupoo 29 }
-- EM Line Supervision
accPstnSupGen	OBJECT IDENTIFIER ::= { accPstnTabSigGenT 4 }
accEMLinSup	OBJECT IDENTIFIER ::= { accPstnSupGen 1 }
accEMLinSupo	OBJECT IDENTIFIER ::= { accEMLinSup 1 }
	accPstnTabSupEmDsOutStDly OBJECT-TYPE
	    SYNTAX INTEGER
	    ACCESS read-write
	    STATUS mandatory
	    DESCRIPTION
	       " Delay Dial Start Dial delay time for
               outbound E&M calls"
	    ::= { accEMLinSupo 1 }
	accPstnTabSupEmGl OBJECT-TYPE
	    SYNTAX INTEGER {
		backoff (1),
		proceed (2)
	    }
	    ACCESS read-write
	    STATUS mandatory
	    DESCRIPTION
	       " Notifies call of what to do if glare
               (call attempts in opposite directions on the 
               same line, at the same time) occurs."
	    ::= { accEMLinSupo 2 }
	accPstnTabSupEmImOutStDly OBJECT-TYPE
	    SYNTAX INTEGER
	    ACCESS read-write
	    STATUS mandatory
	    DESCRIPTION
	       " Start delay for use in Immediate Start Mode"
	    ::= { accEMLinSupo 3 }
	accPstnTabSupEmWiInDur OBJECT-TYPE
	    SYNTAX INTEGER
	    ACCESS read-write
	    STATUS mandatory
	    DESCRIPTION
	       " Duration of incoming wink timer."
	    ::= { accEMLinSupo 4 }
	accPstnTabSupEmWiOutEndTo OBJECT-TYPE
	    SYNTAX INTEGER
	    ACCESS read-write
	    STATUS mandatory
	    DESCRIPTION
	       " Wink end timeout for outgoing E&M calls."
	    ::= { accEMLinSupo 5 }
	accPstnTabSupEmWiOutStDly OBJECT-TYPE
	    SYNTAX INTEGER
	    ACCESS read-write
	    STATUS mandatory
	    DESCRIPTION
	       " Wink start delay duration for outgoing E&M calls."
	    ::= { accEMLinSupo 6 }
	accPstnTabSupEmWiOutStTo OBJECT-TYPE
	    SYNTAX INTEGER
	    ACCESS read-write
	    STATUS mandatory
	    DESCRIPTION
	       " Wink start timeout duration for outgoing E&M calls."
	    ::= { accEMLinSupo 7 }
	accPstnTabSupInMode OBJECT-TYPE
	    SYNTAX INTEGER {
		immediate (1),
		wink (2),
		delayed (3)
	    }
	    ACCESS read-write
	    STATUS mandatory
	    DESCRIPTION
	       " E&M incoming call mode."
	    ::= { accEMLinSupo 8 }
	accPstnTabSupOutMode OBJECT-TYPE
	    SYNTAX INTEGER {
		immediate (1),
		wink (2),
		delayed (3)
	    }
	    ACCESS read-write
	    STATUS mandatory
	    DESCRIPTION
	       " E&M outgoing call mode."
	    ::= { accEMLinSupo 9 }
	accPstnTabSupEmDsInDur OBJECT-TYPE
	    SYNTAX INTEGER
	    ACCESS read-write
	    STATUS mandatory
	    DESCRIPTION
	       " E&M delay dial start delay incoming timeout."
	    ::= { accEMLinSupo 11 }
	accPstnTabSupEmDsOutEndTo OBJECT-TYPE
	    SYNTAX INTEGER
            ACCESS read-write
	    STATUS mandatory
	    DESCRIPTION
	       " E&M delay dial start delay outgoing end timeout."
	    ::= { accEMLinSupo 12 }
	accPstnTabSupEmDsOutStTo OBJECT-TYPE
	    SYNTAX INTEGER
	    ACCESS read-write
	    STATUS mandatory
	    DESCRIPTION
	       " E&M delay dial start delay outgoing start timeout."
	    ::= { accEMLinSupo 13 }
-- R2 Line Supervision
-- accR2LinSup	OBJECT IDENTIFIER ::= { accPstnSupGen 3 }
-- accR2LinSupo	OBJECT IDENTIFIER ::= { accR2LinSup 1 }
accR2LinSupoo	OBJECT IDENTIFIER ::= { accPstnSupGen 3 }
        accPstnTabSupR2AnAnsDly OBJECT-TYPE
	    SYNTAX INTEGER
	    ACCESS read-write
	    STATUS mandatory
	    DESCRIPTION
	       " Answer delay duration."
	    ::= { accR2LinSupoo 1 }
	accPstnTabSupR2AnInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Answer pattern used for incoming calls."
	    ::= { accR2LinSupoo 2 }
	accPstnTabSupR2AnOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Answer pattern used for outgoing calls."
	    ::= { accR2LinSupoo 3 }
	accPstnTabSupR2AnRecTime OBJECT-TYPE
	    SYNTAX INTEGER
	    ACCESS read-write
	    STATUS mandatory
	    DESCRIPTION
	       " Recognition timer for answer pattern."
            ::= { accR2LinSupoo 4 }
	accPstnTabSupR2BlInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	    " Blocking pattern for incoming R2 calls."
	    ::= { accR2LinSupoo 5 }
	accPstnTabSupR2BlOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	    " Blocking pattern for outgoing R2 calls."
	    ::= { accR2LinSupoo 6 }
	accPstnTabSupR2BlRecTime OBJECT-TYPE
	    SYNTAX INTEGER
	    ACCESS read-write
	    STATUS mandatory
	    DESCRIPTION
	       " Recognition timer for block pattern."
            ::= { accR2LinSupoo 7 }
	accPstnTabSupR2CbFcbTime OBJECT-TYPE
	    SYNTAX INTEGER
	    ACCESS read-write
	    STATUS mandatory
	    DESCRIPTION
	       " Forced clearback timer duration."
            ::= { accR2LinSupoo 8 }
	accPstnTabSupR2CbInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Clear backward pattern for incoming R2 calls."
	    ::= { accR2LinSupoo 9 }
	accPstnTabSupR2CbOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Clear backward pattern for outgoing R2 calls."
	    ::= { accR2LinSupoo 10 }
	accPstnTabSupR2CbRecTime OBJECT-TYPE
	    SYNTAX INTEGER
	    ACCESS read-write
	    STATUS mandatory
	    DESCRIPTION
	       " Recognition timer for clear backward pattern."
            ::= { accR2LinSupoo 11 }
	accPstnTabSupR2CfInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Clear forward pattern for incoming R2 calls."
	    ::= { accR2LinSupoo 12 }
	accPstnTabSupR2CfOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Clear forward pattern for outgoing R2 calls."
	    ::= { accR2LinSupoo 13 }
	accPstnTabSupR2CfRecTime OBJECT-TYPE
	    SYNTAX INTEGER
	    ACCESS read-write
	    STATUS mandatory
	    DESCRIPTION
	       " Recognition timer for clear forward pattern."
            ::= { accR2LinSupoo 14 }
	accPstnTabSupR2Gl OBJECT-TYPE
	    SYNTAX INTEGER {
		backoff (1),
		proceed (2)
	    }
	    ACCESS read-write
	    STATUS mandatory
	    DESCRIPTION
	       " Action to be taken if glare (call attempts
                in opposite directions on the same line, at the 
                same time) occurs."
	    ::= { accR2LinSupoo 15 }
	accPstnTabSupR2IdInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Idle pattern for incoming R2 calls."
	    ::= { accR2LinSupoo 16 }
	accPstnTabSupR2IdOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Idle pattern for outgoing R2 calls."
	    ::= { accR2LinSupoo 17 }
	accPstnTabSupR2IdRecTime OBJECT-TYPE
	    SYNTAX INTEGER
	    ACCESS read-write
	    STATUS mandatory
	    DESCRIPTION
	       " Recognition timer for Idle R2 signaling."
            ::= { accR2LinSupoo 18 }
	accPstnTabSupR2Mask OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Parse mask used for R2 line supervision."
            ::= { accR2LinSupoo 19 }
	accPstnTabSupR2SaInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Inbound call pattern for szack R2 signaling."
	    ::= { accR2LinSupoo 20 }
	accPstnTabSupR2SaOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Outbound call pattern for szack R2 signaling."
	    ::= { accR2LinSupoo 21 }
	accPstnTabSupR2SaRecTime OBJECT-TYPE
	    SYNTAX INTEGER
	    ACCESS read-write
	    STATUS mandatory
	    DESCRIPTION
               " Recognition timer for szack R2 signaling."
	    ::= { accR2LinSupoo 22 }
	accPstnTabSupR2SzInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Inbound call pattern for seize R2 signaling."
	    ::= { accR2LinSupoo 23 }
	accPstnTabSupR2SzOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16)
	    }
	    ACCESS read-write
	    STATUS mandatory
	    DESCRIPTION
	       " Outbound call pattern for seize R2 signaling."
	    ::= { accR2LinSupoo 24 }
	accPstnTabSupR2SzRecTime OBJECT-TYPE
	    SYNTAX INTEGER
	    ACCESS read-write
	    STATUS mandatory
	    DESCRIPTION
	       " Recognition timer for seize signaling."
	    ::= { accR2LinSupoo 25 }
	accPstnTabSupR2MeInPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16),
		disabled (17)
	    }
	    ACCESS read-write
	    STATUS mandatory
	    DESCRIPTION
	       " Inbound metering pattern."
	    ::= { accR2LinSupoo 26 }
	accPstnTabSupR2MeOutPat OBJECT-TYPE
	    SYNTAX INTEGER {
		b0000 (1),
		b0001 (2),
		b0010 (3),
		b0011 (4),
		b0100 (5),
		b0101 (6),
		b0110 (7),
		b0111 (8),
		b1000 (9),
		b1001 (10),
		b1010 (11),
		b1011 (12),
		b1100 (13),
		b1101 (14),
		b1110 (15),
		b1111 (16),
		disabled (17)
	    }
	    ACCESS read-write
	    STATUS mandatory
	    DESCRIPTION
	       " Outbound metering pattern."
	    ::= { accR2LinSupoo 27 }
	accPstnTabSupR2MeRecTime OBJECT-TYPE
	    SYNTAX INTEGER
	    ACCESS read-write
	    STATUS mandatory
	    DESCRIPTION
	       " Recognition timer for the metering patterns."
	    ::= { accR2LinSupoo 28 }
	accPstnTabSupR2MeDly OBJECT-TYPE
	    SYNTAX INTEGER
	    ACCESS read-write
	    STATUS mandatory
	    DESCRIPTION
	       " Delay timer for the metering patterns."
	    ::= { accR2LinSupoo 29 }
	accPstnTabSupR2MeOffTime OBJECT-TYPE
	    SYNTAX INTEGER
	    ACCESS read-write
	    STATUS mandatory
	    DESCRIPTION
	       " Metering pattern offtime timer"
            ::= { accR2LinSupoo 30 }
	accPstnTabSupR2MeOnTime OBJECT-TYPE
	    SYNTAX INTEGER
	    ACCESS read-write
	    STATUS mandatory
	    DESCRIPTION
	       " Metering pattern ontime."
            ::= { accR2LinSupoo 31 }
-- MISCELLANEOUS
    accMisc	OBJECT IDENTIFIER ::= { accNewLiberty 5 }
	accDsprmMessageLevel OBJECT-TYPE
	    SYNTAX INTEGER
	    ACCESS read-write
	    STATUS mandatory
	    DESCRIPTION
	       " Level for depth of messages from the DSPRM."
	    ::= { accMisc 1 }
	accPstnTabPstnDslIndex OBJECT-TYPE
	    SYNTAX INTEGER
	    ACCESS read-write
	    STATUS mandatory
	    DESCRIPTION
	      " Wonky index, used for displaying tables. (c/o james)"
            ::= { accMisc 2 }
	accPstnOperstatus OBJECT-TYPE
	    SYNTAX INTEGER
	    ACCESS read-write
	    STATUS mandatory
	    DESCRIPTION
	      " Current use of DSP (unallocated, idle, modem...)"
            ::= { accMisc 3 }

        accDsprmRelnqshFailTrap TRAP-TYPE
        ENTERPRISE   accDsprmTraps 
        VARIABLES  { accDsprmTrapMsg,
		     ifIndex ,
accTrapLogSeqNum}
        DESCRIPTION
                "Indicates that Relinquish has failed.
SEVERITY-DEFAULT: Indeterminate 
EVENTTYPE-DEFAULT: 10 
ADDITIONAL-TEXT-VARIABLES: { accTrapLogSeqNum,accDsprmTrapMsg }
PCAUSE-DEFAULT: 0 " 
 
        ::= 1 
        accDsprmLdspNotInUseTrap TRAP-TYPE
        ENTERPRISE   accDsprmTraps 
        VARIABLES  { accDsprmTrapMsg,
                     ifIndex ,
accTrapLogSeqNum}
        DESCRIPTION
                "Indicates that send has failed becuse LDSP is not
		 in use.
SEVERITY-DEFAULT: Minor 
EVENTTYPE-DEFAULT: 2 
ADDITIONAL-TEXT-VARIABLES: { accTrapLogSeqNum,accDsprmTrapMsg }
PCAUSE-DEFAULT: 110 " 
 
        ::= 2 
        accDsprmCucbErrTrap TRAP-TYPE
        ENTERPRISE   accDsprmTraps 
        VARIABLES  { accDsprmTrapMsg,
                     ifIndex ,
accTrapLogSeqNum}
        DESCRIPTION
                "Indicates that send has failed becuse of CUCB error
SEVERITY-DEFAULT: Minor 
EVENTTYPE-DEFAULT: 2 
ADDITIONAL-TEXT-VARIABLES: { accTrapLogSeqNum,accDsprmTrapMsg }
PCAUSE-DEFAULT: 110 " 
 
        ::= 3 
        accDsprmNoDataTrap TRAP-TYPE
        ENTERPRISE   accDsprmTraps 
        VARIABLES  { accDsprmTrapMsg,
                     ifIndex ,
accTrapLogSeqNum}
        DESCRIPTION
                "Indicates that send has failed becuse of no data
SEVERITY-DEFAULT: Minor 
EVENTTYPE-DEFAULT: 2 
ADDITIONAL-TEXT-VARIABLES: { accTrapLogSeqNum,accDsprmTrapMsg }
PCAUSE-DEFAULT: 110 " 
 
        ::= 4 
        accDsprmMemAllocTrap TRAP-TYPE
        ENTERPRISE   accDsprmTraps 
        VARIABLES  { accDsprmTrapMsg,
                     ifIndex ,
accTrapLogSeqNum}
        DESCRIPTION
                "Indicates that memory allocation failed for the NCI
SEVERITY-DEFAULT: Major 
EVENTTYPE-DEFAULT: 10 
ADDITIONAL-TEXT-VARIABLES: { accTrapLogSeqNum,accDsprmTrapMsg }
PCAUSE-DEFAULT: 32 " 
 
        ::= 5 
        accDsprmInvMplTrap TRAP-TYPE
        ENTERPRISE   accDsprmTraps 
        VARIABLES  { accDsprmTrapMsg ,
                      accTrapLogSeqNum}
        DESCRIPTION
                "Indicates that a packet has been received with an 
		 invalid MPL type
SEVERITY-DEFAULT: Major 
EVENTTYPE-DEFAULT: 2 
ADDITIONAL-TEXT-VARIABLES: { accTrapLogSeqNum,accDsprmTrapMsg }
PCAUSE-DEFAULT: 5 " 
 
        ::= 6 
END
