-- *****************************************************************
-- SSH-MIB:  Cisco private MIB
-- ****************************************************************

CIE1000-SSH-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    TruthValue FROM SNMPv2-TC
    ;

cie1000SshMib MODULE-IDENTITY
    LAST-UPDATED "201407010000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of the SSH MIB"
    REVISION    "201407010000Z"
    DESCRIPTION
        "Initial version"
    ::= { cie1000SwitchMgmt 49 }


cie1000SshMibObjects OBJECT IDENTIFIER
    ::= { cie1000SshMib 1 }

cie1000SshConfig OBJECT IDENTIFIER
    ::= { cie1000SshMibObjects 2 }

cie1000SshConfigGlobals OBJECT IDENTIFIER
    ::= { cie1000SshConfig 1 }

cie1000SshConfigGlobalsAdminState OBJECT-TYPE
    SYNTAX      TruthValue
    MAX-ACCESS  read-write
    STATUS      current
    DESCRIPTION
        "Enable/Disable the SSH functionality."
    ::= { cie1000SshConfigGlobals 1 }

cie1000SshMibConformance OBJECT IDENTIFIER
    ::= { cie1000SshMib 2 }

cie1000SshMibCompliances OBJECT IDENTIFIER
    ::= { cie1000SshMibConformance 1 }

cie1000SshMibGroups OBJECT IDENTIFIER
    ::= { cie1000SshMibConformance 2 }

cie1000SshConfigGlobalsInfoGroup OBJECT-GROUP
    OBJECTS     { cie1000SshConfigGlobalsAdminState }
    STATUS      current
    DESCRIPTION
        "A collection of objects."
    ::= { cie1000SshMibGroups 1 }

cie1000SshMibCompliance MODULE-COMPLIANCE
    STATUS      current
    DESCRIPTION
        "The compliance statement for the implementation."

    MODULE      -- this module

    MANDATORY-GROUPS { cie1000SshConfigGlobalsInfoGroup }

    ::= { cie1000SshMibCompliances 1 }

END
