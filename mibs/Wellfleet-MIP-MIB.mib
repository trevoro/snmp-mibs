Wellfleet-MIP-MIB DEFINITIONS ::= BEGIN


    IMPORTS

        IpAddress
                FROM RFC1155-SMI
        OBJECT-TYPE
                FROM RFC-1212
        wfMobileIpGroup
                FROM Wellfleet-COMMON-MIB;


	wfMobileIpHaTable OBJECT-TYPE
			SYNTAX SEQUENCE OF WfMobileIpHaEntry
		ACCESS  not-accessible
		STATUS  mandatory
		DESCRIPTION
			"Parameters in wfMobileIpHaTable"
		::= { wfMobileIpGroup 1 }

	wfMobileIpHaEntry OBJECT-TYPE
		SYNTAX WfMobileIpHaEntry
		ACCESS  not-accessible
		STATUS   mandatory
		DESCRIPTION
			"An entry in wfMobileIpHaTable."
		INDEX	{ wfMobileIpHaAddr,
			  wfMobileIpHaCct }
		::= {wfMobileIpHaTable 1}

	WfMobileIpHaEntry ::= SEQUENCE {
		wfMobileIpHaCreate
			INTEGER,
		wfMobileIpHaEnable
			INTEGER,
		wfMobileIpHaState
			INTEGER,
		wfMobileIpHaAddr
			IpAddress,	
		wfMobileIpHaCct
			INTEGER,
		wfMobileIpHaProtoMap
			OCTET STRING,
		wfMobileIpHaStatsEnable
			INTEGER,
		wfMobileIpHaDebugLevel
			INTEGER
		}

    wfMobileIpHaCreate	OBJECT-TYPE
	SYNTAX	INTEGER {
		    create(1),
		    delete(2)
		}
	ACCESS  read-write
	STATUS  mandatory
	DESCRIPTION
		"Create/Delete parameter. Default is created.
		Users perform a set operation on this object in order to
		create/delete an wfMobileIpHaEntry instance."
	DEFVAL  { create }
	::= { wfMobileIpHaEntry 1 }
		
    wfMobileIpHaEnable	OBJECT-TYPE
	SYNTAX	INTEGER {
		    enabled(1),
		    disabled(2)
		}
	ACCESS  read-write
	STATUS  mandatory
	DESCRIPTION
		"Enable/Disable parameter. Default is enabled.
		Users perform a set operation on this object in order to
		enable/disable Mobile Ip Home Agent interface."
	DEFVAL	{ enabled }
	::= { wfMobileIpHaEntry 2 }

    wfMobileIpHaState	OBJECT-TYPE
	SYNTAX	INTEGER {
		    up(1),
		    down(2),
		    init(3),
		    notpres(4)
		}
	ACCESS	read-only
	STATUS	mandatory
	DESCRIPTION
		"The current state of  Mobile Ip Home Agent interface."
	DEFVAL	{ notpres }
	::= { wfMobileIpHaEntry 3 }

    wfMobileIpHaAddr	OBJECT-TYPE
	SYNTAX	IpAddress
	ACCESS	read-only
	STATUS	mandatory
		DESCRIPTION
		"The IP interface to run Mobile Ip Home Agent on."
	::= {wfMobileIpHaEntry 4}

    wfMobileIpHaCct	OBJECT-TYPE
	SYNTAX  INTEGER 
	ACCESS  read-only
	STATUS  mandatory
		DESCRIPTION
			"Circuit number of the Home Agent interface."
	::= {wfMobileIpHaEntry 5}

    wfMobileIpHaProtoMap OBJECT-TYPE
	SYNTAX	OCTET STRING
	ACCESS	read-write
	STATUS  mandatory
	DESCRIPTION
		"HA_PROTO_IP  1
		 HA_PROTO_IPX 2"
	::= { wfMobileIpHaEntry 6 }

    wfMobileIpHaStatsEnable OBJECT-TYPE
	SYNTAX  INTEGER {
		    enabled(1),
		    disabled(2)
		}
	ACCESS  read-write
	STATUS  mandatory
	DESCRIPTION
		"Enable/Disable parameter. Default is enabled.
		Users perform a set operation on this object in order to
		enable/disable mib statistics for Mobile Ip Home Agent
		interface."
	DEFVAL  { enabled }
	::= { wfMobileIpHaEntry 7 }

   wfMobileIpHaDebugLevel	OBJECT-TYPE
	SYNTAX  INTEGER 
	ACCESS  read-write
	STATUS  mandatory
	DESCRIPTION
		"A parameter to specify which messages to be printed 
		 in to the log.  Add the types up for level desired :

			Level	Type
			------------
			1	Info
			2	Warning
			4	Fatal
			8	Debug
			15	All
		"
	::= { wfMobileIpHaEntry 8 }

	wfMobileIpSpiTable OBJECT-TYPE
		SYNTAX SEQUENCE OF WfMobileIpSpiEntry
		ACCESS  not-accessible
		STATUS  mandatory
		DESCRIPTION
			"Parameters in wfMobileIpSpiTable"
		::= { wfMobileIpGroup 2 }

	wfMobileIpSpiEntry OBJECT-TYPE
		SYNTAX WfMobileIpSpiEntry
		ACCESS  not-accessible
		STATUS   mandatory
		DESCRIPTION
			"An entry in wfMobileIpSpiTable."
		INDEX   { wfMobileIpSpiValue }
		::= {wfMobileIpSpiTable 1}

	WfMobileIpSpiEntry ::= SEQUENCE {
		wfMobileIpSpiCreate
			INTEGER,
		wfMobileIpSpiValue
			INTEGER,
		wfMobileIpSpiKey
			OCTET STRING,
		wfMobileIpSpiAuthType
			INTEGER
	}

    wfMobileIpSpiCreate  OBJECT-TYPE
        SYNTAX  INTEGER {
                    create(1),
                    delete(2)
                }
        ACCESS  read-write
        STATUS  mandatory
        DESCRIPTION
                "Create/Delete parameter. Default is created.
                Users perform a set operation on this object in order to
                create/delete an wfMobileIpSpiEntry instance."
        DEFVAL  { create }
        ::= { wfMobileIpSpiEntry 1 }

    wfMobileIpSpiValue	OBJECT-TYPE
		SYNTAX	INTEGER (256..65535)
		ACCESS	read-only
		STATUS	mandatory
		DESCRIPTION
	        "..."
		::= { wfMobileIpSpiEntry 2 }

    wfMobileIpSpiKey	OBJECT-TYPE
		SYNTAX	OCTET STRING
		ACCESS	read-write
		STATUS	mandatory
		DESCRIPTION
			"..."
		::= { wfMobileIpSpiEntry 3 }

    wfMobileIpSpiAuthType OBJECT-TYPE
		SYNTAX  INTEGER {
		   md5(1)
		}
        ACCESS  read-write
        STATUS  mandatory
        DESCRIPTION
                "..."
		DEFVAL	{ md5 }
        ::= { wfMobileIpSpiEntry 4 }


    wfHaMobilityBindingTable  OBJECT-TYPE
        SYNTAX      SEQUENCE OF WfHaMobilityBindingEntry
        ACCESS      not-accessible
        STATUS      mandatory
        DESCRIPTION
                "A table containing the home agent's mobility binding
                list.  The home agent updates this table in response
                to registration events from mobile nodes."
		::= { wfMobileIpGroup 3 }

    wfHaMobilityBindingEntry OBJECT-TYPE
        SYNTAX      WfHaMobilityBindingEntry
        ACCESS      not-accessible
        STATUS      mandatory
        DESCRIPTION
                "An IP entry on the mobility binding list."
        INDEX   { wfHaMobilityBindingIdx, wfHaMobilityBindingCOA }
        ::= { wfHaMobilityBindingTable 1 }

    WfHaMobilityBindingEntry ::= SEQUENCE {
		wfHaMobilityBindingIdx
			INTEGER,
		wfHaMobilityBindingMN    
			IpAddress,
		wfHaMobilityBindingCOA   
			IpAddress,
		wfHaMobilityBindingSourceAddress    
			IpAddress,
		wfHaMobilityBindingRegFlags    
			INTEGER,
		wfHaMobilityBindingRegIDLow 
			INTEGER,
		wfHaMobilityBindingRegIDHigh 
			INTEGER,
		wfHaMobilityBindingTimeGranted 
			INTEGER,
		wfHaMobilityBindingTimeRemaining 
			INTEGER
	}

    wfHaMobilityBindingIdx   OBJECT-TYPE
        SYNTAX          INTEGER
        ACCESS          read-only
        STATUS          mandatory
        DESCRIPTION
                 "The index for IP mobile node in the 
                  home agent's IP binding table."
        ::= { wfHaMobilityBindingEntry 1 }

    wfHaMobilityBindingMN    OBJECT-TYPE
        SYNTAX      IpAddress
        ACCESS      read-only
        STATUS      mandatory
        DESCRIPTION
                "Mobile node's home (IP) address."
        ::= { wfHaMobilityBindingEntry 2 }

    wfHaMobilityBindingCOA   OBJECT-TYPE
        SYNTAX      IpAddress
        ACCESS      read-only
        STATUS      mandatory
        DESCRIPTION
                "Mobile node's care-of-address. One mobile node can
                have multiple bindings with different
                care-of-addresses."
        ::= { wfHaMobilityBindingEntry 3 }

    wfHaMobilityBindingSourceAddress    OBJECT-TYPE
        SYNTAX      IpAddress
        ACCESS      read-only
        STATUS      mandatory
        DESCRIPTION
                "IP source address of the Registration Request as
                received by the home agent.  Will be either a mobile
                node's co-located care-of address or an address of the
                foreign agent."
        ::= { wfHaMobilityBindingEntry 4 }

    wfHaMobilityBindingRegFlags OBJECT-TYPE
        SYNTAX      INTEGER (0..65535)
        ACCESS      read-only
        STATUS      mandatory
        DESCRIPTION
                "Registration flags sent by mobile node."
        ::= { wfHaMobilityBindingEntry 5 }

    wfHaMobilityBindingRegIDLow OBJECT-TYPE
        SYNTAX      INTEGER (0..65535)
        ACCESS      read-only
        STATUS      mandatory
        DESCRIPTION
                "Low 32 bits of Identification used in that binding by
                the mobile node."
        ::= { wfHaMobilityBindingEntry 6 }

    wfHaMobilityBindingRegIDHigh OBJECT-TYPE
        SYNTAX      INTEGER (0..65535)
        ACCESS      read-only
        STATUS      mandatory
        DESCRIPTION
               "High 32 bits of Identification used in that binding by
                the mobile node."
        ::= { wfHaMobilityBindingEntry 7 }

    wfHaMobilityBindingTimeGranted OBJECT-TYPE
        SYNTAX      INTEGER (0..65535)
        ACCESS      read-only
        STATUS      mandatory
        DESCRIPTION
                "The lifetime in seconds granted to the mobile node
                for this registration."
        ::= { wfHaMobilityBindingEntry 8 }

    wfHaMobilityBindingTimeRemaining OBJECT-TYPE
        SYNTAX      INTEGER (0..65535)
        ACCESS      read-only
        STATUS      mandatory
        DESCRIPTION
                "The number of seconds remaining until the
                registration is expired. It has the same initial value
                as wfHaMobilityBindingTimeGranted, and is counted down
                by the home agent."
        ::= { wfHaMobilityBindingEntry 9 }

	wfHaIpxMobilityBindingTable  OBJECT-TYPE
        SYNTAX      SEQUENCE OF WfHaIpxMobilityBindingEntry
        ACCESS      not-accessible
        STATUS      mandatory
        DESCRIPTION
                "A table containing the home agent's IPX mobility binding
                list.  The home agent updates this table in response
                to registration events from IPX mobile nodes."
        ::= { wfMobileIpGroup 4 }

	wfHaIpxMobilityBindingEntry OBJECT-TYPE
        SYNTAX      WfHaIpxMobilityBindingEntry
        ACCESS      not-accessible
        STATUS      mandatory
        DESCRIPTION
                "An IPX entry on the mobility binding list."
        INDEX   { wfHaIpxMobilityBindingIdx, wfHaIpxMobilityBindingCOA }
        ::= { wfHaIpxMobilityBindingTable 1 }

    WfHaIpxMobilityBindingEntry ::= SEQUENCE {
		wfHaIpxMobilityBindingIdx
			INTEGER,
		wfHaIpxMobilityBindingMN
			OCTET STRING,
		wfHaIpxMobilityBindingCOA
			IpAddress,
		wfHaIpxMobilityBindingSourceAddress
			IpAddress,
		wfHaIpxMobilityBindingRegFlags
			INTEGER,
		wfHaIpxMobilityBindingRegIDLow
			INTEGER,
		wfHaIpxMobilityBindingRegIDHigh
			INTEGER,
		wfHaIpxMobilityBindingTimeGranted
			INTEGER,
		wfHaIpxMobilityBindingTimeRemaining
			INTEGER
	}

	wfHaIpxMobilityBindingIdx	OBJECT-TYPE
		SYNTAX		INTEGER
		ACCESS		read-only
		STATUS		mandatory
		DESCRIPTION
				"The index for IPX mobile node in the home agent's 
				IPX binding table."
		::= { wfHaIpxMobilityBindingEntry 1 }

	wfHaIpxMobilityBindingMN    OBJECT-TYPE
        SYNTAX      OCTET STRING (SIZE(4))
        ACCESS      read-only
        STATUS      mandatory
        DESCRIPTION
                "The address of the IPX mobile node."
        ::= { wfHaIpxMobilityBindingEntry 2 }

    wfHaIpxMobilityBindingCOA   OBJECT-TYPE
        SYNTAX      IpAddress
        ACCESS      read-only
        STATUS      mandatory
        DESCRIPTION
                "Mobile node's care-of-address. One mobile node can
                have multiple bindings with different
                care-of-addresses."
        ::= { wfHaIpxMobilityBindingEntry 3 }

    wfHaIpxMobilityBindingSourceAddress    OBJECT-TYPE
        SYNTAX      IpAddress
        ACCESS      read-only
        STATUS      mandatory
        DESCRIPTION
                "IP source address of the Registration Request as
                received by the home agent.  Will be either a mobile
                node's co-located care-of address or an address of the
                foreign agent."
        ::= { wfHaIpxMobilityBindingEntry 4 }

	 wfHaIpxMobilityBindingRegFlags OBJECT-TYPE
        SYNTAX      INTEGER (0..65535)
        ACCESS      read-only
        STATUS      mandatory
        DESCRIPTION
                "Registration flags sent by mobile node."
        ::= { wfHaIpxMobilityBindingEntry 5 }

    wfHaIpxMobilityBindingRegIDLow OBJECT-TYPE
        SYNTAX      INTEGER (0..65535)
        ACCESS      read-only
        STATUS      mandatory
        DESCRIPTION
                "Low 32 bits of Identification used in that binding by
                the mobile node."
        ::= { wfHaIpxMobilityBindingEntry 6 }

    wfHaIpxMobilityBindingRegIDHigh OBJECT-TYPE
        SYNTAX      INTEGER (0..65535)
        ACCESS      read-only
        STATUS      mandatory
        DESCRIPTION
               "High 32 bits of Identification used in that binding by
                the mobile node."
        ::= { wfHaIpxMobilityBindingEntry 7 }

    wfHaIpxMobilityBindingTimeGranted OBJECT-TYPE
        SYNTAX      INTEGER (0..65535)
        ACCESS      read-only
        STATUS      mandatory
        DESCRIPTION
                "The lifetime in seconds granted to the mobile node
                for this registration."
        ::= { wfHaIpxMobilityBindingEntry 8 }

    wfHaIpxMobilityBindingTimeRemaining OBJECT-TYPE
        SYNTAX      INTEGER (0..65535)
        ACCESS      read-only
        STATUS      mandatory
        DESCRIPTION
                "The number of seconds remaining until the
                registration is expired. It has the same initial value
                as wfHaMobilityBindingTimeGranted, and is counted down
                by the home agent."
        ::= { wfHaIpxMobilityBindingEntry 9 }


    END -- Wellfleet-MIP-MIB
