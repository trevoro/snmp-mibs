-- *****************************************************************
-- CISCO-IMAGE-CAPABILITY.my: CISCO-IMAGE-MIB AGENT-CAPABILITIES
-- 
-- Jan 1995, Yunsen Wang
-- 
-- Copyright (c) 1995 by cisco Systems, Inc.
-- All rights reserved.
-- 
-- *****************************************************************


CISCO-IMAGE-CAPABILITY DEFINITIONS ::= BEGIN

IMPORTS
	MODULE-IDENTITY
		FROM SNMPv2-SMI
	AGENT-CAPABILITIES
		FROM SNMPv2-CONF
	ciscoAgentCapability
		FROM CISCO-SMI;

ciscoImageMIBCapability	MODULE-IDENTITY
		LAST-UPDATED	"9501250000Z"
		ORGANIZATION    "Cisco Systems, Inc."
		CONTACT-INFO
			"	Cisco Systems
				Customer Service
			
			Postal:	170 West Tasman Drive
				San Jose, CA  95134
				USA
			
			   Tel:	+1 800 553-NETS
			
			E-mail:	cs-snmp@cisco.com"
		DESCRIPTION
			"Agent capabilities for CISCO-IMAGE-MIB"
		REVISION	"9501250000Z"
		DESCRIPTION
			"Initial version of this MIB module."
	::= { ciscoAgentCapability 45 }

ciscoImageMIBCapabilityV10R01 AGENT-CAPABILITIES

PRODUCT-RELEASE "Cisco IOS 10.2"
STATUS		current
DESCRIPTION	"ciscoImageMIB capabilites"

SUPPORTS	CISCO-IMAGE-MIB
INCLUDES	{ ciscoImageMIBGroup }

	::= { ciscoImageMIBCapability 1 }

END
