-- *****************************************************************************
-- Unisphere-Data-V35-MIB
--
-- Unisphere Networks Enterprise MIB
--   X.21/V.35 Server MIB
--
-- Copyright (c) 2002 Unisphere Networks, Inc.  All Rights Reserved.
-- *****************************************************************************

Unisphere-Data-V35-MIB DEFINITIONS ::= BEGIN

IMPORTS
    MODULE-IDENTITY, OBJECT-TYPE, Unsigned32
        FROM SNMPv2-SMI
    MODULE-COMPLIANCE, OBJECT-GROUP
        FROM SNMPv2-CONF
    InterfaceIndex
        FROM IF-MIB
    usDataMibs
        FROM Unisphere-Data-MIBs;

usdV35MIB  MODULE-IDENTITY
    LAST-UPDATED "200202081625Z"  -- 08-Feb-02 11:25 AM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The X.21/V.35 Server MIB for the Unisphere Networks enterprise."
    -- Revision History
    REVISION    "200202081625Z"  -- 08-Feb-02 11:25 AM EST  - RX 4.0
    DESCRIPTION
        "Initial version of this MIB module."
    ::= { usDataMibs 59 }


-- +++++++++++++++++++++++++++++++++++++++++++++++++++++++++++++++++++++++++++++
-- Managed objects
-- +++++++++++++++++++++++++++++++++++++++++++++++++++++++++++++++++++++++++++++

usdV35Objects     OBJECT IDENTIFIER ::= { usdV35MIB 1 }

-- /////////////////////////////////////////////////////////////////////////////
--
-- X.21/V.35 Interfaces
--
-- /////////////////////////////////////////////////////////////////////////////

--
-- The X.21/V.35 Interface Table
--
usdV35IfTable  OBJECT-TYPE
    SYNTAX      SEQUENCE OF UsdV35IfEntry
    MAX-ACCESS  not-accessible
    STATUS      current
    DESCRIPTION
        "This table contains entries for X.21/V.35 interfaces present in the
        system.  This table provides an extension to the
        Unisphere-Data-HDLC-MIB.usdHdlcIfTable for HDLC interfaces that support
        X.21/V.35 signalling."
    ::= { usdV35Objects 2 }

usdV35IfEntry  OBJECT-TYPE
    SYNTAX      UsdV35IfEntry
    MAX-ACCESS  not-accessible
    STATUS      current
    DESCRIPTION
        "Each entry describes the characteristics of an X.21/V.35 interface."
    INDEX     { usdV35IfIndex }
    ::= { usdV35IfTable 1 }

UsdV35IfEntry ::= SEQUENCE {
    usdV35IfIndex           InterfaceIndex,
    usdV35IfType            INTEGER,
    usdV35IfMode            INTEGER,
    usdV35IfClockRate       Unsigned32,
    usdV35IfNrzEncoding     INTEGER,
    usdV35IfTxClock         INTEGER,
    usdV35IfIgnoreDcd       INTEGER,
    usdV35IfLoopback        INTEGER }

usdV35IfIndex  OBJECT-TYPE
    SYNTAX      InterfaceIndex
    MAX-ACCESS  not-accessible
    STATUS      current
    DESCRIPTION
        "The ifIndex of the X.21/V.35 interface.  It has the same value as the
        usdHdlcIfIndex for the common interface."
    ::= { usdV35IfEntry 1 }

usdV35IfType  OBJECT-TYPE
    SYNTAX      INTEGER {
                    x21(0),
                    v35(1),
                    interfaceTypeNoCable(2) }
    MAX-ACCESS  read-only
    STATUS      current
    DESCRIPTION
        "Read only parameter of interface type X.21/V.35."
    ::= {usdV35IfEntry 2}

usdV35IfMode  OBJECT-TYPE
    SYNTAX      INTEGER {
                    dte(0),
                    dce(1),
                    interfaceModeNoCable(2) }
    MAX-ACCESS  read-only
    STATUS      current
    DESCRIPTION
        "Read only parameter of interface mode of interface X.21/V.35 Data
        Terminating Equipment(DTE)/Data Communication Equipment(DCE)."
    ::= { usdV35IfEntry 3 }

usdV35IfClockRate  OBJECT-TYPE
    SYNTAX      Unsigned32
    UNITS       "hertz"
    MAX-ACCESS  read-write
    STATUS      current
    DESCRIPTION
        "The clock rate setting in hertz for this X.21/V.35 interface.  Only the
        following values are valid: 1200, 2400, 4800, 9600, 19200, 38400, 56000,
        64000, 128000, 1024000, 1536000, 2048000, 3072000, 4096000, 4915200,
        6144000, and 8192000.  If a value other than one of the predefined
        values is set, then the closest matching value is used.

        The clock rate parameter is only meaningful when the interface is in DCE
        mode.  When the interface is in DTE mode, the value is simply ignored."
    DEFVAL    { 2048000 }
    ::= { usdV35IfEntry 4 }

usdV35IfNrzEncoding  OBJECT-TYPE
    SYNTAX      INTEGER {
                    normal(0),
                    inverted(1) }
    MAX-ACCESS  read-write
    STATUS      current
    DESCRIPTION
        "The non-return-to-zero (NRZ) encoding for X.21/V.35 interface.
        Inverted encoding is provided with NRZI-encoding command, which is
        non-return-to-zero inverted (NRZI) encoding."
    DEFVAL    { normal }
    ::= { usdV35IfEntry 5 }

usdV35IfTxClock  OBJECT-TYPE
    SYNTAX      INTEGER {
                    normal(0),
                    inverted(1) }
    MAX-ACCESS  read-write
    STATUS      current
    DESCRIPTION
        "There is an option of inverting the transmit clock signal for X.21/V.35
        interface.  Inverting the tranmit clock is used to compensate for skews
        between the clock and data when transmitting across long cables at fast
        data rates."
    DEFVAL    { normal }
    ::= { usdV35IfEntry 6 }

usdV35IfIgnoreDcd  OBJECT-TYPE
    SYNTAX      INTEGER {
                    ignoredNone(0),
                    dcdIgnored(1),
                    linkStateIgnored(2) }
    MAX-ACCESS  read-write
    STATUS      current
    DESCRIPTION
        "When in X.21/V.35 DTE mode we have the capability of ignoring the DCD
        signal in determining whether or not an interface is up."
    DEFVAL    { ignoredNone }
    ::= { usdV35IfEntry 7 }

usdV35IfLoopback  OBJECT-TYPE
    SYNTAX      INTEGER {
                    none(0),
                    loopback(1) }
    MAX-ACCESS  read-write
    STATUS      current
    DESCRIPTION
        "Loopback interface is configured (or not) for X.21/V.35 interface"
    DEFVAL  { none }
    ::= { usdV35IfEntry 8 }


-- +++++++++++++++++++++++++++++++++++++++++++++++++++++++++++++++++++++++++++++
-- Notification control objects
-- +++++++++++++++++++++++++++++++++++++++++++++++++++++++++++++++++++++++++++++
-- No notifications are defined in this MIB.  Placeholder follows.
-- usdV35TrapControl OBJECT IDENTIFIER ::= { usdV35MIB 2 }

-- +++++++++++++++++++++++++++++++++++++++++++++++++++++++++++++++++++++++++++++
-- Notifications
-- +++++++++++++++++++++++++++++++++++++++++++++++++++++++++++++++++++++++++++++
-- No notifications are defined in this MIB.  Placeholders follow.
-- The following two OBJECT IDENTIFIERS are used to define SNMPv2
-- Notifications that are easily translated into SNMPv1 Traps.
-- usdV35Traps            OBJECT IDENTIFIER ::= { usdV35MIB 3 }
-- usdV35TrapPrefix       OBJECT IDENTIFIER ::= { usdV35Traps 0 }


-- +++++++++++++++++++++++++++++++++++++++++++++++++++++++++++++++++++++++++++++
-- Conformance information
-- +++++++++++++++++++++++++++++++++++++++++++++++++++++++++++++++++++++++++++++

usdV35Conformance OBJECT IDENTIFIER ::= { usdV35MIB 4 }
usdV35Compliances OBJECT IDENTIFIER ::= { usdV35Conformance 1 }
usdV35Groups      OBJECT IDENTIFIER ::= { usdV35Conformance 2 }

-- compliance statements

usdV35Compliance  MODULE-COMPLIANCE
    STATUS      current
    DESCRIPTION
        "The compliance statement for entities that implement the Unisphere
        X.21/V.35 MIB."
    MODULE   -- this module
        MANDATORY-GROUPS {
            usdV35Group }
    ::= { usdV35Compliances 1 }


-- units of conformance

usdV35Group  OBJECT-GROUP
    OBJECTS {
        usdV35IfType,
        usdV35IfMode,
        usdV35IfClockRate,
        usdV35IfNrzEncoding,
        usdV35IfTxClock,
        usdV35IfIgnoreDcd,
        usdV35IfLoopback }
    STATUS      current
    DESCRIPTION
        "A collection of objects providing management of X.21/V.35 interfaces in
        a Unisphere product."
    ::= { usdV35Groups 1 }

END
