IP-NAT-MIB DEFINITIONS ::= BEGIN
	IMPORTS
        OBJECT-TYPE, MODULE-IDENTITY, 
        Counter32, IpAddress, Integer32
		FROM SNMPv2-SMI
        DisplayString, common
		FROM USR-DEFINITIONS-MIB;
   usripNat MODULE-IDENTITY
         LAST-UPDATED "200205051340Z"
         ORGANIZATION "CommWorks Corporation, a 3Com Company"
         CONTACT-INFO "Customer Support"
         DESCRIPTION
                 "The commWorks enterprise defined MIB objects
                   for Network Address Translation."
--       REVISION "200205051340Z"
--       DESCRIPTION "Made SNMPv2 compliant"
         ::= { common 78 }
-- Begin managed object definitions here...
ipNatVersion OBJECT-TYPE
	SYNTAX		DisplayString
	MAX-ACCESS	read-only
	STATUS		current
	DESCRIPTION
		"The current software version of the NAT application."
::= { usripNat 1 }
--
-- The NAT session Table.
-- Use the same index as that used in the Flow Manager Connection Table
-- to allow the NAT sessions to be correlated with their respective
-- flows. (Note: 2 flows per NAT session.)
--
ipNatSessTable OBJECT-TYPE
	SYNTAX SEQUENCE OF IpNatSessEntry
	MAX-ACCESS	not-accessible
	STATUS current
	DESCRIPTION
		"The table of NAT sessions."
::= { usripNat 2 }
ipNatSessEntry OBJECT-TYPE
	SYNTAX IpNatSessEntry
	MAX-ACCESS	not-accessible
	STATUS current
	DESCRIPTION
		"An entry for one NAT session."
	INDEX { ipNatSessIndex }
::= { ipNatSessTable 1 }
IpNatSessEntry ::= SEQUENCE {
	ipNatSessIndex Integer32,
	ipNatSessSrcIpAddress	IpAddress,
	ipNatSessDestIpAddress IpAddress,
	ipNatSessTransIpAddress	IpAddress,
	ipNatSessProtocol	INTEGER,
	ipNatSessDirection	INTEGER,
	ipNatSessSrcPort	Integer32 (0..65535),
	ipNatSessDestPort	Integer32 (0..65535),
	ipNatSessTransPort	Integer32 (0..65535),
	ipNatSessLifetime	Integer32
	}
ipNatSessIndex OBJECT-TYPE
    SYNTAX  Integer32
    MAX-ACCESS  read-only
    STATUS current
    DESCRIPTION
        "The index value which indentifies the NAT session
        to which this entry is applicable."
::= { ipNatSessEntry 1 }
ipNatSessSrcIpAddress OBJECT-TYPE
	SYNTAX	IpAddress
	MAX-ACCESS	read-only
	STATUS current
	DESCRIPTION
		"The source IP Address of the packet that initiated
		the flow associated with this NAT session."
::= { ipNatSessEntry 2 }
ipNatSessDestIpAddress OBJECT-TYPE
	SYNTAX	IpAddress
	MAX-ACCESS	read-only
	STATUS current
	DESCRIPTION
		"The destination IP Address of the packet that initiated
		the flow associated with this NAT session."
::= { ipNatSessEntry 3 }
ipNatSessTransIpAddress OBJECT-TYPE
	SYNTAX	IpAddress
	MAX-ACCESS	read-only
	STATUS current
	DESCRIPTION
		"The translation IP Address used by this NAT session."
::= { ipNatSessEntry 4 }
ipNatSessProtocol OBJECT-TYPE
	SYNTAX	INTEGER { icmp(1), tcp(6), udp(17) }
	MAX-ACCESS	read-only
	STATUS current
	DESCRIPTION
		"The value of icmp(1) indicates that this NAT session is using
	 	ICMP	
		The value of tcp(6) indicates that this NAT session is using
		TCP
		The value of udp(17) indicates that this NAT session is
		using UDP"
::= { ipNatSessEntry 5 }
ipNatSessDirection OBJECT-TYPE
	SYNTAX	INTEGER { inbound(2), outbound(1) }
	MAX-ACCESS	read-only
	STATUS current
	DESCRIPTION
		"The direction of the packet that initiated the flow
		associated with this NAT session."
::= { ipNatSessEntry 6 }
ipNatSessSrcPort OBJECT-TYPE
	SYNTAX	Integer32 (0..65535)
	MAX-ACCESS	read-only
	STATUS current
	DESCRIPTION
		"For UDP and TCP NAT sessions, the source port number of the
		packet that initiated the flow associated with this NAT
		session.
		For neither UDP nor TCP NAT sessions this value is 0."
::= { ipNatSessEntry 7 }
ipNatSessDestPort OBJECT-TYPE
	SYNTAX	Integer32 (0..65535)
	MAX-ACCESS	read-only
	STATUS current
	DESCRIPTION
		"For UDP and TCP NAT sessions, the destination port number of
		the packet that initiated the flow associated with this NAT
		session.
		For neither UDP nor TCP NAT sessions this value is 0."
::= { ipNatSessEntry 8 }
ipNatSessTransPort OBJECT-TYPE
	SYNTAX	Integer32 (0..65535)
	MAX-ACCESS	read-only
	STATUS current
	DESCRIPTION
		"For UDP and TCP NAT sessions, the translation port number of
		this NAT session.
		For neither UDP nor TCP NAT sessions this value is 0. "
::= { ipNatSessEntry 9 }
ipNatSessLifetime OBJECT-TYPE
	SYNTAX Integer32
	MAX-ACCESS	read-only
	STATUS current
	DESCRIPTION
		"The number of seconds that this translation session has
		existed."
::= { ipNatSessEntry 10 }
--
-- NAT statistics.
-- Depending on whether the Flow Manager provides the NAT application
-- with an interface index or only an inbound/outbound indication will
-- determine the table index.
--
ipNatStatsTable OBJECT-TYPE
	SYNTAX SEQUENCE OF IpNatStatsEntry
	MAX-ACCESS	not-accessible
	STATUS current
	DESCRIPTION
		"The table of NAT statistics."
::= { usripNat 3 }
ipNatStatsEntry OBJECT-TYPE
	SYNTAX	IpNatStatsEntry
	MAX-ACCESS	not-accessible
	STATUS current
	DESCRIPTION
		"An entry for one NAT session."
	INDEX { ipNatStatsIndex }
::= { ipNatStatsTable 1 }
IpNatStatsEntry ::= SEQUENCE {
	ipNatStatsIndex	Integer32,
	ipNatStatsSessSuccess	Counter32,
	ipNatStatsSessFail	Counter32,
	ipNatStatsInTransPkts	Counter32,
	ipNatStatsInDiscards	Counter32,
	ipNatStatsOutTransPkts	Counter32,
	ipNatStatsOutDiscards	Counter32
	}
ipNatStatsIndex OBJECT-TYPE
	SYNTAX	Integer32
	MAX-ACCESS	read-only
	STATUS current
	DESCRIPTION
		"The index value which indentifies the set of statistics.
		INCOMING(2) or outgoing(1) "
::= { ipNatStatsEntry 1 }
ipNatStatsSessSuccess OBJECT-TYPE
	SYNTAX	Counter32
	MAX-ACCESS	read-only
	STATUS current
	DESCRIPTION
		"The number of NAT sessions that have been successfully
		created."
::= { ipNatStatsEntry 2 }
ipNatStatsSessFail OBJECT-TYPE
	SYNTAX	Counter32
	MAX-ACCESS	read-only
	STATUS current
	DESCRIPTION
		"The number of NAT sessions attempts that have been 
		failed due to either the maximum number of N discarded."
::= { ipNatStatsEntry 3 }
ipNatStatsInTransPkts OBJECT-TYPE
	SYNTAX	Counter32
	MAX-ACCESS	read-only
	STATUS current
	DESCRIPTION
		"The number of INCOMING packets that have been successfully
		translated."
::= { ipNatStatsEntry 4 }
ipNatStatsInDiscards OBJECT-TYPE
	SYNTAX	Counter32
	MAX-ACCESS	read-only
	STATUS current
	DESCRIPTION
		"The number of INCOMING packets that have been discarded."
::= { ipNatStatsEntry 5 }
ipNatStatsOutTransPkts OBJECT-TYPE
	SYNTAX	Counter32
	MAX-ACCESS	read-only
	STATUS current
	DESCRIPTION
		"The number of outgoing packets that have been successfully
		translated."
::= { ipNatStatsEntry 6 }
ipNatStatsOutDiscards OBJECT-TYPE
	SYNTAX	Counter32
	MAX-ACCESS	read-only
	STATUS current
	DESCRIPTION
		"The number of outgoing packets that have been discarded."
::= { ipNatStatsEntry 7 }
END
