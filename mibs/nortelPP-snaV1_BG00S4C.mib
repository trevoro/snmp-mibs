Nortel-Magellan-Passport-SnaMIB
DEFINITIONS ::= BEGIN



IMPORTS

      OBJECT-TYPE
   FROM RFC-1212

      passportMIBs
   FROM Nortel-Magellan-Passport-UsefulDefinitionsMIB

      Counter32,
      RowPointer,
      DisplayString,
      StorageType,
      RowStatus,
      Gauge32,
      Integer32,
      Unsigned32
   FROM Nortel-Magellan-Passport-StandardTextualConventionsMIB

      DashedHexString,
      NonReplicated,
      HexString
   FROM Nortel-Magellan-Passport-TextualConventionsMIB

      vrIndex,
      vrPpIndex,
      vrPp,
      vr
   FROM Nortel-Magellan-Passport-VirtualRouterMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Sna Enterprise MIB."

snaMIB OBJECT IDENTIFIER ::= { passportMIBs 56 }










-- Vr/<string> Pp/<string> SnaPort
-- The SnaPort component contains DLR attributes specific to this 
-- port. A semantic check verifies that an SnaPort component cannot 
-- be added or deleted unless an Sna component under VR is present.

vrPpSnaPort OBJECT IDENTIFIER ::= { vrPp 15 }



vrPpSnaPortRowStatusTable OBJECT-TYPE
   SYNTAX     SEQUENCE OF VrPpSnaPortRowStatusEntry
   ACCESS     not-accessible
   STATUS     mandatory
   DESCRIPTION
     "This entry controls the addition and deletion of 
      vrPpSnaPort components."
::= { vrPpSnaPort 1 }

vrPpSnaPortRowStatusEntry OBJECT-TYPE
   SYNTAX     VrPpSnaPortRowStatusEntry
   ACCESS     not-accessible
   STATUS     mandatory
   DESCRIPTION
     "A single entry in the table represents a single 
      vrPpSnaPort component."
   INDEX {
      vrIndex,
      vrPpIndex,
      vrPpSnaPortIndex }
::= { vrPpSnaPortRowStatusTable 1 }

VrPpSnaPortRowStatusEntry ::= SEQUENCE {
   vrPpSnaPortRowStatus
      RowStatus,
   vrPpSnaPortComponentName
      DisplayString,
   vrPpSnaPortStorageType
      StorageType,
   vrPpSnaPortIndex
      NonReplicated }

vrPpSnaPortRowStatus OBJECT-TYPE
   SYNTAX     RowStatus 
   ACCESS     read-write
   STATUS     mandatory
   DESCRIPTION
     "This variable is used as the basis for SNMP naming of
      vrPpSnaPort components.
      These components can be added and deleted."
::= { vrPpSnaPortRowStatusEntry 1 }

vrPpSnaPortComponentName OBJECT-TYPE
   SYNTAX     DisplayString 
   ACCESS     read-only
   STATUS     mandatory
   DESCRIPTION
     "This variable provides the component's string name for
      use with the ASCII Console Interface"
::= { vrPpSnaPortRowStatusEntry 2 }

vrPpSnaPortStorageType OBJECT-TYPE
   SYNTAX     StorageType 
   ACCESS     read-only
   STATUS     mandatory
   DESCRIPTION
     "This variable represents the storage type value for the
      vrPpSnaPort tables."
::= { vrPpSnaPortRowStatusEntry 4 }

vrPpSnaPortIndex OBJECT-TYPE
   SYNTAX     NonReplicated 
   ACCESS     not-accessible
   STATUS     mandatory
   DESCRIPTION
     "This variable represents the index for the vrPpSnaPort tables."
::= { vrPpSnaPortRowStatusEntry 10 }

vrPpSnaPortAdminControlTable OBJECT-TYPE
   SYNTAX     SEQUENCE OF VrPpSnaPortAdminControlEntry
   ACCESS     not-accessible
   STATUS     mandatory
   DESCRIPTION
     "This group includes the Administrative Control attribute. This 
      attribute defines the current administrative state of this component."
::= { vrPpSnaPort 100 }

vrPpSnaPortAdminControlEntry OBJECT-TYPE
   SYNTAX     VrPpSnaPortAdminControlEntry
   ACCESS     not-accessible
   STATUS     mandatory
   DESCRIPTION
     "An entry in the vrPpSnaPortAdminControlTable."
   INDEX {
      vrIndex,
      vrPpIndex,
      vrPpSnaPortIndex }
::= { vrPpSnaPortAdminControlTable 1 }

VrPpSnaPortAdminControlEntry ::= SEQUENCE {
   vrPpSnaPortSnmpAdminStatus
      INTEGER }

vrPpSnaPortSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrPpSnaPortAdminControlEntry 1 }

vrPpSnaPortProvTable OBJECT-TYPE
   SYNTAX     SEQUENCE OF VrPpSnaPortProvEntry
   ACCESS     not-accessible
   STATUS     mandatory
   DESCRIPTION
     "This group contains provisionable attributes for SNA ports."
::= { vrPpSnaPort 101 }

vrPpSnaPortProvEntry OBJECT-TYPE
   SYNTAX     VrPpSnaPortProvEntry
   ACCESS     not-accessible
   STATUS     mandatory
   DESCRIPTION
     "An entry in the vrPpSnaPortProvTable."
   INDEX {
      vrIndex,
      vrPpIndex,
      vrPpSnaPortIndex }
::= { vrPpSnaPortProvTable 1 }

VrPpSnaPortProvEntry ::= SEQUENCE {
   vrPpSnaPortVirtualSegmentLFSize
      Unsigned32 }

vrPpSnaPortVirtualSegmentLFSize OBJECT-TYPE
   SYNTAX     Unsigned32 (516 | 635 | 754 | 873 | 993 | 1112 | 1231 | 1350 | 1470 | 1542 | 1615 | 1688 | 1761 | 1833 | 1906 | 1979 | 2052 | 2345 | 5331 | 5798 | 6264 | 6730 | 7197 | 7663 | 8130 | 8539 | 8949 | 9358 | 9768 | 10178 | 10587 | 10997 | 11407 | 12199 | 12992 | 13785 | 14578 | 15370 | 16163 | 16956 | 17749 | 20730 | 23711 | 26693 | 29674 | 32655 | 35637 | 38618 | 41600 | 44591 | 47583 | 50575 | 53567 | 56559 | 59551 | 65535)
   ACCESS     read-write
   STATUS     mandatory
   DESCRIPTION
     "This attribute specifies the largest frame size (including DLC header 
      and info field but not any MAC-level or framing octets) for end-to-
      end connections established through this Sna component. This value 
      is used as the largest frame size for all circuits unless a smaller 
      value is specified in XID signals or by local LAN constraints."
   DEFVAL     { 2345 }
::= { vrPpSnaPortProvEntry 1 }

vrPpSnaPortStateTable OBJECT-TYPE
   SYNTAX     SEQUENCE OF VrPpSnaPortStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpSnaPort 103 }

vrPpSnaPortStateEntry OBJECT-TYPE
   SYNTAX     VrPpSnaPortStateEntry
   ACCESS     not-accessible
   STATUS     mandatory
   DESCRIPTION
     "An entry in the vrPpSnaPortStateTable."
   INDEX {
      vrIndex,
      vrPpIndex,
      vrPpSnaPortIndex }
::= { vrPpSnaPortStateTable 1 }

VrPpSnaPortStateEntry ::= SEQUENCE {
   vrPpSnaPortAdminState
      INTEGER,
   vrPpSnaPortOperationalState
      INTEGER,
   vrPpSnaPortUsageState
      INTEGER }

vrPpSnaPortAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpSnaPortStateEntry 1 }

vrPpSnaPortOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpSnaPortStateEntry 2 }

vrPpSnaPortUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpSnaPortStateEntry 3 }

vrPpSnaPortOperStatusTable OBJECT-TYPE
   SYNTAX     SEQUENCE OF VrPpSnaPortOperStatusEntry
   ACCESS     not-accessible
   STATUS     mandatory
   DESCRIPTION
     "This group includes the Operational Status attribute. This attribute 
      defines the current operational state of this component."
::= { vrPpSnaPort 104 }

vrPpSnaPortOperStatusEntry OBJECT-TYPE
   SYNTAX     VrPpSnaPortOperStatusEntry
   ACCESS     not-accessible
   STATUS     mandatory
   DESCRIPTION
     "An entry in the vrPpSnaPortOperStatusTable."
   INDEX {
      vrIndex,
      vrPpIndex,
      vrPpSnaPortIndex }
::= { vrPpSnaPortOperStatusTable 1 }

VrPpSnaPortOperStatusEntry ::= SEQUENCE {
   vrPpSnaPortSnmpOperStatus
      INTEGER }

vrPpSnaPortSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpSnaPortOperStatusEntry 1 }

-- 
-- *** THIS SUBTREE CURRENTLY NOT IMPLEMENTED ***
-- 

-- Vr/<string> Pp/<string> SnaPort Circuit/
-- <s1Mac>,<s1Sap>,<s2Mac>,<s2Sap>
-- This table is the circuit representation in the Sna component. There 
-- is a conceptual row associated with each locally attached end 
-- station. End station 1 (S1) and End station 2 (S2) are used to 
-- represent the two end stations of the circuit. S1 is always an end 
-- station which is locally attached. S2 may be locally attached or 
-- remote. If it is locally attached, the circuit will be represented by 
-- two rows indexed by (A, B) and (B, A) where A & B are the 
-- relevant MACs/SAPs. 

vrPpSnaPortCircuit OBJECT IDENTIFIER ::= { vrPpSnaPort 2 }



vrPpSnaPortCircuitRowStatusTable OBJECT-TYPE
   SYNTAX     SEQUENCE OF VrPpSnaPortCircuitRowStatusEntry
   ACCESS     not-accessible
   STATUS     mandatory
   DESCRIPTION
     "*** THIS TABLE CURRENTLY NOT IMPLEMENTED ***

      This entry controls the addition and deletion of 
      vrPpSnaPortCircuit components."
::= { vrPpSnaPortCircuit 1 }

vrPpSnaPortCircuitRowStatusEntry OBJECT-TYPE
   SYNTAX     VrPpSnaPortCircuitRowStatusEntry
   ACCESS     not-accessible
   STATUS     mandatory
   DESCRIPTION
     "A single entry in the table represents a single 
      vrPpSnaPortCircuit component."
   INDEX {
      vrIndex,
      vrPpIndex,
      vrPpSnaPortIndex,
      vrPpSnaPortCircuitS1MacIndex,
      vrPpSnaPortCircuitS1SapIndex,
      vrPpSnaPortCircuitS2MacIndex,
      vrPpSnaPortCircuitS2SapIndex }
::= { vrPpSnaPortCircuitRowStatusTable 1 }

VrPpSnaPortCircuitRowStatusEntry ::= SEQUENCE {
   vrPpSnaPortCircuitRowStatus
      RowStatus,
   vrPpSnaPortCircuitComponentName
      DisplayString,
   vrPpSnaPortCircuitStorageType
      StorageType,
   vrPpSnaPortCircuitS1MacIndex
      DashedHexString,
   vrPpSnaPortCircuitS1SapIndex
      Integer32,
   vrPpSnaPortCircuitS2MacIndex
      DashedHexString,
   vrPpSnaPortCircuitS2SapIndex
      Integer32 }

vrPpSnaPortCircuitRowStatus OBJECT-TYPE
   SYNTAX     RowStatus 
   ACCESS     read-only
   STATUS     mandatory
   DESCRIPTION
     "This variable is used as the basis for SNMP naming of
      vrPpSnaPortCircuit components.
      These components cannot be added nor deleted."
::= { vrPpSnaPortCircuitRowStatusEntry 1 }

vrPpSnaPortCircuitComponentName OBJECT-TYPE
   SYNTAX     DisplayString 
   ACCESS     read-only
   STATUS     mandatory
   DESCRIPTION
     "This variable provides the component's string name for
      use with the ASCII Console Interface"
::= { vrPpSnaPortCircuitRowStatusEntry 2 }

vrPpSnaPortCircuitStorageType OBJECT-TYPE
   SYNTAX     StorageType 
   ACCESS     read-only
   STATUS     mandatory
   DESCRIPTION
     "This variable represents the storage type value for the
      vrPpSnaPortCircuit tables."
::= { vrPpSnaPortCircuitRowStatusEntry 4 }

vrPpSnaPortCircuitS1MacIndex OBJECT-TYPE
   SYNTAX     DashedHexString (SIZE (6))
   ACCESS     not-accessible
   STATUS     mandatory
   DESCRIPTION
     "This variable represents an index for the vrPpSnaPortCircuit tables."
::= { vrPpSnaPortCircuitRowStatusEntry 10 }

vrPpSnaPortCircuitS1SapIndex OBJECT-TYPE
   SYNTAX     Integer32 (2..254)
   ACCESS     not-accessible
   STATUS     mandatory
   DESCRIPTION
     "This variable represents an index for the vrPpSnaPortCircuit tables."
::= { vrPpSnaPortCircuitRowStatusEntry 11 }

vrPpSnaPortCircuitS2MacIndex OBJECT-TYPE
   SYNTAX     DashedHexString (SIZE (6))
   ACCESS     not-accessible
   STATUS     mandatory
   DESCRIPTION
     "This variable represents an index for the vrPpSnaPortCircuit tables."
::= { vrPpSnaPortCircuitRowStatusEntry 12 }

vrPpSnaPortCircuitS2SapIndex OBJECT-TYPE
   SYNTAX     Integer32 (2..254)
   ACCESS     not-accessible
   STATUS     mandatory
   DESCRIPTION
     "This variable represents an index for the vrPpSnaPortCircuit tables."
::= { vrPpSnaPortCircuitRowStatusEntry 13 }

vrPpSnaPortCircuitOperTable OBJECT-TYPE
   SYNTAX     SEQUENCE OF VrPpSnaPortCircuitOperEntry
   ACCESS     not-accessible
   STATUS     mandatory
   DESCRIPTION
     "*** THIS TABLE CURRENTLY NOT IMPLEMENTED ***

      This group defines an entry in the SnaCircuitEntry Table."
::= { vrPpSnaPortCircuit 100 }

vrPpSnaPortCircuitOperEntry OBJECT-TYPE
   SYNTAX     VrPpSnaPortCircuitOperEntry
   ACCESS     not-accessible
   STATUS     mandatory
   DESCRIPTION
     "An entry in the vrPpSnaPortCircuitOperTable."
   INDEX {
      vrIndex,
      vrPpIndex,
      vrPpSnaPortIndex,
      vrPpSnaPortCircuitS1MacIndex,
      vrPpSnaPortCircuitS1SapIndex,
      vrPpSnaPortCircuitS2MacIndex,
      vrPpSnaPortCircuitS2SapIndex }
::= { vrPpSnaPortCircuitOperTable 1 }

VrPpSnaPortCircuitOperEntry ::= SEQUENCE {
   vrPpSnaPortCircuitS1DlcType
      INTEGER,
   vrPpSnaPortCircuitS1RouteInfo
      HexString,
   vrPpSnaPortCircuitS2Location
      INTEGER,
   vrPpSnaPortCircuitOrigin
      INTEGER,
   vrPpSnaPortCircuitState
      INTEGER,
   vrPpSnaPortCircuitPriority
      INTEGER,
   vrPpSnaPortCircuitVcId
      RowPointer }

vrPpSnaPortCircuitS1DlcType OBJECT-TYPE
   SYNTAX     INTEGER  {
                 other(1),
                 na(2),
                 llc(3),
                 sdlc(4),
                 qllc(5) }
   ACCESS     read-only
   STATUS     mandatory
   DESCRIPTION
     "This attribute indicates the DLC protocol in use between the SNA 
      node and S1."
::= { vrPpSnaPortCircuitOperEntry 2 }

vrPpSnaPortCircuitS1RouteInfo OBJECT-TYPE
   SYNTAX     HexString (SIZE (0..30))
   ACCESS     read-only
   STATUS     mandatory
   DESCRIPTION
     "If source-route bridging is in use between the SNA node and S1, 
      this is the routing information field describing the path between the 
      two devices. The format of the routing information corresponds to 
      that of the route designator fields of a specifically routed SRB 
      frame. Otherwise the value will be a Hex string of zero length."
::= { vrPpSnaPortCircuitOperEntry 3 }

vrPpSnaPortCircuitS2Location OBJECT-TYPE
   SYNTAX     INTEGER  {
                 other(1),
                 internal(2),
                 remote(3),
                 local(4) }
   ACCESS     read-only
   STATUS     mandatory
   DESCRIPTION
     "This attribute indicates the location of End Station 2 (S2). If the 
      location of End Station 2 is local, the interface information will be 
      available in the conceptual row whose S1 and S2 are the S2 and the 
      S1 of this conceptual row, respectively."
::= { vrPpSnaPortCircuitOperEntry 6 }

vrPpSnaPortCircuitOrigin OBJECT-TYPE
   SYNTAX     INTEGER  {
                 s2(0),
                 s1(1) }
   ACCESS     read-only
   STATUS     mandatory
   DESCRIPTION
     "This attribute indicates  which of the two end stations initiated the 
      establishment of this circuit."
::= { vrPpSnaPortCircuitOperEntry 10 }

vrPpSnaPortCircuitState OBJECT-TYPE
   SYNTAX     INTEGER  {
                 disconnected(1),
                 circuitStart(2),
                 resolvePending(3),
                 circuitPending(4),
                 circuitEstablished(5),
                 connectPending(6),
                 contactPending(7),
                 connected(8),
                 disconnectPending(9),
                 haltPending(10),
                 haltPendingNoack(11),
                 circuitRestart(12),
                 restartPending(13) }
   ACCESS     read-only
   STATUS     mandatory
   DESCRIPTION
     "This attribute indicates the current state of this circuit. Note that this 
      implementation does not keep entries after circuit disconnect. 
      Details regarding the state machine and meaning of individual states 
      may be found in RFC 1795."
::= { vrPpSnaPortCircuitOperEntry 13 }

vrPpSnaPortCircuitPriority OBJECT-TYPE
   SYNTAX     INTEGER  {
                 unsupported(1),
                 low(2),
                 medium(3),
                 high(4),
                 highest(5) }
   ACCESS     read-only
   STATUS     mandatory
   DESCRIPTION
     "This attribute indicates the transmission priority of this circuit as 
      understood by this SNA node. This value is determined by the two 
      SNA nodes at circuit startup time."
::= { vrPpSnaPortCircuitOperEntry 14 }

vrPpSnaPortCircuitVcId OBJECT-TYPE
   SYNTAX     RowPointer 
   ACCESS     read-only
   STATUS     mandatory
   DESCRIPTION
     "This attribute indicates the component name of the GvcIf/n Dlci/n 
      which represents this VC connection in the SNA DLR service. This 
      attribute appears only for circuits that are connecting over a Frame 
      Relay DLCI only. For circuits connecting over Qllc VCs or Token 
      Ring interface this attribute does not appear."
::= { vrPpSnaPortCircuitOperEntry 26 }


-- Vr/<string> Sna
-- This component defines the overall characteristics of a Data Link 
-- Routing (DLR)  instance which routes SNA traffic through a 
-- Passport network. 

vrSna OBJECT IDENTIFIER ::= { vr 14 }



vrSnaRowStatusTable OBJECT-TYPE
   SYNTAX     SEQUENCE OF VrSnaRowStatusEntry
   ACCESS     not-accessible
   STATUS     mandatory
   DESCRIPTION
     "This entry controls the addition and deletion of 
      vrSna components."
::= { vrSna 1 }

vrSnaRowStatusEntry OBJECT-TYPE
   SYNTAX     VrSnaRowStatusEntry
   ACCESS     not-accessible
   STATUS     mandatory
   DESCRIPTION
     "A single entry in the table represents a single 
      vrSna component."
   INDEX {
      vrIndex,
      vrSnaIndex }
::= { vrSnaRowStatusTable 1 }

VrSnaRowStatusEntry ::= SEQUENCE {
   vrSnaRowStatus
      RowStatus,
   vrSnaComponentName
      DisplayString,
   vrSnaStorageType
      StorageType,
   vrSnaIndex
      NonReplicated }

vrSnaRowStatus OBJECT-TYPE
   SYNTAX     RowStatus 
   ACCESS     read-write
   STATUS     mandatory
   DESCRIPTION
     "This variable is used as the basis for SNMP naming of
      vrSna components.
      These components can be added and deleted."
::= { vrSnaRowStatusEntry 1 }

vrSnaComponentName OBJECT-TYPE
   SYNTAX     DisplayString 
   ACCESS     read-only
   STATUS     mandatory
   DESCRIPTION
     "This variable provides the component's string name for
      use with the ASCII Console Interface"
::= { vrSnaRowStatusEntry 2 }

vrSnaStorageType OBJECT-TYPE
   SYNTAX     StorageType 
   ACCESS     read-only
   STATUS     mandatory
   DESCRIPTION
     "This variable represents the storage type value for the
      vrSna tables."
::= { vrSnaRowStatusEntry 4 }

vrSnaIndex OBJECT-TYPE
   SYNTAX     NonReplicated 
   ACCESS     not-accessible
   STATUS     mandatory
   DESCRIPTION
     "This variable represents the index for the vrSna tables."
::= { vrSnaRowStatusEntry 10 }

vrSnaAdminControlTable OBJECT-TYPE
   SYNTAX     SEQUENCE OF VrSnaAdminControlEntry
   ACCESS     not-accessible
   STATUS     mandatory
   DESCRIPTION
     "This group includes the Administrative Control attribute. This 
      attribute defines the current administrative state of this component."
::= { vrSna 100 }

vrSnaAdminControlEntry OBJECT-TYPE
   SYNTAX     VrSnaAdminControlEntry
   ACCESS     not-accessible
   STATUS     mandatory
   DESCRIPTION
     "An entry in the vrSnaAdminControlTable."
   INDEX {
      vrIndex,
      vrSnaIndex }
::= { vrSnaAdminControlTable 1 }

VrSnaAdminControlEntry ::= SEQUENCE {
   vrSnaSnmpAdminStatus
      INTEGER }

vrSnaSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrSnaAdminControlEntry 1 }

vrSnaStateTable OBJECT-TYPE
   SYNTAX     SEQUENCE OF VrSnaStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrSna 101 }

vrSnaStateEntry OBJECT-TYPE
   SYNTAX     VrSnaStateEntry
   ACCESS     not-accessible
   STATUS     mandatory
   DESCRIPTION
     "An entry in the vrSnaStateTable."
   INDEX {
      vrIndex,
      vrSnaIndex }
::= { vrSnaStateTable 1 }

VrSnaStateEntry ::= SEQUENCE {
   vrSnaAdminState
      INTEGER,
   vrSnaOperationalState
      INTEGER,
   vrSnaUsageState
      INTEGER }

vrSnaAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrSnaStateEntry 1 }

vrSnaOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrSnaStateEntry 2 }

vrSnaUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrSnaStateEntry 3 }

vrSnaOperStatusTable OBJECT-TYPE
   SYNTAX     SEQUENCE OF VrSnaOperStatusEntry
   ACCESS     not-accessible
   STATUS     mandatory
   DESCRIPTION
     "This group includes the Operational Status attribute. This attribute 
      defines the current operational state of this component."
::= { vrSna 102 }

vrSnaOperStatusEntry OBJECT-TYPE
   SYNTAX     VrSnaOperStatusEntry
   ACCESS     not-accessible
   STATUS     mandatory
   DESCRIPTION
     "An entry in the vrSnaOperStatusTable."
   INDEX {
      vrIndex,
      vrSnaIndex }
::= { vrSnaOperStatusTable 1 }

VrSnaOperStatusEntry ::= SEQUENCE {
   vrSnaSnmpOperStatus
      INTEGER }

vrSnaSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrSnaOperStatusEntry 1 }

vrSnaOperTable OBJECT-TYPE
   SYNTAX     SEQUENCE OF VrSnaOperEntry
   ACCESS     not-accessible
   STATUS     mandatory
   DESCRIPTION
     "This group contains operational attributes which describe the  
      behavior of the Sna component and associated ports under the 
      Virtual Router (VR)."
::= { vrSna 103 }

vrSnaOperEntry OBJECT-TYPE
   SYNTAX     VrSnaOperEntry
   ACCESS     not-accessible
   STATUS     mandatory
   DESCRIPTION
     "An entry in the vrSnaOperTable."
   INDEX {
      vrIndex,
      vrSnaIndex }
::= { vrSnaOperTable 1 }

VrSnaOperEntry ::= SEQUENCE {
   vrSnaVersion
      HexString }

vrSnaVersion OBJECT-TYPE
   SYNTAX     HexString (SIZE (2))
   ACCESS     read-only
   STATUS     mandatory
   DESCRIPTION
     "This attribute indicates the particular version of the SNA standard 
      supported by this Sna.  The first 2 digits  represent the SNA 
      standard Version number of this Sna, the second 2 digits represent 
      the SNA standard Release number."
::= { vrSnaOperEntry 2 }

vrSnaCircStatsTable OBJECT-TYPE
   SYNTAX     SEQUENCE OF VrSnaCircStatsEntry
   ACCESS     not-accessible
   STATUS     mandatory
   DESCRIPTION
     "A circuit is the end-to-end association of two Data Link Routing 
      (DLR) entities through one or two DLR nodes. It is the 
      concatenation of two 'data links', optionally with an intervening 
      transport connection (not initially supported). The origin of the 
      circuit is the end station that initiates the circuit. The target of the 
      circuit is the end station that receives the initiation."
::= { vrSna 104 }

vrSnaCircStatsEntry OBJECT-TYPE
   SYNTAX     VrSnaCircStatsEntry
   ACCESS     not-accessible
   STATUS     mandatory
   DESCRIPTION
     "An entry in the vrSnaCircStatsTable."
   INDEX {
      vrIndex,
      vrSnaIndex }
::= { vrSnaCircStatsTable 1 }

VrSnaCircStatsEntry ::= SEQUENCE {
   vrSnaActives
      Gauge32,
   vrSnaCreates
      Counter32 }

vrSnaActives OBJECT-TYPE
   SYNTAX     Gauge32 (0..4292967295)
   ACCESS     read-only
   STATUS     mandatory
   DESCRIPTION
     "This attribute indiates the current number of circuits in Circuit table 
      that are not in the disconnected state."
   DEFVAL     { 0 }
::= { vrSnaCircStatsEntry 1 }

vrSnaCreates OBJECT-TYPE
   SYNTAX     Counter32 
   ACCESS     read-only
   STATUS     mandatory
   DESCRIPTION
     "This attribute indicates the total number of entries ever added to 
      Circuit table, or reactivated upon exiting disconnected state."
::= { vrSnaCircStatsEntry 2 }

vrSnaDirStatsTable OBJECT-TYPE
   SYNTAX     SEQUENCE OF VrSnaDirStatsEntry
   ACCESS     not-accessible
   STATUS     mandatory
   DESCRIPTION
     "MAC Table Directory statistics"
::= { vrSna 105 }

vrSnaDirStatsEntry OBJECT-TYPE
   SYNTAX     VrSnaDirStatsEntry
   ACCESS     not-accessible
   STATUS     mandatory
   DESCRIPTION
     "An entry in the vrSnaDirStatsTable."
   INDEX {
      vrIndex,
      vrSnaIndex }
::= { vrSnaDirStatsTable 1 }

VrSnaDirStatsEntry ::= SEQUENCE {
   vrSnaMacEntries
      Gauge32,
   vrSnaMacCacheHits
      Counter32,
   vrSnaMacCacheMisses
      Counter32 }

vrSnaMacEntries OBJECT-TYPE
   SYNTAX     Gauge32 (0..10000)
   ACCESS     read-only
   STATUS     mandatory
   DESCRIPTION
     "This attribute indicates the current total number of entries in the 
      DirectoryEntry table."
   DEFVAL     { 0 }
::= { vrSnaDirStatsEntry 1 }

vrSnaMacCacheHits OBJECT-TYPE
   SYNTAX     Counter32 
   ACCESS     read-only
   STATUS     mandatory
   DESCRIPTION
     "This attribute indicates the number of times a cache search for a 
      particular MAC address resulted in success."
::= { vrSnaDirStatsEntry 2 }

vrSnaMacCacheMisses OBJECT-TYPE
   SYNTAX     Counter32 
   ACCESS     read-only
   STATUS     mandatory
   DESCRIPTION
     "This attribute indicates the number of times a cache search for a 
      particular MAC address resulted in failure."
::= { vrSnaDirStatsEntry 3 }




-- 
-- Version and Compliance statements
-- 



-- Object-Group Statement:
-- A list of all current accessible leaf objects.

-- OBJECTS { vrPpSnaPortCircuitS2Location,
--           vrPpSnaPortUsageState,
--           vrPpSnaPortCircuitOrigin,
--           vrPpSnaPortCircuitRowStatus,
--           vrPpSnaPortComponentName,
--           vrPpSnaPortCircuitVcId,
--           vrPpSnaPortCircuitS1RouteInfo,
--           vrPpSnaPortStorageType,
--           vrSnaOperationalState,
--           vrSnaMacEntries,
--           vrSnaUsageState,
--           vrPpSnaPortOperationalState,
--           vrSnaMacCacheHits,
--           vrPpSnaPortCircuitState,
--           vrSnaComponentName,
--           vrPpSnaPortCircuitComponentName,
--           vrPpSnaPortCircuitS1DlcType,
--           vrSnaAdminState,
--           vrPpSnaPortAdminState,
--           vrPpSnaPortCircuitStorageType,
--           vrSnaMacCacheMisses,
--           vrSnaRowStatus,
--           vrPpSnaPortRowStatus,
--           vrSnaVersion,
--           vrSnaSnmpAdminStatus,
--           vrPpSnaPortSnmpAdminStatus,
--           vrSnaStorageType,
--           vrPpSnaPortCircuitPriority,
--           vrSnaActives,
--           vrSnaSnmpOperStatus,
--           vrPpSnaPortSnmpOperStatus,
--           vrSnaCreates,
--           vrPpSnaPortVirtualSegmentLFSize }
-- STATUS  mandatory
-- DESCRIPTION
--   "A list of all current accessible leaf objects."

snaGroup OBJECT IDENTIFIER ::= { snaMIB 1 }
snaGroupBE OBJECT IDENTIFIER ::= { snaGroup 5 }
snaGroupBE01 OBJECT IDENTIFIER ::= { snaGroupBE 2 }
snaGroupBE01A OBJECT IDENTIFIER ::= { snaGroupBE01 2 }



-- Agent-Capabilities Statement:

-- PRODUCT-RELEASE "Passport Release 7.0 Sna."
-- STATUS          mandatory
-- DESCRIPTION     "Sna MIB: MIB Version BE01A,
--                  Software Version BG00S4C."
-- SUPPORTS        Nortel-Magellan-Passport-SnaMIB
--    INCLUDES     { snaGroupBE01A }

snaCapabilities OBJECT IDENTIFIER ::= { snaMIB 3 }
snaCapabilitiesBE OBJECT IDENTIFIER ::= { snaCapabilities 5 }
snaCapabilitiesBE01 OBJECT IDENTIFIER ::= { snaCapabilitiesBE 2 }
snaCapabilitiesBE01A OBJECT IDENTIFIER ::= { snaCapabilitiesBE01 2 }





END
