-- ****************************************************************************
--                             SC5520.mib
-- ****************************************************************************

-- Copyright 1994 - 1995 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
-- This MIB module uses the extended OBJECT-TYPE macro as
-- defined in RFC 1212.

-- The implementation of all groups is mandatory for all products in
-- the SC5520 family.

-- All objects in this mib are directed toward one interface which
-- is the unit. There is one entry per table for each managed SC5520.

-- Note:  All rows in all tables defined within this MIB module are
-- virtual.  They can neither be created or deleted by management
-- operations.

-- The Version Group. This group identifies the version information
-- for the MIB.
--

--
-- ****************************************************************************
--                        Revision History
-- ****************************************************************************

-- Version   Date	Name

-- 1.00A     08-Nov-94  N. Marino	Initial Revision
-- 1.00B     06-Dec-94  N. Marino       Added Alarm OID's
-- 1.00C     23-Jan-95  J. Jacques      Added Diagonostics and renumbered
--          				some enumerations.
-- 1.00D     16-Feb-95  J. Jacques      Added sc5520DiagIntLineloop object
-- 1.00E     28-Mar-95  J. Jacques      Added 6 objects in sc5520UnitCfgTable
--					Added sc5520MasterTable
--					Added 5 new Alarms
--					Added 4 objects to sc5520MaintTable
--					Removed LPDA Table
-- 1.00F     10-Apr-95  J. Jacques 	Removed sc5520RemoteAlarmControl
--					from sc5520UnitCfgTable.
--					Removed sc5520AddDelRemoteAddress &
--					sc5520RemoteSerialNumber from
--					sc5520MasterTable and added 6 new
--					objects to sc520UnitCfgTable.
-- 1.00G     12-Apr-95  R. Strempel	Added additional comments to objects
--					in sc5520MasterTable
-- 1.00H     17-Apr-95  R. Strempel	Imported gdc & dsu rather than define here.
-- 1.00I     13-Jun-95  R. Strempel	Added sc5520HdlcInvert object, took out
--					sc5520FrontPanelTestAlm duplicate alarm,
--					added comments to sc5520DiagSendCode object.
-- 1.00J     14-Jul-95  R. Strempel	Added comments to sc5520DiagTimeDelay.
-- 1.00K     18-Jul-95  C. Amorossi	Added comments to sc5520HdlcInvert
--					Added sc5520EIARemLoop, sc5520EIALineLoop,
--					sc5520PiggyBackDetect to sc5520UnitCfgTable
--					Added sc5520DiagExtRemoteLoop,
--					      sc5520DiagRemLoopWithSelf to
--					      sc5520ExcDiagTable
--					Changed ENUMS for sc5520DiagTestStatus
-- 1.00L     07-Aug-95  C. Amorossi     Changed sc5520MasterTblEntry to
--						sc5520MasterTableEntry.
--					Changed Sc5520MasterTblEntry to
--						Sc5520MasterTableEntry.
--					Changed ENUMS for sc5520DiagTestStatus
-- 1.00M     25-Aug-95  C. Amorossi	Changed description for sc5520MtpointRmRspIntrvl.
-- 1.00N     01-Sep-95  C. Amorossi	Made sc5520StreamingAlm obsolete
-- 1.00O     18-Sep-95  C. Amorossi	Made sc5520DisableAllRemoteAlarms and
--					sc5520EnableAllRemoteAlarms obsolete
--					Added sc5520RateBroadcast
-- 1.00P     26-Feb-96  S. Veillette
--
--           1) Added Sc5520UnitCfgEntry 22 -> sc5520CircuitType
--           2) Added Sc5520UnitCfgEntry 23 -> sc5520WakeUpRemote
--           3) Added Sc5520UnitCfgEntry 24 -> sc5520ListOfRemotes
--           4) Added table headings and page feeds to mib
--
-- 1.00Q     1-May-96   S. Veillette
--
--           1) Added Sc5520UnitCfgEntry 25 -> sc5520TelcoLatchingLoop
--           2) Correct length of sc5520ListOfRemotes from five bytes to four
--           3) Remove  gdc FROM GDCCMN-MIB from IMPORTS declaration block to 
--              eliminate not used warning
--
-- 1.00R     03-Dec-97 D. Baylis 
--	     1) Added sc5520VersionTable to support firmware downloading	
--           2) Added patternGDC(3) to sc5520RemLoopPattern
--	     3) Added sc5520BlinkINS




-- ****************************************************************************

--
-- ****************************************************************************
--                       mib definitions begin
-- ****************************************************************************


SC5520-MIB DEFINITIONS ::= BEGIN

IMPORTS
	TimeTicks			FROM RFC1155-SMI
	OBJECT-TYPE			FROM RFC-1212
	DisplayString			FROM RFC1213-MIB
	SCinstance			FROM GDCMACRO-MIB
	dsu				FROM DDS-MIB;

sc5520 		OBJECT IDENTIFIER ::= { dsu 3 }


-- ****************************************************************************


sc5520MIBversion OBJECT-TYPE
    SYNTAX DisplayString (SIZE (5))
    ACCESS read-only
    STATUS mandatory
    DESCRIPTION
    	"Identifies the version of the MIB. The format of the version
    	is x.yzT, where 'x' identifies the major revision number, 'y'
    	identifies the minor revision number, 'z' identifies the
    	typographical revision, and T identifies the test revision.
    	Acceptable values for the individual revision components are
    	as follows:

    		x: 1 - 9
    		y: 0 - 9
    		z: 0 - 9
    		T: A - Z

    	Upon formal release, no designation for the test revision will
    	be present."
    ::= { sc5520 1 }

--
-- ****************************************************************************
--                        Configuration table
-- ****************************************************************************
-- The SC5520 Unit Configuration Group.
-- This group contains objects that support the specific management
-- requirements for configuring the SC5520 that are not
-- addressed through other standard MIB modules.

sc5520UnitCfgTable OBJECT-TYPE
    SYNTAX SEQUENCE OF Sc5520UnitCfgEntry
    ACCESS not-accessible
    STATUS mandatory
    DESCRIPTION
    	"The SC5520 Unit Configuration table."
    ::= { sc5520 2 }

sc5520UnitCfgEntry OBJECT-TYPE
    SYNTAX Sc5520UnitCfgEntry
    ACCESS not-accessible
    STATUS mandatory
    DESCRIPTION
    	"The SC5520 Unit Configuration table entry.  The information in this
	entry provides unit level configuration for the SC5520."
    INDEX { sc5520UnitCfgIndex }
    ::= { sc5520UnitCfgTable 1 }

Sc5520UnitCfgEntry ::=
    SEQUENCE {
        sc5520UnitCfgIndex               SCinstance,
    	sc5520Nms510CompatibilityMode    INTEGER,
	sc5520PtToPtSentryTime           INTEGER,
	sc5520AlarmHystTime              INTEGER,
	sc5520MtpointRmRspIntrvl         INTEGER,
	sc5520DtePortType                INTEGER,
	sc5520DteCtsDelay                INTEGER,
	sc5520DteCtsDelayExt             INTEGER,
	sc5520BkPlaneFracNum             INTEGER,
	sc5520BkPlaneFracIfIndex         INTEGER,
	sc5520FirmwareLevel              DisplayString,
        sc5520FrontPanelInhibit          INTEGER,
        sc5520FrontPanelEnable           INTEGER,
	sc5520RemLoopAllowed             INTEGER,
	sc5520RemLoopPattern             INTEGER,
	sc5520RemLoopTimeout             INTEGER,
        sc5520HdlcInvert                 INTEGER,
	sc5520EIARemLoop                 INTEGER,
	sc5520EIALineLoop                INTEGER,
	sc5520PiggyBackDetect            INTEGER,
	sc5520RateBroadcast              INTEGER,
	sc5520CircuitType                INTEGER,
	sc5520WakeUpRemote               DisplayString,
	sc5520ListOfRemotes              OCTET STRING,
	sc5520TelcoLatchingLoop          INTEGER
   }

sc5520UnitCfgIndex OBJECT-TYPE
    SYNTAX SCinstance
    ACCESS read-only
    STATUS mandatory
    DESCRIPTION
    	"The index value which uniquely identifies the SC5520 to which this
	entry is applicable.  This has the form of a SCinstance which defines
	the slot, line, and drop of the SC5520 with no sub-identifier value."
    ::= { sc5520UnitCfgEntry 1 }


sc5520Nms510CompatibilityMode OBJECT-TYPE
    SYNTAX INTEGER {
    	disabled(1),
    	enabled(2)
    }
    ACCESS read-write
    STATUS mandatory
    DESCRIPTION
    	"The NMS510 compatibility mode. This mode allows the SC5520 to behave
	in a manner compatible with that of the NMS510. If this object has the
	value enabled(2), then the device can be used in conjunction with an
	NMS510. A value of disabled(1) implies that the device is not
	backwardly compatible with the NMS510."
    ::= { sc5520UnitCfgEntry 2 }

sc5520PtToPtSentryTime OBJECT-TYPE
    SYNTAX INTEGER (0..127)
    ACCESS read-write
    STATUS mandatory
    DESCRIPTION
    	"The Point to point sentry time sc5520PtToPtSentryTime, is used to
	control the amount of time between unsolicited alarm responses from
	a remote unit in a point to point application when there are no alarm
	conditions to report.  This unsolicited response maintains the
	management link between the two units.  These alarm responses are
	intrusive to data.
	The range is from 1 minute to 127 minutes, with 60 minutes being the
	default value. The value of 0(zero) minutes will disable remote alarm
	sentry reporting."
    ::= { sc5520UnitCfgEntry 3 }

sc5520AlarmHystTime OBJECT-TYPE
    SYNTAX INTEGER (1..127)
    ACCESS read-write
    STATUS mandatory
    DESCRIPTION
    	"The Alarm hysteresis time sc5520AlarmHystTime, is used to control the
	amount of time a remote must wait between reporting unsolicited alarm
	conditions. A remote will send an unsolicited alarm response at the
	time of the first alarm. If second alarm occurs the remote will wait
	for the time specified by this object before it will send another alarm
	response. This time applies for both point to point and multipoint
	applications. The range is from 1 second to 127 seconds,  with 10
	seconds being the default value."
    ::= { sc5520UnitCfgEntry 4 }

sc5520MtpointRmRspIntrvl OBJECT-TYPE
    SYNTAX INTEGER (0..127)
    ACCESS read-write
    STATUS mandatory
    DESCRIPTION
	"The multipoint remote response interval sc5520MtpointRmRspIntrvl, is
	used to control the amount of time between unsolicited alarm responses
	from a remote unit in a multipoint applications when there are no alarm
	conditions to report.  This unsolicited response maintains the
	management link between the two units. The range is from 1 second
	to 127 seconds with 10 seconds being the default value. The value
	of 0(zero) seconds is disable remote alarm sentry reporting. All
	remotes in a multipoint application must be set the same.
	These alarm responses are non-intrusive to data."
    ::= { sc5520UnitCfgEntry 5 }


sc5520DtePortType OBJECT-TYPE
    SYNTAX INTEGER {
    	rs232(1),
    	v35(2),
	auto(3)
    }
    ACCESS read-write
    STATUS mandatory
    DESCRIPTION
	"The value auto(3), indicates that the DTE port is automatically being
	detected, and set. The rs232(1), will force the DTE port to
	EIA/TIA-232-E, and v35(2), will force the DTE port to V.35."
    ::= { sc5520UnitCfgEntry 6 }

sc5520DteCtsDelay OBJECT-TYPE
    SYNTAX INTEGER {
    	ctsOn(1),
    	cts0mSec(2),
    	ctsFixed3Char(3)
    }
    ACCESS read-write
    STATUS mandatory
    DESCRIPTION
    	"RTS/CTS Delay options

		ctsOn(1) 	Forces both RTS and CTS On regardless of the
				state of the attached business equipment (the
				transmitter is On regardless of the status of
				the RTS interface lead). MIB object
				sc5520DteCtsDelayExt is ignored.

		cts0mSec(2)	Provides zero bits of delay between active
				RTS and CTS being set to active. MIB object
				sc5520DteCtsDelayExt must be set to ext0mSec(1).

		ctsFix3Char(3)	Provides three character bits of delay between
 				active RTS and CTS being set to active. MIB
 				object sc5520DteCtsDelayExt must be set to
 				ext0mSec(1)."
    ::= { sc5520UnitCfgEntry 7 }


sc5520DteCtsDelayExt OBJECT-TYPE
    SYNTAX INTEGER {
    	ext0mSec(1),
    	ext30mSec(2),
    	ext60mSec(3),
    	ext90mSec(4)
    }
    ACCESS read-write
    STATUS mandatory
    DESCRIPTION
    	"RTS/CTS Delay options extension

		ext0mSec(1)	Used to enable options cts0mSec(2) or
				ctsFix3Char(3) from MIB object
				sc5520DteCtsDelay.

		ext30mSec(2)	Provides 30 msec of delay between active
				RTS and CTS being set to active. MIB object
				sc5520DteCtsDelay must be set for either
				cts0mSec(2) or ctsFix3Char(3).

		ext60mSec(3)	Provides 60 msec of delay between active
				RTS and CTS being set to active. MIB object
				sc5520DteCtsDelay must be set for either
				cts0mSec(2) or ctsFix3Char(3).


		ext90mSec(4)	Provides 90 msec of delay between active
				RTS and CTS being set to active. MIB object
				sc5520DteCtsDelay must be set for either
				cts0mSec(2) or ctsFix3Char(3)."
   ::= { sc5520UnitCfgEntry 8 }


sc5520BkPlaneFracNum OBJECT-TYPE
    SYNTAX INTEGER (1..32)
    ACCESS read-write
    STATUS mandatory
    DESCRIPTION
	"Configures the unit to direct data to 1 of 32 time slots that
	exits on each of 4 highways (see sc5520BkPlaneFracIndex). By setting up
	units to a highway and time slot data can be channeled to different
	units within a management shelf. "
    ::= { sc5520UnitCfgEntry 9 }


sc5520BkPlaneFracIfIndex OBJECT-TYPE
    SYNTAX INTEGER {
    	none(1),
    	highway1(2),
    	highway2(3),
    	highway3(4),
    	highway4(5)
    }
    ACCESS read-write
    STATUS mandatory
    DESCRIPTION
	"Configures the unit to direct data to 1 of 4 hardware channels (pairs)
	that exist on the backplane of the management shelf.  By seting up
	units to a highway and time slot (see sc5520BkPlaneFracNum)
	data can be channeled to different units within a management shelf. The
	default for this object is none(1) which indicates that data is not
	being directed toward the management shelf backplane. "
    ::= { sc5520UnitCfgEntry 10 }


sc5520FirmwareLevel OBJECT-TYPE
    SYNTAX DisplayString (SIZE(2))
    ACCESS read-only
    STATUS mandatory
    DESCRIPTION
	 "The version number of the firmware, to allow products to know which
	 revision is installed.  The released version number is sequenced from
	 --, A-, ... AA, ... ZZ.  Test versions are numerical from 01 to 99."
    ::= { sc5520UnitCfgEntry 11 }


sc5520FrontPanelInhibit OBJECT-TYPE
    SYNTAX INTEGER {
	fpInhibited(1),		-- Read only
	fpEnabled(2),		-- Read only
    	execute(3)		-- Write only
    }
    ACCESS read-write
    STATUS mandatory
    DESCRIPTION
	"Inhibits all front panel test switches.  If a test
	switch is activated while inhibited it will simply be ignored.
	If enabled via the sc5520FrontPanelEnable object the test
	switch will function as normal."
    ::= { sc5520UnitCfgEntry 12 }


sc5520FrontPanelEnable OBJECT-TYPE
    SYNTAX INTEGER {
	fpInhibited(1),		-- Read only
	fpEnabled(2),		-- Read only
    	execute(3)		-- Write only
    }
    ACCESS read-write
    STATUS mandatory
    DESCRIPTION
	"Enables all front panel test switches.  If a test
	switch is activated while inhibited, via the
	sc5520FrontPanelInhibit object, it will simply be ignored.
	If enabled the test switch will function as normal."
    ::= { sc5520UnitCfgEntry 13 }



sc5520RemLoopAllowed OBJECT-TYPE
    SYNTAX INTEGER {
    	enable(1),
    	inhibit(2)
    }
    ACCESS read-write
    STATUS mandatory
    DESCRIPTION
	"Inhibits or enables a unit from going into remote loop
	when requested by the far end. "
    ::= { sc5520UnitCfgEntry 14 }


sc5520RemLoopPattern OBJECT-TYPE
    SYNTAX INTEGER {
    	patternV54(1),
    	patternPn127(2),
        patternGDC(3)
   }
    ACCESS read-write
    STATUS mandatory
    DESCRIPTION
	"Selects the test pattern to be used in a remote loop test."
    ::= { sc5520UnitCfgEntry 15 }


sc5520RemLoopTimeout OBJECT-TYPE
    SYNTAX INTEGER {
    	inhibit(1),
    	enable(2)
    }
    ACCESS read-write
    STATUS mandatory
    DESCRIPTION
	"Inhibits or enables a 10 miniute remote loop test timer.
	When enabled the remote loop test will be terminated 10
	minutes after being initiated.  If inhibited the unit will
	remain in remote loop test indefinately."
    ::= { sc5520UnitCfgEntry 16 }

sc5520HdlcInvert OBJECT-TYPE
    SYNTAX INTEGER {
	normal(1),
	invert(2)
    }
    ACCESS read-write
    STATUS mandatory
    DESCRIPTION
	"Primary data invert option.  Will enhance the quality of
	data when network does not provide B8Z5.  Primarily used
	with DDS II 56k"
    ::= { sc5520UnitCfgEntry 17 }

sc5520EIARemLoop OBJECT-TYPE
    SYNTAX INTEGER {
	disable(1),
	enable(2)
    }
    ACCESS read-write
    STATUS mandatory
    DESCRIPTION
	"The Remote Loop (RL) EIA test control lead option.  This
	option either allows or blocks EIA initiated test inputs
	from the DTE interface.  The remote unit must support v.54
	or PN127 remote loop."
    ::= { sc5520UnitCfgEntry 18 }

sc5520EIALineLoop OBJECT-TYPE
    SYNTAX INTEGER  {
	disable(1),
	enable(2)
    }
    ACCESS read-write
    STATUS mandatory
    DESCRIPTION
	"The LT EIA test control lead option.  This option either
	allows or blocks EIA initiated test inputs from the DTE
	interface.  LT (or Analoop) can be either a bilateral or
	unilateral loopback depending on option dds DTE Termaloop."
    ::= { sc5520UnitCfgEntry 19 }

sc5520PiggyBackDetect OBJECT-TYPE
    SYNTAX INTEGER  {
	not-installed(1),
	installed(2)
    }
    ACCESS read-only
    STATUS mandatory
    DESCRIPTION
	"If set to 2 then either a Data Rate Adadaptor or 530 card is
	installed."
    ::= { sc5520UnitCfgEntry 20 }

sc5520RateBroadcast OBJECT-TYPE
    SYNTAX INTEGER {
	normal(1), -- Read-Only
	enable(2)  -- Write-Only
    }
    ACCESS read-write
    STATUS mandatory
    DESCRIPTION
	"This should only be enabled when adding a remote unit and the
	 Line Type is either DDSII with data rate equal to 56k or
	 64k Clear Channel."
    ::= { sc5520UnitCfgEntry 21 }

sc5520CircuitType OBJECT-TYPE
    SYNTAX INTEGER {
	point-to-point(1),
	multipoint(2)
    }
    ACCESS read-write
    STATUS mandatory
    DESCRIPTION
	"This object defines the circuit type."
    ::= { sc5520UnitCfgEntry 22 }

sc5520WakeUpRemote OBJECT-TYPE
	SYNTAX	  DisplayString (SIZE (16))
	ACCESS	  read-only
	STATUS	  mandatory
	DESCRIPTION
	"This object is requested to initiate the add remote process in a point to point
         circuit. The serial number  of the associated remote is returned."
	::= { sc5520UnitCfgEntry 23}

sc5520ListOfRemotes OBJECT-TYPE
    SYNTAX OCTET STRING (SIZE(4))
    ACCESS read-only
    STATUS mandatory
    DESCRIPTION
    "A bitwise snapshot of the elements associated with this circuit,
     the master is always drop zero, the remote in a point to point circuit
     is always drop one.

    first octet     second octet     third octet     fourth octet
    -----------     -------------    -------------   --------------
    bit0 - drop 0   bit0 - drop 8    bit0 - drop 16  bit0 - drop 24
    bit1 - drop 1   bit1 - drop 9    bit1 - drop 17  bit1 - drop 25
    bit2 - drop 2   bit2 - drop 10   bit2 - drop 18  bit2 - drop 26
    bit3 - drop 3   bit3 - drop 11   bit3 - drop 19  bit3 - drop 27
    bit4 - drop 4   bit4 - drop 12   bit4 - drop 20  bit4 - drop 28
    bit5 - drop 5   bit5 - drop 13   bit5 - drop 21  bit5 - drop 29
    bit6 - drop 6   bit6 - drop 14   bit6 - drop 22  bit6 - drop 30
    bit7 - drop 7   bit7 - drop 15   bit7 - drop 23  bit7 - drop 31

    bit values are:  0 = no element, 1 = element present"
    ::= { sc5520UnitCfgEntry 24}

sc5520TelcoLatchingLoop OBJECT-TYPE
    SYNTAX INTEGER {
    	enable(1),
    	inhibit(2)
    }
    ACCESS read-write
    STATUS mandatory
    DESCRIPTION
	"Inhibits or enables a unit from going into a
 	 latching loopback when requested by Telco. "
    ::= { sc5520UnitCfgEntry 25 }





--
-- ****************************************************************************
--                        Add/Delete Remote from Master
-- ****************************************************************************
--

sc5520MasterTable OBJECT-TYPE
    SYNTAX SEQUENCE OF Sc5520MasterTableEntry
    ACCESS not-accessible
    STATUS mandatory
    DESCRIPTION
    	"Configure Master with Remote addresses."
    ::= { sc5520 3 }

sc5520MasterTableEntry OBJECT-TYPE
    SYNTAX Sc5520MasterTableEntry
    ACCESS not-accessible
    STATUS mandatory
    DESCRIPTION
    	"The SC5520 Mater table entry.  A doublely indexed table
	using the sc5520RemoteSerialNumber object as the second index."
    INDEX { sc5520MasterIndex }
    ::= { sc5520MasterTable 1 }

Sc5520MasterTableEntry ::=
    SEQUENCE {
        sc5520MasterIndex SCinstance,
	sc5520AddRemoteAddress OCTET STRING,
	sc5520DelRemoteAddress OCTET STRING,
	sc5520EnableRemoteAlarm INTEGER,
	sc5520DisableRemoteAlarm INTEGER,
	sc5520EnableAllRemoteAlarms INTEGER,
	sc5520DisableAllRemoteAlarms INTEGER
    }

sc5520MasterIndex OBJECT-TYPE
    SYNTAX SCinstance
    ACCESS read-only
    STATUS mandatory
    DESCRIPTION
    	"The index value which uniquely identifies the SC5520 to which this
	entry is applicable.  This has the form of a SCinstance which defines
	the slot, line, and drop of the SC5520 with no sub-identifier value."
    ::= { sc5520MasterTableEntry 1 }


sc5520AddRemoteAddress OBJECT-TYPE
    SYNTAX OCTET STRING (SIZE(18))
    ACCESS read-write
    STATUS mandatory
    DESCRIPTION
	"Add Remote address from Master tells the master (SC5520)
	how many remotes (nms520) units are in its network, the serial number
	of those remote units and its Drop adrress.  This information allows
	the Master to perform alarm reporting functions in a multipoint
	configuration.  This object allows the master unit to add
	remote units from its network table.  To add a remote unit to the
	Master's network table SET this object and specifiy the Serial Number
	of the unit in the first 16 locations in the OCTET STRING, and the
	Drop address(00 to 31) in the last 2 locations of the OCTET STRING.
	Remote alarm reporting will work in DDS1 only. Reading this object
	will report the last serial/address added or deleted."
    ::= { sc5520MasterTableEntry 2 }


sc5520DelRemoteAddress OBJECT-TYPE
    SYNTAX OCTET STRING (SIZE(18))
    ACCESS read-write
    STATUS mandatory
    DESCRIPTION
	"Delete Remote address from Master tells the master (SC5520)
	how many remotes (nms520) units are in its network, the serial number
	of those remote units and its Drop adrress.  This information allows
	the Master to perform alarm reporting functions in a multipoint
	configuration.  This object allows the master unit to delete
	remote units from its network table.  To delete a remote unit from the
	Master's network table SET this object and specifiy the Serial Number
	of the unit in the first 16 locations in the OCTET STRING, and the
	Drop address(00 to 31) in the last 2 locations of the OCTET STRING.
	Remote alarm reporting will work in DDS1 only. Reading this object
	will report the last serial/address added or deleted."
    ::= { sc5520MasterTableEntry 3 }


sc5520EnableRemoteAlarm OBJECT-TYPE
    SYNTAX INTEGER (1..31)
    ACCESS read-write
    STATUS mandatory
    DESCRIPTION
	"Enable Remote Alarm Control tells the master (SC5520) how to configure
	the remote units (nms520) in a multipoint configuration with respect
	to alarm reporting.  The master unit maintains alarm information about
	the remote units in its network.  This object allows the master unit
	to enable alarm reporting on any remote unit in its network.  To enable
	a remote unit to report alarms SET this object and specifiy the Drop
	address of the Remote, 1 to 31. Reading this object will report the last
	address added or deleted."
    ::= { sc5520MasterTableEntry 4 }


sc5520DisableRemoteAlarm OBJECT-TYPE
    SYNTAX INTEGER (1..31)
    ACCESS read-write
    STATUS mandatory
    DESCRIPTION
	"Disable Remote Alarm Control tells the master (SC5520) how to configure
	the remote units (nms520) in a multipoint configuration with respect
	to alarm reporting.  The master unit maintains alarm information about
	the remote units in its network.  This object allows the master unit
	to disable alarm reporting on any remote unit in its network.  To disable
	remote alarm reporting on a remote unit SET this object and specifiy the
	Drop address of the Remote, 1 to 31. Reading this object will report the last
	address added or deleted."
    ::= { sc5520MasterTableEntry 5 }


sc5520EnableAllRemoteAlarms OBJECT-TYPE
    SYNTAX INTEGER {
	normal(1),	-- Read only
	enable(2)	-- Write only
    }
    ACCESS read-write
    STATUS obsolete
    DESCRIPTION
	"Enable All Remote Alarms tells the master (SC5520) how to configure
	the remote units (nms520) in a multipoint configuration with respect
	to alarm reporting.  The master unit maintains alarm information about
	the remote units in its network.  This object allows the master unit
	to enable alarm reporting on all of the remote units in its network.
	To enable all remote units to report alarms SET this object and
	specifiy enable(1). Reading this object indicates the modem is
	operating normally"
    ::= { sc5520MasterTableEntry 6 }


sc5520DisableAllRemoteAlarms OBJECT-TYPE
    SYNTAX INTEGER {
	normal(1),	-- Read only
	disable(2)	-- Write only
    }
    ACCESS read-write
    STATUS obsolete
    DESCRIPTION
	"Disable All Remote Alarms tells the master (SC5520) how to configure
	the remote units (nms520) in a multipoint configuration with respect
	to alarm reporting.  The master unit maintains alarm information about
	the remote units in its network.  This object allows the master unit
	to disable alarm reporting on all of the remote units in its network.
	To disable all remote units from reporting alarms SET this object
	and specifiy disable(2). Reading this object indicates the modem is
	operating normally"
    ::= { sc5520MasterTableEntry 7 }


--
-- ****************************************************************************
--                         Alarm Configuration
-- ****************************************************************************

sc5520AlarmData OBJECT IDENTIFIER ::= { sc5520 4 }

sc5520NoResponseAlm 		OBJECT IDENTIFIER ::= { sc5520AlarmData 1 }
sc5520DiagRxErrAlm 		OBJECT IDENTIFIER ::= { sc5520AlarmData 2 }
sc5520PowerUpAlm 		OBJECT IDENTIFIER ::= { sc5520AlarmData 3 }
sc5520EEChkSumErrAlm 		OBJECT IDENTIFIER ::= { sc5520AlarmData 4 }
sc5520FpTestAlm	        	OBJECT IDENTIFIER ::= { sc5520AlarmData 5 }

--The following Alarm is Obsolete
--sc5520StreamingAlm      	OBJECT IDENTIFIER ::= { sc5520AlarmData 6 }

sc5520DSRLossAlm		OBJECT IDENTIFIER ::= { sc5520AlarmData 7 }
sc5520DTRLossAlm 		OBJECT IDENTIFIER ::= { sc5520AlarmData 8 }
sc5520DTPLossAlm        	OBJECT IDENTIFIER ::= { sc5520AlarmData 9 }
sc5520DCDLossAlm        	OBJECT IDENTIFIER ::= { sc5520AlarmData 10 }
sc5520RXDLossAlm        	OBJECT IDENTIFIER ::= { sc5520AlarmData 11 }
sc5520TXDLossAlm        	OBJECT IDENTIFIER ::= { sc5520AlarmData 12 }
sc5520TmShortedAlm      	OBJECT IDENTIFIER ::= { sc5520AlarmData 13 }
sc5520DcdShortedAlm     	OBJECT IDENTIFIER ::= { sc5520AlarmData 14 }
sc5520DsrShortedAlm     	OBJECT IDENTIFIER ::= { sc5520AlarmData 15 }
sc5520CtsShortedAlm     	OBJECT IDENTIFIER ::= { sc5520AlarmData 16 }
sc5520RxdShortedAlm     	OBJECT IDENTIFIER ::= { sc5520AlarmData 17 }
sc5520RxcShortedAlm     	OBJECT IDENTIFIER ::= { sc5520AlarmData 18 }
sc5520TxcShortedAlm     	OBJECT IDENTIFIER ::= { sc5520AlarmData 19 }
sc5520DBURequestForScanAlm	OBJECT IDENTIFIER ::= { sc5520AlarmData 20 }
sc5520DBUOnAlm			OBJECT IDENTIFIER ::= { sc5520AlarmData 21 }
sc5520DBUFailedAlm		OBJECT IDENTIFIER ::= { sc5520AlarmData 22 }
sc5520CSULoopbackAlm		OBJECT IDENTIFIER ::= { sc5520AlarmData 23 }

-- The following alarms are 'NOT MASKABLE' sc5520NoResponseAlm {1},
-- sc5520DiagRxErrAlm {2}, sc5520PowerUpAlm {3}.
-- All other alarms 'ARE MASKABLE'.

-- Alarm		Table Entry
-- --------------	---------------------------
-- No Responce		sc5520NoResponseAlm
-- Diag Rx Error	sc5520DiagRxErrAlm
-- Power Up Alarm 	sc5520PowerUpAlm
-- EEPROM Corrupt	sc5520EEChkSumErrAlm
-- Front Panel Test	sc5520FpTestAlm
-- Streaming		sc5520StreamingAlm
-- DSR Loss		sc5520DSRLossAlm
-- DTR Loss		sc5520DTRLossAlm
-- DTP Loss		sc5520DTPLossAlm
-- DCD Loss		sc5520DCDLossAlm
-- RXD Loss		sc5520RXDLossAlm
-- TXD Loss		sc5520TXDLossAlm
-- TM Shorted		sc5520TmShortedAlm
-- DCD Shorted		sc5520DcdShortedAlm
-- DSR Shorted		sc5520DsrShortedAlm
-- CTS Shorted		sc5520CtsShortedAlm
-- RXD Shorted		sc5520RxdShortedAlm
-- RXC Shorted		sc5520RxcShortedAlm
-- TXC Shorted		sc5520TxcShortedAlm
-- DBU Request Scan	sc5520DBURequestForScanAlm
-- DBU is On		sc5520DBUOnAlm
-- DBU has Failed	sc5520DBUFailedAlm
-- FP initiated Test	sc5520FrontPanelTestAlm
-- CSU Loopback(network)sc5520CSULoopbackAlm



--
-- ****************************************************************************
--                           Maintenance Table
-- ****************************************************************************
--

sc5520MaintTable OBJECT-TYPE
    SYNTAX SEQUENCE OF Sc5520MaintEntry
    ACCESS not-accessible
    STATUS mandatory
    DESCRIPTION
    	"The table describes the maintenance functions for the SC5520. "
    ::= { sc5520 5 }

sc5520MaintEntry OBJECT-TYPE
    SYNTAX Sc5520MaintEntry
    ACCESS not-accessible
    STATUS mandatory
    DESCRIPTION
 	"An entry in the GDC maintenance Table"
    INDEX { sc5520MaintIndex }
    ::= { sc5520MaintTable 1 }

Sc5520MaintEntry ::=
SEQUENCE {
    	sc5520MaintIndex SCinstance,
	sc5520LedStatus OCTET STRING,
	sc5520SoftReset INTEGER,
	sc5520SysUpTime TimeTicks,
	sc5520PrivateStorage1 DisplayString,
	sc5520PrivateStorage2 DisplayString,
	sc5520PrivateStorage3 DisplayString,
	sc5520BlinkINS INTEGER 		
    }

sc5520MaintIndex OBJECT-TYPE
    SYNTAX SCinstance
    ACCESS read-only
    STATUS mandatory
    DESCRIPTION
    	"The index value which uniquely identifies the SC5520 to which this
	entry is applicable.  This has the form of a SCinstance which defines
	the slot, line, and drop of the SC5520 with no sub-identifier value."
    ::= { sc5520MaintEntry 1 }

sc5520LedStatus OBJECT-TYPE
    SYNTAX  OCTET STRING (SIZE(3))
    ACCESS  read-only
    STATUS  mandatory
    DESCRIPTION
	"Returns a bitwise snapshot of the front panel LED state.
                Octet 1 bit 7 - not used
                        bit 6 - ON
                        bit 5 - INSV
                        bit 4 - RSP
			bit 3 - TMG
			bit 2 - future use
                        bit 1 - future use
			bit 0 - future use

                Octet 2 bit 7 - not used
                        bit 6 - SD
                        bit 5 - RD
                        bit 4 - RS
                        bit 3 - CO
                        bit 2 - future use
                        bit 1 - ALM
			bit 0 - TM

	        Octet 3 bit 7 - not used
                        bit 6 - ST
                        bit 5 - LT
                        bit 4 - RL
                        bit 3 - DL
                        bit 2 - future use
                        bit 1 - future use
                        bit 0 - future use"
    ::= { sc5520MaintEntry 2 }

sc5520SoftReset OBJECT-TYPE
    SYNTAX INTEGER {
    	normal(1),      -- read only
    	reset(2)	-- write only
    }
    ACCESS read-write
    STATUS mandatory
    DESCRIPTION
    	"This object will cause software reset in dataset."
    ::= { sc5520MaintEntry 3 }


sc5520SysUpTime OBJECT-TYPE
    SYNTAX TimeTicks
    ACCESS read-only
    STATUS mandatory
    DESCRIPTION
		 "This variable is used to report the elapsed system tick
		 time for conversion to real time at the controller and is
		 not related to the sysUpTime referenced in MIB-II.
		 Upon power-up of the unit, the elapsed time is cleared.
		 The elapsed time counter rolls over upon reaching the
		 maximum count."
    ::= { sc5520MaintEntry 4 }

sc5520PrivateStorage1 OBJECT-TYPE
    SYNTAX DisplayString (SIZE(16))
    ACCESS read-write
    STATUS mandatory
    DESCRIPTION
    	"This object is used for general purpose storage."
    ::= { sc5520MaintEntry 5 }

sc5520PrivateStorage2 OBJECT-TYPE
    SYNTAX DisplayString (SIZE(16))
    ACCESS read-write
    STATUS mandatory
    DESCRIPTION
    	"This object is used for general purpose storage."
    ::= { sc5520MaintEntry 6 }

sc5520PrivateStorage3 OBJECT-TYPE
    SYNTAX DisplayString (SIZE(16))
    ACCESS read-write
    STATUS mandatory
    DESCRIPTION
    	"This object is used for general purpose storage."
    ::= { sc5520MaintEntry 7 }

sc5520BlinkINS OBJECT-TYPE
     SYNTAX INTEGER
     {
         notBlinking(1),
         blinking(2)
     }
     ACCESS read-write
     STATUS mandatory
     DESCRIPTION
     "This variable is used to blink the in service (INS) led
      on the front panel of the sc5520. A get returns the current
      status of the INS LED - either blinking(2) or not 
      blinking(1).  A set of blinking(2) will cause the sc5520 to
      blink the INS LED and a set of notBlinking(1) will cause
      the sc5520 to stop blinking the INS LED." 
     ::= { sc5520MaintEntry 8 }



--
-- ****************************************************************************
--                      Diagnostic Configuration Table
-- ****************************************************************************
--
-- The objects in this table are used to config Selftest patterns,
-- read all test results, and halt all tests that might be running.
--

sc5520DiagCfgTable OBJECT-TYPE
    SYNTAX SEQUENCE OF Sc5520DiagCfgEntry
    ACCESS not-accessible
    STATUS mandatory
    DESCRIPTION
    	"The Diagnostic Configuration Table."
    ::= { sc5520 6 }

sc5520DiagCfgEntry OBJECT-TYPE
    SYNTAX Sc5520DiagCfgEntry
    ACCESS not-accessible
    STATUS mandatory
    DESCRIPTION
    	"An entry in the GDC DDS Diagnostic Configuration Table."
    INDEX { sc5520DiagCfgIndex }
    ::= { sc5520DiagCfgTable 1}

Sc5520DiagCfgEntry ::=
  SEQUENCE  {
    	sc5520DiagCfgIndex SCinstance,
        sc5520DiagSendCode INTEGER,
        sc5520DiagTestExceptions INTEGER,
        sc5520DiagBitErrors INTEGER,
    	sc5520DiagBlockErrors INTEGER,
	sc5520DiagTestReset INTEGER,
	sc5520DiagTimeDelay INTEGER
    }

sc5520DiagCfgIndex OBJECT-TYPE
    SYNTAX SCinstance
    ACCESS read-only
    STATUS mandatory
    DESCRIPTION
    	"The index value which uniquely identifies the SC5520 to which this
	entry is applicable.  This has the form of a SCinstance which defines
	the slot, line, and drop of the SC5520 with no sub-identifier value."
    ::= { sc5520DiagCfgEntry 1 }


sc5520DiagSendCode OBJECT-TYPE
    SYNTAX INTEGER {
    	sc5520SendOtherPattern(1),
    	sc5520Send511Pattern(2),
    	sc5520Send2047Pattern(3),
    	sc5520Send15BitPattern(4)
    }
    ACCESS read-write
    STATUS mandatory
    DESCRIPTION
	"Configures the selftest pattern to be run during any
	diagonostic test involving selftest. If option SendOtherPattern is
        selected, then pattern will default to 15 bit if unit is set
	for 56k-DDS/sc-multi point else pattern will default to 511 bit
	for all other conditions"
    ::= { sc5520DiagCfgEntry 2 }


sc5520DiagTestExceptions OBJECT-TYPE
    SYNTAX INTEGER {
	noExceptions(1),
	blocksOutOfRange(2),
	bitsOutOfRange(3),
	blocksAndBitsOutOfRange(4)
    }
    ACCESS read-only
    STATUS mandatory
    DESCRIPTION
    	"Indicates exceptions that have occurred that may affect
    	interpretation of the test results.

    	The value of this object is a sum.  This sum initially take
    	the value zero.  Then, for each exception, the value
    	associated with the exception is added to the sum.

    	The exception values are:

    		value	exception
		    0	No errors
   		    1   bit over range
    		    2   block over range
		    4 	bit and block over range"
    ::= { sc5520DiagCfgEntry 3 }

sc5520DiagBitErrors OBJECT-TYPE
    SYNTAX INTEGER (0..65535)
    ACCESS read-only
    STATUS mandatory
    DESCRIPTION
    	"The bit errors of the last diagnostic test that involved a
	Selftest pattern.  Reading bit errors while a diagnostic
	test in running will cause the unit to drop out of test
	and invalidate the bit errors.  Bit errors should be read
	only after the test is completed.  The valid range for bit
	errors is 0 to 1,023, 65535 will be returned if for any reason
	the test was terminated early."
    ::= { sc5520DiagCfgEntry 4 }

sc5520DiagBlockErrors OBJECT-TYPE
    SYNTAX INTEGER (0..65535)
    ACCESS read-only
    STATUS mandatory
    DESCRIPTION
    	"The block errors of the last diagnostic test that involved a
	Selftest pattern.  Reading block errors while a diagnostic
	test in running will cause the unit to drop out of test
	and invalidate the block errors.  Block errors should be read
	only after the test is completed.  The valid range for block
	errors is 0 to 1,023, 65535 will be returned if for any reason
	the test was terminated early."
    ::= { sc5520DiagCfgEntry 5 }

sc5520DiagTestReset OBJECT-TYPE
    SYNTAX INTEGER {
    	noTestActive(1),	-- read only
	testActive(2),  	-- read only
    	resetTest(3)		-- write only
    }
    ACCESS read-write
    STATUS mandatory
    DESCRIPTION
    	"This object will halt the execution of any and all
	diagnostic test that may be running."
    ::= { sc5520DiagCfgEntry 6 }


sc5520DiagTimeDelay OBJECT-TYPE
    SYNTAX INTEGER (0..16383)
    ACCESS read-only
    STATUS mandatory
    DESCRIPTION
    	"This object reads the results of a Network Delay Test.
	The results are valid only after the test is completed
	which takes about 10 seconds.  The unit for time delay
	is in miliseconds. The valid range for delay is 0 to 4096,
	16383 will be returned if for any reason the test was terminated
	early. Reading this object while a test is in progress will
	terminate the test."
    ::= { sc5520DiagCfgEntry 7 }


--
-- Diagnostic Execution Table
--
--

sc5520ExcDiagTable OBJECT-TYPE
    SYNTAX SEQUENCE OF Sc5520ExcDiagEntry
    ACCESS not-accessible
    STATUS mandatory
    DESCRIPTION
    	"The Diagnostic Execution Table."
    ::= { sc5520 7 }

sc5520ExcDiagEntry OBJECT-TYPE
    SYNTAX Sc5520ExcDiagEntry
    ACCESS not-accessible
    STATUS mandatory
    DESCRIPTION
    	"An entry in the GDC DDS Diagnostic Execution Table."
    INDEX { sc5520ExcDiagIndex }
    ::= { sc5520ExcDiagTable 1 }

Sc5520ExcDiagEntry ::=
  SEQUENCE  {
    	sc5520ExcDiagIndex SCinstance,
	sc5520DiagExtLineloop INTEGER,
	sc5520DiagIntLineloop INTEGER,
 	sc5520DiagExtDataloop INTEGER,
	sc5520DiagTestStatus INTEGER,
	sc5520DiagExtRemoteLoop INTEGER,
	sc5520DiagRemLoopWithSelf INTEGER
    }

sc5520ExcDiagIndex OBJECT-TYPE
    SYNTAX SCinstance
    ACCESS read-only
    STATUS mandatory
    DESCRIPTION
    	"The index value which uniquely identifies the SC5520 to which this
	entry is applicable.  This has the form of a SCinstance which defines
	the slot, line, and drop of the SC5520 with no sub-identifier value."
    ::= { sc5520ExcDiagEntry 1 }


sc5520DiagExtLineloop OBJECT-TYPE
  	SYNTAX INTEGER {
	lineloopOff(1),		-- Read only
        lineloopOn(2),		-- Read only
        external(3)		-- Write only
    }
    ACCESS read-write
    STATUS mandatory
    DESCRIPTION
	"Lineloop (or Analoop) can be either a Bilaterial or Unilaterial
        loopback depending on option ddsDteTermaloop.  To initiate a
	Lineloop with no Selftest SET this object and specifiy external,
	this will allow the data from the DTE to looped back to itself.
	Emun external(3) is write only.  The only valid response to a
	READ is lineloopOn(2) or lineloopOff(1). To halt this test you must
	SET the sc5520DiagTestReset object. Reading test results via the
	sc5520DiagBitErrors or  sc5520DiagBlockErrors objects while the test
	is running will also cause the test to terminate.
	There are no test results associated with this test. "
   ::= { sc5520ExcDiagEntry 2 }

sc5520DiagIntLineloop OBJECT-TYPE
  	SYNTAX INTEGER {
	lineloopOff(1),		-- Read only
        lineloopOn(2),		-- Read only
	blocks1(3),		-- Write only
	blocks10(4),		-- Write only
	blocks100(5),		-- Write only
	blocks500(6),		-- Write only
	blocks1000(7),		-- Write only
	blocks5000(8),		-- Write only
	blocks10000(9),		-- Write only
	blocks50000(10) 	-- Write only
    }
    ACCESS read-write
    STATUS mandatory
    DESCRIPTION
	"Lineloop (or Analoop) can be either a Bilaterial or Unilaterial
	loopback depending on option ddsDteTermaloop.  To initiate a
	Lineloop with Selftest SET this object and specifiy a
	blocksize. The blocksize indicates the number of blocks the
	Selftest pattern generator will run.  There are 1000 bits/block.
	Emuns 3 through 10 are write only.  The only valid
	responses to a READ are lineloopOn(2) or lineloopOff(1). This test
	will terminate after the specified number of blocks have been run.
 	Reading test results via the sc5520DiagBitErrors or sc5520DiagBlockErrors
	objects while the test is running will cause
	the test to terminate prematurely and render the results invalid.
	Test results should be only read after the test is completed.
	The current Test Status can be obtained by reading this object or the
	nms520DiagTestStatus object on the unit under test.  This test can
	also be terminated by seting the sc5520DiagTestReset object. "
    ::= { sc5520ExcDiagEntry 3 }


sc5520DiagExtDataloop OBJECT-TYPE
	SYNTAX INTEGER {
	dataloopOff(1),		-- Read only
        dataloopOn(2),		-- Read only
	external(3)		-- Write only
    }
    ACCESS read-write
    STATUS mandatory
    DESCRIPTION
	"To initiate a Dataloop test with no Selftest SET this object
	and specifiy external, this will allow the data from the DTE attached
	to the far end unit (nms520) to looped back to itself. Emun external(3)
	is write only.  The only valid response to a READ is dataloopOn(2) or
	dataloopOff(1). To halt this test you must SET the sc5520DiagTestReset
	object. Reading test results via the sc5520DiagBitErrors or
	sc5520DiagBlockErrors objects while the test is running will also cause
	the test to terminate. There are no test results associated with this test.
	Reading test status on the remote unit via nms520DiagTestStatus may
	interfere with the diagonostic test pattern generated from the terminal
	equiptment. "
    ::= { sc5520ExcDiagEntry 4 }


sc5520DiagTestStatus OBJECT-TYPE
    	SYNTAX INTEGER {
	noTest(1),
	externalLineloop(2),		-- Analoop
	internalLineloop(3),		-- Analoop & SelfTest
	externalDataloop(4),		-- Dataloop
	serviceTestCenterLoop(5),	-- Network initiated loopback
	endToend(6),			-- EndToEnd & SelfTest
	remoteLoop(7),			-- Remote Loop
	remoteLoopWithSelfTest(8),	-- Remote Loop & SelfTest
	networkDelay(9)			-- Network Delay Test
	}
    ACCESS read-only
    STATUS mandatory
    DESCRIPTION
	"This object gives the current diagonostic test status. noTest
	indicates that no diagonostic test is currently active. "
   ::= { sc5520ExcDiagEntry 5 }

sc5520DiagExtRemoteLoop OBJECT-TYPE
	SYNTAX INTEGER {
	remoteloopOff(1),		-- Read only
        remoteloopOn(2),		-- Read only
	external(3)      		-- Write only
    }
    ACCESS read-write
    STATUS mandatory
    DESCRIPTION
	"Point to Point Application only. To initiate a Remoteloop test with no
	Selftest SET this object and specifiy external. The sc5520 DSE transmitt
	an in-band command to its remote DSU, directing the remote to loop received
	signals back onto the network.  The DSE is configurable to send (and
	accept) either a V.54 or a PN127 remote loop command.  The remote DSU must
	be configured to accept the same command the DSE transmits. Emun external(3)
	is write only.  The only valid response to a READ is remoteloopOn(2) or
	remoteloopOff(1). To halt this test you must SET the sc5520DiagTestReset
	object unless option RemLoopTimeOut is enabled.  If enable maximum test time
	is 10 minutes.  Reading test results via the sc5520DiagBitErrors or
	sc5520DiagBlockErrors objects while the test is running will also cause
	the test to terminate. There are no test results associated with this test.
	Reading test status on the remote unit via nms520DiagTestStatus may
	interfere with the diagonostic test pattern generated from the terminal
	equipment. The Remote Loop Function is for use ONLY on point to point links."
    ::= { sc5520ExcDiagEntry 6 }

sc5520DiagRemLoopWithSelf OBJECT-TYPE
	SYNTAX INTEGER {
	remoteloopOff(1),	-- Read only
        remoteloopOn(2),	-- Read only
	blocks1(3),		-- Write only
	blocks10(4),		-- Write only
	blocks100(5),		-- Write only
	blocks500(6),		-- Write only
	blocks1000(7),		-- Write only
	blocks5000(8),		-- Write only
	blocks10000(9),		-- Write only
	blocks50000(10)		-- Write only
    }
    ACCESS read-write
    STATUS mandatory
    DESCRIPTION
	"To initiate a Remoteloop with Selftest SET this object and specifiy a
	blocksize. The remote unit will go into remoteloop and the master (the sc5520)
	unit will go into Selftest. The sc5520 transmits an in-band command to its
	remote DSU, directing the remote to loop received signals back onto the
	network.  The DSE is configurable to send (and accept) either a V.54 or a
	PN 127 remote loop command.  The remote DSU must be configured to accept
	the same command the DSE transmits. The sc5520 enables its internal Test
	Pattern Generator to provide the signal for the Remote Loop and enables its
	Test Pattern Checker to verify the signal. The DSE is isolated from its DTE
	while the Test Pattern Generator and Checker are enabled.  The blocksize
	indicates the number of blocks the Selftest pattern generator will run.
	There are 1000 bits/block.  Emuns 3 through 10 are write only.  If option
	Remlooptimeout is enabled then the maximum test time is 10 minutes otherwise
	block size time is used. The only valid responses to a READ are remoteloopOn(2)
	or remoteloopOff(1).  This test will terminate after the specified number of
	blocks have been run.  Reading test results via the sc5520DiagBitErrors or
	sc5520DiagBlockErrors objects while the test is running will cause the test
	to terminate prematurely and render the results invalid.  Test results should
	be read only after the test is completed and are available from the master
	(sc5520) unit.  The current Test Status can be obtained by reading the
	sc5520DiagTestStatus object on the master unit, reading test status on the
	remote unit may interfere with the diagonostic test pattern and cause errors.
	This test can also be terminated by seting the nms520DiagTestReset object. "
    ::= { sc5520ExcDiagEntry 7 }






-- ****************************************************************************
--                                Version Table
-- ****************************************************************************


sc5520VersionTable OBJECT-TYPE
    SYNTAX SEQUENCE OF Sc5520VersionEntry
    ACCESS not-accessible
    STATUS mandatory
    DESCRIPTION " "
    ::= { sc5520 8  }

sc5520VersionEntry OBJECT-TYPE
    SYNTAX Sc5520VersionEntry
    ACCESS not-accessible
    STATUS mandatory
    DESCRIPTION
        "An entry in the GDC SC5520 Version Table."
    INDEX	{ sc5520VersionIndex }
    ::= { sc5520VersionTable 1 }

Sc5520VersionEntry ::=
    SEQUENCE {
	sc5520VersionIndex    		SCinstance,
	sc5520ActiveFirmwareRev 	DisplayString,
	sc5520StoredFirmwareRev		DisplayString,
	sc5520BootRev			DisplayString,
	sc5520StoredFirmwareStatus	INTEGER,
	sc5520SwitchActiveFirmware	INTEGER,
	sc5520DownloadingMode          	INTEGER
    }

sc5520VersionIndex OBJECT-TYPE
    SYNTAX SCinstance
    ACCESS read-only
    STATUS mandatory
    DESCRIPTION
        "Identifies Version parameters associated with the managed object."
    ::= { sc5520VersionEntry 1 }


sc5520ActiveFirmwareRev OBJECT-TYPE
    SYNTAX DisplayString (SIZE(8))
    ACCESS read-only
    STATUS mandatory
    DESCRIPTION
        "The version number of the firmware currently executing.

	The format is MM.NN.BB where:
	
		MM: Major Revision (0-99)
		NN: Minor Revision (0-99)
		BB: Bug Fix Revision (0-99)

 	 	"
    ::= { sc5520VersionEntry 2 }

sc5520StoredFirmwareRev OBJECT-TYPE
    SYNTAX DisplayString (SIZE(8))
    ACCESS read-only
    STATUS mandatory
    DESCRIPTION
        "The version number of the firmware stored (in a compressed format) 
         but not currently executing.

	
		MM: Major Revision (0-99)
		NN: Minor Revision (0-99)
		BB: Bug Fix Revision (0-99)

	"
    ::= { sc5520VersionEntry 3 }

sc5520BootRev OBJECT-TYPE
    SYNTAX DisplayString (SIZE(2))
    ACCESS read-only
    STATUS mandatory
    DESCRIPTION
        "The version number of the bootstrap firmware. 

    	The version number of the firmware, to allow products to know which
    	revision is installed.  The released version number is sequenced from
    	--, A-, ... AA, ... ZZ.  
	"
    ::= { sc5520VersionEntry 4 }


sc5520StoredFirmwareStatus OBJECT-TYPE
    SYNTAX INTEGER {
        statBlank(1),                       
        statDownLoading(2),
	statOK(3),
	statCheckSumBad(4),    
	statUnZipping(5),
	statBadUnZip(6),
	statDownloadAborted(7)
                    
    }
    ACCESS read-only
    STATUS mandatory
    DESCRIPTION
        "This object represents the state of the Non-Active or Stored firmware:

        statBlank(1)    	Factory Default                  
        statDownLoading(2)	In process of downloading firmware

	statOK(3)		Zipped version checksum succesful (OK to switch)
				(can set sc5520SwitchActive to switchActive(2))
				
	statCheckSumBad(4)    	Failed checksum after download
	statUnZipping(5)	In process of uncompressing into active area
	statBadUnZip(6)      	Failed last uncompress 
	statDownloadAborted(7)  Download aborted by user             


	The object is read only.
	 "
    ::= { sc5520VersionEntry 5 }


sc5520SwitchActiveFirmware OBJECT-TYPE
    SYNTAX INTEGER {
        switchNorm(1),                  -- Read only
        switchActive(2)			-- Write only
    }
    ACCESS read-write
    STATUS mandatory
    DESCRIPTION
        "This object is used to switch the active executing firmware from the version 
	in sc5520ActiveRev to the version in sc5520StoredRev.

	When a  switchActive(2) is set (write only) the element will:
		1) reboot
		2) uncompress stored code into active area
		3) perform checksum on active area
		4) Set sc5520StoredStatus object to indicate results
		5) If succesfull:
			update sc5520ActiveFirmwareRev and sc5520StoredFirmwareRev
			and begin executing
		   If failed: 
			replace active area with previous revision


	The switchNorm(1) enumeration will always be read. 

	Setting switchActive(2) when the sc5520StoredStatus is not statOK(3) will
	result in an error.
	"
    ::= { sc5520VersionEntry 6 }


sc5520DownloadingMode OBJECT-TYPE
    SYNTAX INTEGER {
        disableAll(1),
        enableAndWait(2),
	enableAndSwitch(3)
    }
    ACCESS read-write
    STATUS mandatory
    DESCRIPTION
        "This object is used to configure the download mode:

        disableAll(1)		Prevents any firmware downloading to SC5520

        enableAndWait(2)        Allows downloading zipped code to be stored only!
								
	enableAndSwitch(3)	Allows downloading and then unzips and begins executing
				the new code

	"
    ::= { sc5520VersionEntry 7 }






END
