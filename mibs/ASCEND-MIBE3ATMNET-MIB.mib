--			Ascend mibe3atmnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBE3ATMNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibe3AtmNetworkProfile  OBJECT IDENTIFIER ::= { configuration 15}

	-- The mibe3AtmNetworkProfile table
	--
	-- This table contains parameters for the mibe3AtmNetworkProfile profile
	--

    mibe3AtmNetworkProfileTable	OBJECT-TYPE
	SYNTAX		SEQUENCE OF Mibe3AtmNetworkProfileEntry
	ACCESS		not-accessible
	STATUS		mandatory
	DESCRIPTION	"A list of mibe3AtmNetworkProfile profile entries."
	::= { mibe3AtmNetworkProfile 1 }

    mibe3AtmNetworkProfileEntry	OBJECT-TYPE
	SYNTAX		Mibe3AtmNetworkProfileEntry
	ACCESS		not-accessible
	STATUS		mandatory
	DESCRIPTION	"A mibe3AtmNetworkProfile entry containing objects that
			 maps to the parameters of mibe3AtmNetworkProfile profile."
	INDEX		{ e3AtmNetworkProfile-Shelf-o, e3AtmNetworkProfile-Slot-o, e3AtmNetworkProfile-Item-o }
	::= { mibe3AtmNetworkProfileTable 1 }

    Mibe3AtmNetworkProfileEntry ::=
	SEQUENCE {
	    e3AtmNetworkProfile-Shelf-o
		INTEGER,
	    e3AtmNetworkProfile-Slot-o
		INTEGER,
	    e3AtmNetworkProfile-Item-o
		INTEGER,
	    e3AtmNetworkProfile-Name
		DisplayString,
	    e3AtmNetworkProfile-PhysicalAddress-Shelf
		INTEGER,
	    e3AtmNetworkProfile-PhysicalAddress-Slot
		INTEGER,
	    e3AtmNetworkProfile-PhysicalAddress-ItemNumber
		INTEGER,
	    e3AtmNetworkProfile-Enabled
		INTEGER,
	    e3AtmNetworkProfile-IgnoreLineup
		INTEGER,
	    e3AtmNetworkProfile-LineConfig-TrunkGroup
		INTEGER,
	    e3AtmNetworkProfile-LineConfig-NailedGroup
		INTEGER,
	    e3AtmNetworkProfile-LineConfig-Loopback
		INTEGER,
	    e3AtmNetworkProfile-LineConfig-HighTxOutput
		INTEGER,
	    e3AtmNetworkProfile-LineConfig-ReceiveEqualization
		INTEGER,
	    e3AtmNetworkProfile-LineConfig-FramerMode
		INTEGER,
	    e3AtmNetworkProfile-LineConfig-VpiVciRange
		INTEGER,
	    e3AtmNetworkProfile-LineConfig-ClockSource
		INTEGER,
	    e3AtmNetworkProfile-LineConfig-ClockPriority
		INTEGER,
	    e3AtmNetworkProfile-LineConfig-CellPayloadScramble
		INTEGER,
	    e3AtmNetworkProfile-LineConfig-StatusChangeTrapEnable
		INTEGER,
	    e3AtmNetworkProfile-SparePhysicalAddress-Shelf
		INTEGER,
	    e3AtmNetworkProfile-SparePhysicalAddress-Slot
		INTEGER,
	    e3AtmNetworkProfile-SparePhysicalAddress-ItemNumber
		INTEGER,
	    e3AtmNetworkProfile-SparingMode
		INTEGER,
	    e3AtmNetworkProfile-Action-o
		INTEGER
	}

    e3AtmNetworkProfile-Shelf-o	OBJECT-TYPE
	SYNTAX	INTEGER
	ACCESS	read-only
	STATUS	mandatory
	DESCRIPTION	""
	::= { mibe3AtmNetworkProfileEntry 1 }

    e3AtmNetworkProfile-Slot-o	OBJECT-TYPE
	SYNTAX	INTEGER
	ACCESS	read-only
	STATUS	mandatory
	DESCRIPTION	""
	::= { mibe3AtmNetworkProfileEntry 2 }

    e3AtmNetworkProfile-Item-o	OBJECT-TYPE
	SYNTAX	INTEGER
	ACCESS	read-only
	STATUS	mandatory
	DESCRIPTION	""
	::= { mibe3AtmNetworkProfileEntry 3 }

    e3AtmNetworkProfile-Name	OBJECT-TYPE
	SYNTAX	DisplayString
	ACCESS	read-write
	STATUS	mandatory
	DESCRIPTION	"For future use. The current design does not use the name field but instead references E3-ATM lines by the physical address; we may in the future support referencing E3-ATM lines by name as well as by address. The name consists of a null terminated ascii string supplied by the user; it defaults to the ascii form of the E3-ATM line physical address."
	::= { mibe3AtmNetworkProfileEntry 4 }

    e3AtmNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibe3AtmNetworkProfileEntry 5 }

    e3AtmNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibe3AtmNetworkProfileEntry 6 }

    e3AtmNetworkProfile-PhysicalAddress-ItemNumber	OBJECT-TYPE
	SYNTAX	INTEGER
	ACCESS	read-write
	STATUS	mandatory
	DESCRIPTION	"A number that specifies an addressable entity within the context of shelf and slot."
	::= { mibe3AtmNetworkProfileEntry 7 }

    e3AtmNetworkProfile-Enabled	OBJECT-TYPE
	SYNTAX	INTEGER {
		    no (1),
		    yes (2)
		}
	ACCESS	read-write
	STATUS	mandatory
	DESCRIPTION	"TRUE if the line is enabled, otherwise FALSE."
	::= { mibe3AtmNetworkProfileEntry 8 }

    e3AtmNetworkProfile-IgnoreLineup	OBJECT-TYPE
	SYNTAX	INTEGER {
		    systemDefined (1),
		    no (2),
		    yes (3)
		}
	ACCESS	read-write
	STATUS	mandatory
	DESCRIPTION	"Ignore line up value for this port."
	::= { mibe3AtmNetworkProfileEntry 27 }

    e3AtmNetworkProfile-LineConfig-TrunkGroup	OBJECT-TYPE
	SYNTAX	INTEGER
	ACCESS	read-write
	STATUS	mandatory
	DESCRIPTION	"The trunk group to which this line is assigned. 0 means this line is not part of a trunk group."
	::= { mibe3AtmNetworkProfileEntry 9 }

    e3AtmNetworkProfile-LineConfig-NailedGroup	OBJECT-TYPE
	SYNTAX	INTEGER
	ACCESS	read-write
	STATUS	mandatory
	DESCRIPTION	"A number that identifies the set of lines that makes up a nailed group. 0 means this line is not part of a nailed group."
	::= { mibe3AtmNetworkProfileEntry 10 }

    e3AtmNetworkProfile-LineConfig-Loopback	OBJECT-TYPE
	SYNTAX	INTEGER {
		    noLoopback (1),
		    facilityLoopback (2),
		    localLoopback (3)
		}
	ACCESS	read-write
	STATUS	mandatory
	DESCRIPTION	"Loopback mode."
	::= { mibe3AtmNetworkProfileEntry 14 }

    e3AtmNetworkProfile-LineConfig-HighTxOutput	OBJECT-TYPE
	SYNTAX	INTEGER {
		    no (1),
		    yes (2)
		}
	ACCESS	read-write
	STATUS	mandatory
	DESCRIPTION	"TRUE if the E3 cable length is more than 300 ft, otherwise FALSE."
	::= { mibe3AtmNetworkProfileEntry 15 }

    e3AtmNetworkProfile-LineConfig-ReceiveEqualization	OBJECT-TYPE
	SYNTAX	INTEGER {
		    no (1),
		    yes (2)
		}
	ACCESS	read-write
	STATUS	mandatory
	DESCRIPTION	"TRUE if receive equalization is needed, otherwise FALSE. Receive equalization is needed if the cable length is more than 300 ft."
	::= { mibe3AtmNetworkProfileEntry 20 }

    e3AtmNetworkProfile-LineConfig-FramerMode	OBJECT-TYPE
	SYNTAX	INTEGER {
		    g751Adm (1),
		    g751Plcp (2),
		    g832Adm (3),
		    g832AdmFrameLocked (4),
		    g832AdmLoopTimed (5)
		}
	ACCESS	read-write
	STATUS	mandatory
	DESCRIPTION	"The E3 ATM framer mode."
	::= { mibe3AtmNetworkProfileEntry 16 }

    e3AtmNetworkProfile-LineConfig-VpiVciRange	OBJECT-TYPE
	SYNTAX	INTEGER {
		    n-01-3232767 (1),
		    n-03-3216383 (2),
		    n-07-328191 (3),
		    n-015-324095 (4),
		    n-031-322047 (5),
		    n-063-321023 (6),
		    n-0127-32511 (7),
		    n-0255-32255 (8),
		    vpi0255Vci32255 (9),
		    vpi0255Vci32511 (10),
		    vpi0255Vci321023 (11),
		    vpi0255Vci322047 (12),
		    vpi0255Vci324095 (13),
		    vpi0255Vci328191 (14),
		    vpi0255Vci3216383 (15)
		}
	ACCESS	read-write
	STATUS	mandatory
	DESCRIPTION	"The E3 ATM valid VPI/VCI value range."
	::= { mibe3AtmNetworkProfileEntry 17 }

    e3AtmNetworkProfile-LineConfig-ClockSource	OBJECT-TYPE
	SYNTAX	INTEGER {
		    eligible (1),
		    notEligible (2)
		}
	ACCESS	read-write
	STATUS	mandatory
	DESCRIPTION	"Determine whether the 8KHz clock from the E3-ATM board is eligible to be used as the system-wide TDM clock source."
	::= { mibe3AtmNetworkProfileEntry 21 }

    e3AtmNetworkProfile-LineConfig-ClockPriority	OBJECT-TYPE
	SYNTAX	INTEGER {
		    highPriority (2),
		    middlePriority (3),
		    lowPriority (4)
		}
	ACCESS	read-write
	STATUS	mandatory
	DESCRIPTION	"Clock priority assigned to the E3-ATM line. Used to select a particular E3 line as clock source."
	::= { mibe3AtmNetworkProfileEntry 22 }

    e3AtmNetworkProfile-LineConfig-CellPayloadScramble	OBJECT-TYPE
	SYNTAX	INTEGER {
		    no (1),
		    yes (2)
		}
	ACCESS	read-write
	STATUS	mandatory
	DESCRIPTION	"TRUE if the cell payload scrambling is enabled, otherwise FALSE."
	::= { mibe3AtmNetworkProfileEntry 18 }

    e3AtmNetworkProfile-LineConfig-StatusChangeTrapEnable	OBJECT-TYPE
	SYNTAX	INTEGER {
		    no (1),
		    yes (2)
		}
	ACCESS	read-write
	STATUS	mandatory
	DESCRIPTION	"When set to No, do not send dsx3LineStatusChangeTrapEnable trap. If Yes, send traps. The default is No."
	::= { mibe3AtmNetworkProfileEntry 28 }

    e3AtmNetworkProfile-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibe3AtmNetworkProfileEntry 23 }

    e3AtmNetworkProfile-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibe3AtmNetworkProfileEntry 24 }

    e3AtmNetworkProfile-SparePhysicalAddress-ItemNumber	OBJECT-TYPE
	SYNTAX	INTEGER
	ACCESS	read-write
	STATUS	mandatory
	DESCRIPTION	"A number that specifies an addressable entity within the context of shelf and slot."
	::= { mibe3AtmNetworkProfileEntry 25 }

    e3AtmNetworkProfile-SparingMode	OBJECT-TYPE
	SYNTAX	INTEGER {
		    inactive (1),
		    manual (2),
		    automatic (3)
		}
	ACCESS	read-write
	STATUS	mandatory
	DESCRIPTION	"Trunk port sparing operational mode for this port."
	::= { mibe3AtmNetworkProfileEntry 26 }

    e3AtmNetworkProfile-Action-o	OBJECT-TYPE
	SYNTAX	INTEGER {
		    noAction (1),
		    createProfile (2),
		    deleteProfile (3)
		}
	ACCESS	read-write
	STATUS	mandatory
	DESCRIPTION	""
	::= { mibe3AtmNetworkProfileEntry 19 }


	-- The mibe3AtmNetworkProfile__line_config__traffic_shapers table
	--
	-- This table contains parameters for the mibe3AtmNetworkProfile__line_config__traffic_shapers profile
	--

    mibe3AtmNetworkProfile-LineConfig-TrafficShapersTable	OBJECT-TYPE
	SYNTAX		SEQUENCE OF Mibe3AtmNetworkProfile-LineConfig-TrafficShapersEntry
	ACCESS		not-accessible
	STATUS		mandatory
	DESCRIPTION	"A list of mibe3AtmNetworkProfile__line_config__traffic_shapers profile entries."
	::= { mibe3AtmNetworkProfile 2 }

    mibe3AtmNetworkProfile-LineConfig-TrafficShapersEntry	OBJECT-TYPE
	SYNTAX		Mibe3AtmNetworkProfile-LineConfig-TrafficShapersEntry
	ACCESS		not-accessible
	STATUS		mandatory
	DESCRIPTION	"A mibe3AtmNetworkProfile__line_config__traffic_shapers entry containing objects that
			 maps to the parameters of mibe3AtmNetworkProfile__line_config__traffic_shapers profile."
	INDEX		{ e3AtmNetworkProfile-LineConfig-TrafficShapers-Shelf-o, e3AtmNetworkProfile-LineConfig-TrafficShapers-Slot-o, e3AtmNetworkProfile-LineConfig-TrafficShapers-Item-o, e3AtmNetworkProfile-LineConfig-TrafficShapers-Index-o }
	::= { mibe3AtmNetworkProfile-LineConfig-TrafficShapersTable 1 }

    Mibe3AtmNetworkProfile-LineConfig-TrafficShapersEntry ::=
	SEQUENCE {
	    e3AtmNetworkProfile-LineConfig-TrafficShapers-Shelf-o
		INTEGER,
	    e3AtmNetworkProfile-LineConfig-TrafficShapers-Slot-o
		INTEGER,
	    e3AtmNetworkProfile-LineConfig-TrafficShapers-Item-o
		INTEGER,
	    e3AtmNetworkProfile-LineConfig-TrafficShapers-Index-o
		INTEGER,
	    e3AtmNetworkProfile-LineConfig-TrafficShapers-Enabled
		INTEGER,
	    e3AtmNetworkProfile-LineConfig-TrafficShapers-BitRate
		INTEGER,
	    e3AtmNetworkProfile-LineConfig-TrafficShapers-PeakRate
		INTEGER,
	    e3AtmNetworkProfile-LineConfig-TrafficShapers-MaxBurstSize
		INTEGER,
	    e3AtmNetworkProfile-LineConfig-TrafficShapers-Aggregate
		INTEGER,
	    e3AtmNetworkProfile-LineConfig-TrafficShapers-Priority
		INTEGER
	}

    e3AtmNetworkProfile-LineConfig-TrafficShapers-Shelf-o	OBJECT-TYPE
	SYNTAX	INTEGER
	ACCESS	read-only
	STATUS	mandatory
	DESCRIPTION	""
	::= { mibe3AtmNetworkProfile-LineConfig-TrafficShapersEntry 1 }

    e3AtmNetworkProfile-LineConfig-TrafficShapers-Slot-o	OBJECT-TYPE
	SYNTAX	INTEGER
	ACCESS	read-only
	STATUS	mandatory
	DESCRIPTION	""
	::= { mibe3AtmNetworkProfile-LineConfig-TrafficShapersEntry 2 }

    e3AtmNetworkProfile-LineConfig-TrafficShapers-Item-o	OBJECT-TYPE
	SYNTAX	INTEGER
	ACCESS	read-only
	STATUS	mandatory
	DESCRIPTION	""
	::= { mibe3AtmNetworkProfile-LineConfig-TrafficShapersEntry 3 }

    e3AtmNetworkProfile-LineConfig-TrafficShapers-Index-o	OBJECT-TYPE
	SYNTAX	INTEGER
	ACCESS	read-only
	STATUS	mandatory
	DESCRIPTION	""
	::= { mibe3AtmNetworkProfile-LineConfig-TrafficShapersEntry 4 }

    e3AtmNetworkProfile-LineConfig-TrafficShapers-Enabled	OBJECT-TYPE
	SYNTAX	INTEGER {
		    no (1),
		    yes (2)
		}
	ACCESS	read-write
	STATUS	mandatory
	DESCRIPTION	"TRUE if the shaper is enabled, otherwise FALSE."
	::= { mibe3AtmNetworkProfile-LineConfig-TrafficShapersEntry 5 }

    e3AtmNetworkProfile-LineConfig-TrafficShapers-BitRate	OBJECT-TYPE
	SYNTAX	INTEGER
	ACCESS	read-write
	STATUS	mandatory
	DESCRIPTION	"What is the sustained rate in Kilobits per second that can be transmitted by the VC(s) when using this shaper. Limited by the framer mode and the interface type."
	::= { mibe3AtmNetworkProfile-LineConfig-TrafficShapersEntry 6 }

    e3AtmNetworkProfile-LineConfig-TrafficShapers-PeakRate	OBJECT-TYPE
	SYNTAX	INTEGER
	ACCESS	read-write
	STATUS	mandatory
	DESCRIPTION	"What is the peak rate in Kilobits per second that can be transmitted by the VC(s) when using this shaper. Limited by the framer mode and the interface type."
	::= { mibe3AtmNetworkProfile-LineConfig-TrafficShapersEntry 7 }

    e3AtmNetworkProfile-LineConfig-TrafficShapers-MaxBurstSize	OBJECT-TYPE
	SYNTAX	INTEGER
	ACCESS	read-write
	STATUS	mandatory
	DESCRIPTION	"What is the maximum burst size in cell that can be transmitted during the peak rate by the VC(s) when using this shaper."
	::= { mibe3AtmNetworkProfile-LineConfig-TrafficShapersEntry 8 }

    e3AtmNetworkProfile-LineConfig-TrafficShapers-Aggregate	OBJECT-TYPE
	SYNTAX	INTEGER {
		    no (1),
		    yes (2)
		}
	ACCESS	read-write
	STATUS	mandatory
	DESCRIPTION	"If FALSE each individual VC gets the bit rate that is assigned to this shaper. If TRUE the VCs share the bit rate that is assigned to this shaper equally."
	::= { mibe3AtmNetworkProfile-LineConfig-TrafficShapersEntry 9 }

    e3AtmNetworkProfile-LineConfig-TrafficShapers-Priority	OBJECT-TYPE
	SYNTAX	INTEGER
	ACCESS	read-write
	STATUS	mandatory
	DESCRIPTION	"A number that represent the prioriy of the shaper in respect to other shapers. 0 is the highest priority and 15 is the lowest."
	::= { mibe3AtmNetworkProfile-LineConfig-TrafficShapersEntry 10 }


	-- The mibe3AtmNetworkProfile__line_config__incomingVCCs table
	--
	-- This table contains parameters for the mibe3AtmNetworkProfile__line_config__incomingVCCs profile
	--

    mibe3AtmNetworkProfile-LineConfig-IncomingVCCsTable	OBJECT-TYPE
	SYNTAX		SEQUENCE OF Mibe3AtmNetworkProfile-LineConfig-IncomingVCCsEntry
	ACCESS		not-accessible
	STATUS		mandatory
	DESCRIPTION	"A list of mibe3AtmNetworkProfile__line_config__incomingVCCs profile entries."
	::= { mibe3AtmNetworkProfile 3 }

    mibe3AtmNetworkProfile-LineConfig-IncomingVCCsEntry	OBJECT-TYPE
	SYNTAX		Mibe3AtmNetworkProfile-LineConfig-IncomingVCCsEntry
	ACCESS		not-accessible
	STATUS		mandatory
	DESCRIPTION	"A mibe3AtmNetworkProfile__line_config__incomingVCCs entry containing objects that
			 maps to the parameters of mibe3AtmNetworkProfile__line_config__incomingVCCs profile."
	INDEX		{ e3AtmNetworkProfile-LineConfig-IncomingVCCs-Shelf-o, e3AtmNetworkProfile-LineConfig-IncomingVCCs-Slot-o, e3AtmNetworkProfile-LineConfig-IncomingVCCs-Item-o, e3AtmNetworkProfile-LineConfig-IncomingVCCs-Index-o }
	::= { mibe3AtmNetworkProfile-LineConfig-IncomingVCCsTable 1 }

    Mibe3AtmNetworkProfile-LineConfig-IncomingVCCsEntry ::=
	SEQUENCE {
	    e3AtmNetworkProfile-LineConfig-IncomingVCCs-Shelf-o
		INTEGER,
	    e3AtmNetworkProfile-LineConfig-IncomingVCCs-Slot-o
		INTEGER,
	    e3AtmNetworkProfile-LineConfig-IncomingVCCs-Item-o
		INTEGER,
	    e3AtmNetworkProfile-LineConfig-IncomingVCCs-Index-o
		INTEGER,
	    e3AtmNetworkProfile-LineConfig-IncomingVCCs-Enabled
		INTEGER,
	    e3AtmNetworkProfile-LineConfig-IncomingVCCs-Vpi
		INTEGER,
	    e3AtmNetworkProfile-LineConfig-IncomingVCCs-StartVci
		INTEGER,
	    e3AtmNetworkProfile-LineConfig-IncomingVCCs-EndVci
		INTEGER
	}

    e3AtmNetworkProfile-LineConfig-IncomingVCCs-Shelf-o	OBJECT-TYPE
	SYNTAX	INTEGER
	ACCESS	read-only
	STATUS	mandatory
	DESCRIPTION	""
	::= { mibe3AtmNetworkProfile-LineConfig-IncomingVCCsEntry 1 }

    e3AtmNetworkProfile-LineConfig-IncomingVCCs-Slot-o	OBJECT-TYPE
	SYNTAX	INTEGER
	ACCESS	read-only
	STATUS	mandatory
	DESCRIPTION	""
	::= { mibe3AtmNetworkProfile-LineConfig-IncomingVCCsEntry 2 }

    e3AtmNetworkProfile-LineConfig-IncomingVCCs-Item-o	OBJECT-TYPE
	SYNTAX	INTEGER
	ACCESS	read-only
	STATUS	mandatory
	DESCRIPTION	""
	::= { mibe3AtmNetworkProfile-LineConfig-IncomingVCCsEntry 3 }

    e3AtmNetworkProfile-LineConfig-IncomingVCCs-Index-o	OBJECT-TYPE
	SYNTAX	INTEGER
	ACCESS	read-only
	STATUS	mandatory
	DESCRIPTION	""
	::= { mibe3AtmNetworkProfile-LineConfig-IncomingVCCsEntry 4 }

    e3AtmNetworkProfile-LineConfig-IncomingVCCs-Enabled	OBJECT-TYPE
	SYNTAX	INTEGER {
		    no (1),
		    yes (2)
		}
	ACCESS	read-write
	STATUS	mandatory
	DESCRIPTION	"TRUE if the item is enabled, otherwise FALSE."
	::= { mibe3AtmNetworkProfile-LineConfig-IncomingVCCsEntry 5 }

    e3AtmNetworkProfile-LineConfig-IncomingVCCs-Vpi	OBJECT-TYPE
	SYNTAX	INTEGER
	ACCESS	read-write
	STATUS	mandatory
	DESCRIPTION	"A number that identifies the Virtual Path Identifier of this item."
	::= { mibe3AtmNetworkProfile-LineConfig-IncomingVCCsEntry 6 }

    e3AtmNetworkProfile-LineConfig-IncomingVCCs-StartVci	OBJECT-TYPE
	SYNTAX	INTEGER
	ACCESS	read-write
	STATUS	mandatory
	DESCRIPTION	"A number that identifies the starting Virtual Channel Identifier of this item."
	::= { mibe3AtmNetworkProfile-LineConfig-IncomingVCCsEntry 7 }

    e3AtmNetworkProfile-LineConfig-IncomingVCCs-EndVci	OBJECT-TYPE
	SYNTAX	INTEGER
	ACCESS	read-write
	STATUS	mandatory
	DESCRIPTION	"A number that identifies the ending Virtual Channel Identifier of this item."
	::= { mibe3AtmNetworkProfile-LineConfig-IncomingVCCsEntry 8 }


	-- The mibe3AtmNetworkProfile__line_config__vc_switching_vpi table
	--
	-- This table contains parameters for the mibe3AtmNetworkProfile__line_config__vc_switching_vpi profile
	--

    mibe3AtmNetworkProfile-LineConfig-VcSwitchingVpiTable	OBJECT-TYPE
	SYNTAX		SEQUENCE OF Mibe3AtmNetworkProfile-LineConfig-VcSwitchingVpiEntry
	ACCESS		not-accessible
	STATUS		mandatory
	DESCRIPTION	"A list of mibe3AtmNetworkProfile__line_config__vc_switching_vpi profile entries."
	::= { mibe3AtmNetworkProfile 4 }

    mibe3AtmNetworkProfile-LineConfig-VcSwitchingVpiEntry	OBJECT-TYPE
	SYNTAX		Mibe3AtmNetworkProfile-LineConfig-VcSwitchingVpiEntry
	ACCESS		not-accessible
	STATUS		mandatory
	DESCRIPTION	"A mibe3AtmNetworkProfile__line_config__vc_switching_vpi entry containing objects that
			 maps to the parameters of mibe3AtmNetworkProfile__line_config__vc_switching_vpi profile."
	INDEX		{ e3AtmNetworkProfile-LineConfig-VcSwitchingVpi-Shelf-o, e3AtmNetworkProfile-LineConfig-VcSwitchingVpi-Slot-o, e3AtmNetworkProfile-LineConfig-VcSwitchingVpi-Item-o, e3AtmNetworkProfile-LineConfig-VcSwitchingVpi-Index-o }
	::= { mibe3AtmNetworkProfile-LineConfig-VcSwitchingVpiTable 1 }

    Mibe3AtmNetworkProfile-LineConfig-VcSwitchingVpiEntry ::=
	SEQUENCE {
	    e3AtmNetworkProfile-LineConfig-VcSwitchingVpi-Shelf-o
		INTEGER,
	    e3AtmNetworkProfile-LineConfig-VcSwitchingVpi-Slot-o
		INTEGER,
	    e3AtmNetworkProfile-LineConfig-VcSwitchingVpi-Item-o
		INTEGER,
	    e3AtmNetworkProfile-LineConfig-VcSwitchingVpi-Index-o
		INTEGER,
	    e3AtmNetworkProfile-LineConfig-VcSwitchingVpi
		INTEGER
	}

    e3AtmNetworkProfile-LineConfig-VcSwitchingVpi-Shelf-o	OBJECT-TYPE
	SYNTAX	INTEGER
	ACCESS	read-only
	STATUS	mandatory
	DESCRIPTION	""
	::= { mibe3AtmNetworkProfile-LineConfig-VcSwitchingVpiEntry 1 }

    e3AtmNetworkProfile-LineConfig-VcSwitchingVpi-Slot-o	OBJECT-TYPE
	SYNTAX	INTEGER
	ACCESS	read-only
	STATUS	mandatory
	DESCRIPTION	""
	::= { mibe3AtmNetworkProfile-LineConfig-VcSwitchingVpiEntry 2 }

    e3AtmNetworkProfile-LineConfig-VcSwitchingVpi-Item-o	OBJECT-TYPE
	SYNTAX	INTEGER
	ACCESS	read-only
	STATUS	mandatory
	DESCRIPTION	""
	::= { mibe3AtmNetworkProfile-LineConfig-VcSwitchingVpiEntry 3 }

    e3AtmNetworkProfile-LineConfig-VcSwitchingVpi-Index-o	OBJECT-TYPE
	SYNTAX	INTEGER
	ACCESS	read-only
	STATUS	mandatory
	DESCRIPTION	""
	::= { mibe3AtmNetworkProfile-LineConfig-VcSwitchingVpiEntry 4 }

    e3AtmNetworkProfile-LineConfig-VcSwitchingVpi	OBJECT-TYPE
	SYNTAX	INTEGER
	ACCESS	read-write
	STATUS	mandatory
	DESCRIPTION	"VPI(s) to be used for the VC switching (VCC). It should always contain VPI 0 for VC switching. All VC switching VPI have similar valid VCI range which is determined by 'vpi-vci-range' attribute. Rest of the VPIs will be used for the VP switching. The user needs to understand that adding a VPI in a list of VC switching VPI will allocate more VCCs for this port. The user needs to make sure that VCCs for the other ports have been reduced to accommodate increase in VCC for this port because system can support only 32k VCCs on all trunk ports combined. If vci-range is 4k and VPI 0 is the only VPI doing VC switching for this port than this port occupies 4k VCCs. If user adds VPI 1 to the list of VPIs to do VCC then total 8k VCCs are occupied for this port. System will reject the configuration if user tries to use more than 32k VCCs for all trunk ports combined. ANY CHANGES IN A LIST OF VPIs WILL BE EFFECTIVE IMMEDIATLY. IN ORDER TO DO THAT ALL CONNECTIONS WITHIN THIS SYSTEM WILL BE DROPPED AND REESTABLISHED."
	::= { mibe3AtmNetworkProfile-LineConfig-VcSwitchingVpiEntry 5 }

END
