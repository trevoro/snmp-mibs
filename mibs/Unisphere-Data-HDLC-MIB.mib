-- *****************************************************************************
-- Unisphere-Data-HDLC-MIB
--
-- Unisphere Networks Inc. Enterprise MIB
-- HDLC MIB
--
-- Copyright (c) 1998, 1999 Redstone Communications, Incorporated.
-- Copyright (c) 1999, 2002 Unisphere Networks, Incorporated.
-- All Rights Reserved.
-- *****************************************************************************

Unisphere-Data-HDLC-MIB DEFINITIONS ::= BEGIN

IMPORTS
    MODULE-IDENTITY, OBJECT-TYPE, Integer32
        FROM SNMPv2-SMI
    RowStatus
        FROM SNMPv2-TC
    MODULE-COMPLIANCE, OBJECT-GROUP
        FROM SNMPv2-CONF
    InterfaceIndex, InterfaceIndexOrZero
        FROM IF-MIB
    usDataMibs
        FROM Unisphere-Data-MIBs
    UsdNextIfIndex
        FROM Unisphere-Data-TC;

usdHdlcMIB  MODULE-IDENTITY
    LAST-UPDATED "200111281343Z"  -- 28-Nov-01 08:43 AM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The HDLC MIB for the Unisphere Networks enterprise.  This MIB provides
        a means for configuring HDLC interfaces on top of various types of
        interfaces, such as packet over SONET (POS) and high speed serial
        interfaces (HSSI).  Management objects are provided to query for an
        available interface index, and to create/delete interfaces of this type.
        Creating/deleting this interface type using this MIB has the side effect
        of creating/deleting corresponding entries in the IF-MIB.ifTable, the
        IF-MIB.ifXTable, and the Unisphere-Data-IF-MIB.usdIfTable."
    -- Revision History
    REVISION    "200111281343Z"  -- 28-Nov-01 08:43 AM EST  - RX 3.2
    DESCRIPTION
        "Removed DEFVALs for usdHdlcIfClockMode usdHdlcIfClockRate and
        usdHdlcIfForceDteAck.  Defaults are chosen according to the type of the
        underlying interface."
    REVISION    "200103221430Z"  -- 22-Mar-01 09:30 AM EST  - RX 3.1
    DESCRIPTION
        "Added the following objects:
             usdHdlcIfClockMode
             usdHdlcIfClockRate
             usdHdlcIfForceDteAck"
    REVISION    "200001260000Z"  -- 26-Jan-00               - RX 1.3
    DESCRIPTION
        "Changed the valid integer range for usdHdlcIfMru and usdHdlcIfMtu."
    REVISION      "9907280000Z"  -- 28-Jul-99               - RX 1.1
    DESCRIPTION
        "o Removed DEFVALs for usdHdlcIfMru and usdHdlcIfMtu.  Defaults are
           chosen according to the type of the underlying interface.
         o Added usdHdlcIfDataPolarity."
    REVISION      "9811130000Z"  -- 13-Nov-98               - RX 1.0
    DESCRIPTION
        "Initial version of this MIB module."
    ::= { usDataMibs 9 }

-- +++++++++++++++++++++++++++++++++++++++++++++++++++++++++++++++++++++++++++++
-- Textual conventions
-- +++++++++++++++++++++++++++++++++++++++++++++++++++++++++++++++++++++++++++++

-- No textual conventions are defined in this MIB module.

-- +++++++++++++++++++++++++++++++++++++++++++++++++++++++++++++++++++++++++++++
-- Managed objects
-- +++++++++++++++++++++++++++++++++++++++++++++++++++++++++++++++++++++++++++++

usdHdlcObjects     OBJECT IDENTIFIER ::= { usdHdlcMIB 1 }

-- /////////////////////////////////////////////////////////////////////////////
--
-- HDLC Interfaces
--
-- /////////////////////////////////////////////////////////////////////////////

--
-- IfIndex selection for creating new HDLC interfaces.
--

usdHdlcNextIfIndex OBJECT-TYPE
    SYNTAX      UsdNextIfIndex
    MAX-ACCESS  read-only
    STATUS      current
    DESCRIPTION
        "Coordinate ifIndex value allocation for entries in usdHdlcIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdHdlcObjects 1 }

--
-- The HDLC Interface Table
--

usdHdlcIfTable OBJECT-TYPE
    SYNTAX      SEQUENCE OF UsdHdlcIfEntry
    MAX-ACCESS  not-accessible
    STATUS      current
    DESCRIPTION
        "This table contains entries for HDLC interfaces present in the system."
    ::= { usdHdlcObjects 2 }

usdHdlcIfEntry OBJECT-TYPE
    SYNTAX      UsdHdlcIfEntry
    MAX-ACCESS  not-accessible
    STATUS      current
    DESCRIPTION
        "Each entry describes the characteristics of an HDLC interface.
        Creating/deleting entries in this table causes corresponding entries for
        be created/deleted in ifTable/ifXTable/usdIfTable."
    INDEX     { usdHdlcIfIndex }
    ::= { usdHdlcIfTable 1 }

UsdHdlcIfEntry ::= SEQUENCE {
    usdHdlcIfIndex          InterfaceIndex,
    usdHdlcIfRowStatus      RowStatus,
    usdHdlcIfLowerIfIndex   InterfaceIndexOrZero,
    usdHdlcIfMtu            Integer32,
    usdHdlcIfMru            Integer32,
    usdHdlcIfCrcSize        INTEGER,
    usdHdlcIfDataPolarity   INTEGER,
    usdHdlcIfClockMode      INTEGER,
    usdHdlcIfClockRate      INTEGER,
    usdHdlcIfForceDteAck    INTEGER
}

usdHdlcIfIndex OBJECT-TYPE
    SYNTAX      InterfaceIndex
    MAX-ACCESS  not-accessible
    STATUS      current
    DESCRIPTION
        "The ifIndex of the HDLC interface.  When creating entries in this
        table, suitable values for this object are determined by reading
        usdHdlcNextIfIndex."
    ::= { usdHdlcIfEntry 1 }

usdHdlcIfRowStatus OBJECT-TYPE
    SYNTAX      RowStatus
    MAX-ACCESS  read-create
    STATUS      current
    DESCRIPTION
        "Controls creation/deletion of entries in this table according to the
        RowStatus textual convention, constrained to support the following
        values only:

            createAndGo
            destroy

        To create an entry in this table, the following entry objects MUST be
        explicitly configured:

            usdHdlcIfRowStatus
            usdHdlcIfLowerIfIndex

        In addition, when creating an entry the following conditions must hold:

            A value for usdHdlcIfIndex must have been determined previously, by
            reading usdHdlcNextIfIndex.

            The interface identified by usdHdlcIfLowerIfIndex must exist.

        A corresponding entry in ifTable/ifXTable/usdIfTable is created/destroyed
        as a result of creating/destroying an entry in this table."
    ::= { usdHdlcIfEntry 2 }

usdHdlcIfLowerIfIndex OBJECT-TYPE
    SYNTAX      InterfaceIndexOrZero
    MAX-ACCESS  read-create
    STATUS      current
    DESCRIPTION
        "The ifIndex of an interface over which this HDLC interface is to be
        layered.  A value of zero indicates no layering.  An implementation may
        choose to require that a nonzero value be configured at entry creation."
    ::= { usdHdlcIfEntry 3 }

usdHdlcIfMtu OBJECT-TYPE
    SYNTAX      Integer32 (0..32763)
    UNITS       "octets"
    MAX-ACCESS  read-create
    STATUS      current
    DESCRIPTION
        "The Maximum Transmission Unit (MTU) this interface is permitted to
        transmit.

        At creation, if a value for this object is not specified, a default will
        be chosen that is suitable for the type of lower interface on which this
        interface is stacked.

        This setting plus 2 bytes for HDLC address/control plus the length
        in bytes of the HDLC CRC cannot exceed 65535. The maximum value for
        this object reflects the largest possible value when no CRC is used;
        technology constraints of a particular implementation may further
        limit the upper bound value."
    ::= { usdHdlcIfEntry 4 }

usdHdlcIfMru OBJECT-TYPE
    SYNTAX      Integer32 (0..32763)
    UNITS       "octets"
    MAX-ACCESS  read-create
    STATUS      current
    DESCRIPTION
        "The Maximum Receive Unit (MRU) this interface is permitted to receive.

        At creation, if a value for this object is not specified, a default will
        be chosen that is suitable for the type of lower interface on which this
        interface is stacked.

        This setting plus 2 bytes for HDLC address/control plus the length in
        bytes of the HDLC CRC cannot exceed 65535.  The maximum value for this
        object reflects the largest possible value when no CRC is used;
        technology constraints of a particular implementation may further limit
        the upper bound value."
    ::= { usdHdlcIfEntry 5 }

usdHdlcIfCrcSize OBJECT-TYPE
    SYNTAX      INTEGER {
                    none(0),
                    crc16(1),
                    crc32(2)
                }
    MAX-ACCESS  read-create
    STATUS      current
    DESCRIPTION
        "Selects the CRC size: none, 16 bits, or 32 bits."
    DEFVAL    { crc16 }
    ::= { usdHdlcIfEntry 6 }

usdHdlcIfDataPolarity OBJECT-TYPE
    SYNTAX      INTEGER {
                    normal(0),
                    inverted(1)
                }
    MAX-ACCESS  read-create
    STATUS      current
    DESCRIPTION
        "Polarity of data transmitted on this HDLC interface.  Inverted data is
        used for certain line coding configurations to ensure sufficient one's
        density for timing recovery by the remote end."
    DEFVAL  { normal }
    ::= { usdHdlcIfEntry 7 }

usdHdlcIfClockMode OBJECT-TYPE
    SYNTAX      INTEGER {
                    hdlcClockUnsupported(0),
                    hdlcClockInternal(1),
                    hdlcClockLine(2)
                }
    MAX-ACCESS  read-create
    STATUS      current
    DESCRIPTION
        "The clock mode setting for this HDLC interface.  This object is only
        applicable to HDLC interfaces directly over a high speed serial
        interface (HSSI).

        At creation, if a value for this object is not specified, a default will
        be chosen that is suitable for the type of lower interface on which this
        interface is stacked.  If the lower interface is not HSSI, then the
        default value will be hdlcClockUnsupported(0); if the lower interface is
        HSSI then the default value will be hdlcClockLine(2)."
    ::= { usdHdlcIfEntry 8 }

usdHdlcIfClockRate OBJECT-TYPE
    SYNTAX      INTEGER {
                    hdlcClockRateUnsupported(0),
                    hdlcClockRate34-368Mhz(1),
                    hdlcClockRate44-736Mhz(2)
                }
    MAX-ACCESS  read-create
    STATUS      current
    DESCRIPTION
        "The clock rate setting for this HDLC interface.  This object is only
        applicable to HDLC interfaces directly over a high speed serial
        interface (HSSI).

        At creation, if a value for this object is not specified, a default will
        be chosen that is suitable for the type of lower interface on which this
        interface is stacked.  If the lower interface is not HSSI, then the
        default value will be hdlcClockRateUnsupported(0); if the lower
        interface is HSSI then the default value will be
        hdlcClockRate44-736Mhz(2)."
    ::= { usdHdlcIfEntry 9 }

usdHdlcIfForceDteAck OBJECT-TYPE
    SYNTAX      INTEGER {
                    forceDteAckUnsupported(0),
                    forceDteAckNormal(1),
                    forceDteAckForced(2)
                }
    MAX-ACCESS  read-create
    STATUS      current
    DESCRIPTION
        "The force DTE acknowledge setting.  This object is only applicable to
        HDLC interfaces directly over a high speed serial interface (HSSI).
        This is set to force Cisco compatibility mode, and is only valid when
        the lower interface is configured for internal (DTE) clocking.

        At creation, if a value for this object is not specified, a default will
        be chosen that is suitable for the type of lower interface on which this
        interface is stacked.  If the lower interface is not HSSI, then the
        default value will be forceDteAckUnsupported(0); if the lower
        interface is HSSI then the default value will be
        forceDteAckNormal(1)."
    ::= { usdHdlcIfEntry 10 }


-- +++++++++++++++++++++++++++++++++++++++++++++++++++++++++++++++++++++++++++++
-- Notification control objects
-- +++++++++++++++++++++++++++++++++++++++++++++++++++++++++++++++++++++++++++++

-- No notifications are defined in this MIB.  A placeholder OID is provided.

-- usdHdlcTrapControl OBJECT IDENTIFIER ::= { usdHdlcMIB 2 }

-- +++++++++++++++++++++++++++++++++++++++++++++++++++++++++++++++++++++++++++++
-- Notifications
-- +++++++++++++++++++++++++++++++++++++++++++++++++++++++++++++++++++++++++++++

-- No notifications are defined in this MIB.  A placeholder OID is provided.

-- The following two OBJECT IDENTIFIERS are used to define SNMPv2 notifications
-- that are easily translated into SNMPv1 traps.

-- usdHdlcTraps            OBJECT IDENTIFIER ::= { usdHdlcMIB 3 }
-- usdHdlcTrapPrefix       OBJECT IDENTIFIER ::= { usdHdlcTraps 0 }


-- +++++++++++++++++++++++++++++++++++++++++++++++++++++++++++++++++++++++++++++
-- Conformance information
-- +++++++++++++++++++++++++++++++++++++++++++++++++++++++++++++++++++++++++++++

usdHdlcConformance OBJECT IDENTIFIER ::= { usdHdlcMIB 4 }
usdHdlcCompliances OBJECT IDENTIFIER ::= { usdHdlcConformance 1 }
usdHdlcGroups      OBJECT IDENTIFIER ::= { usdHdlcConformance 2 }

-- compliance statements

usdHdlcCompliance MODULE-COMPLIANCE
    STATUS  obsolete
    DESCRIPTION
        "Obsolete compliance statement for entities that implement the Unisphere
        HDLC MIB.  This compliance statement became obsolete when
        usdHdlcIfDataPolarity was added."
    MODULE  -- this module
        MANDATORY-GROUPS { usdHdlcGroup }
    ::= { usdHdlcCompliances 1 }                                       -- RX 1.0

usdHdlcCompliance2 MODULE-COMPLIANCE
    STATUS  obsolete
    DESCRIPTION
        "The compliance statement for entities that implement the Unisphere HDLC
        MIB.  This compliance statement became obsolete when usdHdlcIfClockMode,
        usdHdlcIfClockRate, and usdHdlcIfForceDteAck were added."
    MODULE  -- this module
        MANDATORY-GROUPS { usdHdlcGroup2 }
    ::= { usdHdlcCompliances 2 }                                       -- RX 1.1

usdHdlcCompliance3 MODULE-COMPLIANCE
    STATUS  current
    DESCRIPTION
        "The compliance statement for entities that implement the Unisphere HDLC
        MIB."
    MODULE  -- this module
        MANDATORY-GROUPS { usdHdlcGroup3 }
    ::= { usdHdlcCompliances 3 }                                       -- RX 3.1

-- units of conformance

usdHdlcGroup OBJECT-GROUP
    OBJECTS {
        usdHdlcNextIfIndex,

        usdHdlcIfRowStatus,
        usdHdlcIfLowerIfIndex,
        usdHdlcIfMtu,
        usdHdlcIfMru,
        usdHdlcIfCrcSize }
    STATUS  obsolete
    DESCRIPTION
        "Obsolete collection of objects providing management of HDLC interfaces
        in a Unisphere product.  This group became obsolete when
        usdHdlcIfDataPolarity was added."
    ::= { usdHdlcGroups 1 }

usdHdlcGroup2 OBJECT-GROUP
    OBJECTS {
        usdHdlcNextIfIndex,

        usdHdlcIfRowStatus,
        usdHdlcIfLowerIfIndex,
        usdHdlcIfMtu,
        usdHdlcIfMru,
        usdHdlcIfCrcSize,
        usdHdlcIfDataPolarity }
    STATUS  obsolete
    DESCRIPTION
        "Obsolete collection of objects providing management of HDLC interfaces
        in a Unisphere product.  This group became obsolete when
        usdHdlcIfClockMode, usdHdlcIfClockRate, and usdHdlcIfForceDteAck were
        added."
    ::= { usdHdlcGroups 2 }

usdHdlcGroup3 OBJECT-GROUP
    OBJECTS {
        usdHdlcNextIfIndex,

        usdHdlcIfRowStatus,
        usdHdlcIfLowerIfIndex,
        usdHdlcIfMtu,
        usdHdlcIfMru,
        usdHdlcIfCrcSize,
        usdHdlcIfDataPolarity,
        usdHdlcIfClockMode,
        usdHdlcIfClockRate,
        usdHdlcIfForceDteAck }
    STATUS  current
    DESCRIPTION
        "A collection of objects providing management of HDLC interfaces
        in a Unisphere product."
    ::= { usdHdlcGroups 3 }

END
