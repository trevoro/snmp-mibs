--
-- 
--	INTEL CORPORATION PROPRIETARY INFORMATION
--
--	This software is supplied under the terms of a license agreement or
--	comment "nondisclosure agreement with Intel Corporation and may not be copied
--	or disclosed except in accordance with the terms of that agreement.
--
--	Copyright (c) 1999 Intel Corporation. All Rights Reserved.
--
--
--
--

	MIB-INTEL-RIP DEFINITIONS ::= BEGIN

	IMPORTS
		IpAddress
			FROM RFC1155-SMI
		OBJECT-TYPE
			FROM RFC-1212

		mib2ext
			FROM INTEL-GEN-MIB;


	rip OBJECT IDENTIFIER ::= { mib2ext 39 }


	--
	-- The IP RIP routing table 
	--

	ripIpRouteTable OBJECT-TYPE
		SYNTAX  SEQUENCE OF RipIpRouteEntry
		ACCESS  not-accessible
		STATUS  optional
		DESCRIPTION
			"This entity's RIP Routing table."
		::= { rip 1 }

	ripIpRouteEntry OBJECT-TYPE
		SYNTAX  RipIpRouteEntry
		ACCESS  not-accessible
		STATUS  optional
		DESCRIPTION
			"A route to a particular destination."
		INDEX   { 
			  ripIpRouteChassis, 
			  ripIpRouteModule, 
			  ripIpRouteInst, 
			  ripIpRouteDest, 
			  ripIpRouteMask,
			  ripIpIfIndex,
			  ripIpRouteNextHop 
			}
		::= { ripIpRouteTable 1 }

	RipIpRouteEntry ::=
		SEQUENCE {
		ripIpRouteChassis
			INTEGER,
		ripIpRouteModule
			INTEGER,
		ripIpRouteInst
			INTEGER,
		ripIpRouteDest
			IpAddress,
		ripIpRouteMask
			IpAddress,
		ripIpIfIndex
			INTEGER,
		ripIpRouteNextHop
			IpAddress,
		ripIpRoutePref
			INTEGER,
		ripIpRouteMetric
			INTEGER,
		ripIpRouteState
			INTEGER,
		ripIpRouteAge
			INTEGER,
		ripIpRouteProtoVersion
			INTEGER,
		ripIpRouteProtoTrigger
			INTEGER
		}

	ripIpRouteChassis OBJECT-TYPE
		SYNTAX  INTEGER
		ACCESS  read-only
		STATUS  optional
		DESCRIPTION
			"Chassis number in stack that contains the module."
		::= { ripIpRouteEntry 1 }

	ripIpRouteModule OBJECT-TYPE
		SYNTAX  INTEGER
		ACCESS  read-only
		STATUS  optional
		DESCRIPTION
			"Module number in the chassis."
		::= { ripIpRouteEntry 2 }

	ripIpRouteInst OBJECT-TYPE
		SYNTAX  INTEGER
		ACCESS  read-only
		STATUS  optional
		DESCRIPTION
			"Routing table instance number."
		::= { ripIpRouteEntry 3 }

	ripIpRouteDest OBJECT-TYPE
		SYNTAX  IpAddress
		ACCESS  read-only
		STATUS  optional
		DESCRIPTION
			"The destination IP address of this route."
		::= { ripIpRouteEntry 4 }

	ripIpRouteMask OBJECT-TYPE
		SYNTAX  IpAddress
		ACCESS  read-only
		STATUS  optional
		DESCRIPTION
			"Indicate the mask to be logical-ANDed with the
			destination address before being compared to the
			value in the ripIpRouteDest field."
		::= { ripIpRouteEntry 5 }

	ripIpIfIndex OBJECT-TYPE
		SYNTAX  INTEGER
		ACCESS  read-only
		STATUS  optional
		DESCRIPTION
			"The interface that the frame is forwarded on."
		::= { ripIpRouteEntry 6 }

	ripIpRouteNextHop OBJECT-TYPE
		SYNTAX  IpAddress
		ACCESS  read-only
		STATUS  optional
		DESCRIPTION
			"The IP address of the next hop of this route."
		::= { ripIpRouteEntry 7 }

	ripIpRoutePref OBJECT-TYPE
		SYNTAX  INTEGER
		ACCESS  read-only
		STATUS  optional
		DESCRIPTION
			"The preference value for this route."
		::= { ripIpRouteEntry 8 }

	ripIpRouteMetric OBJECT-TYPE
		SYNTAX  INTEGER
		ACCESS  read-only
		STATUS  optional
		DESCRIPTION
			"The RIP routing metric for this route."
		::= { ripIpRouteEntry 9 }

        ripIpRouteState OBJECT-TYPE
		SYNTAX  INTEGER {
			active(1),
			inactive(2)
		}
		ACCESS  read-write
		STATUS  optional
		DESCRIPTION
			"The current state of the route."
		::= { ripIpRouteEntry 10 }

	ripIpRouteAge OBJECT-TYPE
		SYNTAX  INTEGER
		ACCESS  read-only
		STATUS  optional
		DESCRIPTION
			"The number of seconds since this route was last 
			updated or otherwise detemined to be correct."
		::= { ripIpRouteEntry 11 }

	ripIpRouteProtoVersion OBJECT-TYPE
		SYNTAX  INTEGER {
			rip1(1),
			rip2(2)
		}
		ACCESS  read-only
		STATUS  optional
		DESCRIPTION
			"The RIP protocol version."
		::= { ripIpRouteEntry 12 }

	ripIpRouteProtoTrigger OBJECT-TYPE
		SYNTAX  INTEGER {
			on(1),
			off(2)
		}
		ACCESS  read-only
		STATUS  optional
		DESCRIPTION
			"The RIP protocol trigger state."
		::= { ripIpRouteEntry 13 }

	END
