LEFTHAND-NETWORKS-NUS-COMMON-STATUS-MIB DEFINITIONS ::= BEGIN

-- IMPORTS: Include definitions from other mibs here, which is always
-- the first item in a MIB file.
IMPORTS
	MODULE-IDENTITY, OBJECT-TYPE               FROM SNMPv2-SMI
	OBJECT-TYPE											FROM RFC-1212
	lhnModules                                 FROM LEFTHAND-NETWORKS-GLOBAL-REG 
	lhnNusCommonStatus                         FROM LEFTHAND-NETWORKS-NUS-COMMON-MIB;

--
-- A brief description and update information about this mib.
--
lhnNusCommonStatusModule MODULE-IDENTITY
    LAST-UPDATED "0106010000Z"            
    ORGANIZATION "LeftHand Networks, Inc."
    CONTACT-INFO "
                  Author:     Jose Faria
                              LeftHand Networks
                  postal:     6185 Arapahoe Rd.
                              Boulder, CO 80301
                              USA
                  email:      jfaria@lefthandnetworks.com
                  phone:      +1 303 449-4100
                 "
    DESCRIPTION  "Status items for NUS Devices"
    ::= { lhnModules 99 }

-- *********************************************************************************
--
-- Status Objects
--
-- *********************************************************************************

status OBJECT-TYPE
    SYNTAX           INTEGER { online(1), offline(2) }
    MAX-ACCESS       read-only
    STATUS           current
    DESCRIPTION      "LeftHand Networks MIB status"
    ::= { lhnNusCommonStatus 1 }

statusMessage OBJECT-TYPE
    SYNTAX           OCTET STRING
    MAX-ACCESS       read-only
    STATUS           current
    DESCRIPTION      "LeftHand Networks MIB status message"
    ::= { lhnNusCommonStatus 2 }
 
END
