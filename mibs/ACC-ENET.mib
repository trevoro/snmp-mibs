ACC-ENET DEFINITIONS ::= BEGIN

    IMPORTS
	 OBJECT-TYPE, Counter FROM RFC1155-SMI
                      accTrapLogSeqNum FROM ACC-SYSTEM
	 accBRG, DisplayString FROM ACC-MIB;
-- Ethernet Group
     accEnet   OBJECT IDENTIFIER  ::= { accBRG 8 }
	accEnetNum	OBJECT-TYPE   
			SYNTAX	INTEGER
			ACCESS	read-only
			STATUS	mandatory
			DESCRIPTION
               		 " Number of Ethernet ports on this unit."
			::= { accEnet 1 }
	accEnetParmTable	OBJECT-TYPE
			SYNTAX SEQUENCE OF AccEnetParmEntry
			ACCESS not-accessible
			STATUS mandatory
			 DESCRIPTION
                          " A table of parameters of Ethernet ports
                            The number of table entries is accEnetNum."
			 ::= { accEnet 2 }
	  accEnetParmEntry  OBJECT-TYPE
			SYNTAX AccEnetParmEntry
			ACCESS not-accessible
			STATUS mandatory
			DESCRIPTION
                           " Parameters relative to a specific Ethernet port."
                        INDEX { accEnetPortNo }
			::= { accEnetParmTable 1 }
             AccEnetParmEntry ::= SEQUENCE {
			accEnetPortNo      INTEGER,
			accEnetMACaddr     OCTET STRING,
			accEthSpeed	   INTEGER,
			accEthDuplex	   INTEGER
			}
	    accEnetPortNo  OBJECT-TYPE   
			SYNTAX	INTEGER
			ACCESS	read-only
			STATUS	mandatory
			DESCRIPTION
                         " Number of this ethernet port."
			::= { accEnetParmEntry 1 }
	    accEnetMACaddr  OBJECT-TYPE   
			SYNTAX	OCTET STRING -- (SIZE(6))
			ACCESS	read-write
			STATUS	mandatory
			DESCRIPTION
                         "MAC address to be used for this ethernet port."
			::= { accEnetParmEntry 2 }
	     accEthSpeed OBJECT-TYPE
			SYNTAX	INTEGER (1..3)
			ACCESS	read-write
			STATUS	mandatory
			DESCRIPTION
			"The speed options are: 
				auto(1)
				10(2)
				100(3) "
			::= { accEnetParmEntry 3 }
	     accEthDuplex OBJECT-TYPE
			SYNTAX	INTEGER (1..3)
			ACCESS	read-write
			STATUS	mandatory
			DESCRIPTION
			" The duplex options are:
				auto(1)
				half(2)
				full(3) "
			::= { accEnetParmEntry 4 }
	accEnetStatTable  OBJECT-TYPE
			SYNTAX SEQUENCE OF AccEnetStatEntry
			ACCESS not-accessible
			STATUS mandatory
			DESCRIPTION
                         " A list of per-port statistics for ports
                           configured as Ethernet LANs."
			::= { accEnet 3 }
	  accEnetStatEntry  OBJECT-TYPE
			SYNTAX AccEnetStatEntry
			ACCESS not-accessible
			STATUS mandatory
			DESCRIPTION
                         " Statistics for specific ethernet ports."
                        INDEX { accEnetIndex }
			::= { accEnetStatTable 1 }
		AccEnetStatEntry ::= SEQUENCE {
	    		accEnetIndex			INTEGER,
	    		accEnetStatCRCErrs		Counter,
	    		accEnetStatAlignErrs 		Counter,
	    		accEnetStatOutColls		Counter,
	    		accEnetStatJabberConds 		Counter,
	    		accEnetStatCarrierLosts 	Counter,
	    		accEnetStatHeartbeatErrs 	Counter,
	    		accEnetStatGiants 		Counter,
	    		accEnetStatOneRetrys 		Counter,
	    		accEnetStatMultRetrys 		Counter,
	    		accEnetStatLateColls 		Counter,
	    		accEnetChipCrashes 		Counter
			}
	    accEnetIndex	OBJECT-TYPE   
			SYNTAX	INTEGER
			ACCESS	read-only
			STATUS	mandatory
			DESCRIPTION
                          " Port number of this entry"
			::= { accEnetStatEntry 1 }
	    accEnetStatCRCErrs	OBJECT-TYPE 
			SYNTAX	Counter
			ACCESS	read-only
			STATUS	mandatory
			DESCRIPTION
                          " Number of CRC (Checksum) errors detected on this
                            port."
			::= { accEnetStatEntry 2 }
	    accEnetStatAlignErrs  OBJECT-TYPE 
			SYNTAX	Counter
			ACCESS	read-only
			STATUS	mandatory
			DESCRIPTION
                          " Number of alignment errors detected."
			::= { accEnetStatEntry 3 }
	    accEnetStatOutColls	 OBJECT-TYPE 
			SYNTAX	Counter
			ACCESS	read-only
			STATUS	mandatory
			DESCRIPTION
                          " Number of collisions detected on output."
			::= { accEnetStatEntry 4 }
	    accEnetStatJabberConds  OBJECT-TYPE 
			SYNTAX	Counter
			ACCESS	read-only
			STATUS	mandatory
			DESCRIPTION
                          " Number of jabber conditions detected."
			::= { accEnetStatEntry 5 }
	    accEnetStatCarrierLosts  OBJECT-TYPE 
			SYNTAX	Counter
			ACCESS	read-only
			STATUS	mandatory
			DESCRIPTION
                          " Number of losses of carrier detected."
			::= { accEnetStatEntry 6 }
	    accEnetStatHeartbeatErrs  OBJECT-TYPE 
			SYNTAX	Counter
			ACCESS	read-only
			STATUS	mandatory
			DESCRIPTION
                          " Number of heartbeat errors detected."
			::= { accEnetStatEntry 7 }
	    accEnetStatGiants  OBJECT-TYPE 
			SYNTAX	Counter
			ACCESS	read-only
			STATUS	mandatory
			DESCRIPTION
                          " Number of giant frames detected."
			::= { accEnetStatEntry 8 }
	    accEnetStatOneRetrys  OBJECT-TYPE 
			SYNTAX	Counter
			ACCESS	read-only
			STATUS	mandatory
			DESCRIPTION
                          " Number of times a retry condition was detected."
			::= { accEnetStatEntry 9 }
	    accEnetStatMultRetrys  OBJECT-TYPE 
			SYNTAX	Counter
			ACCESS	read-only
			STATUS	mandatory
			DESCRIPTION
                           " Total number of retries."
			::= { accEnetStatEntry 10 }
	    accEnetStatLateColls  OBJECT-TYPE 
			SYNTAX	Counter
			ACCESS	read-only
			STATUS	mandatory
			DESCRIPTION
                          " Number of late collisions detected."
			::= { accEnetStatEntry 11 }
	    accEnetChipCrashes  OBJECT-TYPE 
			SYNTAX	Counter
			ACCESS	read-only
			STATUS	mandatory
			DESCRIPTION
                          " Number of times aberrant behaviour
			    was detected in Ethernet chip"
			::= { accEnetStatEntry 12 }

END
