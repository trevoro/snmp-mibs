AIISUBNET-MIB DEFINITIONS ::= BEGIN

IMPORTS
		MODULE-IDENTITY, OBJECT-TYPE,
		Integer32, IpAddress, enterprises
				FROM SNMPv2-SMI
		RowStatus
				FROM SNMPv2-TC;

		SubnetIndex ::= INTEGER (1..512)

        aii         OBJECT IDENTIFIER ::= { enterprises 539 }
        aiSLC2      OBJECT IDENTIFIER ::= { aii 16 }

aiiSubnet MODULE-IDENTITY
		LAST-UPDATED "9909141400Z"
		ORGANIZATION "Applied Innovation Inc."
		CONTACT-INFO
                     "        Engineering MIB Administrator

                      Postal: Applied Innovation Inc.
                              5800 Innovation Drive
                              Dublin, Ohio 43016-3271

                              Tel: 614-798-2000
                              Fax: 614-798-1770
                              E-mail: snmp@aiinet.com"
		DESCRIPTION
				"This MIB provides configuration and status information
                 for IP parameters not otherwise configurable by SNMP
				 for the AII XIRB."

		::= { aiSLC2 3 }


aiiSubnetTable			OBJECT-TYPE
		SYNTAX			SEQUENCE OF AiiSubnetEntry
		MAX-ACCESS		not-accessible	
		STATUS			current
		DESCRIPTION
				"This table contains objects which specify the parameters
			     for an IP subnet"
		::= { aiiSubnet 1}

aiiSubnetEntry			OBJECT-TYPE
		SYNTAX			AiiSubnetEntry
		MAX-ACCESS		not-accessible
		STATUS			current
		DESCRIPTION		"Configured parameters for a specific subnet"
		INDEX			{aiiSubnetIndex}
		::= { aiiSubnetTable 1 }

AiiSubnetEntry ::= SEQUENCE {
		aiiSubnetIndex			SubnetIndex,
		aiiSubnetEntryStatus	RowStatus,
		aiiSubnetAddr			IpAddress,
		aiiSubnetIfIndex		Integer32,
		aiiSubnetNetMask		IpAddress,
		aiiSubnetBcastAddr		Integer32,
		aiiSubnetType			Integer32,
		aiiSubnetAdmnStatus		Integer32
		}

	
aiiSubnetIndex			OBJECT-TYPE
		SYNTAX			SubnetIndex
		MAX-ACCESS		read-only
		STATUS			current
		DESCRIPTION		"The index of this entry"
		::= { aiiSubnetEntry 1 }

aiiSubnetEntryStatus	OBJECT-TYPE
		SYNTAX			RowStatus
		MAX-ACCESS		read-write
		STATUS			current
		DESCRIPTION		"The status of this subnet entry, as defined in RFC1443"
		::= { aiiSubnetEntry 2 }


aiiSubnetAddr			OBJECT-TYPE
		SYNTAX			IpAddress
		MAX-ACCESS		read-write
		STATUS			current
		DESCRIPTION
				"The IP address to which this entry's addressing
				 information pertains."
		::= { aiiSubnetEntry 3 }


aiiSubnetIfIndex		OBJECT-TYPE
		SYNTAX			Integer32
		MAX-ACCESS		read-write
        STATUS			current
		DESCRIPTION
				"The index value which identifies the physical
				 interface to which this entry is applicable.  The
                 interface identified by a particular value of this
                 index is the same interface as identified by the
                 same value of ifIndex ."
		::= { aiiSubnetEntry 4 }

aiiSubnetNetMask		OBJECT-TYPE
		SYNTAX			IpAddress
		MAX-ACCESS		read-write
		STATUS			current
		DESCRIPTION
				"The subnet mask associated with the IP address of
                 this entry.  The value of the mask is an IP
                 address with all the network bits set to 1 and all
                 the hosts bits set to 0."
		::= { aiiSubnetEntry 5 }

aiiSubnetBcastAddr		OBJECT-TYPE
		SYNTAX			Integer32
		MAX-ACCESS		read-write
		STATUS			current
		DESCRIPTION
				"The value of the least-significant bit in the IP
                 broadcast address used for sending datagrams on
                 the (logical) interface associated with the IP
                 address of this entry.  For example, when the
                 Internet standard all-ones broadcast address is
                 used, the value will be 1.  This value applies to
                 both the subnet and network broadcasts addresses
                 used by the entity on this (logical) interface."
		::= { aiiSubnetEntry 6 }

aiiSubnetType			OBJECT-TYPE
		SYNTAX			Integer32
		MAX-ACCESS		read-write
		STATUS			current
		DESCRIPTION
				"The type of the interface over which this
				 subnet is configured.  Takes same values 
				 as IfType."
        ::= { aiiSubnetEntry 7 }

aiiSubnetAdmnStatus		OBJECT-TYPE
		SYNTAX			Integer32
		MAX-ACCESS		read-write
		STATUS			current
		DESCRIPTION
				"The operational state to be taken by this
				 interface at the next system restart"
		::= { aiiSubnetEntry 8 }

aiiSubnetTable2		OBJECT-TYPE
		SYNTAX			SEQUENCE OF AiiSubnetEntry2
		MAX-ACCESS		not-accessible	
		STATUS			current
		DESCRIPTION
				"This table contains objects which specify the parameters
			     for multiple IP subnets"
		::= { aiiSubnet 2}

aiiSubnetEntry2		OBJECT-TYPE
		SYNTAX			AiiSubnetEntry2
		MAX-ACCESS		not-accessible
		STATUS			current
		DESCRIPTION		"Configured parameters for a specific subnet"
		INDEX			{aiiSubnetIndex2}
		::= { aiiSubnetTable2 1 }

AiiSubnetEntry2 ::= SEQUENCE {
		aiiSubnetIndex2	   INTEGER,
		aiiIPAddr			   IpAddress,
      aiiSubnetRange       INTEGER,
		aiiSubnetMask		   IpAddress
      }

aiiSubnetIndex2		OBJECT-TYPE
		SYNTAX			INTEGER(1..20)
		MAX-ACCESS		read-only
		STATUS			current
		DESCRIPTION		"The index of this entry"
		::= { aiiSubnetEntry2 1 }

aiiIPAddr			OBJECT-TYPE
		SYNTAX			IpAddress
		MAX-ACCESS		read-write
		STATUS			current
		DESCRIPTION
				"The IP address to which this entry's addressing
				 information pertains."
		::= { aiiSubnetEntry2 2 }

aiiSubnetRange       OBJECT-TYPE
   	SYNTAX		   INTEGER (1..255)
   	MAX-ACCESS	   read-write
   	STATUS		   current
   	DESCRIPTION
      		"IP Address Range."
		::= { aiiSubnetEntry2 3 }

aiiSubnetMask		   OBJECT-TYPE
		SYNTAX			IpAddress
		MAX-ACCESS		read-write
		STATUS			current
		DESCRIPTION
				"The subnet mask associated with the IP address of
                 this entry.  The value of the mask is an IP
                 address with all the network bits set to 1 and all
                 the hosts bits set to 0."
		::= { aiiSubnetEntry2 4 }
		
END
