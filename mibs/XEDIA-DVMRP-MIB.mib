XEDIA-DVMRP-MIB DEFINITIONS ::= BEGIN

IMPORTS
    MODULE-IDENTITY, OBJECT-TYPE
	  FROM SNMPv2-SMI
    xediaMibs
	FROM XEDIA-REG
    ;

xdvmrpMIB MODULE-IDENTITY
    LAST-UPDATED "9905151600Z" -- April 15, 1999
    ORGANIZATION "Xedia Corp."
    CONTACT-INFO
          "support@xedia.com"
    DESCRIPTION
            "The Xedia extention MIB module for management of DVMRP routers."
    ::= { xediaMibs 32 }

xdvmrpMIBObjects OBJECT IDENTIFIER ::= { xdvmrpMIB 1 }

xdvmrp           OBJECT IDENTIFIER ::= { xdvmrpMIBObjects 1 }

xdvmrpInterfaceTable OBJECT-TYPE
    SYNTAX     SEQUENCE OF XdvmrpInterfaceEntry
    MAX-ACCESS not-accessible
    STATUS     current
    DESCRIPTION
            "The (conceptual) table listing the router's multicast-
            capable interfaces."
    ::= { xdvmrp 1 }

xdvmrpInterfaceEntry OBJECT-TYPE
    SYNTAX     XdvmrpInterfaceEntry
    MAX-ACCESS not-accessible
    STATUS     current
    DESCRIPTION
            "An entry (conceptual row) in the dvmrpInterfaceTable.  This
            row augments ipMRouteInterfaceEntry in the IP Multicast MIB,
            where the threshold object resides."

    INDEX      { xdvmrpInterfaceIfIndex }
    ::= { xdvmrpInterfaceTable 1 }

XdvmrpInterfaceEntry ::= SEQUENCE {
    xdvmrpInterfaceIfIndex      INTEGER,
    xdvmrpInterfaceState	INTEGER,
    xdvmrpInterfaceDefaultInformation INTEGER,
    xdvmrpInterfaceUnicastTunnel INTEGER
}

xdvmrpInterfaceIfIndex OBJECT-TYPE
    SYNTAX     INTEGER
    MAX-ACCESS not-accessible
    STATUS     current
    DESCRIPTION
            "The ifIndex value of the interface for which DVMRP is
            enabled."
    ::= { xdvmrpInterfaceEntry 1 }

xdvmrpInterfaceState OBJECT-TYPE
    SYNTAX     INTEGER { up(1), down(2) }
    MAX-ACCESS read-only
    STATUS     current
    DESCRIPTION
            "The current status of this DVMRP interface."
    ::= { xdvmrpInterfaceEntry 2 }

xdvmrpInterfaceDefaultInformation OBJECT-TYPE
    SYNTAX	INTEGER { disabled(1), originate(2), only(3) }
    MAX-ACCESS  read-create
    STATUS	current
    DESCRIPTION
	    "Control the advertisement of default route (0.0.0.0) to the 
	    DVMRP neighbor(s) on the interface.  When the value is set to
	    disabled(1), no default route is advertised.  When set to 
	    originate(2), default route is advertised along the other
	    routes.   When the value is set to only(3), only the default
	    route is advertised through this interface."
    DEFVAL	{ disabled }
    ::= { xdvmrpInterfaceEntry 3 }

xdvmrpInterfaceUnicastTunnel OBJECT-TYPE
    SYNTAX	INTEGER { enabled(1), disabled(2) }
    MAX-ACCESS  read-create
    STATUS	current
    DESCRIPTION
	    "Control the transmission of DVMRP messages to be unicast
	     to the remote end point of the tunnel instead of send through
	     the tunnel.  Enabled this to interoperate with mrouted or 
	     cisco with tunnel configured in dvmrp mode."
    DEFVAL	{ disabled }
    ::= { xdvmrpInterfaceEntry 4 }
END
