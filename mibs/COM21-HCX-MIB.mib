-- 
--  Copyright 1996, Com21 Inc.  All Rights Reserved.
--
 
COM21-HCX-MIB DEFINITIONS ::= BEGIN
        IMPORTS enterprises, MODULE-IDENTITY
	FROM SNMPv2-SMI;


        com21                   OBJECT IDENTIFIER ::=   { enterprises 1141 }

        com21Hcx                OBJECT IDENTIFIER ::=   { com21 2 }
        com21Stu                OBJECT IDENTIFIER ::=   { com21 3 }
        com21Traps              OBJECT IDENTIFIER ::=   { com21 4 }
        com21Nmaps              OBJECT IDENTIFIER ::=   { com21 5 }
	com21Reg		OBJECT IDENTIFIER ::=   { com21 6 }


        FrequencyKhz     ::= INTEGER (0..800000)
	UpstrmFreqKhz    ::= INTEGER (5000..40000)
        Gain             ::= INTEGER (0..255)
	StuGain		 ::= INTEGER (18..58)
        EpochTime        ::= INTEGER (0..2147483647)
        PrimServiceState ::= INTEGER { is(1), oos(2) }
	Offset           ::= INTEGER (0..16383)
        AlarmSeverity    ::= INTEGER { clear(1), warning(2), minor(3),
                                       major(4), critical(5) }
	Com21RowStatus	 ::= INTEGER { active(1), create(2), destroy(3),
				       deactive(4) }

END
