COM21-NMAPS-MIB DEFINITIONS ::= BEGIN
        IMPORTS enterprises, TimeTicks, IpAddress
        FROM RFC1155-SMI
        OBJECT-TYPE
        FROM RFC-1212
        DisplayString
        FROM RFC1213-MIB
        TRAP-TYPE
        FROM RFC-1215
        MacAddress
        FROM BRIDGE-MIB
        com21Nmaps
	FROM COM21-HCX-MIB
	hcxAlmSeverity, hcxEventLogTime
	FROM COM21-HCXALM-MIB;


--
--  This MIB defines those traps sent by NMAPS applications
--

--
--  Var binds for the traps that follow.
--

        com21NmapsVarBinds                OBJECT IDENTIFIER ::= {com21Nmaps 1}

	nmapsAlertMessage OBJECT-TYPE
		SYNTAX DisplayString
		ACCESS read-only
		STATUS mandatory
		DESCRIPTION "
			A string giving the application name, time, error
			number, and a description of the error."
		::= { com21NmapsVarBinds 1 }

	nmapsMacAddress OBJECT-TYPE
		SYNTAX MacAddress
		ACCESS read-only
		STATUS mandatory
		DESCRIPTION "
			A Mac Address var bind."
		::= { com21NmapsVarBinds 2 }

	nmapsDaemonName OBJECT-TYPE
		SYNTAX DisplayString
		ACCESS read-only
		STATUS mandatory
		DESCRIPTION "
			The name of an NMAPS daemon."
		::= { com21NmapsVarBinds 3 }

	nmapsDaemonPid OBJECT-TYPE
		SYNTAX INTEGER (0..32768)
		ACCESS read-only
		STATUS mandatory
		DESCRIPTION "
			The process id of an NMAPS daemon."
		::= { com21NmapsVarBinds 4 }

	nmapsIpAddress OBJECT-TYPE
		SYNTAX IpAddress
		ACCESS read-only
		STATUS mandatory
		DESCRIPTION "
			An Ip Address var bind."
		::= { com21NmapsVarBinds 5 }

	nmapsDaemonForcePoll OBJECT-TYPE
		SYNTAX INTEGER {
				optional(0),
				required(1) }
		ACCESS read-only
		STATUS mandatory
		DESCRIPTION "
			Indicates whether polling is required."
		::= { com21NmapsVarBinds 6 }

--
--  Traps start here
--

        nmapsStuTopologyChange TRAP-TYPE
				ENTERPRISE com21Nmaps
                DESCRIPTION "
			generated whenever it is suspected that a
			STU topology change has occured."
                ::= 1

        nmapsStuDuplicateMac TRAP-TYPE
				ENTERPRISE com21Nmaps
                VARIABLES { nmapsMacAddress }
                DESCRIPTION "
			generated whenever two STU's with the same
			Mac Address are found on the same NMAPS."
                ::= 2

        nmapsDaemonDown TRAP-TYPE
				ENTERPRISE com21Nmaps
                VARIABLES { nmapsDaemonName , nmapsDaemonPid }
                DESCRIPTION "
			generated whenever the Hcx List application detects
			an NMAPS daemon has gone down."
                ::= 3

        nmapsDaemonUp TRAP-TYPE
				ENTERPRISE com21Nmaps
                VARIABLES { nmapsDaemonName , nmapsDaemonPid }
                DESCRIPTION "
			generated whenever the Hcx List application detects
			an NMAPS daemon has come up."
                ::= 4

        nmapsUpdateHcxInDb TRAP-TYPE
				ENTERPRISE com21Nmaps
                VARIABLES { nmapsDaemonForcePoll }
                DESCRIPTION "
			A request to poll the HCX for current configuration
			and put the results in the NMAPS database."
                ::= 5

        nmapsUpdateStusInDb TRAP-TYPE
				ENTERPRISE com21Nmaps
                VARIABLES { nmapsDaemonForcePoll }
                DESCRIPTION "
			A request to poll the Hcx for current STU 
			configuration and put the results in the NMAPS 
			database."
                ::= 6

        nmapsConfiguredStuMissing TRAP-TYPE
				ENTERPRISE com21Nmaps
                VARIABLES { nmapsMacAddress }
                DESCRIPTION "
			generated whenever a configured STU is discovered
			to be missing from the ComCONTROLLER database.
			Either unconfiguration was done via a means other
			than NMAPS (e.g. CUI), or there is a bug."
                ::= 7
--
--  The following traps are generated by the debug logging subsystem
--

        nmapsDebugAlert TRAP-TYPE
				ENTERPRISE com21Nmaps
                VARIABLES { nmapsAlertMessage }
                DESCRIPTION "
			Generated when a Debug message is logged
			in the NMAPS Error Log."
                ::= 101

        nmapsInfoAlert TRAP-TYPE
				ENTERPRISE com21Nmaps
                VARIABLES { nmapsAlertMessage }
                DESCRIPTION "
			Generated when a Info message is logged
			in the NMAPS Error Log."
                ::= 102

        nmapsWarningAlert TRAP-TYPE
				ENTERPRISE com21Nmaps
                VARIABLES { nmapsAlertMessage }
                DESCRIPTION "
			Generated when a Warning message is logged
			in the NMAPS Error Log."
                ::= 103

        nmapsErrorAlert TRAP-TYPE
				ENTERPRISE com21Nmaps
                VARIABLES { nmapsAlertMessage }
                DESCRIPTION "
			Generated when a Error message is logged
			in the NMAPS Error Log."
                ::= 104

        nmapsFatalAlert TRAP-TYPE
				ENTERPRISE com21Nmaps
                VARIABLES { nmapsAlertMessage }
                DESCRIPTION "
			Generated when a Fatal message is logged
			in the NMAPS Error Log."
                ::= 105

        nmapsDisasterAlert TRAP-TYPE
				ENTERPRISE com21Nmaps
                VARIABLES { nmapsAlertMessage }
                DESCRIPTION "
			Generated when a Disaster message is logged
			in the NMAPS Error Log."
                ::= 106

END
