-- *****************************************************************
-- CISCO-FLASH-CAPABILITY.my: CISCO-FLASH-MIB AGENT-CAPABILITIES
--
-- September 2001, A S Kiran Koushik
-- April 2004, Wen Xu
-- 
-- Copyright (c) 2001, 2003, 2004 by Cisco Systems, Inc.
-- All rights reserved.
--
-- *****************************************************************

CISCO-FLASH-CAPABILITY DEFINITIONS ::= BEGIN

IMPORTS
        MODULE-IDENTITY
                FROM SNMPv2-SMI
        AGENT-CAPABILITIES
                FROM SNMPv2-CONF
        ciscoAgentCapability
                FROM CISCO-SMI;   

ciscoFlashCapability MODULE-IDENTITY
                LAST-UPDATED    "200404010000Z"
                ORGANIZATION    "Cisco Systems, Inc."
                CONTACT-INFO  
                        "       Cisco Systems
                                Customer Service

                        Postal: 170 West Tasman Drive
                                San Jose, CA  95134
                                USA

                           Tel: +1 800 553-NETS

                        E-mail: cs-snmp@cisco.com"
                DESCRIPTION
                        "Agent capabilities for CISCO-FLASH-MIB"
                REVISION        "200404010000Z"
                DESCRIPTION
                        "Added ciscoFlashMibCapCatOSV08R0301."
                REVISION        "200310210000Z"
                DESCRIPTION
                        "Added ciscoFlashMibCapCatOSV7R0501Cat6k,
                        and ciscoFlashMibCapV12R0113ECat6K."
                REVISION        "200109251234Z"
                DESCRIPTION
                        "Initial version of this MIB module."
        ::= { ciscoAgentCapability 222 }

ciscoFlashCapabilityV12R00S AGENT-CAPABILITIES

PRODUCT-RELEASE "Cisco IOS 12.0S"
STATUS          current
DESCRIPTION     "CISCO-FLASH-MIB capabilities"

SUPPORTS        CISCO-FLASH-MIB
INCLUDES        { ciscoFlashDeviceInfoGroup }

VARIATION       ciscoFlashDeviceChangeTrap -- NOTIFICATION-TYPE
--              OBJECTS { ciscoFlashDeviceIndex, ciscoFlashDeviceSize }
DESCRIPTION     
        "A ciscoFlashDeviceChangeTrap is sent whenever a
        removable Flash device is inserted or removed.
        If the value of ciscoFlashDeviceSize is 0, it means
        that the flash device was removed.
        If the value of ciscoFlashDeviceSize is greater than
        zero, it means that the flash device was inserted."

    ::= { ciscoFlashCapability 1 } 
 
ciscoFlashCapabilityV12R01 AGENT-CAPABILITIES

PRODUCT-RELEASE "Cisco IOS 12.1"
STATUS          current
DESCRIPTION     "CISCO-FLASH-MIB capabilities"

SUPPORTS        CISCO-FLASH-MIB
INCLUDES        { ciscoFlashDeviceInfoGroup }

VARIATION       ciscoFlashDeviceChangeTrap -- NOTIFICATION-TYPE
--              OBJECTS { ciscoFlashDeviceIndex, ciscoFlashDeviceSize }
DESCRIPTION     
        "A ciscoFlashDeviceChangeTrap is sent whenever a
        removable Flash device is inserted or removed.
        If the value of ciscoFlashDeviceSize is 0, it means
        that the flash device was removed.
        If the value of ciscoFlashDeviceSize is greater than
        zero, it means that the flash device was inserted."

    ::= { ciscoFlashCapability 2 } 
 
ciscoFlashCapabilityV12R02 AGENT-CAPABILITIES

PRODUCT-RELEASE "Cisco IOS 12.2"
STATUS          current
DESCRIPTION     "CISCO-FLASH-MIB capabilities"

SUPPORTS        CISCO-FLASH-MIB
INCLUDES        { ciscoFlashDeviceInfoGroup }

VARIATION       ciscoFlashDeviceChangeTrap -- NOTIFICATION-TYPE
--              OBJECTS { ciscoFlashDeviceIndex, ciscoFlashDeviceSize }
DESCRIPTION     
        "A ciscoFlashDeviceChangeTrap is sent whenever a
        removable Flash device is inserted or removed.
        If the value of ciscoFlashDeviceSize is 0, it means
        that the flash device was removed.
        If the value of ciscoFlashDeviceSize is greater than
        zero, it means that the flash device was inserted."

    ::= { ciscoFlashCapability 3 } 

ciscoFlashMibCapCatOSV7R0501Cat4k  AGENT-CAPABILITIES
PRODUCT-RELEASE "Cisco CatOS 7.5(1) on  Catalyst 4000."
STATUS          current
DESCRIPTION     "CISCO-FLASH-MIB capabilities."

SUPPORTS        CISCO-FLASH-MIB
INCLUDES        {
                  ciscoFlashDeviceInfoGroup,
                  ciscoFlashPartitionInfoGroup,
                  ciscoFlashFileInfoGroupRev1,
                  ciscoFlashCopyOpGroup,
                  ciscoFlashMiscOpGroup,
                  ciscoFlashNotifGroup
                }
VARIATION       ciscoFlashCopyCommand
SYNTAX          INTEGER { 
                          copyToFlashWithoutErase(2),
                          copyFromFlash(3)
                        }
DESCRIPTION
        "Only limited set of enumerated values are supported."

VARIATION       ciscoFlashCopyProtocol
SYNTAX          INTEGER {
                          tftp(1),
                          rcp(2)
                        }
DESCRIPTION     
        "Only limited set of enumerated values are supported."

VARIATION       ciscoFlashCopySourceName
SYNTAX          DisplayString (SIZE (1..63))
DESCRIPTION     "Only support up to 63 characters long."

VARIATION       ciscoFlashCopyRemoteUserName 
SYNTAX          DisplayString (SIZE (1..40)) 
DESCRIPTION     "Only support up to 40 characters long."

VARIATION       ciscoFlashMiscOpCommand 
SYNTAX          INTEGER {
                          verify(2),
                          delete(3),
                          undelete(4),
                          squeeze(5),
                          format(6)
                        }
DESCRIPTION
        "Only limited set of enumerated values are supported."

VARIATION       ciscoFlashMiscOpDestinationName 
SYNTAX          DisplayString (SIZE (1..63))
DESCRIPTION     "Only support up to 63 characters long."

VARIATION       ciscoFlashPartitioningCompletionTrap
ACCESS          not-implemented
DESCRIPTION
        "The current implentation does not support flash partitioning.
        Hense, this object is not supported."

    ::= { ciscoFlashCapability 4 }

ciscoFlashMibCapCatOSV7R0501Cat6k AGENT-CAPABILITIES
PRODUCT-RELEASE "Cisco CatOS 7.5(1) on Catalyst 6000."
STATUS          current
DESCRIPTION     "CISCO-FLASH-MIB capabilities."

SUPPORTS        CISCO-FLASH-MIB
INCLUDES        {
                  ciscoFlashDeviceInfoGroupRev1,
                  ciscoFlashPartitionInfoGroup,
                  ciscoFlashFileInfoGroupRev1,
                  ciscoFlashCopyOpGroup,
                  ciscoFlashMiscOpGroup,
                  ciscoFlashNotifGroupRev1
                }
VARIATION       ciscoFlashCopyCommand
SYNTAX          INTEGER {
                          copyToFlashWithoutErase(2),
                          copyFromFlash(3)
                        }
DESCRIPTION
        "Only limited set of enumerated values are supported."

VARIATION       ciscoFlashCopyProtocol
SYNTAX          INTEGER {
                          tftp(1),
                          rcp(2)
                        }
DESCRIPTION     
        "Only limited set of enumerated values are supported."

VARIATION       ciscoFlashCopySourceName
SYNTAX          DisplayString (SIZE (1..63))
DESCRIPTION     "Only support up to 63 characters long."

VARIATION       ciscoFlashCopyRemoteUserName
SYNTAX          DisplayString (SIZE (1..40))
DESCRIPTION     "Only support up to 40 characters long."

VARIATION       ciscoFlashMiscOpCommand
SYNTAX          INTEGER {
                          verify(2),
                          delete(3),
                          undelete(4),
                          squeeze(5),
                          format(6)
                        }
DESCRIPTION
        "Only limited set of enumerated values are supported."

VARIATION       ciscoFlashMiscOpDestinationName
SYNTAX          DisplayString (SIZE (1..63))
DESCRIPTION     "Only support up to 63 characters long."

VARIATION       ciscoFlashPartitioningCompletionTrap
ACCESS          not-implemented
DESCRIPTION
        "The current implentation does not support flash partitioning.
        Hense, this object is not supported."

    ::= { ciscoFlashCapability 5 }

ciscoFlashMibCapV12R0113ECat6K AGENT-CAPABILITIES
PRODUCT-RELEASE "Cisco IOS 12.1(13E) on Catalyst 6000/6500 and Cisco
                7600 series devices."
STATUS          current
DESCRIPTION     "CISCO-FLASH-MIB capabilities."

SUPPORTS        CISCO-FLASH-MIB
INCLUDES        {
                  ciscoFlashDeviceInfoGroupRev1,
                  ciscoFlashPartitionInfoGroup,
                  ciscoFlashFileInfoGroupRev1,
                  ciscoFlashCopyOpGroup,
                  ciscoFlashMiscOpGroup,
                  ciscoFlashNotifGroupRev1
                }
VARIATION       ciscoFlashCopyProtocol
SYNTAX          INTEGER {
                          tftp(1),
                          rcp(2)
                        }
DESCRIPTION     
        "Only limited set of enumerated values are supported."

VARIATION       ciscoFlashPartitioningCompletionTrap
ACCESS          not-implemented
DESCRIPTION
        "The current implentation does not support flash partitioning.
        Hense, this object is not supported."

    ::= { ciscoFlashCapability 6 }

ciscoFlashMibCapCatOSV08R0301 AGENT-CAPABILITIES
PRODUCT-RELEASE "Cisco CatOS 8.3(1)on Catalyst 6000/6500
                and Cisco 7600 series devices."
STATUS          current
DESCRIPTION     "CISCO-FLASH-MIB capabilities."

SUPPORTS        CISCO-FLASH-MIB
INCLUDES        {
                  ciscoFlashDeviceInfoGroupRev1,
                  ciscoFlashPartitionInfoGroup,
                  ciscoFlashFileInfoGroupRev1,
                  ciscoFlashCopyOpGroupRev1,
                  ciscoFlashMiscOpGroup,
                  ciscoFlashNotifGroupRev1
                }
VARIATION       ciscoFlashCopyCommand
SYNTAX          INTEGER {
                          copyToFlashWithoutErase(2),
                          copyFromFlash(3)
                        }
DESCRIPTION     
        "Only limited set of enumerated values are supported."

VARIATION       ciscoFlashCopyProtocol
SYNTAX          INTEGER {
                          tftp(1),
                          rcp(2)
                        }
DESCRIPTION     
        "Only limited set of enumerated values are supported."

VARIATION       ciscoFlashCopySourceName
SYNTAX          DisplayString (SIZE (1..63))
DESCRIPTION     "Only support up to 63 characters long."

VARIATION       ciscoFlashCopyRemoteUserName
SYNTAX          DisplayString (SIZE (1..40))
DESCRIPTION     "Only support up to 40 characters long."

VARIATION       ciscoFlashMiscOpCommand
SYNTAX          INTEGER {
                          verify(2),
                          delete(3),
                          undelete(4),
                          squeeze(5),
                          format(6)
                        }
DESCRIPTION     
        "Only limited set of enumerated values are supported."

VARIATION       ciscoFlashMiscOpDestinationName
SYNTAX          DisplayString (SIZE (1..63))
DESCRIPTION     "Only support up to 63 characters long."

VARIATION       ciscoFlashPartitioningCompletionTrap
ACCESS          not-implemented
DESCRIPTION     "The current implentation does not support flash 
                partitioning.  Hense, this object is not 
                supported."

    ::= { ciscoFlashCapability 7 }

END
