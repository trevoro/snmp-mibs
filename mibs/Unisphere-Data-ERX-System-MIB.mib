-- *****************************************************************************
-- Unisphere-Data-ERX-System-MIB
--
-- Unisphere Networks Enterprise MIB
--   ERX System MIB
--
-- Copyright (c) 1999 Redstone Communications, Inc.
-- Copyright (c) 1999, 2002 Unisphere Networks, Inc.
--   All Rights Reserved.
-- *****************************************************************************

Unisphere-Data-ERX-System-MIB  DEFINITIONS ::= BEGIN

IMPORTS
    MODULE-IDENTITY, OBJECT-TYPE, NOTIFICATION-TYPE, Integer32, Unsigned32,
    TimeTicks
        FROM SNMPv2-SMI
    TEXTUAL-CONVENTION, DisplayString, TruthValue, DateAndTime
        FROM SNMPv2-TC
    MODULE-COMPLIANCE, OBJECT-GROUP, NOTIFICATION-GROUP
        FROM SNMPv2-CONF
    InterfaceIndexOrZero
        FROM IF-MIB
    usDataMibs
        FROM Unisphere-Data-MIBs
    UsdEnable
        FROM Unisphere-Data-TC;

usdERXSysMIB  MODULE-IDENTITY
    LAST-UPDATED "200210141740Z"  -- 14-Oct-02 01:40 PM EDT
    ORGANIZATION "Juniper Networks, Inc."
    CONTACT-INFO
        "       Juniper Networks, Inc.
        Postal: 10 Technology Park Drive
                Westford, MA  01886
                USA
        Tel:    +1 978 589 5800
        Email:  mib@UnisphereNetworks.com"
    DESCRIPTION
        "MIB objects for managing ERX Edge Router systems."
    -- Revision History
    REVISION    "200210141740Z"  -- 14-Oct-02 01:40 PM EDT  - RX 4.0
    DESCRIPTION
        "Added new line card types: X.21/V.35, Ut3f12, Ue3f12, Cocx-F3."
    REVISION    "200204122057Z"  -- 12-Apr-02 04:57 PM EDT  - RX 3.3
    DESCRIPTION
        "Modified the following objects:
             usdERXSysTempFanStatus
             usdERXSysTempStatus
         Added the following objects:
             usdERXSysTempProtectionStatus
             usdERXSysTempProtectionHoldOffTime
             usdERXSysTempProtectionHoldOffTimeRemaining
         Added the following notification:
             usdERXSysTempProtectionStatusChange "
    REVISION    "200105211927Z"  -- 21-May-01 03:27 PM EDT  - RX 3.2
    DESCRIPTION
        "Added the following objects:
             usdERXSysMemUtilPct
             usdERXSysMemCapacity
             usdERXSysHighMemUtilThreshold
             usdERXSysAbatedMemUtilThreshold
             usdERXSysMemUtilTrapEnable
         Added the following notifications:
             usdERXSysHighMemUtil
             usdERXSysAbatedMemUtil "
    REVISION    "200105151827Z"  -- 15-May-01 02:27 PM EDT  - RX 3.0
    DESCRIPTION
        "Added support for system timing parameters.
         Added usdERXSysSlotDescr to usdERXSysSlotOperStatusChange trap."
    REVISION    "200004251844Z"  -- 25-Apr-00  2:44 PM EDT  - RX 2.0
    DESCRIPTION
        "Added board serial number, assembly number and assembly revision."
    REVISION    "200001200000Z"  -- 20-Jan-00               - RX 1.3
    DESCRIPTION
        "Added OC-12 card and Dual FE card support.
         Added redundancy/reversion and boot record configuration support."
    REVISION      "9902100000Z"  -- 10-Feb-99               - RX 1.0
    DESCRIPTION
        "Initial version of this MIB module."
    ::= { usDataMibs 17 }


-- +++++++++++++++++++++++++++++++++++++++++++++++++++++++++++++++++++++++++++++
-- Textual conventions
-- +++++++++++++++++++++++++++++++++++++++++++++++++++++++++++++++++++++++++++++

UsdTimingSelector ::= TEXTUAL-CONVENTION
    STATUS      current
    DESCRIPTION
        "The system timing selector.
         A value of 1 corresponds to the primary timing selector.
         A value of 2 corresponds to the secondary timing selector.
         A value of 3 corresponds to the tertiary timing selector.
         A value of 4 indicates an error with the timing selector."
    SYNTAX      INTEGER (1..4)

UsdTimingSourceType ::= TEXTUAL-CONVENTION
    STATUS       current
    DESCRIPTION
        "The set of selectable timing source types.  The timing source type
        determines the timing source parameters."
    SYNTAX      INTEGER {
                    timingInterfaceIfIndex(1),
                    timingInternal(2),
                    timingLine(3) }

UsdTimingSourceLineType ::= TEXTUAL-CONVENTION
    STATUS      current
    DESCRIPTION
        "The set of choices for line type timing."
    SYNTAX      INTEGER {
                    timingSourceLineUndefined(0),
                    timingSourceLineE1PortA(1),  -- e1:a
                        --  External SC E1 line input, port A
                    timingSourceLineE1PortB(2),  -- e1:b
                        --  External SC E1 line input, port B
                    timingSourceLineT1PortA(3),  -- t1:a
                        --  External SC T1 line input, port A
                    timingSourceLineT1PortB(4) } -- t1:b
                        --  External SC T1 line input, port B

UsdSysCardType ::= TEXTUAL-CONVENTION
    STATUS      current
    DESCRIPTION
        "The type of card in a system slot:
            unknown     Unknown type.
            srp         Switch/Route Processor.
            ct3         Channelized T3.
            oc3         OC-3 (SONET/SDH).
            ut3Atm      Unchannelized T3 (ATM service).
            ut3Frame    Unchannelized T3 (Frame service).
            ue3Atm      Unchannelized E3 (ATM service).
            ue3Frame    Uncahnnelized E3 (Frame service).
            ce1         Channelized   E1.
            ct1         Channelized   T1.
            dpfe        Dual Port Fast Ethernet.
            oc12Pos     OC-12 (POS/SDH).
            oc12Atm     OC-12 (ATM service).
            oc3Pos      Quad OC-3 (POS/SDH).
            oc3Atm      Quad OC-3 (ATM service).
            ge          Gigabit Ethernet.
            fe8         Fast Ethernet 8-port.
            oc3oc12Pos  Generic OC3/OC12 POS (multi-personality).
            oc3oc12Atm  Generic OC3/OC12 ATM (multi-personality).
            coc3oc12    Channelized generic OC3/OC12 (multi-personality).
            coc3        Channelized OC3.
            coc12       Channelized OC12.
            oc12Server  OC-12 Rate Server Card.
            hssi        High Speed Serial Interface.
            geFe        Generic GE/FE (multi-personality).
            ct3P12      Channelized T3 12-port.
            v35         X.21/V.35 Card.
            ut3f12      Unchannelized T3 12-port.
            ue3f12      Unchannelized E3 12-port.
            coc3F3      OC-3 channelized to T3.
            coc12F3     OC-12 channelized to T3.
            cocxF3      12-port T3/E3 or OC3/OC12 (multi-personality)."
    SYNTAX      INTEGER {
                    unknown(0),
                    srp(1),
                    ct3(2),
                    oc3(3),
                    ut3Atm(4),
                    ut3Frame(5),
                    ue3Atm(6),
                    ue3Frame(7),
                    ce1(8),
                    ct1(9),
                    dpfe(10),
                    oc12Pos(11),
                    oc12Atm(12),
                    oc3Pos(13),
                    oc3Atm(14),
                    ge(15),
                    fe8(16),
                    oc3oc12Pos(17),
                    oc3oc12Atm(18),
                    coc3oc12(19),
                    coc3(20),
                    coc12(21),
                    oc12Server(22),
                    hssi(23),
                    geFe(24),
                    ct3P12(25),
                    v35(26),
                    ut3f12(27),
                    ue3f12(28),
                    coc12F3(29),
                    coc3F3(30),
                    cocxF3(31) }


-- +++++++++++++++++++++++++++++++++++++++++++++++++++++++++++++++++++++++++++++
-- MIB Structure
-- +++++++++++++++++++++++++++++++++++++++++++++++++++++++++++++++++++++++++++++
usdERXSysTrap          OBJECT IDENTIFIER ::= { usdERXSysMIB 0 }
usdERXSysObjects       OBJECT IDENTIFIER ::= { usdERXSysMIB 1 }
usdERXSysConformance   OBJECT IDENTIFIER ::= { usdERXSysMIB 2 }

-- +++++++++++++++++++++++++++++++++++++++++++++++++++++++++++++++++++++++++++++
-- Managed objects
-- +++++++++++++++++++++++++++++++++++++++++++++++++++++++++++++++++++++++++++++
--
-- Object Groups
--
usdERXSysGeneral       OBJECT IDENTIFIER ::= { usdERXSysObjects 1 }
usdERXSysFabric        OBJECT IDENTIFIER ::= { usdERXSysObjects 2 }
usdERXSysNvs           OBJECT IDENTIFIER ::= { usdERXSysObjects 3 }
usdERXSysSlot          OBJECT IDENTIFIER ::= { usdERXSysObjects 4 }
usdERXSysPort          OBJECT IDENTIFIER ::= { usdERXSysObjects 5 }
usdERXSysPower         OBJECT IDENTIFIER ::= { usdERXSysObjects 6 }
usdERXSysTemperature   OBJECT IDENTIFIER ::= { usdERXSysObjects 7 }
usdERXSysSubsystem     OBJECT IDENTIFIER ::= { usdERXSysObjects 8 }


-- +++++++++++++++++++++++++++++++++++++++++++++++++++++++++++++++++++++++++++++
--
-- Chassis objects
--
-- +++++++++++++++++++++++++++++++++++++++++++++++++++++++++++++++++++++++++++++
usdERXSysChassisRev OBJECT-TYPE
    SYNTAX      Integer32 (0..255)
    MAX-ACCESS  read-only
    STATUS      current
    DESCRIPTION
        "Chassis revision number.  If unknown, the value 255 is reported."
    ::= { usdERXSysGeneral 1 }

usdERXSysSwVersion OBJECT-TYPE
    SYNTAX      DisplayString
    MAX-ACCESS  read-only
    STATUS      current
    DESCRIPTION
        "Currently executing operational software version."
    ::= { usdERXSysGeneral 2 }

usdERXSysSwBuildDate OBJECT-TYPE
    SYNTAX      DisplayString
    MAX-ACCESS  read-only
    STATUS      current
    DESCRIPTION
        "Build date of currently executing operational software version."
    ::= { usdERXSysGeneral 3 }

usdERXSysRevertControl OBJECT-TYPE
    SYNTAX      INTEGER {
                    off(0),
                    immediate(1),
                    timeOfDay(2) }
    MAX-ACCESS  read-write
    STATUS      current
    DESCRIPTION
        "Global revert control:
            off             Disable global revert.
            immediate       All slots are to revert immediately (asap).
            timeOfDay       All slots are to revert at time specified by
                            usdRxSysRevertTimeOfDay.  This object/value must
                            be set concurrently with usdERXSysRevertTimeOfDay."
    ::= { usdERXSysGeneral 4 }

usdERXSysRevertTimeOfDay OBJECT-TYPE
    SYNTAX      Integer32 (0..86399)
    UNITS       "seconds"
    MAX-ACCESS  read-write
    STATUS      current
    DESCRIPTION
        "The number of seconds past midnight on any given day at which time
        reverts are allowed to occur.  This object must be set concurrently with
        usdERXSysRevertControl."
    ::= { usdERXSysGeneral 5 }

usdERXSysBootConfigControl OBJECT-TYPE
    SYNTAX      INTEGER {
                    file(0),
                    fileOnce(1),
                    factoryDefaults(2),
                    runningConfiguration(3) }
    MAX-ACCESS  read-write
    STATUS      current
    DESCRIPTION
        "System boot configuration control:
            file                  Revert to configuration settings specified by
                                  usdERXSysBootConfigFile.  The
                                  usdERXSysBootConfigControl and
                                  usdERXSysBootConfigFile must be specified
                                  together in the same set request PDU.
            fileOnce              Revert to configuration settings specified by
                                  usdERXSysBootConfigFile.  Do not continue to
                                  use file after using it once.  The
                                  usdERXSysBootConfigControl and
                                  usdERXSysBootConfigFile must be specified
                                  together in the same set request PDU.
            factoryDefaults       Revert to factory default settings.
            runningConfiguration  Revert to current settings."
    ::= { usdERXSysGeneral 6 }

usdERXSysBootBackupConfigControl OBJECT-TYPE
    SYNTAX      INTEGER {
                    file(0),
                    factoryDefaults(1),
                    none(2) }
    MAX-ACCESS  read-write
    STATUS      current
    DESCRIPTION
        "System boot backup configuration control:
            file                  Revert to backup configuration settings
                                  specified by usdERXSysBootBackupConfigFile.
                                  The usdERXSysBootBackupConfigControl and
                                  usdERXSysBootBackupConfigFile must be
                                  specified together in the same set request
                                  PDU.
            factoryDefaults       Revert to factory default settings.
            none                  Specify no backup."
    ::= { usdERXSysGeneral 7 }

usdERXSysBootForceBackupControl OBJECT-TYPE
    SYNTAX      INTEGER {
                    off(0),
                    on(1) }
    MAX-ACCESS  read-write
    STATUS      current
    DESCRIPTION
        "System boot force backup control:
            off      Do not force revert to backup settings.
            on       Do force revert to backup settings."
    ::= { usdERXSysGeneral 8 }

usdERXSysBootAutoRevertControl OBJECT-TYPE
    SYNTAX      INTEGER {
                    default(0),
                    never(1),
                    set(2) }
    MAX-ACCESS  read-write
    STATUS      current
    DESCRIPTION
        "System boot auto revert control:
            default  Use default auto-revert tolerances.
            never    Never auto-revert to backup.
            set      Set auto-revert settings at specified tolerances."
    ::= { usdERXSysGeneral 9 }

usdERXSysBootAutoRevertCountTolerance OBJECT-TYPE
    SYNTAX      Unsigned32 (0..4294967294)
    MAX-ACCESS  read-write
    STATUS      current
    DESCRIPTION
        "The auto-revert reboot count tolerance.  This object cannot be set to
        zero, but may contain a zero value when the control is set to never(1)."
    ::= { usdERXSysGeneral 10 }

usdERXSysBootAutoRevertTimeTolerance OBJECT-TYPE
    SYNTAX      Unsigned32 (0..4294967294)
    UNITS       "seconds"
    MAX-ACCESS  read-write
    STATUS      current
    DESCRIPTION
        "The auto-revert reboot time tolerance.  This object cannot be set to
        zero, but will contain a zero value when the control is set to
        never(1)."
    ::= { usdERXSysGeneral 11 }

usdERXSysBootReleaseFile OBJECT-TYPE
    SYNTAX      DisplayString (SIZE(0..128))
    MAX-ACCESS  read-write
    STATUS      current
    DESCRIPTION
        "The local boot release file name, with extension .rel."
    DEFVAL    { "" }
    ::= { usdERXSysGeneral 12 }

usdERXSysBootConfigFile OBJECT-TYPE
    SYNTAX      DisplayString (SIZE(0..128))
    MAX-ACCESS  read-write
    STATUS      current
    DESCRIPTION
        "The local boot configuration file name, with extension .cnf.  The
        usdERXSysBootConfigControl and usdERXSysBootConfigFile must be specified
        together in the same set request PDU."
    DEFVAL    { "" }
    ::= { usdERXSysGeneral 13 }

usdERXSysBootBackupReleaseFile OBJECT-TYPE
    SYNTAX      DisplayString (SIZE(0..128))
    MAX-ACCESS  read-write
    STATUS      current
    DESCRIPTION
        "The local backup boot release file name, with extension .rel."
    DEFVAL    { "" }
    ::= { usdERXSysGeneral 14 }

usdERXSysBootBackupConfigFile OBJECT-TYPE
    SYNTAX      DisplayString (SIZE(0..128))
    MAX-ACCESS  read-write
    STATUS      current
    DESCRIPTION
        "The local backup boot configuration file name, with extension .cnf.
        The usdERXSysBootBackupConfigControl and usdERXSysBootBackupConfigFile
        must be specified together in the same set request PDU."
    DEFVAL    { "" }
    ::= { usdERXSysGeneral 15 }

usdERXSysAdminTimingSource OBJECT-TYPE
    SYNTAX      UsdTimingSelector
    MAX-ACCESS  read-write
    STATUS      current
    DESCRIPTION
        "The administrative timing source for the ERX system.  The ERX
        periodically monitors the status of three timing sources, primary,
        secondary and tertiary.  If the systems current timing source fails, the
        system will automatically downgrade to the next timing source.  If the
        system is configured to automatically upgrade
        (usdERXSysTimingDisableAutoUpgrade is set to false(2)) the system will
        switch back to the higher timing source when it becomes available.

        A timing source failure can be detected by comparing the operational and
        admin timing sources.  If they are not equal, the system has swapped
        timing sources because the administratively set value is in the error
        state."
    ::= { usdERXSysGeneral 16 }

usdERXSysOperTimingSource OBJECT-TYPE
    SYNTAX      UsdTimingSelector
    MAX-ACCESS  read-only
    STATUS      current
    DESCRIPTION
        "The operations timing source for the ERX system.  The ERX periodically
        monitors the status of three timing sources, primary, secondary and
        tertiary.  If the systems current timing source fails, the system will
        automatically downgrade to the next timing source.  If the system is
        configured to automatically upgrade (usdERXSysTimingDisableAutoUpgrade
        is set to false(2)) the system will switch back to the higher timing
        source when it becomes available."
    ::= { usdERXSysGeneral 17 }

usdERXSysTimingDisableAutoUpgrade OBJECT-TYPE
    SYNTAX      TruthValue
    MAX-ACCESS  read-write
    STATUS      current
    DESCRIPTION
        "This object controls the automatic timing selector upgrade.  Setting
        this object to true(1) will prevent automatic upgrade to the next
        highest timing selector.  Setting this object to false(2) will enable
        the automatic upgrade of timing selectors."
    DEFVAL    { false }
    ::= { usdERXSysGeneral 18 }

usdERXSysTimingSelectorTable OBJECT-TYPE
    SYNTAX      SEQUENCE OF UsdERXSysTimingSelectorEntry
    MAX-ACCESS  not-accessible
    STATUS      current
    DESCRIPTION
        "Table of system timing selectors."
    ::= { usdERXSysGeneral 19 }

usdERXSysTimingSelectorEntry OBJECT-TYPE
    SYNTAX      UsdERXSysTimingSelectorEntry
    MAX-ACCESS  not-accessible
    STATUS      current
    DESCRIPTION
        "A table entry describing a system timing selector."
    INDEX     { usdERXSysTimingSelectorIndex }
    ::= {usdERXSysTimingSelectorTable 1 }

UsdERXSysTimingSelectorEntry ::= SEQUENCE {
    usdERXSysTimingSelectorIndex UsdTimingSelector,
    usdERXSysTimingSourceType    UsdTimingSourceType,
    usdERXSysTimingSourceIfIndex InterfaceIndexOrZero,
    usdERXSysTimingSourceLine    UsdTimingSourceLineType,
    usdERXSysTimingStatus        INTEGER }

usdERXSysTimingSelectorIndex OBJECT-TYPE
    SYNTAX      UsdTimingSelector
    MAX-ACCESS  not-accessible
    STATUS      current
    DESCRIPTION
        "The system timing selector index associated with this entry."
    ::= { usdERXSysTimingSelectorEntry 1 }

usdERXSysTimingSourceType OBJECT-TYPE
    SYNTAX      UsdTimingSourceType
    MAX-ACCESS  read-write
    STATUS      current
    DESCRIPTION
        "The system timing source type for this entry.  This object must be
        present when setting either the usdERXSysTimingSourceIfIndex or
        usdERXSysTimingSourceLine objects.  Also, if the value of this object is
        set to timingInternal(2), no other objects should be simultanously set,
        otherwise the agent will return an error."
    ::= { usdERXSysTimingSelectorEntry 2 }

usdERXSysTimingSourceIfIndex OBJECT-TYPE
    SYNTAX      InterfaceIndexOrZero
    MAX-ACCESS  read-write
    STATUS      current
    DESCRIPTION
        "The ifIndex of the interface selected as the system timing source.  The
        usdERXSysTimingSourceType object must be set to
        timingInterfaceIfIndex(1) otherwise setting this object will fail."
    ::= { usdERXSysTimingSelectorEntry 3 }

usdERXSysTimingSourceLine OBJECT-TYPE
    SYNTAX      UsdTimingSourceLineType
    MAX-ACCESS  read-write
    STATUS      current
    DESCRIPTION
        "The line type timing source for this entry.  The
        usdRxSysTimingSourceType object must be set to timingLine(3) for the
        agent to accept a set to this object."
    DEFVAL    { timingSourceLineUndefined }
    ::= { usdERXSysTimingSelectorEntry 4 }

usdERXSysTimingStatus OBJECT-TYPE
    SYNTAX      INTEGER {
                    timingStatusOk(1),
                    timingStatusError(2),
                    timingStatusUnknown(3) }
    MAX-ACCESS  read-only
    STATUS      current
    DESCRIPTION
        "The status associated with this system timing selector."
    ::= { usdERXSysTimingSelectorEntry 5 }

usdERXSysMemUtilPct OBJECT-TYPE
    SYNTAX      Integer32 (-1..100)
    UNITS       "percent"
    MAX-ACCESS  read-only
    STATUS      current
    DESCRIPTION
        "Percentage of system memory utilization.  A value of -1 indicates the
        utilization is unknown."
    ::= { usdERXSysGeneral 20 }

usdERXSysMemCapacity OBJECT-TYPE
    SYNTAX      Integer32
    UNITS       "bytes"
    MAX-ACCESS  read-only
    STATUS      current
    DESCRIPTION
        "The total memory capacity of the system."
    ::= { usdERXSysGeneral 21 }

usdERXSysHighMemUtilThreshold OBJECT-TYPE
    SYNTAX      Integer32 (1..100)
    UNITS       "percent"
    MAX-ACCESS  read-write
    STATUS      current
    DESCRIPTION
        "The value of system memory utilization, where if reached for the first
        time will generate a high memory utilization event to the management
        entity on this system.

        The value of this object must be greated than the value of
        usdERXSysAbatedMemUtilThreshold."
    DEFVAL    { 85 }
    ::= { usdERXSysGeneral 22 }

usdERXSysAbatedMemUtilThreshold OBJECT-TYPE
    SYNTAX      Integer32 (0..99)
    UNITS       "percent"
    MAX-ACCESS  read-write
    STATUS      current
    DESCRIPTION
        "The value of system memory utilization that is used to determine when
        to generate an abated memory utilization event notification to the
        management entity on this system.

        The value of this object must be less than the value of
        usdERXSysHighMemUtilThreshold.

        The abated memory utilization trap is sent once if the high memory
        threshold was reached, and memory utilization falls to the value of this
        object."
    DEFVAL    { 75 }
    ::= { usdERXSysGeneral 23 }

usdERXSysMemUtilTrapEnable OBJECT-TYPE
    SYNTAX      TruthValue
    MAX-ACCESS  read-write
    STATUS      current
    DESCRIPTION
        "Controls the sending of system memory utilization events.  Setting the
        value of this object to true(1) will cause system memory utilization
        event notification, if they occur, to be sent to the management entity
        on this system.  Setting the value of this object to false(2) will
        disable event notifications."
    DEFVAL    { false }
    ::= { usdERXSysGeneral 24 }


-- +++++++++++++++++++++++++++++++++++++++++++++++++++++++++++++++++++++++++++++
--
-- Fabric objects
--
-- +++++++++++++++++++++++++++++++++++++++++++++++++++++++++++++++++++++++++++++
usdERXSysFabricSpeed OBJECT-TYPE
    SYNTAX      Integer32
    UNITS       "gigabits per second"
    MAX-ACCESS  read-only
    STATUS      current
    DESCRIPTION
        "Speed of switching fabric, in gigabits per second."
    ::= { usdERXSysFabric 1 }

usdERXSysFabricRev OBJECT-TYPE
    SYNTAX      Integer32 (0..255)
    MAX-ACCESS  read-only
    STATUS      current
    DESCRIPTION
        "Fabric revision number.  If unknown, the value 255 is reported."
    ::= { usdERXSysFabric 2 }


-- +++++++++++++++++++++++++++++++++++++++++++++++++++++++++++++++++++++++++++++
--
-- Nvs objects
--
-- +++++++++++++++++++++++++++++++++++++++++++++++++++++++++++++++++++++++++++++
usdERXSysNvsStatus OBJECT-TYPE
    SYNTAX      INTEGER {
                    notPresent(0),
                    writeProtected(1),
                    volumeError(2),
                    nearCapacity(3),
                    ok(4),
                    nearConfigCapacity(5) }
    MAX-ACCESS  read-only
    STATUS      current
    DESCRIPTION
        "Status of non-volatile storage (NVS):
            notPresent          NVS is not installed.
            writeProtected      NVS is write-protected.
            volumeError         Status poll of NVS failed.
            nearCapacity        Utilization exceeds 85% of NVS capacity.
            ok                  NVS is operational, none of the preceding
                                conditions apply.
            nearConfigCapacity  Utilization exceeds the ability to save the
                                running configuration."
    ::= { usdERXSysNvs 1 }

usdERXSysNvsCapacity OBJECT-TYPE
    SYNTAX      Integer32
    UNITS       "megabytes"
    MAX-ACCESS  read-only
    STATUS      current
    DESCRIPTION
        "Capacity of NVS storage in megabytes."
    ::= { usdERXSysNvs 2 }

usdERXSysNvsUtilPct OBJECT-TYPE
    SYNTAX      Integer32 (-1..100)
    UNITS       "percent"
    MAX-ACCESS  read-only
    STATUS      current
    DESCRIPTION
        "Percentage of NVS storage used.  A value of -1 indicates NVS
        utilization is unknown."
    ::= { usdERXSysNvs 3 }


-- +++++++++++++++++++++++++++++++++++++++++++++++++++++++++++++++++++++++++++++
--
-- Slot objects
--
-- +++++++++++++++++++++++++++++++++++++++++++++++++++++++++++++++++++++++++++++
usdERXSysSlotCount OBJECT-TYPE
    SYNTAX      Integer32
    MAX-ACCESS  read-only
    STATUS      current
    DESCRIPTION
        "The number of slots in the system."
    ::= { usdERXSysSlot 1 }

usdERXSysSlotTable OBJECT-TYPE
    SYNTAX      SEQUENCE OF UsdERXSysSlotEntry
    MAX-ACCESS  not-accessible
    STATUS      current
    DESCRIPTION
        "Table of system slots."
    ::= { usdERXSysSlot 2 }

usdERXSysSlotEntry OBJECT-TYPE
    SYNTAX      UsdERXSysSlotEntry
    MAX-ACCESS  not-accessible
    STATUS      current
    DESCRIPTION
        "A table entry describing contents of a system slot."
    INDEX     { usdERXSysSlotIndex }
    ::= {usdERXSysSlotTable 1 }

UsdERXSysSlotEntry ::= SEQUENCE {
    usdERXSysSlotIndex                   Integer32,
    usdERXSysSlotDescr                   DisplayString,
    usdERXSysSlotCurrentCardType         UsdSysCardType,
    usdERXSysSlotRev                     Integer32,
    usdERXSysSlotAdminStatus             UsdEnable,
    usdERXSysSlotOperStatus              INTEGER,
    usdERXSysSlotDisableReason           INTEGER,
    usdERXSysSlotExpectedCardType        UsdSysCardType,
    usdERXSysSlotControl                 INTEGER,
    usdERXSysSlotCpuUtilPct              Integer32,
    usdERXSysSlotMemUtilPct              Integer32,
    usdERXSysSlotIoaPresent              TruthValue,
    usdERXSysSlotPortCount               Integer32,
    usdERXSysSlotLastChange              TimeTicks,
    usdERXSysSlotRedundancyLockout       UsdEnable,
    usdERXSysSlotRedundancyGroupId       Unsigned32,
    usdERXSysSlotSpareServer             TruthValue,
    usdERXSysSlotAssociatedSlot          Integer32,
    usdERXSysSlotRevertControl           INTEGER,
    usdERXSysSlotRedundancyRevertTime    DateAndTime,
    usdERXSysSlotBootReleaseFile         DisplayString,
    usdERXSysSlotBootBackupReleaseFile   DisplayString,
    usdERXSysSlotSerialNumber            DisplayString,
    usdERXSysSlotAssemblyPartNumber      DisplayString,
    usdERXSysSlotAssemblyRev             DisplayString,
    usdERXSysSlotIoaSerialNumber         DisplayString,
    usdERXSysSlotIoaAssemblyPartNumber   DisplayString,
    usdERXSysSlotIoaAssemblyRev          DisplayString }

usdERXSysSlotIndex OBJECT-TYPE
    SYNTAX      Integer32 (0..255)
    MAX-ACCESS  not-accessible
    STATUS      current
    DESCRIPTION
        "Slot number.

        NOTE: Slot numbers are zero-based."
    ::= { usdERXSysSlotEntry 1 }

usdERXSysSlotDescr OBJECT-TYPE
    SYNTAX      DisplayString (SIZE(0..63))
    MAX-ACCESS  read-only
    STATUS      current
    DESCRIPTION
        "Textual description of the card."
    ::= { usdERXSysSlotEntry 2 }

usdERXSysSlotCurrentCardType OBJECT-TYPE
    SYNTAX      UsdSysCardType
    MAX-ACCESS  read-only
    STATUS      current
    DESCRIPTION
        "Type of card actually in the slot.  This could be different from the
        type reported in usdERXSysSlotExpectedCardType, in which case it may be
        necessary to set usdERXSysSlotControl to 'flush' before this card can be
        made operational."
    ::= { usdERXSysSlotEntry 3 }

usdERXSysSlotRev OBJECT-TYPE
    SYNTAX      Integer32 (0..255)
    MAX-ACCESS  read-only
    STATUS      current
    DESCRIPTION
        "Revision number of the card.  If unknown, the value 255 is reported."
    ::= { usdERXSysSlotEntry 4 }

usdERXSysSlotAdminStatus OBJECT-TYPE
    SYNTAX      UsdEnable
    MAX-ACCESS  read-write
    STATUS      current
    DESCRIPTION
        "Exerts administrative control to enable/disable the slot."
    ::= { usdERXSysSlotEntry 5 }

usdERXSysSlotOperStatus OBJECT-TYPE
    SYNTAX      INTEGER {
                    unknown(0),
                    empty(1),
                    disabled(2),
                    failed(3),
                    booting(4),
                    initializing(5),
                    online(6),
                    standby(7),
                    inactive(8) }
    MAX-ACCESS  read-only
    STATUS      current
    DESCRIPTION
        "Status of the card."
    ::= { usdERXSysSlotEntry 6 }

usdERXSysSlotDisableReason OBJECT-TYPE
    SYNTAX      INTEGER {
                    none(0),
                    unknown(1),
                    assessing(2),
                    admin(3),
                    cardMismatch(4),
                    fabricLimit(5),
                    imageError(6) }
    MAX-ACCESS  read-only
    STATUS      current
    DESCRIPTION
        "Indicates the condition causing the slot to be disabled:
            none            Value when card is not disabled.
            unknown         Unknown reason for disablement.
            assessing       The slot content is being assessed (transient
                            initialization state).
            admin           The slot is administratively disabled.
            cardMismatch    The current card type conflicts with configuration
                            associated with a different card type that
                            previously occupied the slot.
            fabricLimit     Card resource requirements exceed available fabric
                            capacity.
            imageError      Software image for card is missing or invalid."
    ::= { usdERXSysSlotEntry 7 }

usdERXSysSlotExpectedCardType OBJECT-TYPE
    SYNTAX      UsdSysCardType
    MAX-ACCESS  read-only
    STATUS      current
    DESCRIPTION
        "Type of card associated with this slot through prior presence.  After
        the card is removed, this association persists (and inhibits operation
        of a different card type in this slot, if one is inserted) until
        usdERXSysSlotControl is set to 'flush'."
    ::= { usdERXSysSlotEntry 8 }

usdERXSysSlotControl OBJECT-TYPE
    SYNTAX      INTEGER {
                    noOperation(0),
                    flush(1),
                    reset(2),
                    forceFailover(3),
                    noBoot(4),
                    noBootBackup(5) }
    MAX-ACCESS  read-write
    STATUS      current
    DESCRIPTION
        "Administrative control of this slot:
            noOperation     Setting this value has no effect.
            flush           Flushes configuration associated with a
                            card type that previously occupied this slot.
                            Used to explicitly confirm that the slot is
                            now empty, or contains a different card type.
                            Card must be disabled when this value is asserted.
                            See description for usdERXSysSlotDisableReason.
            reset           Resets the slot.
            forceFailover   Forces the slot to failover to backup.
            noBoot          Deconfigure primary release file for the slot.
            noBootBackup    Deconfigure backup release file for the slot."
    ::= { usdERXSysSlotEntry 9 }

usdERXSysSlotCpuUtilPct OBJECT-TYPE
    SYNTAX      Integer32 (-1..100)
    UNITS       "percent"
    MAX-ACCESS  read-only
    STATUS      current
    DESCRIPTION
        "Percentage of CPU utilization.  A value of -1 indicates the utilization
        is unknown."
    ::= { usdERXSysSlotEntry 10 }

usdERXSysSlotMemUtilPct OBJECT-TYPE
    SYNTAX      Integer32 (-1..100)
    UNITS       "percent"
    MAX-ACCESS  read-only
    STATUS      current
    DESCRIPTION
        "Percentage of memory utilization.  A value of -1 indicates the
        utilization is unknown."
    ::= { usdERXSysSlotEntry 11 }

usdERXSysSlotIoaPresent OBJECT-TYPE
    SYNTAX      TruthValue
    MAX-ACCESS  read-only
    STATUS      current
    DESCRIPTION
        "Indicates whether the card's corresponding I/O adapter is present."
    ::= { usdERXSysSlotEntry 12 }

usdERXSysSlotPortCount OBJECT-TYPE
    SYNTAX      Integer32
    MAX-ACCESS  read-only
    STATUS      current
    DESCRIPTION
        "Number of physical ports for the EXPECTED card type for this slot.

        NOTE: In event of a card mismatch in this slot, the port count for the
        CURRENT card in this slot is not recognized/reported until the
        configuration for the EXPECTED card is explicitly flushed via
        usdERXSysSlotControl."
    ::= { usdERXSysSlotEntry 13 }

usdERXSysSlotLastChange OBJECT-TYPE
    SYNTAX      TimeTicks
    MAX-ACCESS  read-only
    STATUS      current
    DESCRIPTION
        "The value of sysUpTime when the value of usdERXSysSlotOperStatus
        last changed."
    ::= { usdERXSysSlotEntry 14 }

usdERXSysSlotRedundancyLockout OBJECT-TYPE
    SYNTAX      UsdEnable
    MAX-ACCESS  read-write
    STATUS      current
    DESCRIPTION
        "Exerts administrative control to enable/disable Redundancy protection
        for the slot."
    ::= { usdERXSysSlotEntry 15 }

usdERXSysSlotRedundancyGroupId OBJECT-TYPE
    SYNTAX      Unsigned32
    MAX-ACCESS  read-only
    STATUS      current
    DESCRIPTION
        "Identifies the Redundancy group as derived from hardware settings."
    ::= { usdERXSysSlotEntry 16 }

usdERXSysSlotSpareServer OBJECT-TYPE
    SYNTAX      TruthValue
    MAX-ACCESS  read-only
    STATUS      current
    DESCRIPTION
        "True only if the line card in slot is a spare redundant server."
    ::= { usdERXSysSlotEntry 17 }

usdERXSysSlotAssociatedSlot OBJECT-TYPE
    SYNTAX      Integer32
    MAX-ACCESS  read-only
    STATUS      current
    DESCRIPTION
        "If the module is a primary card and the spare is acting on its behalf,
        then the value of this object is the slot number of the associated
        spare.

        If the module is a primary card and is active (not spared), then the
        value of this object is the cards actual slot number.

        If the module is a spare card and it is active, then the value of this
        object is the slot number of the primary card that is being spared for.

        If the module is a spare and it is inactive, then the value of this
        object is the its own slot number.

        If module is not part of a redundancy group, or the slot is empty, the
        value of this object is 255."
    ::= { usdERXSysSlotEntry 18 }

usdERXSysSlotRevertControl OBJECT-TYPE
    SYNTAX      INTEGER {
                    off(0),
                    immediate(1),
                    timeAndDate(2) }
    MAX-ACCESS  read-write
    STATUS      current
    DESCRIPTION
        "Per-slot revert control:
            off             Disable slot revert.
            immediate       Slot is to revert immediately (asap).
            timeAndDate     Slot is to revert at time specified by
                            usdRxSysSlotRedundancyRevertTime."
    ::= { usdERXSysSlotEntry 19 }

usdERXSysSlotRedundancyRevertTime OBJECT-TYPE
    SYNTAX      DateAndTime
    MAX-ACCESS  read-write
    STATUS      current
    DESCRIPTION
        "The date and time associated with the timeAndDate (delayed) revert
        operation."
    ::= { usdERXSysSlotEntry 20 }

usdERXSysSlotBootReleaseFile OBJECT-TYPE
    SYNTAX      DisplayString (SIZE(0..128))
    MAX-ACCESS  read-write
    STATUS      current
    DESCRIPTION
        "The local boot release file name for this slot, with extension .rel."
    DEFVAL    { "" }
    ::= { usdERXSysSlotEntry 21 }

usdERXSysSlotBootBackupReleaseFile OBJECT-TYPE
    SYNTAX      DisplayString (SIZE(0..128))
    MAX-ACCESS  read-write
    STATUS      current
    DESCRIPTION
        "The local backup boot release file name for this slot, with extension
        .rel."
    DEFVAL    { "" }
    ::= { usdERXSysSlotEntry 22 }

usdERXSysSlotSerialNumber OBJECT-TYPE
    SYNTAX      DisplayString (SIZE(0..10))
    MAX-ACCESS  read-only
    STATUS      current
    DESCRIPTION
        "The serial number of the card in this slot."
    DEFVAL    { "" }
    ::= { usdERXSysSlotEntry 23 }

usdERXSysSlotAssemblyPartNumber OBJECT-TYPE
    SYNTAX      DisplayString (SIZE(0..10))
    MAX-ACCESS  read-only
    STATUS      current
    DESCRIPTION
        "The part number of the card in this slot."
    DEFVAL    { "" }
    ::= { usdERXSysSlotEntry 24 }

usdERXSysSlotAssemblyRev OBJECT-TYPE
    SYNTAX      DisplayString (SIZE(0..3))
    MAX-ACCESS  read-only
    STATUS      current
    DESCRIPTION
        "The revision number of the card assembly in this slot."
    DEFVAL    { "" }
    ::= { usdERXSysSlotEntry 25 }

usdERXSysSlotIoaSerialNumber OBJECT-TYPE
    SYNTAX      DisplayString (SIZE(0..10))
    MAX-ACCESS  read-only
    STATUS      current
    DESCRIPTION
        "The serial number of the I/O adaptor on the card in this slot."
    DEFVAL    { "" }
    ::= { usdERXSysSlotEntry 26 }

usdERXSysSlotIoaAssemblyPartNumber OBJECT-TYPE
    SYNTAX      DisplayString (SIZE(0..10))
    MAX-ACCESS  read-only
    STATUS      current
    DESCRIPTION
        "The part number of the I/O adaptor on the card in this slot."
    DEFVAL    { "" }
    ::= { usdERXSysSlotEntry 27 }

usdERXSysSlotIoaAssemblyRev OBJECT-TYPE
    SYNTAX     DisplayString (SIZE (0..3))
    MAX-ACCESS read-only
    STATUS     current
    DESCRIPTION
        "The revision number of the I/O adaptor assembly on the card in this
        slot."
    DEFVAL    { "" }
    ::= { usdERXSysSlotEntry 28 }


-- +++++++++++++++++++++++++++++++++++++++++++++++++++++++++++++++++++++++++++++
--
-- System Port objects
--
-- +++++++++++++++++++++++++++++++++++++++++++++++++++++++++++++++++++++++++++++
usdERXSysPortTable OBJECT-TYPE
    SYNTAX      SEQUENCE OF UsdERXSysPortEntry
    MAX-ACCESS  not-accessible
    STATUS      current
    DESCRIPTION
        "Table of system physical ports.

        The information in this table reflects the ports for the EXPECTED card
        type in each slot; in event of a card mismatch, this table permits
        navigation of the existing configuration of the expected card type."
    ::= { usdERXSysPort 1 }

usdERXSysPortEntry OBJECT-TYPE
    SYNTAX      UsdERXSysPortEntry
    MAX-ACCESS  not-accessible
    STATUS      current
    DESCRIPTION
        "A table entry describing a physical port of the system."
    INDEX     { usdERXSysSlotIndex,
                usdERXSysPortIndex }
    ::= {usdERXSysPortTable 1 }

UsdERXSysPortEntry ::= SEQUENCE {
    usdERXSysPortIndex   Integer32,
    usdERXSysPortDescr   DisplayString,
    usdERXSysPortType    INTEGER,
    usdERXSysPortIfIndex InterfaceIndexOrZero }

usdERXSysPortIndex OBJECT-TYPE
    SYNTAX      Integer32 (0..255)
    MAX-ACCESS  not-accessible
    STATUS      current
    DESCRIPTION
        "Port number of this physical port, relative to the slot in which it
        resides.  Each physical port is uniquely distinguished by its slot/port
        pair.

        NOTE: Port numbers are zero-based."
    ::= { usdERXSysPortEntry 1 }

usdERXSysPortDescr OBJECT-TYPE
    SYNTAX      DisplayString (SIZE(0..63))
    MAX-ACCESS  read-only
    STATUS      current
    DESCRIPTION
        "Textual description of this port."
    ::= { usdERXSysPortEntry 2 }

usdERXSysPortType OBJECT-TYPE
    SYNTAX      INTEGER {
                    unknown(0),
                    eth(1),
                    ct3(2),
                    oc3c(3),
                    ut3Atm(4),
                    ut3Frame(5),
                    ue3Atm(6),
                    ue3Frame(7),
                    ce1(8),
                    ct1(9),
                    oc12cPos(10),
                    oc12cAtm(11),
                    oc3cPos(12),
                    oc3cAtm(13),
                    coc3(14),
                    coc12(15),
                    oc12Server(16),
                    hssi(17),
                    v35(18) }
    MAX-ACCESS  read-only
    STATUS      current
    DESCRIPTION
        "Type of the physical port:
            unknown     Unknown port type.
            eth         Ethernet.
            ct3         Channelized T3.
            oc3c        OC-3c (SONET/SDH).
            ut3Atm      Unchannelized T3 (ATM service).
            ut3Frame    Unchannelized T3 (Frame service).
            ue3Atm      Unchannelized E3 (ATM service).
            ue3Frame    Unchannelized E3 (Frame service).
            ce1         Channelized   E1.
            ct1         Channelized   T1.
            oc12Pos     OC-12 (POS/SDH).
            oc12Atm     OC-12 (ATM service).
            oc3Pos      OC-3 (POS/SDH).
            oc3Atm      OC-3 (ATM service).
            coc3        Channelized OC-3.
            coc12       Channelized OC-12.
            oc12Server  OC-12 (Server card).
            hssi        High Speed Serial Interface.
            v35         X.21/V.35."
    ::= { usdERXSysPortEntry 3 }

usdERXSysPortIfIndex OBJECT-TYPE
    SYNTAX      InterfaceIndexOrZero
    MAX-ACCESS  read-only
    STATUS      current
    DESCRIPTION
        "The ifIndex of the Interfaces MIB ifTable entry corresponding to this
        physical port; if zero, the ifIndex is unknown or does not exist."
    ::= { usdERXSysPortEntry 4 }


-- +++++++++++++++++++++++++++++++++++++++++++++++++++++++++++++++++++++++++++++
--
-- System Power objects
--
-- +++++++++++++++++++++++++++++++++++++++++++++++++++++++++++++++++++++++++++++
usdERXSysPowerTable OBJECT-TYPE
    SYNTAX      SEQUENCE OF UsdERXSysPowerEntry
    MAX-ACCESS  not-accessible
    STATUS      current
    DESCRIPTION
        "Table of system power elements."
    ::= { usdERXSysPower 1 }

usdERXSysPowerEntry OBJECT-TYPE
    SYNTAX      UsdERXSysPowerEntry
    MAX-ACCESS  not-accessible
    STATUS      current
    DESCRIPTION
        "A table entry describing status of a system power element."
    INDEX     { usdERXSysPowerIndex }
    ::= {usdERXSysPowerTable 1 }

UsdERXSysPowerEntry ::= SEQUENCE {
    usdERXSysPowerIndex  Integer32,
    usdERXSysPowerDescr  DisplayString,
    usdERXSysPowerStatus INTEGER }

usdERXSysPowerIndex OBJECT-TYPE
    SYNTAX      Integer32 (0..255)
    MAX-ACCESS  not-accessible
    STATUS      current
    DESCRIPTION
        "Arbitrary integer index to distinguish entries in this table."
    ::= { usdERXSysPowerEntry 1 }

usdERXSysPowerDescr OBJECT-TYPE
    SYNTAX      DisplayString (SIZE(0..63))
    MAX-ACCESS  read-only
    STATUS      current
    DESCRIPTION
        "Textual description of this power element."
    ::= { usdERXSysPowerEntry 2 }

usdERXSysPowerStatus OBJECT-TYPE
    SYNTAX      INTEGER {
                    inactive(0),
                    active(1) }
    MAX-ACCESS  read-only
    STATUS      current
    DESCRIPTION
        "The status of the power element:
            inactive    No power available from this element.
            active      Power available from this element."
    ::= { usdERXSysPowerEntry 3 }


-- +++++++++++++++++++++++++++++++++++++++++++++++++++++++++++++++++++++++++++++
--
-- System Temp objects
--
-- +++++++++++++++++++++++++++++++++++++++++++++++++++++++++++++++++++++++++++++
usdERXSysTempFanStatus OBJECT-TYPE
    SYNTAX      INTEGER {
                    failed(0),
                    ok(1),
                    warning(2) }
    MAX-ACCESS  read-only
    STATUS      current
    DESCRIPTION
        "Status of fan subsystem.
            ok          All components operational
            warning     The fan subsystem has a non-critical failure.
            failed      The fan subsystem has a critical failure, or has been
                        removed, and is now non-operational."
    ::= { usdERXSysTemperature 1 }


usdERXSysTempTable OBJECT-TYPE
    SYNTAX      SEQUENCE OF UsdERXSysTempEntry
    MAX-ACCESS  not-accessible
    STATUS      current
    DESCRIPTION
        "Table of system temperature sensors.

        Sensors are distributed across the chassis, at least one sensor per
        populated slot."
    ::= { usdERXSysTemperature 2 }

usdERXSysTempEntry OBJECT-TYPE
    SYNTAX      UsdERXSysTempEntry
    MAX-ACCESS  not-accessible
    STATUS      current
    DESCRIPTION
        "A table entry describing status of a temperature sensor."
    INDEX     { usdERXSysSlotIndex,
                usdERXSysTempIndex }
    ::= {usdERXSysTempTable 1 }

UsdERXSysTempEntry ::= SEQUENCE {
    usdERXSysTempIndex   Integer32,
    usdERXSysTempDescr   DisplayString,
    usdERXSysTempStatus  INTEGER,
    usdERXSysTempValue   Integer32 }

usdERXSysTempIndex OBJECT-TYPE
    SYNTAX      Integer32 (0..255)
    MAX-ACCESS  not-accessible
    STATUS      current
    DESCRIPTION
        "Arbitrary integer index to distinguish sensors associated with the same
        chassis slot."
    ::= { usdERXSysTempEntry 1 }

usdERXSysTempDescr OBJECT-TYPE
    SYNTAX      DisplayString (SIZE(0..63))
    MAX-ACCESS  read-only
    STATUS      current
    DESCRIPTION
        "Textual description of this sensor."
    ::= { usdERXSysTempEntry 2 }

usdERXSysTempStatus OBJECT-TYPE
    SYNTAX      INTEGER {
                    unknown(0),
                    failed(1),
                    tooLow(2),
                    nominal(3),
                    tooHigh(4),
                    tooLowWarning(5),
                    tooHighWarning(6) }
    MAX-ACCESS  read-only
    STATUS      current
    DESCRIPTION
        "The status of a temperature sensor:
            unknown         unknown
            failed          failed
            tooLow          below nominal range
            nominal         within nominal range
            tooHigh         above nominal range
            tooLowWarning   near lower limit
            tooHighWarning  near upper limit"
    ::= { usdERXSysTempEntry 3 }

usdERXSysTempValue OBJECT-TYPE
    SYNTAX      Integer32
    UNITS       "degrees Celsius"
    MAX-ACCESS  read-only
    STATUS      current
    DESCRIPTION
        "The temperature measured by this sensor in degrees Celsius.  This
        measurement is valid only if the value of the corresponding
        usdERXSysTempStatus is nominal."
    ::= { usdERXSysTempEntry 4 }

usdERXSysTempProtectionStatus OBJECT-TYPE
    SYNTAX      INTEGER {
                    monitoring(1),
                    inHoldOff(2),
                    activatedHoldOffExpired(3),
                    activatedTempTooHigh(4) }
    MAX-ACCESS  read-only
    STATUS      current
    DESCRIPTION
        "Thermal protection status:
            monitoring                  monitoring
            inHoldOff                   hold off time has begun
            activatedHoldOffExpired     hold off time has expired, the system
                                        is in thermal protection mode
            activatedTempTooHigh        temperature too high, the system is in
                                        thermal protection mode "
    ::= { usdERXSysTemperature 3 }

usdERXSysTempProtectionHoldOffTime OBJECT-TYPE
    SYNTAX      Integer32 (0..1200)
    UNITS       "seconds"
    MAX-ACCESS  read-only
    STATUS      current
    DESCRIPTION
        "The time, in seconds, before the system enters thermal protection mode
        after a critical fan subsystem failure is detected."
    DEFVAL    { 150 }
    ::= { usdERXSysTemperature 4 }

usdERXSysTempProtectionHoldOffTimeRemaining OBJECT-TYPE
    SYNTAX      Integer32 (0..1200)
    UNITS       "seconds"
    MAX-ACCESS  read-only
    STATUS      current
    DESCRIPTION
        "The time remaining, in seconds, before the system enters thermal
        protection mode while the thermal protection status is set to inHoldOff.
        The value decrements every second until it reaches zero, and the status
        changes to activatedHoldOffExpired.  When the thermal protection status
        is not inHoldOff or activatedHoldOffExpired, the value is set to the
        hold off time."
    DEFVAL    { 150 }
    ::= { usdERXSysTemperature 5 }


-- +++++++++++++++++++++++++++++++++++++++++++++++++++++++++++++++++++++++++++++
--
-- Subsystem objects
--
-- +++++++++++++++++++++++++++++++++++++++++++++++++++++++++++++++++++++++++++++
usdERXSysSubsystemTable OBJECT-TYPE
    SYNTAX      SEQUENCE OF UsdERXSysSubsystemEntry
    MAX-ACCESS  not-accessible
    STATUS      current
    DESCRIPTION
        "Table of subsystems."
    ::= { usdERXSysSubsystem 1 }

usdERXSysSubsystemEntry OBJECT-TYPE
    SYNTAX      UsdERXSysSubsystemEntry
    MAX-ACCESS  not-accessible
    STATUS      current
    DESCRIPTION
        "A table entry containing information pertaining to a subsystem."
    INDEX     { usdERXSysSubsystemIndex }
    ::= {usdERXSysSubsystemTable 1 }

UsdERXSysSubsystemEntry ::= SEQUENCE {
    usdERXSysSubsystemIndex                  Integer32,
    usdERXSysSubsystemName                   DisplayString,
    usdERXSysSubsystemControl                INTEGER,
    usdERXSysSubsystemBootReleaseFile        DisplayString,
    usdERXSysSubsystemBootBackupReleaseFile  DisplayString }

usdERXSysSubsystemIndex OBJECT-TYPE
    SYNTAX      Integer32 (0..255)
    MAX-ACCESS  not-accessible
    STATUS      current
    DESCRIPTION
        "Subsystem number."
    ::= { usdERXSysSubsystemEntry 1 }

usdERXSysSubsystemName OBJECT-TYPE
    SYNTAX      DisplayString (SIZE(0..128))
    MAX-ACCESS  read-only
    STATUS      current
    DESCRIPTION
        "The name of the subsystem."
    ::= { usdERXSysSubsystemEntry 2 }

usdERXSysSubsystemControl OBJECT-TYPE
    SYNTAX      INTEGER {
                    noOperation(0),
                    noBoot(1),
                    noBootBackup(2) }
    MAX-ACCESS  read-write
    STATUS      current
    DESCRIPTION
        "Administrative control of this subsystem:
            noOperation     Setting this value has no effect.
            noBoot          Deconfigure primary release file for the subsystem.
            noBootBackup    Deconfigure backup release file for the subsystem."
    ::= { usdERXSysSubsystemEntry 3 }

usdERXSysSubsystemBootReleaseFile OBJECT-TYPE
    SYNTAX      DisplayString (SIZE(0..128))
    MAX-ACCESS  read-write
    STATUS      current
    DESCRIPTION
        "The local boot release file name for this subsystem, with extension
        .rel."
    DEFVAL    { "" }
    ::= { usdERXSysSubsystemEntry 4 }

usdERXSysSubsystemBootBackupReleaseFile OBJECT-TYPE
    SYNTAX      DisplayString (SIZE(0..128))
    MAX-ACCESS  read-write
    STATUS      current
    DESCRIPTION
        "The local backup boot release file name for this subsystem, with
        extension .rel."
    DEFVAL    { "" }
    ::= { usdERXSysSubsystemEntry 5 }


-- +++++++++++++++++++++++++++++++++++++++++++++++++++++++++++++++++++++++++++++
-- Traps & Trap Control
-- +++++++++++++++++++++++++++++++++++++++++++++++++++++++++++++++++++++++++++++
-- The usdERXSysTrap OBJECT IDENTIFIER is used to define SNMPv2
-- Notifications that are easily translated into SNMPv1 Traps.

usdERXSysSlotOperStatusChange NOTIFICATION-TYPE
    OBJECTS {
        usdERXSysSlotCurrentCardType,
        usdERXSysSlotAdminStatus,
        usdERXSysSlotOperStatus,
        usdERXSysSlotDisableReason,
        usdERXSysSlotSpareServer,
        usdERXSysSlotAssociatedSlot,
        usdERXSysSlotDescr }
    STATUS      current
    DESCRIPTION
        "Reports a status change for a slot.

        This trap is generated on a transition into a stable state (online or
        disabled) or on a transition out of online."
    ::= { usdERXSysTrap 1 }

usdERXSysPowerStatusChange NOTIFICATION-TYPE
    OBJECTS {
        usdERXSysPowerStatus }
    STATUS      current
    DESCRIPTION
        "Reports a change in the status of a power element."
    ::= { usdERXSysTrap 2 }

usdERXSysTempFanStatusChange NOTIFICATION-TYPE
    OBJECTS {
        usdERXSysTempFanStatus }
    STATUS      current
    DESCRIPTION
        "Reports a transition between the three states of the fan subsystem.
        When the fan subsystem transitions to the failed state the thermal
        protection hold off time begins."
    ::= { usdERXSysTrap 3 }

usdERXSysTempStatusChange NOTIFICATION-TYPE
    OBJECTS {
        usdERXSysTempStatus }
    STATUS      current
    DESCRIPTION
        "Reports a change in the temperature status.  When the status
        transitions to the tooHigh state the system enters thermal protection
        mode."
    ::= { usdERXSysTrap 4 }

usdERXSysHighMemUtil NOTIFICATION-TYPE
    OBJECTS {
        usdERXSysMemCapacity,
        usdERXSysMemUtilPct,
        usdERXSysAbatedMemUtilThreshold,
        usdERXSysHighMemUtilThreshold }
    STATUS      current
    DESCRIPTION
        "Report system memory utilization has met the conditions of
        usdERXSysHighMemUtilThreshold."
    ::= { usdERXSysTrap 5 }

usdERXSysAbatedMemUtil NOTIFICATION-TYPE
    OBJECTS {
        usdERXSysMemCapacity,
        usdERXSysMemUtilPct,
        usdERXSysAbatedMemUtilThreshold,
        usdERXSysHighMemUtilThreshold }
    STATUS      current
    DESCRIPTION
        "Reports system memory utilization has met the conditions of
        usdERXSysAbatedMemUtilThreshold."
    ::= { usdERXSysTrap 6 }

usdERXSysTempProtectionStatusChange NOTIFICATION-TYPE
    OBJECTS {
        usdERXSysTempProtectionStatus,
        usdERXSysTempProtectionHoldOffTimeRemaining }
    STATUS      current
    DESCRIPTION
        "Notification about changes in the state of Thermal Protection.  This
        notification is sent when the tempProtectionStatus changes.  It is also
        sent when the holdOffTimeRemaining is 50% of the holdOffTime."
    ::= { usdERXSysTrap 7 }


-- +++++++++++++++++++++++++++++++++++++++++++++++++++++++++++++++++++++++++++++
-- Conformance information
-- +++++++++++++++++++++++++++++++++++++++++++++++++++++++++++++++++++++++++++++
usdERXSysCompliances OBJECT IDENTIFIER ::= { usdERXSysConformance 1 }
usdERXSysGroups      OBJECT IDENTIFIER ::= { usdERXSysConformance 2 }

--
-- compliance statements
--
usdERXSysCompliance MODULE-COMPLIANCE
    STATUS      obsolete
    DESCRIPTION
        "Obsolete compliance statement for entities which implement the ERX
        System MIB.  This compliance statement became obsolete when new slot
        information objects were added."
    MODULE   -- this module
        MANDATORY-GROUPS {
            usdERXSysGroup,
            usdERXSysNotifyGroup }
    ::= { usdERXSysCompliances 1 }                                     -- RX 1.3

usdERXSysCompliance1 MODULE-COMPLIANCE
    STATUS      obsolete
    DESCRIPTION
        "Obsolete compliance statement for entities which implement the ERX
        System MIB.  This compliance statement became obsolete when the timing
        group was added."
    MODULE -- this module
        MANDATORY-GROUPS {
            usdERXSysGeneralGroup,
            usdERXSysFabricGroup,
            usdERXSysNvsGroup,
            usdERXSysSlotGroup,
            usdERXSysPortGroup,
            usdERXSysPowerGroup,
            usdERXSysTemperatureGroup,
            usdERXSysSubsystemGroup,
            usdERXSysNotifyGroup }
    ::= { usdERXSysCompliances 2 }                                     -- RX 2.0

usdERXSysCompliance2 MODULE-COMPLIANCE
    STATUS      obsolete
    DESCRIPTION
        "Obsolete compliance statement for entities which implement the ERX
        System MIB.  This compliance statement became obsolete when new memory
        information objects and notifications were added."
    MODULE -- this module
        MANDATORY-GROUPS {
            usdERXSysGeneralGroup,
            usdERXSysTimingGroup,
            usdERXSysFabricGroup,
            usdERXSysNvsGroup,
            usdERXSysSlotGroup,
            usdERXSysPortGroup,
            usdERXSysPowerGroup,
            usdERXSysTemperatureGroup,
            usdERXSysSubsystemGroup,
            usdERXSysNotifyGroup }
    ::= { usdERXSysCompliances 3 }                                     -- RX 3.0

usdERXSysCompliance3 MODULE-COMPLIANCE
    STATUS      obsolete
    DESCRIPTION
        "Obsolete compliance statement for entities which implement the ERX
        System MIB.  This compliance statement became obsolete when new system
        temperature information objects and notifications were added."
    MODULE -- this module
        MANDATORY-GROUPS {
            usdERXSysGeneralGroup2,
            usdERXSysTimingGroup,
            usdERXSysFabricGroup,
            usdERXSysNvsGroup,
            usdERXSysSlotGroup,
            usdERXSysPortGroup,
            usdERXSysPowerGroup,
            usdERXSysTemperatureGroup,
            usdERXSysSubsystemGroup,
            usdERXSysNotifyGroup2 }
    ::= { usdERXSysCompliances 4 }                                     -- RX 3.2

usdERXSysCompliance4 MODULE-COMPLIANCE
    STATUS      current
    DESCRIPTION
        "The compliance statement for entities which implement the ERX System
        MIB."
    MODULE -- this module
        MANDATORY-GROUPS {
            usdERXSysGeneralGroup2,
            usdERXSysTimingGroup,
            usdERXSysFabricGroup,
            usdERXSysNvsGroup,
            usdERXSysSlotGroup,
            usdERXSysPortGroup,
            usdERXSysPowerGroup,
            usdERXSysTemperatureGroup2,
            usdERXSysSubsystemGroup,
            usdERXSysNotifyGroup3 }
    ::= { usdERXSysCompliances 5 }                                     -- RX 3.3

--
-- units of conformance
--
usdERXSysGroup OBJECT-GROUP
    OBJECTS {
        -- General chassis objects
        usdERXSysChassisRev,
        usdERXSysSwVersion,
        usdERXSysSwBuildDate,
        usdERXSysRevertControl,
        usdERXSysRevertTimeOfDay,
        usdERXSysBootConfigControl,
        usdERXSysBootBackupConfigControl,
        usdERXSysBootForceBackupControl,
        usdERXSysBootAutoRevertControl,
        usdERXSysBootAutoRevertCountTolerance,
        usdERXSysBootAutoRevertTimeTolerance,
        usdERXSysBootReleaseFile,
        usdERXSysBootConfigFile,
        usdERXSysBootBackupReleaseFile,
        usdERXSysBootBackupConfigFile,

        -- Fabric objects
        usdERXSysFabricSpeed,
        usdERXSysFabricRev,

        -- NVS objects
        usdERXSysNvsStatus,
        usdERXSysNvsCapacity,
        usdERXSysNvsUtilPct,

        -- Slot objects
        usdERXSysSlotCount,
        usdERXSysSlotDescr,
        usdERXSysSlotCurrentCardType,
        usdERXSysSlotRev,
        usdERXSysSlotAdminStatus,
        usdERXSysSlotOperStatus,
        usdERXSysSlotDisableReason,
        usdERXSysSlotExpectedCardType,
        usdERXSysSlotControl,
        usdERXSysSlotCpuUtilPct,
        usdERXSysSlotMemUtilPct,
        usdERXSysSlotIoaPresent,
        usdERXSysSlotPortCount,
        usdERXSysSlotLastChange,
        usdERXSysSlotRedundancyLockout,
        usdERXSysSlotRedundancyGroupId,
        usdERXSysSlotSpareServer,
        usdERXSysSlotAssociatedSlot,
        usdERXSysSlotRevertControl,
        usdERXSysSlotRedundancyRevertTime,
        usdERXSysSlotBootReleaseFile,
        usdERXSysSlotBootBackupReleaseFile,

        -- Port objects
        usdERXSysPortDescr,
        usdERXSysPortType,
        usdERXSysPortIfIndex,

        -- Power objects
        usdERXSysPowerDescr,
        usdERXSysPowerStatus,

        -- Temperature objects
        usdERXSysTempFanStatus,
        usdERXSysTempDescr,
        usdERXSysTempStatus,
        usdERXSysTempValue,

        -- Subsystem objects
        usdERXSysSubsystemName,
        usdERXSysSubsystemControl,
        usdERXSysSubsystemBootReleaseFile,
        usdERXSysSubsystemBootBackupReleaseFile }
    STATUS      obsolete
    DESCRIPTION
        "Obsolete collection of management objects pertaining to system
        capabilities in a Juniper product.  This group became obsolete when new
        slot information objects were added."
    ::= { usdERXSysGroups 1 }

usdERXSysNotifyGroup NOTIFICATION-GROUP
    NOTIFICATIONS {
        usdERXSysSlotOperStatusChange,
        usdERXSysPowerStatusChange,
        usdERXSysTempFanStatusChange,
        usdERXSysTempStatusChange }
    STATUS      obsolete
    DESCRIPTION
        "Obsolete collection of management notifications pertaining to system
        operations in a Juniper product.  This group became obsolete when new
        memory threshold notificaitons were added."
    ::= { usdERXSysGroups 2 }

usdERXSysGeneralGroup OBJECT-GROUP
    OBJECTS {
        usdERXSysChassisRev,
        usdERXSysSwVersion,
        usdERXSysSwBuildDate,
        usdERXSysRevertControl,
        usdERXSysRevertTimeOfDay,
        usdERXSysBootConfigControl,
        usdERXSysBootBackupConfigControl,
        usdERXSysBootForceBackupControl,
        usdERXSysBootAutoRevertControl,
        usdERXSysBootAutoRevertCountTolerance,
        usdERXSysBootAutoRevertTimeTolerance,
        usdERXSysBootReleaseFile,
        usdERXSysBootConfigFile,
        usdERXSysBootBackupReleaseFile,
        usdERXSysBootBackupConfigFile }
    STATUS      obsolete
    DESCRIPTION
        "Obsolete collection of management objects pertaining to general system
        capabilities in a Juniper product.  This group became obsolete when new
        memory management objects were added."
   ::= { usdERXSysGroups 3 }

usdERXSysFabricGroup OBJECT-GROUP
    OBJECTS {
        usdERXSysFabricSpeed,
        usdERXSysFabricRev }
    STATUS      current
    DESCRIPTION
        "A collection of management objects pertaining to system fabric
        capabilities in a Juniper product."
    ::= { usdERXSysGroups 4 }

usdERXSysNvsGroup OBJECT-GROUP
    OBJECTS {
        usdERXSysNvsStatus,
        usdERXSysNvsCapacity,
        usdERXSysNvsUtilPct }
    STATUS      current
    DESCRIPTION
        "A collection of management objects pertaining to non-volitile storage
        subsystem capabilities in a Juniper product."
    ::= { usdERXSysGroups 5 }

usdERXSysSlotGroup OBJECT-GROUP
    OBJECTS {
        usdERXSysSlotCount,
        usdERXSysSlotDescr,
        usdERXSysSlotCurrentCardType,
        usdERXSysSlotRev,
        usdERXSysSlotAdminStatus,
        usdERXSysSlotOperStatus,
        usdERXSysSlotDisableReason,
        usdERXSysSlotExpectedCardType,
        usdERXSysSlotControl,
        usdERXSysSlotCpuUtilPct,
        usdERXSysSlotMemUtilPct,
        usdERXSysSlotIoaPresent,
        usdERXSysSlotPortCount,
        usdERXSysSlotLastChange,
        usdERXSysSlotRedundancyLockout,
        usdERXSysSlotRedundancyGroupId,
        usdERXSysSlotSpareServer,
        usdERXSysSlotAssociatedSlot,
        usdERXSysSlotRevertControl,
        usdERXSysSlotRedundancyRevertTime,
        usdERXSysSlotBootReleaseFile,
        usdERXSysSlotBootBackupReleaseFile,
        usdERXSysSlotSerialNumber,
        usdERXSysSlotAssemblyPartNumber,
        usdERXSysSlotAssemblyRev,
        usdERXSysSlotIoaSerialNumber,
        usdERXSysSlotIoaAssemblyPartNumber,
        usdERXSysSlotIoaAssemblyRev }
    STATUS      current
    DESCRIPTION
        "A collection of management objects pertaining to slot-specific system
        capabilities in a Juniper product."
    ::= { usdERXSysGroups 6 }

usdERXSysPortGroup OBJECT-GROUP
    OBJECTS {
        usdERXSysPortDescr,
        usdERXSysPortType,
        usdERXSysPortIfIndex }
    STATUS      current
    DESCRIPTION
        "A collection of management objects pertaining to port-related system
        capabilities in a Juniper product."
    ::= { usdERXSysGroups 7 }

usdERXSysPowerGroup OBJECT-GROUP
    OBJECTS {
        usdERXSysPowerDescr,
        usdERXSysPowerStatus }
    STATUS      current
    DESCRIPTION
        "A collection of management objects pertaining to the power subsystem
        capabilities in a Juniper product."
    ::= { usdERXSysGroups 8 }

usdERXSysTemperatureGroup OBJECT-GROUP
    OBJECTS {
        usdERXSysTempFanStatus,
        usdERXSysTempDescr,
        usdERXSysTempStatus,
        usdERXSysTempValue }
    STATUS      obsolete
    DESCRIPTION
        "Obsolete collection of management objects pertaining to system
        temperature monitoring capabilities in a Juniper product.  This group
        became obsolete when temperature shutdown parameters were added."
    ::= { usdERXSysGroups 9 }

usdERXSysSubsystemGroup OBJECT-GROUP
    OBJECTS {
        usdERXSysSubsystemName,
        usdERXSysSubsystemControl,
        usdERXSysSubsystemBootReleaseFile,
        usdERXSysSubsystemBootBackupReleaseFile }
    STATUS      current
    DESCRIPTION
        "A collection of management objects pertaining to subsystem capabilities
        in a Juniper product."
    ::= { usdERXSysGroups 10 }

usdERXSysTimingGroup OBJECT-GROUP
    OBJECTS {
        usdERXSysAdminTimingSource,
        usdERXSysOperTimingSource,
        usdERXSysTimingDisableAutoUpgrade,

        usdERXSysTimingSourceType,
        usdERXSysTimingSourceIfIndex,
        usdERXSysTimingSourceLine,
        usdERXSysTimingStatus }
    STATUS      current
    DESCRIPTION
        "A collection of management objects pertaining to system timing
        capabilities in a Juniper product."
    ::= { usdERXSysGroups 11 }

usdERXSysGeneralGroup2 OBJECT-GROUP
    OBJECTS {
        usdERXSysChassisRev,
        usdERXSysSwVersion,
        usdERXSysSwBuildDate,
        usdERXSysRevertControl,
        usdERXSysRevertTimeOfDay,
        usdERXSysBootConfigControl,
        usdERXSysBootBackupConfigControl,
        usdERXSysBootForceBackupControl,
        usdERXSysBootAutoRevertControl,
        usdERXSysBootAutoRevertCountTolerance,
        usdERXSysBootAutoRevertTimeTolerance,
        usdERXSysBootReleaseFile,
        usdERXSysBootConfigFile,
        usdERXSysBootBackupReleaseFile,
        usdERXSysBootBackupConfigFile,
        usdERXSysMemUtilPct,
        usdERXSysMemCapacity,
        usdERXSysHighMemUtilThreshold,
        usdERXSysAbatedMemUtilThreshold,
        usdERXSysMemUtilTrapEnable }
    STATUS      current
    DESCRIPTION
        "A collection of management objects pertaining to general system
        capabilities in a Juniper product."
   ::= { usdERXSysGroups 12 }

usdERXSysNotifyGroup2 NOTIFICATION-GROUP
    NOTIFICATIONS {
        usdERXSysSlotOperStatusChange,
        usdERXSysPowerStatusChange,
        usdERXSysTempFanStatusChange,
        usdERXSysTempStatusChange,
        usdERXSysHighMemUtil,
        usdERXSysAbatedMemUtil }
    STATUS      obsolete
    DESCRIPTION
        "Obsolete collection of management notifications pertaining to system
        operations in a Juniper product.  This group became obsolete when the
        tempProtectionStatusChange notification was added."
    ::= { usdERXSysGroups 13 }

usdERXSysTemperatureGroup2 OBJECT-GROUP
    OBJECTS {
        usdERXSysTempFanStatus,
        usdERXSysTempDescr,
        usdERXSysTempStatus,
        usdERXSysTempValue,
        usdERXSysTempProtectionStatus,
        usdERXSysTempProtectionHoldOffTime,
        usdERXSysTempProtectionHoldOffTimeRemaining }
    STATUS      current
    DESCRIPTION
        "A collection of management objects pertaining to system temperature
        monitoring capabilities in a Juniper product."
    ::= { usdERXSysGroups 14 }

usdERXSysNotifyGroup3 NOTIFICATION-GROUP
    NOTIFICATIONS {
        usdERXSysSlotOperStatusChange,
        usdERXSysPowerStatusChange,
        usdERXSysTempFanStatusChange,
        usdERXSysTempStatusChange,
        usdERXSysHighMemUtil,
        usdERXSysAbatedMemUtil,
        usdERXSysTempProtectionStatusChange }
    STATUS      current
    DESCRIPTION
        "A collection of management notifications pertaining to system
        operations in a Juniper product."
    ::= { usdERXSysGroups 15 }

END
