-- *****************************************************************
-- REDSTONE-RXSYS-MIB
--
-- Redstone Communications Inc. Enterprise MIB
-- RX1400/RX700 System MIB
--
-- Copyright 1998-1999 Redstone Communications, Incorporated.
-- All Rights Reserved.
-- *****************************************************************

REDSTONE-RXSYS-MIB DEFINITIONS ::= BEGIN

IMPORTS
	TEXTUAL-CONVENTION FROM SNMPv2-TC
    MODULE-IDENTITY,
    OBJECT-TYPE,
    NOTIFICATION-TYPE,
    Integer32,
    TimeTicks
        FROM SNMPv2-SMI

    DisplayString,
    TruthValue
        FROM SNMPv2-TC

    MODULE-COMPLIANCE,
    OBJECT-GROUP
        FROM SNMPv2-CONF

    InterfaceIndexOrZero
        FROM IF-MIB

    rsMgmt
        FROM REDSTONE-SMI

    RsEnable
        FROM REDSTONE-TC;

rsRXSysMIB  MODULE-IDENTITY
    LAST-UPDATED "9907120000Z"
    ORGANIZATION "Redstone Communications, Inc."
    CONTACT-INFO
            "Redstone Communications, Inc.

            5 Carlisle Road
            Westford MA 01886
            USA

            +1-978-692-1999

            mib@redstonecom.com"
    DESCRIPTION
        "Added 'ct1' enumeration to RsSysCardType and rsRxSysPortType."
    REVISION      "9907120000Z"
    DESCRIPTION
        "MIB objects for managing RX1400/RX700 systems."
    REVISION      "9907020000Z"
    DESCRIPTION
        "Added 'ce1' enumeration to RsSysCardType and rsRxSysPortType."
    REVISION      "9904220000Z"
    DESCRIPTION
        "Added new enumerations to RsSysCardType and rsRxSysPortType."
    REVISION      "9801010000Z"
    DESCRIPTION
        "Initial version of this MIB module."
    ::= { rsMgmt 17 }

-- ++++++++++++++++++++++++++++++++++++++++++++++++++++++++++++++++++++++
-- Textual conventions
-- ++++++++++++++++++++++++++++++++++++++++++++++++++++++++++++++++++++++


-- ++++++++++++++++++++++++++++++++++++++++++++++++++++++++++++++++++++++
-- MIB Structure
-- ++++++++++++++++++++++++++++++++++++++++++++++++++++++++++++++++++++++

rsRXSysTrap          OBJECT IDENTIFIER ::= { rsRXSysMIB 0 }
rsRXSysObjects       OBJECT IDENTIFIER ::= { rsRXSysMIB 1 }
rsRXSysConformance   OBJECT IDENTIFIER ::= { rsRXSysMIB 2 }

-- ++++++++++++++++++++++++++++++++++++++++++++++++++++++++++++++++++++++
-- Managed objects
-- ++++++++++++++++++++++++++++++++++++++++++++++++++++++++++++++++++++++

--
-- Object Groups
--
rsRXSysGeneral       OBJECT IDENTIFIER ::= { rsRXSysObjects 1 }
rsRXSysFabric        OBJECT IDENTIFIER ::= { rsRXSysObjects 2 }
rsRXSysNvs           OBJECT IDENTIFIER ::= { rsRXSysObjects 3 }
rsRXSysSlot          OBJECT IDENTIFIER ::= { rsRXSysObjects 4 }
rsRXSysPort          OBJECT IDENTIFIER ::= { rsRXSysObjects 5 }
rsRXSysPower         OBJECT IDENTIFIER ::= { rsRXSysObjects 6 }
rsRXSysTemperature   OBJECT IDENTIFIER ::= { rsRXSysObjects 7 }


-- ++++++++++++++++++++++++++++++++++++++++++++++++++++++++++++++++++++++
-- Textual conventions
-- ++++++++++++++++++++++++++++++++++++++++++++++++++++++++++++++++++++++

RsSysCardType ::= TEXTUAL-CONVENTION
    STATUS      current
    DESCRIPTION
        "The type of card in a system slot:

        unknown     Unknown type.
        srp         Switch/Route Processor.
        ct3         Channelized T3.
        oc3         OC-3 (SONET/SDH).
        ut3Atm      Unchannelized T3 (ATM service).
        ut3Frame    Unchannelized T3 (Frame service).
        ue3Atm      Unchannelized E3 (ATM service).
        ue3Frame    Uncahnnelized E3 (Frame service).
        ce1         Channelized   E1.
        ct1         Channelized   T1."
    SYNTAX  INTEGER {
                unknown(0),
                srp(1),
                ct3(2),
                oc3(3),
                ut3Atm(4),
                ut3Frame(5),
                ue3Atm(6),
                ue3Frame(7),
                ce1(8),
                ct1(9)
            }
    

-- +++++++++++++++++++++++++++++++++++++++++++++++++++++++++++++++++++++++++++++
-- 
-- Chassis objects
-- 
-- +++++++++++++++++++++++++++++++++++++++++++++++++++++++++++++++++++++++++++++

rsRXSysChassisRev OBJECT-TYPE
    SYNTAX      Integer32(0..255)
    MAX-ACCESS  read-only
    STATUS      current
    DESCRIPTION
        "Chassis revision number. If unknown, the value 255 is reported."
    ::= { rsRXSysGeneral 1 }

rsRXSysSwVersion OBJECT-TYPE
    SYNTAX      DisplayString
    MAX-ACCESS  read-only
    STATUS      current
    DESCRIPTION
        "Currently executing operational software version."
    ::= { rsRXSysGeneral 2 }

rsRXSysSwBuildDate OBJECT-TYPE
    SYNTAX      DisplayString
    MAX-ACCESS  read-only
    STATUS      current
    DESCRIPTION
        "Build date of currently executing operational software version."
    ::= { rsRXSysGeneral 3 }

-- +++++++++++++++++++++++++++++++++++++++++++++++++++++++++++++++++++++++++++++
-- 
-- Fabric objects
-- 
-- +++++++++++++++++++++++++++++++++++++++++++++++++++++++++++++++++++++++++++++

rsRXSysFabricSpeed OBJECT-TYPE
    SYNTAX      Integer32
    UNITS       "gigabits per second"
    MAX-ACCESS  read-only
    STATUS      current
    DESCRIPTION
        "Speed of switching fabric, in gigabits per second."
    ::= { rsRXSysFabric 1 }

rsRXSysFabricRev OBJECT-TYPE
    SYNTAX      Integer32(0..255)
    MAX-ACCESS  read-only
    STATUS      current
    DESCRIPTION
        "Fabric revision number. If unknown, the value 255 is reported."
    ::= { rsRXSysFabric 2 }

-- +++++++++++++++++++++++++++++++++++++++++++++++++++++++++++++++++++++++++++++
-- 
-- Nvs objects
-- 
-- +++++++++++++++++++++++++++++++++++++++++++++++++++++++++++++++++++++++++++++

rsRXSysNvsStatus OBJECT-TYPE
    SYNTAX      INTEGER {
                    notPresent(0),
                    writeProtected(1),
                    volumeError(2),
                    nearCapacity(3),
                    ok(4)
                }
    MAX-ACCESS  read-only
    STATUS      current
    DESCRIPTION
        "Status of non-volatile storage (NVS):

        notPresent          NVS is not installed.
        writeProtected      NVS is write-protected.
        volumeError         Status poll of NVS failed.
        nearCapacity        Utilization exceeds 85% of NVS capacity.
        ok                  NVS is operational, none of the preceding
                            conditions apply."
    ::= { rsRXSysNvs 1 }

rsRXSysNvsCapacity OBJECT-TYPE
    SYNTAX      Integer32
    UNITS       "megabytes"
    MAX-ACCESS  read-only
    STATUS      current
    DESCRIPTION
        "Capacity of NVS storage in megabytes."
    ::= { rsRXSysNvs 2 }

rsRXSysNvsUtilPct OBJECT-TYPE
    SYNTAX      Integer32(-1..100)
    UNITS       "percent"
    MAX-ACCESS  read-only
    STATUS      current
    DESCRIPTION
        "Percentage of NVS storage used.

        A value of -1 indicates NVS utilization is unknown."
    ::= { rsRXSysNvs 3 }

-- +++++++++++++++++++++++++++++++++++++++++++++++++++++++++++++++++++++++++++++
--
-- Slot objects
--
-- +++++++++++++++++++++++++++++++++++++++++++++++++++++++++++++++++++++++++++++

rsRXSysSlotCount OBJECT-TYPE
    SYNTAX      Integer32
    MAX-ACCESS  read-only
    STATUS      current
    DESCRIPTION
        "The number of slots in the system."
    ::= { rsRXSysSlot 1 }

rsRXSysSlotTable OBJECT-TYPE
    SYNTAX      SEQUENCE OF RsSysSlotEntry
    MAX-ACCESS  not-accessible
    STATUS      current
    DESCRIPTION
        "Table of system slots."
    ::= { rsRXSysSlot 2 }

rsRXSysSlotEntry OBJECT-TYPE
    SYNTAX      RsSysSlotEntry
    MAX-ACCESS  not-accessible
    STATUS      current
    DESCRIPTION
        "A table entry describing contents of a system slot."
    INDEX   { rsRXSysSlotIndex }
    ::= {rsRXSysSlotTable 1 }

RsSysSlotEntry ::= SEQUENCE {
    rsRXSysSlotIndex                  Integer32,
    rsRXSysSlotDescr                  DisplayString,
    rsRXSysSlotCurrentCardType        RsSysCardType,
    rsRXSysSlotRev                    Integer32,
    rsRXSysSlotAdminStatus            RsEnable,
    rsRXSysSlotOperStatus             INTEGER,
    rsRXSysSlotDisableReason          INTEGER,
    rsRXSysSlotExpectedCardType       RsSysCardType,
    rsRXSysSlotControl                INTEGER,
    rsRXSysSlotCpuUtilPct             Integer32,
    rsRXSysSlotMemUtilPct             Integer32,
    rsRXSysSlotIoaPresent             TruthValue,
    rsRXSysSlotPortCount              Integer32,
    rsRXSysSlotLastChange             TimeTicks
}

rsRXSysSlotIndex OBJECT-TYPE
    SYNTAX      Integer32
    MAX-ACCESS  not-accessible
    STATUS      current
    DESCRIPTION
        "Slot number.

        NOTE: Port numbers are zero-based."
    ::= { rsRXSysSlotEntry 1 }

rsRXSysSlotDescr OBJECT-TYPE
    SYNTAX      DisplayString(SIZE(0..63))
    MAX-ACCESS  read-only
    STATUS      current
    DESCRIPTION
        "Textual description of the card."
    ::= { rsRXSysSlotEntry 2 }

rsRXSysSlotCurrentCardType OBJECT-TYPE
    SYNTAX      RsSysCardType
    MAX-ACCESS  read-only
    STATUS      current
    DESCRIPTION
        "Type of card actually in the slot. This could be different from the 
        type reported in rsRXSysSlotExpectedCardType, in which case it may
        be necessary to set rsRXSysSlotControl to 'flush' before this card
        can be made operational."
    ::= { rsRXSysSlotEntry 3 }

rsRXSysSlotRev OBJECT-TYPE
    SYNTAX      Integer32(0..255)
    MAX-ACCESS  read-only
    STATUS      current
    DESCRIPTION
        "Revision number of the card. If unknown, the value 255 is reported."
    ::= { rsRXSysSlotEntry 4 }

rsRXSysSlotAdminStatus OBJECT-TYPE
    SYNTAX      RsEnable
    MAX-ACCESS  read-write
    STATUS      current
    DESCRIPTION
        "Exerts administrative control to enable/disable the slot."
    ::= { rsRXSysSlotEntry 5 }

rsRXSysSlotOperStatus OBJECT-TYPE
    SYNTAX      INTEGER {
                    unknown(0),
                    empty(1),
                    disabled(2),
                    failed(3),
                    booting(4),
                    initializing(5),
                    online(6),
                    standby(7)
                }
    MAX-ACCESS  read-only
    STATUS      current
    DESCRIPTION
        "Status of the card."
    ::= { rsRXSysSlotEntry 6 }

rsRXSysSlotDisableReason OBJECT-TYPE
    SYNTAX      INTEGER {
                    none(0),
                    unknown(1),
                    assessing(2),
                    admin(3),
                    cardMismatch(4),
                    fabricLimit(5),
                    imageError(6)
                }
    MAX-ACCESS  read-only
    STATUS      current
    DESCRIPTION
        "Indicates the condition causing the slot to be disabled:
        
        none            Value when card is not disabled.

        unknown         Unknown reason for disablement.

        assessing       The slot content is being assessed (transient 
                        initialization state).

        admin           The slot is administratively disabled.

        cardMismatch    The current card type conflicts with configuration
                        associated with a different card type that previously
                        occupied the slot.

        fabricLimit     Card resource requirements exceed available fabric capacity.

        imageError      Software image for card is missing or invalid."
    ::= { rsRXSysSlotEntry 7 }

rsRXSysSlotExpectedCardType OBJECT-TYPE
    SYNTAX      RsSysCardType
    MAX-ACCESS  read-only
    STATUS      current
    DESCRIPTION
        "Type of card associated with this slot through prior presence.
        After the card is removed, this association persists (and inhibits
        operation of a different card type in this slot, if one is inserted)
        until rsRXSysSlotControl is set to 'flush'."
    ::= { rsRXSysSlotEntry 8 }

rsRXSysSlotControl OBJECT-TYPE
    SYNTAX      INTEGER {
                    noOperation(0),
                    flush(1),
                    reset(2)
                }
    MAX-ACCESS  read-write
    STATUS      current
    DESCRIPTION
        "Administrative control of this slot:

            noOperation     Setting this value has no effect.

            flush           Flushes configuration associated with a
                            card type that previously occupied this slot.
                            Used to explicitly confirm that the slot is
                            now empty, or contains a different card type.
                            Card must be disabled when this value is asserted.
                            See description for rsRXSysSlotDisableReason.

            reset           Resets the slot."
    ::= { rsRXSysSlotEntry 9 }

rsRXSysSlotCpuUtilPct OBJECT-TYPE
    SYNTAX      Integer32(-1..100)
    UNITS       "percent"
    MAX-ACCESS  read-only
    STATUS      current
    DESCRIPTION
        "Percentage of CPU utilization.

        A value of -1 indicates the utilization is unknown."
    ::= { rsRXSysSlotEntry 10 }

rsRXSysSlotMemUtilPct OBJECT-TYPE
    SYNTAX      Integer32(-1..100)
    UNITS       "percent"
    MAX-ACCESS  read-only
    STATUS      current
    DESCRIPTION
        "Percentage of memory utilization.

        A value of -1 indicates the utilization is unknown."
    ::= { rsRXSysSlotEntry 11 }

rsRXSysSlotIoaPresent OBJECT-TYPE
    SYNTAX      TruthValue
    MAX-ACCESS  read-only
    STATUS      current
    DESCRIPTION
        "Indicates whether the card's corresponding I/O adapter
        is present."
    ::= { rsRXSysSlotEntry 12 }

rsRXSysSlotPortCount OBJECT-TYPE
    SYNTAX      Integer32
    MAX-ACCESS  read-only
    STATUS      current
    DESCRIPTION
        "Number of physical ports for the EXPECTED card type for this slot.

        NOTE: In event of a card mismatch in this slot, the port count for
        the CURRENT card in this slot is not recognized/reported until 
        the configuration for the EXPECTED card is explicitly flushed via
        rsRXSysSlotControl."
    ::= { rsRXSysSlotEntry 13 }

rsRXSysSlotLastChange OBJECT-TYPE
    SYNTAX      TimeTicks
    MAX-ACCESS  read-only
    STATUS      current
    DESCRIPTION
        "The value of sysUpTime when the value of rsRXSysSlotOperStatus
        last changed."
    ::= { rsRXSysSlotEntry 14 }


-- +++++++++++++++++++++++++++++++++++++++++++++++++++++++++++++++++++++++++++++
--
-- System Port objects
--
-- +++++++++++++++++++++++++++++++++++++++++++++++++++++++++++++++++++++++++++++

rsRXSysPortTable OBJECT-TYPE
    SYNTAX      SEQUENCE OF RsSysPortEntry
    MAX-ACCESS  not-accessible
    STATUS      current
    DESCRIPTION
        "Table of system physical ports.

        The information in this table reflects the ports for the EXPECTED
        card type in each slot; in event of a card mismatch, this table
        permits navigation of the existing configuration of the expected
        card type."
    ::= { rsRXSysPort 1 }

rsRXSysPortEntry OBJECT-TYPE
    SYNTAX      RsSysPortEntry
    MAX-ACCESS  not-accessible
    STATUS      current
    DESCRIPTION
        "A table entry describing a physical port of the system."
    INDEX   { rsRXSysSlotIndex, rsRXSysPortIndex }
    ::= {rsRXSysPortTable 1 }

RsSysPortEntry ::= SEQUENCE {
    rsRXSysPortIndex              Integer32,
    rsRXSysPortDescr              DisplayString,
    rsRXSysPortType               INTEGER,
    rsRXSysPortIfIndex            InterfaceIndexOrZero
}

rsRXSysPortIndex OBJECT-TYPE
    SYNTAX      Integer32
    MAX-ACCESS  not-accessible
    STATUS      current
    DESCRIPTION
        "Port number of this physical port, relative to
        the slot in which it resides. Each physical port
        is uniquely distinguished by its slot/port pair.

        NOTE: Port numbers are zero-based."
    ::= { rsRXSysPortEntry 1 }

rsRXSysPortDescr OBJECT-TYPE
    SYNTAX      DisplayString(SIZE(0..63))
    MAX-ACCESS  read-only
    STATUS      current
    DESCRIPTION
        "Textual description of this port."
    ::= { rsRXSysPortEntry 2 }

rsRXSysPortType OBJECT-TYPE
    SYNTAX      INTEGER {
                    unknown(0),
                    eth(1),
                    ct3(2),
                    oc3c(3),
                    ut3Atm(4),
                    ut3Frame(5),
                    ue3Atm(6),
                    ue3Frame(7),
                    ce1(8),
                    ct1(9)
                }
    MAX-ACCESS  read-only
    STATUS      current
    DESCRIPTION
        "Type of the physical port:
        
            unknown     Unknown port type.
            eth         Ethernet.
            ct3         Channelized T3.
            oc3c        OC-3c (SONET/SDH).
            ut3Atm      Unchannelized T3 (ATM service).
            ut3Frame    Unchannelized T3 (Frame service).
            ue3Atm      Unchannelized E3 (ATM service).
            ue3Frame    Unchannelized E3 (Frame service).
            ce1         Channelized   E1.
            ct1         Channelized   T1."
    ::= { rsRXSysPortEntry 3 }

rsRXSysPortIfIndex OBJECT-TYPE
    SYNTAX      InterfaceIndexOrZero
    MAX-ACCESS  read-only
    STATUS      current
    DESCRIPTION
        "The ifIndex of the Interfaces MIB ifTable entry 
        corresponding to this physical port; if zero, 
        the ifIndex is unknown or does not exist."
    ::= { rsRXSysPortEntry 4 }


-- +++++++++++++++++++++++++++++++++++++++++++++++++++++++++++++++++++++++++++++
--
-- System Power objects
--
-- +++++++++++++++++++++++++++++++++++++++++++++++++++++++++++++++++++++++++++++

rsRXSysPowerTable OBJECT-TYPE
    SYNTAX      SEQUENCE OF RsSysPowerEntry
    MAX-ACCESS  not-accessible
    STATUS      current
    DESCRIPTION
        "Table of system power elements."
    ::= { rsRXSysPower 1 }

rsRXSysPowerEntry OBJECT-TYPE
    SYNTAX      RsSysPowerEntry
    MAX-ACCESS  not-accessible
    STATUS      current
    DESCRIPTION
        "A table entry describing status of a system power element."
    INDEX   { rsRXSysPowerIndex }
    ::= {rsRXSysPowerTable 1 }

RsSysPowerEntry ::= SEQUENCE {
    rsRXSysPowerIndex              Integer32,
    rsRXSysPowerDescr              DisplayString,
    rsRXSysPowerStatus             INTEGER
}

rsRXSysPowerIndex OBJECT-TYPE
    SYNTAX      Integer32
    MAX-ACCESS  not-accessible
    STATUS      current
    DESCRIPTION
        "Arbitrary integer index to distinguish entries in this table."
    ::= { rsRXSysPowerEntry 1 }

rsRXSysPowerDescr OBJECT-TYPE
    SYNTAX      DisplayString(SIZE(0..63))
    MAX-ACCESS  read-only
    STATUS      current
    DESCRIPTION
        "Textual description of this power element."
    ::= { rsRXSysPowerEntry 2 }

rsRXSysPowerStatus OBJECT-TYPE
    SYNTAX      INTEGER {
                    inactive(0),
                    active(1)
                }
    MAX-ACCESS  read-only
    STATUS      current
    DESCRIPTION
        "The status of the power element:

        inactive    No power available from this element.
        active      Power available from this element."
    ::= { rsRXSysPowerEntry 3 }


-- +++++++++++++++++++++++++++++++++++++++++++++++++++++++++++++++++++++++++++++
--
-- System Temp objects
--
-- +++++++++++++++++++++++++++++++++++++++++++++++++++++++++++++++++++++++++++++

rsRXSysTempFanStatus OBJECT-TYPE
    SYNTAX      INTEGER {
                    failed(0),
                    ok(1)
                }
    MAX-ACCESS  read-only
    STATUS      current
    DESCRIPTION
        "Status of fan tray."
    ::= { rsRXSysTemperature 1 }


rsRXSysTempTable OBJECT-TYPE
    SYNTAX      SEQUENCE OF RsSysTempEntry
    MAX-ACCESS  not-accessible
    STATUS      current
    DESCRIPTION
        "Table of system temperature sensors.

        Sensors are distributed across the chassis, at least
        one sensor per populated slot."
    ::= { rsRXSysTemperature 2 }

rsRXSysTempEntry OBJECT-TYPE
    SYNTAX      RsSysTempEntry
    MAX-ACCESS  not-accessible
    STATUS      current
    DESCRIPTION
        "A table entry describing status of a temperature sensor."
    INDEX   { rsRXSysSlotIndex, rsRXSysTempIndex }
    ::= {rsRXSysTempTable 1 }

RsSysTempEntry ::= SEQUENCE {
    rsRXSysTempIndex              Integer32,
    rsRXSysTempDescr              DisplayString,
    rsRXSysTempStatus             INTEGER,
    rsRXSysTempValue              Integer32
}

rsRXSysTempIndex OBJECT-TYPE
    SYNTAX      Integer32
    MAX-ACCESS  not-accessible
    STATUS      current
    DESCRIPTION
        "Arbitrary integer index to distinguish sensors associated with
        the same chassis slot."
    ::= { rsRXSysTempEntry 1 }

rsRXSysTempDescr OBJECT-TYPE
    SYNTAX      DisplayString(SIZE(0..63))
    MAX-ACCESS  read-only
    STATUS      current
    DESCRIPTION
        "Textual description of this sensor."
    ::= { rsRXSysTempEntry 2 }

rsRXSysTempStatus OBJECT-TYPE
    SYNTAX      INTEGER {
                    unknown(0),
                    failed(1),
                    tooLow(2),
                    nominal(3),
                    tooHigh(4)
                }
    MAX-ACCESS  read-only
    STATUS      current
    DESCRIPTION
        "The status of a temperature sensor:

        unknown     Unknown.
        failed      Failed.
        tooLow      Below nominal range.
        nominal     Within nominal range.
        tooHigh     Above nominal range."
    ::= { rsRXSysTempEntry 3 }

rsRXSysTempValue OBJECT-TYPE
    SYNTAX      Integer32
    UNITS       "degrees Celsius"
    MAX-ACCESS  read-only
    STATUS      current
    DESCRIPTION
        "The temperature measured by this sensor in degrees Celsius.
        This measurement is valid only if the value of the corresponding
        rsRXSysTempStatus is nominal."
    ::= { rsRXSysTempEntry 4 }


-- ++++++++++++++++++++++++++++++++++++++++++++++++++++++++++++++++++++++
-- Traps & Trap Control
-- ++++++++++++++++++++++++++++++++++++++++++++++++++++++++++++++++++++++

-- The rsRXSysTrap OBJECT IDENTIFIER is used to define SNMPv2 
-- Notifications that are easily translated into SNMPv1 Traps.


rsRXSysSlotOperStatusChange NOTIFICATION-TYPE
    OBJECTS     { rsRXSysSlotCurrentCardType,
                  rsRXSysSlotAdminStatus, 
                  rsRXSysSlotOperStatus,
                  rsRXSysSlotDisableReason }
    STATUS      current
    DESCRIPTION
        "Reports a status change for a slot. 
        
        This trap is generated on a transition into a stable state
        (online or disabled) or on a transition out of online."
    ::= { rsRXSysTrap 1 }

rsRXSysPowerStatusChange NOTIFICATION-TYPE
    OBJECTS     { rsRXSysPowerStatus }
    STATUS      current
    DESCRIPTION
        "Reports a change in the status of a power element."
    ::= { rsRXSysTrap 2 }

rsRXSysTempFanStatusChange NOTIFICATION-TYPE
    OBJECTS     { rsRXSysTempFanStatus }
    STATUS      current
    DESCRIPTION
        "Reports a change in the status of the fan tray."
    ::= { rsRXSysTrap 3 }

rsRXSysTempStatusChange NOTIFICATION-TYPE
    OBJECTS     { rsRXSysTempStatus }
    STATUS      current
    DESCRIPTION
        "Reports a change in the status of a temperature sensor."
    ::= { rsRXSysTrap 4 }

-- ++++++++++++++++++++++++++++++++++++++++++++++++++++++++++++++++++++++
-- Conformance information
-- ++++++++++++++++++++++++++++++++++++++++++++++++++++++++++++++++++++++

rsRXSysCompliances OBJECT IDENTIFIER ::= { rsRXSysConformance 1 }
rsRXSysGroups      OBJECT IDENTIFIER ::= { rsRXSysConformance 2 }

-- compliance statements

rsRXSysCompliance MODULE-COMPLIANCE
        STATUS  current
        DESCRIPTION
                "The compliance statement for entities which implement
                the Redstone System MIB."
        MODULE  -- this module
                MANDATORY-GROUPS { rsRXSysGroup }
        ::= { rsRXSysCompliances 1 }

-- units of conformance

rsRXSysGroup OBJECT-GROUP
        OBJECTS {

        -- General chassis objects
        rsRXSysChassisRev,
        rsRXSysSwVersion,
        rsRXSysSwBuildDate,

        -- Fabric objects
        rsRXSysFabricSpeed,
        rsRXSysFabricRev,

        -- NVS objects
        rsRXSysNvsStatus,
        rsRXSysNvsCapacity,
        rsRXSysNvsUtilPct,

        -- Slot objects
        rsRXSysSlotCount,
        rsRXSysSlotDescr,
        rsRXSysSlotCurrentCardType,
        rsRXSysSlotRev,
        rsRXSysSlotAdminStatus,
        rsRXSysSlotOperStatus,
        rsRXSysSlotDisableReason,
        rsRXSysSlotExpectedCardType,
        rsRXSysSlotControl,
        rsRXSysSlotCpuUtilPct,
        rsRXSysSlotMemUtilPct,
        rsRXSysSlotIoaPresent,
        rsRXSysSlotPortCount,
        rsRXSysSlotLastChange,

        -- Port objects
        rsRXSysPortDescr,
        rsRXSysPortType,
        rsRXSysPortIfIndex,

        -- Power objects
        rsRXSysPowerDescr,
        rsRXSysPowerStatus,

        -- Temperature objects
        rsRXSysTempFanStatus,
        rsRXSysTempDescr,
        rsRXSysTempStatus,
        rsRXSysTempValue
    }
    STATUS  current
    DESCRIPTION
        "A collection of management objects pertaining
        to system capabilities in a Redstone product."
        ::= { rsRXSysGroups 1 }

END
