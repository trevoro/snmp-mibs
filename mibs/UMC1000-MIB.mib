-- SCCS ID: %W%	%G% %U%

UMC1000-MIB DEFINITIONS ::= BEGIN
IMPORTS
    IpAddress FROM RFC1155-SMI
    OBJECT-TYPE FROM RFC-1212
    DisplayString FROM SNMPv2-TC
    umc1000 FROM AFC-OIDS;

            

--
-- Global Data Types
--


-- A unique value, greater than (0) but smaller than 34, for each terminal in 
-- a UMC system. The identifiers may assume non-contiguous values. The Local
-- Exchange Terminal (LET) is 1, Remote Subscribe Terminal (RST) 1 is 2, RST2
-- is 3, etc.
--
TerminalIdType ::= INTEGER


-- A unique value, greater than (0), that identifies a shelf in a terminal.
-- Shelf identifiers may be non-contiguous. The shelf-identifier of a
-- shelf is one higher than the value its top bank selector is set to.
-- If the top bank selector of a shelf is set to, say, 3, its
-- shelf identifier is 4.
--
ShelfIdType ::= INTEGER


-- A unique value, greater than (0), for each slot in a shelf. The identifier
-- of the first slot is 1, the second slot is 2, etc. The identifiers for 
-- CPU/EBC A, CPU/EBC B, PSU A and PSU B are fixed irrespective of the number
-- of physical slots in a shelf and are always 23, 24, 25 and 26,
-- respectively.
--
SlotIdType ::= INTEGER

--
-- Plug In Type is a value, greater than zero (0) that uniquely identifies
-- the type of functionality a card presents The current list of plugins 
-- is:
--
--    Value	    PIT
--    0x00        Unknown	
--    0x01        CPU		
--    0x02        E1-XCVR	
--    0x03        E1AX		
--    0x04        E1X-XCVR	
--    0x05        EBC		
--    0x06        ELU		
--    0x07        FO-XCVR	
--    0x08        L-PSU	
--    0x09        L-UVG	
--    0x0A        LI-POTS	
--    0x0B        MTU		
--    0x0C        R-PSU	
--    0x0D        R-UVG	
--    0x0E        RI-POTS	
--    0x0F        T1-XCVR	
--    0x10        T1X-XCVR	
--    0x11        DL-XCVR	
--    0x12        ITO		
--    0x13        FON-XCVR	
--    0x14        AnyE1	
--    0x15        AnyFO	
--    0x16        AnyT1	
--    0x17        AnyTrans	
--    0x18        FOS-XCVR	
--    0x19        SSR-XCVR	
--    0x1A        L-POTS	
--    0x1B        R-POTS	
--    0x1C        E&M		
--    0x1D        ADU		
--    0x1E        T1AX		
--    0x1F        SDU		
--    0x20        L-ISDN or LI-ISDN	
--    0x21        R-ISDN or RI-ISDN
--    0x22        DS0-DP	
--    0x23        OCU-DP	
--    0x24        L-PAY	
--    0x25        R-PAY	
--    0x26        LT-PAY	
--    0x27        RT-PAY	
--    0x28        FOE-XCVR	
--    0x29        TO		
--    0x2A        AUVG		
--    0x2B        T1HD-XCVR
--    0x2C        E1HD-XCVR
--    0x2D        L-EBS	
--    0x2E        R-EBS	
--    0x2F        T1A		
--    0x30        LI-APOTS	
--    0x31        RI-APOTS	
--    0x32        CDU		
--    0x33        E3-XCVR	
--    0x34        E1A		
--    0x35        NPSU		
--    0x36        IATO		
--    0x37        FRF-XCVR	
--    0x38        RRF-XCVR	
--    0x39        MRF-XCVR	
--    0x3A        AnyRF	
--    0x3b        ENPSU	
--    0x3c        R-EPOTS	
--    0x3d        CPSU60	
--    0x3e        R-MPOTS	
--    0x3f        R-HCPOTS	
--    0x40        R-HVPOTS	
--    0x41        L-HPOTS	
--    0x42        R-HCUVG	
--    0x43        R-HVUVG	
--    0x44        L-HUVG	
--    0x45        FOW-XCVR	
--    0x46        R-SRPOTS	
--    0x47        RAI		
--    0x48        RSU-1	
--    0x49        AnyMRF	
--    0x4A        DLP		
--    0x4B        OSI		
--    0x4C        CPSU90	
--    0x4D        HCU		
--    0x4E        CPU16	
--    0x4F        AnyE1A	
--    0x50        AnyT1A	
--    0x51        Any6		
--    0x52        AnyIsdn	
--    0x53        AnyDds	
--    0x54        AnyPsu	
--    0x55        DBP		
--    0x56        AnyCPU		
--    0x57        TIE		
--    0x58        LI-BPOTS	
--    0x59        RI-BPOTS	
--    0x5A        ETI		
--    0x5B        OC3cu-XCVR
--    0x5C        AD1		
--    0x5D        ADSL		
--    0x5E        LI-VPOTS	
--    0x5F        RI-VPOTS	 
--    0x60        768HD-XCVR
--    0x61        ELU-3
--    0x62        SNMP		
--    0x63        FOB-XCVR	
--    0x64        T1HDA-XCVR
--    0x65        EBC-3
--    0x66        mCPU		
--    0x67        mT1HD-PAIR
--    0x68        mFO-XCVR	
--    0x69        mFOB-XCVR
--    0x6A        mT1-XCVR	
--    0x6B        mR-PSU	
--    0x6C        mNPSU	
--    0x6D        mENPSU	
--    0x6E        mR-POTS	
--    0x6F        mT1HD-ADTN
--    0x70        CPU2 	
--    0x71        BCPU 	
--    0x72        V-XCVR 	
--    0x73        mR-ISDN	
--    0x74        mOCU-DP	
--    0x75        DDU		
--    0x76        mCPU2	
--    0x77        RTT1-XCVR
--    0x78        DS3I-XCVR
--    0x79        This Pit has been retired	
--    0x7A        DS3C-XCVR
--    0x7B        E1HD-ADTN
--    0x7C        This Pit has been retired	
--    0x7D        OC3c-XCVR	
--    0x7E        ADSL 2+6	
--    0x7F        ADSL 6+0	
--    0x80        ADSL 6+6	
--    0x81        This Pit has been retired	
--    0x82        This Pit has been retired	
--    0x83        Any ADSL	
--    0x84        Any ATMX	
--    0x85        IDLP		
--    0x86        E3I-XCVR	
--    0x87        T1HD2A-XCVR        
--    0x88        R-CPOTS	
--    0x89        L-JPOTS	
--    0x8A        R-JPOTS	
--    0x8B        This Pit has been retired	
--    0x8C        STM1cu-XCVR 
--    0x8D        SHDSL 
--    0x8E        STM1c-XCVR 

PlugInType ::= INTEGER



-- A unique value, that indicates the status of the Database record being
-- referenced.  
--      0x00 = record updated (new or modified)
--      0x01 = record deleted.

DbActionType ::= INTEGER


-- A unique non-negative value, smaller than 27, for each V5 group in 
-- a UMC system. The identifiers may assume non-contiguous values. V5 Groups
-- in the range between 0 through 4 represent V5.2 groups. V5 Groups in the
-- range between 5 through 26 represent V5.1 groups.

V5GroupIdType ::= INTEGER


-- This data type describes the data operation that the EMS desires.
-- 0 = GET EXACT Record (Only valid for SNMP GET requests)
--     Gets the DB record (if it exists) for the KEY 
--     specified or the default record (if there is one).
--     If there is no default record or DB record an error 
--     will be returned.
-- 1 = GET PROGRESSIVE (Only valid for SNMP GET requests)
--     Gets the DB record (if it exists) for the KEY 
--     specified or the next closest lexical match in the UMC
--     system database (if there is one).  If NO database 
--     record can be found an error will be returned.
-- 2 = GET DEFAULT Record (Only valid for SNMP GET requests)
--     Gets the Default DB record (if it exists) for the KEY 
--     specified. If there is no default record an error 
--     will be returned.
-- 3 = WRITE DATA Record (Only valid for SNMP SET requests)
--     Writes the DB record for the KEY specified into the UMC
--     system Database.
-- 4 = DELETE DATA record (Only valid for SNMP SET requests)
--     Deleted the DB record for the KEY specified from the 
--     UMC system database.

DataOperation ::= INTEGER
 


 --umc1000Mib MODULE-IDENTITY
 --LAST-UPDATED "9806191500Z"
 --ORGANIZATION "afc"
 --CONTACT-INFO
 --Advanced Fibre Communications, Inc.
 --One Willow Brook Court
 --Petaluma, CA  94954
 --Voice: 707-794-7700
 --Fax: 707-794-7777
 --DESCRIPTION
 --"The MIB module to manage the UMC 1000.  This mib defines the naming
 -- subtree below umc1000 (1.3.6.1.4.1.2067.1.1.2)"
--::= { umc1000 1  }


--
-- Define some naming sub-trees that will be used in this MIB.  The
-- use of these subtrees will allow us to break up the MIB into separate
-- groups, thus allowing us to make additions within a group without
-- affecting the overall look of the MIB.  Note that not all of these
-- subtrees are defined in this MIB or implemented in the agent.
--

umc1System          OBJECT IDENTIFIER ::= { umc1000 1 }       -- system-wide info
umc1Terminal        OBJECT IDENTIFIER ::= { umc1000 3 }       -- terminal-wide info
umc1Alarm           OBJECT IDENTIFIER ::= { umc1000 8 }       -- alarm related info
umc1ManagerIf       OBJECT IDENTIFIER ::= { umc1000 9 }       -- management interfaces
umc1Topology        OBJECT IDENTIFIER ::= { umc1000 10 }      -- topology information
umc1DataService     OBJECT IDENTIFIER ::= { umc1000 11 }      -- data lookup services
umc1Trap            OBJECT IDENTIFIER ::= { umc1000 100 }     -- generic trap definitions

umc1Inventory       OBJECT IDENTIFIER ::= { umc1000 2 }       -- equipment inventory
umc1ACOSnapTopology OBJECT IDENTIFIER ::= { umc1000 4 }	      -- ACO topology snapshot 
                                                              -- information
umc1CommandResponse OBJECT IDENTIFIER ::= { umc1000 5 }       -- Command-Response
umc1Span		    OBJECT IDENTIFIER ::= { umc1000 6 }       -- Span

umc1InventoryShelf          OBJECT IDENTIFIER ::= { umc1Inventory 1 } -- shelf inventory.
umc1InventoryShelfExtended  OBJECT IDENTIFIER ::= { umc1Inventory 2 } -- shelf inventory 
                                                                      -- extended information.
umc1InventoryPlugin         OBJECT IDENTIFIER ::= { umc1Inventory 3 } -- plug-in card inventory.
umc1InventoryPluginExtended OBJECT IDENTIFIER ::= { umc1Inventory 4 } -- extended information 
                                                                      -- for plug-in cards.





--
-- System Wide Information
--

   umc1SystemDateTime OBJECT-TYPE
   SYNTAX OCTET STRING   (SIZE (11..11))
   ACCESS read-write
   STATUS mandatory
   DESCRIPTION
       "The system date and time is accessible as follows:
            octet[0]   Timezone (0 through 24)
            octet[1]   High-order 8-bits (MSB) of Year
            octet[2]   Low-order 8-bits (LSB) of Year
            octet[3]   Month (1 through 12, where Jan.=1, Feb.=2, etc.)
            octet[4]   Day (1 through 31)
            octet[5]   Hour (0 through 23)
            octet[6]   Minutes (0 through 59)
            octet[7]   Seconds (0 through 59)
            octet[8]   High-order 8-bits (MSB) of Mseconds (always 0)
            octet[9]   Low-order 8-bits (LSB) of Mseconds (always 0)
            octet[10]  Day of Week (0 through 7)"
   ::= { umc1System 1 }


--
-- Global System Type Provisioning
--

    umc1SystemSysProv  OBJECT IDENTIFIER ::= { umc1System 2 }

    umc1SystemSysProvTableChangeSeqNum OBJECT-TYPE
        SYNTAX INTEGER (1..2147483647)
        ACCESS read-only
        STATUS mandatory
        DESCRIPTION
        "A sequence number used to indicate that the Global System Provisioning
         Table, umc1SystemSysProvTable, has been modified and it needs to be 
         re-read. Whenever the SNMP agent is restarted, this value will be reset
         to 0(zero). The value will be incremented by one whenever a change to 
         the Global System Provisioning Table has been made. This number will 
         also be sent in the umc1TrapSysProvChgTableChangeUpd trap and can be 
         used to determine if any traps have been lost by the manager. This 
         value will be incremented before the trap is sent.

	 The maximum value it can assume is 2,147,483,647. An increment, 
	 every time it has reached its maximum value, shall cause it to 
	 be reset to 1.
	 " 
        ::= { umc1SystemSysProv 7 }


   umc1SystemSysProvBerTable OBJECT-TYPE
   SYNTAX SEQUENCE OF Umc1SystemSysProvBerEntry
   ACCESS not-accessible
   STATUS mandatory
   DESCRIPTION
       "This table stores BER provisioning information per Plug-In Type.
        Access to this Table is read-write. By implementation, this table
        supports GET, SET, and GET-NEXT Operations."
   ::= { umc1SystemSysProv 1 }


   umc1SystemSysProvBerEntry OBJECT-TYPE
   SYNTAX Umc1SystemSysProvBerEntry
   ACCESS not-accessible
   STATUS mandatory
   DESCRIPTION
       "An entry in the System Global Provisioning table. The relationship 
        and allowed ranges of values for the Maintenance and Red BER columns
        is as follows:

            _PitAnyE1_   Red BER range in 3-7, Maintenance BER range in 4-8
            _PitAnyFO_   Red BER range in 3-9, Maintenance BER range in 4-10
            _PitAnyT1_   Red BER range in 3-7, Maintenance BER range in 4-8
            _PitAnyRF_   Red BER range in 3-7, Maintenance BER range in 4-8
            _PitAnyE1A_  Red BER range in 3-7, Maintenance BER range in 4-8
            _PitAnyT1A_  Red BER range in 3-7, Maintenance BER range in 4-8
            _PitAnyIsdn_ Red BER range in 3-6, Maintenance BER range in 4-7"
   INDEX { umc1SystemSysProvBerPit }
   ::= { umc1SystemSysProvBerTable 1 }


   Umc1SystemSysProvBerEntry ::=
   SEQUENCE { umc1SystemSysProvBerPit           PlugInType,
              umc1SystemSysProvBerRedThresh     INTEGER,
              umc1SystemSysProvBerMaintThresh   INTEGER,
              umc1SystemSysProvBerMarginData    INTEGER }


   umc1SystemSysProvBerPit OBJECT-TYPE
   SYNTAX PlugInType
   ACCESS read-write
   STATUS mandatory
   DESCRIPTION
       "See description of the 'PlugInType'. However, currently, entries for 
        the following PITs are supported in this table:
            _PitAnyE1_
            _PitAnyFO_
            _PitAnyT1_
            _PitAnyRF_
            _PitAnyE1A_
            _PitAnyT1A_
            _PitAnyIsdn_"
   ::= { umc1SystemSysProvBerEntry 1 }


   umc1SystemSysProvBerRedThresh OBJECT-TYPE
   SYNTAX INTEGER
   ACCESS read-write
   STATUS mandatory
   DESCRIPTION
       "This is the RED BER threshold exponent. If the value is 5,
        then the maintenance BER threshold is 10e-05 (10^-5), or 1 in one
        thousand. The range of this threshold value is dependent upon
        the PIT type. This value must always be less than that of the
        Maintenance BER Threshold value."
   ::= { umc1SystemSysProvBerEntry 2 }


   umc1SystemSysProvBerMaintThresh OBJECT-TYPE
   SYNTAX INTEGER
   ACCESS read-write
   STATUS mandatory
   DESCRIPTION
       "This is the maintenance BER threshold exponent. If the value is 6,
        then the maintenance BER threshold is 10e-06 (10^-6), or 1 in one
        million. The range of this threshold value is dependent upon
        the PIT type. This value must always be greater than that of the
        RED BER Threshold value."
   ::= { umc1SystemSysProvBerEntry 3 }


   umc1SystemSysProvBerMarginData OBJECT-TYPE
   SYNTAX INTEGER
   ACCESS read-write
   STATUS mandatory
   DESCRIPTION
       "This is the facility margin data in dB. Valid values range from zero
        (0) through fifteen (15), inclusive. The default value is 6."
   ::= { umc1SystemSysProvBerEntry 4 }



   umc1SystemSysProvSystemCcsThresh OBJECT-TYPE
   SYNTAX INTEGER
   ACCESS read-write
   STATUS mandatory
   DESCRIPTION
       "The range of allowable values is zero (0) through thirty-seven (37)
        in steps of one (1)."
   ::= { umc1SystemSysProv 2 }



    umc1SystemSysProvPsuRingVoltage OBJECT-TYPE
    SYNTAX INTEGER
    ACCESS read-write
    STATUS mandatory
    DESCRIPTION
    "This number indicates the number of Volts; the following voltage 
     levels are supported:
     Integer Value		Meaning
                60 		60 Volts
                65 		65 Volts
                85 		85 Volts
                95 		95 Volts
    "
    ::= { umc1SystemSysProv 3 }


    umc1SystemSysProvPsuPulseMeterTone OBJECT-TYPE
    SYNTAX INTEGER
    ACCESS read-write
    STATUS mandatory
    DESCRIPTION
    "This value indicates the frequency of the pulse tone. The following 
     frequencies are supported, with zero (0) disabling pulse metering:
            Integer Value	Meaning
               12000		12 KHz pulse metering tone
               16000		16 KHz pulse metering tone
                8000		8 KHz US EBS backplane tone
                   0        pulse-metering disabled
    "
    ::= { umc1SystemSysProv 4 }


    umc1SystemSysProvPsuRingFreq OBJECT-TYPE
    SYNTAX INTEGER
    ACCESS read-write
    STATUS mandatory
    DESCRIPTION
    "This value is equal to the Ring Frequency Hertz multiplied by ten (10); 
     the following values are supported:
        Integer Value		        Meaning 
               167			16.7 Hz
               177			17.7 Hz
               187			18.7 Hz
               200			20.0 Hz
               210			21.0 Hz
               223			22.3 Hz
               235			23.5 Hz
               250			25.0 Hz
               264			26.4 Hz
               280			28.0 Hz
               298			29.8 Hz
               316			31.6 Hz
               333			33.3 Hz
               354			35.4 Hz
               376			37.6 Hz
               400			40.0 Hz
               422			42.2 Hz
               444			44.4 Hz
               474			47.4 Hz
               500			50.0 Hz
    "
    ::= { umc1SystemSysProv 5 }



    umc1SystemSysProvChgTable OBJECT-TYPE
        SYNTAX SEQUENCE OF Umc1SystemSysProvChgEntry
        ACCESS not-accessible
        STATUS mandatory
        DESCRIPTION
        "The EMS uses this table to synchronize its internal representation of 
         System Global Provisioning information with that managed by the UMC 
         Agent. A trap is sent to the EMS indicating a change to System Global 
         Provisioning information has been made and entered as a row in this 
         table. The EMS queries this table, using the sequence number received 
         in the umc1TrapSysProvChange trap to determine whether it can re-learn 
         the changed System Global Provisioning information from this table or 
         must re-learn *all* System Global Provisioning information, bypassing 
         this table."
        ::= { umc1SystemSysProv 6 }


    umc1SystemSysProvChgEntry OBJECT-TYPE
        SYNTAX Umc1SystemSysProvChgEntry
        ACCESS not-accessible
        STATUS mandatory
        DESCRIPTION
        "An entry in the System Global Provisioning Changes table."
        INDEX { umc1SystemSysProvChgSeqNbr }
        ::= { umc1SystemSysProvChgTable 1 }


    Umc1SystemSysProvChgEntry ::=
        SEQUENCE {  umc1SystemSysProvChgSeqNbr        INTEGER,
                    umc1SystemSysProvChgData          OCTET STRING }


    umc1SystemSysProvChgSeqNbr OBJECT-TYPE
        SYNTAX INTEGER
        ACCESS read-only
        STATUS mandatory
        DESCRIPTION
        "This objects value matches the value of 
         umc1SystemSysProvTableChangeSeqNum at the time the row was created.
         A valid value of this object is in the range of 1 through 
         umc1SystemSysProvTableChangeSeqNum."
        ::= { umc1SystemSysProvChgEntry 1 }


    umc1SystemSysProvChgData OBJECT-TYPE
        SYNTAX OCTET STRING 		(SIZE (1..255))
        ACCESS read-only
        STATUS mandatory
        DESCRIPTION
        "The first octet, octet 0, indicates which System Global object has 
         changed. This value will be one of the following:
            0x00  - System Date & Time
            0x01  - ACO Configuration   (NOT SUPPORTED AT PRESENT)
            0x02  - System Timing Interface (NOT SUPPORTED AT PRESENT)
            0x03  - PSU Ring Voltage
            0x04  - PSU Pulse Meter Tone
            0x05  - PSU Ring Frequency
            0x06  - SNMP Community Name (NOT SUPPORTED AT PRESENT)
            0x07  - SNMP Trap Types Enabled
            0x08  - SNMP Trap Receiver 1 IP Address
            0x09  - SNMP Trap Receiver UDP Port
            0x0A  - SNMP Trap Receiver 2 IP Address
            0x0B  - SNMP Trap Receiver 2 Traps Enabled
            0x0C  - SNMP Trap Receiver 3 IP Address
            0x0D  - SNMP Trap Receiver 3 Traps Enabled
            0x0E  - SNMP Trusted Hosts Enabled
            0x0F  - SNMP Telnet Port    (NOT SUPPORTED AT PRESENT)
            0x10  - Transceiver Channel Attributes
            0x11  - CPU Build Options

        The trailing octets, octet 1 through the last octet in the object 
        store the new data for the object that has changed.

        If octet 0 is 0x00 (System Date & Time has changed) octets 1 through 
        the last octet in the octet string store the new value.  The new value
        will be of the format defined by umc1SystemDateTime.

        If octet 0 is 0x01 (ACO Configuration has changed) octet 1 stores 
        the new value. The format of the new value is defined by
        umc1SystemSysProvACOConfig. (NOT SUPPORTED AT PRESENT)

        If octet 0 is 0x02 (System Timing Interface has changed), the trailing 
        octets contain the value. OPEN ISSUE: We will add the description once 
        we ascertain the format of the CPU database record for the current 
        release. The format of the data returned is defined by
        umc1SystemSysTimingSource.   (NOT SUPPORTED AT PRESENT)

        If octet 0 is 0x03 (PSU Ring Voltage has changed), octet 1 contains 
        PSU Ring Voltage value.  The format of the data returned is defined by
        umc1SystemSysProvPsuRingVoltage.

        If octet 0 is 0x04 (PSU Meter Tone has changed), octets 1 through 4 
        contain PSU Meter Tone value, where octets 1, 2, 3, and 4 contain 
        bits 24..31, 16..23, 8..15, 0..7, respectively.  The format of the 
        data returned is defined by umc1SystemSysProvPsuPulseMeterTone.

        If octet 0 is 0x05 (PSU Ring Frequency has changed), octets 1 through 
        2 contain PSU Ring Frequency value, where octets 1 and 2 contain bits 
        8..15 and 0..7, respectively.  The format of the data returned is 
        defined by umc1SystemSysProvPsuRingFreq.

        If octet 0 is 0x06 (SNMP Community name has changed), octets 1 through 
        the last octet in the octet string contain the new SNMP community name.
        (NOT SUPPORTED AT PRESENT - we do not issue this information for 
        security reasons !).

        If octet 0 is 0x07 (SNMP Trap Types Enabled has changed), octet 1 
        contains the new value for object umc1SnmpTrapTypesEnabled.

        If octet 0 is 0x08 (SNMP Trap Receiver 1 IP Address has changed), 
        octets 1 through 4 contain the new value of the object 
        umc1SnmpTrapRcvrAddress.

        If octet 0 is 0x09 (SNMP Trap Receiver UDP Port has changed), 
        octets 1 through 4 contain the new value of the object 
        umc1SnmpTrapRcvrPort.

        If octet 0 is 0x0A (SNMP Trap Receiver 2 IP Address has changed), 
        octets 1 through 4 contain the new value of the object 
        umc1SnmpMgmtHost2Address.

        If octet 0 is 0x0B (SNMP Trap Receiver 2 Traps Enabled has changed), 
        octet 1 contains umc1SnmpMgmtHost2TrapsEnabled.

        If octet 0 is 0x0C (SNMP Trap Receiver 3 IP Address has changed), 
        octets 1 through 4 contain the new value of the object 
        umc1SnmpMgmtHost3Address.

        If octet 0 is 0x0D (SNMP Traps Receiver 3 Traps Enabled has changed), 
        octets 1 through 4 contain the new value of the object 
        umc1SnmpMgmtHost3TrapsEnabled.

        If octet 0 is 0x0E (SNMP Trusted Hosts Enabled has changed), 
        octets 1 through 4 contain the new value of the object 
        umc1SnmpTrustedHostsEnabled.

        If octet 0 is 0x0F (SNMP Telnet Port has changed), 
        octets 1 through 4 contain the new value of the object 
        umc1SnmpTelnetPort.  (NOT SUPPORTED AT PRESENT - this is managed 
        via the IPMI Plugin Provisioning record table and associated TRAPs).

        If octet 0 is 0x10 (Transceiver Channel Attributes), 
        the trailing octets contain the value. The remainder of the octet 
        contents are described as follow :
        octet[1]        'version' of data (1 for this release)

        for octet[1]    (version ) equal 1
        octet[2]        'action', either record delete or modify/create.
                        See 'DbActionType'.
        octet[3]        'dbSpecifier', set to _DbChanAtrb_ (0x0A)
        octet[4]        'dbRecLen', length of the database record to follow
                        in number of bytes.  The database record will be held
                        in octets[5] - [?]. The actual number of octets will
                        vary, dependent upon the type of Channel Attribute
                        record being reported.
        octet[5] - [?]  The actual CPU database record.


        If octet 0 is 0x11 (CPU Build Options), 
        the trailing octets contain the value of the changed option(s) 
        object 'umc1CpuSoftwareFeatures'.  If the CPU does not support  
        the reporting of this data the values of all bytes of the object 
        returned will be set to zero (including the version octet[0]).
        "
        ::= { umc1SystemSysProvChgEntry 2 }



    umc1SystemSysProvACOConfig OBJECT-TYPE
        SYNTAX INTEGER
        ACCESS read-write
        STATUS mandatory
        DESCRIPTION
        "This object defines the configuration of the system-wide alarm 
         cut-off (ACO) button. It could be UMC_Mode, Standard_Mode, or 
         Extended_Mode ACO operation. In the UMC_Mode, one push of the 
         ACO button results in the cut-off of the current alarms and the 
         clearing of the Plug-and-play current alarm conditions. 
         The Plug-and-play alarms are Missing Card Alarm, Loss of 
         Composite Clock Alarm, Loss of A/B Power Lead Alarm, Unexpected 
         RSU Registration Alarm. In Standard_Mode mode, the ACO button 
         operates as a traditional ACO and only cuts off audible alarms. 
         The Plug-and-play alarms can only be cleared via the Craft User 
         interface or the restoration of the event that caused the alarm. 
         In the Extended_Mode ACO the ACO button has two time thresholds, 
         a short one, and a long one. A short depression of the ACO button 
         results in alarm cut-off, but it does not clear the plug and play 
         alarms. A long depression of the ACO button results in the alarm 
         cut off and the clearing of plug and play alarms. 

         The acceptable values for this object and their corresponding meanings are:
             Integer Value		Meaning
             1 		            UMC Mode
             2 		            Standard Mode
             3                  Extended ACO Mode
        "
        ::= { umc1SystemSysProv 8 }


    umc1SystemSysTimingSource OBJECT-TYPE
        SYNTAX OCTET STRING (SIZE (1..255))
        ACCESS read-write
        STATUS mandatory
        DESCRIPTION
        "This object is used to access or modify the timing source used by 
         the UMC system. 

         OPEN ISSUE: We will add the description once we ascertain the format 
         of the CPU database record for the current release.
        "
        ::= { umc1SystemSysProv 9 }


    umc1SystemSysTemperature OBJECT-TYPE
        SYNTAX INTEGER
        ACCESS read-write
        STATUS mandatory
        DESCRIPTION
        "This object is used to access get the current temperature of the 
         terminal that houses the IPMI Agent. 

         OPEN ISSUE: We will change the description once we ascertain the CPU 
         support for retrieval of the system temperature.
        "
        ::= { umc1SystemSysProv  10 }


    umc1SystemSysProvCATable OBJECT-TYPE
        SYNTAX SEQUENCE OF Umc1SystemSysProvCAEntry
        ACCESS not-accessible
        STATUS mandatory
        DESCRIPTION
        "The EMS uses this table to access and update the channel attributes 
         associated with ADSL port in the system or the channel attributes of
         transceiver plugin cards (eg, T1)."
        ::= { umc1SystemSysProv 11 }


    umc1SystemSysProvCAEntry OBJECT-TYPE
        SYNTAX Umc1SystemSysProvCAEntry
        ACCESS not-accessible
        STATUS mandatory
        DESCRIPTION
        "An entry in the System Global Channel Attribute table."
        INDEX { umc1SystemSysProvCAIndex }
        ::= { umc1SystemSysProvCATable 1 }


    Umc1SystemSysProvCAEntry ::=
        SEQUENCE {  umc1SystemSysProvCAIndex    OCTET STRING,
                    umc1SystemSysProvCAData     OCTET STRING }


    umc1SystemSysProvCAIndex OBJECT-TYPE
        SYNTAX OCTET STRING 		(SIZE (1..255))
        ACCESS read-only
        STATUS mandatory
        DESCRIPTION
		"This object contains the information that identifies the 
		ADSL port associated with the DMT carrier mask being defined 
		or the terminal, shelf, slot and channel(s) associated with 
		the transceiver they are associated with. It also contains 
                the information on the transceiver channel attributes and 
                Nx64 groups.

		For the initial implementation the OCTET representation 
		will be as follows:

		octet[0]  Version number of the octet representation being used 
		          to define this INDEX.  The version number for the 
				  initial implementation will be 0x01.

		For Version number 0x01 the remaining octets will be 
		defined as follows :
		octet[1]  DB specifier octet for the type of channel 
		          attribute record being referenced.
                octet[2]  High-order byte of plugin type (see PlugInType).
		octet[3]  Low-order byte of the plugin type.
		octet[4]  Terminal Identifier (see TerminalIdType).
		octet[5]  Shelf Identifier (see ShelfIdType).
		octet[6]  Slot Identifier (see SlotIdType).
		octet[7]  Bits 31..24 of Channel or Port identifier. The 
		          channel or port identifier value to access Nx64 
			  provisioning records starts at 128, i.e., the 
			  index of the first Nx64 provisioning record is 128,
			  the index of the second one is 129ecu, and so on.
		octet[8]  Bits 23..16 of Channel or Port identifier.
		octet[9]  Bits 15..8  of Channel or Port identifier.
		octet[10] Bits 7..0   of Channel or Port identifier.
		octet[11] - [?] The packed DB record index info .. this 
		                will depend upon the DB specifier type (octet[1]).
        "
        ::= { umc1SystemSysProvCAEntry 1 }


    umc1SystemSysProvCAData OBJECT-TYPE
        SYNTAX OCTET STRING 		(SIZE (1..255))
        ACCESS read-write
        STATUS mandatory
        DESCRIPTION
        "This object contains the DMT carrier mask associated with an 
         ADSL port or the channel attributes of a Transceiver card. 

        octet[1] 'version' of data (1 for this release)

        for octet[1]    (version ) equal 1
        octet[2] 'dbSpecifier', set to _DbChanAtrb_ (0x0A)
        octet[3] 'dbRecLen', length of the database record to follow
                 in number of bytes.  The database record will be held
                 in octets[4] - [?]. The actual number of octets will
                 vary, dependent upon the type of Channel Attribute
                 record being reported.
        octet[4] - [?]  The actual CPU database record.
        "
        ::= { umc1SystemSysProvCAEntry 2 }




--
-- Slot-Specific Plug-In Type Provisioning
--

    umc1SystemPitProv  OBJECT IDENTIFIER ::= { umc1System 3 }


	umc1SystemPitProvTable OBJECT-TYPE
		SYNTAX SEQUENCE OF Umc1SystemPitProvEntry
		ACCESS not-accessible
		STATUS mandatory
		DESCRIPTION
		"A Management Station uses this table to GET and SET a *single* Plug-in
		Provisioning record. Access to this table is read-write. By implementation,
		this table supports GET and SET operations, but does not support GET-NEXT 
		operations."
	::= { umc1SystemPitProv 1 }


	umc1SystemPitProvEntry OBJECT-TYPE
		SYNTAX Umc1SystemPitProvEntry
		ACCESS not-accessible
		STATUS mandatory
		DESCRIPTION
                "An entry in the Plug-In Provisioning."
		INDEX { umc1SystemPitProvTerminalId,
			umc1SystemPitProvShelfId, 
			umc1SystemPitProvSlotId,
			umc1SystemPitProvPit}
	::= { umc1SystemPitProvTable 1 }


	Umc1SystemPitProvEntry ::=
	SEQUENCE {	umc1SystemPitProvTerminalId    TerminalIdType,
			umc1SystemPitProvShelfId       ShelfIdType,
			umc1SystemPitProvSlotId        SlotIdType,
			umc1SystemPitProvPit           PlugInType,
			umc1SystemPitProvData          OCTET STRING }

	umc1SystemPitProvTerminalId OBJECT-TYPE
		SYNTAX TerminalIdType
		ACCESS read-write
		STATUS mandatory
		DESCRIPTION
		"See description for 'TerminalIdType'."
	::= { umc1SystemPitProvEntry 1 }


	umc1SystemPitProvShelfId OBJECT-TYPE
		SYNTAX ShelfIdType
		ACCESS read-write
		STATUS mandatory
		DESCRIPTION
		"See description for 'ShelfIdType'."
	::= { umc1SystemPitProvEntry 2 }


	umc1SystemPitProvSlotId OBJECT-TYPE
		SYNTAX SlotIdType
		ACCESS read-write
		STATUS mandatory
		DESCRIPTION
		"See description for 'SlotIdType'."
	::= { umc1SystemPitProvEntry 3 }


	umc1SystemPitProvPit OBJECT-TYPE
		SYNTAX PlugInType
		ACCESS read-write
		STATUS mandatory
		DESCRIPTION
		"See description for 'PlugInType'."
	::= { umc1SystemPitProvEntry 4 }


	umc1SystemPitProvData OBJECT-TYPE
		SYNTAX OCTET STRING     (SIZE (1..255))
		ACCESS read-write
		STATUS mandatory
		DESCRIPTION
		"The structure of this object is the same for Get Response PDUs
		and Set Request PDUs. In a SET Request the data is included in 
		the Request PDU. In a GET Request the data is returned in the 
		Response PDU.

		An operation to delete a PlugIn provisioning record is not
		implemented, per se. In order to delete a PlugIn Provisioning record
		for a given PlugInType in a given location, the manager must issue a 
		SET request; the umc1SystemPitProvData column must contain the Default 
		PlugIn Provisioning record for the PlugInType. A GET Request for a 
		PlugIn Provisioning Record thus deleted shall return the Default PlugIn 
		Provisioning Record for the given PlugIn.

		The byte-format structure of this object, taking into account the above 
		description, is as follows:

                octet[0] Version number of the octet representation. The version number 
			 for the initial implementation will be 0x01.

                For Version number 0x01 the remaining octets will be defined as follows :
	        octet[1] DB specifier octet.
                octet[2] - [?] The plug-in provisioning DB record.
		"
        ::= { umc1SystemPitProvEntry 5 }


--
-- Default Plug-In Type Provisioning Table
--
	umc1SystemDefPitProvTable OBJECT-TYPE
	   SYNTAX SEQUENCE OF Umc1SystemDefPitProvEntry
	   ACCESS not-accessible
	   STATUS mandatory
	   DESCRIPTION
	        "A Management Station uses this table to read a *single* Default 
	        Plug-in Provisioning record. Access to this table is read-only. 
	        By implementation, this table supports GET and GET-NEXT operations 
	        but does not support SET operations."
	   ::= { umc1SystemPitProv 2 }


	umc1SystemDefPitProvEntry OBJECT-TYPE
	   SYNTAX Umc1SystemDefPitProvEntry
	   ACCESS not-accessible
	   STATUS mandatory
	   DESCRIPTION
			"An entry in the Default Plug-In Provisioning Table."
	   INDEX { umc1SystemDefPitProvTerminalId,
			   umc1SystemDefPitProvShelfId, 
			   umc1SystemDefPitProvSlotId,
			   umc1SystemDefPitProvPit }
	   ::= { umc1SystemDefPitProvTable 1 }


	Umc1SystemDefPitProvEntry ::=
	   SEQUENCE {   umc1SystemDefPitProvTerminalId    TerminalIdType,
		        umc1SystemDefPitProvShelfId       ShelfIdType,
			umc1SystemDefPitProvSlotId        SlotIdType,
			umc1SystemDefPitProvPit           PlugInType,
			umc1SystemDefPitProvData          OCTET STRING }


	umc1SystemDefPitProvTerminalId OBJECT-TYPE
	   SYNTAX TerminalIdType
	   ACCESS read-only
	   STATUS mandatory
	   DESCRIPTION
		   "See description for 'TerminalIdType'."
	   ::= { umc1SystemDefPitProvEntry 1 }


	umc1SystemDefPitProvShelfId OBJECT-TYPE
	   SYNTAX ShelfIdType
	   ACCESS read-only
	   STATUS mandatory
	   DESCRIPTION
		   "See description for 'ShelfIdType'."
	   ::= { umc1SystemDefPitProvEntry 2 }


	umc1SystemDefPitProvSlotId OBJECT-TYPE
	   SYNTAX SlotIdType
	   ACCESS read-only
	   STATUS mandatory
	   DESCRIPTION
		   "See description for 'SlotIdType'."
	   ::= { umc1SystemDefPitProvEntry 3 }


	umc1SystemDefPitProvPit OBJECT-TYPE
	   SYNTAX PlugInType
	   ACCESS read-only
	   STATUS mandatory
	   DESCRIPTION
		   "See description for 'PlugInType'."
	   ::= { umc1SystemDefPitProvEntry 4 }


	umc1SystemDefPitProvData OBJECT-TYPE
	   SYNTAX OCTET STRING     (SIZE (1..255))
	   ACCESS read-only
	   STATUS mandatory
	   DESCRIPTION
	        "In a SNMP GET or GET-NEXT operation the data is returned in 
	        the Response PDU.
                
	        The byte-format structure of this object, taking into account 
	        the above description, is as follows:
                
	         octet[0] Version number of the octet representation. The version number 
	        	  for the initial implementation will be 0x01.
                
	        For Version number 0x01 the remaining octets will be defined as follows :
	         octet[1]       DB specifier octet.
	         octet[2] - [?] The default plug-in provisioning DB record."
	   ::= { umc1SystemDefPitProvEntry 5 }


--
-- Plug-In Type Provisioning Changes Table
--
	umc1SystemPitProvChgTable OBJECT-TYPE
	   SYNTAX SEQUENCE OF Umc1SystemPitProvChgEntry
	   ACCESS not-accessible
	   STATUS mandatory
	   DESCRIPTION
		"The EMS uses this table to synchronize its internal representation of  
		the Plug-In Provisioning data with that managed by the UMC Agent. A 
		trap is issued to the EMS indicating a change to the Provisioning  
		data has been made and entered as a row in this table. The EMS  
		queries this table, using the sequence number received in the  
		umc1TrapPitProvChange trap to determine whether it can re-learn the  
		changed Provisioning information from this table or must re-learn  
		*all* Plug-In Provisioning information, bypassing this table.

		When the value of umc1SystemPitProvTableChangeSeqNum is zero this table 
		is empty."
	::= { umc1SystemPitProv 3 }


	umc1SystemPitProvChgEntry OBJECT-TYPE
	   SYNTAX Umc1SystemPitProvChgEntry
	   ACCESS not-accessible
	   STATUS mandatory
	   DESCRIPTION
		   "An entry in the Plug-In Provisioning Change table."
	   INDEX { umc1SystemPitProvChgSeqNbr }
	   ::= { umc1SystemPitProvChgTable 1 }


	Umc1SystemPitProvChgEntry ::=
	   SEQUENCE {   umc1SystemPitProvChgSeqNbr        INTEGER,
			umc1SystemPitProvChgData          OCTET STRING
	   }


	umc1SystemPitProvChgSeqNbr OBJECT-TYPE
	   SYNTAX INTEGER
	   ACCESS read-only
	   STATUS mandatory
	   DESCRIPTION
		"This object's value matches the value of umc1SystemPitProvTableChangeSeqNum 
		at the time the row was created. A valid value of this object is in the range 
		of 1 through umc1SystemPitProvTableChangeSeqNum."
	::= { umc1SystemPitProvChgEntry 1 }

	umc1SystemPitProvChgData OBJECT-TYPE
	   SYNTAX OCTET STRING     (SIZE (6..255))
	   ACCESS read-only
	   STATUS mandatory
	   DESCRIPTION
	        "This object records the location of the Plug-in, type of the Plug-In, nature 
	        of the change (add/modify/delete) and, possibly, the database record associated 
	        with the change that has been made to the Plug-in Provisioning Table. The format 
	        of the object is as follows:
	        octet 0: Version number of the octet representation. The version number 
	        	 for the initial implementation will be 0x01.
	        octet 1: Terminal Identifier of the Plug-in.
	        octet 2: Shelf Identifier of the Plug-in.
	        octet 3: Slot Identifier of the Plug-in.
	        octet 4: High-order octet of the plug-in type of the Plug-in.
	        octet 5: Low-order octet of the plug-in type of the Plug-in.
	        octet 6: Action octet, stores the action (update/delete) performed on the 
	        	 umc1SystemPitProvTable. See DbActionType for valid values of this octet.
                
	        In case of a delete action octet 6 is the last octet in the octet string. Otherwise,
	        more octets are present and they are defined as follows:
	        octet 7: DB specifier octet
	        octet 8 through the last octet contain the database record.
	        	"
	   ::= { umc1SystemPitProvChgEntry 2 }



	umc1SystemPitProvTableChangeSeqNum OBJECT-TYPE
        SYNTAX INTEGER (1..2147483647)
		ACCESS read-only
		STATUS mandatory
		DESCRIPTION
		"A sequence number used to indicate that the PlugIn Provisioning 
		Table, umc1SystemPitProvTable, has been modified and it needs to 
		be re-read. Whenever the SNMP agent is restarted, this value will 
		be reset to 0(zero). The value will be incremented by one whenever 
		a change to the PlugIn Provisioning Table has been made. This number 
		will also be sent in the umc1TrapPitProvChgTableChangeUpd trap and 
		can be used to determine if any traps have been lost by the manager. 
		This value will be incremented before the trap is sent.

		The maximum value it can assume is 2,147,483,647. An increment, 
		every time it has reached its maximum value, shall cause it to 
		be reset to 1.
		"
   ::= { umc1SystemPitProv 4 }


--
-- Facility Alarm String Table
--

umc1FacAlmStringTableChangeSeqNum OBJECT-TYPE
    SYNTAX INTEGER (1..2147483647)
    ACCESS read-only
    STATUS mandatory
    DESCRIPTION
     "A sequence number used to indicate that facility alarm 
     description string table has been modified and it needs to be 
     re-read. Whenever the SNMP agent is restarted, this value will 
     be reset to 0(zero). The value will be incremented by one 
     whenever a change to the facility alarm description string 
     table is made. This number will also be sent in the 
     umc1TrapFacAlmStringTableChange trap and can be used to 
     determine if any traps have been lost. This value will be 
     incremented before the trap is sent.

     The maximum value it can assume is 2,147,483,647. An increment, 
     every time it has reached its maximum value, shall cause it to 
     be reset to 1.
     " 
    ::= { umc1SystemPitProv 5 }



umc1FacAlmStringTable OBJECT-TYPE
    SYNTAX SEQUENCE OF Umc1FacAlmStringEntry
    ACCESS not-accessible
    STATUS mandatory
    DESCRIPTION
     "This table contains facility alarm description strings for a 
     given plugin in a UMC system. SNMP GET-NEXT operation is not 
     allowed. 
     "
    ::= { umc1SystemPitProv 6 }

Umc1FacAlmStringEntry ::= 
    SEQUENCE {umc1FacAlmStringTerminalId   TerminalIdType,
              umc1FacAlmStringShelfId      ShelfIdType,
              umc1FacAlmStringSlotId       SlotIdType,
              umc1FacAlmStringFacilityId   INTEGER,
              umc1FacAlmStringPluginType   PlugInType,
              umc1FacAlmStringData         DisplayString
             }


umc1FacAlmStringEntry OBJECT-TYPE
    SYNTAX Umc1FacAlmStringEntry 
    ACCESS not-accessible
    STATUS mandatory
    DESCRIPTION
     "An entry in the facility alarm description strings table."
    INDEX { umc1FacAlmStringTerminalId, 
            umc1FacAlmStringShelfId, 
            umc1FacAlmStringSlotId,
            umc1FacAlmStringFacilityId,
            umc1FacAlmStringPluginType 
      }
    ::= { umc1FacAlmStringTable 1 }


umc1FacAlmStringTerminalId OBJECT-TYPE
    SYNTAX TerminalIdType
    ACCESS read-write
    STATUS mandatory
    DESCRIPTION
     "Identifier of a terminal."
    ::= { umc1FacAlmStringEntry 1 }


umc1FacAlmStringShelfId OBJECT-TYPE
    SYNTAX ShelfIdType
    ACCESS read-write
    STATUS mandatory
    DESCRIPTION
     "Identifier of a shelf."
    ::= { umc1FacAlmStringEntry 2 }

umc1FacAlmStringSlotId OBJECT-TYPE
    SYNTAX SlotIdType
    ACCESS read-write
    STATUS mandatory
    DESCRIPTION
     "Identifier of a slot."
    ::= { umc1FacAlmStringEntry 3 }

umc1FacAlmStringFacilityId OBJECT-TYPE
    SYNTAX INTEGER
    ACCESS read-write
    STATUS mandatory
    DESCRIPTION
     "Identifier of a port on a card. The range of the value depends on  
     the plugin-type of the card. If the card does not have a port use 0xFF.
     "
    ::= { umc1FacAlmStringEntry 4 }


umc1FacAlmStringPluginType OBJECT-TYPE
    SYNTAX PlugInType
    ACCESS read-write
    STATUS mandatory
    DESCRIPTION
     "This object identifies the plug-in type (PIT) of a card in 
     the UMC system.
     "
    ::= { umc1FacAlmStringEntry 5 }

umc1FacAlmStringData OBJECT-TYPE
    SYNTAX DisplayString (SIZE(0..255))
    ACCESS read-write
    STATUS mandatory
    DESCRIPTION
     "This object contains the facility alarm string description. In 
     order to delete an alarm string the user *MUST* perform a SET 
     operation with a string containing just the NULL character.

     In the current UMC Release the maximum length of a facility alarm
     description string is 20 characters..

     The string is not terminated by a NULL character.
     "
    ::= { umc1FacAlmStringEntry 6 }



umc1FacAlmStringChgTable OBJECT-TYPE
    SYNTAX SEQUENCE OF  Umc1FacAlmStringChgEntry
    ACCESS not-accessible
    STATUS mandatory
    DESCRIPTION
     "The EMS uses this table to synchronize its internal 
     representation of the facility alarm description strings with 
     that managed by the UMC Agent. A trap is issued to the EMS 
     indicating that a change to the facility alarm description 
     string database (and hence the umc1FacAlmStringTable) has been 
     made and entered as a row in this table. The EMS queries this 
     table, using the sequence number received in the 
     umc1TrapFacAlmStringTableChange trap, to determine whether it 
     can re-learn the changed umc1FacAlmStringTable row/record from 
     this table or must re-learn *all* strings, bypassing this table.

     When the value of umc1FacAlmStringTableChangeSeqNum is zero 
     this table is empty.
     "
    ::= { umc1SystemPitProv 7 }


umc1FacAlmStringChgEntry OBJECT-TYPE
    SYNTAX  Umc1FacAlmStringChgEntry
    ACCESS not-accessible
    STATUS mandatory
    DESCRIPTION
     "An entry in the facility alarm description string table 
     change history table.
     "
    INDEX { umc1FacAlmStringChgSeqNum}
    ::= {  umc1FacAlmStringChgTable 1 }


Umc1FacAlmStringChgEntry ::=
    SEQUENCE { umc1FacAlmStringChgSeqNum    INTEGER,
               umc1FacAlmStringChgData      OCTET STRING }


umc1FacAlmStringChgSeqNum OBJECT-TYPE
    SYNTAX INTEGER
    ACCESS read-only
    STATUS mandatory
    DESCRIPTION
     "This object's value matches the value of 
     umc1FacAlmStringTableChangeSeqNum at the time the row was 
     created. A valid value of this object is in the range of 1 
     through umc1FacAlmStringTableChangeSeqNum.
     "
    ::= {  umc1FacAlmStringChgEntry 1 }


umc1FacAlmStringChgData OBJECT-TYPE
    SYNTAX OCTET STRING     (SIZE (1..255))
    ACCESS read-only
    STATUS mandatory
    DESCRIPTION
     "This object records the changes to umc1FacAlmStringTable.
     In the initial implementation the first octet, octet[0] 
     will store the version number of the octet representation 
     being used to define the changed provisioning data. The 
     version number for the initial implementation will be 0x01.

     For Version number 0x01 the remaining octets will be defined 
     as follows:

       octet[1] action octet, stores the action (update/delete) 
                performed on the umc1FacAlmStringTable. See 
                DbActionType for valid values of this octet.
       octet[2] Terminal Identifier.
       octet[3] Shelf Identifier.
       octet[4] Slot Identifier
       octet[5] Facility Identifier.
       octet[6] Bits 15..8 of the plugin type.
       octet[7] Bits 7..0  of the plugin type.
       octet[8]-[x]  The facility alarm description string record 
                     that was create/modified/deleted. The string
                     will be terminated by a NULL character.
      "
     ::= {  umc1FacAlmStringChgEntry 2 }


--
-- TL1 Interface Provisioning
--

umc1TL1IfProvTableChangeSeqNum OBJECT-TYPE
    SYNTAX INTEGER (1..2147483647)
    ACCESS read-only
    STATUS mandatory
    DESCRIPTION
     "A sequence number used to indicate that TL1 interface 
     provisioning table has been modified and it needs to be 
     re-read. Whenever the SNMP agent is restarted, this value will 
     be reset to 0(zero). The value will be incremented by one 
     whenever a change to the TL1 interface provisioning table
     is made. This number will also be sent in the 
     umc1TrapTL1IfProvTableChange trap and can be used to 
     determine if any traps have been lost. This value will be 
     incremented before the trap is sent.

     The maximum value it can assume is 2,147,483,647. An increment, 
     every time it has reached its maximum value, shall cause it to 
     be reset to 1.
     " 
    ::= { umc1SystemPitProv 8 }



umc1TL1IfProvTable OBJECT-TYPE
    SYNTAX SEQUENCE OF Umc1TL1IfProvEntry
    ACCESS not-accessible
    STATUS mandatory
    DESCRIPTION
     "This table contains TL1 interface provisioning for a given 
     OSI card in a UMC system. SNMP GET-NEXT operation is not 
     allowed. 
     "
    ::= { umc1SystemPitProv 9 }

Umc1TL1IfProvEntry ::= 
    SEQUENCE {umc1TL1IfProvTerminalId   TerminalIdType,
              umc1TL1IfProvShelfId      ShelfIdType,
              umc1TL1IfProvSlotId       SlotIdType,
              umc1TL1IfProvInterfaceId  INTEGER,
              umc1TL1IfProvPluginType   PlugInType,
              umc1TL1IfProvData         OCTET STRING
             }


umc1TL1IfProvEntry OBJECT-TYPE
    SYNTAX Umc1TL1IfProvEntry 
    ACCESS not-accessible
    STATUS mandatory
    DESCRIPTION
     "An entry in the TL1 interface provisioning table."
    INDEX { umc1TL1IfProvTerminalId, 
            umc1TL1IfProvShelfId, 
            umc1TL1IfProvSlotId,
            umc1TL1IfProvInterfaceId
      }
    ::= { umc1TL1IfProvTable 1 }


umc1TL1IfProvTerminalId OBJECT-TYPE
    SYNTAX TerminalIdType
    ACCESS read-write
    STATUS mandatory
    DESCRIPTION
     "Identifier of a terminal."
    ::= { umc1TL1IfProvEntry 1 }


umc1TL1IfProvShelfId OBJECT-TYPE
    SYNTAX ShelfIdType
    ACCESS read-write
    STATUS mandatory
    DESCRIPTION
     "Identifier of a shelf."
    ::= { umc1TL1IfProvEntry 2 }

umc1TL1IfProvSlotId OBJECT-TYPE
    SYNTAX SlotIdType
    ACCESS read-write
    STATUS mandatory
    DESCRIPTION
     "Identifier of a slot."
    ::= { umc1TL1IfProvEntry 3 }

umc1TL1IfProvInterfaceId OBJECT-TYPE
    SYNTAX INTEGER
    ACCESS read-write
    STATUS mandatory
    DESCRIPTION
     "Identifier of a TL1 interface on the OSI card. The range of  
     the value is between 1 (one) and 6 (six).
     "
    ::= { umc1TL1IfProvEntry 4 }


umc1TL1IfProvPluginType OBJECT-TYPE
    SYNTAX PlugInType
    ACCESS read-write
    STATUS mandatory
    DESCRIPTION
     "This object identifies the plug-in type (PIT) of a card in 
     the UMC system.
     "
    ::= { umc1TL1IfProvEntry 5 }


umc1TL1IfProvData OBJECT-TYPE
    SYNTAX OCTET STRING (SIZE(1..255))
    ACCESS read-write
    STATUS mandatory
    DESCRIPTION
     "This object contains the TL1 interface provisioning database. In the 
     current UMC Release the maximum length of a TL1 interface provisioning 
     database is 15 octets. For the initial implementation the OCTET 
     representation will be as follows :

      octet[0]	Version number of the octet representation. The version number 
               for the initial implementation will be 0x01.

     For Version number 0x01 the remaining octets will be defined as follows:
		octet[1]        DB specifier octet.
		octet[2]        TL1 Type
		octet[3-10]	    Record Type

	 The values of octet[3] to octet[10] will depends on value of TL1 Type octet.
	    TL1 Type	Meaning			Value of Record Type
		0 			Disabled 		Octet[3]-octet[10] will be Zero
		1			Asynchronous	Octet[3]-octet[10] will be Zero
		2			SVC				Octet[3]-octet[10] represents Binary Coded 
									Decimal(BCD) for Data Terminal Number(DTN)
		3			PVC				Octet[3]represents Logical Channel Number 
									Octet[4]-octet[10] will be Zero

     In order to delete a TL1 interface provisioning database record, the 
     Management Station *MUST* perform a SET and send an octet string of length 
     2 octets (for the version octet and the DB specifier octet) with octet[0] 
     set to a valid version number, octet[1] set to the valid DB Specifier 
     and with NO additional data octets supplied.
     "
    ::= { umc1TL1IfProvEntry 6 }



umc1TL1IfProvChgTable OBJECT-TYPE
    SYNTAX SEQUENCE OF  Umc1TL1IfProvChgEntry
    ACCESS not-accessible
    STATUS mandatory
    DESCRIPTION
     "The EMS uses this table to synchronize its internal 
     representation of the TL1 interface provisioning with 
     that managed by the UMC Agent. A trap is issued to the EMS 
     indicating that a change to the TL1 interface provisioning 
     database (and hence the umc1TL1IfProvTable) has been made and
     entered as a row in this table. The EMS queries this table, 
     using the sequence number received in the 
     umc1TrapTL1IfProvTableChange trap, to determine whether it 
     can re-learn the changed umc1TL1IfProvTable row/record from 
     this table or must re-learn *all* TL1 interface provisioning 
     database records, bypassing this table.

     When the value of umc1TL1IfProvTableChangeSeqNum is zero 
     this table is empty.
     "
    ::= { umc1SystemPitProv 10 }


umc1TL1IfProvChgEntry OBJECT-TYPE
    SYNTAX  Umc1TL1IfProvChgEntry
    ACCESS not-accessible
    STATUS mandatory
    DESCRIPTION
     "An entry in the TL1 interface provisioning table 
     change history table.
     "
    INDEX { umc1TL1IfProvChgSeqNum}
    ::= {  umc1TL1IfProvChgTable 1 }


Umc1TL1IfProvChgEntry ::=
    SEQUENCE { umc1TL1IfProvChgSeqNum    INTEGER,
               umc1TL1IfProvChgData      OCTET STRING }


umc1TL1IfProvChgSeqNum OBJECT-TYPE
    SYNTAX INTEGER
    ACCESS read-only
    STATUS mandatory
    DESCRIPTION
     "This object's value matches the value of 
     umc1TL1IfProvTableChangeSeqNum at the time the row was 
     created. A valid value of this object is in the range of 1 
     through umc1TL1IfProvTableChangeSeqNum.
     "
    ::= {  umc1TL1IfProvChgEntry 1 }


umc1TL1IfProvChgData OBJECT-TYPE
    SYNTAX OCTET STRING     (SIZE (1..255))
    ACCESS read-only
    STATUS mandatory
    DESCRIPTION
     "This object records the changes to umc1TL1IfProvTable.
     In the initial implementation the first octet, octet[0] 
     will store the version number of the octet representation 
     being used to define the changed provisioning data. The 
     version number for the initial implementation will be 0x01.

     For Version number 0x01 the remaining octets will be defined 
     as follows:

      octet[1] action octet, stores the action (update/delete) 
               performed on the umc1TL1IfProvTable. See 
               DbActionType for valid values of this octet.
      octet[2] Terminal Identifier.
      octet[3] Shelf Identifier.
      octet[4] Slot Identifier
      octet[5] Interface Identifier.
      Octet[6] Bit 15..8 of Plugin Type
	  Octet[7] Bit  0..7 of Plugin Type
      Octet[8] TL1 Type
	  Octet[9-16] Record Type

	 See the description of umc1TL1IfProvData for the possible values TL1
     Type and Record Type octet.

      "
     ::= {  umc1TL1IfProvChgEntry 2 }



---
-- Features supported by the CPU Load.
---
	umc1CpuSoftwareFeatures OBJECT-TYPE
	SYNTAX 	OCTET STRING (SIZE (1..255))
	ACCESS	read-only
	STATUS	mandatory
	DESCRIPTION
		"This object lists the features built into the UMC system.
		 The list information required by the IPMI and EMS to determine
         the type of features the UMC system supports, and hence, what
         the EMS and IPMI Agent can manage.
        
         octet[0]	Version number of the octet representation being used to 
                    define this information.  The version number for the  
                    initial implementation will be 0x01.

         For Version number 0x01 the remaining octets will be defined as 
         follows :

         octet[1]	CPU Application Version  
         octet[2]	CPU Application Revision  
         octet[3]	CPU Application Point
         
         octet[4]   High-order 8-bits (MSB) CPU Application CRC-16
         octet[5]   Low-order  8-bits (LSB) CPU Application CRC-16
         octet[6]	Represents National Standards. The valid values and
		            their corresponding meanings are: 
			    Value   Meaning
                            =====   =======
			    0x01    North American (ANSI)
			    0x02    European Telecommunications Standards 
                                    International (ETSI)

         octet[7]   Max Terminals the CPU can support
         octet[8]   Max Shelves   the CPU can support
         octet[9]   Bit Mapped representation of Supported Languages
			    Value   Meaning
                            =====   =======
                            0x01    English
			    0x02	French           
			    0x04	Portuguese
			    0x08	Spanish
			    0x10	Hungarian
			    0x20	Russian
         octet[10]  Max GR303 Groups the CPU can support
         octet[11]  Max TR08  Groups the CPU can support
         octet[12]  Max Number of Plug-in types the CPU supports: MSB
         octet[13]  Max Number of Plug-in types the CPU supports: LSB
        "
     ::= { umc1System 4 } 



    umc1SystemRelearnTrapSeqNum OBJECT-TYPE
     SYNTAX 	INTEGER
     ACCESS	read-only
     STATUS	mandatory
     DESCRIPTION
	"A sequence number used to indicate the number of times the ACO operation has
	been performed since the agent last restarted. Whenever the SNMP agent is
	restarted, this value will be reset to 0 (zero).  This number will also
	be sent in the umc1TrapSytemRelearnTrap trap and can be used to determine if
	any traps have been lost. The value will be incremented before the trap
	is sent." 
    ::= { umc1System 5 } 


    umc1RestrictedAccess OBJECT-TYPE
     SYNTAX     INTEGER
	{ 
          enable(1),
	  disable(2)
	}
     ACCESS	read-write
     STATUS	mandatory
     DESCRIPTION
	"A change in the value of certain MIB objects could be service affecting. Henceforth,
	such objects are called restricted objects. The object umc1RestrictedAccess is
	used to control a SET operation on the restricted objects. A SET to the
	umc1RestrictedAccess object (set to enable) must precede a SET to restricted objects
	in the same PDU. Further, a SET to the umc1RestrictedAccess object (set
	to disable) must follow a SET to restricted objects in the same PDU. 

	A GET operation to read its value shall always return the value disable."
    ::= { umc1System 6 }





--
--  Services Groups
--

--  This section defines the MIB variables that are applicable to
--  the UMC service groups.  Currently the groups supported are the GR303 
--  and TR08 groups.  
--

    umc1Service OBJECT IDENTIFIER ::= { umc1System 7 }

--  GR303 Tables and definitions


    umc1GR303Grp OBJECT IDENTIFIER ::=  { umc1Service 1 }

    umc1GR303TableChangeSeqNum OBJECT-TYPE
        SYNTAX INTEGER (1..2147483647)
	ACCESS read-only
	STATUS mandatory
        DESCRIPTION
        "A sequence number used to indicate that the GR-303 group 
         provisioning Table, umc1GR303Table, has been modified and 
         it needs to be re-read. Whenever the SNMP agent is restarted, 
         this value will be reset to 0(zero). The value will be 
         incremented by one whenever a change to the GR-303 group 
         provisioning table is made. This number will also be sent 
         in the umc1TrapGR303TableChange trap and can be used to 
         determine if the manager has lost any traps. This value will 
         be incremented before the trap is sent.

	 The maximum value it can assume is 2,147,483,647. An increment, 
	 every time it has reached its maximum value, shall cause it to 
	 be reset to 1.
        " 
       ::= { umc1GR303Grp 1 }


    umc1GR303Table OBJECT-TYPE
        SYNTAX SEQUENCE OF Umc1GR303Entry
        ACCESS not-accessible
        STATUS mandatory
        DESCRIPTION
        "A Management Station uses this table to read, modify, create or 
         delete a GR-303 Group in the UMC system. The MIB Table has two 
         columns one for the Index and one for the Group provisioning 
         information. It is currently indexed by the GR-303 Group Number 
         value.
        "
        ::= { umc1GR303Grp 2 }

    umc1GR303Entry OBJECT-TYPE
        SYNTAX Umc1GR303Entry
        ACCESS not-accessible
        STATUS mandatory
        DESCRIPTION
        "An entry in the GR-303 Group Provisioning Table."
        INDEX { umc1Gr303Index }
        ::= { umc1GR303Table 1 }

    Umc1GR303Entry ::= 
        SEQUENCE {  umc1Gr303Index	OCTET STRING,
		    umc1Gr303Data	OCTET STRING }

    umc1Gr303Index OBJECT-TYPE
        SYNTAX OCTET STRING (SIZE (1..255))
        ACCESS read-write
        STATUS mandatory
        DESCRIPTION
        "It contains the Terminal and GR-303 Group number that identifies 
         the record in the UMC system.  For the initial implementation the 
         OCTET representation will be as follows:

         octet[0] Version number of the octet representation being used to 
                  define this INDEX.  The version number for the initial 
                  implementation will be 0x01.

         For Version number 0x01 the remaining octets will be defined as 
         follows :
	 octet[1]   DB specifier octet for the type of GR-303 
                    record being referenced.
         octet[2]   Terminal number the GR-303 Group is associated with.  
                    See 'TerminalIdType' for the definition of valid Terminal
                    values. Currently, only (Terminal equal LET) is valid for 
                    this field.
         octet[3]   GR-303 Group number of the GR-303 Group to retrieve.  
                    The Group number is 1 based (i.e., set this to 0x01 for 
                    GR-303 Group 1, 0x02 for GR-303 Group 2, etc.
        "
        ::= { umc1GR303Entry 1 }


    umc1Gr303Data OBJECT-TYPE
        SYNTAX OCTET STRING (SIZE(0..255))
        ACCESS read-write
        STATUS mandatory
        DESCRIPTION
        "The GR-303 Group Provisioning record. 
         For the initial implementation the OCTET representation will be as 
         follows :
         octet[0]   Version number of the octet representation being used to 
                    define the following provisioning data.  The version 
                    number for the initial implementation will be 0x01.

         For Version number 0x01 the remaining octets will be defined as 
         follows:
         Octet[1]   DB Specifier octet
         Octet[2] - [n]	Octet packed GR-303 Group Provisioning record.

         In a GET Request the data field is empty. In a SET Request it contains
         the GR-303 provisioning record. 

         In order to delete a GR-303 Group, the Management Station *MUST* 
         perform a SET and send an octet string of length 2 octets (for the 
         version octet and the DB specifier octet) with octet[0] set to a valid 
	 version number, octet[1] set to the valid DB Specifier and with 
         NO additional data octets supplied.
        "
        ::= { umc1GR303Entry 2 }


    umc1GR303ChgTable OBJECT-TYPE
        SYNTAX SEQUENCE OF Umc1GR303ChgEntry
        ACCESS not-accessible
        STATUS mandatory
        DESCRIPTION
        "The EMS uses this table to synchronize its internal representation of
         the GR-303 Group Provisioning data with that managed by the UMC Agent.
         A trap is issued to the EMS indicating that a change to the GR-303 
         database (and hence the umc1GR303Table) has been made and entered as 
         a row in this table. The EMS queries this table, using the sequence 
         number received in the umc1TrapGR303TableChange trap, to determine 
         whether it can re-learn the changed umc1GR303Table row/record from 
         this table or must re-learn *all* GR-303 information, bypassing this 
         table.

         When the value of umc1GR303TableChangeSeqNum is zero this table 
         is empty.
        "
        ::= { umc1Service 2 }

    umc1GR303ChgEntry OBJECT-TYPE
        SYNTAX Umc1GR303ChgEntry
        ACCESS not-accessible
        STATUS mandatory
        DESCRIPTION
        "An entry in the GR-303 Group Provisioning Table Change history 
         table.
        "
        INDEX {umc1GR303ChgSeqNum}
        ::= { umc1GR303ChgTable 1 }

    Umc1GR303ChgEntry ::=
        SEQUENCE    { 
                    umc1GR303ChgSeqNum  INTEGER,
                    umc1GR303ChgData    OCTET STRING
                    }

    umc1GR303ChgSeqNum OBJECT-TYPE
        SYNTAX INTEGER
        ACCESS read-only
        STATUS mandatory
        DESCRIPTION
        "This objects value matches the value of umc1GR303TableChangeSeqNum 
         at the time the row was created. A valid value of this object is in 
         the range of 1 through umc1GR303TableChangeSeqNum.
        "
        ::= { umc1GR303ChgEntry 1 }

    umc1GR303ChgData OBJECT-TYPE
        SYNTAX OCTET STRING     (SIZE (1..255))
        ACCESS read-only
        STATUS mandatory
        DESCRIPTION
        "This object records the changes to the GR-303 Group Provisioning 
         table.  For the initial implementation the OCTET representation 
         will be as follows:
         octet[0]   Version number of the octet representation being used 
                    to define the following changed provisioning data.  
                    The version number for the initial implementation will 
                    be 0x01.

         For Version number 0x01 the remaining octets will be defined as 
         follows:
         octet[1] action octet, stores the action (update/delete) 
                  performed on the umc1GR303Table. See DbActionType 
                  for valid values of this octet.
	 octet[2] DB specifier octet
         octet[3]-[n]	The octet packed GR-303 Group Provisioning record 
                        that was create/modified/deleted.
        "
        ::= { umc1GR303ChgEntry 2 }


--  TR08 Tables and definitions

    umc1TR8Grp OBJECT IDENTIFIER ::=  { umc1Service 3 }

    umc1TR8TableChangeSeqNum OBJECT-TYPE
        SYNTAX INTEGER (1..2147483647)
        ACCESS read-only
        STATUS mandatory
        DESCRIPTION
        "A sequence number used to indicate that the TR-8 group provisioning 
         Table, umc1TR8Table, has been modified and it needs to be re-read. 
         Whenever the SNMP agent is restarted, this value will be reset to 
         0(zero). The value will be incremented by one whenever a change to 
         the TR-8 group provisioning table is made. This number will also be
         sent in the mc1TrapTR8TableChange trap and can be used to determine
         if the manager has lost any traps. This value will be incremented 
         before the trap is sent.

	 The maximum value it can assume is 2,147,483,647. An increment, 
	 every time it has reached its maximum value, shall cause it to 
	 be reset to 1.
        " 
        ::= { umc1TR8Grp 1 }


    umc1TR8Table OBJECT-TYPE
        SYNTAX SEQUENCE OF Umc1TR8Entry
        ACCESS not-accessible
        STATUS mandatory
        DESCRIPTION
        "A Management Station uses this table to read, modify, create or 
         delete a TR-8 Group in the UMC system. The MIB Table has two columns
         one for the Index and one for the Group provisioning information. 
        "
        ::= { umc1TR8Grp 2 }


    umc1TR8Entry OBJECT-TYPE
        SYNTAX Umc1TR8Entry
        ACCESS not-accessible
        STATUS mandatory
        DESCRIPTION
        "An entry in the TR-8 Group Provisioning Table."
        INDEX { umc1TR8Index }
        ::= { umc1TR8Table 1 }

    Umc1TR8Entry ::= 
        SEQUENCE { umc1TR8Index		OCTET STRING,
		   umc1TR8Data		OCTET STRING }

    umc1TR8Index OBJECT-TYPE
        SYNTAX OCTET STRING (SIZE (1..255))
        ACCESS read-write
        STATUS mandatory
        DESCRIPTION
        "It contains the Terminal and TR-8 Group number that identifies the
         record in the UMC system. For the initial implementation the OCTET 
         representation will be as follows:
         octet[0] Version number of the octet representation being used to 
                  define this INDEX. The version number for the initial 
                  implementation will be 0x01.

         For Version number 0x01 the remaining octets will be defined as 
         follows:

	 octet[1] DB specifier octet for the type of TR-8 
                  record being referenced.
         octet[2] Terminal number the TR-8 Group is associated with.  
                  See 'TerminalIdType' for the definition of valid Terminal
                  values.
         octet[3] TR-8 Group number of the TR-8 Group to retrieve.  The 
                  Group number is 1 based (i.e., set this to 0x01 for TR-8 
                  Group 1, 0x02 for TR-8 Group 2, etc.
        "
        ::= { umc1TR8Entry 1 }


    umc1TR8Data OBJECT-TYPE
        SYNTAX OCTET STRING (SIZE(0..255))
        ACCESS read-write
        STATUS mandatory
        DESCRIPTION
        "The TR-8 Group Provisioning record. For the initial implementation 
         the OCTET representation will be as follows:
         octet[0] Version number of the octet representation being used to 
                  define the following provisioning data.  The version 
                  number for the initial implementation will be 0x01.

         For Version number 0x01 the remaining octets will be defined 
         as follows:
         octet[1] DB specifier octet
         octet[2]-[n]   Octet packed TR-8 Group Provisioning record.

         In a GET Request the data field is empty. In a SET Request it 
         contains the TR-8 provisioning record. 

         In order to delete a TR-8 Group, the Management Station *MUST* 
         perform a SET and send an octet string of length 2 octets 
         (for the version and DB specifier octets) with octet[0] set to 
         a valid version number and octet[1] set to a valid DB type.  
         No additional data octets should be supplied.
        "
        ::= { umc1TR8Entry 2 }

    umc1TR8ChgTable OBJECT-TYPE
        SYNTAX SEQUENCE OF Umc1TR8ChgEntry
        ACCESS not-accessible
        STATUS mandatory
        DESCRIPTION
        "The EMS uses this table to synchronize its internal representation 
         of the TR-8 Group Provisioning data with that managed by the UMC 
         Agent.  A trap is issued to the EMS indicating that a change to the 
         TR-8 database (and hence the umc1TR8Table) has been made and entered 
         as a row in this table. The EMS queries this table, using the sequence
         number received in the umc1TrapTR8TableChange trap, to determine 
         whether it can re-learn the changed umc1TR8Table row/record from this 
         table or must re-learn *all* TR-8 information, bypassing this table.

         When the value of umc1TR8TableChangeSeqNum is zero this table is 
         empty.
        "
        ::= { umc1Service 4 }


    umc1TR8ChgEntry OBJECT-TYPE
        SYNTAX Umc1TR8ChgEntry
        ACCESS not-accessible
        STATUS mandatory
        DESCRIPTION
        "An entry in the TR-8 Group Provisioning Table Change history 
         table.
        "
        INDEX {umc1TR8ChgSeqNum}
        ::= { umc1TR8ChgTable 1 }


    Umc1TR8ChgEntry ::=
        SEQUENCE    { 
                    umc1TR8ChgSeqNum    INTEGER,
                    umc1TR8ChgData      OCTET STRING
                    }

    umc1TR8ChgSeqNum OBJECT-TYPE
        SYNTAX INTEGER
        ACCESS read-only
        STATUS mandatory
        DESCRIPTION
        "This objects value matches the value of umc1TR8TableChangeSeqNum 
         at the time the row was created. A valid value of this object is 
         in the range of 1 through umc1TR8TableChangeSeqNum.
        "
        ::= { umc1TR8ChgEntry 1 }

    umc1TR8ChgData OBJECT-TYPE
        SYNTAX OCTET STRING     (SIZE (1..255))
        ACCESS read-only
        STATUS mandatory
        DESCRIPTION
        "This object records the changes to the TR-08 Group Provisioning table.
         For the initial implementation the OCTET representation will be as 
         follows:
         octet[0] Version number of the octet representation being used to 
                  define the following changed provisioning data.  The 
                  version number for the initial implementation will be 0x01.

         For Version number 0x01 the remaining octets will be defined as 
         follows:
         octet[1] action octet, stores the action (update/delete) 
                  performed on the umc1Tr8Table. See DbActionType 
                  for valid values of this octet.
         octet[2] DB specifier octet
         octet[3]-[n]   The octet packed TR-08 Group Provisioning record that
                        was create/modified/deleted.
        "
        ::= { umc1TR8ChgEntry 2 }


--  V5 Tables and definitions

--The V5 Object Group provides a unified interface to access, modify
--or delete V5.1 or V5.2 group provisioning data, variant provisioning
--data and C-Channel provisioning data (V5.2 only). 

    umc1V5Grp OBJECT IDENTIFIER ::=  { umc1Service 5 }

    umc1V5TableChangeSeqNum OBJECT-TYPE
        SYNTAX INTEGER (1..2147483647)
        ACCESS read-only
        STATUS mandatory
        DESCRIPTION
        "A sequence number used to indicate that the V5 provisioning Table,
         umc1V5Table, has been modified and it needs to be re-read. 
         Whenever the SNMP agent is restarted, this value will be reset to 
         0(zero). The value will be incremented by one whenever a change to 
         the V5 provisioning table is made. This number will also be sent in
         the umc1TrapV5TableChange trap and can be used to determine if the 
         manager has lost any traps. This value will be incremented before
         the trap is sent.

         The maximum value it can assume is 2,147,483,647. An increment, 
         every time it has reached its maximum value, shall cause it to 
         be reset to 1.
        " 
        ::= { umc1V5Grp 1 }


    umc1V5Table OBJECT-TYPE
        SYNTAX SEQUENCE OF Umc1V5Entry
        ACCESS not-accessible
        STATUS mandatory
        DESCRIPTION
        "A Management Station uses this table to read, modify, create or 
         delete V5.1 or V5.2 groups, variant records and C-Channel records 
	 (V5.2 only) in the UMC system. The MIB Table has two columns
         one for the Index and one for the provisioning information. 
        "
        ::= { umc1V5Grp 2 }


    umc1V5Entry OBJECT-TYPE
        SYNTAX Umc1V5Entry
        ACCESS not-accessible
        STATUS mandatory
        DESCRIPTION
        "An entry in the V5 Provisioning Table."
        INDEX { umc1V5Index }
        ::= { umc1V5Table 1 }


    Umc1V5Entry ::= 
        SEQUENCE { umc1V5Index	OCTET STRING,
		   umc1V5Data	OCTET STRING }


    umc1V5Index OBJECT-TYPE
        SYNTAX OCTET STRING (SIZE (4..5))
        ACCESS read-write
        STATUS mandatory
        DESCRIPTION
        "It contains the indices that identify a V5 record in the UMC system.
	 The format of the indices depends on the type of the record that will
	 be accessed. There are three (3) types of records, namely, Group 
	 provisioning records, Variant provisioning records and C-Channel 
         provisioning records (V5.2 only). For the initial implementation the 
         OCTET representation for each type of record is given below.
		 
         octet[0] Version number of the octet representation being used to define 
                  this INDEX. The version number for the initial implementation
                  will be 0x01.

         For Version number 0x01 the remaining octets will be defined as 
         follows for each type of record:

	 1. For V5 Group Provisioning records.

	    octet[1]  DB specifier octet.
            octet[2]  Terminal number the V5 Group is associated with.  
                      See 'TerminalIdType' for the definition of valid Terminal
                      values.
            octet[3]  Group number the V5 Group is associated with.  The 
                      See 'V5GroupIdType' for the definition of valid Group
                      values.

	 2. For V5 Variant Provisioning records.

	     octet[1]  DB specifier octet.
             octet[2]  Terminal number the V5 Variant is associated with.  
                       See 'TerminalIdType' for the definition of valid Terminal
                       values.
             octet[3]  Group number the V5 Variant is associated with.  The 
                       See 'V5GroupIdType' for the definition of valid Group
                       values.
             octet[4]  Variant identifier of the V5 Variant. Valid values are 0x00
                       and 0x01.

	 3. For V5.2 C-Channel Provisioning records.

	     octet[1]  DB specifier octet.
             octet[2]  Terminal number the V5.2 C-Channel is associated with.  
                       See 'TerminalIdType' for the definition of valid Terminal
                       values.
             octet[3]  Group number the V5.2 C-Channel is associated with.  The 
                       See 'V5GroupIdType' for the definition of valid Group
                       values.
             octet[4]  C-Channel Set identifier. A valid value of the C-Channel Set 
                       identifier lies between 0x00 through 0x03. 
        "
        ::= { umc1V5Entry 1 }


    umc1V5Data OBJECT-TYPE
        SYNTAX OCTET STRING (SIZE(0..255))
        ACCESS read-write
        STATUS mandatory
        DESCRIPTION
        "The V5 Provisioning record. For the initial implementation the OCTET
         representation will be as follows:
         octet[0]   Version number of the octet representation being used to 
                    define the following provisioning data.  The version 
                    number for the initial implementation will be 0x01.

         For Version number 0x01 the remaining octets will be defined 
         as follows:
         octet[1]       DB specifier octet
         octet[2]-[n]   Octet packed V5 Provisioning record.

         In a GET Request the data field is empty. In a SET Request it 
         contains the V5 provisioning record. See the definition of umc1V5Index
	 for the types V5 provisioning records.

         In order to delete a V5 provisioning record, the Management Station *MUST* 
         perform a SET and send an octet string of length 2 octets 
         (for the version and DB specifier octets) with octet[0] set to 
         a valid version number and octet[1] set to a valid DB type.  
         No additional data octets should be supplied.
        "
        ::= { umc1V5Entry 2 }


    umc1V5ChgTable OBJECT-TYPE
        SYNTAX SEQUENCE OF Umc1V5ChgEntry
        ACCESS not-accessible
        STATUS mandatory
        DESCRIPTION
        "The EMS uses this table to synchronize its internal representation 
         of the V5 Provisioning data with that managed by the UMC Agent. A
         trap is issued to the EMS indicating that a change to the 
         V5 database (and hence the umc1V5Table) has been made and entered 
         as a row in this table. The EMS queries this table, using the sequence
         number received in the umc1TrapV5TableChange trap, to determine 
         whether it can re-learn the changed umc1V5Table row/record from this 
         table or must re-learn *all* V5 information, bypassing this table.

         When the value of umc1V5TableChangeSeqNum is zero this table is 
         empty.
        "
        ::= { umc1Service 6 }


    umc1V5ChgEntry OBJECT-TYPE
        SYNTAX Umc1V5ChgEntry
        ACCESS not-accessible
        STATUS mandatory
        DESCRIPTION
        "An entry in the V5 Provisioning Table Change history table.
        "
        INDEX {umc1V5ChgSeqNum}
        ::= { umc1V5ChgTable 1 }


    Umc1V5ChgEntry ::=
        SEQUENCE    { 
                    umc1V5ChgSeqNum    INTEGER,
                    umc1V5ChgData      OCTET STRING
                    }


    umc1V5ChgSeqNum OBJECT-TYPE
        SYNTAX INTEGER
        ACCESS read-only
        STATUS mandatory
        DESCRIPTION
        "This objects value matches the value of umc1V5TableChangeSeqNum 
         at the time the row was created. A valid value of this object is 
         in the range of 1 through umc1V5TableChangeSeqNum.
        "
        ::= { umc1V5ChgEntry 1 }



    umc1V5ChgData OBJECT-TYPE
        SYNTAX OCTET STRING     (SIZE (1..255))
        ACCESS read-only
        STATUS mandatory
        DESCRIPTION
        "This object records the changes to the V5 Provisioning table.
         In the initial implementation the first octet, octet[0]  will
         store the version number of the octet representation being used to 
         define the changed provisioning data. The version number for the 
         initial implementation will be 0x01.

         For Version number 0x01 the remaining octets will be defined as 
         follows:
          octet[1]  Holds the number of database records in this object.

          The packed octet representation of each record is given below
           octet[2]  Length of a record.
           octet[3]  action octet, stores the action (update/delete) performed
                     on the umc1V5Table. See DbActionType for valid values of 
                     this octet.
           octet[4]  DB specifier octet
           octet[5]-[x]  The octet packed V5 Provisioning record that was 
		         create/modified/deleted.
        "
        ::= { umc1V5ChgEntry 2 }




--
--  Cross Connects (narrow and broadband
--

--  This section defines the MIB variables that are applicable to
--  the UMC cross connects.  The cross connect group stores information about 
--  all groomed, standard, TR08, GR303, ATM, V5.1, V5.2 and Nx64 cross connects 
--  in the system.
--

	umc1XConnect OBJECT IDENTIFIER ::=  { umc1System 8 }

--  Cross connect Tables and definitions

umc1XCTableChangeSeqNum OBJECT-TYPE
    SYNTAX INTEGER (1..2147483647)
    ACCESS read-only
    STATUS mandatory
    DESCRIPTION
    "A sequence number used to indicate that the cross connect Table, 
     umc1XCTable, has been modified and it needs to be re-read. Whenever 
     the SNMP agent is restarted, this value will be reset to 0(zero). 
     The value will be incremented by one whenever a change to the 
     cross connect Table is made. This number will also be sent in the 
     umc1TrapXCTableChange trap and can be used to determine if the manager 
     has lost any trap. This value will be incremented before the trap is 
     sent.

     The maximum value it can assume is 2,147,483,647. An increment, 
     every time it has reached its maximum value, shall cause it to 
     be reset to 1.
    " 
    ::= { umc1XConnect 1 }

    umc1XCTable OBJECT-TYPE
        SYNTAX SEQUENCE OF Umc1XCEntry
        ACCESS not-accessible
        STATUS mandatory
        DESCRIPTION
        "A Management Station uses this table to read/update/delete a 
         cross connect in the UMC system. Call Reference Numbers (CRNs) 
         identify the end-points of a cross connect in the UMC system. 
         The CRNs could be of variable size. Every cross connect has 
         two end-points: a CRN IN and a CRN OUT. The MIB Table has 
         two columns one for each CRN. It is indexed by the CRN IN 
         value.
        "
        ::= { umc1XConnect 2 }

    umc1XCEntry OBJECT-TYPE
        SYNTAX Umc1XCEntry
        ACCESS not-accessible
        STATUS mandatory
        DESCRIPTION
        "An entry in the cross connect Table."
        INDEX { umc1XCIndex }
        ::= { umc1XCTable 1 }

    Umc1XCEntry ::= 
    SEQUENCE {  umc1XCIndex		OCTET STRING,
		umc1XCData		OCTET STRING }

    umc1XCIndex OBJECT-TYPE
        SYNTAX OCTET STRING (SIZE (1..255))
        ACCESS read-write
        STATUS mandatory
        DESCRIPTION
        "It contains one end-point of a cross connect in the UMC system, 
         i.e., the CRN IN number.  For the initial implementation the 
         OCTET representation will be as follows:
         octet[0]   Version number of the octet representation being used to 
                    define the cross connect data.  The version number for 
                    the initial implementation will be 0x01.

         For Version number 0x01 the remaining octets will be defined as 
         follows :
	 octet[1]       DB specifier octet for the type of cross connect 
                        record being referenced.
         Octet[2] - [n] Octet packed CRN IN of cross connect.
        "
        ::= { umc1XCEntry 1 }

    umc1XCData OBJECT-TYPE
        SYNTAX OCTET STRING (SIZE(0..255))
        ACCESS read-write
        STATUS mandatory
        DESCRIPTION
        "The cross connect record. 
         For the initial implementation the OCTET representation will be as 
         follows:
         octet[0]   Version number of the octet representation being used to 
                    define the cross connect data.  The version number for 
                    the initial implementation will be 0x01.

         For Version number 0x01 the remaining octets will be defined 
         as follows :
         Octet[1]       DB Specifier octet
         Octet[2] - [n] Entire cross connect record (i.e. both CRN IN
                        & CRN OUT).

         In a GET Request the data field is empty. 
         In a SET Request it contains the new cross connect record. 

         In order to delete a cross connect, the Management Station *MUST* 
         perform a SET and send an octet string of length 2 octets 
         (for the version and DB specifier octets) with octet[0] set to 
         a valid version number and octet[1] set to a valid DB type.  
         No additional data octets should be supplied.
        "
        ::= { umc1XCEntry 2 }


    umc1XCChgTable OBJECT-TYPE
        SYNTAX SEQUENCE OF Umc1XCChgEntry
        ACCESS not-accessible
        STATUS mandatory
        DESCRIPTION
        "The EMS uses this table to synchronize its internal representation 
         of the cross connect data with that managed by the UMC Agent.  
         A trap is issued to the EMS indicating that a change to the 
         cross connect database has been made and entered as a row in this 
         table. The EMS queries this table, using the sequence number received 
         in the umc1TrapXCChange trap, to determine whether it can re-learn the 
         changed cross connect database record from this table or must re-learn 
         *all* cross connect information, bypassing this table.

         When the value of umc1XCChangeSeqNum is zero this table is empty.
        "
        ::= { umc1XConnect 3 }


    umc1XCChgEntry OBJECT-TYPE
        SYNTAX Umc1XCChgEntry
        ACCESS not-accessible
        STATUS mandatory
        DESCRIPTION
        "An entry in the cross connect Table Change history table."
        INDEX { umc1XCChgSeqNum }
        ::= { umc1XCChgTable 1 }



    Umc1XCChgEntry ::=
        SEQUENCE    { 
                    umc1XCChgSeqNum     INTEGER,
                    umc1XCChgData       OCTET STRING
                    }


    umc1XCChgSeqNum OBJECT-TYPE
        SYNTAX INTEGER
        ACCESS read-only
        STATUS mandatory
        DESCRIPTION
        "This objects value matches the value of umc1XCTableChangeSeqNum at 
         the time the row was created. A valid value of this object is in 
         the range of 1 through umc1XCTableChangeSeqNum.
        "
        ::= { umc1XCChgEntry 1 }


    umc1XCChgData OBJECT-TYPE
        SYNTAX OCTET STRING     (SIZE (1..255))
        ACCESS read-only
        STATUS mandatory
        DESCRIPTION
        "This object records the changes made to the cross connect table.  
         For the initial implementation the OCTET representation will be 
         as follows :
         octet[0]   Version number of the octet. The version number for the 
                    initial implementation will be 0x01.

         For Version number 0x01 the remaining octets will be defined 
         as follows :
         octet[1]       action octet, stores the action (update/delete) 
                        performed on the umc1XCTable. See DbActionType 
                        for valid values of this octet.
         octet[2]       DB specifier octet
         octet[3] - [n] The octet packed cross connect record that was 
                        create/modified/deleted
        "
        ::= { umc1XCChgEntry 2 }



-- A new object group, umc1Security, has been added to 
-- the MIB to store information for User Security Data. 

 umc1Security OBJECT IDENTIFIER ::= { umc1System 17 }


 umc1SecurityDataTableChangeSeqNum OBJECT-TYPE
    SYNTAX INTEGER (1..2147483647)
    ACCESS read-only
    STATUS mandatory
    DESCRIPTION
     "A sequence number used to indicate that the User Security 
      Data Table, umc1SecurityDataTable, has been modified and it 
      needs to be re-read. Whenever the SNMP agent is restarted, 
      this value will be reset to 0(zero). The value will be 
      incremented by one whenever a change to the User Security 
      Data Table is made. This number will also be sent in the 
      umc1TrapSecurityDataTableChange trap and can be used to 
      determine if the manager has lost any traps. This value will 
      be incremented before the trap is sent.

      The maximum value it can assume is 2,147,483,647. An increment, 
      every time it has reached its maximum value, shall cause it to 
      be reset to 1.
     "
   ::= { umc1Security 1 }



 umc1SecurityDataTable OBJECT-TYPE
   SYNTAX SEQUENCE OF Umc1SecurityDataEntry
   ACCESS not-accessible
   STATUS mandatory
   DESCRIPTION
    "A Management Station uses this table to read, modify, create or 
     delete an User Security Data in the UMC system. The MIB Table has 
     two columns one for the Index and one for the User Security
     Information. It is currently indexed by the User Number. In order
     to delete a User Security Data record the Management Station *MUST*
     perform a PUT operation with all octets of umc1SecurityDataTableData
     (defined shortly) to 0x00.
    "
   ::= { umc1Security 2 }


 umc1SecurityDataEntry OBJECT-TYPE
   SYNTAX Umc1SecurityDataEntry
   ACCESS not-accessible
   STATUS mandatory
   DESCRIPTION
    "An entry in the User Security Data Table."
   INDEX { umc1SecurityDataTableIndex }
   ::= { umc1SecurityDataTable 1 }


 Umc1SecurityDataEntry ::= 
   SEQUENCE {umc1SecurityDataTableIndex		OCTET STRING,
             umc1SecurityDataTableData		OCTET STRING }


 umc1SecurityDataTableIndex OBJECT-TYPE
   SYNTAX OCTET STRING (SIZE(1..255))
   ACCESS read-write
   STATUS mandatory
   DESCRIPTION
    "It contains the User Number that identifies the record in the UMC 
     system. For the initial implementation the OCTET representation will 
     be as follows:
      octet[0]	Version number of the octet representation being used to define 
	        this INDEX. The version number for the initial implementation 
	        will be 0x01.

      For Version number 0x01 the remaining octets will be defined as follows:

        octet[1]  DB specifier octet for the type of User Security  record 
		  being referenced.
	octet[2]  User Number with the User Security Data record is 
		  associated. It can take value from 0 to 29."
   ::= { umc1SecurityDataEntry 1 }


 umc1SecurityDataTableData OBJECT-TYPE
   SYNTAX OCTET STRING (SIZE(0..255))
   ACCESS read-write
   STATUS mandatory
   DESCRIPTION
    "The User security Data record.  For the initial implementation the
     OCTET representation will be as follows:
       octet[0]	 Version number of the octet representation being used to
                 define the following provisioning data. The version number
                 for the initial implementation will be 0x01.

       For Version number 0x01 the remaining octets will be defined as 
       follows:
        octet[1]       DB specifier octet
        octet[2] - [n] Octet packed encrypted User Security Data record.

     In a GET Request the data field is empty. 
     In a SET Request it contains the User Security Data record. 

     In order to delete a User Security Data, the Management Station *MUST*
     perform a SET and send an octet string of length 2 octets (for the 
     version octet and the DB specifier octet) with octet[0] set to a valid
     version number, octet[1] set to a valid DB specifier value and with NO
     additional data octets supplied.
    "
   ::= { umc1SecurityDataEntry 2 }




 umc1SecurityDataChgTable OBJECT-TYPE
   SYNTAX SEQUENCE OF Umc1SecurityDataChgEntry
   ACCESS not-accessible
   STATUS mandatory
   DESCRIPTION
    "The EMS uses this table to synchronize its internal representation of 
     the User Security data with that managed by the UMC Agent. A trap is 
     issued to the EMS indicating that a change to the User Security data 
     (and hence the umc1securityDataTable) has been made and entered as a 
     row in this table. The EMS queries this table, using the sequence 
     number received in the umc1TrapSecurityDataTableChange trap, to 
     determine whether it can re-learn the changed umc1SecurityDataTable 
     row/record from this table or must re-learn *all* User Security data, 
     bypassing this table.

     When the value of umc1SecurityDataTableChangeSeqNum is zero this table 
     is empty.
    "
::= { umc1Security 3 }



 umc1SecurityDataChgEntry OBJECT-TYPE
   SYNTAX Umc1SecurityDataChgEntry
   ACCESS not-accessible
   STATUS mandatory
   DESCRIPTION
     "An entry in the User Security Data Table Change history 
      table."
   INDEX { umc1SecurityDataChgSeqNum }
   ::= { umc1SecurityDataChgTable 1 }


 Umc1SecurityDataChgEntry ::=
   SEQUENCE { 
        umc1SecurityDataChgSeqNum       INTEGER,
        umc1SecurityDataChgData         OCTET STRING
   }


 umc1SecurityDataChgSeqNum OBJECT-TYPE
   SYNTAX INTEGER
   ACCESS read-only
   STATUS mandatory
   DESCRIPTION
     "This object's value matches the value of 
      umc1SecurityTableTableChangeSeqNum at the time the row was created.
      A valid value of this object is in the range of 1 through 
      umc1SecurityTableTableChangeSeqNum.
     "
   ::= { umc1SecurityDataChgEntry 1 }


 umc1SecurityDataChgData OBJECT-TYPE
   SYNTAX OCTET STRING     (SIZE (1..255))
   ACCESS read-only
   STATUS mandatory
   DESCRIPTION
     "This object records the changes to the User Security Data table. For 
      the initial implementation the OCTET representation will be as follows:
        octet[0]  Version number of the octet representation being used to 
                  define the following changed provisioning data. The version 
                  number for the initial implementation will be 0x01.

        For Version number 0x01 the remaining octets will be defined as follows:
         octet[1]  action octet, stores the action (update/delete) on the 
                   umc1SecurityDataTable. See DbActionType for valid values and 
                   meaning of this octet.
         octet[2]  DB specifier octet
	   octet[3]  User Number
         octet[4] - [n] The octet packed encrypted User Security Data record  
                        that was create/modified/deleted.
      "
   ::= { umc1SecurityDataChgEntry 2 }


--
--  Inter terminal and inter sheld SPANs
--

--	This section defines the MIB variables that are applicable to
--	the UMC shelf and terminal connections (Spans).  
--

-- Inter Terminal Spans

    umc1TerminalSpanTableChangeSeqNum OBJECT-TYPE
        SYNTAX INTEGER (1..2147483647)
        ACCESS read-only
        STATUS mandatory
        DESCRIPTION
        "A sequence number used to indicate that the Terminal Span table, 
         umc1TerminalSpanTable, has been modified and it needs to be 
         re-read. Whenever the SNMP agent is restarted, this value will be 
         reset to 0(zero). The value will be incremented by one whenever a 
         change to the Terminal Span table has been made. This number will 
         also be sent in the umc1TrapTerminalSpanTableChange trap and can 
         be used to determine if any traps have been lost. This value will 
         be incremented before the trap is sent.

	 The maximum value it can assume is 2,147,483,647. An increment, 
	 every time it has reached its maximum value, shall cause it to 
	 be reset to 1.
        " 
        ::= { umc1Span 1 }


    umc1TerminalSpanTable OBJECT-TYPE
        SYNTAX SEQUENCE OF Umc1TerminalSpanTableEntry
        ACCESS not-accessible
        STATUS mandatory
        DESCRIPTION
	 "This table contains current information about all Span 
         Connecting two terminals in a UMC system.
        "
        ::= { umc1Span 2 }

    Umc1TerminalSpanTableEntry ::= 
        SEQUENCE {
	        umc1TermSpanNearEndTerminalId   TerminalIdType,
	        umc1TermSpanNearEndShelfId      ShelfIdType,
	        umc1TermSpanNearEndSlotId       SlotIdType,
	        umc1TermSpanNearEndPitType      PlugInType,
	        umc1TermSpanFarEndTerminalId    TerminalIdType,
	        umc1TermSpanFarEndShelfId       ShelfIdType,
	        umc1TermSpanFarEndSlotId        SlotIdType
            }

    umc1TerminalSpanTableEntry OBJECT-TYPE
        SYNTAX Umc1TerminalSpanTableEntry 
        ACCESS not-accessible
        STATUS mandatory
        DESCRIPTION
        "An entry in the Terminal Span table."
        INDEX   { 
                umc1TermSpanNearEndTerminalId,
                umc1TermSpanNearEndShelfId,
                umc1TermSpanNearEndSlotId 
                }
        ::= { umc1TerminalSpanTable 1 }

    umc1TermSpanNearEndTerminalId OBJECT-TYPE
        SYNTAX TerminalIdType
        ACCESS read-only
        STATUS mandatory
        DESCRIPTION
        "The Terminal ID of a terminal at the near end of the span."
        ::= { umc1TerminalSpanTableEntry 1 }

    umc1TermSpanNearEndShelfId OBJECT-TYPE
        SYNTAX ShelfIdType
        ACCESS read-only
        STATUS mandatory
        DESCRIPTION
        "The Shelf ID of a shelf at the near end of span."
        ::= { umc1TerminalSpanTableEntry 2 }

    umc1TermSpanNearEndSlotId OBJECT-TYPE
        SYNTAX SlotIdType
        ACCESS read-only
        STATUS mandatory
        DESCRIPTION
        "The Slot ID of a slot at the near end of span."
        ::= { umc1TerminalSpanTableEntry 3 }

    umc1TermSpanNearEndPitType OBJECT-TYPE
        SYNTAX PlugInType
        ACCESS read-only
        STATUS mandatory
        DESCRIPTION
        "The plug-in type at at the near end of span."
        ::= { umc1TerminalSpanTableEntry 4 }

    umc1TermSpanFarEndTerminalId OBJECT-TYPE
        SYNTAX TerminalIdType
        ACCESS read-only
        STATUS mandatory
        DESCRIPTION
        "The Terminal ID of a terminal at the far end of span."
        ::= { umc1TerminalSpanTableEntry 5 }

    umc1TermSpanFarEndShelfId OBJECT-TYPE
        SYNTAX ShelfIdType
        ACCESS read-only
        STATUS mandatory
        DESCRIPTION
        "The shelf ID of a shelf at the far end of span."
        ::= { umc1TerminalSpanTableEntry 6 }

    umc1TermSpanFarEndSlotId OBJECT-TYPE
        SYNTAX SlotIdType
        ACCESS read-only
        STATUS mandatory
        DESCRIPTION
        "The Slot ID of a slot at the far end of span."
        ::= { umc1TerminalSpanTableEntry 7 }

    umc1TerminalSpanTableChangeHistoryTable OBJECT-TYPE
        SYNTAX SEQUENCE OF Umc1TerminalSpanTableChangeHistoryEntry
        ACCESS not-accessible
        STATUS mandatory
        DESCRIPTION
        "This table records the near end and far end location of the inter 
         terminal span whose addition/deletion to the UMC system caused the 
         agent to emit umc1TrapTerminalSpanTableChange trap. The contents of
         the table are indexed by the value of 
         umc1TerminalSpanTableChangeSeqNum. When the value of 
         umc1TerminalSpanTableChangeSeqNum is zero the history table is empty.
         A management station shall query this table, using the value of 
         umc1TerminalSpanTableChangeSeqNum received in 
         umc1TrapTerminalSpanTableChange trap to determine if it can detect 
         the new terminal span that have been added to the system. If it 
         does not find such a row in this table it must re-read the entire 
         umc1TerminalSpanTable table.
        "
        ::= { umc1Span 3 }


    Umc1TerminalSpanTableChangeHistoryEntry ::= 
        SEQUENCE    {
                    umc1TerminalSpanTableChangeHistoryIndex INTEGER,
                    umc1TerminalSpanTableChangeHistoryData  OCTET STRING
                    }

    umc1TerminalSpanTableChangeHistoryEntry OBJECT-TYPE
        SYNTAX Umc1TerminalSpanTableChangeHistoryEntry
        ACCESS not-accessible
        STATUS mandatory
        DESCRIPTION
        "An entry in the history table."
        INDEX { umc1TerminalSpanTableChangeHistoryIndex }
        ::= { umc1TerminalSpanTableChangeHistoryTable 1 }

    umc1TerminalSpanTableChangeHistoryIndex OBJECT-TYPE
        SYNTAX INTEGER
        ACCESS read-only
        STATUS mandatory
        DESCRIPTION
        "This objects value matches the value of 
         umc1TerminalSpanTableChangeSeqNum at the time the row was created. 
         A valid value of this object is in the range of 1 through 
         umc1TerminalSpanTableChangeSeqNum.
        "
        ::= { umc1TerminalSpanTableChangeHistoryEntry 1 }

    umc1TerminalSpanTableChangeHistoryData OBJECT-TYPE
        SYNTAX OCTET STRING (SIZE (1..255))
        ACCESS read-only
        STATUS mandatory
        DESCRIPTION
        "This object stores the near end and far end location of all inter 
         terminal spans that were added to/deleted from the UMC system when 
         umc1TrapTerminalSpanTableChange trap was emitted by the agent with 
         umc1TerminalSpanTableChangeHistoryIndex sequence number. The 
         umc1TerminalSpanTableChangeHistoryData contains multiple terminal 
         span entries corresponding to the all inter terminal spans that 
         were added to/deleted from the UMC system. Each entry in the 
         umc1TerminalSpanTableChangeHistoryData consisting of action byte 
         followed by packed terminal span record. 
         For initial implementation the OCTET representation will be as 
         follows:

         Octet[0]   Version number (currently 0x01)

         For version 0x01
         octet[1]   Holds the number of spans in this history record.

         octets[2] through [11] hold the packed record for the 1st Terminal
         Span being reported and are defined as follows.
	   Octet[2]   Length of record. 
         Octet[3]   Action octet which specifies that the record attached 
                    after the action object has been added to/deleted from 
                    the umc1TerminalSpanTable. See DbActionType for valid 
                    values and meaning of this octet.
         Octet[4]   Near End Terminal Id
         Octet[5]   Near End Shelf Id
         Octet[6]   Near End Slot Id
         Octet[7-8] Near End plug-in type	
         Octet[9]   Far End Terminal Id
         Octet[10]  Far End Shelf Id
         Octet[11]  Far End Slot Id

         octets[12] through [20] hold the packed record for the next Terminal 
         and so forth, until up to octet[1] number of spans have been defined.
        "
        ::= { umc1TerminalSpanTableChangeHistoryEntry 2 }


-- Inter Shelf (EBC/ELU) spans

    umc1ShelfSpanTableChangeSeqNum OBJECT-TYPE
        SYNTAX INTEGER (1..2147483647)
        ACCESS read-only
        STATUS mandatory
        DESCRIPTION
        "A sequence number used to indicate that the Shelf Span table, 
         umc1ShelfSpanTable, has been modified and it needs to be re-read. 
         Whenever the SNMP agent is restarted, this value will be reset to 
         0(zero). The value will be incremented by one whenever a change to 
         the Shelf Span table has been made. This number will also be sent 
         in the umc1TrapShelfSpanTableChange trap and can be used to determine
         if any traps have been lost. This value will be incremented before 
         the trap is sent.

	 The maximum value it can assume is 2,147,483,647. An increment, 
	 every time it has reached its maximum value, shall cause it to 
	 be reset to 1.
        " 
        ::= { umc1Span 4 }


    umc1ShelfSpanTable OBJECT-TYPE
        SYNTAX SEQUENCE OF Umc1ShelfSpanTableEntry
        ACCESS not-accessible
        STATUS mandatory
        DESCRIPTION
        "This table contains current EBC/ELU links in a terminal in a UMC
         system. The near end of shelf span is always at EBC card and far 
         end of shelf span at ELU card.
        "
        ::= { umc1Span 5 }


    Umc1ShelfSpanTableEntry ::= 
        SEQUENCE    {
                    umc1ShelfSpanNearEndTerminalId  TerminalIdType,
                    umc1ShelfSpanNearEndShelfId     ShelfIdType,
                    umc1ShelfSpanNearEndSlotId      SlotIdType,
                    umc1ShelfSpanNearEndPitType     PlugInType,
                    umc1ShelfSpanFarEndShelfId      ShelfIdType,
                    umc1ShelfSpanFarEndSlotId       SlotIdType,
                    umc1ShelfSpanFarEndPitType      PlugInType
                    }


    umc1ShelfSpanTableEntry OBJECT-TYPE
        SYNTAX Umc1ShelfSpanTableEntry 
        ACCESS not-accessible
        STATUS mandatory
        DESCRIPTION
        "An entry in the Shelf Span table."
        INDEX { umc1ShelfSpanNearEndTerminalId,
                umc1ShelfSpanNearEndShelfId,
                umc1ShelfSpanNearEndSlotId }
        ::= { umc1ShelfSpanTable 1 }

    umc1ShelfSpanNearEndTerminalId OBJECT-TYPE
        SYNTAX TerminalIdType
        ACCESS read-only
        STATUS mandatory
        DESCRIPTION
        "The Terminal ID of a terminal to which the requested shelf span 
         belongs.
        "
        ::= { umc1ShelfSpanTableEntry 1 }


    umc1ShelfSpanNearEndShelfId OBJECT-TYPE
        SYNTAX ShelfIdType
        ACCESS read-only
        STATUS mandatory
        DESCRIPTION
        "The Shelf ID of a shelf to which near end of requested shelf 
         span belongs.
        "
        ::= { umc1ShelfSpanTableEntry 2 }


    umc1ShelfSpanNearEndSlotId OBJECT-TYPE
        SYNTAX SlotIdType
        ACCESS read-only
        STATUS mandatory
        DESCRIPTION
        "The slot ID of a slot to which near end of requested shelf 
         span belongs.
        "
        ::= { umc1ShelfSpanTableEntry 3 }


    umc1ShelfSpanNearEndPitType OBJECT-TYPE
        SYNTAX PlugInType
        ACCESS read-only
        STATUS mandatory
        DESCRIPTION
        "The plug-in type at the near end of span."
        ::= { umc1ShelfSpanTableEntry 4 }


    umc1ShelfSpanFarEndShelfId OBJECT-TYPE
        SYNTAX ShelfIdType
        ACCESS read-only
        STATUS mandatory
        DESCRIPTION
        "The Shelf ID of a shelf to which far end of requested shelf 
         span belongs.
        "
        ::= { umc1ShelfSpanTableEntry 5 }


    umc1ShelfSpanFarEndSlotId OBJECT-TYPE
        SYNTAX SlotIdType
        ACCESS read-only
        STATUS mandatory
        DESCRIPTION
        "The slot ID of a slot to which far end of requested shelf 
         span belongs.
        "
        ::= { umc1ShelfSpanTableEntry 6 }


    umc1ShelfSpanFarEndPitType OBJECT-TYPE
        SYNTAX PlugInType
        ACCESS read-only
        STATUS mandatory
        DESCRIPTION
        "The plug-in type at the far end of span."
        ::= { umc1ShelfSpanTableEntry 7 }


    umc1ShelfSpanTableChangeHistoryTable OBJECT-TYPE
        SYNTAX SEQUENCE OF Umc1ShelfSpanTableChangeHistoryEntry
        ACCESS not-accessible
        STATUS mandatory
        DESCRIPTION
        "This table records the near end and far end location of the inter 
         shelf span whose addition/deletion to the UMC system caused the 
         agent to emit umc1TrapShelfSpanTableChange trap. The contents of 
         the table are indexed by the value of umc1ShelfSpanTableChangeSeqNum.
         When the value of umc1ShelfSpanTableChangeSeqNum is zero the history 
         table is empty.
         A management station shall query this table, using the value of 
         umc1ShelfSpanTableChangeSeqNum received in 
         umc1TrapShelfSpanTableChange trap to determine if it can detect 
         the new shelf span that have been added to the system. If it does 
         not find such a row in this table it must re-read the entire 
         umc1ShelfSpanTable table.
        "
        ::= { umc1Span 6 }


    Umc1ShelfSpanTableChangeHistoryEntry ::= 
        SEQUENCE    {
                    umc1ShelfSpanTableChangeHistoryIndex    INTEGER,
                    umc1ShelfSpanTableChangeHistoryData     OCTET STRING
                    }

    umc1ShelfSpanTableChangeHistoryEntry OBJECT-TYPE
        SYNTAX Umc1ShelfSpanTableChangeHistoryEntry
        ACCESS not-accessible
        STATUS mandatory
        DESCRIPTION
        "An entry in the history table."
        INDEX { umc1ShelfSpanTableChangeHistoryIndex }
        ::= { umc1ShelfSpanTableChangeHistoryTable 1 }

    umc1ShelfSpanTableChangeHistoryIndex OBJECT-TYPE
        SYNTAX INTEGER
        ACCESS read-only
        STATUS mandatory
        DESCRIPTION
        "This objects value matches the value of 
         umc1ShelfSpanTableChangeSeqNum at the time the row was created. 
         A valid value of this object is in the range of 1 through 
         umc1ShelfSpanTableChangeSeqNum.
        "
        ::= { umc1ShelfSpanTableChangeHistoryEntry 1 }

    umc1ShelfSpanTableChangeHistoryData OBJECT-TYPE
        SYNTAX OCTET STRING (SIZE (1..255))
        ACCESS read-only
        STATUS mandatory
        DESCRIPTION
        "This object stores the near end and far end location of all inter 
         shelf spans that were added to/deleted from the UMC system when 
         umc1TrapShelfSpanTableChange trap was emitted by the agent with 
         umc1ShelfSpanTableChangeHistoryIndex sequence number. The 
         umc1ShelfSpanTableChangeHistoryData contains multiple shelf span 
         entries corresponding to the all inter shelf spans that were added 
         to/deleted from the UMC system. Each entry in the 
         umc1ShelfSpanTableChangeHistoryData consisting of action byte 
         followed by packed shelf span record. 
         For initial implementation the OCTET representation will be 
         as follows:

         Octet[0]		Version number (currently 0x01)

         The contents of the remaining octets are defined as follows for
         version 0x01.

         octet[1]  Holds the number of spans in this history record.

         octets[2] through [12] hold the packed record for the 1st Shelf 
         Span being reported.
	 Octet[2]   Length of Record
         Octet[3]   Action object which specifies that the record attached 
                    after the action object has been added to/deleted from 
                    the umc1ShelfSpanTable. See DbActionType for valid 
                    values of this byte.
         Octet[4]   Near End Terminal Id
         Octet[5]   Near End Shelf Id
         Octet[6]   Near End Slot Id
         Octet[7-8] Near End plug-in type	
         Octet[9]   Far End Shelf Id
         Octet[10]  Far End Slot Id
         Octet[11-12]   Far End plug-in type

         octets[13] through [22] hold the packed record for the next Shelf span 
         and so forth, until up to octet[1] number of spans have been defined.
        "
        ::= { umc1ShelfSpanTableChangeHistoryEntry 2 }


--
-- Terminal Wide Information
--

--	This section defines the MIB variables that are applicable to
--	the UMC on a terminal by terminal basis.  It consists of two tables
--	whose columns specify all of the terminal-by-terminal data and
--	a variable that indicates that the table needs to be re-read.
--

umc1TerminalStatusChangeSeqNum OBJECT-TYPE
   SYNTAX INTEGER (1..2147483647)
   ACCESS read-only
   STATUS mandatory
   DESCRIPTION
       "A sequence number used to indicate that the terminal status
       table needs to be read again.  Whenever the SNMP agent is
       restarted, this value will be reset to 0 (zero).  The value
       will be incremented by one whenever a change to the table 
       information has been made. This number will also be
       sent in the umc1TrapTerminalStatusChange trap and can be used to
       determine if any traps have been lost.  The value will be
       incremented before the trap is sent.

       The maximum value it can assume is 2,147,483,647. An increment, 
       every time it has reached its maximum value, shall cause it to 
       be reset to 1.
       "
   ::= { umc1Terminal 1 }

umc1TerminalStatusTable OBJECT-TYPE
   SYNTAX SEQUENCE OF Umc1TerminalStatusEntry
   ACCESS not-accessible
   STATUS mandatory
   DESCRIPTION
       "This table contains the status that is associated with each
       terminal.  There will be an entry in this table for every
       terminal known to the UMC, regardless of whether or not the
       terminal is actually reachable at this moment.  There will
       not be entries in this table for terminals that have never
       been known to exist."
   ::= { umc1Terminal 2 }

umc1TerminalStatusEntry OBJECT-TYPE
   SYNTAX Umc1TerminalStatusEntry
   ACCESS not-accessible
   STATUS mandatory
   DESCRIPTION
       "An entry in the terminal table. The data is indexed by the
       terminal whose data is represented."
   INDEX { umc1TerminalStatusTerminalId }
       ::= { umc1TerminalStatusTable 1 }

Umc1TerminalStatusEntry ::=
   SEQUENCE {
       umc1TerminalStatusTerminalId	TerminalIdType,
       umc1TerminalStatusValue		INTEGER
   }

umc1TerminalStatusTerminalId OBJECT-TYPE
	SYNTAX TerminalIdType
	ACCESS read-only
	STATUS mandatory
	DESCRIPTION
	    "The ID number of the terminal that this row references.  The
	     LET is 1, RST1 is 2, RST2 is 3, etc."
	::= { umc1TerminalStatusEntry 1 }

umc1TerminalStatusValue OBJECT-TYPE
	SYNTAX INTEGER
		{
		normal(1),
		minor(2),
		major(3),
		critical(4),
		unreachable(255)
		}
	ACCESS read-only
	STATUS mandatory
	DESCRIPTION
	   "The status of this terminal, based on the status of the
	   most severe current alarm.  The status of normal means
	   that there are no current alarms present for this terminal.
	   The status of minor means that only minor alarms are
	   currently active.  The status of major means that the worst
	   alarm currently active is of a major status.  Likewise for
	   critical, with the exception that link alarms are not taken
	   into account, as they are associated with the link status (as
	   found in the topology link table). If the terminal cannot be
	   reached due to link outages, then the status is unreachable."
	::= { umc1TerminalStatusEntry 2 }

 
umc1TerminalInfoChangeSeqNum OBJECT-TYPE
	SYNTAX INTEGER
	ACCESS read-only
	STATUS mandatory
	DESCRIPTION
	   "A sequence number used to indicate that the terminal
	   information table needs to be read again.  Whenever the SNMP
	   agent is restarted, this value will be reset to 0 (zero).  The
	   value will be incremented by one whenever a change to the table 
	   information has been made. This number will also be
	   sent in the umc1TrapTerminalInfoChange trap and can be used to
	   determine if any traps have been lost.  The value will be
	   incremented before the trap is sent."
	::= { umc1Terminal 3 }

umc1TerminalInfoTable OBJECT-TYPE
	SYNTAX SEQUENCE OF Umc1TerminalInfoEntry
	ACCESS not-accessible
	STATUS mandatory
	DESCRIPTION
	   "This table contains the provisioning data that is associated
	   with each terminal.  This table has an row for every terminal
	   database entry, regardless of whether or not the terminal is
	   actively known to the UMC.  (In other words, it is possible to
	   view and/or change the data for a terminal that does not
	   exist.)"
	::= { umc1Terminal 4 }

umc1TerminalInfoEntry OBJECT-TYPE
	SYNTAX Umc1TerminalInfoEntry
	ACCESS not-accessible
	STATUS mandatory
	DESCRIPTION
	    "An entry in the terminal provisioning table. The data is
	     indexed by the terminal whose data is represented."
	INDEX { umc1TerminalInfoTerminalId }
	::= { umc1TerminalInfoTable 1 }

 
Umc1TerminalInfoEntry ::=
    SEQUENCE {
	umc1TerminalInfoTerminalId          TerminalIdType,
	umc1TerminalInfoName                DisplayString,
	umc1TerminalInfoSerialDeviceType    INTEGER,
	umc1TerminalInfoBaudRate            INTEGER,
	umc1TerminalInfoNewTerminalId       TerminalIdType
    }

umc1TerminalInfoTerminalId OBJECT-TYPE
    SYNTAX TerminalIdType
    ACCESS read-only
    STATUS mandatory
    DESCRIPTION
	"The ID number of the terminal that this row references."
    ::= { umc1TerminalInfoEntry 1 }

umc1TerminalInfoName OBJECT-TYPE
    SYNTAX DisplayString (SIZE (0..20))
    ACCESS read-write
    STATUS mandatory
    DESCRIPTION
	"The name of the terminal.  If this is the LET, then 
	it also ends up being the initial name of the UMC as a 
	whole. This is not a null-terminated string." 
    ::= { umc1TerminalInfoEntry 2 }

umc1TerminalInfoSerialDeviceType OBJECT-TYPE
    SYNTAX INTEGER
	{
	    modem(1),
	    other(255)
	}
    ACCESS read-write
    STATUS mandatory
    DESCRIPTION
	"Specifies the type of device that is connected to the
	serial port of the terminal."
    ::= { umc1TerminalInfoEntry 3 }
 
umc1TerminalInfoBaudRate OBJECT-TYPE
    SYNTAX INTEGER
	{
	    autobaud(1),
	    baud1200(2),
	    baud2400(3),
	    baud9600(4),
	    other(255)
	}
    ACCESS read-write
    STATUS mandatory
    DESCRIPTION
	"Specifies the current baud rate of the serial port
	of the terminal."
    ::= { umc1TerminalInfoEntry 4 }

umc1TerminalInfoNewTerminalId OBJECT-TYPE
    SYNTAX TerminalIdType
    ACCESS read-write
    STATUS mandatory
    DESCRIPTION
	"The new identifier of the terminal referenced by this 
	row. The terminal shall be rebooted after a successful 
	write. The response to a SET request will refer to the 
	old terminal identifier. Care must be taken to ensure 
	that all cross connects associated with the old 
	terminal identifier value are changed to reflect the 
	new terminal identifier value.

	When read, it contains the current terminal identifier 
	of the terminal referenced by this row."
    ::= { umc1TerminalInfoEntry 5 }


--
-- Alarm Information
--
--      The following tables represent the current alarm information that can
--      be retrieved from the UMC.  
--      The first table is indexed by Terminal number and holds a sequence 
--      number that is used to indicate that the Current Alarm Table needs 
--      to be read again.  Whenever the SNMP agent is restarted, this value 
--      will be reset to 0 (zero).  The value will be incremented by one 
--      whenever Alarm/Event TRAP is issued.  This number will also be
--		sent in the 'umc1AlarmTrap' trap and can be used to determine if 
--      any traps have been lost.  The value will be incremented before 
--      the trap is sent.
--      The second table contains the Currently Active alarms for the UMC 
--      system.  The Current Alarm information is available in two formats
--      (raw and TL1).  The raw representation will be more suitable for 
--      machine processing.  The TL1 representation will be more suitable for
--      direct user display.  Both formats are available via the MIB.


--
--  Alarm Sequence Table Changed Sequence Number
--      This is just a place holder for possible future use
--
umc1AlmSeqTableChangeSeqNum OBJECT-TYPE
    SYNTAX INTEGER (1..2147483647)
 	ACCESS read-only
 	STATUS mandatory
 	DESCRIPTION
 	   "A sequence number used to indicate that the alarm sequence
	   table has been modified and needs to be re-read.  Whenever
	   the SNMP agent restarted, this value will be reset to 0 (zero).
	   The value will be incremented by one whenever a change to the
	   Alarm Sequence table information has been made. This number
	   will also be sent in the umc1AlarmTrap trap and can be used to
 	   determine if any traps have been lost.  The value will be
 	   incremented before the trap is sent.
           
	   The maximum value it can assume is 2,147,483,647. An increment, 
	   every time it has reached its maximum value, shall cause it to 
	   be reset to 1.
		"
 	::= { umc1Alarm 1 }



--
--  Alarm Sequence Table
--
umc1AlmSeqTable OBJECT-TYPE
	SYNTAX SEQUENCE OF Umc1AlmSeqEntry
	ACCESS not-accessible
	STATUS mandatory
	DESCRIPTION
	    "This table contains the sequence numbers for each terminal in
	    a UMC system.  The sequence numbers are used to indicate if the 
            current alarm table for a given Terminal needs to be re-read
            due to missed TRAP updates.  This table is Read Only"
	::= { umc1Alarm 2 }


umc1AlmSeqEntry OBJECT-TYPE
	SYNTAX Umc1AlmSeqEntry
	ACCESS not-accessible
	STATUS mandatory
	DESCRIPTION
	    "A single entry in the Alarm Sequence Table."
    INDEX { umc1AlmSeqTerminalId }
	::= { umc1AlmSeqTable 1 }


Umc1AlmSeqEntry ::= 
        SEQUENCE {
                 umc1AlmSeqTerminalId   TerminalIdType,
                 umc1AlmSeqNumber       INTEGER
                 }


umc1AlmSeqTerminalId OBJECT-TYPE
	SYNTAX TerminalIdType
	ACCESS read-only
	STATUS mandatory
	DESCRIPTION
	    "The Terminal that has generated the alarms we are tracking
             via this sequence number."
	::= { umc1AlmSeqEntry 1 }


umc1AlmSeqNumber OBJECT-TYPE
	SYNTAX INTEGER
	ACCESS read-only
	STATUS mandatory
	DESCRIPTION
            "A counter which gets incremented each time an ALARM or Event
             for this terminal occurs.  It is used to indicate wether the 
             Current Alarm table for this terminal needs to be re-read.
            "
	::= { umc1AlmSeqEntry 2 }



--
--  Current Alarm Table
--
umc1CurAlmTable OBJECT-TYPE
	SYNTAX SEQUENCE OF Umc1CurAlmEntry
	ACCESS not-accessible
	STATUS mandatory
	DESCRIPTION
	   "This table contains the currently active alarms in a UMC system
           (the LET and all of its connected terminals).  Only alarms for 
           reachable terminals are available via this table."
	::= { umc1Alarm 3 }


umc1CurAlmEntry OBJECT-TYPE
	SYNTAX Umc1CurAlmEntry
	ACCESS not-accessible
	STATUS mandatory
	DESCRIPTION
	    "A single entry in the Current Alarm Table."
	INDEX { umc1CurAlmTerminalId, umc1CurAlmOccurrenceIndex }
	::= { umc1CurAlmTable 1 }


Umc1CurAlmEntry ::= 
        SEQUENCE {
                 umc1CurAlmTerminalId       TerminalIdType,
                 umc1CurAlmOccurrenceIndex  OCTET STRING,
                 umc1CurAlmTL1Message       DisplayString,
                 umc1CurAlmDetails          OCTET STRING
                 }


umc1CurAlmTerminalId OBJECT-TYPE
	SYNTAX TerminalIdType
	ACCESS read-only
	STATUS mandatory
	DESCRIPTION
		"The Terminal that has generated the alarm this record
		represents.  The LET is 1, RST1 is 2, RST2 is 3, etc."
	::= { umc1CurAlmEntry 1 }


umc1CurAlmOccurrenceIndex OBJECT-TYPE
	SYNTAX OCTET STRING     (SIZE (8..8))
	ACCESS read-only
	STATUS mandatory
	DESCRIPTION
	"A representation of the relative occurrence of the ALARM/EVENT.
        The contents of the octets in this OBJECT are actually the ONEs
        COMPLEMENT of the values represented, a neccessity due to the
        fact that umc1CurAlmTable entries must be retrievable in reverse
        chronological order as the table is walked.  This would result in
        decrementing column index values as the umc1CurAlmOccurrenceIndex
        column was traversed.  The true occurrence values can be extracted
        from this octet string by taking the COMPLEMENT of each byte
        (with the exception of octets 0 and 1, which must first be
        combined into a 16 bit representation of the year before COMPLEMENTing
        and then broken apart into the High and Low bytes after the COMPLEMENT
        has been accomplished).
        The format of the umc1CurAlmOccurrenceIndex is as follows:
        octet[0]    High 8bits of the YEAR
        octet[1]    Low  8bits of the YEAR
        octet[2]    Month   (January is 1, February is 2, etc.)
        octet[3]    Day     (1 through 31)
        octet[4]    Hour    (0 through 23)
        octet[5]    Minutes (0 through 59)
        octet[6]    Seconds (0 through 59)
        octet[7]    mSec    (0 through 255).  This is an index to
		    differentiate this alarm from any others that 
                    may have occurred in the same second."
	::= { umc1CurAlmEntry 2 }


umc1CurAlmTL1Message OBJECT-TYPE
	SYNTAX DisplayString
	ACCESS read-only
	STATUS mandatory
	DESCRIPTION
	    "This is a TL1 formatted string representing the ALARM/EVENT"
	::= { umc1CurAlmEntry 3 }


umc1CurAlmDetails OBJECT-TYPE
	SYNTAX OCTET STRING
	ACCESS read-only
	STATUS mandatory
	DESCRIPTION
        "This is an encoded representation of the alarm to be reported.
        The format of the encoded data is as follows :
        octet[0]    umc1CurAlmDetails IMPLEMENTATION VERSION.  This will
                    be used to identify the structure of the following data.
                    For IMPLEMENTATION VERSION equal 1 the following data within
                    umc1CurAlmDetails be of the form:
        octet[1]    UMC eFacAlarm value for this alarm/event (High 8-bits).
        octet[2]    UMC eFacAlarm value for this alarm/event (Low  8-bits).
        octet[3]    category (SET=1, CLEAR=2, EVENT=3)
        octet[4]    severity (CRITICAL=1, MAJOR=2, MINOR=3, EVENT=4, STATUS=5)
        octet[5]    PLUG IN TYPE this alarm was generated for (High 8-bits).
        octet[6]    PLUG IN TYPE this alarm was generated for (Low  8-bits).

        octet[7]    alarm misc byte[0]
        octet[8]    alarm misc byte[1]
        octet[9]    alarm misc byte[2]
        octet[10]   alarm misc byte[3]

        octet[11]   LOCATION_TYPE - indicates the format of the following 4 
                                    octets of information.  The valid values
                                    for this field are listed below:
                                        0 = Invalid_data
                                        1 = Term_valid
                                        2 = Shelf_valid
                                        3 = Slot_valid
                                        4 = Circuit_valid
                                        5 = Group_valid
                                    The contents of the following four octets
                                    for each of these types is detailed below.
        
        LOCATION_TYPE equals Invalid_data
        octet[12]   unused - set to zero
        octet[13]   unused - set to zero
        octet[14]   unused - set to zero
        octet[15]   unused - set to zero

        LOCATION_TYPE equals Term_valid
        octet[12]   LOCATION -  Terminal number 
                                (LET = 1, RST1 = 2, RST2 = 3, etc.)
        octet[13]   unused - set to zero
        octet[14]   unused - set to zero
        octet[15]   unused - set to zero

        LOCATION_TYPE equals Shelf_valid
        octet[12]   LOCATION -  Terminal number 
                                (LET = 1, RST1 = 2, RST2 = 3, etc.)
        octet[13]   LOCATION -  Terminal shelf number
        octet[14]   unused - set to zero
        octet[15]   unused - set to zero
        
        LOCATION_TYPE equals Slot_valid
        octet[12]   LOCATION -  Terminal number 
                                (LET = 1, RST1 = 2, RST2 = 3, etc.)
        octet[13]   LOCATION -  Terminal shelf number
        octet[14]   LOCATION -  Shelf slot number
        octet[15]   unused - set to zero

        LOCATION_TYPE equals Circuit_valid
        octet[12]   LOCATION -  Terminal number 
                                (LET = 1, RST1 = 2, RST2 = 3, etc.)
        octet[13]   LOCATION -  Terminal shelf number
        octet[14]   LOCATION -  Shelf slot number
        octet[15]   LOCATION -  Slot circuit number (0 = circuit 0

        LOCATION_TYPE equals Group_valid
        octet[12]   LOCATION -  Terminal number 
                                (LET = 1, RST1 = 2, RST2 = 3, etc.)
        octet[13]   TR08/TR303/etc. Group number (High 8-bits) 
        octet[14]   TR08/TR303/etc. Group number (Low  8-bits)
        octet[15]   unused - set to zero

        octet[16]   COORELATION TAG - High 8-bits of the YEAR
        octet[17]   COORELATION TAG - Low  8-bits of the YEAR
        octet[18]   COORELATION TAG - Month   (January=1, February=2, etc.)
        octet[19]   COORELATION TAG - Day     (1 through 31)
        octet[20]   COORELATION TAG - Hour    (0 through 23)
        octet[21]   COORELATION TAG - Minutes (0 through 59)
        octet[22]   COORELATION TAG - Seconds (0 through 59)
        octet[23]   COORELATION TAG - mSec    (0 through 255).  
                    mSec is an index to differentiate this alarm from any 
                    others that  may have occurred in the same second.

        octet[24]   Term name length in octets, 
                    (eg, 10 if the terminal name is 130 W. Elm).

        octet[25] to        Term name string.  eTNL = (25+Term name length).
        octet[eTNL]             

        octet[eTNL] RAI/Environmental alarm description string length in
                    octets. This is an OPTIONAL string used to present  
                    additional information about RAI or External ALARMS.
                    If the alarm is of one of the types that supports user
                    defined descriptions in the UMC system, that description
                    will be contained in the following string.  If it isnt,
                    or there was no user defined string, this byte will be 
                    set to zero.

        octet[eTNL + 1] to      Environmental alarm description string.
        octet[eEADSTR]          eEADSTR = ((eTNL + 1) + RAI/External Alarm
                                                        description string
                                                        length)."
	::= { umc1CurAlmEntry 4 }



-- Management Interfaces
--	This branch us used to define the mib variables used to control the
--	various UMC management interfaces (TL1, SNMP, TBOS, whatever).  It is
--	broken up into subtrees that are used for each interface type.
--
umc1Snmp	OBJECT IDENTIFIER ::= { umc1ManagerIf 1 } -- snmp agent mgmt

-- SNMP Agent Management
--
--	The following variables and tables represent the information required
--	to manage the SNMP agent on the UMC.  Specifically, it allows the
--	EMS to change the information that would be stored in the UMC's
--	provisioning record for the SNMP Agent.  Note that the data in this
--	section applies to any SNMP Agent in the system (e.g. it is global
--	data) and so does not include any plug-in specific information.

--
-- Community Name Information
--

umc1SnmpCommName OBJECT-TYPE
	SYNTAX DisplayString (SIZE (1..8))
	ACCESS read-write
	STATUS mandatory
	DESCRIPTION
		"The Community Name that allows read and write access to the
		UMC1000 MIB variables.  Changing this variable will take
		immediate effect and so must be done with caution.  Note that
		this value must be initially provisioned via the Craft User
		Interface, as the current value must be known in order to
		change it to something else.  Although its ACCESS field is
		specified as read-write (to get past a MIB compiler issue), it
		is really considered a write-only variable.  The implementation
		is such that a read of the variable will always return an
		empty string."
	::= { umc1Snmp 1 }

--
-- SNMP Trap Generation Information
--

umc1SnmpTrapTypesEnabled OBJECT-TYPE
	SYNTAX INTEGER
	ACCESS read-write
	STATUS mandatory
	DESCRIPTION
		"This is a bit field that specifies which traps, if any, will
		be generated by the SNMP Agent.  If the bit is set, then the
		traps of the indicated type will be generated.  The bits are
		defined as follows:
		|	BIT    HexValue    Description
		|	-----------------------------------------------------
		|    1      0x01        Send standard SNMP traps
		|    2      0x02        Send authentication traps
		|    3      0x04        Send UMC High-level traps
		|    4      0x08        Send detailed UMC alarm traps
		|    5      0x10        Reserved (set to zero)
		|    6      0x20        Reserved (set to zero)
		|    7      0x40        Reserved (set to zero)
		|    8      0x80        Send IPMI Software diagnostic traps"
	::= { umc1Snmp 3 }


umc1SnmpTrapRcvrAddress OBJECT-TYPE
	SYNTAX IpAddress
	ACCESS read-write
	STATUS mandatory
	DESCRIPTION
		"The IP Address of the EMS platform to which traps are to
		be sent."
	::= { umc1Snmp 4 }

umc1SnmpTrapRcvrPort OBJECT-TYPE
	SYNTAX INTEGER
	ACCESS read-write
	STATUS mandatory
	DESCRIPTION
		"The UDP Port to which the traps are sent. The default
		is port 162"
	::= { umc1Snmp 5 }

umc1SnmpMgmtHost2Address OBJECT-TYPE
	SYNTAX IpAddress
	ACCESS read-write
	STATUS mandatory
	DESCRIPTION
		"The IP Address of the EMS platform on a Secondary Management Host
       to which traps are to be sent."
	::= { umc1Snmp 6 }

umc1SnmpMgmtHost2TrapsEnabled OBJECT-TYPE
	SYNTAX INTEGER
	ACCESS read-write
	STATUS mandatory
	DESCRIPTION
		"A boolean value indicating whether this Management Host receives
       traps or not."
	::= { umc1Snmp 7 }

umc1SnmpMgmtHost3Address OBJECT-TYPE
	SYNTAX IpAddress
	ACCESS read-write
	STATUS mandatory
	DESCRIPTION
		"The IP Address of the EMS platform on a Secondary Management Host
       to which traps are to be sent."
	::= { umc1Snmp 8 }

umc1SnmpMgmtHost3TrapsEnabled OBJECT-TYPE
	SYNTAX INTEGER
	ACCESS read-write
	STATUS mandatory
	DESCRIPTION
		"A boolean value indicating whether this Management Host receives
       traps or not."
	::= { umc1Snmp 9 }

umc1SnmpTrustedHostsEnabled OBJECT-TYPE
	SYNTAX INTEGER
	ACCESS read-write
	STATUS mandatory
	DESCRIPTION
		"A boolean value indicating whether Trusted Hosts are enabled or not."
	::= { umc1Snmp 10 }

umc1SnmpTelnetPort OBJECT-TYPE
	SYNTAX INTEGER
	ACCESS read-write
	STATUS mandatory
	DESCRIPTION
		"The TCP Port on which the Telnet Server listens for connection
       requests. The default is port 23."
	::= { umc1Snmp 11 }


--
-- Topology Information
--
--	The following variables and tables represent the information required
--	to determine the topology of the UMC network and the status of the
--	links between the terminals.  Although terminals may be linked by more
--	than one pair of tranceiver cards, there is only one link in
--	this table. The terminals are numbered according to their
--	terminal ID.  For any given link, it is expected that a lower numbered
--	terminal is 'closer' to the LET than a higher numbered one.


umc1TopologyChangeSeqNum OBJECT-TYPE
    SYNTAX INTEGER (1..2147483647)
	ACCESS read-only
	STATUS mandatory
	DESCRIPTION
		"A sequence number used to indicate that the topology link
		table needs to be read again.  Whenever the SNMP agent is
		restarted, this value will be reset to 0 (zero).  The
		value will be incremented by one whenever a change to
		either table has been made. This number will also be
		sent in the umc1TrapTopologyChange trap and can be used to
		determine if any traps have been lost.  The value will be
		incremented before the trap is sent.
		

		The maximum value it can assume is 2,147,483,647. An increment, 
		every time it has reached its maximum value, shall cause it to 
		be reset to 1.
		"
	::= { umc1Topology 1 }

umc1TopologyThisTerminal OBJECT-TYPE
	SYNTAX INTEGER
	ACCESS read-only
	STATUS mandatory
	DESCRIPTION
        "The ID of the terminal that contains the SNMP agent.  This
        may, or may not, identify the root of the topology tree.  The
		root of the toplogy tree is really an abstraction, defined as
		the terminal having the lowest ID number in a UMC network.
		If the umc1TopologyTable has any rows in it, then the smallest
		terminal ID is considered the root of the topology tree.  If
		the umc1TopologyTable empty, then (and only then) can the
		assumption be made that this variable holds the ID of the
		root of the topology tree, since it identifies the only
		known terminal.  Unfortunately, all bets are off if the
		*real* root of the topology tree is unreachable at the time
		of autodiscovery.  The LET is 1, RST1 is 2, RST2 is 3, etc.)"
	::= { umc1Topology 2 }



umc1TopologyLinkTable OBJECT-TYPE
	SYNTAX SEQUENCE OF Umc1TopologyLinkEntry
	ACCESS not-accessible
	STATUS mandatory
	DESCRIPTION
		"The link table.  This table will be empty if only one
		terminal makes up this UMC.  Only active links will be
		in this table.  If a link is lost, then the corresponding
		row in this table will be removed."
	::= { umc1Topology 3 }



umc1TopologyLinkEntry OBJECT-TYPE
	SYNTAX Umc1TopologyLinkEntry
	ACCESS not-accessible
	STATUS mandatory
	DESCRIPTION
		"An entry in the link table."
	INDEX { umc1TopologyLinkTerminalA, umc1TopologyLinkTerminalB  }
	::= { umc1TopologyLinkTable 1 }



Umc1TopologyLinkEntry ::=
	SEQUENCE { 
		umc1TopologyLinkTerminalA	INTEGER,
		umc1TopologyLinkTerminalB	INTEGER
	}



umc1TopologyLinkTerminalA OBJECT-TYPE
	SYNTAX INTEGER
	ACCESS read-only
	STATUS mandatory
	DESCRIPTION
		"The Terminal ID of the terminal closest to the root of the
		network tree.  The terminal IDs start with 1.  (E.g. the LET
		is 1, RST1 is 2, RST2 is 3, etc.)"
	::= { umc1TopologyLinkEntry 1 }



umc1TopologyLinkTerminalB OBJECT-TYPE
	SYNTAX INTEGER
	ACCESS read-only
	STATUS mandatory
	DESCRIPTION
		"The Terminal ID of the terminal that connects to Terminal A."
	::= { umc1TopologyLinkEntry 2 }


--
-- Data Lookup Services
--
--	The following variables and tables represent static information stored
--	in the UMC that may need to be retrieved by the EMS.  The ability of
--	the EMS to get this information from the UMC allows the EMS to
--	update itself in the event that it discovers a UMC that has newer
--	software than it currently knows how to handle.  Note that many
--	of these tables do not allow for 'get-next' operations because
--	it might unduly load the UMC.  Looking up a particular item, however,
--	is allowed, but should only be used in the case where the item is not
--	already known to the EMS.


umc1DsPlugInNameTable OBJECT-TYPE
	SYNTAX SEQUENCE OF Umc1DsPlugInNameEntry
	ACCESS not-accessible
	STATUS mandatory
	DESCRIPTION
		"The Plug-in name table.  This table maps the Plug-in type
		with the appropriate textual Plug-in name.  This table does
		*not* support the get-next operation."
	::= { umc1DataService 1 }

umc1DsPlugInNameEntry OBJECT-TYPE
	SYNTAX Umc1DsPlugInNameEntry
	ACCESS not-accessible
	STATUS mandatory
	DESCRIPTION
		"An entry in the Plug-in name table."
	INDEX { umc1DsPlugInType }
	::= { umc1DsPlugInNameTable 1 }

Umc1DsPlugInNameEntry ::=
	SEQUENCE { 
		umc1DsPlugInType		INTEGER,
		umc1DsPlugInName		DisplayString
	}

umc1DsPlugInType OBJECT-TYPE
	SYNTAX INTEGER
	ACCESS read-only
	STATUS mandatory
	DESCRIPTION
		"The numeric value associated with a UMC Plug-in.  This is the
		index into the table"
	::= { umc1DsPlugInNameEntry 1 }

umc1DsPlugInName OBJECT-TYPE
	SYNTAX DisplayString
	ACCESS read-only
	STATUS mandatory
	DESCRIPTION
		"The name of the UMC Plug-in that is associated with the
		Plug-in type."
	::= { umc1DsPlugInNameEntry 2 }

umc1DsAlarmStringTable OBJECT-TYPE
	SYNTAX SEQUENCE OF Umc1DsAlarmStringEntry
	ACCESS not-accessible
	STATUS mandatory
	DESCRIPTION
		"The Alarm string table.  This table maps the facility alarm
		number with the appropriate textual message string.  This
		table does *not* support the get-next operation."
	::= { umc1DataService 2 }

umc1DsAlarmStringEntry OBJECT-TYPE
	SYNTAX Umc1DsAlarmStringEntry
	ACCESS not-accessible
	STATUS mandatory
	DESCRIPTION
		"An entry in the Alarm string table."
	INDEX { umc1DsAlarmFacilityNumber }
	::= { umc1DsAlarmStringTable 1 }

Umc1DsAlarmStringEntry ::=
	SEQUENCE { 
		umc1DsAlarmFacilityNumber	INTEGER,
		umc1DsAlarmString		DisplayString
	}

umc1DsAlarmFacilityNumber OBJECT-TYPE
	SYNTAX INTEGER
	ACCESS read-only
	STATUS mandatory
	DESCRIPTION
		"The numeric value associated with a UMC alarm.  This is the
		index into the table"
	::= { umc1DsAlarmStringEntry 1 }

umc1DsAlarmString OBJECT-TYPE
	SYNTAX DisplayString
	ACCESS read-only
	STATUS mandatory
	DESCRIPTION
		"The text string associated with the UMC alarm value."
	::= { umc1DsAlarmStringEntry 2 }



--
-- Maintenance TRAP Information
--
--	This section defines the MIB variables that are applicable to
--	the IPMI software diagnostic message TRAPs.  
--
 
umc1SoftwareDiagMessageTimestamp OBJECT-TYPE
	SYNTAX OCTET STRING     (SIZE (7..7))
	ACCESS read-only
	STATUS mandatory
	DESCRIPTION
		"The time the message was reported by the IPMI card.
        The format of the umc1SoftwareDiagMessageTimestamp is as follows:
        octet[0]   High 8-bits of the YEAR
        octet[1]   Low  8-bits of the YEAR
        octet[2]   Month   (January=1, February=2, etc.)
        octet[3]   Day     (1 through 31)
        octet[4]   Hour    (0 through 23)
        octet[5]   Minutes (0 through 59)
        octet[6]   Seconds (0 through 59)"
	::= { umc1Trap 1 }


umc1SoftwareDiagMessageType OBJECT-TYPE
	SYNTAX OCTET STRING     (SIZE (5..5))
	ACCESS read-only
	STATUS mandatory
	DESCRIPTION
		"A representation of the type of diagnostic message to follow.
        The format of the umc1SoftwareDiagMessageType is as follows:
        octet[0]    Diagnostic message type (SYSERR=1)
        octet[1]    Reserved (set to zero)
        octet[2]    Reserved (set to zero)
        octet[3]    Reserved (set to zero)
        octet[4]    Reserved (set to zero)"
	::= { umc1Trap 2 }


umc1SoftwareDiagMessageString OBJECT-TYPE
	SYNTAX DisplayString
	ACCESS read-only
	STATUS mandatory
	DESCRIPTION
		"The diagnostic message itself."
	::= { umc1Trap 3 }


--UMC1000 Inventory Basic Shelf Information
--

umc1InventoryShelfTableChangeSeqNum OBJECT-TYPE
    SYNTAX INTEGER (1..2147483647)
    ACCESS read-only
    STATUS mandatory
    DESCRIPTION
	"A sequence number used to indicate that inventory 
	shelf table has been modified and it needs to be re-
	read. Whenever the SNMP agent restarted, this value 
	will be reset to 0(zero). The value will be 
	incremented by one whenever a change to the inventory 
	shelf table information had been made4. This number 
	will also be sent in the 
	umc1TrapInventoryShelfTableChange trap and can be used 
	to determine if any traps have been lost. This value 
	will be incremented before the trap is sent.


    The maximum value it can assume is 2,147,483,647. An increment, 
	every time it has reached its maximum value, shall cause it to 
	be reset to 1.
	"
    ::= { umc1InventoryShelf 1 }

umc1InventoryShelfTable OBJECT-TYPE
    SYNTAX SEQUENCE OF Umc1InventoryShelfEntry
    ACCESS not-accessible
    STATUS mandatory
    DESCRIPTION
	"This table contains information about all shelves in 
	a UMC system.  There will be an entry in this table 
	for every reachable shelf in the system."
    ::= { umc1InventoryShelf 2 }

Umc1InventoryShelfEntry ::=
    SEQUENCE {
	umc1InventoryShelfTerminalId    TerminalIdType,
	umc1InventoryShelfShelfId       ShelfIdType,
	umc1InventoryShelfType          OCTET STRING
    }

umc1InventoryShelfEntry OBJECT-TYPE
    SYNTAX Umc1InventoryShelfEntry 
    ACCESS not-accessible
    STATUS mandatory
    DESCRIPTION
	"An entry in the shelf table."
    INDEX { umc1InventoryShelfTerminalId, 
	    umc1InventoryShelfShelfId }
    ::= { umc1InventoryShelfTable 1 }

umc1InventoryShelfTerminalId OBJECT-TYPE
    SYNTAX TerminalIdType
    ACCESS read-only
    STATUS mandatory
    DESCRIPTION
	"Identifier of a terminal." 
    ::= { umc1InventoryShelfEntry 1 }

umc1InventoryShelfShelfId OBJECT-TYPE
    SYNTAX ShelfIdType
    ACCESS read-only
    STATUS mandatory
    DESCRIPTION
	"Identifier of a shelf."
    ::= { umc1InventoryShelfEntry 2 }

umc1InventoryShelfType OBJECT-TYPE
    SYNTAX OCTET STRING(SIZE (1..1))
    ACCESS read-only
    STATUS mandatory
    DESCRIPTION
	"This object describes the type of the shelf. The 
	following table lists the valid values and the 
	corresponding shelf type they denote.

	Value	    Shelf Type
         0	   Old shelf or
		   Unrecognized Shelf type
         1         Euro-CBA 120
         2         Euro-BBA 120
         3         CBA-120
         4         CBA-48
         5         BBA-120
         6         BBA-48
         7         CAB-90
         8         CAB-30
         9         BBA-24
         10        DP-BBA-120
         11        DP-Euro-BBA-120
         12        DP-BBA-48
	"
    ::= { umc1InventoryShelfEntry 3 }

--UMC1000 Inventory Shelf Table Change History Information
--
umc1InventoryShelfTableChangeHistoryTable OBJECT-TYPE
	SYNTAX SEQUENCE OF Umc1InventoryShelfTableChangeHistoryEntry
	ACCESS not-accessible
	STATUS mandatory
	DESCRIPTION
		"This table records the location and type of the shelves whose
		addition to the UMC system caused the agent to emit 
		umc1TrapInventoryShelfTableChange trap. The contents of the
		table are indexed by the value of umc1InventoryShelfTableChangeSeqNum.
		When the value of umc1InventoryShelfTableChangeSeqNum is zero
		the history table is empty.

		A management station shall query this table, using the value
		of umc1InventoryShelfTableChangeSeqNum received in 
		umc1TrapInventoryShelfTableChange trap to determine if it can
		detect the new cards that have been added to the system. If
		it does not find such a row in this table it must re-read the
		entire umc1InventoryShelfTable table."
   ::= { umc1InventoryShelf 3 }



Umc1InventoryShelfTableChangeHistoryEntry ::= 
	SEQUENCE {
             umc1InventoryShelfTableChangeHistoryIndex  INTEGER,
             umc1InventoryShelfTableChangeHistoryData   OCTET STRING
             }



umc1InventoryShelfTableChangeHistoryEntry OBJECT-TYPE
	SYNTAX Umc1InventoryShelfTableChangeHistoryEntry
	ACCESS not-accessible
	STATUS mandatory
	DESCRIPTION
		"An entry in the history table."
	INDEX {umc1InventoryShelfTableChangeHistoryIndex }
	::= { umc1InventoryShelfTableChangeHistoryTable 1 }



umc1InventoryShelfTableChangeHistoryIndex OBJECT-TYPE
	SYNTAX INTEGER
	ACCESS read-only
	STATUS mandatory
	DESCRIPTION
		"This objects value matches the value of 
		umc1InventoryShelfTableChangeSeqNum at the time the row was
		created. A valid value of this object is in the range of 1
		through umc1InventoryShelfTableChangeSeqNum."
	::= { umc1InventoryShelfTableChangeHistoryEntry 1 }



umc1InventoryShelfTableChangeHistoryData OBJECT-TYPE
	SYNTAX OCTET STRING (SIZE (1..255))
	ACCESS read-only
	STATUS mandatory
	DESCRIPTION
		"This object stores information of all shelves that were added
		to the UMC system when umc1TrapInventoryShelfTableChange trap
		was emitted by the agent with umc1InventoryShelfTableChangeHistoryIndex
		sequence number. 

		The byte-format structure of this object is as follows:
			octet[0]	Version number of the octet representation. The version number 
			            for the initial implementation will be 0x01.

			For version number 0x01 the remaining octets will be defined as follows :
			octet[1]    Total number of records in the varbind, where each record consists 
			            of a length octet(length of the record), a terminal identifier octet, 
						a shelf identifier octet and a shelf-type octet.
			--- Record #1
			octet[2]	Length of the first record.
			octet[3]	Terminal Identifier of the first record.
			octet[4]	Shelf identifier of the first record.
			octet[5]	Shelf-type of the first record.
			........
	"
	::= { umc1InventoryShelfTableChangeHistoryEntry 2 }



--UMC1000 Inventory Extended Shelf Information
--

umc1InventoryShelfExtendedTable OBJECT-TYPE
    SYNTAX SEQUENCE OF Umc1InventoryShelfExtendedEntry
    ACCESS not-accessible
    STATUS mandatory
    DESCRIPTION
	"This table contains extended information that can be 
	read from a shelf about all shelves in a UMC system. 
	There will be an entry in this table for every 
	reachable shelf in the system."
    ::= { umc1InventoryShelfExtended 1 }

Umc1InventoryShelfExtendedEntry ::=
    SEQUENCE {
	umc1InventoryShelfExtendedTerminalId        TerminalIdType,
	umc1InventoryShelfExtendedShelfId           ShelfIdType,
	umc1InventoryShelfExtendedVersion           OCTET STRING,
	umc1InventoryShelfExtendedAssemblyNumber    DisplayString,
	umc1InventoryShelfExtendedSerialNumber      DisplayString,
	umc1InventoryShelfExtendedCLEICode          DisplayString
    }

umc1InventoryShelfExtendedEntry OBJECT-TYPE
    SYNTAX Umc1InventoryShelfExtendedEntry 
    ACCESS not-accessible
    STATUS mandatory
    DESCRIPTION
	"An entry in the extended shelf table."
    INDEX { umc1InventoryShelfExtendedTerminalId, 
	    umc1InventoryShelfExtendedShelfId }
    ::= { umc1InventoryShelfExtendedTable 1 }

umc1InventoryShelfExtendedTerminalId OBJECT-TYPE
    SYNTAX TerminalIdType
    ACCESS read-only
    STATUS mandatory
    DESCRIPTION
	"Identifier of a terminal."
    ::= { umc1InventoryShelfExtendedEntry 1 }

umc1InventoryShelfExtendedShelfId OBJECT-TYPE
    SYNTAX ShelfIdType
    ACCESS read-only
    STATUS mandatory
    DESCRIPTION
	"Identifier of a shelf."
    ::= { umc1InventoryShelfExtendedEntry 2 }

umc1InventoryShelfExtendedVersion OBJECT-TYPE
    SYNTAX OCTET STRING (SIZE(2))
    ACCESS read-only
    STATUS mandatory
    DESCRIPTION
	"The first octet contains the hardware version of the 
	BOOT PROM of the shelf. The second octet contains the 
	hardware revision of the BOOT PROM of the shelf.

	For a shelf with an older version of the hardware the 
	values of the octets are 0xFF"
    ::= { umc1InventoryShelfExtendedEntry 3 }

umc1InventoryShelfExtendedAssemblyNumber OBJECT-TYPE
    SYNTAX DisplayString (SIZE(9))
    ACCESS read-only
    STATUS mandatory
    DESCRIPTION
	"This is the assembly number of the shelf. The string 
	is not terminated by a NULL character. For a shelf with an 
	older version of the hardware the values of the octets 
	are 0xFF."
    ::= { umc1InventoryShelfExtendedEntry 4 }

umc1InventoryShelfExtendedSerialNumber OBJECT-TYPE
    SYNTAX DisplayString (SIZE(11))
    ACCESS read-only
    STATUS mandatory
    DESCRIPTION
	"This is the serial number of the shelf. The string is 
	not terminated by a NULL character. For a shelf with 
	an older version of the hardware the values of the 
	octets are 0xFF"
    ::= { umc1InventoryShelfExtendedEntry 5 }

umc1InventoryShelfExtendedCLEICode OBJECT-TYPE
    SYNTAX DisplayString (SIZE(10))
    ACCESS read-only
    STATUS mandatory
    DESCRIPTION
	"This is the CLEI code assigned to the shelf. The 
	string is not terminated by a NULL character."
    ::= { umc1InventoryShelfExtendedEntry 6 }

--UMC1000 Inventory Basic Plug-in Information
--

umc1InventoryPluginTableChangeSeqNum OBJECT-TYPE
    SYNTAX INTEGER (1..2147483647)
    ACCESS read-only
    STATUS mandatory
    DESCRIPTION
	"A sequence number used to indicate that inventory plug-in
	table has been modified and it needs to be re-read.
	Whenever the SNMP agent restarted, this value will 
	be reset to 0(zero). The value will be incremented by 
	one whenever a change to the inventory plug-in table 
	information had been made. This number will also be 
	sent in the umc1TrapInventoryPluginTableChange trap 
	and can be used to determine if any traps have been 
	lost. This value will be incremented before the trap 
	is sent.

	The maximum value it can assume is 2,147,483,647. An increment, 
	very time it has reached its maximum value, shall cause it to 
	be reset to 1.
	" 
    ::= { umc1InventoryPlugin 1 }

umc1InventoryPluginTable OBJECT-TYPE
    SYNTAX SEQUENCE OF Umc1InventoryPluginEntry
    ACCESS not-accessible
    STATUS mandatory
    DESCRIPTION
	"This table contains information about all plug-in 
	cards in a UMC system."
    ::= { umc1InventoryPlugin 2 }

Umc1InventoryPluginEntry ::= 
    SEQUENCE {
             umc1InventoryPluginTerminalId   TerminalIdType,
             umc1InventoryPluginShelfId      ShelfIdType,
             umc1InventoryPluginSlotId       SlotIdType,
             umc1InventoryPluginType         PlugInType
             }

umc1InventoryPluginEntry OBJECT-TYPE
    SYNTAX Umc1InventoryPluginEntry 
    ACCESS not-accessible
    STATUS mandatory
    DESCRIPTION
	"An entry in the plug-in table."
    INDEX { umc1InventoryPluginTerminalId, 
	    umc1InventoryPluginShelfId, 
	    umc1InventoryPluginSlotId }
    ::= { umc1InventoryPluginTable 1 }

umc1InventoryPluginTerminalId OBJECT-TYPE
    SYNTAX TerminalIdType
    ACCESS read-only
    STATUS mandatory
    DESCRIPTION
	"Identifier of a terminal."
    ::= { umc1InventoryPluginEntry 1 }

umc1InventoryPluginShelfId OBJECT-TYPE
    SYNTAX ShelfIdType
    ACCESS read-only
    STATUS mandatory
    DESCRIPTION
	"Identifier of a shelf."
    ::= { umc1InventoryPluginEntry 2 }

umc1InventoryPluginSlotId OBJECT-TYPE
    SYNTAX SlotIdType
    ACCESS read-only
    STATUS mandatory
    DESCRIPTION
	"Identifier of a slot."
    ::= { umc1InventoryPluginEntry 3 }

umc1InventoryPluginType OBJECT-TYPE
    SYNTAX PlugInType
    ACCESS read-only
    STATUS mandatory
    DESCRIPTION
	"This object identifies the plug-in type (PIT) of a 
	card in the UMC system."
    ::= { umc1InventoryPluginEntry 4 }


umc1InventoryPluginTableChangeHistoryTable OBJECT-TYPE
    SYNTAX SEQUENCE OF Umc1InventoryPluginTableChangeHistoryEntry
    ACCESS not-accessible
    STATUS mandatory
    DESCRIPTION
	"This table records the location and type of the plug-
	in cards whose addition to the UMC system caused the 
	agent to emit umc1TrapInventoryPluginTableChange trap. 
	The contents of the table are indexed by the value of 
	umc1InventoryPluginTableChangeSeqNum. When the value 
	of umc1InventoryPluginTableChangeSeqNum is zero the 
	history table is empty.

	A management station shall query this table, using the 
	value of umc1InventoryPluginTableChangeSeqNum received 
	in umc1TrapInventoryPluginTableChange trap to 
	determine if it can detect the new cards that have 
	been added to the system. If it does not find such a 
	row in this table it must re-read the entire 
	umc1InventoryPluginTable table."
   ::= { umc1InventoryPlugin 3 }

Umc1InventoryPluginTableChangeHistoryEntry ::= 
    SEQUENCE {
             umc1InventoryPluginTableChangeHistoryIndex INTEGER,
             umc1InventoryPluginTableChangeHistoryData  OCTET STRING
             }

umc1InventoryPluginTableChangeHistoryEntry OBJECT-TYPE
    SYNTAX Umc1InventoryPluginTableChangeHistoryEntry
    ACCESS not-accessible
    STATUS mandatory
    DESCRIPTION
	"An entry in the history table."
    INDEX {umc1InventoryPluginTableChangeHistoryIndex }
    ::= { umc1InventoryPluginTableChangeHistoryTable 1 }

umc1InventoryPluginTableChangeHistoryIndex OBJECT-TYPE
    SYNTAX INTEGER
    ACCESS read-only
    STATUS mandatory
    DESCRIPTION
	"This objects value matches the value of 
	umc1InventoryPluginTableChangeSeqNum at the time the 
	row was created. A valid value of this object is in 
	the range of 1 through 
	umc1InventoryPluginTableChangeSeqNum."
    ::= { umc1InventoryPluginTableChangeHistoryEntry 1 }

umc1InventoryPluginTableChangeHistoryData OBJECT-TYPE
    SYNTAX OCTET STRING (SIZE (1..255))
    ACCESS read-only
    STATUS mandatory
    DESCRIPTION
	"This object stores the location and plug-in type of 
	all cards that were added to the UMC system when 
	umc1TrapInventoryPluginTableChange trap was emitted by 
	the agent with 
	umc1InventoryPluginTableChangeHistoryIndex sequence 
	number. 
	
	The byte-format structure of this object is as follows:
	   octet[0] Version number of the octet representation. The 
	   	    version number for the initial implementation will 
	   	    be 0x01.
           
	   For version number 0x01 the remaining octets will be defined 
	   as follows :
	   octet[1] Total number of records in the varbind, where each 
	   	    record consists of a length octet(length of the record),
	   	    a terminal identifier octet, a shelf identifier octet, 
	   	    a slot identifier octet and two octets for saving 
	   	    plug-in type.
           
	   ---Record #1
	   octet[2] Length of the first record.
	   octet[3] Terminal Identifier of the first record.
	   octet[4] Shelf identifier of the first record.
	   octet[5] Slot identifier of the first record.
	   octet[6] Low-order byte of plug-in type of the first record.
	   octet[7] High-order byte of plug-in type of the first record.
	   ........
	"
    ::= { umc1InventoryPluginTableChangeHistoryEntry 2 }


--UMC1000 Inventory Extended Plug-in Information
--


umc1InventoryPluginExtendedTable OBJECT-TYPE
    SYNTAX SEQUENCE OF Umc1InventoryPluginExtendedEntry
    ACCESS not-accessible
    STATUS mandatory
    DESCRIPTION
	"This table contains information about all plug-in 
	cards in a UMC system."
    ::= { umc1InventoryPluginExtended 1 }

Umc1InventoryPluginExtendedEntry ::= 
    SEQUENCE    {
                umc1InventoryPluginExtendedTerminalId       TerminalIdType,
                umc1InventoryPluginExtendedShelfId          ShelfIdType,
                umc1InventoryPluginExtendedSlotId           SlotIdType,
                umc1InventoryPluginExtendedStatus           INTEGER,
                umc1InventoryPluginExtendedVersion          OCTET STRING,
                umc1InventoryPluginExtendedAssemblyNumber   DisplayString,
                umc1InventoryPluginExtendedSerialNumber     DisplayString,
                umc1InventoryPluginExtendedCLEICode         DisplayString
                }

umc1InventoryPluginExtendedEntry OBJECT-TYPE
    SYNTAX Umc1InventoryPluginExtendedEntry 
    ACCESS not-accessible
    STATUS mandatory
    DESCRIPTION
	"An entry in the plug-in table."
    INDEX { umc1InventoryPluginExtendedTerminalId, 
	    umc1InventoryPluginExtendedShelfId, 
	    umc1InventoryPluginExtendedSlotId }
    ::= { umc1InventoryPluginExtendedTable 1 }

umc1InventoryPluginExtendedTerminalId OBJECT-TYPE
    SYNTAX TerminalIdType
    ACCESS read-only
    STATUS mandatory
    DESCRIPTION
	"Identifier of a terminal."
    ::= { umc1InventoryPluginExtendedEntry 1 }

umc1InventoryPluginExtendedShelfId OBJECT-TYPE
    SYNTAX ShelfIdType
    ACCESS read-only
    STATUS mandatory
    DESCRIPTION
	"Identifier of a shelf."
    ::= { umc1InventoryPluginExtendedEntry 2 }

umc1InventoryPluginExtendedSlotId OBJECT-TYPE
    SYNTAX SlotIdType
    ACCESS read-only
    STATUS mandatory
    DESCRIPTION
	"Identifier of a slot."
    ::= { umc1InventoryPluginExtendedEntry 3 }

umc1InventoryPluginExtendedStatus OBJECT-TYPE
    SYNTAX INTEGER
    ACCESS read-only
    STATUS mandatory
    DESCRIPTION
	"This object identifies the current state of a plug-in 
	card. The following table lists the valid values and 
	the corresponding plug-in status.

		  Value	Plug-in Status
			1	failed
			2	in-service
			3	missing-card
			4	disabled
			5	unequipped
			6	wrong-type
			7	old-software
			8	active
			9	standby
			10	upgrade
			11	old-boot-prom
			12	loopback
			13	out-of-service
			14	calibration
	"
    ::= { umc1InventoryPluginExtendedEntry 4 }

umc1InventoryPluginExtendedVersion OBJECT-TYPE
    SYNTAX OCTET STRING (SIZE(12))
    ACCESS read-only
    STATUS mandatory
    DESCRIPTION
	"This object contains the information regarding 
	hardware and software versions of a plug-in card. If 
	the value of octet[0] is not 0 then data in octet[9] 
	through octet[11] contains valid information about 
	standby main code version, revision and point. 
	Otherwise, the data in octet[9] through octet[11] 
	should be ignored. The data in each octet is:

	Octet[0]  If non-zero then Standby main code information 
		  is valid.
	Octet[1]  contains hardware version information, e.g., 5.
	Octet[2]  contains hardware revision information, e.g., D.
	Octet[3]  contains boot code version information, e.g., 0x2.
	Octet[4]  contains boot code revision information, e.g., 0x4.
	Octet[5]  contains boot code point information, e.g., 0x0.
	Octet[6]  contains active main code version information, 
		  e.g., 0x2.
	Octet[7]  contains active main code revision information, 
		  e.g., 0x4.
	Octet[8]  contains active main code point information, 
		  e.g., 0x2.
	Octet[9]  contains standby main code version information, 
		  e.g., 0x2.
	Octet[10] contains standby main code revision information, 
		  e.g., 0x4.
	Octet[11] contains standby main code point information, 
		  e.g., 0x3.
	"
    ::= { umc1InventoryPluginExtendedEntry 5 }
 
umc1InventoryPluginExtendedAssemblyNumber OBJECT-TYPE
    SYNTAX DisplayString (SIZE(9))
    ACCESS read-only
    STATUS mandatory
    DESCRIPTION
	"This is the assembly number of the plug-in card. This 
	string is not terminated by a null character."
    ::= { umc1InventoryPluginExtendedEntry 6 }


umc1InventoryPluginExtendedSerialNumber OBJECT-TYPE
    SYNTAX DisplayString (SIZE(11))
    ACCESS read-only
    STATUS mandatory
    DESCRIPTION
	"This is the serial number of the plug-in card. This 
	string is not terminated by a null character."
    ::= { umc1InventoryPluginExtendedEntry 7 }

umc1InventoryPluginExtendedCLEICode OBJECT-TYPE
    SYNTAX DisplayString (SIZE(10))
    ACCESS read-only
    STATUS mandatory
    DESCRIPTION
	"This is the CLEI code assigned to the plug-in card. 
	This string is not terminated by a null character."
    ::= { umc1InventoryPluginExtendedEntry 8 }

--UMC1000 System Relearn Information
--

umc1ACOSnapTopologySeqNum OBJECT-TYPE
    SYNTAX INTEGER (1..2147483647)
    ACCESS	read-only
    STATUS	mandatory
    DESCRIPTION
	"The value of umc1TopologyChangeSeqNum at the time 
	that the snapshot was taken.  This allows the 
	management station to know if the links specified in 
	the umc1TopologyLinkTable still matches the snapshot. 
	If the value stored here matches that in the 
	umc1TopologyChangeSeqNu , then the data in the tables 
	match.  If the tables match, then there is no reason 
	to read the umc1TopologyLinkTable to reconcile any 
	changes that have been made since the ACO operation 
	was performed. If the tables do not match, then the 
	links listed in the two tables will have to be 
	reconciled by the management station.

	The maximum value it can assume is 2,147,483,647. An increment, 
	very time it has reached its maximum value, shall cause it to 
	be reset to 1.
	"
    ::= { umc1ACOSnapTopology 1 } 

umc1ACOSnapTopologyLinkTable OBJECT-TYPE
    SYNTAX SEQUENCE OF Umc1ACOSnapTopologyLinkEntry
    ACCESS not-accessible
    STATUS mandatory
    DESCRIPTION
	"The link table.  This table will be empty if only one
	terminal makes up this UMC.  Only active links will be
	in this table.  If a link is lost, then the corresponding
	row in this table will be removed."
    ::= { umc1ACOSnapTopology 2 }

umc1ACOSnapTopologyLinkEntry OBJECT-TYPE
    SYNTAX Umc1ACOSnapTopologyLinkEntry
    ACCESS not-accessible
    STATUS mandatory
    DESCRIPTION
	"An entry in the link table."
    INDEX   { 
            umc1ACOSnapTopologyLinkTerminalA, 
            umc1ACOSnapTopologyLinkTerminalB
            }
    ::= { umc1ACOSnapTopologyLinkTable 1 }

Umc1ACOSnapTopologyLinkEntry ::=
    SEQUENCE { 
	umc1ACOSnapTopologyLinkTerminalA	TerminalIdType,
	umc1ACOSnapTopologyLinkTerminalB	TerminalIdType
    }

umc1ACOSnapTopologyLinkTerminalA OBJECT-TYPE
    SYNTAX TerminalIdType
    ACCESS read-only
    STATUS mandatory
    DESCRIPTION
	"The Terminal ID of the terminal at one end of the link.
	This ID will always be lower in value than that 
	specified for Terminal B. The order of the terminal 
	IDs does not in any way indicate which terminal is 
	closer to the lowest numbered terminal.  The terminal 
	IDs start with 1.  (E.g. the LET is 1, RST1 is 2, RST2 
	is 3, etc.)"
    ::= { umc1ACOSnapTopologyLinkEntry 1 }

umc1ACOSnapTopologyLinkTerminalB OBJECT-TYPE
    SYNTAX TerminalIdType
    ACCESS read-only
    STATUS mandatory
    DESCRIPTION
	"The Terminal ID of the terminal that connects to 
	Terminal A."
    ::= { umc1ACOSnapTopologyLinkEntry 2 }


--UMC1000 Command Response Mechanism
--

umc1SystemAllSeqNbr OBJECT-TYPE
    SYNTAX OCTET STRING (SIZE (1..255))
    ACCESS read-only
    STATUS mandatory
    DESCRIPTION
    "This object encapsulates all sequence numbers. The format of this  
     object is:
     Octet[0]       contains version, 0x01 for this release.
     Octet[1-4]     contains snmpOutTraps, which represents the number  
                    of traps sent by Agent.

     Octet[5-136]   contains umc1AlmSeqNumbers corresponding to a 
                    umc1AlmTerminalIds. There are four octet for each 
                    umc1AlmSeqNumber and 33 Alarm Sequence Numbers one for 
                    each Terminal in UMC system. 

     The first four octet represents umc1AlmSeqNumber for Terminal with 
     identifier 1, subsequent four octet represents umc1AlmSeqNumber for 
     Terminal with identifier 2 and so on.

     Octet[137-140]  contains umc1AlmSeqTableChangeSeqNum
     Octet[141-144]  contains umc1InventoryShelfTableChangeSeqNum
     Octet[145-148]  contains umc1InventoryPluginTableChangeSeqNum
     Octet[149-152]  contains umc1ACOSnapTopologySeqNum
     Octet[153-156]  contains umc1SystemSysProvTableChangeSeqNum
     Octet[157-160]  contains umc1SystemRelearnTrapSeqNum
     Octet[161-164]  contains umc1TerminalInfoChangeSeqNum
     Octet[165-168]  contains umc1TerminalStatusChangeSeqNum
     Octet[169-172]  contains umc1TopologyChangeSeqNum
     Octet[173-176]  contains umc1TerminalSpanTableChangeSeqNum
     Octet[177-180]  contains umc1ShelfSpanTableChangeSeqNum
     Octet[181-184]  contains umc1XCTableChangeSeqNum
     Octet[185-188]  contains umc1GR303TableChangeSeqNum
     Octet[189-192]  contains umc1TR8TableChangeSeqNum
     Octet[193-196]  contains umc1AtmProtTableChangeSeqNum
     Octet[197-200]  contains umc1PortProfTableChangeSeqNum
     Octet[201-204]  contains umc1V5TableChangeSeqNum
     Octet[205-208]  contains umc1FacAlmStringTableChangeSeqNum
     Octet[209-212]  contains umc1TL1IfProvTableChangeSeqNum
     Octet[213-216]  contains umc1SecurityDataTableChangeSeqNum
     Octet[217-220]  contains umc1SystemGenericDbProvTableSeqNum
     Octet[221-224]  contains umc1SystemTCAHistoryTableSeqNum
     Octet[225-255]  ignored

     This object is a varbind for trap umc1TrapAllSeqNumber. The agent 
     shall send trap umc1TrapAllSeqNbrDump when Management Station sends 
     GET Request to read all sequence numbers.
    "
    ::= { umc1System 9 }



umc1CommandTable OBJECT-TYPE
    SYNTAX SEQUENCE OF Umc1CommandTableEntry
    ACCESS not-accessible
    STATUS mandatory
    DESCRIPTION
    "A Management application may use the umc1CommandTable to execute a 
     command in an agent. In order to execute a command with an argument, 
     possibly null, the management application shall get a transaction 
     number from the agent (see the definition of umc1CommandTransNbr for 
     a description of how to obtain a transaction number). Once a 
     transaction number has been received the manager shall gather the 
     response from the response table (see the definition of 
     umc1ResponseTable)."
    ::= { umc1CommandResponse 1 }

Umc1CommandTableEntry ::=
    SEQUENCE    {
                umc1CommandId       INTEGER,
                umc1CommandArg      OCTET STRING,
                umc1CommandTransNbr INTEGER
                }

umc1CommandTableEntry OBJECT-TYPE
    SYNTAX Umc1CommandTableEntry
    ACCESS not-accessible
    STATUS mandatory
    DESCRIPTION
    "An entry in the command table."
    INDEX { umc1CommandId, 
            umc1CommandArg
          }
    ::= { umc1CommandTable 1 }

umc1CommandId OBJECT-TYPE
    SYNTAX INTEGER
    ACCESS read-only
    STATUS mandatory
    DESCRIPTION
    "This object identifies a command that a manager may execute in an agent. 
     The following table describes the supported commands and their 
     corresponding values.

     Value Command Type         Description
     1     _ReadTable_          Read the Table Type specified by the umc1CommandArg
     2     _GetAllSeqNbr_       Read All Sequence Numbers
     3     _GetActiveTermName_  Read the terminal name of all active terminals
     4     _GetCpuDbDumpPort_   Read the port for Cpu Db Dump
     5     _SetOrDelete_        Set or Delete the MIB Object specified by umc1CommandArg
     6     _ClearCache_         Clear IPMI Agent Cache
     7     _RebootIpmi_         Reboot IPMI Card
     8     _ActivateAco_        Activate ACO
     9     _AotRollover_        AoT to End-To-End Rollover
     10    _CurTrafficStats_    Get the Current Traffic Status
     11    _GetVcStatusInfo_    Get Virtual Circuit Status Information
     12    _GetLineCardStatus_  Get Status Information for Digital Line Card(ADSL's)
     13    _GetBlockedVccInfo_  Get Information on blocked VCCs
     14    _GetAtmBandwidth_    Get ATM Bandwidth for Uplink circuit
     15    _GetAtmStatistics_   Get ATM Statistics 
     16    _GetAdslBitsPerTone_ Get Bits Per Tone Data for ADSL Line
     17    _GetAdslPmAttribute_ Get / Clear ADSL Perfomance Measurement data by attribute
     18    _GetPmDataBin_       Get / Clear ADSL or ATM Perfomance Measurement data by bin
     19    _GetNBLinkStats_     Get Narrow Band Link Traffic Statistics
     20    _DeleteEquipment_    Delete Provisioning and cross-connects for a slot
     21    _SoftwareActivation_ Manual Software Activation
     22    _ManualProtectionSwitch_ Manual Protection Switch
     23    _GetAPSInfo_         Get APS Info
     24    _GenericIB_		    Generic Get / Set command utilizing IB message types
     25    _GetAtmStatsPerVcc_  Get ATM statistic per Vcc
     26    _GetDropTestResults_ Get MTU Drop Test results
    " 
    ::= { umc1CommandTableEntry 1 }

umc1CommandArg OBJECT-TYPE
    SYNTAX OCTET STRING (SIZE (1..255))
    ACCESS read-only
    STATUS mandatory
    DESCRIPTION
    " 
    This object specifies the argument to a command. The format of this  
    object is:

    octet[0]   contains command argument.
    octet[1]   contains Time-out value for Command in seconds.

    When umc1CommandId is _ReadTable_ and value of octet[0] is 10,20 & 
    120 than  Octet[2]   contains Terminal Id.

    Following table describes valid values of 0ctet[2] with its meaning.
 
     Value
    Octet[2]            Description
    ------------        ----------------------------------
       0                Read entire MIB Table
     1-33               Read all entries of MIB Table specified 
                        by Octet Zero of Command Arg that 
                        corresponds to given Terminal Id
 
    For a _ReadTable_ command the first octet is an argument. It identifies 
    the table that has to be read.  Any command type that is not explicitly
    listed below will ignore any value found in octet[0].

    Command Type        Valid Command Arguments 
    ------------        -----------------------
    _ReadTable_	        Value    Description
                        0ctet[0]
                          10       Read umc1InventoryShelfTable
                                        
                          20       Read umc1InventoryPluginTable
                          30       Read umc1TerminalInfoTable
                          40       Read umc1TerminalSpanTable

                          50       Read umc1ACOSnapTopologyLinkTable
                          60       Read umc1TopologyLinkTable
                          70       Read umc1InventoryPluginTableChangeHistoryTable
                          80       Read umc1InventoryShelfTableChangeHistoryTable
                          90       Read umc1TerminalStatusTable
                          100      Read umc1CurAlmTable
                          110      Read umc1XCTable
                          120      Read umc1ShelfSpanTable
                          130      Read umc1GR303Table
                          140      Read umc1TR8Table
                          150      Read umc1AtmProtGrpTable
                          160      Read umc1PortProfTable
    _SetOrDelete_         10       Set/Delete umc1SystemSysProvCATable
    _ActivateAco_         1 or 2   ACO Type
    _CurTrafficStats_     0-33     Terminal Id
	
    The following table describes valid timeout values:

    Timeout Value       Description 
    octet[1]            The Timeout Value used by Agent
    --------------      -------------------------------------
        0               Use default timeout value 10 seconds.
        1-60            Use corresponding timeout value.
        61-255          Use maximum timeout value 60 seconds.

    For _SetOrDelete_ Command for umc1SystemSysProvCATable, the format of
    Command Argument is:

    octet[2]  Number of records to Set or Delete
    octet[3]  Length of Record (For Delete value of this octet is Zero.) 
    octet[4]  Db Specifier
    octet[5]  Plug-in Type
    octet[6]  Terminal Id.
    octet[7]  Icard Id.
    octet[8]  Channel Id ( Always 0)
    octet[9]  Mux Code
    octet[10] TxSgTCond
    octet[11] Chan Bits
    octet[12] Chan Bits 2

    For _ActivateAco_ Command, Following table describes Command Argument
    ACO Type.

    Value
    Octet[0]            Description
    --------            ----------------------
       1                CUI Standard ACO Operation
       2                CUI Extended ACO Operation

    For _AotRollover_, _GetVcStatusInfo_, and _GetBlockedVccInfo_ Command, 
    the format of Command Argument is:

    Octet[2-11]     represents Upstream end of the Bb cross-connect
	Octet[12-21]    represents Downstream end of the Bb cross-connect

    Octet[2]    Terminal Id
    Octet[3]    Shelf Id
    Octet[4]    Slot Id
    Octet[5]    Channel Id
    Octet[6]    Group Id
    Octet[7]    CRN Type
    Octet[8]    Bits 15..8 of VCI
    Octet[9]    Bits 7...0 of VCI
    Octet[10]   Bits 15..8 of VPI
    Octet[11]   Bits 7...0 of VPI
    Octet[12]   Terminal Id
    Octet[13]   Shelf Id
    Octet[14]   Slot Id
    Octet[15]   Channel Id
    Octet[16]   Group Id
    Octet[17]   CRN Type
    Octet[18]   Bits 15..8 of VCI
    Octet[19]   Bits 7...0 of VCI
    Octet[20]   Bits 15..8 of VPI
    Octet[21]   Bits 7...0 of VPI
    Octet[22]   Data Operation: Exact Get or Progressive Get (See DataOperation)
	    Octet[23]	Crn64reqType:   0 for Plugin to Plugin request, 
                                    1 for group  to group  request
                                    2 both the above (retrieve any type)


    For _CurTrafficStats_ Command, the following table describes valid values 
    of 0ctet[0] with its meaning.

    Value
    Octet[0]            Description
    ------------        --------------------------------------------
       0                Get Current Traffic Status for all Terminals
     1-33               Get Current Traffic Status for specified 
                        Terminal Id
    
    --------------------------------------------------
    For _GetLineCardStatus_ Command, the format of
    Command Argument is:

    octet[2]    Terminal Id
    octet[3]    Shelf Id
    octet[4]    Slot Id
    octet[5]    Bits 15..8 of Plugin Type
    octet[6]    Bits 7...0 of Plugin Type
    octet[7]    Data Operation: Exact Get only (See DataOperation)
    octet[8]    Version (Argument List)

    Note: octet[8] definition.  The UMC1000 supports two unique response 
    data formats for this command.  When the version octet is not present,
    the SNMP host only support the original response data format.  A version 
    octet equal to 1 indicates the SNMP host supports both response data formats.  

    -------------------------------------------------------------------------
    For the _GetAtmBandwidth_ command, the format of the command argument is:

    octet[2]    Version
    octet[3]    Cac Data Type
    octet[4]    Terminal Id
    octet[5]    Location index 1
    octet[6]    Location index 2

    --------------------------------------------------------------------------
    For the _GetAtmStatistics_ command, the format of the command argument is:

    octet[2]    Version
    octet[3]    Terminal Id
    octet[4]    Shelf Id
    octet[5]    Slot Id
    octet[6]    Port: overloaded with Group Number for IMA 
    octet[7]    Data Operation: Exact Get or Write Data (Clear Statistics)
                (See DataOperation)

    ----------------------------------------------------------------------------
    For the _GetAdslBitsPerTone_ command, the format of the command argument is:

    octet[2]    Version
    octet[3]    Terminal Id
    octet[4]    Shelf Id
    octet[5]    Slot Id
    octet[6]    Circuit Id (Port Id)
    octet[7]    Bits 15..8 of Plugin Type
    octet[8]    Bits 7...0 of Plugin Type

    ----------------------------------------------------------------------------
    For the _GetAdslPmAttribute_ command, the format of the command argument is:

    octet[2]    Version
    octet[3]    Terminal Id
    octet[4]    Shelf Id
    octet[5]    Slot Id
    octet[6]    Circuit Id (Port ID) (0-6)
    octet[7]    ADSL PM Attribute ID / clear (reset type )
    octet[8]    Response format
    octet[9]    Data Operation: Exact Get, or Write Data (Clear PM) 
                (See DataOperation)
    octet[10]   Bits 15..8 of Plugin Type
    octet[11]   Bits 7...0 of Plugin Type

    Note: octet[7] definition. (ADSL PM Attribute ID)
      When octet[9] is equal 'GET EXACT'.
         Attribute enumerations as defined by UMC1000
      When octet[9] is equal 'WRITE'(clear).
         Type of clear, as defined by UMC1000

    Note: octet[8] definition.  Response format: 0 = Uncompressed, 
    1 = Compressed.

    Note: octet[9] (Data Operation) definition. 
      Data Operation = 'GET EXACT'
        The response data will contain a single record.  Valid range for 
        octet[6] is 1-6.  Valid range for octet[7] is 1-10.
      Data Operation = 'WRITE DATA'
        PM data is cleared for the specified port (octet[6] = 1-6) or 
        all ports (octet[6] = 0).  The valid range for octet[7] (0-2).

    -------------------------------------------------------------------------
    For the _GetPmDataBin_ command, the format of the command argument is:

    octet[2]    Version
    octet[3]    Terminal Id
    octet[4]    Shelf Id
    octet[5]    Slot Id
    octet[6]    Port ID (0 = all ports,1-6) for ADSL/OC3c/OC12c cards
		Group ID (0-3) for IMA card
    octet[7]    Number of ports supported at specified slot (1-6)
    octet[8]    Bin Type / Reset Type (0-2)
    octet[9]    Bits 31..24 of time (seconds since 1992)
    octet[10]   Bits 23..16 of time 
    octet[11]   Bits 15..8 of time
    octet[12]   Bits 7..0 of time
    octet[13]   Bits 15..8 of Plugin Type (supports ADSL family, OC3c/OC12c, IMA cards)
    octet[14]   Bits 7...0 of Plugin Type
    octet[15]   Data Operation: Get Exact, or Write Data (Clear PM) 
                (See DataOperation)
    octet[16]   ADSL (0), OC3c/Oc12c (1), or IMA (2) Card

    Note: 
    octet[6] definition.  Port Id is set to 1 for a OC3c/OC12c/IMA PIT type
    and 0 - 6 (0 - all ports) for an ADSL family PIT types.
    
    octet[8] definition.  For Data Operation equal Get Exact and Get 
    Progressive, Bin Type is set to 0 = 15 minute near-end(NE) section, 
    2 = daily NE section, 6 = 15 minute NE line, 
    7 = all 15 minute bins (pre system 9.0 release), 
    8 = daily NE line, 18 = 15-minute NE path, 20 = daily NE path,
    44 = 15-minute ATM, and 45 = daily ATM.
    For Data Operation equal Write Data (Clear PM), Reset Type set to 0 = 
    current data, 1 = current day data, 2 = all. 
    
    octet[15] definition. When Data Operation is 'GET EXACT', the response 
    data will contain a single record if the request is for a single port and
    a single bin, the response data will contain multiple records if the request 
    is for all ports and/or all bins (GET PROGRESIVE).
    When Data Operation is 'WRITE DATA', the command arguments specify a card.  
    PM data is cleared for all ports and all bins on the card.

    -------------------------------------------------------------------------
    For the _GetNBLinkStats_ command, the command argument list format is:

    octet[2]    Version
    octet[3]    Bits 31..24 of time (seconds since 1992)
    octet[4]    Bits 23..16 of time 
    octet[5]    Bits 15..8 of time
    octet[6]    Bits 7..0 of time
    octet[7]    Terminal End Point 1
    octet[8]    Terminal End Point 2
    octet[9]    Data Operation (Exact Get, or Progressive Get)
    octet[10]   GR303 group ID (1-3), Version 3 field only

    Note: 
    octet[2] represents the version of the request and expected response.
    This field set to (1) represents the original implementation.  This field
    set to (2) will lead to responses with additional fields for nailed-up DS0s.
    And, this field set to (3) requires octet[10], and retreives GR303 interface
    data on a per interface basis.

    octet[7], octet[8] and octet[10] definitions.  Terminal Endpoint 1 and 2 
    identify the endpoints of the link.   For a Get Exact Operation, data on 
    a single link will be retrieved, identified by the two terminal endpoints.
    For a Get Progressive Data Operation, terminal endpoints will represent 
    the starting point to retrieve data.  Both Terminal endpoints set to 1 will 
    indicate GR303 group data will be retrieved from the LET as specified by the 
    GR303 group ID, followed by narrowband CCS Data for each link in the system. 

    octet[9] definition. Data Operation will be set to Get Exact for retrieval 
    of a single link's data or Get Progressive for retrieval of all narrowband 
    CCS data. 

    -------------------------------------------------------------------------
    For the _DeleteEquipment_ command, the command argument list format is:

    octet[2]    Version
    octet[3]    Terminal Id
    octet[4]    Shelf Id
    octet[5]    Slot Id
    octet[6]    Bits 15..8 of Plugin Type
    octet[7]    Bits 7...0 of Plugin Type
    octet[8]    Control (0=query,1=delete)

    -------------------------------------------------------------------------
    For the _SoftwareActivation_ command, the cmd argument list format is:

    octet[2]    Version
    octet[3]    Terminal Id
    octet[4]    Shelf Id
    octet[5]    Slot Id
    octet[6]    Action (0=Activate standby bank,1=reset card)

    -------------------------------------------------------------------------
    For the _ManualProtectionSwitch_ command, the cmd argument list format is:

    octet[2]    Version
    octet[3]    Data Operation: Exact Get, or Write Data (Switch)
    octet[4]    Terminal Id
    octet[5]    Active Shelf Id
    octet[6]    Active Slot Id
    octet[7]    Standby Shelf Id    (not used with Exact Get)
    octet[8]    Standby Slot Id	(not used with Exact Get)
    octet[9]    Bits 15..8 of Plugin Type
    octet[10]   Bits 7...0 of Plugin Type

    -------------------------------------------------------------------------
    For the _GetAPSInfo_ command, the cmd argument list format is:

    octet[2]    Version
    octet[3]    Terminal Id
    octet[4]    Protection Group Id

   --------------------------------------------------------------------------
    For the _GenericIB_ command, the format of the command argument is:

    octet[2]    Version
    octet[3]    Terminal Id
    octet[4]    IB Data Type (IxType)
    octet[5]    Operation (SNMP Get Exact, Get Progressive, or Put)
    octet[6]    IB Payload Length (maximun of 55 bytes)
    octet[7]    First byte of IB Payload
    octet[x]	Last byte of the IB Payload

    -------------------------------------------------------------------------
    For the _GetAtmStatsPerVcc_ command, the cmd argument list format is as
    follows.  This command is used to retrieve ATM statistics for a given
    channel from upto four circuit cards used to transport the channel. The 
    ATM channel is specified by the Uplink Channel Routing Number (CRN).  
    The CRN is uniquely identified using octets 3 through 12.  Four card 
    location identifier follow the CRN.  

      octet[2]    Version
      octet[3]    Terminal Id
      octet[4]    Shelf Id
      octet[5]    Slot Id
      octet[6]    Channel Id
      octet[7]    Group Id
      octet[8]    CRN Type
      octet[9]    Bits 15..8 of VCI
      octet[10]   Bits 7...0 of VCI
      octet[11]   Bits 15..8 of VPI
      octet[12]   Bits 7...0 of VPI

    Location of Primary Uplink circuit
    When uplink is T1 or T1x, provide location of uplink concentrator.
      octet[13]   Uplink Terminal Id
      octet[14]   Uplink Shelf Id
      octet[15]   Uplink Slot Id

    Location of Secondary Uplink circuit (if APS Group, set to 0xFF 
        if not provided)
      octet[16]   Uplink Terminal Id
      octet[17]   Uplink Shelf Id
      octet[18]   Uplink Slot Id

    Location of DSL circuit (or Downlink Group Primary)
      octet[19]   Downlink Terminal Id
      octet[20]   Downlink Shelf Id
      octet[21]   Downlink Slot Id

    Location of DSL concentration (or Downlink Group Secondary,
        optional, set to 0xFF if not provided)
      octet[22]   Downlink Terminal Id
      octet[23]   Downlink Shelf Id
      octet[24]   Downlink Slot Id

    -------------------------------------------------------------------------
    For the _GetDropTestResults_ command, the cmd argument list format is:

    octet[2]    Version
    octet[3]    Terminal Id
    octet[4]    Shelf Id
    octet[5]    Slot Id
    octet[6]    Circuit Id (Port Id)

    -------------------------------------------------------------------------
    " 
    ::= { umc1CommandTableEntry 2 }

umc1CommandTransNbr OBJECT-TYPE
    SYNTAX INTEGER
    ACCESS read-only
    STATUS mandatory
    DESCRIPTION
    "In order to execute a command, a Management Application must first 
     initiate a Get request to read the transaction number for a given 
     command and a given argument. The agent will assign a unique transaction 
     number that can then be used for all subsequent requests to execute the 
     command the transaction number was requested for. Thus, several managers 
     executing the same command with the same argument will be assigned 
     different transaction numbers. The manager shall use the value of 
     transaction number to gather the response(s) from the response table 
     (see the definition of umc1ResponseTable)."
    ::= { umc1CommandTableEntry 3 }



umc1ResponseTable OBJECT-TYPE
    SYNTAX SEQUENCE OF Umc1ResponseTableEntry
    ACCESS not-accessible
    STATUS mandatory
    DESCRIPTION
    "A Management Application may use the umc1ResponseTable to read response 
     that was generated as a result of a command execution in an agent. The 
     response data (see the definition of umc1ResponseData) shall be read by 
     issuing successive Get-Next requests for the object umc1ResponseData. It 
     shall start reading the response data by providing the value of 
     transaction number it read earlier from umc1CommandTransNbr and a 
     sequence number 0 (zero). The response data corresponding to a transaction
     number and sequence number smaller than the sequence number returned in 
     the response to a Get-Next request shall not be accessible to subsequent 
     Get or Get-Next Requests."
    ::= { umc1CommandResponse 2 }


umc1ResponseTableEntry OBJECT-TYPE
    SYNTAX Umc1ResponseTableEntry
    ACCESS not-accessible
    STATUS mandatory
    DESCRIPTION
    "An entry in the Response table."
    INDEX   { 
            umc1ResponseTransNbr, 
            umc1ResponseSeqNbr 
            }
    ::= { umc1ResponseTable 1 }



Umc1ResponseTableEntry ::=
    SEQUENCE {
             umc1ResponseTransNbr   INTEGER,
             umc1ResponseSeqNbr     INTEGER,
             umc1ResponseData       OCTET STRING
             }


umc1ResponseTransNbr OBJECT-TYPE
    SYNTAX INTEGER
    ACCESS read-only
    STATUS mandatory
    DESCRIPTION
    "This object shall be used by the manager to retrieve the response of 
     a command executed by the Agent." 
    ::= { umc1ResponseTableEntry 1 }


umc1ResponseSeqNbr OBJECT-TYPE
    SYNTAX INTEGER
    ACCESS read-only
    STATUS mandatory
    DESCRIPTION
    "This object uniquely identifies the rows of umc1ResponseTable along with
     umc1ResponseTransNbr. It keeps track of the last fragment of the response
     data read by the manager. The manager shall continue to perform Get-Next 
     operations until the end of data is reached. At that stage the manager 
     shall receive the OID of an object that is not in the umc1ResponseTable." 
    ::= { umc1ResponseTableEntry 2 }


umc1ResponseData OBJECT-TYPE
    SYNTAX OCTET STRING (SIZE (1..255))
    ACCESS read-only
    STATUS mandatory
    DESCRIPTION
    "This object encapsulates the data corresponding to the umc1ResponseTransNbr 
     and umc1ResponseSeqNbr. The first byte of this umc1ResponseData is a version 
     byte. The second byte is a number of records encapsulated in the 
     umc1ResponseData. A length field precedes all records (Variable as well as 
     fixed length records). The length field specifies the length of record in 
     Octets. 

    General Response Data Format is shown below:
    -------------------------------------------

    Version     Number Of     Length of     Record 1    Length of     Record 2 ...
    (Byte)      Records       Record 1                  Record 2 
                (Byte)        (Byte)                    (Byte)

    The record format depends on the type of data that is being dumped.

    Record Data Format.
    ------------------
	
    For the _ReadTable_ command.
    ---------------------------

    1. Record format for Terminal Info Table (umc1TerminalInfoTable)

        Fields        Terminal    Terminal   Serial       Baud    New  
                      Id          Name       Device       Rate    Terminal
                                             Type                 Id
        Num Bytes     1           1-21       1            1       1

    2. Record Format for Terminal Status Table (umcTerminalStatusTable)

        Fields        Terminal    Terminal   
                      Id          Status      
        Num Bytes     1           1        

    3. Record Format for Inventory Shelf Table (umcInventoryShelfTable)

        Fields        Terminal    Shelf   Shelf 
                      Id          Id      Type      
        Num Bytes     1           1       2

    4. Record Format for Inventory Plug-in Table (umcInventoryPluginTable)

        Fields        Terminal    Shelf   Slot    Plugin 
                      Id          Id      Id      Type
        Num Bytes     1           1       1       2

    5. Record Format for Topology Link Table and ACO Snap Topology Link Table 
        (umc1TopologyLinkTable and umc1AcoSnapTopologyLinkTable)

        Fields        TerminalA   TerminaB
                      Id          Id 
        Num Bytes     1           1

    6. Record Format for cross connect Table( umc1XCTable)

        Fields        XC Index    XC Data
        Num Bytes     1-255       0-255

    7. Record Format for GR-303 Group Provisioning Table 
        (umc1GR303Table)

        Fields      GR-303  GR-303
                    Index   Data
        Num Bytes   1-255   0-255

    8. Record Format for TR-08 Group Provisioning Table 
        (umc1TR8Table)

        Fields      TR-08   TR-08
                    Index   Data
        Num Bytes   1-255   0-255

    9. Record Format for ATM Protection Group Provisioning Table 
        (umc1AtmProtGrpTable)

        Fields      ATM         ATM
                    Protection  Protection
                    Index       Data
        Num Bytes   1-255       0-255

    10. Record Format for Port Profile Provisioning Table 
        (umc1PortProfTable)

        Fields      Port        Port
                    Profile     Profile
                    Index       Data
        Num Bytes   1-255       0-255

    11. Record Format for Terminal Span Table (umc1TerminalSpanTable)

        Fields      Near    Near    Near    Near    Far     Far     Far
                    End     End     End     End     End     End     End
                    Term    Shelf   Slot    Plugin  Term    Shelf   Slot
                    Id      Id      Id      type    Id      Id      Id
        Num Bytes   1       1       1       2       1       1       1

    12. Record Format for Shelf Span Table (umc1ShelfSpanTable)

        Fields      Near    Near    Near    Near    Far     Far     Far    
                    End     End     End     End     End     End     End     
                    Term    Shelf   Slot    Plugin  Shelf   Slot    Plugin  
                    Id      Id      Id      type    Id      Id      type    
        Num Bytes   1       1       1       2       1       1       2        


    For the _GetAllSeqNum_ command.
    ------------------------------
    When the umc1CommandId is _GetAllSeqNum_, refer to the object description of 
    umc1SystemAllSeqNbr for the record format.


    For the _GetActiveTermName_ command.
    -----------------------------------
    When the umc1CommandId is _GetActiveTermName_, the record format is:

    Fields      Terminal    Terminal    Terminal    Baud    New         Serial
                Id          Status      Name        Rate    Terminal    Device
                                                            Id          Type
    Num Bytes   1           1           1-21        1       1           1


    For the _GetCpuDbDumpPort_ command.
    ----------------------------------
    When the umc1CommandId is _GetCpuDbDumpPort_, the record format is:

    Fields       Port Number
    Num Bytes    4


    For the _SetOrDelete_ command.
    -----------------------------
    When the umc1CommandId is _SetOrDelete_, the record format is:

    Fields        No. of Record Created/Deleted
    Num Bytes     1


    For the _ClearCache_ command.
    ----------------------------
    When the umc1CommandId is _ClearCache_, the record format is:

    Fields        Is Cache Cleared
    Num Bytes     1
 
    Is Cache Cleared value      Meaning
           1                    Cache Successfully cleared 
    If error occured while clearing cache, Agent shall issue _gerErr_ to 
    Management Station.


    For the _ActivateAco_ command.
    -----------------------------
    When the umc1CommandId is _ActivateAco_, the record format is:

    Fields        Result Byte
    Num Bytes     1
 
    Result Byte value            Meaning
           1                     ACO Activated Successfully 
    If error occured while activating ACO, Agent shall issue _gerErr_ to
    Management Station.


    For the _AotRollover_ command.
    -----------------------------
    When the umc1CommandId is _AotRollover_, the record format is:

    Fields        Result Byte
    Num Bytes     1
 
    Result Byte value            Meaning
           1                     AoT to End-To-End ATM Rollover was Successful 
    If error occured while rolling over Aot, Agent shall issue _gerErr_ to
    Management Station.


    For the _CurTrafficStats_ command.
    ---------------------------------
    When the umc1CommandId is _CurTrafficStats_, the record format is:

    Fields     Terminal  Total   Blocked   Used      Available   Non-Available Current
               Id        Calls   Calls     Channels  Channels    Channels      Hour Load
                                                            
    Num Bytes  1         2       2         2         2           2             2

    ---------------------------------------------------------------------------
    For the command ID equal to _GetLineCardStatus_, the response data will 
    follow the 'General Response Data Format' as defined above.  The definition 
    of the response record will vary depending upon the version of the UMC system.
    In all cases, the response data will contain a single record.  

    Original Response data format for command ID _GetLineCardStatus_.
    The version octet = 1.  The number of records octet = 1.  The length of 
    record #1 and the record format are determined by the octet string returned 
    by the UMC system CPU card.  In general, the record represents an array of six 
    elements where each element contains the following attributes for a single
    circuit/port: port status, downstream rate, downstream SNR margin, upstream 
    rate, and upstream SNR margin.

    Enhanced Response data format for command ID _GetLineCardStatus_.
    The version octet = 1.  The number of records octet = 1.  The record will 
    contain an array of equivalent data elements.  The size of the array 
    will depend on the number of circuits/ports supported by the card.  The length 
    of each element and the element format are determined by the octet string 
    returned by the UMC system CPU card.  In general, each record contains the 
    following attributes for a single circuit/port: port status, downstream rate, 
    downstream SNR margin, upstream rate, and upstream SNR margin, downstream signal 
    attenuation, downstream current channel bit rate, downstream transmitted signal 
    power, downstream relative capacity operation, upstream signal attenuation, 
    upstream current channel bit rate, upstream transmitted signal power, and 
    upstream relative capacity operation.

    ---------------------------------------------------------------------------
    For the command ID equal to _GetAtmStatistics_, the response data will 
    follow the 'General Response Data Format' as defined above.  The version 
    octet = 1.  The number of records octet = 2.  The response data will contain 
    a two records.  The first record represents the 'receive' ATM 
    statistics and the second record represents the 'transmit' 
    ATM statistics.  The length of each record and the record format
    are determined by the octet string returned by the UMC system CPU card.

    ---------------------------------------------------------------------------
    For the command ID equal to _GetAdslPmAttribute_, the response data will 
    follow the 'General Response Data Format' as defined above.  The response
    data will contain a single record or multiple equivalent records depending
    on the 'Data Operation' octet specified in the corresponding command table
    record.  The length of each record and the record format are determined by 
    the octet string returned by the UMC system CPU card.

    ---------------------------------------------------------------------------
    For the command ID equal to _GetPmDataBin_, the response data  
    will follow the 'General Response Data Format' as defined above.  The 
    version octet = 1.  The number of records octet depends on the 'Data 
    Operation' specified in the request.  For a 'GET EXACT' request, the 
    response data will contain 
    - a single record for a single port and bin request.
    - multiple records for an all port and/or all bin request
    For a Write request, the response data will contain a single record.
    The format and length of each record is determined by the octet string 
    returned by the UMC system CPU card.

    ---------------------------------------------------------------------------
    For the command ID equal to _GetNBLinkStats_, the response data will 
    follow the 'General Response Data Format' as defined above.  The version 
    octet = 1.  The number of records octet = 1 for a Get Exact operation and 
    1 - 8 (maximum number of GR303/transport link CCS data before overflowing 
    the 255 byte limit) for a Get Progressive operation.  The response data 
    can be one of two record types (transport link record or GR303 Group record).  
    The length of each record and the record format are determined by the octet 
    string returned by the UMC system CPU card (IB response payload).
    
    ---------------------------------------------------------------------------
    For the command ID equal to _ManualProtectionSwitch_, the response data 
    will always contain two records.  The first record has a length of one 
    octet and represents the response field from the internal system interface.  
    The possible values are: _RvOk_, _RvInvalidData_, & _RvFailure_.  The length 
    and format of the second record are determined by the octet string returned 
    by the internal system interface
   
    ---------------------------------------------------------------------------
    For each of the following commands ID, the response data will follow the 
    'General Response Data Format' as defined above.  The record format will 
    consist of an octet string as returned by the CPU:
        _GetVcStatusInfo_
        _GetBlockedVccInfo_
        _GetAtmBandwidth_
        _GetAdslBitsPerTone_
        _GetDropTestResults_

    ---------------------------------------------------------------------------
    For the command ID equal to _GenericIB_, the response data will be formatted
    as follows:  
    - First octet = version number = 1.  
    - Second octet =  number of records octet = 1.  
    - Third octet = size of record in bytes.
    - Forth octet = first byte of record will contain the CPU error code.
    - Fifth octet = second byte of record will contain the first byte of the IB
      payload.
    - Sixth octet = third byte of record will contain the second byte of the IB
      payload.
    - xth octet = last byte of the record will contain the last byte of the IB
      payload.
    Note:  The third octet will be set to 1 if the CPU returns an error code
    (not equal to _RvOk_) back to the IPMI via the IB response message.  The 
    third octet will be set to a value of greater than 1 if the CPU returns
    valid data back to the IPMI via the IB response message.  The forth octet
    will contain a value of 0 (RvOk) when valid data is returned in the IB
    payload.  The forth octet will contain a value greater than 0 (error type)
    when the CPU identifies an error condition.

    ---------------------------------------------------------------------------
    For the command ID equal to _GetAtmStatsPerVcc_, the response data will 
    follow the 'General Response Data Format' as defined above.  The response
    can contain anywhere from zero (0) response records up to six (6) response 
    records.  The record format will consist of an octet string as returned by 
    the CPU:

    " 
    ::= { umc1ResponseTableEntry 3 }


--UMC1000 ATM Protection groups
--
umc1AtmProtTableChangeSeqNum OBJECT-TYPE
    SYNTAX INTEGER (1..2147483647)
    ACCESS read-only
    STATUS mandatory
    DESCRIPTION
    "A sequence number used to indicate that the ATM Protection group 
     provisioning Table, umc1AtmProtGrpTable, has been modified and it needs 
     to be re-read. Whenever the SNMP agent is restarted, this value will be 
     reset to 0(zero). The value will be incremented by one whenever a change 
     to the ATM Protection group provisioning Table is made. This number will 
     also be sent in the umc1TrapAtmProtGrpTableChange trap and can be used 
     to determine if the manager has lost any traps. This value will be 
     incremented before the trap is sent.

     The maximum value it can assume is 2,147,483,647. An increment, 
     every time it has reached its maximum value, shall cause it to 
     be reset to 1.
    " 
    ::= { umc1System 10 }



umc1AtmProtGrpTable OBJECT-TYPE
    SYNTAX SEQUENCE OF Umc1AtmProtGrpEntry
    ACCESS not-accessible
    STATUS mandatory
    DESCRIPTION
    "A Management Station uses this table to read, modify, create or delete 
     a ATM Protection Group in the UMC system. The MIB Table has two columns 
     one for the Index and one for the Group provisioning information. It is 
     currently indexed by the Terminal number and the ATM Protection Group 
     Number value.
    "
    ::= { umc1System 11 }



umc1AtmProtGrpEntry OBJECT-TYPE
    SYNTAX Umc1AtmProtGrpEntry
    ACCESS not-accessible
    STATUS mandatory
    DESCRIPTION
    "An entry in the ATM Protection Group Provisioning Table."
    INDEX { umc1AtmProtGrpIndex }
    ::= { umc1AtmProtGrpTable 1 }


Umc1AtmProtGrpEntry ::= 
    SEQUENCE {  umc1AtmProtGrpIndex	OCTET STRING,
                umc1AtmProtGrpData	OCTET STRING }


umc1AtmProtGrpIndex OBJECT-TYPE
    SYNTAX OCTET STRING (SIZE (1..255))
    ACCESS read-write
    STATUS mandatory
    DESCRIPTION
    "It contains the Terminal and ATM Protection Group number that identifies 
     the record in the UMC system.  For the initial implementation the OCTET 
     representation will be as follows :
     octet[0]   Version number of the octet representation being used to 
                define this INDEX.  The version number for the initial 
                implementation will be 0x01.

     For Version number 0x01 the remaining octets will be defined 
     as follows :

	 octet[1]   DB specifier octet for the type of ATM Protection Group 
                record being referenced.
     octet[2]   Terminal number the ATM Protection Group is associated with.
                See TerminalIdType for the definition of valid Terminal 
                values.
     octet[3]   ATM Protection Group number of the ATM Protection Group to 
                retrieve.  The Group number is 1 based (i.e., set this to
                0x01 for ATM Protection Group 1, 
                0x02 for ATM Protection Group 2, etc.
    "
    ::= { umc1AtmProtGrpEntry 1 }



umc1AtmProtGrpData OBJECT-TYPE
    SYNTAX OCTET STRING (SIZE(0..255))
    ACCESS read-write
    STATUS mandatory
    DESCRIPTION
    "The ATM Protection Group Provisioning record. 
     For the initial implementation the OCTET representation will be 
     as follows :
     octet[0]   Version number of the octet representation being used to 
                define the following provisioning data.  The version number
                for the initial implementation will be 0x01.

     For Version number 0x01 the remaining octets will be defined 
     as follows :

     octet[1]       DB specifier octet
     octet[2] - [n] Octet packed ATM Protection Group Provisioning record.

     In a GET Request the data field is empty. In a SET Request it contains 
     the ATM Protection provisioning record to be written to the UMC 
     database. 

     In order to delete a ATM Protection Group, the Management Station 
     *MUST* :
     1. perform a SET operation and send an octet string of length 2 octet 
        (for the version octet) with octet[0] set to a valid version number,  
        octet[1] set to a valid DB type specifier and with NO additional 
        data octets supplied.
     OR
     2. perform a SET operation with octet[0] set to a valid version number,  
        octet[1] set to a valid DB type specifier and with all following 
        octets of umc1AtmProtGrpData set to the values of a DEFAULT ATM 
        Protection Group provisioning record.
    "
    ::= { umc1AtmProtGrpEntry 2 }


umc1AtmProtGrpChgTable OBJECT-TYPE
    SYNTAX SEQUENCE OF Umc1AtmProtGrpChgEntry
    ACCESS not-accessible
    STATUS mandatory
    DESCRIPTION
    "The EMS uses this table to synchronize its internal representation of 
     the ATM Protection Group Provisioning data with that managed by the 
     UMC Agent.  A trap is issued to the EMS indicating that a change to 
     the ATM Protection database (and hence the umc1AtmProtGrpTable) has 
     been made and entered as a row in this table. The EMS queries this table,
     using the sequence number received in the umc1TrapAtmProtGrpTableChange 
     trap, to determine whether it can re-learn the changed 
     umc1AtmProtGrpTable row/record from this table or must re-learn *all* 
     ATM Protection information, bypassing this table.

     When the value of umc1AtmProtTableChangeSeqNum is zero this table 
     is empty.
    "
    ::= { umc1System 12 }


umc1AtmProtGrpChgEntry OBJECT-TYPE
    SYNTAX Umc1AtmProtGrpChgEntry
    ACCESS not-accessible
    STATUS mandatory
    DESCRIPTION
    "An entry in the ATM Protection Group Provisioning Table Change 
     history table.
    "
    INDEX { umc1AtmProtGrpChgSeqNum }
    ::= { umc1AtmProtGrpChgTable 1 }


Umc1AtmProtGrpChgEntry ::=
    SEQUENCE { 
             umc1AtmProtGrpChgSeqNum	INTEGER,
             umc1AtmProtGrpChgData		OCTET STRING
             }


umc1AtmProtGrpChgSeqNum OBJECT-TYPE
    SYNTAX INTEGER
    ACCESS read-only
    STATUS mandatory
    DESCRIPTION
    "This objects value matches the value of umc1AtmProtTableChangeSeqNum 
     at the time the row was created. A valid value of this object is in 
     the range of 1 through umc1AtmProtTableChangeSeqNum.
    "
    ::= { umc1AtmProtGrpChgEntry 1 }



umc1AtmProtGrpChgData OBJECT-TYPE
    SYNTAX OCTET STRING     (SIZE (1..255))
    ACCESS read-only
    STATUS mandatory
    DESCRIPTION
    "This object records the changes to the ATM Protection Group 
     Provisioning table. 
     For the initial implementation the OCTET representation will be 
     as follows :
     octet[0]   Version number of the octet representation being used
                to define the following changed provisioning data.  
                The version number for the initial implementation will 
                be 0x01.

     For Version number 0x01 the remaining octets will be defined 
     as follows :
     octet[1]   action octet, stores the action (update/delete) 
                performed on the umc1AtmProtGrpTable. See DbActionType for 
                valid values and meaning of this octet.
     octet[2]       DB specifier octet
     octet[3] - [n] The octet packed ATM Protection Group Provisioning record
                    that was create/modified/deleted.
    "
    ::= { umc1AtmProtGrpChgEntry 2 }



--UMC1000 Port Profiles
--
umc1PortProfTableChangeSeqNum OBJECT-TYPE
    SYNTAX INTEGER (1..2147483647)
    ACCESS read-only
    STATUS mandatory
    DESCRIPTION
    "A sequence number used to indicate that the Port Profile provisioning 
     Table, umc1PortProfTable, has been modified and it needs to be re-read. 
     Whenever the SNMP agent is restarted, this value will be reset to 0x00 
     (zero). The value will be incremented by one whenever a change to the 
     Port Profile provisioning Table is made. This number will also be sent 
     in the umc1TrapPortProfTableChange trap and can be used to determine if 
     the manager has lost any traps. This value will be incremented before 
     the trap is sent.

	 The maximum value it can assume is 2,147,483,647. An increment, 
	 every time it has reached its maximum value, shall cause it to 
	 be reset to 1.
    " 
    ::= { umc1System 13 }


umc1PortProfTable OBJECT-TYPE
    SYNTAX SEQUENCE OF Umc1PortProfEntry
    ACCESS not-accessible
    STATUS mandatory
    DESCRIPTION
    "A Management Station uses this table to read, modify, create or delete 
     a Port Profile in the UMC system. The MIB Table has two columns one for 
     the Index and one for the Port Profile provisioning information. 
    "
    ::= { umc1System 14 }


umc1PortProfEntry OBJECT-TYPE
    SYNTAX Umc1PortProfEntry
    ACCESS not-accessible
    STATUS mandatory
    DESCRIPTION
    "An entry in the Port Profile Provisioning Table."
    INDEX { umc1PortProfIndex }
    ::= { umc1PortProfTable 1 }



Umc1PortProfEntry ::= 
    SEQUENCE {  umc1PortProfIndex	OCTET STRING,
                umc1PortProfData	OCTET STRING }


umc1PortProfIndex OBJECT-TYPE
    SYNTAX OCTET STRING (SIZE (1..255))
    ACCESS read-write
    STATUS mandatory
    DESCRIPTION
    "It contains the Plugin type the profile is for and  Port Profile number 
     that identifies the record in the UMC system.  For the initial 
     implementation the OCTET representation will be as follows :
     octet[0]   Version number of the octet representation being used to 
                define this INDEX.  The version number for the initial 
                implementation will be 0x01.

     For Version number 0x01 the remaining octets will be defined 
     as follows :

	 octet[1]   DB specifier octet for the type of Port Profile 
                record being referenced.
     octet[2]   Plugin Type the Port Profile is associated with.
     octet[3]   Port Profile number of the  Port Profile being referenced.
                The Port Profile number is 1 based (i.e., set this to 0x01 
                for Port Profile 1, 0x02 for Port Profile 2, etc.)
    "
    ::= { umc1PortProfEntry 1 }



umc1PortProfData OBJECT-TYPE
    SYNTAX OCTET STRING (SIZE(0..255))
    ACCESS read-write
    STATUS mandatory
    DESCRIPTION
    "The Port Profile provisioning record. 
     For the initial implementation the OCTET representation will be 
     as follows :

     octet[0]   Version number of the octet representation being used to 
                define the following provisioning data.  The version number 
                for the initial implementation will be 0x01.

     For Version number 0x01 the remaining octets will be defined 
     as follows :

     octet[1]       DB specifier octet
     octet[2] - [n] Octet packed Port Profile Provisioning record.

     In a GET Request the data field is empty. 
     In a SET Request it contains the Port Profile provisioning record. 

     In order to delete a Port Profile, the Management Station *MUST* :

     1. perform a SET and send an octet string of length 2 octets (for the 
        version octet and the DB specifier octet) with octet[0] set to a 
        valid version number, octet[1] set to a valid DB specifier value 
        and with NO additional data octets supplied.
     OR
     2. perform a SET operation with octet[0] set to a valid version number, 
        octet[1] set to a valid DB specifier value and with all following 
        octets of umc1PortProfData set to the values of a DEFAULT Port 
        Profile provisioning record.
    "
    ::= { umc1PortProfEntry 2 }



umc1PortProfChgTable OBJECT-TYPE
    SYNTAX SEQUENCE OF Umc1PortProfChgEntry
    ACCESS not-accessible
    STATUS mandatory
    DESCRIPTION
    "The EMS uses this table to synchronize its internal representation of 
     the Port Profile Provisioning data with that managed by the UMC Agent.
     A trap is issued to the EMS indicating that a change to the Port 
     Profile database (and hence the umc1PortProfTable) has been made and 
     entered as a row in this table. The EMS queries this table, using the 
     sequence number received in the umc1TrapPortProfTableChange trap, to 
     determine whether it can re-learn the changed umc1PortProfTable 
     row/record from this table or must re-learn *all* Port Profile 
     information, bypassing this table.

     When the value of umc1PortProfTableChangeSeqNum is zero this table 
     is empty.
    "
    ::= { umc1System 15 }



umc1PortProfChgEntry OBJECT-TYPE
    SYNTAX Umc1PortProfChgEntry
    ACCESS not-accessible
    STATUS mandatory
    DESCRIPTION
    "An entry in the  Port Profile Provisioning Table 
    Change history table."
    INDEX { umc1PortProfChgSeqNum }
    ::= { umc1PortProfChgTable 1 }




Umc1PortProfChgEntry ::=
    SEQUENCE { 
             umc1PortProfChgSeqNum	INTEGER,
             umc1PortProfChgData	OCTET STRING
             }



umc1PortProfChgSeqNum OBJECT-TYPE
    SYNTAX INTEGER
    ACCESS read-only
    STATUS mandatory
    DESCRIPTION
    "This objects value matches the value of umc1PortProfTableChangeSeqNum 
     at the time the row was created. A valid value of this object is in the 
     range of 1 through umc1PortProfTableChangeSeqNum.
    "
    ::= { umc1PortProfChgEntry 1 }



umc1PortProfChgData OBJECT-TYPE
    SYNTAX OCTET STRING     (SIZE (1..255))
    ACCESS read-only
    STATUS mandatory
    DESCRIPTION
    "This object records the changes to the Port Profile Provisioning table. 
     For the initial implementation the OCTET representation will be 
     as follows :
     octet[0]   Version number of the octet representation being used to 
                define the following changed provisioning data. The version 
                number for 	the initial implementation will be 0x01.

     For Version number 0x01 the remaining octets will be defined 
     as follows :

     octet[1]   action octet, stores the action (update/delete) 
                on the umc1PortProfTable. See DbActionType for valid values
                and meaning of this octet.
     octet[2]       DB specifier octet
     octet[3] - [n] The octet packed Port Profile Provisioning record that 
                    was create/modified/deleted.
    "
    ::= { umc1PortProfChgEntry 2 }





    umc1MyAgentSoftwareFeatures OBJECT-TYPE
        SYNTAX OCTET STRING (SIZE(0..255))
        ACCESS	read-only
        STATUS	mandatory
        DESCRIPTION
        "This object lists the features built into this load of IPMI software. 

         Octet[0]   represents the version of the packed format of features 
                    described below.  For this release the Version number will
                    be 0x01.

        For version equal 0x01 the format of the following octets will be :
        OPEN ISSUE - define the format of this info !
        "
        ::= { umc1System 16 } 

	--
-- Generic Database interface management table
--

    umc1SystemGenericDbProv  OBJECT IDENTIFIER ::= { umc1System 18 }


	umc1SystemGenericDbProvTableSeqNum OBJECT-TYPE
        SYNTAX INTEGER (1..2147483647)
		ACCESS read-only
		STATUS mandatory
		DESCRIPTION
		"A sequence number used to indicate that the Generic Database 
		Table, umc1SystemGenericDbProvTable, has been modified and it needs  
		to be re-read. Whenever the SNMP agent is restarted, this value will 
		be reset to 0(zero). The value will be incremented by one whenever 
		a change to the Generic Database Table has been made. This number 
		will also be sent in the umc1TrapGenericDbProvChange trap and 
		can be used to determine if any traps have been lost by the manager. 
		This value will be incremented before the trap is sent.

		The maximum value it can assume is 2,147,483,647. An increment, 
		every time it has reached its maximum value, shall cause it to 
		be reset to 1.
		"
   ::= { umc1SystemGenericDbProv 1 }


	umc1SystemGenericDbProvTable OBJECT-TYPE
		SYNTAX SEQUENCE OF Umc1SystemGenericDbProvEntry
		ACCESS not-accessible
		STATUS mandatory
		DESCRIPTION
		"A Management Station uses this table to GET or SET a *single* UMC 
        database Provisioning record. Access to this table is read-write. 
        By implementation, this table supports GET and SET operations ONLY.  
        
        GET NEXT (Progressive) is a special variant of GET which emulates 
        a true SNMP GETNEXT by overloading the GET operation. We overload the
        GET to do this because the Management Station accessing us must 
        actually perform the increment of the INDEX for us to truly make 
        this table a generic interface.  If the IPMI had to do this 
        incrementing we would have to roll out a new IPMI release for each 
        new DB record we wanted to support.

        Like GET NEXT (Progressive), GET DEFAULT is another special variant 
        of GET which allows the retrieval of DEFAULT DATABASE records (where
        supported by the UMC System) by again overloading the GET operation.
        
        DELETE of a provisioning record is an extension of the SNMP SET 
        operation and is described in more detail below."
	::= { umc1SystemGenericDbProv 2 }


	umc1SystemGenericDbProvEntry OBJECT-TYPE
		SYNTAX Umc1SystemGenericDbProvEntry
		ACCESS not-accessible
		STATUS mandatory
		DESCRIPTION
                "An entry in the System Database."
		INDEX { umc1SystemGenericDbProvIndex }
	::= { umc1SystemGenericDbProvTable 1 }


	Umc1SystemGenericDbProvEntry ::=
	SEQUENCE {  umc1SystemGenericDbProvIndex    OCTET STRING,
			    umc1SystemGenericDbProvData     OCTET STRING }

	umc1SystemGenericDbProvIndex OBJECT-TYPE
		SYNTAX OCTET STRING     (SIZE (1..255))
		ACCESS read-write
		STATUS mandatory
		DESCRIPTION
		"This is the table INDEX.  It is actually an octet encoded key 
        representing the database record to be managed and how it is to 
        be treated.
        It contains the Database Operation type, the DBSpecifier for 
        database record, and the UMC system DB KEY identifying the 
        record being referenced.
        For the initial implementation the OCTET representation will be as 
        follows :
        octet[0]    Version number of the octet representation being used to 
                    define this INDEX.  The version number for the initial 
                    implementation will be 0x01.

        For Version number 0x01 the remaining octets will be defined 
        as follows :

	    octet[1]    DB specifier octet for the database record being 
                    referenced.
        octet[2]    Operation Type :  See the DataOperation data type.
        octet[3]    The Length (in bytes) of the database key in the following
                    octets.
        octet[4] - [?]  The actual UMC System database key to be used to 
                        manage the database record in question.
        "
	::= { umc1SystemGenericDbProvEntry 1 }


	umc1SystemGenericDbProvData OBJECT-TYPE
		SYNTAX OCTET STRING     (SIZE (1..255))
		ACCESS read-write
		STATUS mandatory
		DESCRIPTION
		"The structure of this object is the same for Get Response PDUs
		and Set Request PDUs. In a SET Request the data is included in 
		the Request PDU. In a GET Request the data is returned in the 
		Response PDU.

        This object holds the actual octets sent (for a SNMP SET) or retrieved 
        (for a SNMP GET) request.

		The byte-format structure of this object, taking into account the above 
		description, is as follows:

        octet[0]    Version number of the octet representation. The version
                    number for the initial implementation will be 0x01.

        For Version number 0x01 the remaining octets will be defined as 
        follows :
        octet[1]       Length of the following octet string.
        octet[2] - [?] The DB record data as it appears in the UMC system 
                       database.
                       For a GET PROGRESSIVE request the returned key in the 
                       DATA octets described here should be compared to the 
                       key in umc1SystemGenericDbProvIndex to identify the 
                       actual record returned.

		In a GET Request the data field is empty. 
		In a SET Request it contains the only the Data portion of database
		record. It does not contain the key bytes because Key for the
		database record is already specified in the Index
		umc1SystemGenericDbProvIndex. 

		In order to delete a database record, the Management Station *MUST* 
		perform a SET and send an octet string of length 1 octets (for the 
	 	version octet) with octet[0] set to a valid version number with NO 
		additional data octets supplied.

		"
        ::= { umc1SystemGenericDbProvEntry 2 }




--
-- Generic Database interface management Changes Table
--
	
	umc1SystemGenericDbProvChgTable OBJECT-TYPE
	   SYNTAX SEQUENCE OF Umc1SystemGenericDbProvChgEntry
	   ACCESS not-accessible
	   STATUS mandatory
	   DESCRIPTION
		"The EMS uses this table to synchronize its internal representation of  
		the Generic Database management data with that managed by the UMC 
        Agent. A trap is issued to the EMS indicating a change to the Generic 
        Database Interface Management data has been made and entered as a row 
        in this table. The EMS  
		queries this table, using the sequence number received in the  
		umc1TrapGenericDbProvChange trap to determine whether it can re-learn   
		the changed Provisioning information from this table or must re-learn  
		*all* the umc1SystemGenericDbProvTable information, bypassing 
        this table.

		When the value of umc1SystemGenericDbProvTableSeqNum is zero this 
        table is empty."
	::= { umc1SystemGenericDbProv 3 }


	umc1SystemGenericDbProvChgEntry OBJECT-TYPE
	   SYNTAX Umc1SystemGenericDbProvChgEntry
	   ACCESS not-accessible
	   STATUS mandatory
	   DESCRIPTION
		   "An entry in the Generic Database Change table."
	   INDEX { umc1SystemGenericDbProvChgTableSeqNum }
	   ::= { umc1SystemGenericDbProvChgTable 1 }


	Umc1SystemGenericDbProvChgEntry ::=
	   SEQUENCE {   umc1SystemGenericDbProvChgTableSeqNum    INTEGER,
			        umc1SystemGenericDbProvChgData          OCTET STRING
	   }


	umc1SystemGenericDbProvChgTableSeqNum OBJECT-TYPE
	   SYNTAX INTEGER
	   ACCESS read-only
	   STATUS mandatory
	   DESCRIPTION
		"This object's value matches the value of umc1SystemGenericDbProvTableSeqNum 
		at the time the row was created. A valid value of this object is in the range 
		of 1 through umc1SystemGenericDbProvTableSeqNum."
	::= { umc1SystemGenericDbProvChgEntry 1 }

	umc1SystemGenericDbProvChgData OBJECT-TYPE
	   SYNTAX OCTET STRING     (SIZE (1..255))
	   ACCESS read-only
	   STATUS mandatory
	   DESCRIPTION
	        "This object records the list of modified Database record(s) managed
            by umc1SystemGenericDbProvTable, nature of the change 
            (add/modify/delete) and, possibly, the database record associated 
	        with the change that has been made..The format of the object is as 
            follows:
	        octet [0]   Version number of the octet representation. 
                        The version number for the initial implementation 
                        will be 0x01.
	        octet [1]   Action octet, stores the action (update/delete) 
                        performed on the umc1SystemGenericDbProvTable. See 
                        DbActionType for valid values of this octet.
            octet [2] - [?] The DB record data as it appears in the UMC system 
                       database.
                       For a DELETE entry these octets will only include the 
                       returned key to identify the DB record.
            "
	   ::= { umc1SystemGenericDbProvChgEntry 2 }

	umc1MibVersion OBJECT-TYPE
        SYNTAX OCTET STRING (SIZE(0..255))
        ACCESS	read-only
        STATUS	mandatory
        DESCRIPTION
        "This object gives Version of MIB supported by this load of IPMI software. 

         Octet[0]   represents the version of the packed format of MIB Version 
                    described below.  For this release the Version number will
                    be 0x01.

        For version equal 0x01 the format of the following octets will be :
         Octet[1]	MIB Version
		 Octet[2]	MIB Revision
		 Octet[3]	MIB Point

		Default Value of this MIB object needs to be modified, in order to reflect 
		the new version of MIB. 
        "
		DEFVAL { '01050003'h }  -- For IPMI MIB Version 5.0.3
        ::= { umc1System 19 }

	umc1DbRecordChangeTrapHandleMask OBJECT-TYPE
        SYNTAX OCTET STRING (SIZE(3..3))
        ACCESS	read-write
        STATUS	mandatory
        DESCRIPTION
        "This object describes how Db Record Change Trap for a given Db Record Type
		 is being handle by IPMI. For the Db Record Type listed below, IPMI can send 
		 db Record change Trap to EMS via two different mechanism:
		   (i)  Generic Db Interface
		   (ii) Respective Table Interface

         Octet[0]   represents the version of the packed format of Db Record Change 
					Trap Handling Mask described below.  
					For this release the Version number will be 0x01.

        For version equal 0x01 the format of the following octets will be :

         Octet[1-2]	Bit 15 to 0 of Db Record Change Trap Handling Mask
		 
		 Where.. 

		 Bit 0 corresponds to TR08 Db Record
		 Bit 1 corresponds to GR303 Db Record 
		 Bit 2 corresponds to Cross-Connect(Ckt-to-Ckt and ATM Virtual Ckt.) Db Record
		 Bit 3 corresponds to Protection Group Db Record
		 Bit 4 corresponds to Port Profile Db Record
		 Bit 5 corresponds to Channel Attribute Db Record
		 Bit 6 corresponds to V5 (V5 Group and V5 Variant) Db Record
		 Bit 7 corresponds to Facility Alarm String Db Record
		 Bit 8 corresponds to TL1 Interface Provisioning Db Record
		 Bit 9-15 Ignored
		 
		For a give Db Record Type if corresponding bit is set to 1, The Db Record Change 
		Trap for that Db Record Type shall be send through Generic Db Interface, 
		Otherwise The Db Record Change Trap for that Db Record Type shall be send through
		it's own Trap handling mechanism.   
        "
		DEFVAL { '010100'h }
        ::= { umc1System 20 }


--
--  Autonomous Event Table
--

    umc1SystemAutonomousEvent  OBJECT IDENTIFIER ::= { umc1System 21 }


	umc1SystemAutonomousEventSeqNum OBJECT-TYPE
        SYNTAX INTEGER (1..2147483647)
		ACCESS read-only
		STATUS mandatory
		DESCRIPTION
		"A counter which gets incremented each time an Autonomous Event(Other than Alarm) 
		occurs in the UMC System. Whenever the SNMP agent is restarted, 
		this value will be reset to 0(zero). The value will be incremented 
		by one whenever Autonomous Event occurs in the UMC System. 
		This number will also be sent in the umc1TrapSystemAutonomousEvent 
		trap and can be used to determine if any traps have been lost by 
		the manager. This value will be incremented before the trap is sent.

		The maximum value it can assume is 2,147,483,647. An increment, 
		every time it has reached its maximum value, shall cause it to 
		be reset to 1.
		"
   ::= { umc1SystemAutonomousEvent 1 }


   umc1SystemAutonomousEventTable OBJECT-TYPE
	   SYNTAX SEQUENCE OF Umc1SystemAutonomousEventTableEntry
	   ACCESS not-accessible
	   STATUS mandatory
	   DESCRIPTION
		"The EMS uses this table to synchronize its internal representation of  
		the Autonomous Event data with that managed by the UMC Agent. A trap is 
		issued to the EMS whenever Event occurs in the UMC System and entered 
		as a row in this table. The EMS  queries this table, using the sequence 
		number received in the umc1TrapSystemAutonomousEvent trap to synchronize. 

		When the value of umc1SystemAutonomousEventSeqNum is zero this 
        table is empty."
	::= { umc1SystemAutonomousEvent 2 }


	umc1SystemAutonomousEventTableEntry OBJECT-TYPE
	   SYNTAX Umc1SystemAutonomousEventTableEntry
	   ACCESS not-accessible
	   STATUS mandatory
	   DESCRIPTION
		   "An entry in the Autonomous Event Table."
	   INDEX { umc1SystemAutonomousEventTableSeqNum }
	   ::= { umc1SystemAutonomousEventTable 1 }


	Umc1SystemAutonomousEventTableEntry ::=
	   SEQUENCE {   umc1SystemAutonomousEventTableSeqNum    INTEGER,
			        umc1SystemAutonomousEventTableData      OCTET STRING
	   }


	umc1SystemAutonomousEventTableSeqNum OBJECT-TYPE	
	   SYNTAX INTEGER
	   ACCESS read-only
	   STATUS mandatory
	   DESCRIPTION
		"This object's value matches the value of umc1SystemAutonomousEventSeqNum 
		at the time the row was created. A valid value of this object is in 
		the range of 1 through umc1SystemAutonomousEventSeqNum."
	::= { umc1SystemAutonomousEventTableEntry 1 }

	umc1SystemAutonomousEventTableData OBJECT-TYPE
	   SYNTAX OCTET STRING     (SIZE (1..255))
	   ACCESS read-only
	   STATUS mandatory
	   DESCRIPTION
	        "This object represents detailed Autonomous Event Information. 
			The format of the object is as follows:

	        octet [0]		Version number of the octet representation. 
							The version number for the initial implementation 
							will be 0x01.
	        octet [1]		Event Message Type, i.e 0xbb for _LcMtEvent_ message.
			octet [2]		Length of following octet string.
			octet [3-255]	octet string returned by the CPU.	
            
            "
	   ::= { umc1SystemAutonomousEventTableEntry 2 }



-- ============================================================
--
-- Threshold Crossing Alert History Table
--
-- ============================================================

umc1SystemTcaEvent  OBJECT IDENTIFIER ::= { umc1000 13 }

umc1SystemTCASeqNum OBJECT-TYPE
    SYNTAX INTEGER (1..2147483647)
    ACCESS read-only
    STATUS mandatory
    DESCRIPTION
        "A sequence number used to indicate that the Threshold Crossing Alert 
        History (TCA) Table, umc1SystemTCAHistoryTable, has been modified and 
        it needs to be re-read. Whenever the SNMP agent is restarted, this 
        value will reset to 0(zero). The value will be incremented by one 
        whenever a change to the Threshold Crossing Alert History Table has 
        been made. This number will also be sent in the 
        umc1TrapTCAHistoryTableChange TRAP and can be used to determine 
        if any traps have been lost by the manager.  This value will be 
        incremented before the trap is sent.

        The maximum value it can assume is 2,147,483,647. An increment, 
        every time it has reached its maximum value, shall cause it to 
        be reset to 1.
        "
    ::= { umc1SystemTcaEvent 1 }


umc1SystemTCAHistoryTable OBJECT-TYPE
        SYNTAX SEQUENCE OF Umc1SystemTCAHistoryTableEntry
        ACCESS not-accessible
        STATUS mandatory
        DESCRIPTION
            "The EMS uses this table to synchronize its internal representation 
            of the Threshold Crossing Alert data with that managed by the UMC 
            Agent. A trap is issued to the EMS indicating a change to Threshold 
            Crossing Alert History Table data has been made and entered as a row 
            in this table. The EMS queries this table, using the sequence number 
            received in the umc1TrapTCAHistoryTableChange trap to determine 
            whether it can re-learn the missed TCA information from this.

            When the value of umc1SystemTCAHistoryTableSeqNum is zero this 
            table is empty."
    ::= { umc1SystemTcaEvent 2 }



    umc1SystemTCAHistoryTableEntry OBJECT-TYPE
        SYNTAX Umc1SystemTCAHistoryTableEntry
        ACCESS not-accessible
        STATUS mandatory
        DESCRIPTION
            "An entry in the TCA History table."
        INDEX { umc1SystemTCAHistoryTableSeqNum }
    ::= { umc1SystemTCAHistoryTable 1 }




    Umc1SystemTCAHistoryTableEntry ::=
        SEQUENCE    {   umc1SystemTCAHistoryTableSeqNum     INTEGER,
                        umc1SystemTCAHistoryTableChgData    OCTET STRING
                    }



	
    umc1SystemTCAHistoryTableSeqNum OBJECT-TYPE
        SYNTAX INTEGER (1..2147483647)
        ACCESS read-only
        STATUS mandatory
        DESCRIPTION
		    "This object's value matches the value of umc1SystemTCASeqNum 
		    at the time the row was created. A valid value of this object is in 
		    the range of 1 through umc1SystemTCASeqNum."
        ::= { umc1SystemTCAHistoryTableEntry 1 }



    umc1SystemTCAHistoryTableChgData OBJECT-TYPE
        SYNTAX OCTET STRING     (SIZE (1..255))
        ACCESS read-only
        STATUS mandatory
        DESCRIPTION
            "This object records the list of TCAs managed by the 
            umc1SystemTCAHistoryTable.  The format of the object is as
            follows:
            octet [0]   Version number of the octet representation. 
                        The version number for the initial implementation 
                        will be 0x01.
            octet [1] - [?] The TCA data as it was received from the 
                        AccessMax system.
            "
    ::= { umc1SystemTCAHistoryTableEntry 2 }


--
--  Sequence Number Trap Trigger
--

    umc1TriggerTrapAllSeqNumbers OBJECT-TYPE
        SYNTAX    INTEGER
        ACCESS	read-only
        STATUS	mandatory
        DESCRIPTION
            "This object provides a mechanism for triggering the 'umc1TrapAllSeqNbrDump' 
             trap.  A GET operation to read its value shall trigger a trap event and 
             return the value 0 (Trap issued successfully) or 1 (trap failed).
            "
        ::= { umc1000 12 }

--
-- F5 Loopback 
--

umc1F5Loopback  OBJECT IDENTIFIER ::= { umc1000 17 }

umc1F5LoopbackRequestTable OBJECT-TYPE
    SYNTAX SEQUENCE OF Umc1F5LoopbackRequestEntry
    ACCESS not-accessible
    STATUS mandatory
    DESCRIPTION
       "Contains the contents of an F5 loopback request"
    ::= { umc1F5Loopback 1 }

umc1F5LoopbackRequestEntry OBJECT-TYPE
    SYNTAX Umc1F5LoopbackRequestEntry
    ACCESS not-accessible
    STATUS mandatory
    DESCRIPTION
        "An entry in the terminal provisioning table. The data is
         indexed by the terminal whose data is represented."
    INDEX {umc1F5LoopbackTransactionNumber}
    ::= { umc1F5LoopbackRequestTable 1 }


Umc1F5LoopbackRequestEntry ::=
    SEQUENCE {
    umc1F5LoopbackTransactionNumber          INTEGER,
    umc1F5LoopbackTransactionIpAddress      IpAddress,
    umc1F5LoopbackTransactionIbMessage    OCTET STRING
    }

umc1F5LoopbackTransactionNumber OBJECT-TYPE
        SYNTAX INTEGER (1..2147483647)
    ACCESS read-write
    STATUS mandatory
    DESCRIPTION
        "A sequence number used to associate the request with the trap
        that contains the F5 loopback results"
        ::= { umc1F5LoopbackRequestEntry 1 }

umc1F5LoopbackTransactionIpAddress OBJECT-TYPE
    SYNTAX IpAddress
    ACCESS read-write
    STATUS mandatory
    DESCRIPTION
        "An IP address of the host that requested the loopback"
        ::= { umc1F5LoopbackRequestEntry 2 }

umc1F5LoopbackTransactionIbMessage OBJECT-TYPE
   SYNTAX OCTET STRING   (SIZE (36..36))
    ACCESS read-write
    STATUS mandatory
    DESCRIPTION
        "Contents of the ib message that  will be sent to the interface
         card, the tOAMLpbkRequest size + 1 byte for the destination icard"
        ::= { umc1F5LoopbackRequestEntry 3 }

Umc1F5LoopbackTransactionResponse ::=
        SEQUENCE {
                 umc1F5LoopbackResponseSequence   INTEGER,
                 umc1F5LoopbackResponseAddress   IpAddress,
                 umc1F5LoopbackIbResponse    OCTET STRING
                 }

--
-- ADSL2+ LoopDiagnostics 
--

umc1LoopDiagnostics  OBJECT  IDENTIFIER ::= { umc1000 18 }

umc1LoopDiagnosticsRequestTable OBJECT-TYPE
    SYNTAX SEQUENCE OF Umc1LoopDiagnosticsRequestEntry
    ACCESS not-accessible
    STATUS mandatory
    DESCRIPTION
       "Contains the contents of an ADSL 2+ loop 
       diagnostics request.  The EMS shall issue this 
       SET to start the LoopDiagnostics on the specified card.
       When the operation is complete the agent will send a TRAP
       that contains the LoopCharacteristics, and the EMS can
       GET any of the other parameters using the 
       umc1LoopDiagnosticsResponseTable"
    ::= { umc1LoopDiagnostics 1 }

umc1LoopDiagnosticsRequestEntry OBJECT-TYPE
    SYNTAX Umc1LoopDiagnosticsRequestEntry
    ACCESS not-accessible
    STATUS mandatory
    DESCRIPTION
        "Format for Umc1LoopDiagnosticsRequestTable."
    INDEX {umc1LoopDiagnosticsRequestTransactionNumber,umc1LoopDiagnosticsRequestIpAddress}
    ::= { umc1LoopDiagnosticsRequestTable 1 }

Umc1LoopDiagnosticsRequestEntry ::=
    SEQUENCE {
    umc1LoopDiagnosticsRequestTransactionNumber          INTEGER,
    umc1LoopDiagnosticsRequestIpAddress      IpAddress,
    umc1LoopDiagnosticsRequestData    OCTET STRING
    }

umc1LoopDiagnosticsRequestTransactionNumber OBJECT-TYPE
        SYNTAX INTEGER (1..2147483647)
    ACCESS read-write
    STATUS mandatory
    DESCRIPTION
        "A sequence number used to associate the request with the trap
        that contains the LoopCharacteristics results, and subsequent
        Get requests."
        ::= { umc1LoopDiagnosticsRequestEntry 1 }

umc1LoopDiagnosticsRequestIpAddress OBJECT-TYPE
    SYNTAX IpAddress
    ACCESS read-write
    STATUS mandatory
    DESCRIPTION
        "An IP address of the host that requested the diagnostics."
        ::= { umc1LoopDiagnosticsRequestEntry 2 }

umc1LoopDiagnosticsRequestData OBJECT-TYPE
    SYNTAX OCTET STRING   (SIZE (5..5))
    ACCESS read-write
    STATUS mandatory
    DESCRIPTION
        "Loop diagnostics request in the following format:
         byte[0] - version number (1 for now)
         byte[1] - ADSL PIT
         byte[2] - ADSL Port number (0-based)
         byte[3] - Terminal ID (LET = 1)
         byte[4] - icard (0-based)"
        ::= { umc1LoopDiagnosticsRequestEntry 3 }


umc1LoopDiagnosticsResponseTable OBJECT-TYPE
    SYNTAX SEQUENCE OF Umc1LoopDiagnosticsResponseEntry
    ACCESS not-accessible
    STATUS mandatory
    DESCRIPTION
       "Once the LoopDiagnostics have been performed using the
       umc1LoopDiagnosticsRequestTable, the results are cached on the
       card.  The EMS can then ask for the remaining results (CCF, QLN, 
       etc.) using this table.  The LoopCharacteristics are already sent
       back as part of the trap."
    ::= { umc1LoopDiagnostics 2 }

umc1LoopDiagnosticsResponseEntry OBJECT-TYPE
    SYNTAX Umc1LoopDiagnosticsResponseEntry
    ACCESS not-accessible
    STATUS mandatory
    DESCRIPTION
        "The format of the umc1LoopDiagnosticsResponseTable."
    INDEX {umc1LoopDiagnosticsResponseTransactionNumber,
           umc1LoopDiagnosticsResponseIpAddress,
           umc1LoopDiagnosticsResponseStartToneIdentifier}
    ::= { umc1LoopDiagnosticsResponseTable 1 }

Umc1LoopDiagnosticsResponseEntry ::=
    SEQUENCE {
    umc1LoopDiagnosticsResponseTransactionNumber          INTEGER,
    umc1LoopDiagnosticsResponseIpAddress      IpAddress,
    umc1LoopDiagnosticsResponseStartToneIdentifier   INTEGER,
    umc1LoopDiagnosticsResponseEndToneIdentifier     INTEGER,
    umc1LoopDiagnosticsResponseResponse    OCTET STRING
    }

umc1LoopDiagnosticsResponseTransactionNumber OBJECT-TYPE
        SYNTAX INTEGER (1..2147483647)
    ACCESS read-only
    STATUS mandatory
    DESCRIPTION
        "A sequence number used to associate the test that was 
        performed with the results of the test"
        ::= { umc1LoopDiagnosticsResponseEntry 1 }

umc1LoopDiagnosticsResponseIpAddress OBJECT-TYPE
    SYNTAX IpAddress
    ACCESS read-only
    STATUS mandatory
    DESCRIPTION
        "An IP address of the host that requested the diagnostics"
        ::= { umc1LoopDiagnosticsResponseEntry 2 }

umc1LoopDiagnosticsResponseStartToneIdentifier OBJECT-TYPE
        SYNTAX INTEGER (1..2147483647)
    ACCESS read-only
    STATUS mandatory
    DESCRIPTION
        "Enumerated value from SIS:
             0x01 = Loop Characteristics
             0x02 = CCF for Tones 0 to 42
         0x03 = CCF for Tones 43 to 85
         0x04 = CCF for Tones 86 to 128
         0x05 = CCF for Tones 129 to 171
         0x06 = CCF for Tones 172 to 214
         0x07 = CCF for Tones 215 to 255
         0x08 = CCF for Tones 256 to 298
         0x09 = CCF for Tones 299 to 341
         0x0A = CCF for Tones 342 to 384
         0x0B = CCF for Tones 385 to 427
         0x0C = CCF for Tones 428 to 470
         0x0D = CCF for Tones 471 to 511
         0x0E = QLN for Tones 0 to 42
         0x0F = QLN for Tones 43 to 85
         0x10 = QLN for Tones 86 to 128
         0x11 = QLN for Tones 129 to 171
         0x12 = QLN for Tones 172 to 214
         0x13 = QLN for Tones 215 to 255
         0x14 = QLN for Tones 256 to 298
         0x15 = QLN for Tones 299 to 341
         0x16 = QLN for Tones 342 to 384
         0x17 = QLN for Tones 385 to 427
         0x18 = QLN for Tones 428 to 470
         0x19 = QLN for Tones 471 to 511
         0x1A = SNR for Tones 0 to 42
         0x1B = SNR for Tones 43 to 85
         0x1C = SNR for Tones 86 to 128
         0x1D = SNR for Tones 129 to 171
         0x1E = SNR for Tones 172 to 214
         0x1F = SNR for Tones 215 to 255
         0x20 = SNR for Tones 256 to 298
         0x21 = SNR for Tones 299 to 341
         0x22 = SNR for Tones 342 to 384
         0x23 = SNR for Tones 385 to 427
         0x24 = SNR for Tones 428 to 470
         0x25 = SNR for Tones 471 to 511
        "
        ::= { umc1LoopDiagnosticsResponseEntry 3 }

umc1LoopDiagnosticsResponseEndToneIdentifier OBJECT-TYPE
        SYNTAX INTEGER (1..2147483647)
    ACCESS read-only
    STATUS mandatory
    DESCRIPTION "The last tone represented in the message, same
        enumeration as start tone."
        ::= { umc1LoopDiagnosticsResponseEntry 4 }
    
umc1LoopDiagnosticsResponseData OBJECT-TYPE
    SYNTAX OCTET STRING   (SIZE (36..36))
    ACCESS read-only
    STATUS mandatory
    DESCRIPTION
        "Contents of the LoopDiagnostics data in the
         following format:
         byte [0]  Start tone of response data  (from 
            umc1LoopDiagnosticsDataStartToneIdentifier enum)
         byte [1]  End tone of response data (from 
            umc1LoopDiagnosticsDataStartToneIdentifier enum)
         byte [2]  Response Status (0 means valid data)
       Then either:
         byte[3-45] Data for first tone
         byte[46-88] Data for second tone, if applicable
         byte[89-131] Data for third tone, if applicable
         byte[132-174] Data for fourth tone, if applicable
         byte[175-217] Data for fifth tone, if applicable
       or:
         byte[3-4] Loop Attenuation
         byte[5-6] Signal attenuation
         byte[7-8] SNR margin
         byte[9-10] Attainable net data rate
         byte[11-12] Actual aggregate transmit power.
         
         The start tone identifier will indicate the value of the 
         payload bytes."
        ::= { umc1LoopDiagnosticsResponseEntry 6 }

-- This response comes in the form of a trap.  The trap will
-- contain the LoopCharacteristics form of the response, if the
-- client want the noise readings then he has to send seperate
-- Get or GetNext requests.  The data response is in the
-- following format:
--         byte[3-4] Loop Attenuation
--         byte[5-6] Signal attenuation
--         byte[7-8] SNR margin
--         byte[9-10] Attainable net data rate
--         byte[11-12]Actual aggregate transmit power
Umc1LoopDiagnosticsTrapData ::=
        SEQUENCE {
                 umc1LoopDiagnosticsSequence   INTEGER,
                 umc1LoopDiagnosticsAddress   IpAddress,
                 umc1LoopDiagnosticsLoopCharacterstics    OCTET STRING
                 }

END
