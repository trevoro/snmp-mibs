AIX1-MIB DEFINITIONS ::=  BEGIN

-- Applied Innovation AI X.25 Series 1 MIB definitions
-- @(#) ai $Revision:   1.9  $ $Date:   15 Jan 1999 12:09:48  $

IMPORTS
		DisplayString FROM SNMPv2-TC
    MODULE-IDENTITY, OBJECT-TYPE, Counter32, Integer32,
    enterprises
        FROM SNMPv2-SMI;
--  InterfaceIndex
--      FROM IF-MIB;


-- group object IDs

aii             OBJECT IDENTIFIER ::= { enterprises 539 }
aiSystemOID     OBJECT IDENTIFIER ::= { aii 2 }
aiX1            OBJECT IDENTIFIER ::= { aii 12 }

-- Group for all Series One X.25 Smart Line Cards (CLC)

aiX1System      OBJECT IDENTIFIER ::= { aiX1 1 }
aiX1Appl        OBJECT IDENTIFIER ::= { aiX1 2 }
aiX1Pkt         OBJECT IDENTIFIER ::= { aiX1 3 }
aiX1Frm         OBJECT IDENTIFIER ::= { aiX1 4 }
aiX1Phys        OBJECT IDENTIFIER ::= { aiX1 5 }
aiX1VC          OBJECT IDENTIFIER ::= { aiX1 6 }

-- sysObjectIDs

ai192           OBJECT IDENTIFIER ::= { aiSystemOID 192 }
ai192Ver7       OBJECT IDENTIFIER ::= { ai192 7 }
ai192Ver70      OBJECT IDENTIFIER ::= { ai192Ver7 0 }
ai192Ver708     OBJECT IDENTIFIER ::= { ai192Ver70 8 }
ai192Ver709     OBJECT IDENTIFIER ::= { ai192Ver70 9 }
ai192Ver71      OBJECT IDENTIFIER ::= { ai192Ver7 1 }
ai192Ver710     OBJECT IDENTIFIER ::= { ai192Ver71 0 }
ai192Ver711     OBJECT IDENTIFIER ::= { ai192Ver71 1 }
ai192Ver72      OBJECT IDENTIFIER ::= { ai192Ver7 2 }
ai192Ver720     OBJECT IDENTIFIER ::= { ai192Ver72 0 }
ai192Ver721     OBJECT IDENTIFIER ::= { ai192Ver72 1 }
ai192Ver77      OBJECT IDENTIFIER ::= { ai192Ver7 7 }

ai196           OBJECT IDENTIFIER ::= { aiSystemOID 196 }
ai196Ver7       OBJECT IDENTIFIER ::= { ai196 7 }
ai196Ver70      OBJECT IDENTIFIER ::= { ai196Ver7 0 }
ai196Ver708     OBJECT IDENTIFIER ::= { ai196Ver70 8 }
ai196Ver709     OBJECT IDENTIFIER ::= { ai196Ver70 9 }
ai196Ver71      OBJECT IDENTIFIER ::= { ai196Ver7 1 }
ai196Ver710     OBJECT IDENTIFIER ::= { ai196Ver71 0 }
ai196Ver711     OBJECT IDENTIFIER ::= { ai196Ver71 1 }
ai196Ver72      OBJECT IDENTIFIER ::= { ai196Ver7 2 }
ai196Ver720     OBJECT IDENTIFIER ::= { ai196Ver72 0 }
ai196Ver721     OBJECT IDENTIFIER ::= { ai196Ver72 1 }
ai196Ver77      OBJECT IDENTIFIER ::= { ai196Ver7 7 }

          IfIndexType     ::= INTEGER (1..2147483647)
          -- IfIndexType specifies an index object for a table
          -- with entries that match entries in the MIB-II ifTable.
          -- The value of the index for the table will match the
          -- ifIndex entry for same interface in the ifTable.
          -- The values of this object range from 1 to ifNumber
          -- inclusive.


-- System Group

-- Implementation of this group is mandatory for all Applied Innovation
-- X.25 Series 1 cards(SLC's) that support SNMP management

    aix1AdminGbufXoffThreshold OBJECT-TYPE
        SYNTAX     INTEGER(0..'ffff'h)
        ACCESS     read-write
        STATUS     mandatory
        DESCRIPTION
            "The configured XOFF global flow control threshold.  If
            zero and if aix1AdminGbufRecovThreshold is zero, the
            global flow control mechanism is disabled."
        DEFVAL     { 0 }
        ::= { aiX1System 1 }

    aix1AdminGbufRecovThreshold OBJECT-TYPE
        SYNTAX     INTEGER(0..'ffff'h)
        ACCESS     read-write
        STATUS     mandatory
        DESCRIPTION
            "The configured recovery global flow control threshold.
            If zero and if aix1AdminGbufXoffThreshold is zero, the
            global flow control mechanism is disabled."
        DEFVAL     { 0 }
        ::= { aiX1System 2 }

    aix1AdminRollover OBJECT-TYPE
        SYNTAX     INTEGER {
                         ready(1),
                         roll(2)
                        }
        ACCESS     read-only
        STATUS     mandatory
        DESCRIPTION
            "This object has been depricated and remains in the MIB
            for backward compatibility."
        DEFVAL     { ready }
        ::= { aiX1System 3 }

    aix1Bx25AdminCallDown OBJECT-TYPE
        SYNTAX     INTEGER {
                         on(1),
                         off(2)
                        }
        ACCESS     read-write
        STATUS     mandatory
        DESCRIPTION
            "If set to off(2), an active BX.25 link will stay up after
            all calls are disconnected.  If set to on(1), an active
            BX.25 link will drop and go into DMLOCK (see
            aix1Bx25AdminDMlock below) when all the link's backplane
            connections are terminated.  This object is meaningful only
            when aix1ApplOperLinkMode is set to passive(2) on a given
            packet layer entity."
        DEFVAL     { off }
        ::= { aiX1System 4 }

    aix1Bx25AdminDMlock OBJECT-TYPE
        SYNTAX     INTEGER(25..'ffffffff'h)
        ACCESS     read-write
        STATUS     mandatory
        DESCRIPTION
            "The number of seconds to wait after a BX.25 passive link
            has gone inactive before allowing an outgoing call to
            attempt to bring up the link.  Any outgoing call attempts
            will be rejected until the DMLOCK timer expires and the
            passive link returns to the standby mode.  This object is
            meaningful only when aix1ApplOperLinkMode is set to
            passive(2) on a given packet layer entity."
        DEFVAL     { 60 }
        ::= { aiX1System 5 }

    aix1Bx25AdminLinkUp OBJECT-TYPE
        SYNTAX     INTEGER(5..'ffffffff'h)
        ACCESS     read-write
        STATUS     mandatory
        DESCRIPTION
            "The number of seconds to wait for a passive link to become
            active. This object is meaningful only when
            aix1ApplOperLinkMode is set to passive(2) on a given packet
            layer entity."
        DEFVAL     { 25 }
        ::= { aiX1System 6 }

    aix1StatErrX25InData OBJECT-TYPE
        SYNTAX     Counter32
        ACCESS     read-only
        STATUS     mandatory
        DESCRIPTION
            "Number of data bytes from X.25 which were lost due to
            buffer failures." 
        ::= { aiX1System 7 }

    aix1StatErrX25OutData OBJECT-TYPE
        SYNTAX     Counter32
        ACCESS     read-only
        STATUS     mandatory
        DESCRIPTION
            "Number of data bytes from the FIFO which were discarded
            due to buffer failures."
        ::= { aiX1System 8 }

    aix1StatErrX25OutPkt OBJECT-TYPE
        SYNTAX     Counter32
        ACCESS     read-only
        STATUS     mandatory
        DESCRIPTION
            "Number of messages from X.25 to GCOM which were lost due
            to some kind of resource failure in the GCOM library."
        ::= { aiX1System 9 }

    aix1StatErrX25OutChoked OBJECT-TYPE
        SYNTAX     Counter32
        ACCESS     read-only
        STATUS     mandatory
        DESCRIPTION
            "Number of times a port has received a flow control stop
            message from GCOM(or perhaps from X.25), and thus entered
            the Choked state.  This may not be indicative of a
            serious problem, but may also mean that data has been lost."
        ::= { aiX1System 10 }

    aix1StatErrPlogCount OBJECT-TYPE
        SYNTAX     Counter32
        ACCESS     read-only
        STATUS     mandatory
        DESCRIPTION
            "Number of times an internal error routine has been called
            due to unexpected packets received from GCOM ( or X.25)."
        ::= { aiX1System 11 }

    aix1StatErrGfctlXoffs OBJECT-TYPE
        SYNTAX     Counter32
        ACCESS     read-only
        STATUS     mandatory
        DESCRIPTION
            "Number of times the global flow control mechanism attempted
            to back pressure data flow from the backplane."
        ::= { aiX1System 12 }

    aix1StatErrGfctlDiscards OBJECT-TYPE
        SYNTAX     Counter32
        ACCESS     read-only
        STATUS     mandatory
        DESCRIPTION
            "Number of times the global flow control mechanism has
            detected a buffer level so low that it discarded data
            received from the backplane."
        ::= { aiX1System 13 }

    aix1StatErrUwteBadTrans OBJECT-TYPE
        SYNTAX     Counter32
        ACCESS     read-only
        STATUS     mandatory
        DESCRIPTION
            "Number of unified window transactions with bad transaction
            codes received from CLC or a remote SLC.  If this counter
            is non-zero, it indicated the presence of incompatible
            versions of firmware on the SLC and CLC, or a bug in either
            the SLC or CLC firmware."
        ::= { aiX1System 14 }

    aix1StatErrUwteBadFlds OBJECT-TYPE
        SYNTAX     Counter32
        ACCESS     read-only
        STATUS     mandatory
        DESCRIPTION
            "Number of invalid fields received in unified window
            transactions.  If this counter is non-zero, it indicates
            the presence of incompatible versions or a bug in either
            the SLC or CLC firmware."
        ::= { aiX1System 15 }

    aix1StatErrUwteMissingFlds OBJECT-TYPE
        SYNTAX     Counter32
        ACCESS     read-only
        STATUS     mandatory
        DESCRIPTION
            "Number of required fields absent from received unified
            window transactions. If this counter is non-zero, it
            indicates the presence of incompatible versions or a bug
            in either the SLC or CLC firmware."
        ::= { aiX1System 16 }

    aix1StatErrLogOutLost OBJECT-TYPE
        SYNTAX     Counter32
        ACCESS     read-only
        STATUS     mandatory
        DESCRIPTION
            "Number of outbound log messages discarded to avoid flooding
            the log.  This arises because the SLC is attempting to
            generate log messages too frequently on a particular TDS or
            globally.  When this occurs, the SLC will discard the log
            message and increment the counter.  This is not a serious
            error, and typically occurs during periods of intense,
            repetitive logging activity."
        ::= { aiX1System 17 }

    aix1StatErrVcMuxErrs OBJECT-TYPE
        SYNTAX     Counter32
        ACCESS     read-only
        STATUS     mandatory
        DESCRIPTION
            "Number of serious multiplexing errors which have occurred.
            Such an error generally involves an impossible value in an
            internal header or receipt of a message on the wrong
            internal channel."
        ::= { aiX1System 18 }

    aix1StatErrEmptyPktsRcv OBJECT-TYPE
        SYNTAX     Counter32
        ACCESS     read-only
        STATUS     mandatory
        DESCRIPTION
            "Number of empty data packets received from the network."
        ::= { aiX1System 19 }

    aix1StatInCharsPerSec80s OBJECT-TYPE
        SYNTAX     Counter32
        ACCESS     read-only
        STATUS     mandatory
        DESCRIPTION
            "The average number of data characters (characters in the
            data field of X.25 data packets) received from the network
            per second over the last 80 seconds."
        ::= { aiX1System 20 }

    aix1StatOutCharsPerSec80s OBJECT-TYPE
        SYNTAX     Counter32
        ACCESS     read-only
        STATUS     mandatory
        DESCRIPTION
            "The average number of data characters (characters in the
            data field of X.25 data packets) transmitted to the network
            per second over the last 80 seconds."
        ::= { aiX1System 21 }


-- the Application Interface group

-- Implementation of this group is mandatory for all Applied Innovation
-- X.25 Series 1 cards that support SNMP management


          -- the Application Interface Administrative table

          aix1ApplAdminTable OBJECT-TYPE
              SYNTAX     SEQUENCE OF ApplAdminEntry
              ACCESS     not-accessible
              STATUS     mandatory
              DESCRIPTION
                      "The table of administrative elements which apply
                      to an individual X.25 link above the packet layer."
              ::= { aiX1Appl 1 }

          aix1ApplAdminEntry OBJECT-TYPE
              SYNTAX     ApplAdminEntry
              ACCESS     not-accessible
              STATUS     mandatory
              DESCRIPTION
                      "The addressing information for one of this X.25
                      link's administrative objects."
              INDEX      { aix1ApplAdminIndex }
              ::= { aix1ApplAdminTable 1 }

          ApplAdminEntry ::=
              SEQUENCE {
                  aix1ApplAdminIndex
                      IfIndexType,
                  aix1ApplAdminLinkStart
                      INTEGER,
                  aix1ApplAdminLinkMode
                      INTEGER,
                  aix1ApplAdminResetErrs
                      INTEGER,
                  aix1ApplAdminXONXOFFProto
                      INTEGER,
                  aix1ApplAdminNMAProto
                      INTEGER,
                  aix1ApplAdminOPSINEProto
                      INTEGER,
                  aix1ApplAdminTL1Proto
                      INTEGER,
                  aix1ApplAdminLinkDescription
                      DisplayString,
                  aix1ApplAdminLinkConnectionMode
                      INTEGER
              }


    aix1ApplAdminIndex OBJECT-TYPE
        SYNTAX     IfIndexType
        ACCESS     read-only
        STATUS     mandatory
        DESCRIPTION
            "The ifIndex value of the packet layer entity associated
             with these application level objects."
        ::= { aix1ApplAdminEntry 1 }

    aix1ApplAdminLinkStart OBJECT-TYPE
        SYNTAX     INTEGER {
                         started(1),
                         stopped(2)
                        }
        ACCESS     read-write
        STATUS     mandatory
        DESCRIPTION
            "Start or stop a link that's enabled by the standard MIB
            link status objects.  If the link is not enabled by the
            standard MIB objects, a write to this object will have no
            effect.  Stopping a link by writing to this object does
            not free significant resources, it just stops activity on
            the link."
        DEFVAL     { started }
        ::= { aix1ApplAdminEntry 2 }

    aix1ApplAdminLinkMode OBJECT-TYPE
        SYNTAX     INTEGER {
                         normal(1),
                         passive(2)
                        }
        ACCESS     read-write
        STATUS     mandatory
        DESCRIPTION
            "Determines whether link behaves as a normal X.25 link or
            a BX.25-style passive link.  This is the most recently
            configured value of this attribute, and may not yet have
            taken effect.  The current operating value is available
            as aix1ApplOperLinkMode."
        DEFVAL     { normal }
        ::= { aix1ApplAdminEntry 3 }

    aix1ApplAdminResetErrs OBJECT-TYPE
        SYNTAX     INTEGER {
                         ready(1),
                         resetCounters(2)
                        }
        ACCESS     read-write
        STATUS     mandatory
        DESCRIPTION
            "Writing the value resetCounters(2) to this object resets
            the per-link level 1 error counters.  No other writes are
            accepted.  They are aix1PhysStatRxCRCErrors,
            aix1PhysStatRxAborts, aix1PhysStatRxOverruns,
            aix1PhysStatTxAborts, aix1PhysStatTxUnderruns."
        ::= { aix1ApplAdminEntry 4 }

    aix1ApplAdminXONXOFFProto OBJECT-TYPE
        SYNTAX     INTEGER {
                         on(1),
                         off(2)
                        }
        ACCESS     read-write
        STATUS     mandatory
        DESCRIPTION
            "Determines whether XON/XOFF protocol processing is in
            effect by default on all virtual circuits on the link."
        ::= { aix1ApplAdminEntry 5 }

    aix1ApplAdminNMAProto OBJECT-TYPE
        SYNTAX     INTEGER {
                         on(1),
                         off(2)
                        }
        ACCESS     read-write
        STATUS     mandatory
        DESCRIPTION
            "Determines whether NMA protocol processing is in effect
            by default on all virtual circuits on the link."
        ::= { aix1ApplAdminEntry 6 }

    aix1ApplAdminOPSINEProto OBJECT-TYPE
        SYNTAX     INTEGER {
                         on(1),
                         off(2)
                        }
        ACCESS     read-write
        STATUS     mandatory
        DESCRIPTION
            "Determines whether OPSINE protocol processing is in effect
            by default on all virtual circuits on the link."
        ::= { aix1ApplAdminEntry 7 }

    aix1ApplAdminTL1Proto OBJECT-TYPE
        SYNTAX     INTEGER {
                         on(1),
                         off(2)
                        }
        ACCESS     read-write
        STATUS     mandatory
        DESCRIPTION
            "Determines whether TL1 protocol processing is in effect
            by default on all virtual circuits on the link."
        ::= { aix1ApplAdminEntry 8 }

    aix1ApplAdminLinkDescription OBJECT-TYPE
        SYNTAX     DisplayString (SIZE (0..50))
        ACCESS     read-write
        STATUS     mandatory
        DESCRIPTION
            "A descriptive string associated with this link.  This
            provides a place for the agent to supply any descriptive
            information about the use or owner of the link.  A zero
            length value indicates that the agent doesn't have any
            additional information."
        ::= { aix1ApplAdminEntry 9 }

    aix1ApplAdminLinkConnectionMode OBJECT-TYPE
        SYNTAX     INTEGER {
                         connected(1),
                         disconnected(2),
                         disabled(4)
                        }
        ACCESS     read-write
        STATUS     mandatory
        DESCRIPTION
            "Connect or disconnect a link that's enabled by the
            standard MIB linmk status objects.  If the link is not
            enabled by the standard MIB objects, a write to this object
            will have no effect.  Disconnecting a link by writing to
            this object does not free any resources, it marks the link
            as not connected, so that the link will not cause a level 4
            (LINKDOWN) alarm to be generated."
        ::= { aix1ApplAdminEntry 10 }


          -- the Application Interface Operational table

          aix1ApplOperTable OBJECT-TYPE
              SYNTAX     SEQUENCE OF ApplOperEntry
              ACCESS     not-accessible
              STATUS     mandatory
              DESCRIPTION
                      "The table of operational elements which apply
                      to an individual X.25 link above the packet
                      layer."
              ::= { aiX1Appl 2 }

          aix1ApplOperEntry OBJECT-TYPE
              SYNTAX     ApplOperEntry
              ACCESS     not-accessible
              STATUS     mandatory
              DESCRIPTION
                      "The addressing information for one of this
                      X.25 link's operational objects."
              INDEX      { aix1ApplOperIndex }
              ::= { aix1ApplOperTable 1 }

          ApplOperEntry ::=
              SEQUENCE {
                  aix1ApplOperIndex
                      IfIndexType,
                  aix1ApplOperLinkMode
                      INTEGER,
                  aix1ApplOperXONXOFFProto
                      INTEGER,
                  aix1ApplOperNMAProto
                      INTEGER,
                  aix1ApplOperOPSINEProto
                      INTEGER,
                  aix1ApplOperTL1Proto
                      INTEGER,
                  aix1ApplOperLinkDescription
                      DisplayString,
                  aix1ApplOperLinkConnectionMode
                      INTEGER
              }


    aix1ApplOperIndex OBJECT-TYPE
        SYNTAX     IfIndexType
        ACCESS     read-only
        STATUS     mandatory
        DESCRIPTION
            "The ifIndex value of the packet level associated with
             these application level objects."
        ::= { aix1ApplOperEntry 1 }

    aix1ApplOperLinkMode OBJECT-TYPE
        SYNTAX     INTEGER {
                         normal(1),
                         passive(2)
                        }
        ACCESS     read-only
        STATUS     mandatory
        DESCRIPTION
            "Determines whether link behaves as a normal X.25 link
            or a BX.25-style passive link.  This is the mandatory
            operating value of this attribute.  The most recently
            configured value is available as aix1ApplAdminLinkMode."
        DEFVAL     { normal }
        ::= { aix1ApplOperEntry 2 }

    aix1ApplOperXONXOFFProto OBJECT-TYPE
        SYNTAX     INTEGER {
                         on(1),
                         off(2)
                        }
        ACCESS     read-only
        STATUS     mandatory
        DESCRIPTION
            "Determines whether XON/XOFF protocol processing is in
            effect by default on all virtual circuits on the link."
        ::= { aix1ApplOperEntry 3 }

    aix1ApplOperNMAProto OBJECT-TYPE
        SYNTAX     INTEGER {
                         on(1),
                         off(2)
                        }
        ACCESS     read-only
        STATUS     mandatory
        DESCRIPTION
            "Determines whether NMA protocol processing is in effect
            by default on all virtual circuits on the link."
        ::= { aix1ApplOperEntry 4 }

    aix1ApplOperOPSINEProto OBJECT-TYPE
        SYNTAX     INTEGER {
                         on(1),
                         off(2)
                        }
        ACCESS     read-only
        STATUS     mandatory
        DESCRIPTION
            "Determines whether OPSINE protocol processing is in
            effect by default on all virtual circuits on the link."
        ::= { aix1ApplOperEntry 6 }
    
    aix1ApplOperTL1Proto OBJECT-TYPE
        SYNTAX     INTEGER {
                         on(1),
                         off(2)
                        }
        ACCESS     read-only
        STATUS     mandatory
        DESCRIPTION
            "Determines whether TL1 protocol processing is in effect
            by default on all virtual circuits on the link."
        ::= { aix1ApplOperEntry 7 }

    aix1ApplOperLinkDescription OBJECT-TYPE
        SYNTAX     DisplayString (SIZE (0..50))
        ACCESS     read-only
        STATUS     mandatory
        DESCRIPTION
            "A descriptive string associated with this link.  This
            provides a place for the agent to supply any descriptive
            information about the use or owner of the link.  A zero
            length value indicates that the agent doesn't have any
            additional information."
        ::= { aix1ApplOperEntry 8 }

    aix1ApplOperLinkConnectionMode OBJECT-TYPE
        SYNTAX     INTEGER {
                         connected(1),
                         disconnected(2),
                         reconnected(3),
                         disabled(4),
                         linkdown(5),
                         linkup(6)
                        }
        ACCESS     read-only
        STATUS     mandatory
        DESCRIPTION
            "Determines whether the link is currently disconnected,
            connected or has been reconnected after it was
            disconnected."
        ::= { aix1ApplOperEntry 9 }


          -- the Packet Layer Interface Administrative table

          aix1PktAdminTable OBJECT-TYPE
              SYNTAX     SEQUENCE OF PktAdminEntry
              ACCESS     not-accessible
              STATUS     mandatory
              DESCRIPTION
                      "The table of administrative elements which
                      apply to an individual X.25 link at the packet
                      layer."
              ::= { aiX1Pkt 1 }

          aix1PktAdminEntry OBJECT-TYPE
              SYNTAX     PktAdminEntry
              ACCESS     not-accessible
              STATUS     mandatory
              DESCRIPTION
                      "The addressing information for one of this
                      X.25 link's packet layer administrative objects."
              INDEX      { aix1PktAdminIndex }
              ::= { aix1PktAdminTable 1 }

          PktAdminEntry ::=
              SEQUENCE {
                  aix1PktAdminIndex
                      IfIndexType,
                  aix1PktAdminConformanceMode
                      INTEGER,
                  aix1PktAdminDBit
                      INTEGER,
                  aix1PktAdminQBitMBit
                      INTEGER,
                  aix1PktAdminUseRejectPkts
                      INTEGER,
                  aix1PktAdminSendInitialRestart
                      INTEGER,
                  aix1PktAdminStdsBody
                      INTEGER,
                  aix1PktAdminFacilChecking
                      INTEGER,
                  aix1PktAdminUndefinedFacils
                      INTEGER,
                  aix1PktAdminDefMaxPktSize
                      INTEGER,
                  aix1PktAdminDefWindowSize
                      INTEGER,
                  aix1PktAdminNegMaxPktSize
                      INTEGER,
                  aix1PktAdminNegWindowSize
                      INTEGER,
                  aix1PktAdminPacketizingTimer
                      INTEGER,
                  aix1PktAdminPVCOffset
                      INTEGER,
                  aix1PktAdminSVCOffset
                      INTEGER
              }


    aix1PktAdminIndex OBJECT-TYPE
        SYNTAX     IfIndexType
        ACCESS     read-only
        STATUS     mandatory
        DESCRIPTION
            "The ifIndex value of the packet layer entity associated
            with these objects."
        ::= { aix1PktAdminEntry 1 }

    aix1PktAdminConformanceMode OBJECT-TYPE
        SYNTAX     INTEGER {
                        ccitt(1),
                        ddn(2)
                       }
        ACCESS     read-write
        STATUS     mandatory
        DESCRIPTION
            "The configured conformance testing mode to which X.25's
            behavior will adhere.  This value may not have taken
            effect.  The value with which the SLC is currently operating
            is the value of aix1OperConformanceMode."
        DEFVAL     { ccitt }
        ::= { aix1PktAdminEntry 2 }

    aix1PktAdminDBit OBJECT-TYPE
        SYNTAX     INTEGER {
                         dbitNotAllowed(1),
                         dbitAllowed(2)
                        }
        ACCESS     read-write
        STATUS     mandatory
        DESCRIPTION
            "Determines whether the packet level will allow the D-bit
            in call setup packets."
        DEFVAL     { dbitNotAllowed }
        ::= { aix1PktAdminEntry 3 }

    aix1PktAdminQBitMBit OBJECT-TYPE
        SYNTAX     INTEGER {
                         noQMCheck(1),
                         qmCheck(2)
                        }
        ACCESS     read-write
        STATUS     mandatory
        DESCRIPTION
            "Determines whether the packet level will check for
            consistency in the use of Q and M bits, i. e. that the
            value of the Q-bit is the same in every packet of an M-bit
            sequence."
        DEFVAL     { noQMCheck }
        ::= { aix1PktAdminEntry 4 }

    aix1PktAdminUseRejectPkts OBJECT-TYPE
        SYNTAX     INTEGER {
                         noPktRetrans(1),
                         pktRetrans(2)
                        }
        ACCESS     read-write
        STATUS     mandatory
        DESCRIPTION
            "Enables and disables the use of packet retransmission.
            If the packet level is acting as a DTE it will send a REJ
            packet in response to a data packet received out of
            sequence.  If the packet level is acting as a DCE, it will
            accept a REJ packet and retransmit the requested data
            packet(s)."
        DEFVAL     { noPktRetrans }
        ::= { aix1PktAdminEntry 5 }

    aix1PktAdminSendInitialRestart OBJECT-TYPE
        SYNTAX     INTEGER {
                         initialRestart(1),
                         noInitialRestart(2)
                        }
        ACCESS     read-write
        STATUS     mandatory
        DESCRIPTION
            "Enables and disables sending of an initial restart request
            packet when the link comes up."
        DEFVAL     { initialRestart }
        ::= { aix1PktAdminEntry 6 }

    aix1PktAdminStdsBody OBJECT-TYPE
        SYNTAX     INTEGER {
                         ccittPktLvl(1),
                         isoPktLvl(2)
                        }
        ACCESS     read-write
        STATUS     mandatory
        DESCRIPTION
            "Selects between ISO and CCITT packet level specifications."
        DEFVAL     { ccittPktLvl }
        ::= { aix1PktAdminEntry 7 }

    aix1PktAdminFacilChecking OBJECT-TYPE
        SYNTAX     INTEGER {
                         checkFacils(1),
                         noCheckFacils(2)
                        }
        ACCESS     read-write
        STATUS     mandatory
        DESCRIPTION
            "Enables and disables packet level checking of the
            facilities field of call processing packets for validity."
        DEFVAL     { noCheckFacils }
        ::= { aix1PktAdminEntry 8 }

    aix1PktAdminUndefinedFacils OBJECT-TYPE
        SYNTAX     INTEGER {
                         noUndefFacils(1),
                         undefFacils(2)
                        }
        ACCESS     read-write
        STATUS     mandatory
        DESCRIPTION
            "Enables and disables packet level allowing undefined
            facilities to appear in the facilities field of call
            processing packets."
        DEFVAL     { noUndefFacils }
        ::= { aix1PktAdminEntry 9 }

    aix1PktAdminDefMaxPktSize OBJECT-TYPE
        SYNTAX     INTEGER {
                         pkt128(128),
                         pkt256(256),
                         pkt512(512),
                         pkt1024(1024)
                        }
        ACCESS     read-write
        STATUS     mandatory
        DESCRIPTION
            "The maximum packet size to use for all calls placed on
            this packet layer entity.  If aix1PktAdminNegPktSize is
            set to negotiate(2), this will be the proposed value for
            calls placed on the packet level entitry."
        DEFVAL     { 128 }
        ::= { aix1PktAdminEntry 10 }

    aix1PktAdminDefWindowSize OBJECT-TYPE
        SYNTAX     INTEGER (1..127)
        ACCESS     read-write
        STATUS     mandatory
        DESCRIPTION
            "The maximum packet level window size to use on this PLE.
            If aix1PktAdminNegWindowSize is set to negotiate(2), this
            will be the proposed value for calls placed on the packet
            layer entity."
        DEFVAL     { 2 }
        ::= { aix1PktAdminEntry 11 }

    aix1PktAdminNegMaxPktSize OBJECT-TYPE
        SYNTAX     INTEGER {
                         noNegotiation(1),
                         negotiate(2)
                        }
        ACCESS     read-write
        STATUS     mandatory
        DESCRIPTION
            "Determines whether this PLE will originate calls which
            negotiate packet size."
        DEFVAL     { noNegotiation }
        ::= { aix1PktAdminEntry 12 }

    aix1PktAdminNegWindowSize OBJECT-TYPE
        SYNTAX     INTEGER {
                         noNegotiation(1),
                         negotiate(2)
                        }
        ACCESS     read-write
        STATUS     mandatory
        DESCRIPTION
            "Determines whether this PLE will originate calls which
            negotiate window size."
        DEFVAL     { noNegotiation }
        ::= { aix1PktAdminEntry 13 }

    aix1PktAdminPacketizingTimer OBJECT-TYPE
        SYNTAX     INTEGER (0..255)
        ACCESS     read-write
        STATUS     mandatory
        DESCRIPTION
            "The interval from the time of receipt of the first
            character from the TDM backplane to transmission of a
            block of characters to the X.25 protocol stack for
            transmission in a data packet to the network.  In 100ths
            of a second.  This value is not meaningful on backplane
            connections on which escape framing, TL1 packetizing, or
            programmable forwarding characters are active."
        DEFVAL     { 6 }
        ::= { aix1PktAdminEntry 14 }

    aix1PktAdminPVCOffset OBJECT-TYPE
        SYNTAX     INTEGER(0..4095)
        ACCESS     read-write
        STATUS     mandatory
        DESCRIPTION
            "Specifies an offset that gets added to the PVC logical
            channel range specified by x25AdmnMaxActiveCircuits and 
            x25AdmnNumberPVCs from RFC 1382."
        DEFVAL     { 0 }
        ::= { aix1PktAdminEntry 15 }

    aix1PktAdminSVCOffset OBJECT-TYPE
        SYNTAX     INTEGER(0..4095)
        ACCESS     read-write
        STATUS     mandatory
        DESCRIPTION
            "Specifies an offset that gets added to the SVC logical
            channel range specified by x25AdmnMaxActiveCircuits and
            x25AdmnNumberPVCs from RFC 1382."
        DEFVAL     { 0 }
        ::= { aix1PktAdminEntry 16 }


          -- the Packet Layer Interface Operational table

          aix1PktOperTable OBJECT-TYPE
              SYNTAX     SEQUENCE OF PktOperEntry
              ACCESS     not-accessible
              STATUS     mandatory
              DESCRIPTION
                      "The table of operational elements which apply
                      to an individual X.25 link at the packet
                      layer."
              ::= { aiX1Pkt 2 }

          aix1PktOperEntry OBJECT-TYPE
              SYNTAX     PktOperEntry
              ACCESS     not-accessible
              STATUS     mandatory
              DESCRIPTION
                      "The addressing information for one of this
                      X.25 link's packet layer operational objects."
              INDEX   { aix1PktOperIndex }
              ::= { aix1PktOperTable 1 }

          PktOperEntry ::=
              SEQUENCE {
                  aix1PktOperIndex
                      IfIndexType,
                  aix1PktOperConformanceMode
                      INTEGER,
                  aix1PktOperDBit
                      INTEGER,
                  aix1PktOperQBitMBit
                      INTEGER,
                  aix1PktOperUseRejectPkts
                      INTEGER,
                  aix1PktOperSendInitialRestart
                      INTEGER,
                  aix1PktOperStdsBody
                      INTEGER,
                  aix1PktOperFacilChecking
                      INTEGER,
                  aix1PktOperUndefinedFacils
                      INTEGER,
                  aix1PktOperDefMaxPktSize
                      INTEGER,
                  aix1PktOperDefWindowSize
                      INTEGER,
                  aix1PktOperNegMaxPktSize
                      INTEGER,
                  aix1PktOperNegWindowSize
                      INTEGER,
                  aix1PktOperPacketizingTimer
                      INTEGER,
                  aix1PktOperPVCOffset
                      INTEGER,
                  aix1PktOperSVCOffset
                      INTEGER
              }


    aix1PktOperIndex OBJECT-TYPE
        SYNTAX     IfIndexType
        ACCESS     read-only
        STATUS     mandatory
        DESCRIPTION
            "The ifIndex value of the packet level associated with
            these objects."
        ::= { aix1PktOperEntry 1 }

    aix1PktOperConformanceMode OBJECT-TYPE
        SYNTAX     INTEGER {
                         ccitt(1),
                         ddn(2)
                        }
        ACCESS     read-only
        STATUS     mandatory
        DESCRIPTION
            "The conformance testing mode to which X.25's behavior
            will adhere.  This is the currently operational value."
        DEFVAL     { ccitt }
        ::= { aix1PktOperEntry 2 }

    aix1PktOperDBit OBJECT-TYPE
        SYNTAX     INTEGER {
                         dbitNotAllowed(1),
                         dbitAllowed(2)
                        }
        ACCESS     read-only
        STATUS     mandatory
        DESCRIPTION
            "Determines whether the packet level will allow the D-bit
            in call setup packets."
        DEFVAL     { dbitNotAllowed }
        ::= { aix1PktOperEntry 3 }

    aix1PktOperQBitMBit OBJECT-TYPE
        SYNTAX     INTEGER {
                         noQMCheck(1),
                         qmCheck(2)
                        }
        ACCESS     read-only
        STATUS     mandatory
        DESCRIPTION
            "Determines whether the packet level will check for
            consistency in the use of Q and M bits, i. e. that the
            value of the Q-bit is the same in every packet of an M-bit
            sequence."
        DEFVAL     { noQMCheck }
        ::= { aix1PktOperEntry 4 }

    aix1PktOperUseRejectPkts OBJECT-TYPE
        SYNTAX     INTEGER {
                         noPktRetrans(1),
                         pktRetrans(2)
                        }
        ACCESS     read-only
        STATUS     mandatory
        DESCRIPTION
            "Enables and disables the use of packet retransmission.
            If the packet level is acting as a DTE it will send a REJ 
            packet in response to a data packet received out of
            sequence.  If the packet level is acting as a DCE, it will
            accept a REJ packet and retransmit the requested data
            packet(s)."
        DEFVAL     { noPktRetrans }
        ::= { aix1PktOperEntry 5 }

    aix1PktOperSendInitialRestart OBJECT-TYPE
        SYNTAX     INTEGER {
                         initialRestart(1),
                         noInitialRestart(2)
                        }
        ACCESS     read-only
        STATUS     mandatory
        DESCRIPTION
            "Enables and disables sending of an initial restart
            request packet when the link comes up."
        DEFVAL     { initialRestart }
        ::= { aix1PktOperEntry 6 }

    aix1PktOperStdsBody OBJECT-TYPE
        SYNTAX     INTEGER {
                         ccittPktLvl(1),
                         isoPktLvl(2)
                        }
        ACCESS     read-only
        STATUS     mandatory
        DESCRIPTION
            "Selects between ISO and CCITT packet level specifications."
        DEFVAL     { ccittPktLvl }
        ::= { aix1PktOperEntry 7 }

    aix1PktOperFacilChecking OBJECT-TYPE
        SYNTAX     INTEGER {
                         checkFacils(1),
                         noCheckFacils(2)
                        }
        ACCESS     read-only
        STATUS     mandatory
        DESCRIPTION
            "Enables and disables packet level checking of the
            facilities field of call processing packets for validity."
        DEFVAL     { noCheckFacils }
        ::= { aix1PktOperEntry 8 }

    aix1PktOperUndefinedFacils OBJECT-TYPE
        SYNTAX     INTEGER {
                         noUndefFacils(1),
                         undefFacils(2)
                        }
        ACCESS     read-only
        STATUS     mandatory
        DESCRIPTION
            "Enables and disables packet level allowing undefined
            facilities to appear in the facilities field of call
            processing packets."
        DEFVAL     { noUndefFacils }
        ::= { aix1PktOperEntry 9 }

    aix1PktOperDefMaxPktSize OBJECT-TYPE
        SYNTAX     INTEGER {
                         pkt128(128),
                         pkt256(256),
                         pkt512(512),
                         pkt1024(1024)
                        }
        ACCESS     read-only
        STATUS     mandatory
        DESCRIPTION
            "The maximum packet size to use for all calls placed on
            this packet layer entity.  If aix1PktOperNegPktSize is set
            to negotiate(2), this will be the proposed value for calls
            placed on the packett layer entity."
        DEFVAL     { 128 }
        ::= { aix1PktOperEntry 10 }

    aix1PktOperDefWindowSize OBJECT-TYPE
        SYNTAX     INTEGER (0..127)
        ACCESS     read-only
        STATUS     mandatory
        DESCRIPTION
            "The maximum packet level window size to use for all calls
            placed on this packet layer entity.  If
            aix1PktOperNegWindowSize is set to negotiate(2), this will
            be the proposed value for calls placed on the packet layer
            entity."
        DEFVAL     { 2 }
        ::= { aix1PktOperEntry 11 }

    aix1PktOperNegMaxPktSize OBJECT-TYPE
        SYNTAX     INTEGER {
                         noNegotiation(1),
                         negotiate(2)
                        }
        ACCESS     read-only
        STATUS     mandatory
        DESCRIPTION
            "Determines whether this packet layer entity will originate
            calls which negotiate packet size."
        DEFVAL     { noNegotiation }
        ::= { aix1PktOperEntry 12 }

    aix1PktOperNegWindowSize OBJECT-TYPE
        SYNTAX     INTEGER {
                         noNegotiation(1),
                         negotiate(2)
                        }
        ACCESS     read-only
        STATUS     mandatory
        DESCRIPTION
            "Determines whether this packet layer entity will originate
            calls which negotiate window size."
        DEFVAL     { noNegotiation }
        ::= { aix1PktOperEntry 13 }

    aix1PktOperPacketizingTimer OBJECT-TYPE
        SYNTAX     INTEGER (0..255)
        ACCESS     read-only
        STATUS     mandatory
        DESCRIPTION
            "The interval from the time of receipt of the first
            character from the TDM backplane to transmission of a
            block of characters to the X.25 protocol stack for
            transmission in a data packet to the network.  In 100ths
            of a second.  This value is not meaningful on backplane
            connections on which escape framing, TL1 packetizing, or
            programmable forwarding characters are active."
        DEFVAL     { 6 }
        ::= { aix1PktOperEntry 14 }

    aix1PktOperPVCOffset OBJECT-TYPE
        SYNTAX     INTEGER(0..4095)
        ACCESS     read-only
        STATUS     mandatory
        DESCRIPTION
            "Specifies an offset that gets added to the PVC logical
            channel range specified by x25AdmnMaxActiveCircuits and
            x25AdmnNumberPVCs from RFC 1382."
        DEFVAL     { 0 }
        ::= { aix1PktOperEntry 15 }

    aix1PktOperSVCOffset OBJECT-TYPE
        SYNTAX     INTEGER(0..4095)
        ACCESS     read-only
        STATUS     mandatory
        DESCRIPTION
            "Specifies an offset that gets added to the SVC logical
            channel range specified by x25AdmnMaxActiveCircuits and
            x25AdmnNumberPVCs from RFC 1382."
        DEFVAL     { 0 }
        ::= { aix1PktOperEntry 16 }


          -- the Packet Layer Interface Statistics table

          aix1PktStatTable OBJECT-TYPE
              SYNTAX     SEQUENCE OF PktStatEntry
              ACCESS     not-accessible
              STATUS     mandatory
              DESCRIPTION
                      "The table of statistical elements which apply
                      to an individual X.25 link at the packet layer."
              ::= { aiX1Pkt 3 }

          aix1PktStatEntry OBJECT-TYPE
              SYNTAX     PktStatEntry
              ACCESS     not-accessible
              STATUS     mandatory
              DESCRIPTION
                      "The addressing information for one of this
                      X.25 link's packet layer statistical objects."
              INDEX   { aix1PktStatIndex }
              ::= { aix1PktStatTable 1 }

          PktStatEntry ::=
              SEQUENCE {
                  aix1PktStatIndex
                      IfIndexType,
                  aix1PktStatInCharsPerSec80s
                      Counter32,
                  aix1PktStatOutCharsPerSec80s
                      Counter32
              }


    aix1PktStatIndex OBJECT-TYPE
        SYNTAX     IfIndexType
        ACCESS     read-only
        STATUS     mandatory
        DESCRIPTION
            "The ifIndex value of the packet layer entity associated
            with these objects."
        ::= { aix1PktStatEntry 1 }

    aix1PktStatInCharsPerSec80s OBJECT-TYPE
        SYNTAX     Counter32
        ACCESS     read-only
        STATUS     mandatory
        DESCRIPTION
            "The average number of data characters (characters in the
            data field of X.25 data packets) received from the network
            per second over the last 80 seconds by this packet layer
            entity."
        ::= { aix1PktStatEntry 2 }

    aix1PktStatOutCharsPerSec80s OBJECT-TYPE
        SYNTAX     Counter32
        ACCESS     read-only
        STATUS     mandatory
        DESCRIPTION
            "The average number of data characters (characters in the
            data field of X.25 data packets) transmitted to the network
            per second over the last 80 seconds by this packet layer
            entity."
        ::= { aix1PktStatEntry 3 }


          -- the Frame Layer Interface Administrative table

          aix1FrmAdminTable OBJECT-TYPE
              SYNTAX     SEQUENCE OF FrmAdminEntry
              ACCESS     not-accessible
              STATUS     mandatory
              DESCRIPTION
                      "The table of administrative elements which apply
                      to an individual X.25 link at the frame layer."
              ::= { aiX1Frm 1 }

          aix1FrmAdminEntry OBJECT-TYPE
              SYNTAX     FrmAdminEntry
              ACCESS     not-accessible
              STATUS     mandatory
              DESCRIPTION
                      "The addressing information for one of this X.25
                      link's frame layer administrative objects."
              INDEX   { aix1FrmAdminIndex }
              ::= { aix1FrmAdminTable 1 }

          FrmAdminEntry ::=
              SEQUENCE {
                  aix1FrmAdminIndex
                      IfIndexType,
                  aix1FrmAdminIdleRRs
                      INTEGER,
                  aix1FrmAdminRandomizeT1
                      INTEGER
              }


    aix1FrmAdminIndex OBJECT-TYPE
        SYNTAX     IfIndexType
        ACCESS     read-only
        STATUS     mandatory
        DESCRIPTION
            "The ifIndex value of the frame layer entity associated
            with these objects."
        ::= { aix1FrmAdminEntry 1 }

    aix1FrmAdminIdleRRs OBJECT-TYPE
        SYNTAX     INTEGER {
                         idleRRs(1),
                         noIdleRRs(2)
                        }
        ACCESS     read-write
        STATUS     mandatory
        DESCRIPTION
            "Enables and disables transmission of idle Receive Ready
            frames by the frame layer."
        DEFVAL     { idleRRs }
        ::= { aix1FrmAdminEntry 2 }

    aix1FrmAdminRandomizeT1 OBJECT-TYPE
        SYNTAX     INTEGER {
                         randomT1(1),
                         noRandomT1(2)
                        }
        ACCESS     read-write
        STATUS     mandatory
        DESCRIPTION
            "Enables and disables the introduction of random jitter
            into the frame layer's T1 timer to avoid T1 timer
            synchronization with the remote frame layer."
        DEFVAL     { randomT1 }
        ::= { aix1FrmAdminEntry 3 }


          -- the Frame Layer Interface Operational table

          aix1FrmOperTable OBJECT-TYPE
              SYNTAX     SEQUENCE OF FrmOperEntry
              ACCESS     not-accessible
              STATUS     mandatory
              DESCRIPTION
                  "The table of operational elements which apply to
                  an individual X.25 link at the frame layer."
              ::= { aiX1Frm 2 }

          aix1FrmOperEntry OBJECT-TYPE
              SYNTAX     FrmOperEntry
              ACCESS     not-accessible
              STATUS     mandatory
              DESCRIPTION
                  "The addressing information for one of this X.25
                  link's frame layer operational objects."
              INDEX   { aix1FrmOperIndex }
              ::= { aix1FrmOperTable 1 }

          FrmOperEntry ::=
              SEQUENCE {
                  aix1FrmOperIndex
                      IfIndexType,
                  aix1FrmOperIdleRRs
                      INTEGER,
                  aix1FrmOperRandomizeT1
                      INTEGER
              }


    aix1FrmOperIndex OBJECT-TYPE
        SYNTAX     IfIndexType
        ACCESS     read-only
        STATUS     mandatory
        DESCRIPTION
            "The ifIndex value of the frame level associated with
            these objects."
        ::= { aix1FrmOperEntry 1 }

    aix1FrmOperIdleRRs OBJECT-TYPE
        SYNTAX     INTEGER {
                         idleRRs(1),
                         noIdleRRs(2)
                        }
        ACCESS     read-only
        STATUS     mandatory
        DESCRIPTION
            "Enables and disables transmission of idle Receive Ready
            frames by the frame layer."
        DEFVAL     { idleRRs }
        ::= { aix1FrmOperEntry 2 }
    
    aix1FrmOperRandomizeT1 OBJECT-TYPE
        SYNTAX     INTEGER {
                         randomT1(1),
                         noRandomT1(2)
                        }
        ACCESS     read-only
        STATUS     mandatory
        DESCRIPTION
            "Enables and disables the introduction of random jitter
            into the frame layer's T1 timer to avoid T1 timer
            synchronization with the remote frame layer."
        DEFVAL     { randomT1 }
        ::= { aix1FrmOperEntry 3 }


          -- the Physical Layer Interface Administrative table

          aix1PhysAdminTable OBJECT-TYPE
              SYNTAX     SEQUENCE OF PhysAdminEntry
              ACCESS     not-accessible
              STATUS     mandatory
              DESCRIPTION
                  "The table of administrative elements which apply
                  to an individual X.25 link at the physical layer."
              ::= { aiX1Phys 1 }

          aix1PhysAdminEntry OBJECT-TYPE
              SYNTAX     PhysAdminEntry
              ACCESS     not-accessible
              STATUS     mandatory
              DESCRIPTION
                  "The addressing information for one of this X.25
                  link's physical layer administrative objects."
              INDEX   { aix1PhysAdminIndex }
              ::= { aix1PhysAdminTable 1 }

          PhysAdminEntry ::=
              SEQUENCE {
                  aix1PhysAdminIndex
                      IfIndexType,
                  aix1PhysAdminInterFrameDelayStatus
                      INTEGER,
                  aix1PhysAdminInterFrameDelayInterval
                      INTEGER,
                  aix1PhysAdminT1LineBuildOut
                      INTEGER
              }


    aix1PhysAdminIndex OBJECT-TYPE
        SYNTAX     IfIndexType
        ACCESS     read-only
        STATUS     mandatory
        DESCRIPTION
            "The ifIndex value of the physical port associated with
            these objects."
        ::= { aix1PhysAdminEntry 1 }
    
    aix1PhysAdminInterFrameDelayStatus OBJECT-TYPE
        SYNTAX     INTEGER {
                         ifdDisabled(1),
                         ifdEnabled(2)
                        }
        ACCESS     read-write
        STATUS     mandatory
        DESCRIPTION
            "Enables and disables a delay period between transmitted
            frames."
        DEFVAL     { ifdDisabled }
        ::= { aix1PhysAdminEntry 2 }

    aix1PhysAdminInterFrameDelayInterval OBJECT-TYPE
        SYNTAX     INTEGER(0..'7fffffff'h)
        ACCESS     read-write
        STATUS     mandatory
        DESCRIPTION
            "Sets the interframe delay interval.  This value is
            effective only if aix1PhysAdminInterFrameDelayStatus is
            set to ifdEnabled(2).  This value is expressed in
            microseconds, with 100 microsecond granularity (it's
            truncated to the nearest 100 microseconds)."
        DEFVAL     { 100 }
        ::= { aix1PhysAdminEntry 3 }

    aix1PhysAdminT1LineBuildOut OBJECT-TYPE
        SYNTAX     INTEGER {
                         lbo0to133(1),
                         lbo133to266(2),
                         lbo266to399(3),
                         lbo399to533(4),
                         lbo533to655(5)
                        }
        ACCESS     read-write
        STATUS     mandatory
        DESCRIPTION
            "The T1 line build out value.  The specified syntax
            represents ranges of line length expressed in feet."
        DEFVAL     { lbo133to266 }
        ::= { aix1PhysAdminEntry 4 }


          -- the Physical Layer Interface Operational table

          aix1PhysOperTable OBJECT-TYPE
              SYNTAX     SEQUENCE OF PhysOperEntry
              ACCESS     not-accessible
              STATUS     mandatory
              DESCRIPTION
                  "The table of operational elements which apply
                  to an individual X.25 link at the physical layer."
              ::= { aiX1Phys 2 }

          aix1PhysOperEntry OBJECT-TYPE
              SYNTAX     PhysOperEntry
              ACCESS     not-accessible
              STATUS mandatory
              DESCRIPTION
                  "The addressing information for one of this X.25
                  link's physical layer operational objects."
              INDEX   { aix1PhysOperIndex }
              ::= { aix1PhysOperTable 1 }

          PhysOperEntry ::=
              SEQUENCE {
                  aix1PhysOperIndex
                      IfIndexType,
                  aix1PhysOperInterFrameDelayStatus
                      INTEGER,
                  aix1PhysOperInterFrameDelayInterval
                      INTEGER,
                  aix1PhysOperT1LineBuildOut
                      INTEGER
              }


    aix1PhysOperIndex OBJECT-TYPE
        SYNTAX     IfIndexType
        ACCESS     read-only
        STATUS     mandatory
        DESCRIPTION
            "The ifIndex value of the physical port associated with
            these objects."
        ::= { aix1PhysOperEntry 1 }

    aix1PhysOperInterFrameDelayStatus OBJECT-TYPE
        SYNTAX     INTEGER {
                         ifdDisabled(1),
                         ifdEnabled(2)
                        }
        ACCESS     read-only
        STATUS     mandatory
        DESCRIPTION
            "Enables and disables a delay period between transmitted
            frames."
        DEFVAL     { ifdDisabled }
        ::= { aix1PhysOperEntry 2 }

    aix1PhysOperInterFrameDelayInterval OBJECT-TYPE
        SYNTAX     INTEGER(0.. '7fffffff'h)
        ACCESS     read-only
        STATUS     mandatory
        DESCRIPTION
            "Sets the interframe delay interval.  This value is
            effective only if aix1PhysAdminInterFrameDelayStatus is
            set to ifdEnabled(2).  This value is expressed in
            microseconds, with 100 microsecond granularity (it's
            truncated to the nearest 100 microseconds)."
        DEFVAL     { 100 }
        ::= { aix1PhysOperEntry 3 }

    aix1PhysOperT1LineBuildOut OBJECT-TYPE
        SYNTAX     INTEGER {
                         lbo0to133(1),
                         lbo133to266(2),
                         lbo266to399(3),
                         lbo399to533(4),
                         lbo533to655(5)
                        }
        ACCESS     read-only
        STATUS     mandatory
        DESCRIPTION
            "The T1 line build out value.  The specified syntax
            represents ranges of line length expressed in feet."
        DEFVAL     { lbo133to266 }
        ::= { aix1PhysOperEntry 4 }


          -- the Physical Layer Interface Statistics table

          aix1PhysStatTable OBJECT-TYPE
              SYNTAX     SEQUENCE OF PhysStatEntry
              ACCESS     not-accessible
              STATUS     mandatory
              DESCRIPTION
                  "The table of statistical elements which apply
                  to an individual X.25 link at the physical layer."
              ::= { aiX1Phys 3 }

          aix1PhysStatEntry OBJECT-TYPE
              SYNTAX     PhysStatEntry
              ACCESS     not-accessible
              STATUS     mandatory
              DESCRIPTION
                  "The addressing information for one of this X.25
                  link's physical layer statistical objects."
              INDEX   { aix1PhysStatIndex }
              ::= { aix1PhysStatTable 1 }

          PhysStatEntry ::=
              SEQUENCE {
                  aix1PhysStatIndex
                      IfIndexType,
                  aix1PhysStatTxAborts
                      Counter32
              }


    aix1PhysStatIndex OBJECT-TYPE
        SYNTAX     IfIndexType
        ACCESS     read-only
        STATUS     mandatory
        DESCRIPTION
            "The ifIndex value of the physical port associated with
            these objects."
        ::= { aix1PhysStatEntry 1 }

    aix1PhysStatTxAborts OBJECT-TYPE
        SYNTAX     Counter32
        ACCESS     read-only
        STATUS     mandatory
        DESCRIPTION
            "The number of abort sequences transmitted on the serial
            interfaces.  This is a proprietary object because the
            RS232-like MIB (RFC 1659) doesn't define a similar object!
            RFC 1659 defines a counter for receive aborts, but not
            transmit aborts."
        ::= { aix1PhysStatEntry 2 }


          -- the Virtual Connection Circuit table

          aix1CircuitTable OBJECT-TYPE
              SYNTAX     SEQUENCE OF CircuitEntry
              ACCESS     not-accessible
              STATUS     mandatory
              DESCRIPTION
                  "The table of objects which maps logical channel
                  number and packet level ifIndex number to  Virtual
                  Connection(VC) number."
              ::= { aiX1VC 1 }

          aix1CircuitEntry OBJECT-TYPE
              SYNTAX     CircuitEntry
              ACCESS     not-accessible
              STATUS     mandatory
              DESCRIPTION
                  "The addressing information for the VC Circuit table."
              INDEX   { aix1CircuitLinkId,aix1CircuitChannelNumber }
              ::= { aix1CircuitTable 1 }

          CircuitEntry ::=
              SEQUENCE {
                  aix1CircuitLinkId
                      IfIndexType,
                  aix1CircuitChannelNumber
                      INTEGER,
                  aix1CircuitState
                      INTEGER,
                  aix1CircuitConType
                      INTEGER,
                  aix1CircuitBCNumber
                      INTEGER,
                  aix1CircuitUserData
                      DisplayString,
                  aix1CircuitRemoteBasePort
                      INTEGER,
                  aix1CircuitRemoteVCNumber
                      INTEGER,
                  aix1CircuitPktsSent
                      Counter32,
                  aix1CircuitPktsRcvd
                      Counter32,
                  aix1CircuitOperPVCType
                      INTEGER,
                  aix1CircuitOperPVCTimer
                      INTEGER
              }

 
    aix1CircuitLinkId OBJECT-TYPE
        SYNTAX     IfIndexType
        ACCESS     read-only
        STATUS     mandatory
        DESCRIPTION
            "The ifindex value of the packet layer entity."
        ::= { aix1CircuitEntry 1 }

    aix1CircuitChannelNumber OBJECT-TYPE
        SYNTAX     INTEGER (0..4095)
        ACCESS     read-only
        STATUS     mandatory
        DESCRIPTION
            "X.25 logical channel number."
        ::= { aix1CircuitEntry 2 }

    aix1CircuitState OBJECT-TYPE
        SYNTAX     INTEGER {
                         idle(1),
                         active(2),
                         csCall(3),
                         csDisco(4),
                         csCancel(5),
                         csReject(6),
                         csCol(7),
                         csUncol(8),
                         npCall(9),
                         npDisco(10),
                         npCancel(11),
                         npReject(12),
                         npCol(13),
                         npUncol(14),
                         trapped(15),
                         csSuspend(16)
                        }
        ACCESS     read-only
        STATUS     mandatory
        DESCRIPTION
            "The call processing state of the local Virtual Connection.
            This is not a standard packet level state.  This is the
            call processing state of the AI version 7 system firmware
            that mediates between the X.25 protocol stack and AISwitch
            internal connection mechanisms."
        ::= { aix1CircuitEntry 3 }

    aix1CircuitConType OBJECT-TYPE
        SYNTAX     INTEGER {
                         lmux(1),
                         rmux(2),
                         debug(5),
                         background(6),
                         pvc(11),
                         svc(12)
                        }
        ACCESS     read-only
        STATUS     mandatory
        DESCRIPTION
            "The type of connection currently supported by the VC."
        ::= { aix1CircuitEntry 4 }

    aix1CircuitBCNumber OBJECT-TYPE
        SYNTAX     INTEGER (0..31)
        ACCESS     read-only
        STATUS     mandatory
        DESCRIPTION
            "The number of the Bus Connection with which this VC is
            associated."
        ::= { aix1CircuitEntry 5 }

    aix1CircuitUserData OBJECT-TYPE
        SYNTAX     DisplayString (SIZE (0..16))
        ACCESS     read-only
        STATUS     mandatory
        DESCRIPTION
            "The user data that was sent or received in the call
            request."
        ::= { aix1CircuitEntry 6 }

    aix1CircuitRemoteBasePort OBJECT-TYPE
        SYNTAX     INTEGER (-1..256)
        ACCESS     read-only
        STATUS     mandatory
        DESCRIPTION
            "The baseport of the card to which the SLC is connected
            across the backplane.  This value is meaningful only when
            this VC is multiplexed to the other SLC.  If not, the value
            returned is -1."
        ::= { aix1CircuitEntry 7 }

    aix1CircuitRemoteVCNumber OBJECT-TYPE
        SYNTAX     INTEGER(0..'ffff'h)
        ACCESS     read-only
        STATUS     mandatory
        DESCRIPTION
            "The Virtual Connection number of the VC on the remote SLC
            to which this VC is connected.  This value is meaningful
            only on multiplexed VCs."
        ::= { aix1CircuitEntry 8 }

    aix1CircuitPktsSent OBJECT-TYPE
        SYNTAX     Counter32
        ACCESS     read-only
        STATUS     mandatory
        DESCRIPTION
            "The number of packets sent to the packet level by the AI
            version 7 system software.  This counts all kinds of packets,
            not just data packets."
        ::= { aix1CircuitEntry 9 }

    aix1CircuitPktsRcvd OBJECT-TYPE
        SYNTAX     Counter32
        ACCESS     read-only
        STATUS     mandatory
        DESCRIPTION
            "The number of packets received from the packet level by the
            AI version 7 system software.  This counts all kinds of
            packets, not just data packets."
        ::= { aix1CircuitEntry 10 }

    aix1CircuitOperPVCType OBJECT-TYPE
        SYNTAX     INTEGER {
                         none(1),
                         active (2),
                         connectOnActivity(3),
                         passive (4)
                        }
        ACCESS     read-write
        STATUS     mandatory
        DESCRIPTION
            "Defines the relationship between a PVC and the 
            connection-oriented AISwitch TDM backplane.  The three types
            represented are defined as follows:
              Active:  initiates connections across the backplane at an
                       interval defined by the timer.
              Passive: waits to respond to a connection attempt across
                       the backplane.  Uses timer to wait for reset
                       confirm from network.  Accepts backplane
                       connection if it receives reset confirmation in
                       time.
              Connect on Activity:
                       initiates connection across backplane upon the
                       receipt of data from the network.  Forwards
                       received data once connection is established.
                       Disconnects backplane connection if a timer
                       interval passes with no data activity in either
                       direction.

            This object will return the value none(1) if the value of
            aix1CircuitConType for this VC is not pvc(11).

            This object reflects the current operational value of this
            parameter.  Note that unlike most operational objects, it is
            writable.  If the value of this object is changed, it modifies
            the current behavior of the board, but is not saved in
            nonvolatile memory."
        DEFVAL     { active }
        ::= { aix1CircuitEntry 11 }

    aix1CircuitOperPVCTimer OBJECT-TYPE
        SYNTAX     INTEGER(0..600)
        ACCESS     read-write
        STATUS     mandatory
        DESCRIPTION
            "Defines the timer interval, in seconds used to manage the
            PVC's relationship with an internal backplane connection.
            The timer is used for different purposes depending on the
            value of aix1VCPVCType as described above.

            This object will return the value 0 if the VC in question
            is not associated with a PVC.

            This object reflects the current operational value of this
            parameter.  Note that unlike most operational objects, it is
            writable. If the value of this object is changed, it modifies
            the current behavior of the board, but is not saved in
            nonvolatile memory."
        DEFVAL     { 15 }
        ::= { aix1CircuitEntry 12 }


        -- the Virtual Connection table

          aix1VCTable OBJECT-TYPE
              SYNTAX     SEQUENCE OF VCEntry
              ACCESS     not-accessible
              STATUS     mandatory
              DESCRIPTION
                  "The table of objects containing information pertaining
                  to Virtual Connections(VC)."
              ::= { aiX1VC 2 }

          aix1VCEntry OBJECT-TYPE
              SYNTAX     VCEntry
              ACCESS     not-accessible
              STATUS     mandatory
              DESCRIPTION
                      "The addressing information for the VC table."
              INDEX   { aix1VCVCNumber }
              ::= { aix1VCTable 1 }

          VCEntry ::=
              SEQUENCE {
                  aix1VCVCNumber
                      INTEGER(0..287),
                  aix1VCState
                      INTEGER,
                  aix1VCConType
                      INTEGER,
                  aix1VCBCNumber
                      INTEGER,
                  aix1VCUserData
                      DisplayString,
                  aix1VCRemoteBasePort
                      INTEGER,
                  aix1VCRemoteVCNumber
                      INTEGER,
                  aix1VCPktsSent
                      Counter32,
                  aix1VCPktsRcvd
                      Counter32,
                  aix1VCOperPVCType
                      INTEGER,
                  aix1VCOperPVCTimer
                      INTEGER
              }


    aix1VCVCNumber OBJECT-TYPE
        SYNTAX     INTEGER (0..287)
        ACCESS     read-only
        STATUS     mandatory
        DESCRIPTION
            "The local Virtual Connection number."
        ::= { aix1VCEntry 1 }

    aix1VCState OBJECT-TYPE
        SYNTAX     INTEGER {
                         idle(1),
                         active(2),
                         csCall(3),
                         csDisco(4),
                         csCancel(5),
                         csReject(6),
                         csCol(7),
                         csUncol(8),
                         npCall(9),
                         npDisco(10),
                         npCancel(11),
                         npReject(12),
                         npCol(13),
                         npUncol(14),
                         trapped(15),
                         csSuspend(16)
                        }
        ACCESS     read-only
        STATUS     mandatory
        DESCRIPTION
            "The call processing state of the local Virtual Connection.
            This is not a standard packet level state.  This is the call
            call processing state of the AI version 7 system firmware
            that mediates between the X.25 protocol stack and AISwitch
            internal connection mechanisms."
        ::= { aix1VCEntry 2 }

    aix1VCConType OBJECT-TYPE
        SYNTAX     INTEGER {
                         lmux(1),
                         rmux(2),
                         debug(5),
                         background(6),
                         pvc(11),
                         svc(12)
                        }
        ACCESS     read-only
        STATUS     mandatory
        DESCRIPTION
            "The type of connection currently supported by the VC."
        ::= { aix1VCEntry 3 }

    aix1VCBCNumber OBJECT-TYPE
        SYNTAX     INTEGER (0..31)
        ACCESS     read-only
        STATUS     mandatory
        DESCRIPTION
            "The number of the Bus Connection with which this VC is
            associated."
        ::= { aix1VCEntry 4 }

    aix1VCUserData OBJECT-TYPE
        SYNTAX     DisplayString (SIZE (0..16))
        ACCESS     read-only
        STATUS     mandatory
    DESCRIPTION
            "The user data that was sent or received in the call request."
        ::= { aix1VCEntry 5 }

    aix1VCRemoteBasePort OBJECT-TYPE
        SYNTAX     INTEGER (-1..256)
        ACCESS     read-only
        STATUS     mandatory
        DESCRIPTION
            "The baseport of the card to which the SLC is connected
            across the backplane.  This value is meaningful only when
            this VC is multiplexed to the other SLC.  If not, the value
            returned is -1."
        ::= { aix1VCEntry 6 }

    aix1VCRemoteVCNumber OBJECT-TYPE
        SYNTAX     INTEGER(0..'ffff'h)
        ACCESS     read-only
        STATUS     mandatory
        DESCRIPTION
            "The Virtual Connection number of the VC on the remote SLC
            to which this VC is connected.  This value is meaningful
            only on multiplexed VCs."
        ::= { aix1VCEntry 7 }

    aix1VCPktsSent OBJECT-TYPE
        SYNTAX     Counter32
        ACCESS     read-only
        STATUS     mandatory
        DESCRIPTION
            "The number of packets sent to the packet level by the AI
            version 7 system software.  This counts all kinds of packets,
            not just data packets."
        ::= { aix1VCEntry 8 }

    aix1VCPktsRcvd OBJECT-TYPE
        SYNTAX     Counter32
        ACCESS     read-only
        STATUS     mandatory
        DESCRIPTION
            "The number of packets received from the packet level by
            the AI version 7 system software.  This counts all kinds
            of packets, not just data packets."
        ::= { aix1VCEntry 9 }

    aix1VCOperPVCType OBJECT-TYPE
        SYNTAX     INTEGER {
                         none(1),
                         active(2),
                         connectOnActivity(3),
                         passive(4)
                        }
        ACCESS     read-write
        STATUS     mandatory
        DESCRIPTION
            "Defines the relationship between a PVC and the 
            connection-oriented AISwitch TDM backplane.  The three
            types represented are defined as follows:
              Active:  initiates connections across the backplane at
                       an interval defined by the timer.
              Passive: waits to respond to a connection attempt across
                       the backplane.  Uses timer to wait for reset
                       confirm from network.  Accepts backplane
                       connection if it receives reset confirmation in
                       time.
              Connect on Activity:
                       initiates connection across backplane upon
                       receipt of data from network.  Forwards received
                       data once connection is established.  Disconnects
                       backplane connection if a timer interval passes
                       with no data activity in either direction.

            This object will return the value none(1) if the value of
            aix1VCConType for this VC is not pvc(11).

            This object reflects the current operational value of this
            parameter.  Note that unlike most operational objects, it is
            writable.  If the value of this object is changed, it
            modifies the current behavior of the board, but is not saved
            in nonvolatile memory."
        DEFVAL     { active }
        ::= { aix1VCEntry 10 }

    aix1VCOperPVCTimer OBJECT-TYPE
        SYNTAX     INTEGER(0..600)
        ACCESS     read-write
        STATUS     mandatory
        DESCRIPTION
            "Defines the timer interval, in seconds used to manage the
            PVC's relationship with an internal backplane connection.
            The timer is used for different purposes depending on the
            value of aix1VCPVCType as described above.

            This object will return the value 0 if the VC in question
            question is not associated with a PVC.

            This object reflects the current operational value of this
            parameter.  Note that unlike most operational objects, it is
            writable.  If the value of this object is changed, it
            modifies the current behavior of the board, but is not saved
            in nonvolatile memory."
        DEFVAL     { 15 }
        ::= { aix1VCEntry 11 }


          -- the PVC Admin table

          aix1AdminPVCTable OBJECT-TYPE
              SYNTAX     SEQUENCE OF AdminPVCEntry
              ACCESS     not-accessible
              STATUS     mandatory
              DESCRIPTION
                  "The table of objects which control attributes of PVCs
                  configured, but not necessarily in effect."
              ::= { aiX1VC 3 }

          aix1AdminPVCEntry OBJECT-TYPE
              SYNTAX     AdminPVCEntry
              ACCESS     not-accessible
              STATUS     mandatory
              DESCRIPTION
                  "The addressing information for the PVC Admin table."
              INDEX   { aix1AdminPVCLinkId,aix1AdminPVCChannelNumber }
              ::= { aix1AdminPVCTable 1 }

          AdminPVCEntry ::=
              SEQUENCE {
                  aix1AdminPVCLinkId
                      IfIndexType,
                  aix1AdminPVCChannelNumber
                      INTEGER,
                  aix1AdminPVCType
                      INTEGER,
                  aix1AdminPVCTimer
                      INTEGER
              }


    aix1AdminPVCLinkId OBJECT-TYPE
        SYNTAX     IfIndexType
        ACCESS     read-only
        STATUS     mandatory
        DESCRIPTION
            "The ifindex value of the packet layer entity."
        ::= { aix1AdminPVCEntry 1 }

    aix1AdminPVCChannelNumber OBJECT-TYPE
        SYNTAX     INTEGER (0..4095)
        ACCESS     read-only
        STATUS     mandatory
        DESCRIPTION
            "X.25 logical channel number."
        ::= { aix1AdminPVCEntry 2 }

    aix1AdminPVCType OBJECT-TYPE
        SYNTAX     INTEGER {
                         none(1),
                         active(2),
                         connectOnActivity(3),
                         passive(4)
                        }
        ACCESS     read-write
        STATUS     mandatory
        DESCRIPTION
            "Defines the relationship between a PVC and the
            connection-oriented AISwitch TDM backplane.  The three
            types represent are defined as follows:
              Active:  initiates connections across the backplane at
                       an interval defined by the timer.
              Passive: waits to respond to a connection attempt across
                       the backplane.  Uses timer to wait for reset
                       confirm from network.  Accepts the backplane
                       connection if it receives reset confirmation in
                       time.
              Connect on Activity:
                       initiates connection across backplane upon
                       receipt of data from network.  Forwards received
                       data once connection is established.  Disconnects
                       backplane connection if a timer interval passes
                       with no data activity in either direction.

            This object will return the value none(1) if
            aix1AdminPVCChannelNumber doesn't correspond to a channel in
            the range specified by the combination of x25admnNumberPVCs
            and aix1PktAdminPVCOffset for the link specified by
            aix1AdminPVCLinkID.

            This object is settable, but does not reflect the mandatory
            operational value of this parameter."
        DEFVAL     { active }
        ::= { aix1AdminPVCEntry 3 }

    aix1AdminPVCTimer OBJECT-TYPE
        SYNTAX     INTEGER(0..600)
        ACCESS     read-write
        STATUS     mandatory
        DESCRIPTION
            "Defines the timer interval, in seconds used to manage the
            PVC's relationship with an internal backplane connection.
            The timer is used for different purposes depending on the
            value of aix1VCPVCType as described above.

            This object will return the value 0 if
            aix1AdminPVCChannelNumber doesn't correspond to a channel in
            the range specified by the combination of x25admnNumberPVCs
            and aix1PktAdminPVCOffset for the link specified by
            aix1AdminPVCLinkID.

            This object is settable, but does not reflect the mandatory
            operational value of this parameter."
        DEFVAL     { 15 }
        ::= { aix1AdminPVCEntry 4 }

END
