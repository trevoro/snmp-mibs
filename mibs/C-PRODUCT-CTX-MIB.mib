C-PRODUCT-CTX-MIB DEFINITIONS ::= BEGIN

-- Abstract
--
--    This memo defines a portion of the Management Information
--    Base (MIB) for managing objects for AB9300 CTX interface card.  
--

IMPORTS
    ctx                  FROM C-PRODUCT-GROUP-MIB
    TimeAndDate,
    cardSlot,
    vcpSideId            FROM C-PRODUCT-BASE-MIB
    Counter              FROM RFC1155-SMI
    OBJECT-TYPE          FROM RFC-1212;

-- CTX groups

ctxCardConfig     OBJECT IDENTIFIER ::= { ctx 1 }
ctxATMStats       OBJECT IDENTIFIER ::= { ctx 2 }

ctxCardBuffer     OBJECT IDENTIFIER ::= { ctxCardConfig 1 }
ctxCardShapers    OBJECT IDENTIFIER ::= { ctxCardConfig 2 }
ctxCard           OBJECT IDENTIFIER ::= { ctxCardConfig 3 }


-- CTX Card Buffer Group (ctxCardBuffer)

ctxCardBufferTable OBJECT-TYPE
    SYNTAX SEQUENCE OF CtxCardBufferEntry
    ACCESS not-accessible
    STATUS mandatory
    DESCRIPTION
            "This object contains the CTX Queue Buffer information table.
             There are one ctxCardBufferEntry associated for each CTX Queue.
             Within the shelf, there are 16 queue buffers.  The table uses
             the slot number and queue number as an index associated with
             each queue buffer.
           "
    ::= { ctxCardBuffer 1 }

ctxCardBufferEntry OBJECT-TYPE
    SYNTAX CtxCardBufferEntry
    ACCESS not-accessible
    STATUS mandatory
    DESCRIPTION
            "Information about a CTX Buffer information."
    INDEX { cardSlot, ctxCardBufferIndex }
    ::= { ctxCardBufferTable 1 }

CtxCardBufferEntry ::=
    SEQUENCE {
        ctxCardBufferIndex
            INTEGER,
        ctxCardInterface 
            OCTET STRING,
        ctxCardBufferCells
            INTEGER,
        ctxCardCongOn
            INTEGER,
        ctxCardCongOff
            INTEGER
    }


ctxCardBufferIndex OBJECT-TYPE
    SYNTAX  INTEGER (1..16)
    ACCESS  not-accessible
    STATUS  mandatory
    DESCRIPTION
            "Queue Index "
    ::= { ctxCardBufferEntry 1 }

ctxCardInterface OBJECT-TYPE
    SYNTAX  OCTET STRING (SIZE(1..80)) 
    ACCESS read-only
    STATUS mandatory
    DESCRIPTION
            "This object describes the Description of the queue. The queue
             Description is combined with slot, Card Interface, high/low 
             priority queue. For example:

                Slot    Interface  Queue
                 3      IMA Grp 1  0 CBR
                 3      IMA Grp 1  1 VBR
                 3      IMA Grp 1  2 UBR1
                         ...
                 (SAR ports)       1 low 
                 8      (none)     0 high
                 8      (none)     1 low
           "
    ::= { ctxCardBufferEntry 2 }

ctxCardBufferCells OBJECT-TYPE
    SYNTAX INTEGER (512..65280)
    ACCESS read-write
    STATUS mandatory
    DESCRIPTION
            "This object indicates the buffer cells configured to a 
             specified card interface. The integer value contains
             between 512 and 65280.  The unit of Buffer Cells
             is in number of cells.  
            "
    DEFVAL { 512 }
    ::= { ctxCardBufferEntry 3 }

ctxCardCongOn OBJECT-TYPE
    SYNTAX INTEGER (0..100) 
    ACCESS read-write
    STATUS mandatory
    DESCRIPTION
            "This object indicates the percentage of Congestion ON
             configured to a specified card interface. The integer
             value contains 0-100 percentage. 
            "
    DEFVAL { 0 }
    ::= { ctxCardBufferEntry 4 }

ctxCardCongOff OBJECT-TYPE
    SYNTAX INTEGER (0..100)
    ACCESS read-write
    STATUS mandatory
    DESCRIPTION
            "This object indicates the percentage of Congestion OFF
             configured to a specified card interface. The integer
             value contains 0-100 percentage. 
            "
    DEFVAL { 0 }
    ::= { ctxCardBufferEntry 5 }

-- CTX Buffer Sharper Group (ctxCardShapers)


ctxCardShapersTable OBJECT-TYPE
    SYNTAX SEQUENCE OF CtxCardShapersEntry
    ACCESS not-accessible
    STATUS mandatory
    DESCRIPTION
            "This object contains the CTX Traffic Shaper information 
             table.  There are one ctxCardShapersEntry associated 
             for each Traffic Shaper.  Within the shelf, there are
             total of seven Traffic Shapers.  The table uses the
             slot number and shaper Index as an index associated
             for each Traffic shaper.
           "
    ::= { ctxCardShapers 1 }

ctxCardShapersEntry OBJECT-TYPE
    SYNTAX CtxCardShapersEntry
    ACCESS not-accessible
    STATUS mandatory
    DESCRIPTION
            "Information about a CTX Shaper information."
    INDEX { cardSlot, ctxCardShapersIndex }
    ::= { ctxCardShapersTable 1 }

CtxCardShapersEntry ::=
    SEQUENCE {
        ctxCardShapersIndex
            INTEGER,
        ctxCardShapersDesc
            OCTET STRING,
        ctxCardShapersRate
            INTEGER
    }

ctxCardShapersIndex OBJECT-TYPE
    SYNTAX  INTEGER (1..7) 
    ACCESS  not-accessible
    STATUS  mandatory
    DESCRIPTION
            "The Index is associated with Traffic shaper.
            "
    ::= { ctxCardShapersEntry 1 }

ctxCardShapersDesc OBJECT-TYPE
    SYNTAX  OCTET STRING (SIZE(1..80)) 
    ACCESS read-only
    STATUS mandatory
    DESCRIPTION
            "This object describes the Description of the Traffic
             shaper.  For example:
                Trunk Bulk
                Trk Grp 1 (VBR HI)
                Trk Grp 1 (VBR LO)
                Trk Grp 1 (UBR)
                SAR Output
                SAR Input
                OC3 Bulk
           "
    ::= { ctxCardShapersEntry 2 }

ctxCardShapersRate OBJECT-TYPE
    SYNTAX  INTEGER (150..390625)
    ACCESS  read-write
    STATUS  mandatory
    DESCRIPTION
            "This object contains the Traffic Shapers Rate.
             The integer value contains between 150 and 390625
             for Trunk Bulk, Trk Grp and OC3 Bulk.  The max
             Shaper rate for SAR Output/Input is 78125.  The
             unit of Shapers Rate is in cells per seconds.
            "
    ::= { ctxCardShapersEntry 3 }

-- CTX Card Group (ctxCard)

ctxCardTable OBJECT-TYPE
    SYNTAX SEQUENCE OF CtxCardEntry
    ACCESS not-accessible
    STATUS mandatory
    DESCRIPTION
            "This object contains the CTX card information table.
             There are one ctxCardEntry associated for each CTX card.
           "
    ::= { ctxCard 1 }

ctxCardEntry OBJECT-TYPE
    SYNTAX CtxCardEntry
    ACCESS not-accessible
    STATUS mandatory
    DESCRIPTION
            "Information about a CTX Card information."
    INDEX { cardSlot }
    ::= { ctxCardTable 1 }

CtxCardEntry ::=
    SEQUENCE {
        ctxCardReset
            INTEGER
    }

ctxCardReset OBJECT-TYPE
    SYNTAX  INTEGER { reset(1) }
    ACCESS  read-write
    STATUS  mandatory
    DESCRIPTION
            "This object indicates the action to be changed CTX
             buffer by a reset CTX card. It will cause cell loss
	     on all Virtual Circuits for 10ms. A read request always
             return zero.
            "
    DEFVAL { reset }
    ::= { ctxCardEntry 1 }

-- CTX ATM Statistics Group (ctxATMStats)

ctxATMStatsTable OBJECT-TYPE
    SYNTAX SEQUENCE OF CbrATMStatsEntry
    ACCESS not-accessible
    STATUS mandatory
    DESCRIPTION
            "This object contains the CTX specific VC Statistics table.
             There is one ctxATMStatsEntry associated for each CTX VC 
             connection provisioned within the shelf.  This table uses 
             vcpSideId as an index which is defined in the vcBaseTable
	     of the C-PRODUCT BASE MIB. This index value uniquely 
	     identifies the CTX VC connection to which this entry
	     is applicable.
        "
    ::= { ctxATMStats 1 }

ctxATMStatsEntry OBJECT-TYPE
    SYNTAX CbrATMStatsEntry
    ACCESS not-accessible
    STATUS mandatory
    DESCRIPTION
         "An entry in the CTX specific VC Statistics table."
    INDEX { vcpSideId }
    ::= { ctxATMStatsTable 1 }

CbrATMStatsEntry ::=
    SEQUENCE {
      ctxATMStatsRxCells
          Counter,
      ctxATMStatsTxCells
          Counter,
      ctxATMStatsResetStats
          INTEGER,
      ctxATMStatsResetTimeDate
          TimeAndDate
    }

ctxATMStatsRxCells OBJECT-TYPE
    SYNTAX Counter
    ACCESS read-only
    STATUS mandatory
    DESCRIPTION
         "This object indicates the total number of ATM cells received
          over the CTX ATM VC connection since the last ATM VC clear
          time and date."
    ::= { ctxATMStatsEntry 1 }

ctxATMStatsTxCells OBJECT-TYPE
    SYNTAX Counter
    ACCESS read-only
    STATUS mandatory
    DESCRIPTION
         "This object indicates the total number of ATM cells transmitted
          over the CTX ATM VC connection since the last ATM VC clear
          time and date."
    ::= { ctxATMStatsEntry 2 }

ctxATMStatsResetStats OBJECT-TYPE
    SYNTAX INTEGER {
           reset (1),
           not-applicable (2)
    }
    ACCESS read-write
    STATUS mandatory
    DESCRIPTION
         "This object will (1) clear the ATM statistics counters and (2)
          initialize the reset time and date to the current time and date
          for the specified ATM VC connection.  NOTE:  A value of '2' is
          returned for any attempted reads of this object." 
    ::= { ctxATMStatsEntry 3 }

ctxATMStatsResetTimeDate OBJECT-TYPE
    SYNTAX TimeAndDate
    ACCESS read-only
    STATUS mandatory
    DESCRIPTION
         "This object indicates the last time and date the ATM statistics
          were cleared for the specified ATM VC connection."
    ::= { ctxATMStatsEntry 4 }
END
