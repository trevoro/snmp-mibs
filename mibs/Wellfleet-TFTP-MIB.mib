Wellfleet-TFTP-MIB DEFINITIONS ::= BEGIN

-- Created by mdl2asn version 3.1
-- Creation date: Wed Aug 30 16:49:29 EDT 1995


    IMPORTS

      Counter
        FROM RFC1155-SMI
      OBJECT-TYPE
        FROM RFC-1212
      wfInternet
        FROM Wellfleet-COMMON-MIB;


    wfTftp		OBJECT IDENTIFIER ::= { wfInternet 6 }

    wfTftpDisable OBJECT-TYPE
        SYNTAX	INTEGER {
    		    enabled(1),
    		    disabled(2)
    		}
        ACCESS	read-write
        STATUS	mandatory
        DESCRIPTION
                "Enables or Disables TFTP Subsystem"
        DEFVAL	{ enabled }
        ::= { wfTftp 1 }

    wfTftpDefaultVolume OBJECT-TYPE
        SYNTAX	INTEGER {
    		    volume1(1),
    		    volume2(2),
    		    volume3(3),
    		    volume4(4),
    		    volume5(5),
    		    volume6(6),
                    volume7(7),
    		    volume8(8),
    		    volume9(9),
    		    volume10(10),
    		    volume11(11),
    		    volume12(12),
    		    volume13(13),
    		    volume14(14),
                    volumea(65),
                    volume1a(100),
                    volume1b(101),
                    volume2a(200),
                    volume2b(201),
                    volume3a(300),
                    volume3b(301),
                    volume4a(400),
                    volume4b(401),
                    volume5a(500),
                    volume5b(501),
                    volume6a(600),
                    volume6b(601),
                    volume7a(700),
                    volume7b(701),
                    volume8a(800),
                    volume8b(801),
                    volume9a(900),
                    volume9b(901),
                    volume10a(1000),
                    volume10b(1001),
                    volume11a(1100),
                    volume11b(1101),
                    volume12a(1200),
                    volume12b(1201),
                    volume13a(1300),
                    volume13b(1301),
                    volume14a(1400),
                    volume14b(1401)
                }
        ACCESS	read-write
        STATUS	mandatory
        DESCRIPTION
                "The file system volume number to which transferred files will
                be written and from which they will be retrieved. The volume
                number corresponds to the slot number on which the volume
                resides. On systems with a floppy disk, the value 65 represents
                volume 'A'.  On systems which support flash file system 
                partitioning, the volume is = (slot * 100 + partition number)
                where 0 and 1 are valid partition numbers, and represent 
                'partition a' and 'partition b' respectively.
                If no default volume is specified, the system chooses the 
                lowest available active volume."
        DEFVAL	{ volume2 }
        ::= { wfTftp 2 }

    wfTftpXfers OBJECT-TYPE
        SYNTAX	Counter
        ACCESS	read-only
        STATUS	mandatory
        DESCRIPTION
                "Number of Transfers in Progress"
        ::= { wfTftp 3 }

    wfTftpTimeOut OBJECT-TYPE
        SYNTAX	INTEGER(1..60)
        ACCESS	read-write
        STATUS	mandatory
        DESCRIPTION
                "General Retransmission time-out value (seconds)"
        DEFVAL	{ 5 }
        ::= { wfTftp 4 }

    wfTftpCloseTimeOut OBJECT-TYPE
        SYNTAX	INTEGER(1..300)
        ACCESS	read-write
        STATUS	mandatory
        DESCRIPTION
                "Retransmission time-out value for sender of final ACK (seconds)"
        DEFVAL	{ 25 }
        ::= { wfTftp 5 }

    wfTftpRexmit OBJECT-TYPE
        SYNTAX	INTEGER(0..10)
        ACCESS	read-write
        STATUS	mandatory
        DESCRIPTION
                "Maximum Number of Retransmissions"
        DEFVAL	{ 5 }
        ::= { wfTftp 6 }

    wfTftpIpTos OBJECT-TYPE
        SYNTAX	INTEGER {
    		    normal(1),
    		    lowdelay(2)
    		}
        ACCESS	read-write
        STATUS	obsolete
        DESCRIPTION
                "The Type Of Service value set in the IP
                datagram specifies to the Internet transport
                layer how the datagram should be handled.
                For TFTP packet transfers low delay
                is preferred"
        DEFVAL	{ lowdelay }
        ::= { wfTftp 7 }

    wfTftpInFiles OBJECT-TYPE
        SYNTAX	Counter
        ACCESS	read-only
        STATUS	mandatory
        DESCRIPTION
                "Number of files Successfully received"
        ::= { wfTftp 8 }

    wfTftpOutFiles OBJECT-TYPE
        SYNTAX	Counter
        ACCESS	read-only
        STATUS	mandatory
        DESCRIPTION
                "Number of files Successfully sent"
        ::= { wfTftp 9 }

    wfTftpInWRQ OBJECT-TYPE
        SYNTAX	Counter
        ACCESS	read-only
        STATUS	mandatory
        DESCRIPTION
                "Number of write requests received"
        ::= { wfTftp 10 }

    wfTftpOutWRQ OBJECT-TYPE
        SYNTAX	Counter
        ACCESS	read-only
        STATUS	mandatory
        DESCRIPTION
                "Number of write requests sent"
        ::= { wfTftp 11 }

    wfTftpInRRQ OBJECT-TYPE
        SYNTAX	Counter
        ACCESS	read-only
        STATUS	mandatory
        DESCRIPTION
                "Number of read requests received"
        ::= { wfTftp 12 }

    wfTftpOutRRQ OBJECT-TYPE
        SYNTAX	Counter
        ACCESS	read-only
        STATUS	mandatory
        DESCRIPTION
                "Number of read requests sent"
        ::= { wfTftp 13 }

    wfTftpRexmitPkts OBJECT-TYPE
        SYNTAX	Counter
        ACCESS	read-only
        STATUS	mandatory
        DESCRIPTION
                "Number of Re-transmitted packets"
        ::= { wfTftp 14 }

    wfTftpInErr OBJECT-TYPE
        SYNTAX	Counter
        ACCESS	read-only
        STATUS	mandatory
        DESCRIPTION
                "Number of Error PDUs Received"
        ::= { wfTftp 15 }

    wfTftpOutErr OBJECT-TYPE
        SYNTAX	Counter
        ACCESS	read-only
        STATUS	mandatory
        DESCRIPTION
                "Number of Error PDUs Sent"
        ::= { wfTftp 16 }

    wfTftpAborts OBJECT-TYPE
        SYNTAX	Counter
        ACCESS	read-only
        STATUS	mandatory
        DESCRIPTION
                "Number of Aborted Pseudo Connections"
        ::= { wfTftp 17 }

    wfTftpDelete OBJECT-TYPE
        SYNTAX  INTEGER {
                    created(1),
                    deleted(2)
                }
        ACCESS  read-write
        STATUS  mandatory
        DESCRIPTION
                "Create/Delete parameter. Default is created."
        DEFVAL  { created }
        ::= { wfTftp 18 }

    END  -- Wellfleet-TFTP-MIB
