COMPANY-MIB DEFINITIONS ::= BEGIN

-- Allot communication V5.1 MIB
-- April 01, 2003


IMPORTS
    MODULE-IDENTITY, OBJECT-TYPE, NOTIFICATION-TYPE, enterprises    FROM SNMPv2-SMI
    NOTIFICATION-GROUP						    FROM SNMPv2-CONF         
    DisplayString                                                   FROM SNMPv2-TC;

allotCom MODULE-IDENTITY
    LAST-UPDATED "0103120000Z"
    ORGANIZATION "Allot Communications"
    CONTACT-INFO
         "Allot Communications

	 postal:     5 Hanagar St.
                     Industrial Zone Neve Neeman
                     Hod Hasharon 45800 Israel
         phone:      +972-(0)9-761-9200
         fax:        +972-(0)9-744-3626
         email:      support@allot.com" 
    DESCRIPTION
        "This file defines the private Allot SNMP MIB extensions."
     ::= { enterprises 2603 }
    

-- NEStatistics		OBJECT IDENTIFIER ::= { AllotCom 1 }
-- neStatMIB		OBJECT IDENTIFIER ::= { NEStatistics 1 }
-- pipeStat		OBJECT IDENTIFIER ::= { NEStatistics 2 }
-- vcStat		OBJECT IDENTIFIER ::= { NEStatistics 3 }
-- qidPipeStat		OBJECT IDENTIFIER ::= { NEStatistics 4 }
-- qidVcStat		OBJECT IDENTIFIER ::= { NEStatistics 5 }

neTraps                 OBJECT IDENTIFIER ::= { allotCom 2 }
 
nePrimaryActive   NOTIFICATION-TYPE
    STATUS        current
    DESCRIPTION
        "This trap is sent when the primary NE changes to Active mode"
    ::= { neTraps 11 }

nePrimaryBypass   NOTIFICATION-TYPE
    STATUS        current
    DESCRIPTION
        "This trap is sent when the primary NE changes to Bypass mode"
    ::= { neTraps 12 }

neSecondaryActive  NOTIFICATION-TYPE
    STATUS         current
    DESCRIPTION
        "This trap is sent when the secondary NE changes to Active mode"
    ::= { neTraps 13 }    

neSecondaryStandBy NOTIFICATION-TYPE
    STATUS         current
    DESCRIPTION
        "This trap is sent when the secondary NE changes to StandBy mode"
    ::= { neTraps 14 }    

neSecondaryBypass  NOTIFICATION-TYPE
    STATUS         current
    DESCRIPTION
        "This trap is sent when the secondary NE changes to Bypass mode"
    ::= { neTraps 15 }    

collTableOverFlow  NOTIFICATION-TYPE
    STATUS         current
    DESCRIPTION
        "This trap is sent when acounting is not reading from the collector
        which causes the collector table to exceeds limits"
    ::= { neTraps 21 }
    
neAlertEvent       NOTIFICATION-TYPE
    STATUS         current
    DESCRIPTION
        "This trap is sent when user defined event occurs"
    ::= { neTraps 22 }    

    
neNotificationsGroup  NOTIFICATION-GROUP
    NOTIFICATIONS { nePrimaryActive, nePrimaryBypass, neSecondaryActive, 
		    neSecondaryStandBy, neSecondaryBypass, 
		    collTableOverFlow, neAlertEvent}
    STATUS  current
    DESCRIPTION
            "The notifications which indicate specific changes of the NE state."
    ::= { allotCom 3 }


END
