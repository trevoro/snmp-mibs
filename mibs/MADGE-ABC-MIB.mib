----------------------------------------------------------------------------
--
-- The Madge Active Broadcast Control MIB               Madge Networks Ltd
--
-- Version 1.1                                                October 1996
--
----------------------------------------------------------------------------
--
-- Overview
-- --------
-- The Madge Active Broadcast Control (ABC) MIB defines enterprise specific 
-- objects to allow the management of Madge products supporting ABC features.
--
-- The Madge ABC MIB contains the following groups:
--
--   madgeAbcTokenRing    - Token-Ring specific broadcast controls
--   madgeAbcNetBIOS      - NetBIOS specific broadcast controls
--   madgeAbcIP           - IP (and family) specifc broadcast controls
--   madgeAbcIPX          - IPX (and family) specifc broadcast controls
--
----------------------------------------------------------------------------

        MADGE-ABC-MIB DEFINITIONS ::= BEGIN

        IMPORTS
                TimeTicks, Counter, OBJECT-TYPE, enterprises
                        FROM RFC1155-SMI;
-- Data Types

        AbcState ::=    INTEGER {
                                disable                 (1),
                                enable                  (2),
                                monitor                 (3)
                                }

        AbcFlush ::=    INTEGER {
                                flush                   (1)
                                }

-- the ABC MIB

        madge           OBJECT IDENTIFIER ::= { enterprises 494 }
        madgeAbc        OBJECT IDENTIFIER ::= { madge 15 }

-- version information

        madgeAbcVersion OBJECT-TYPE
                SYNTAX  INTEGER
                ACCESS  read-only
                STATUS  mandatory
                DESCRIPTION
                        "The version number of the Active Broadcast Control
                        MIB.

                        The most recent version is 1."
                ::= { madgeAbc 1 }

-- groups in the ABC MIB

        madgeAbcTokenRing       OBJECT IDENTIFIER ::= { madgeAbc 2 }
        madgeAbcNetbios         OBJECT IDENTIFIER ::= { madgeAbc 3 }
        madgeAbcIp              OBJECT IDENTIFIER ::= { madgeAbc 4 }
        madgeAbcIpx             OBJECT IDENTIFIER ::= { madgeAbc 5 }
        
        madgeAbcTokenRingAreFilter 
                                OBJECT IDENTIFIER ::= {madgeAbcTokenRing 1}
        madgeAbcTokenRingAreConversion 
                                OBJECT IDENTIFIER ::= {madgeAbcTokenRing 2}

                        
        madgeAbcNetbiosName     OBJECT IDENTIFIER ::= {madgeAbcNetbios 1}
        madgeAbcNetbiosAddName  OBJECT IDENTIFIER ::= {madgeAbcNetbios 2}

                                
        madgeAbcIpArp           OBJECT IDENTIFIER ::= {madgeAbcIp 1}

                        
        madgeAbcIpxRipSapSuppress
                                OBJECT IDENTIFIER ::= {madgeAbcIpx 1}
        madgeAbcIpxType20Filter
                                OBJECT IDENTIFIER ::= {madgeAbcIpx 2}
        
----------------------------------------------------------------------------
-- the madgeAbcTokenRingAreFilter group

        madgeAbcTokenRingAreFilterState OBJECT-TYPE
                SYNTAX  AbcState
                ACCESS  read-write
                STATUS  mandatory
                DESCRIPTION
                        "The current state of the ARE (All Route Explorer)
                        filter.
                        
                        disable:        Perform no action.

                        enable:         Only optimal ARE frames will be 
                                        forwared onto other ports - optimal 
                                        frames are those which are quicker 
                                        or have shorter routing information 
                                        than other frames.

                        monitor:        No filtering will be performed but
                                        the potential performance of the
                                        filter will be measured, i.e.
                                        the count and timeout keys will
                                        be incremented as if the filter was
                                        on."
                ::= { madgeAbcTokenRingAreFilter 1 }

        madgeAbcTokenRingAreFilterFlushCache OBJECT-TYPE
                SYNTAX  AbcFlush
                ACCESS  read-write
                STATUS  mandatory
                DESCRIPTION
                        "Write the value 1 (flush) to flush the ARE filter 
                        cache and reset counters."
                ::= { madgeAbcTokenRingAreFilter 2 }
            
        madgeAbcTokenRingAreFilterCount OBJECT-TYPE
                SYNTAX  Counter
                ACCESS  read-only
                STATUS  mandatory
                DESCRIPTION
                        "The total number of ARE frames seen by the filter."
                ::= { madgeAbcTokenRingAreFilter 3 }
            
        madgeAbcTokenRingAreFilterFiltered OBJECT-TYPE
                SYNTAX  Counter
                ACCESS  read-only
                STATUS  mandatory
                DESCRIPTION
                        "The total number of ARE frames the filter has 
                        removed."
                ::= { madgeAbcTokenRingAreFilter 4 }
            
        madgeAbcTokenRingAreFilterTimeout OBJECT-TYPE
                SYNTAX  TimeTicks
                ACCESS  read-write
                STATUS  mandatory
                DESCRIPTION
                        "The maximum lifetime of an entry in the ARE filter 
                        cache.

                        Default value :   100 (centiseconds)
                        Minimum value :    25
                        Maximum value : 60000 (=10 minutes)"
                ::= { madgeAbcTokenRingAreFilter 5 }
            
----------------------------------------------------------------------------
-- the madgeAbcAreConversion group

        madgeAbcTokenRingAreConversionState OBJECT-TYPE
                SYNTAX  AbcState
                ACCESS  read-write
                STATUS  mandatory
                DESCRIPTION
                        "The current state of the ARE (All Route Explorer) 
                        conversion filter.
                        
                        disable:        Perform no action.

                        enable:         Turn on ARE conversion. The frames 
                                        specified by the mode key will be 
                                        converted into Spanning Tree 
                                        Explorers (ARE).

                        monitor:        No filtering will be performed but
                                        the potential performance of the
                                        filter will be measured, i.e.
                                        the count and timeout keys will
                                        be incremented as if the filter was
                                        on."
                ::= { madgeAbcTokenRingAreConversion 1 }

        madgeAbcTokenRingAreConversionFlushCache OBJECT-TYPE
                SYNTAX  AbcFlush
                ACCESS  read-write
                STATUS  mandatory
                DESCRIPTION
                        "Write the value 1 (flush) to flush the ARE filter 
                        cache and reset counters."
                ::= { madgeAbcTokenRingAreConversion 2 }
            
        madgeAbcTokenRingAreConversionCount OBJECT-TYPE
                SYNTAX  Counter
                ACCESS  read-only
                STATUS  mandatory
                DESCRIPTION
                        "The total number of ARE frames seen by the filter."
                ::= { madgeAbcTokenRingAreConversion 3 }
        
        madgeAbcTokenRingAreConversionFiltered OBJECT-TYPE
                SYNTAX  Counter
                ACCESS  read-only
                STATUS  mandatory
                DESCRIPTION
                        "The total number of ARE frames the filter has 
                        converted into STEs."
                ::= { madgeAbcTokenRingAreConversion 4 }
        
        madgeAbcTokenRingAreConversionMode OBJECT-TYPE
                SYNTAX  INTEGER {
                                first           (1),
                                all             (2),
                                bcast-first     (3),
                                bcast-all       (4)
                                }
                ACCESS  read-write
                STATUS  mandatory
                DESCRIPTION
                      "This variable controls the action taken when 
                      forwarding All Routes Explorer frames. 
                      
                      first:       convert all ARE frames with a RIF 
                                          length of 2 to STE frames.

                      all:         convert all ARE frames to STE frames.

                      bcast-first: convert all ARE frames with the
                                          broadcast destination address, with 
                                          a RIF length of 2 to STE frames.

                      bcast-all:   convert all ARE frames with the
                                          broadcast destination address to
                                          STE frames."
                ::= { madgeAbcTokenRingAreConversion 5 }
            
----------------------------------------------------------------------------
-- the madgeAbcNetbiosName group

        madgeAbcNetbiosNameState OBJECT-TYPE
                SYNTAX  AbcState
                ACCESS  read-write
                STATUS  mandatory
                DESCRIPTION
                        "The current state of the NetBIOS name filter. 
                        
                        disable:        Perform no action.

                        enable:         Frames sent to recognised NetBIOS 
                                        names will be forwarded on the
                                        port(s) on which the names are 
                                        known to exist.

                        monitor:        No filtering will be performed but
                                        the potential performance of the
                                        filter will be measured, i.e.
                                        the count and timeout keys will
                                        be incremented as if the filter was
                                        on."
                ::= { madgeAbcNetbiosName 1 }
            
        madgeAbcNetbiosNameFlushCache OBJECT-TYPE
                SYNTAX  AbcFlush
                ACCESS  read-write
                STATUS  mandatory
                DESCRIPTION
                        "Write the value 1 (flush) to flush the NetBIOS name 
                        filter cache and reset counters."
                ::= { madgeAbcNetbiosName 2 }
            
        madgeAbcNetbiosNameCount OBJECT-TYPE
                SYNTAX  Counter
                ACCESS  read-only
                STATUS  mandatory
                DESCRIPTION
                        "The total number of NetBIOS frames seen by the 
                        filter that have a named destination."
                ::= { madgeAbcNetbiosName 3 }
            
        madgeAbcNetbiosNameFiltered OBJECT-TYPE
                SYNTAX  Counter
                ACCESS  read-only
                STATUS  mandatory
                DESCRIPTION
                        "The total number of NetBIOS frames that the filter 
                        has been able to forward on the appropriate port(s)."
                ::= { madgeAbcNetbiosName 4 }
            
        madgeAbcNetbiosNameTimeout OBJECT-TYPE
                SYNTAX  TimeTicks
                ACCESS  read-write
                STATUS  mandatory
                DESCRIPTION
                        "The time for which a name will remain in the 
                        NetBIOS name cache.

                        Default value :    78000 (centiseconds) (=13 minutes)
                        Minimum value :      100
                        Maximum value : 60480000 (=1 day)"
                ::= { madgeAbcNetbiosName 5 }
            
        madgeAbcNetbiosNameForwardTimeout OBJECT-TYPE
                SYNTAX  TimeTicks
                ACCESS  read-write
                STATUS  mandatory
                DESCRIPTION
                        "The time for which NAME_QUERY frames for a name will
                        be forwarded without receiving a reply. If no reply
                        is received within this time the entry will be removed
                        from the cache

                        Default value :      40 (centiseconds) (=.4 seconds)
                        Minimum value :      10
                        Maximum value :    6000 (=1 minute)"
                ::= { madgeAbcNetbiosName 6 }
            
----------------------------------------------------------------------------
-- the madgeAbcNetbiosAddName group

        madgeAbcNetbiosAddNameState OBJECT-TYPE
                SYNTAX  AbcState
                ACCESS  read-write
                STATUS  mandatory
                DESCRIPTION
                        "The current state of the NetBIOS ADD_NAME_QUERY 
                        filter.
                        
                        disable:        Perform no action.

                        enable:         The frequency of retries by NetBIOS 
                                        stations will be limited to a 
                                        certain number over a particular 
                                        period of time. The number and time 
                                        are configureable.

                        monitor:        No filtering will be performed but
                                        the potential performance of the
                                        filter will be measured, i.e.
                                        the count and timeout keys will
                                        be incremented as if the filter was
                                        on."
                ::= { madgeAbcNetbiosAddName 1 }
            
        madgeAbcNetbiosAddNameFlushCache OBJECT-TYPE
                SYNTAX  AbcFlush
                ACCESS  read-write
                STATUS  mandatory
                DESCRIPTION
                        "Write the value 1 (flush) to flush the 
                        ADD_NAME_QUERY filter cache and reset counters."
                ::= { madgeAbcNetbiosAddName 2 }
            
        madgeAbcNetbiosAddNameCount OBJECT-TYPE
                SYNTAX  Counter
                ACCESS  read-only
                STATUS  mandatory
                DESCRIPTION
                        "The total number of ADD_NAME_QUERY NetBIOS frames 
                        seen by the filter."
                ::= { madgeAbcNetbiosAddName 3 }
            
        madgeAbcNetbiosAddNameFiltered OBJECT-TYPE
                SYNTAX  Counter
                ACCESS  read-only
                STATUS  mandatory
                DESCRIPTION
                        "The total number of ADD_NAME_QUERY NetBIOS frames 
                        that have been removed by the filter."
                ::= { madgeAbcNetbiosAddName 4 }
            
        madgeAbcNetbiosAddNameRetryPeriod OBJECT-TYPE
                SYNTAX  TimeTicks
                ACCESS  read-write
                STATUS  mandatory
                DESCRIPTION
                        "The time over which a maximum number of 
                        ADD_NAME_QUERY frames will be forwarded.

                        Default value :  500 (centiseconds)
                        Minimum value :  100
                        Maximum value : 6000 (=1 minute)"
                ::= { madgeAbcNetbiosAddName 5 }
            
        madgeAbcNetbiosAddNameRetryCount OBJECT-TYPE
                SYNTAX  INTEGER
                ACCESS  read-write
                STATUS  mandatory
                DESCRIPTION
                        "The maximum number of times a ADD_NAME_QUERY frame 
                        will be forwarded within a given period of time.
                        
                        Default value :  2
                        Minimum value :  1
                        Maximum value : 10"
                ::= { madgeAbcNetbiosAddName 6 }
            
----------------------------------------------------------------------------
-- the madgeAbcIpArp group

        madgeAbcIpArpState OBJECT-TYPE
                SYNTAX  AbcState
                ACCESS  read-write
                STATUS  mandatory
                DESCRIPTION
                        "The current state of the ARP filter. 
                        
                        disable:        Perform no action.

                        enable:         ARP frames for recognised IP 
                                        addresses will be forwarded only on 
                                        the port(s) on which the IP address 
                                        is known to be.

                        monitor:        No filtering will be performed but
                                        the potential performance of the
                                        filter will be measured, i.e.
                                        the count and timeout keys will
                                        be incremented as if the filter was
                                        on."
                ::= { madgeAbcIpArp 1 }
            
        madgeAbcIpArpFlushCache OBJECT-TYPE
                SYNTAX  AbcFlush
                ACCESS  read-write
                STATUS  mandatory
                DESCRIPTION
                        "Write the value 1 (flush) to flush the 
                        ARP filter cache and reset counters."
                ::= { madgeAbcIpArp 2 }
            
        madgeAbcIpArpCount OBJECT-TYPE
                SYNTAX  Counter
                ACCESS  read-only
                STATUS  mandatory
                DESCRIPTION
                        "The total number of ARP frames seen by the 
                        filter."
                ::= { madgeAbcIpArp 3 }
            
        madgeAbcIpArpFiltered OBJECT-TYPE
                SYNTAX  Counter
                ACCESS  read-only
                STATUS  mandatory
                DESCRIPTION
                        "The total number of ARP frames that the filter 
                        has been able to forward on the appropriate port(s)."
                ::= { madgeAbcIpArp 4 }
            
        madgeAbcIpArpTimeout OBJECT-TYPE
                SYNTAX  TimeTicks
                ACCESS  read-write
                STATUS  mandatory
                DESCRIPTION
                        "The time for which an IP address will remain in 
                        the ARP cache.

                        Default value :    60000 (centiseconds) (=10 minutes)
                        Minimum value :      100
                        Maximum value : 60480000 (=1 day)"
                ::= { madgeAbcIpArp 5 }
            
----------------------------------------------------------------------------
-- the madgeAbcRipSapSuppress group
                
        madgeAbcIpxRipSapSuppressState OBJECT-TYPE
                SYNTAX  AbcState
                ACCESS  read-write
                STATUS  mandatory
                DESCRIPTION
                        "The current state of the RIP/SAP suppression
                        filter.
                        
                        disable:        Perform no action.

                        enable:         IPX RIP and SAP Response frames 
                                        will be forwarded only to those ports 
                                        that have recently sourced such a 
                                        frame. This reduces the number of 
                                        gratuitous frames sent out on LANs 
                                        that only have IPX workstations 
                                        attached.

                        monitor:        No filtering will be performed but
                                        the potential performance of the
                                        filter will be measured, i.e.
                                        the count and timeout keys will
                                        be incremented as if the filter was
                                        on."
                ::= { madgeAbcIpxRipSapSuppress 1 }

        madgeAbcIpxRipSapSuppressFlushCache OBJECT-TYPE
                SYNTAX  AbcFlush
                ACCESS  read-write
                STATUS  mandatory
                DESCRIPTION
                        "Write the value 1 (flush) to flush the 
                        IPX RIP/SAP suppression filter cache 
                        and reset counters."
                ::= { madgeAbcIpxRipSapSuppress 2 }
            
        madgeAbcIpxRipSapSuppressCount OBJECT-TYPE
                SYNTAX  Counter
                ACCESS  read-only
                STATUS  mandatory
                DESCRIPTION
                        "The total number of RIP and SAP frames 
                        seen by the filter."
                ::= { madgeAbcIpxRipSapSuppress 3 }
        
        madgeAbcIpxRipSapSuppressFiltered OBJECT-TYPE
                SYNTAX  Counter
                ACCESS  read-only
                STATUS  mandatory
                DESCRIPTION
                        "The total number of frames the filter has 
                        has been able to filter."
                ::= { madgeAbcIpxRipSapSuppress 4 }
                
        madgeAbcIpxRipSapSuppressTimeout OBJECT-TYPE
                SYNTAX  TimeTicks
                ACCESS  read-write
                STATUS  mandatory
                DESCRIPTION
                        "The time for which a port will receive RIP and SAP 
                        response frames after sourcing such a frame.
                        
                        Default value :  60000 (centiseconds) (=10 minutes)
                        Minimum value :  36000 (=6 minutes)
                        Maximum value : 720000 (=2 hours)"
                ::= { madgeAbcIpxRipSapSuppress 5 }
            
----------------------------------------------------------------------------
-- the madgeAbcTokenRingAreFilter group

        madgeAbcIpxType20FilterState OBJECT-TYPE
                SYNTAX  AbcState
                ACCESS  read-write
                STATUS  mandatory
                DESCRIPTION
                        "The current state of the IPX Type 20
                        filter.
                        
                        disable:        Perform no action.

                        enable:         Only optimal Type 20 frames will be 
                                        forwared onto other ports - optimal 
                                        frames are those which are quicker 
                                        or have shorter routing information 
                                        than other frames.

                        monitor:        No filtering will be performed but
                                        the potential performance of the
                                        filter will be measured, i.e.
                                        the count and timeout keys will
                                        be incremented as if the filter was
                                        on."
                ::= { madgeAbcIpxType20Filter 1 }

        madgeAbcIpxType20FilterFlushCache OBJECT-TYPE
                SYNTAX  AbcFlush
                ACCESS  read-write
                STATUS  mandatory
                DESCRIPTION
                        "Write the value 1 (flush) to flush the Type 20 
                        filter cache and reset counters."
                ::= { madgeAbcIpxType20Filter 2 }
            
        madgeAbcIpxType20FilterCount OBJECT-TYPE
                SYNTAX  Counter
                ACCESS  read-only
                STATUS  mandatory
                DESCRIPTION
                        "The total number of Type 20 frames seen by the 
                        filter."
                ::= { madgeAbcIpxType20Filter 3 }
            
        madgeAbcIpxType20FilterFiltered OBJECT-TYPE
                SYNTAX  Counter
                ACCESS  read-only
                STATUS  mandatory
                DESCRIPTION
                        "The total number of Type 20 frames the filter has 
                        removed."
                ::= { madgeAbcIpxType20Filter 4 }
            
        madgeAbcIpxType20FilterTimeout OBJECT-TYPE
                SYNTAX  TimeTicks
                ACCESS  read-write
                STATUS  mandatory
                DESCRIPTION
                        "The maximum lifetime of an entry in the Type 20 
                        filter 
                        cache.

                        Default value :      100 (centiseconds)
                        Minimum value :       25 
                        Maximum value :     6000 (=1 minute)"
                ::= { madgeAbcIpxType20Filter 5 }
            
----------------------------------------------------------------------------
        END
----------------------------------------------------------------------------
