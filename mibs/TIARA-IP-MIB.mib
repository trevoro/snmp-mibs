-- *****************************************************************
-- tiaranet-ip.mib:  Tiara Networks IP Interface MIB
--
-- July,1st 1999, kumar
--
-- Copyright (c) 1999-2000 by Tiara Networks, Inc.
-- All rights reserved.
--
-- *****************************************************************

TIARA-IP-MIB DEFINITIONS ::= BEGIN

IMPORTS
        MODULE-IDENTITY, OBJECT-TYPE, 
        IpAddress,Integer32     FROM SNMPv2-SMI
        TruthValue, RowStatus   FROM SNMPv2-TC
        DisplayString           FROM RFC1213-MIB
        tiaraMgmt               FROM TIARA-NETWORKS-SMI;


tiaraIpMib MODULE-IDENTITY
        LAST-UPDATED      "0001270000Z" 
        ORGANIZATION      "Tiara Networks Inc."
        CONTACT-INFO
                 "         Tiara Networks
                           Customer Support

                           525 Race Street, Suite 100,
                           San Jose, CA 95126
                           USA

                           Tel: +1 408-216-4700
                           Fax: +1 408-216-4701

                           E-mail: support@tiaranetworks.com"

        DESCRIPTION

            "This MIB defines objects for IP addressable interfaces and 
            the static routing table."

                           ::= { tiaraMgmt 23} 

tiaraIpRoutingEnable                    OBJECT-TYPE
        SYNTAX                          TruthValue
        MAX-ACCESS                      read-write
        STATUS                          current
        DESCRIPTION 

            "This object toggles between the IP routing and the IP
            muxing modes. If the IP routing mode is disabled, the 
            IP muxing mode is enabled. If the IP routing mode is
            enabled, the IP muxing mode is disabled."

                          ::= { tiaraIpMib 1}

-- TiaraIpIfTable Table definition
-- An entry in this table is created when an IP address is assigned to
-- an interface. An entry in this table is deleted when an IP address
-- is unconfigured from an interface.

tiaraIpIfTable                          OBJECT-TYPE
        SYNTAX                          SEQUENCE OF TiaraIpIfTableEntry
        MAX-ACCESS                      not-accessible
        STATUS                          current
        DESCRIPTION    

            "The TiaraIpIfTable defines objects for IP addressable 
            interfaces that are currently configured on the Tiara
            system. It maps a unique index value to each interface."

                          ::= {tiaraIpMib 2}

tiaraIpIfTableEntry                     OBJECT-TYPE
        SYNTAX                          TiaraIpIfTableEntry
        MAX-ACCESS                      not-accessible
        STATUS                          current
        DESCRIPTION   

            "An entry in the TiaraIpIfTable that defines objects for 
            a particular IP interface."

        INDEX             { tiaraIpIfIndex }
                          ::= {tiaraIpIfTable 1}

TiaraIpIfTableEntry ::= SEQUENCE {
        tiaraIpIfIndex                  Integer32,
        tiaraIpIfName                   DisplayString,
        tiaraIpIfAddr                   IpAddress,
        tiaraIpIfMask                   IpAddress,
        tiaraIpIfPeerAddr               IpAddress,
        tiaraIpIfType                   INTEGER
        }
 

tiaraIpIfIndex OBJECT-TYPE
        SYNTAX                          Integer32
        MAX-ACCESS                      read-only
        STATUS                          current
        DESCRIPTION 

            "This value identifies a particular IP interface and serves 
            as an index for the tiarIpIfTable."

                          ::= { tiaraIpIfTableEntry 1}

tiaraIpIfName OBJECT-TYPE
        SYNTAX                          DisplayString
        MAX-ACCESS                      read-only
        STATUS                          current
        DESCRIPTION 

            "A unique name associated with an IP interface."

                           ::= { tiaraIpIfTableEntry 2}

tiaraIpIfAddr                           OBJECT-TYPE
        SYNTAX                          IpAddress
        MAX-ACCESS                      read-only
        STATUS                          current
        DESCRIPTION

           "The unique IP address of an IP interface."

                           ::= { tiaraIpIfTableEntry 3}

tiaraIpIfMask                           OBJECT-TYPE
        SYNTAX                          IpAddress
        MAX-ACCESS                      read-only
        STATUS                          current
        DESCRIPTION   

            "The network mask associated with an IP interface."

                           ::= { tiaraIpIfTableEntry 4}

tiaraIpIfPeerAddr                       OBJECT-TYPE
        SYNTAX                          IpAddress
        MAX-ACCESS                      read-only
        STATUS                          current
        DESCRIPTION        

            "The IP address of the peer which is the other end of
            a point-to-point link. The peer IP address object is
            only valid for a WAN or point-to-point interface."

                           ::= { tiaraIpIfTableEntry 5}

tiaraIpIfType                           OBJECT-TYPE
         SYNTAX                         INTEGER {
                                            ethernet (1),
                                            wan (2)
                                        }
         MAX-ACCESS                     read-only
         STATUS                         current
         DESCRIPTION 

            "This object identifies the type of interface as
            either Ethernet or WAN."

                           ::= { tiaraIpIfTableEntry 6}

-- Static Route Table

tiaraStaticRouteTable                   OBJECT-TYPE
        SYNTAX                          SEQUENCE OF TiaraStaticRouteEntry
        MAX-ACCESS                      not-accessible
        STATUS                          current
        DESCRIPTION        

            "A list of static route table entries for this entity. The
            following variables are required for row creation:

                  tiaraStaticRouteIndex       = 65535
                  tiaraStaticRouteNetworkAddr = Destination IP address
                  tiaraStaticRouteNetworkMask = Subnet mask
                  tiaraStaticRouteGatewayAddr = Next hop IP address
                  tiaraStaticRouteNoOfHops    = Number of hops or metric
                  tiaraStaticRouteRowStatus   = createAndGo"

                           ::= { tiaraIpMib 3 }

tiaraStaticRouteEntry                   OBJECT-TYPE
      SYNTAX                            TiaraStaticRouteEntry 
      MAX-ACCESS                        not-accessible
      STATUS                            current
      DESCRIPTION    

           "A single static route entry in the static route table."

       INDEX               {  tiaraStaticRouteIndex }
                           ::= { tiaraStaticRouteTable 1 }

TiaraStaticRouteEntry ::= SEQUENCE {
        tiaraStaticRouteIndex           INTEGER,
        tiaraStaticRouteNetworkAddr     IpAddress,
        tiaraStaticRouteNetworkMask     IpAddress,
        tiaraStaticRouteGatewayAddr     DisplayString,
        tiaraStaticRouteNoOfHops        INTEGER,
        tiaraStaticRouteRowStatus       RowStatus
        }

tiaraStaticRouteIndex                   OBJECT-TYPE
        SYNTAX                          INTEGER
        MAX-ACCESS                      not-accessible
        STATUS                          current
        DESCRIPTION  

            "A numeric index for static route table entries. This
            index is internally generated by the SNMP agent, and it
            uniquely identifies a single entry in the table.

            To create a row in the table, use the invalid value 65535 
            for this variable.

            To query any variable in this table, use this variable,
            which can be found for a given 
            (network address-network mask-gateway address) tuple 
            using the snmp-walk operation."

                           ::= { tiaraStaticRouteEntry 1 }
           
tiaraStaticRouteNetworkAddr             OBJECT-TYPE
        SYNTAX                          IpAddress
        MAX-ACCESS                      read-create
        STATUS                          current
        DESCRIPTION 

            "The destination IP address of this route. This can be 
            either a complete host address for one particular host or 
            or a network address for all the hosts on that network.

            An entry with a value of 0.0.0.0 for the network address is 
            considered a default route."

                            ::= { tiaraStaticRouteEntry 2 }
           
tiaraStaticRouteNetworkMask             OBJECT-TYPE
        SYNTAX                          IpAddress
        MAX-ACCESS                      read-create
        STATUS                          current
        DESCRIPTION  

            "The network mask associated with the network address"
                           
                            ::= { tiaraStaticRouteEntry 3 }

tiaraStaticRouteGatewayAddr             OBJECT-TYPE
        SYNTAX                          DisplayString
        MAX-ACCESS                      read-create   
        STATUS                          current
        DESCRIPTION   

            "This can either be the IP address of a next hop router or 
            the IP address of a directly connected network. The next 
            hop router receives datagrams from the Tiara system and
            forwards them to the final destination. This can also be an
            interface name."

                            ::= { tiaraStaticRouteEntry 4 }

tiaraStaticRouteNoOfHops                OBJECT-TYPE
        SYNTAX                          INTEGER (1..15)
        MAX-ACCESS                      read-create   
        STATUS                          current
        DESCRIPTION  

            "The number of hops for this route."

                           ::= { tiaraStaticRouteEntry 5 }

tiaraStaticRouteRowStatus               OBJECT-TYPE
        SYNTAX                          RowStatus
        MAX-ACCESS                      read-create   
        STATUS                          current
        DESCRIPTION        

            "Used to configure or delete a static route. To configure
            a route, set the value of this object to createAndGo. To delete
            a route, set the value of this object to destroy."

                           ::= { tiaraStaticRouteEntry 6 }

END
