CXTokenBus-MIB DEFINITIONS ::= BEGIN

IMPORTS
	Counter         FROM RFC1155-SMI
	OBJECT-TYPE     FROM RFC-1212
	cxTokenBus, SapIndex, Alias
				FROM CXProduct-SMI;



--  Service Access Point Configuration Table

--  The table describing parameters required to system bus LLC
--  service access point.


tbSapTable OBJECT-TYPE
	SYNTAX  SEQUENCE OF TbSapEntry
	ACCESS  not-accessible
	STATUS  mandatory
	DESCRIPTION
"A table containing configuration information about each LLC service access 
		point."
	::= { cxTokenBus 1 }

	tbSapEntry OBJECT-TYPE
		SYNTAX  TbSapEntry
		ACCESS  not-accessible
		STATUS  mandatory
		DESCRIPTION
"The parameters for a particular frame relay module service access point."
		INDEX { tbSapNumber
			}
		::= { tbSapTable 1 }

	TbSapEntry ::=
		SEQUENCE {
			tbSapNumber
				SapIndex,
			tbSapRowStatus
				INTEGER,
			tbSapAlias
				Alias,
			tbSapCompanionAlias
				Alias,
			tbSapType
				INTEGER,
			tbSapStatGathering
				INTEGER,
			tbSapStatRxUnitDataFrames
				Counter,
			tbSapStatRxUnitDataOctets
				Counter,
			tbSapStatRxDataAckFrames
				Counter,
			tbSapStatRxDataAckOctets
				Counter,
			tbSapStatTxUnitDataFrames
				Counter,
			tbSapStatTxUnitDataOctets
				Counter,
			tbSapStatTxDataAckFrames
				Counter,
			tbSapStatTxDataAckOctets
				Counter
			}



	tbSapNumber OBJECT-TYPE
		SYNTAX  SapIndex
		ACCESS  read-only
		STATUS  mandatory
		DESCRIPTION
"This object serves to identify the service access point by a numerical 
value."
		::= { tbSapEntry 1 }

	tbSapRowStatus OBJECT-TYPE
		SYNTAX  INTEGER {
					invalid (1),
					valid   (2)
				}
		ACCESS  read-write
		STATUS  mandatory
		DESCRIPTION
"Indicates whether the particular service access point is configured within 
the MIB. Service access point entries (rows) may be created by setting this 
object value to 'valid', or deleted by changing this object value 
to 'invalid'.

Options:
invalid (1)

valid (2)"
		::= { tbSapEntry 2 }

	tbSapAlias OBJECT-TYPE
		SYNTAX  Alias
		ACCESS  read-write
		STATUS  mandatory
		DESCRIPTION
"Identifies the service access point by a textual name. Names are unique 
per service access point."
		::= { tbSapEntry 3 }

	tbSapCompanionAlias OBJECT-TYPE
		SYNTAX  Alias
		ACCESS  read-write
		STATUS  mandatory
		DESCRIPTION
"Identifies the remote service access point that will communicate with this 
service access point by a textual name. Names are unique per service 
access point."
		DEFVAL { ''h }
		::= { tbSapEntry 4 }

	tbSapType OBJECT-TYPE
		SYNTAX  INTEGER {
					upper   (2)
				}
		ACCESS  read-write
		STATUS  mandatory
		DESCRIPTION
"This object serves to identify the service access point by type: 'lower' or 
'upper'. In our case, only upper is relevent but this object is kept for 
uniformity with the other Sap definition in the system"
		DEFVAL { upper }
		::= { tbSapEntry 5 }

	tbSapStatGathering OBJECT-TYPE
		SYNTAX  INTEGER {
					disabled (1),
					enabled (2)
				}
		ACCESS  read-write
		STATUS  mandatory
		DESCRIPTION
"This object specifies if the SAP statistics will be updated. If disabled, 
the counter will always be zero."
		DEFVAL { enabled }
		::= { tbSapEntry 6 }

	tbSapStatRxUnitDataFrames OBJECT-TYPE
		SYNTAX  Counter
		ACCESS  read-only
		STATUS  mandatory
		DESCRIPTION
"Indicates the number of data frames received from the upper layer which 
requested no acknowledgment from the destination token bus module."
		::= { tbSapEntry 7 }

	tbSapStatRxUnitDataOctets OBJECT-TYPE
		SYNTAX  Counter
		ACCESS  read-only
		STATUS  mandatory
		DESCRIPTION
"Indicates the number of data octets received from the upper layer which 
requested no acknowledgment from the destination token bus module."
		::= { tbSapEntry 8 }

	tbSapStatRxDataAckFrames OBJECT-TYPE
		SYNTAX  Counter
		ACCESS  read-only
		STATUS  mandatory
		DESCRIPTION
"Indicates the number of data frames received from the upper layer which 
requested an acknowledgment from the destination token bus module."
		::= { tbSapEntry 9 }

	tbSapStatRxDataAckOctets OBJECT-TYPE
		SYNTAX  Counter
		ACCESS  read-only
		STATUS  mandatory
		DESCRIPTION
"Indicates the number of data octets received from the upper layer which 
requested an acknowledgment from the destination token bus module."
		::= { tbSapEntry 10 }

	tbSapStatTxUnitDataFrames OBJECT-TYPE
		SYNTAX  Counter
		ACCESS  read-only
		STATUS  mandatory
		DESCRIPTION
"Indicates the number of data frames sent to the upper layer where the 
originating card did not request an acknowledgment."
		::= { tbSapEntry 11 }

	tbSapStatTxUnitDataOctets OBJECT-TYPE
		SYNTAX  Counter
		ACCESS  read-only
		STATUS  mandatory
		DESCRIPTION
"Indicates the number of data octets sent to the upper layer where the 
originating card did not request an acknowledgment."
		::= { tbSapEntry 12 }

	tbSapStatTxDataAckFrames OBJECT-TYPE
		SYNTAX  Counter
		ACCESS  read-only
		STATUS  mandatory
		DESCRIPTION
"Indicates the number of data frames sent to the upper layer where the 
originating card requested an acknowledgment."
		::= { tbSapEntry 13 }

	tbSapStatTxDataAckOctets OBJECT-TYPE
		SYNTAX  Counter
		ACCESS  read-only
		STATUS  mandatory
		DESCRIPTION
"Indicates the number of data octets sent to the upper layer where the 
originating card requested an acknowledgment."
		::= { tbSapEntry 14 }


-- Parameter group to configure the 802.4 token bus device functionalites.

tbDevice                OBJECT IDENTIFIER ::= { cxTokenBus 2}

tbDevPollingInterval OBJECT-TYPE
	SYNTAX  INTEGER
	ACCESS  read-write
	STATUS  mandatory
	DESCRIPTION
"This determine how often the Token Bus Device will be polled for 
transmission completion and frame reception. This value is in millisecond. 
If this value is 0, the token bus module is waiting for an external polling 
message. This is the case in special test software only."
	DEFVAL { 10 }
	::= { tbDevice 1 }

tbRxFrameDescriptors OBJECT-TYPE
	SYNTAX  INTEGER
	ACCESS  read-write
	STATUS  mandatory
	DESCRIPTION
"Number of frame descriptors allocated to the token bus device (MC68824) to 
perform the receive process."
	DEFVAL { 32 }
	::= { tbDevice 2 }

tbRxBufferDescriptors OBJECT-TYPE
	SYNTAX  INTEGER
	ACCESS  read-write
	STATUS  mandatory
	DESCRIPTION
"Number of buffer descriptors allocated to the token bus device (MC68824) 
to perform the receive process."
	DEFVAL { 320 }
	::= { tbDevice 3 }

tbTxFrameDescriptors OBJECT-TYPE
	SYNTAX  INTEGER
	ACCESS  read-write
	STATUS  mandatory
	DESCRIPTION
"Number of frame descriptors allocated to the token bus device (MC68824) to 
perform the transmission process."
	DEFVAL { 16 }
	::= { tbDevice 4 }

tbTxBufferDescriptors OBJECT-TYPE
	SYNTAX  INTEGER
	ACCESS  read-write
	STATUS  mandatory
	DESCRIPTION
"Number of buffer descriptors allocated to the token bus device (MC68824) 
to perform the transmission process."
	DEFVAL { 160 }
	::= { tbDevice 5 }

tbMaxFrameSizeClass6 OBJECT-TYPE
	SYNTAX  INTEGER
	ACCESS  read-write
	STATUS  mandatory
	DESCRIPTION
"Maximum frame size permit to be transmitted at the access class 6. This 
maximum must be enforced to guaranty the maximum token rotation time 
specified above."
	::= { tbDevice 6 }

tbMaxFrameSizeClass4 OBJECT-TYPE
	SYNTAX  INTEGER
	ACCESS  read-write
	STATUS  mandatory
	DESCRIPTION
"Maximum frame size permit to be transmitted at the access class 4."
	::= { tbDevice 7 }

tbMaxFrameSizeClass2 OBJECT-TYPE
	SYNTAX  INTEGER
	ACCESS  read-write
	STATUS  mandatory
	DESCRIPTION
"Maximum frame size permit to be transmitted at the access class 2."
	::= { tbDevice 8 }

tbMaxFrameSizeClass0 OBJECT-TYPE
	SYNTAX  INTEGER
	ACCESS  read-write
	STATUS  mandatory
	DESCRIPTION
"Maximum frame size permit to be transmitted at the access class 0."
	::= { tbDevice 9 }

tbHiPriorityTokenHoldTime OBJECT-TYPE
	SYNTAX  INTEGER ( 0 .. 4095 )
	ACCESS  read-write
	STATUS  mandatory
	DESCRIPTION
"Maximum time a station can hold the token to transmit frame at the highest 
priority (access class 6). The value to configure may be calculated with 
this formula:

tbHiPriorityTokenHoldTime=(target rotation time(sec)) * Bus Clock frequency
			  -------------------------------------------------
					number of card * 64"
	DEFVAL { 30 }
	::= { tbDevice 10 }

tbTargetRotationTimeClass4 OBJECT-TYPE
	SYNTAX  INTEGER ( 0 .. 32767 )
	ACCESS  read-write
	STATUS  mandatory
	DESCRIPTION
"This parameter defines the target rotation time for the access class 4. 
The value to configure may be calculated with this formula:

tbTargetRotationTimeClass4=(target rotation time(sec)) * Bus Clock frequency
			   -------------------------------------------------
						  64"
	DEFVAL { 480 }
	::= { tbDevice 11 }

tbTargetRotationTimeClass2 OBJECT-TYPE
	SYNTAX  INTEGER ( 0 .. 32767 )
	ACCESS  read-write
	STATUS  mandatory
	DESCRIPTION
"This parameter defines the target rotation time for the access class 2. 
The value to configure may be calculated with this formula:

tbTargetRotationTimeClass2=(target rotation time(sec)) * Bus Clock frequency
			    ------------------------------------------------
						64"
	DEFVAL { 384 }
	::= { tbDevice 12 }

tbTargetRotationTimeClass0 OBJECT-TYPE
	SYNTAX  INTEGER ( 0 .. 32767 )
	ACCESS  read-write
	STATUS  mandatory
	DESCRIPTION
"This parameter defines the target rotation time for the access class 0. 
The value to configure may be calculated with this formula:

tbTargetRotationTimeClass0=(target rotation time(sec)) * Bus Clock frequency
			   -------------------------------------------------
							64"
	DEFVAL { 288 }
	::= { tbDevice 13 }

tbTargetRotationForMaintenance OBJECT-TYPE
	SYNTAX  INTEGER ( 0 .. 32767 )
	ACCESS  read-write
	STATUS  mandatory
	DESCRIPTION
"This parameter defines the target rotation time for the ring maintenance. 
The value to configure may be calculated with this formula:

tbTargetRotationorMaintenance  =
 
target rotation time(sec)) * Bus Clock frequency
------------------------------------------------
			64"
	DEFVAL { 288 }
	::= { tbDevice 14 }

tbMaxInterSolicitCount OBJECT-TYPE
	SYNTAX  INTEGER ( 16 .. 255 )
	ACCESS  read-write
	STATUS  mandatory
	DESCRIPTION
"This parameter defines the target rotation time for the ring maintenance. 
The value to configure may be calculated with this formula:

tbTimeForMaintenance = (target rotation time(sec)) * Bus Clock frequency
		       -------------------------------------------------
						64"
	DEFVAL { 32 }
	::= { tbDevice 15 }

tbNonRwrMaxRetryLimit OBJECT-TYPE
	SYNTAX  INTEGER ( 0 .. 255 )
	ACCESS  read-write
	STATUS  mandatory
	DESCRIPTION
"This parameter specifies how many times the MC68824 chip set will try to 
retransmit a request with no response (RWNR) frame on which it detected    
 a transmission failure."
	DEFVAL { 0 }
	::= { tbDevice 16 }

tbRwrMaxRetryLimit OBJECT-TYPE
	SYNTAX  INTEGER ( 0 .. 255 )
	ACCESS  read-write
	STATUS  mandatory
	DESCRIPTION
"This parameter specifies how many time the MC68824 chip set will try to 
retransmit a request with response (RWR) frame on which it detected a 
transmission failure through a lack of response."
	DEFVAL { 3 }
	::= { tbDevice 17 }

tbSlotTime OBJECT-TYPE
	SYNTAX  INTEGER ( 0 .. 8191 )
	ACCESS  read-write
	STATUS  mandatory
	DESCRIPTION
"This parameter specifies how much time the MC68824 chip set will wait for 
a response on a transmission a request with response (RWR) frame. This 
parameter must be specified in octet time."
	DEFVAL { 256 }
	::= { tbDevice 18 }

tbTxNonRwrFailures OBJECT-TYPE
	SYNTAX  Counter
	ACCESS  read-only
	STATUS  mandatory
	DESCRIPTION
"Number of transmission failures related to the request with no response 
frames."
	::= { tbDevice 19 }

tbTxRwrFailures OBJECT-TYPE
	SYNTAX  Counter
	ACCESS  read-only
	STATUS  mandatory
	DESCRIPTION
"Number of transmission failure related to the request with response 
frames."
	::= { tbDevice 20 }

tbUnexpectedFrame6s OBJECT-TYPE
	SYNTAX  Counter
	ACCESS  read-only
	STATUS  mandatory
	DESCRIPTION
"This counter incrementes when the TBC hears an unexpected frame when 
expecting a response to a transmitted request with response frame. An 
unexpected frame in this case is any valid frame which is not a response 
frame addressed to this station. Upon detecting this event, the TBC 
increment this counter and goes to the IDLE without passing the token."
	::= { tbDevice 21 }

tbUnexpectedFrame10s OBJECT-TYPE
	SYNTAX  Counter
	ACCESS  read-only
	STATUS  mandatory
	DESCRIPTION
"The TBC module incremented this counter when it executes the 'unexpected 
frame 10' transition the IEEE 802.4 access control machine (ACM). It occurs 
when the TBC attempted to solicit a new successor and while waiting for a 
response, heard either a data frame not sent by itself. When this event 
occurs, it indicates a protocol error, possibly a duplicate token situation. After this event, 
The TBC will go to the IDLE without passing the token."
	::= { tbDevice 22 }

tbNbUnderruns OBJECT-TYPE
	SYNTAX  Counter
	ACCESS  read-only
	STATUS  mandatory
	DESCRIPTION
"This statistic represents the number of times the TBC detected a FIFO 
underrun during transmission."
	::= { tbDevice 23 }

tbRxRetryRwrFrames OBJECT-TYPE
	SYNTAX  Counter
	ACCESS  read-only
	STATUS  mandatory
	DESCRIPTION
"Number of detected retransmitted request with response frame. This event 
mostly occurs when the RWR frame or its response is lost."
	::= { tbDevice 24 }

tbRxNullLsduRwrFrames OBJECT-TYPE
	SYNTAX  Counter
	ACCESS  read-only
	STATUS  mandatory
	DESCRIPTION
"Number of received request with response frame which did not contain any 
LLC service data unit (LDSU)."
	::= { tbDevice 25 }

tbNbPassedTokens OBJECT-TYPE
	SYNTAX  Counter
	ACCESS  read-only
	STATUS  mandatory
	DESCRIPTION
"Number of time this station thinks it has sucessfully passed the token. 
It can be used to calculate the average token rotation time."
	::= { tbDevice 26 }

tbNbHeardTokens OBJECT-TYPE
	SYNTAX  Counter
	ACCESS  read-only
	STATUS  mandatory
	DESCRIPTION
"Number of time this station heard a token where Destination Address (DA) or 
Source Address (SA) are not equal to This Station (TS) address. This number 
can be used to determine how many stations there is on the logical ring."
	::= { tbDevice 27 }

tbNbNoSuccessor8Passes OBJECT-TYPE
	SYNTAX  Counter
	ACCESS  read-only
	STATUS  mandatory
	DESCRIPTION
"This statistic indicates the number of times this station has gone through 
the no successor 8 arc in the state machine. This happens when the TBC 
fails to pass the token and does not succeed in finding a new successor 
station. The counter is incremented only if the TBC thinks it is not the 
only active station in the network. A significantly large value in this 
counter may indicate a 'faulty' transmitter condition in this station."
	::= { tbDevice 28 }

tbNbWhoFollowsFrames OBJECT-TYPE
	SYNTAX  Counter
	ACCESS  read-only
	STATUS  mandatory
	DESCRIPTION
"This statistic is the number of times this station has had to look for a 
new next station to pass the token to. This frame is sent as part of the 
TBC's effort to pass the token to its former successor's successor if the 
original successor station does not respond to the token. This counter 
is incremented by two every time a failure occurs."
	::= { tbDevice 29 }

tbNbTokenPassFailures OBJECT-TYPE
	SYNTAX  Counter
	ACCESS  read-only
	STATUS  mandatory
	DESCRIPTION
"This statistic indicates the number of token pass failed transitions when 
pass state is equal to pass token. Upon failing to pass the token, the 
TBC tries to send a second token (pass state equals repeat pass token). 
If this effort fails too, this counter is not incremented again; but the 
TBC will then send a who follows frame and the who follows query counter 
will be incremented."
	::= { tbDevice 30 }

tbRxPeriodNonSilences OBJECT-TYPE
	SYNTAX  Counter
	ACCESS  read-only
	STATUS  mandatory
	DESCRIPTION
"This statistic is the number of received periods of non-silence."
	::= { tbDevice 31}

tbRxBadCrcFrames OBJECT-TYPE
	SYNTAX  Counter
	ACCESS  read-only
	STATUS  mandatory
	DESCRIPTION
"This statistic tracks the number of received frames with FCS (or CRC) 
errors and the E-bit reset."
	::= { tbDevice 32 }

tbRxEBitSetFrames OBJECT-TYPE
	SYNTAX  Counter
	ACCESS  read-only
	STATUS  mandatory
	DESCRIPTION
"This statistic counts the number of received frames with the E-bit set in 
the end delimiter. The E bit, or error bit, is set by the regenerative 
repeater (headend remodulator), when the headend detects a FCS error on 
the forward channel."
	::= { tbDevice 33 }

tbRxFrameFragments OBJECT-TYPE
	SYNTAX  Counter
	ACCESS  read-only
	STATUS  mandatory
	DESCRIPTION
"This statistic represents the number of frame fragments (start delimiter 
(SD) not followed by a valid end delimiter (ED)). A valid frame consists 
of only data (zero or one MAC symbols) between the SD and the ED. If an 
SD is detected and then, before a valid ED, the TBC detects either silence, 
non data (not part of the aligned ED), or bad signal, then this counter is 
incremented. Note that this includes abort sequences."
	::= { tbDevice 34 }

tbRxFrameTooLongs OBJECT-TYPE
	SYNTAX  Counter
	ACCESS  read-only
	STATUS  mandatory
	DESCRIPTION
"This statistic is the number of received frames tart are too long 
(>8 KBytes)."
	::= { tbDevice 35 }

tbNbNoFdBdErrors OBJECT-TYPE
	SYNTAX  Counter
	ACCESS  read-only
	STATUS  mandatory
	DESCRIPTION
"This statistic counts the number of frames that were not received because 
there were not enough frame descriptors or there were not enough buffers."
	::= { tbDevice 36 }

tbNbOverruns OBJECT-TYPE
	SYNTAX  Counter
	ACCESS  read-only
	STATUS  mandatory
	DESCRIPTION
"This statistic represents the number of times the TBC detected a FIFO 
overrun during receive."
	::= { tbDevice 37}

END
