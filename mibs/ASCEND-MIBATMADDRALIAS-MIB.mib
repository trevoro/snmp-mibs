--			Ascend mibatmaddralias MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMADDRALIAS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmAddrAliasProfile  OBJECT IDENTIFIER ::= { configuration 37}

	-- The mibatmAddrAliasProfile table
	--
	-- This table contains parameters for the mibatmAddrAliasProfile profile
	--

    mibatmAddrAliasProfileTable	OBJECT-TYPE
	SYNTAX		SEQUENCE OF MibatmAddrAliasProfileEntry
	ACCESS		not-accessible
	STATUS		mandatory
	DESCRIPTION	"A list of mibatmAddrAliasProfile profile entries."
	::= { mibatmAddrAliasProfile 1 }

    mibatmAddrAliasProfileEntry	OBJECT-TYPE
	SYNTAX		MibatmAddrAliasProfileEntry
	ACCESS		not-accessible
	STATUS		mandatory
	DESCRIPTION	"A mibatmAddrAliasProfile entry containing objects that
			 maps to the parameters of mibatmAddrAliasProfile profile."
	INDEX		{ atmAddrAliasProfile-AliasName }
	::= { mibatmAddrAliasProfileTable 1 }

    MibatmAddrAliasProfileEntry ::=
	SEQUENCE {
	    atmAddrAliasProfile-AliasName
		DisplayString,
	    atmAddrAliasProfile-Address
		DisplayString,
	    atmAddrAliasProfile-Length
		INTEGER,
	    atmAddrAliasProfile-Action-o
		INTEGER
	}

    atmAddrAliasProfile-AliasName	OBJECT-TYPE
	SYNTAX	DisplayString
	ACCESS	read-only
	STATUS	mandatory
	DESCRIPTION	"The alias name for the address."
	::= { mibatmAddrAliasProfileEntry 1 }

    atmAddrAliasProfile-Address	OBJECT-TYPE
	SYNTAX	DisplayString
	ACCESS	read-write
	STATUS	mandatory
	DESCRIPTION	"The address to be aliased."
	::= { mibatmAddrAliasProfileEntry 2 }

    atmAddrAliasProfile-Length	OBJECT-TYPE
	SYNTAX	INTEGER
	ACCESS	read-write
	STATUS	mandatory
	DESCRIPTION	"The length of the address to be aliased in bytes."
	::= { mibatmAddrAliasProfileEntry 3 }

    atmAddrAliasProfile-Action-o	OBJECT-TYPE
	SYNTAX	INTEGER {
		    noAction (1),
		    createProfile (2),
		    deleteProfile (3)
		}
	ACCESS	read-write
	STATUS	mandatory
	DESCRIPTION	""
	::= { mibatmAddrAliasProfileEntry 4 }

END
