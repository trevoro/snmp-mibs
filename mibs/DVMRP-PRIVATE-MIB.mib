DVMRP-PRIVATE-MIB DEFINITIONS ::= BEGIN

-- Referencing the parent branch.

IMPORTS
            MODULE-IDENTITY, OBJECT-TYPE, IpAddress  	FROM SNMPv2-SMI
	    RowStatus					FROM SNMPv2-TC
	    cjnProtocol                             	FROM Cajun-ROOT; 

cjnDvmrp MODULE-IDENTITY
        LAST-UPDATED "9902230000Z" -- Tuesday Feb 23, 1999"
        ORGANIZATION "Lucent's Concord Technology Center (CTC)"
        CONTACT-INFO
	        "Erick Crowell -- ecrowell@lucent.com
		 Raj Duggal (Group Leader) -- rduggal@lucent.com
		 Marie Pacini -- mfpacini@lucent.com
		 Ira Steckler -- isteckler@lucent.com"
		
	DESCRIPTION
       		"Cajun DVMRP PRIVATE MIB"
	::= { cjnProtocol 13 }

-- DVMRP Global Group
--
	cjnDvmrpGblGroup	OBJECT IDENTIFIER ::= { cjnDvmrp 1 }
	
	cjnDvmrpIsEnabled OBJECT-TYPE
              SYNTAX  INTEGER {
        	  false(0),
		   true(1)
		}	
              MAX-ACCESS  read-write
              STATUS  current
              DESCRIPTION
            	   "Enables DVMRP services on this device."
	      DEFVAL {1} 
    	  ::= { cjnDvmrpGblGroup 1 }

	cjnDvmrpNbrProbeInterval OBJECT-TYPE
              SYNTAX  INTEGER
              MAX-ACCESS  read-write
              STATUS  current
              DESCRIPTION
            	   "The DVMRP Neighbor probe interval - default to 10 seconds."
	      DEFVAL {10}
	      ::= { cjnDvmrpGblGroup 2 }

	cjnDvmrpNbrTimeout OBJECT-TYPE
              SYNTAX  INTEGER
              MAX-ACCESS  read-write
              STATUS  current
              DESCRIPTION
            	   "The DVMRP Neighbor timeout - default to 35 seconds."
	      DEFVAL {35}
	      ::= { cjnDvmrpGblGroup 3 }

	cjnDvmrpMinFlashUpdateInterval OBJECT-TYPE
              SYNTAX  INTEGER
              MAX-ACCESS  read-write
              STATUS  current
              DESCRIPTION
            	   "Minimum route flash update period - default to 5 seconds."
	      DEFVAL {5}
	      ::= { cjnDvmrpGblGroup 4 }

	cjnDvmrpMaxRoutes OBJECT-TYPE
              SYNTAX  INTEGER
              MAX-ACCESS  read-write
              STATUS  current
              DESCRIPTION
            	   "Maximum number of routes allowed - default 5000."
	      DEFVAL {5000}
	      ::= { cjnDvmrpGblGroup 5 }

	cjnDvmrpRteReportInterval OBJECT-TYPE
              SYNTAX  INTEGER
              MAX-ACCESS  read-write
              STATUS  current
              DESCRIPTION
            	   "The DVMRP Route report interval - default to 60."
	      DEFVAL {60}
	      ::= { cjnDvmrpGblGroup 6 }

	cjnDvmrpRteExpireTime OBJECT-TYPE
              SYNTAX  INTEGER
              MAX-ACCESS  read-write
              STATUS  current
              DESCRIPTION
            	   "The DVMRP Route expirartion time - default to 140 seconds."
	      DEFVAL {140}
	      ::= { cjnDvmrpGblGroup 7 }

	cjnDvmrpRteHoldTime OBJECT-TYPE
              SYNTAX  INTEGER
              MAX-ACCESS  read-write
              STATUS  current
              DESCRIPTION
            	   "The DVMRP Route holddown period - default to 120 seconds."
	      DEFVAL {120}
	      ::= { cjnDvmrpGblGroup 8 }

	cjnDvmrpPruneLifeTime OBJECT-TYPE
              SYNTAX  INTEGER (1..7200)
              MAX-ACCESS  read-write
              STATUS  current
              DESCRIPTION
            	   "The DVMRP Upstream prune message lifetime - default to 7200 seconds (1-7200)."
	      DEFVAL {7200}
	      ::= { cjnDvmrpGblGroup 9 }

	cjnDvmrpPruneRxmitTime OBJECT-TYPE
              SYNTAX  INTEGER
              MAX-ACCESS  read-write
              STATUS  current
              DESCRIPTION
            	   "The DVMRP Prune message retransmit interval - default ot 3 seconds."
	      DEFVAL {3}
	      ::= { cjnDvmrpGblGroup 10 }

	cjnDvmrpGraftRxmitTime OBJECT-TYPE
              SYNTAX  INTEGER
              MAX-ACCESS  read-write
              STATUS  current
              DESCRIPTION
            	   "The DVMRP Graft message retransmit interval - default to 5 seconds."
	      DEFVAL {5}
	      ::= { cjnDvmrpGblGroup 11 }


	cjnDvmrpGlobalStatsReset  OBJECT-TYPE
	    SYNTAX  INTEGER {
	      enable(1),
	      disable(2)
	    }	
	   MAX-ACCESS read-write
	   STATUS current
	   DESCRIPTION
	   "When set to the value enable (1) all DVMRP statistics are
	  reset to zero after which the value of this MIB object returns to disable(2)"
	   ::= { cjnDvmrpGblGroup 12 }

-- The following are in the Web data structure but commented out. They may be added later
--
--	cjnDvmrpRteExpireTime OBJECT-TYPE
--            SYNTAX  INTEGER
--            MAX-ACCESS  read-write
--            STATUS  current
--            DESCRIPTION
--          	   "Route expiration period - default to 200 seconds."
--     	  DEFVAL {200}
--        ::= { cjnDvmrpGblGroup 12 }
--
-- cjnDvmrpIsLeafRouter OBJECT-TYPE
--            SYNTAX  INTEGER {
--      	  false(0),
--                true(1) 
--		}	
--            MAX-ACCESS  read-write
--            STATUS  current
--            DESCRIPTION
--          	   "Router is a leaf - is experimental and default to FALSE."
--        DEFVAL {0}
--  	  ::= { cjnDvmrpGblGroup 13 }
--
-- cjnDvmrpCanPrune OBJECT-TYPE
--            SYNTAX  INTEGER {
--      	  false(0),
--                true(1) 
--		}	
--            MAX-ACCESS  read-write
--            STATUS  current
--            DESCRIPTION
--          	   "Router has prune capabilities - default to TRUE."
--        DEFVAL {1}
--  	  ::= { cjnDvmrpGblGroup 14 }
--
-- cjnDvmrpCanGenID OBJECT-TYPE
--            SYNTAX  INTEGER {
--      	  false(0),
--                true(1) 
--		}
--            MAX-ACCESS  read-write
--            STATUS  current
--            DESCRIPTION
--          	   "Router can generate generation IDs - default to TRUE."
--        DEFVAL {1}
--  	  ::= { cjnDvmrpGblGroup 15 }
--
-- cjnDvmrpCanMtrace OBJECT-TYPE
--            SYNTAX  INTEGER {
--      	  false(0),
--                true(1) 
--		}
--            MAX-ACCESS  read-write
--            STATUS  current
--            DESCRIPTION
--          	   "Router supports MTRACE requests - deafault to TRUE."
--        DEFVAL {1}
--  	  ::= { cjnDvmrpGblGroup 16 }
--
-- cjnDvmrpCanSNMP OBJECT-TYPE
--            SYNTAX  INTEGER {
--      	  false(0),
--                true(1) 
--		}
--            MAX-ACCESS  read-write
--            STATUS  current
--            DESCRIPTION
--          	   "Router supports SNMP queries - default to TRUE."
--        DEFVAL {1}
--  	  ::= { cjnDvmrpGblGroup 17 }
--
-- cjnDvmrpWillEncapsulate OBJECT-TYPE
--            SYNTAX  INTEGER {
--      	  false(0),
--                true(1) 
--		}
--            MAX-ACCESS  read-write
--            STATUS  current
--            DESCRIPTION
--          	   "Router encapsulates all as IP-IP over tunnel interfaces. default true."
--        DEFVAL {1}
--  	  ::= { cjnDvmrpGblGroup 18 }

-- DVMRP Global Statistics Group
--
	cjnDvmrpStatsGroup	OBJECT IDENTIFIER ::= { cjnDvmrp 2 }

	cjnDvmrpRxProbe OBJECT-TYPE
              SYNTAX  INTEGER
              MAX-ACCESS  read-write
              STATUS  current
              DESCRIPTION
            	   "Number of Probe packets received."
	      ::= { cjnDvmrpStatsGroup 1 }

	cjnDvmrpTxProbe OBJECT-TYPE
              SYNTAX  INTEGER
              MAX-ACCESS  read-write
              STATUS  current
              DESCRIPTION
            	   "Number of Probe packets transmitted."
	      ::= { cjnDvmrpStatsGroup 2 }

	cjnDvmrpRxReport OBJECT-TYPE
              SYNTAX  INTEGER
              MAX-ACCESS  read-write
              STATUS  current
              DESCRIPTION
            	   "Number of Route Report packets received."
	      ::= { cjnDvmrpStatsGroup 3 }

	cjnDvmrpTxReport OBJECT-TYPE
              SYNTAX  INTEGER
              MAX-ACCESS  read-write
              STATUS  current
              DESCRIPTION
            	   "Number of Route Report packets transmitted."
	      ::= { cjnDvmrpStatsGroup 4 }

	cjnDvmrpRxPrune OBJECT-TYPE
              SYNTAX  INTEGER
              MAX-ACCESS  read-write
              STATUS  current
              DESCRIPTION
            	   "Number of Prune packets received."
	      ::= { cjnDvmrpStatsGroup 5 }

	cjnDvmrpTxPrune OBJECT-TYPE
              SYNTAX  INTEGER
              MAX-ACCESS  read-write
              STATUS  current
              DESCRIPTION
            	   "Number of Prune packets transmitted."
	      ::= { cjnDvmrpStatsGroup 6 }

	cjnDvmrpRxGraft OBJECT-TYPE
              SYNTAX  INTEGER
              MAX-ACCESS  read-write
              STATUS  current
              DESCRIPTION
            	   "Number of Graft packets received."
	      ::= { cjnDvmrpStatsGroup 7 }

	cjnDvmrpTxGraft OBJECT-TYPE
              SYNTAX  INTEGER
              MAX-ACCESS  read-write
              STATUS  current
              DESCRIPTION
            	   "Number of Graft packets transmitted."
	      ::= { cjnDvmrpStatsGroup 8 }

	cjnDvmrpRxGraftAck OBJECT-TYPE
              SYNTAX  INTEGER
              MAX-ACCESS  read-write
              STATUS  current
              DESCRIPTION
            	   "Number of Graft Acknowledgment packets received."
	      ::= { cjnDvmrpStatsGroup 9 }

	cjnDvmrpTxGraftAck OBJECT-TYPE
              SYNTAX  INTEGER
              MAX-ACCESS  read-write
              STATUS  current
              DESCRIPTION
            	   "Number of Graft Acknowledgment packets transmitted."
	      ::= { cjnDvmrpStatsGroup 10 }

	cjnDvmrpRxUnknownCode OBJECT-TYPE
              SYNTAX  INTEGER
              MAX-ACCESS  read-write
              STATUS  current
              DESCRIPTION
            	   "Number of received DVMRP packets with unknown codes."
	      ::= { cjnDvmrpStatsGroup 11 }

	cjnDvmrpNumValidRts OBJECT-TYPE
              SYNTAX  INTEGER
              MAX-ACCESS  read-write
              STATUS  current
              DESCRIPTION
            	   "Number of currently valid (met<32) local and received routes on this node."
	      ::= { cjnDvmrpStatsGroup 12 }

	cjnDvmrpNumRts OBJECT-TYPE
              SYNTAX  INTEGER
              MAX-ACCESS  read-write
              STATUS  current
              DESCRIPTION
            	   "Total number of local and received routes on this node."
	      ::= { cjnDvmrpStatsGroup 13 }

	cjnDvmrpNumTrigdRts OBJECT-TYPE
              SYNTAX  INTEGER
              MAX-ACCESS  read-write
              STATUS  current
              DESCRIPTION
            	   "Number of triggered routes received on this node."
	      ::= { cjnDvmrpStatsGroup 14 }

	cjnDvmrpLastRep OBJECT-TYPE
              SYNTAX  INTEGER
              MAX-ACCESS  read-write
              STATUS  current
              DESCRIPTION
            	   "Time of last route report transmitted on this node."
	      ::= { cjnDvmrpStatsGroup 15 }	


-- DVMRP Interface Group
--
	cjnDvmrpIfGroup		OBJECT IDENTIFIER ::= { cjnDvmrp 3 }

	cjnDvmrpIfTable OBJECT-TYPE
              SYNTAX  SEQUENCE OF CjnDvmrpIfEntry
              MAX-ACCESS  not-accessible
              STATUS  current
              DESCRIPTION
                      "A list of Cajun DVMRP interface entries.  The number of
                      entries is given by the value of cjnDvmrpIfNumber."
              ::= { cjnDvmrpIfGroup 1 }

	
        cjnDvmrpIfEntry OBJECT-TYPE
              SYNTAX  CjnDvmrpIfEntry
              MAX-ACCESS  not-accessible
              STATUS  current
              DESCRIPTION
                      "An cajun DVMRP Interface instance "
              INDEX   { cjnDvmrpIfIndex }
              ::= { cjnDvmrpIfTable 1 }

        CjnDvmrpIfEntry ::=
              SEQUENCE {
		cjnDvmrpIfIndex
			INTEGER,
		cjnDvmrpIfRowStatus
			RowStatus,	
		cjnDvmrpIfType
			INTEGER,
		cjnDvmrpIfTnAddress
			IpAddress,
		cjnDvmrpIfMetric
			INTEGER,
		cjnDvmrpIfScope
			INTEGER,
		cjnDvmrpPruneSource
			INTEGER
		}

	cjnDvmrpIfIndex OBJECT-TYPE
              SYNTAX  INTEGER
              MAX-ACCESS  not-accessible
              STATUS  current
              DESCRIPTION
                      "The globally unique INDEX that identifes this interface. This number
                    	MUST corrolate with the cjnIpIfIndex."
	      ::= { cjnDvmrpIfEntry 1 } 

	cjnDvmrpIfRowStatus OBJECT-TYPE
              SYNTAX  RowStatus	
              MAX-ACCESS  read-create
              STATUS  current
              DESCRIPTION
                      "The Status of this entry in the table.  Note the
		available states: 
		active(1), -- Obviously Active on this interface.
		notInService(2) -- Configured on Interface but disabled.
		notReady(3), -- Interface entry NOT FULLY configured.
		createAndGo(4), -- NOT SUPPORTED. 
		createAndWait(5)  
		or destroy(6) "
	      ::= { cjnDvmrpIfEntry 2 }

	cjnDvmrpIfType OBJECT-TYPE
              SYNTAX  INTEGER {
		broadcast(0),
		nonEncapsulatedTunnel(1),
		ipIpTunnel(2)
		}	
              MAX-ACCESS  read-create
              STATUS  current
              DESCRIPTION
                      "The Interface type. 0=broadcast,1=nonEncapsulatedTunnel,2=IPIPTunnel. default is 0."
	      DEFVAL {0}
	      ::= { cjnDvmrpIfEntry 3 }

	cjnDvmrpIfTnAddress OBJECT-TYPE
              SYNTAX  IpAddress
              MAX-ACCESS  read-create
              STATUS  current
              DESCRIPTION
                      "The Tunnel Address associated with this DVMRP interface."
	      ::= { cjnDvmrpIfEntry 4 } 

	cjnDvmrpIfMetric OBJECT-TYPE
              SYNTAX  INTEGER ( 1..31 )
              MAX-ACCESS  read-create
              STATUS  current
              DESCRIPTION
                      "Interface Metric (hop count) - 1-31. default is 1."
	      DEFVAL {1}
	      ::= { cjnDvmrpIfEntry 5 }

	cjnDvmrpIfScope OBJECT-TYPE
              SYNTAX  INTEGER {
		scope0(0),
		scope127(1),
		scope255(2)
		}	
              MAX-ACCESS  read-create
              STATUS  current
              DESCRIPTION
                      "Interface scope 0=0, 1=127, 2=255. default is 0."
	      DEFVAL {0}
	      ::= { cjnDvmrpIfEntry 6 }

	cjnDvmrpPruneSource OBJECT-TYPE
              SYNTAX  INTEGER {
		hostAddr(1),
		networkAddr(0)
		}	
              MAX-ACCESS  read-create
              STATUS  current
              DESCRIPTION
                    "By default Full Src Host addr is in Prune pkt (not just Net portion) default True."
	      DEFVAL {1}
	      ::= { cjnDvmrpIfEntry 7 }

-- DVMRP Interface Statistic Group
--
	cjnDvmrpIfStatTable OBJECT-TYPE
              SYNTAX  SEQUENCE OF CjnDvmrpIfStatEntry
              MAX-ACCESS  not-accessible
              STATUS  current
              DESCRIPTION
                      "A list of Cajun DVMRP interface Statistic entries.  The number
		      of entries is given by the value of cjnDvmrpIfNumber."
              ::= { cjnDvmrpIfGroup 2 }

	
        cjnDvmrpIfStatEntry OBJECT-TYPE
              SYNTAX  CjnDvmrpIfStatEntry
              MAX-ACCESS  not-accessible
              STATUS  current
              DESCRIPTION
                      "An cajun DVMRP Interface Statistics instance "
              INDEX   { cjnDvmrpIfStatIndex }
              ::= { cjnDvmrpIfStatTable 1 }

        CjnDvmrpIfStatEntry ::=
              SEQUENCE {
		cjnDvmrpIfStatIndex
			INTEGER,
		cjnDvmrpIfBadPackets
			INTEGER,
		cjnDvmrpIfBadRoutes
			INTEGER,
		cjnDvmrpIfNbrCount
			INTEGER,
		cjnDvmrpIfSentRoutes
			INTEGER,
		cjnDvmrpIfState
			INTEGER
		}

	cjnDvmrpIfStatIndex OBJECT-TYPE
              SYNTAX  INTEGER
              MAX-ACCESS  not-accessible
              STATUS  current
              DESCRIPTION
                      "The globally unique INDEX that identifes this interface. This number
                    	MUST corrolate with the cjnIpIfIndex."
	      ::= { cjnDvmrpIfStatEntry 1 } 

  	cjnDvmrpIfBadPackets OBJECT-TYPE
              SYNTAX  INTEGER
              MAX-ACCESS  read-write
              STATUS  current
              DESCRIPTION
            	   "Number of empty (no routes in pkt) Route Report packets received on this interface."
	      ::= { cjnDvmrpIfStatEntry 2 }

  	cjnDvmrpIfBadRoutes OBJECT-TYPE
              SYNTAX  INTEGER
              MAX-ACCESS  read-write
              STATUS  current
              DESCRIPTION
            	   "Number of routes with an invalid metric received on this interface."
	      ::= { cjnDvmrpIfStatEntry 3 }

  	cjnDvmrpIfNbrCount OBJECT-TYPE
              SYNTAX  INTEGER
              MAX-ACCESS  read-write
              STATUS  current
              DESCRIPTION
            	   "Number of neighbor DVMRP Router(s) on this interface."
	      ::= { cjnDvmrpIfStatEntry 4 }

  	cjnDvmrpIfSentRoutes OBJECT-TYPE
              SYNTAX  INTEGER
              MAX-ACCESS  read-write
              STATUS  current
              DESCRIPTION
            	   "Number of Route Report packets sent on this interface."
	      ::= { cjnDvmrpIfStatEntry 5 }

  	cjnDvmrpIfState OBJECT-TYPE
              SYNTAX  INTEGER
              MAX-ACCESS  read-only
              STATUS  current
              DESCRIPTION
                      "The Status of this entry in the table.  Note the
		available states: 
		active(1), -- Obviously Active on this interface.
		notInService(2) -- Configured on Interface but disabled.
		notReady(3) -- Interface entry NOT FULLY configured."
	      ::= { cjnDvmrpIfStatEntry 6 }
END
