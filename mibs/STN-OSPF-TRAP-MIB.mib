-- *****************************************************************
--
-- stn-ospft.mib: 
--                Spring Tide Networks OSPF Traps file.
--
--
--      Copyright (c) 1999, 2000 by Spring Tide Networks, Inc.
--                      ALL RIGHTS RESERVED       
--
-- *****************************************************************

-- MIB Object definitions for Spring Tide Network OSPF Trap Extensions 


STN-OSPF-TRAP-MIB DEFINITIONS ::= BEGIN

    IMPORTS
        MODULE-IDENTITY, OBJECT-TYPE, NOTIFICATION-TYPE, IpAddress
            FROM SNMPv2-SMI

        MODULE-COMPLIANCE, OBJECT-GROUP
            FROM SNMPv2-CONF

        ospfRouterId, ospfIfIpAddress, ospfAddressLessIf, ospfIfState,
        ospfVirtIfAreaId, ospfVirtIfNeighbor, ospfVirtIfState,
        ospfNbrIpAddr, ospfNbrAddressLessIndex, ospfNbrRtrId,
        ospfNbrState, ospfVirtNbrArea, ospfVirtNbrRtrId, ospfVirtNbrState,
        ospfLsdbType, ospfLsdbLsid, ospfLsdbRouterId, ospfLsdbAreaId,
        ospfExtLsdbLimit, ospf
            FROM OSPF-MIB

        ospfConfigErrorType, ospfPacketType, ospfPacketSrc 
            FROM OSPF-TRAP-MIB

        stnNotification
            FROM SPRING-TIDE-NETWORKS-SMI

        stnOspfTraps
            FROM STN-IPROUTING-MIB

        stnRouterIndex
            FROM STN-ROUTER-MIB;


    stnOspfTrap    MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes traps for the OSPF
                         Version 2 Protocol."
        ::= { stnOspfTraps 1 }


    --
    -- Top Level STN OSPF Trap MIB Objects
    --
    stnOspfTrapVars		OBJECT IDENTIFIER ::= { stnOspfTrap 1 }
    stnOspfNotificationPrefix   OBJECT IDENTIFIER ::= { stnOspfTrap 2 }
    stnOspfNotification		OBJECT IDENTIFIER ::= { stnOspfNotificationPrefix 0 }


    --
    -- STN OSPF Traps / Notifications
    -- 

    stnOspfVirtIfStateChange NOTIFICATION-TYPE
        OBJECTS     {   stnRouterIndex, 
                        ospfRouterId, -- The originator of the trap
                        ospfVirtIfAreaId,
                        ospfVirtIfNeighbor,
                        ospfVirtIfState  -- The new state
                    }
        STATUS      current
        DESCRIPTION
            "A stnOspfVirtIfStateChange trap signifies that there
            has been a change in the state of an OSPF virtual interface.
            This trap should be generated when  the  interface  state  
            regresses  (e.g., goes from Point-to-Point to Down) or progresses
            to  a  terminal state (i.e., Point-to-Point).
            The generation of this trap can be controlled by the OSPFTraps 
            configuration object."
        ::= { stnOspfNotification 1 }

    stnOspfNbrStateChange NOTIFICATION-TYPE
        OBJECTS {   stnRouterIndex,
                    ospfRouterId, -- The originator of the trap
                    ospfNbrIpAddr,
                    ospfNbrAddressLessIndex,
                    ospfNbrRtrId,
                    ospfNbrState  -- The new state
                }
        STATUS      current
        DESCRIPTION
            "A stnOspfNbrStateChange trap signifies that there has been a 
            change in the state of a non-virtual OSPF neighbor. This trap
            should be generated when the neighbor state regresses
            (e.g., goes from Attempt or Full  to  1-Way  or Down) or progresses
            to a terminal state (e.g., 2-Way or Full).  When an neighbor 
            transitions from or to Full on non-broadcast multi-access and 
            broadcast networks, the trap should be generated by the designated
            router. A designated router transitioning to Down will be noted by
            ospfIfStateChange.
            The generation of this trap can be controlled by the OSPFTraps 
            configuration object."
        ::= { stnOspfNotification 2 }

    stnOspfVirtNbrStateChange NOTIFICATION-TYPE
        OBJECTS {   stnRouterIndex,
                    ospfRouterId, -- The originator of the trap
                    ospfVirtNbrArea,
                    ospfVirtNbrRtrId,
                    ospfVirtNbrState  -- The new state
                }
        STATUS      current
        DESCRIPTION
            "A stnOspfVirtNbrStateChange trap signifies that there has been a 
            change in the state of an OSPF virtual neighbor. This trap should 
            be generated when the neighbor state regresses (e.g., goes from 
            Attempt or Full to 1-Way or Down) or progresses to a terminal 
            state (e.g., Full).
            The generation of this trap can be controlled by the OSPFTraps 
            configuration object."
        ::= { stnOspfNotification 3 }

    stnOspfIfConfigError NOTIFICATION-TYPE
        OBJECTS {   stnRouterIndex,
                    ospfRouterId, -- The originator of the trap
                    ospfIfIpAddress,
                    ospfAddressLessIf,
                    ospfPacketSrc,  -- The source IP address
                    ospfConfigErrorType, -- Type of error
                    ospfPacketType
                }
        STATUS      current
        DESCRIPTION
            "An stnOspfIfConfigError trap signifies that a packet has been 
            received on a non-virtual interface from a router whose 
            configuration parameters conflict with this router's 
            configuration parameters. Note that the event optionMismatch  
            should cause a trap only if it prevents an adjacency from forming.
            The generation of this trap can be controlled by the OSPFTraps 
            configuration object."
        ::= { stnOspfNotification 4 }

    stnOspfVirtIfConfigError NOTIFICATION-TYPE
        OBJECTS {   stnRouterIndex,
                    ospfRouterId, -- The originator of the trap
                    ospfVirtIfAreaId,
                    ospfVirtIfNeighbor,
                    ospfConfigErrorType, -- Type of error
                    ospfPacketType
                }
        STATUS      current
        DESCRIPTION
            "A stnOspfVirtIfConfigError trap signifies that a packet has been 
            received on a virtual interface from a router whose configuration
            parameters conflict with this router's configuration parameters. 
            Note that the event optionMismatch should cause a trap only if it
            prevents an adjacency from forming.
            The generation of this trap can be controlled by the OSPFTraps 
            configuration object."
        ::= { stnOspfNotification 5 }

    stnOspfIfAuthFailure NOTIFICATION-TYPE
        OBJECTS {   stnRouterIndex,
                    ospfRouterId, -- The originator of the trap
                    ospfIfIpAddress,
                    ospfAddressLessIf,
                    ospfPacketSrc,  -- The source IP address
                    ospfConfigErrorType, -- authTypeMismatch or
                                         -- authFailure
                    ospfPacketType
                }
        STATUS      current
        DESCRIPTION
            "A stnOspfIfAuthFailure trap signifies that a packet has been 
            received on a non-virtual interface from a router whose 
            authentication key or authentication type conflicts with this 
            router's authentication key or authentication type.
            The generation of this trap can be controlled by the OSPFTraps 
            configuration object."
        ::= { stnOspfNotification 6 }

    stnOspfVirtIfAuthFailure NOTIFICATION-TYPE
        OBJECTS {   stnRouterIndex,
                    ospfRouterId, -- The originator of the trap
                    ospfVirtIfAreaId,
                    ospfVirtIfNeighbor,
                    ospfConfigErrorType, -- authTypeMismatch or
                                         -- authFailure
                    ospfPacketType
                }
        STATUS      current
        DESCRIPTION
            "A stnOspfVirtIfAuthFailure trap signifies that a packet has been 
            received on a virtual interface from a router whose authentication
            key or authentication type conflicts with this router's
            authentication key or authentication type.
            The generation of this trap can be controlled by the OSPFTraps 
            configuration object."
        ::= { stnOspfNotification 7 }

    stnOspfIfRxBadPacket NOTIFICATION-TYPE
        OBJECTS {   stnRouterIndex,
                    ospfRouterId, -- The originator of the trap
                    ospfIfIpAddress,
                    ospfAddressLessIf,
                    ospfPacketSrc,  -- The source IP address
                    ospfPacketType
                }
        STATUS             current
        DESCRIPTION
            "A stnOspfIfRxBadPacket trap signifies that an OSPF packet has 
            been received on a non-virtual interface that cannot be parsed.
            The generation of this trap can be controlled by the OSPFTraps 
            configuration object."
        ::= { stnOspfNotification 8 }

    stnOspfVirtIfRxBadPacket NOTIFICATION-TYPE
        OBJECTS {   stnRouterIndex,
                    ospfRouterId, -- The originator of the trap
                    ospfVirtIfAreaId,
                    ospfVirtIfNeighbor,
                    ospfPacketType
                }
        STATUS      current
        DESCRIPTION
            "An stnOspfVirtIfRxBadPacket trap signifies that an OSPF packet 
            has been received on a virtual interface that cannot be parsed.
            The generation of this trap can be controlled by the OSPFTraps 
            configuration object."
        ::= { stnOspfNotification 9 }

    stnOspfTxRetransmit NOTIFICATION-TYPE
        OBJECTS {   stnRouterIndex,
                    ospfRouterId, -- The originator of the trap
                    ospfIfIpAddress,
                    ospfAddressLessIf,
                    ospfNbrRtrId, -- Destination
                    ospfPacketType,
                    ospfLsdbType,
                    ospfLsdbLsid,
                    ospfLsdbRouterId
                }
        STATUS      current
        DESCRIPTION
            "A stnOspfTxRetransmit trap signifies than an OSPF packet has been 
            retransmitted on a non-virtual interface. All packets that may be 
            retransmitted are associated with an LSDB entry. The LS type, 
            LS ID, and Router ID are used to identify the LSDB entry.
            The generation of this trap can be controlled by the OSPFTraps 
            configuration object."
        ::= { stnOspfNotification 10 }

    stnOspfVirtIfTxRetransmit NOTIFICATION-TYPE
        OBJECTS {   stnRouterIndex,
                    ospfRouterId, -- The originator of the trap
                    ospfVirtIfAreaId,
                    ospfVirtIfNeighbor,
                    ospfPacketType,
                    ospfLsdbType,
                    ospfLsdbLsid,
                    ospfLsdbRouterId
                }
        STATUS      current
        DESCRIPTION
            "A stnOspfVirtIfTxRetransmit trap signifies than an OSPF packet 
            has been retransmitted on a virtual interface. All packets that 
            may be retransmitted are associated with an LSDB entry. The LS 
            type, LS ID, and Router ID are used to identify the LSDB entry.
            The generation of this trap can be controlled by the OSPFTraps 
            configuration object."
        ::= { stnOspfNotification 11 }

    stnOspfOriginateLsa NOTIFICATION-TYPE
        OBJECTS {   stnRouterIndex,
                    ospfRouterId, -- The originator of the trap
                    ospfLsdbAreaId,  -- 0.0.0.0 for AS Externals
                    ospfLsdbType,
                    ospfLsdbLsid,
                    ospfLsdbRouterId
                  }
        STATUS      current
        DESCRIPTION
            "A stnOspfOriginateLsa trap signifies that a new LSA has been 
            originated by this router. This trap should not be invoked for 
            simple refreshes of LSAs (which happens every 30 minutes), but
            instead will only be invoked when an LSA is (re)originated due to 
            a topology change.  Additionally, this trap does not include LSAs 
            that are  being  flushed  because they have reached MaxAge.
            The generation of this trap can be controlled by the OSPFTraps 
            configuration object."
        ::= { stnOspfNotification 12 }

    stnOspfMaxAgeLsa NOTIFICATION-TYPE
        OBJECTS {   stnRouterIndex,
                    ospfRouterId, -- The originator of the trap
                    ospfLsdbAreaId,  -- 0.0.0.0 for AS Externals
                    ospfLsdbType,
                    ospfLsdbLsid,
                    ospfLsdbRouterId
                  }
        STATUS      current
        DESCRIPTION
            "A stnOspfMaxAgeLsa trap signifies that one of the LSA in the 
            router's link-state database has aged to MaxAge.
            The generation of this trap can be controlled by the OSPFTraps 
            configuration object."
        ::= { stnOspfNotification 13 }

    stnOspfLsdbOverflow NOTIFICATION-TYPE
        OBJECTS {   stnRouterIndex,
                    ospfRouterId, -- The originator of the trap
                    ospfExtLsdbLimit
                }
        STATUS      current
        DESCRIPTION
            "A stnOspfLsdbOverflow trap signifies that the number of LSAs in 
            the router's link-state database has exceeded ospfExtLsdbLimit.
            The generation of this trap can be controlled by the OSPFTraps 
            configuration object."
       ::= { stnOspfNotification 14 }

    stnOspfLsdbApproachingOverflow NOTIFICATION-TYPE
        OBJECTS {   stnRouterIndex,
                    ospfRouterId, -- The originator of the trap
                    ospfExtLsdbLimit
                  }
        STATUS      current
        DESCRIPTION
            "A stnOspfLsdbApproachingOverflow trap signifies that the number 
            of LSAs in the router's link state database has exceeded ninety 
            percent of ospfExtLsdbLimit.
            The generation of this trap can be controlled by the OSPFTraps 
            configuration object."
        ::= { stnOspfNotification 15 }

    stnOspfIfStateChange NOTIFICATION-TYPE
        OBJECTS {   stnRouterIndex,
                    ospfRouterId, -- The originator of the trap
                    ospfIfIpAddress,
                    ospfAddressLessIf,
                    ospfIfState   -- The new state
                  }
        STATUS      current
        DESCRIPTION
            "A stnOspfIfStateChange trap signifies that there has been a 
            change in the state of a non-virtual OSPF interface. This trap 
            should be generated when the interface state regresses 
            (e.g., goes from Dr to Down) or progresses to a terminal state
            (i.e., Point-to-Point, DR Other, Dr, or Backup).
            The generation of this trap can be controlled by the OSPFTraps 
            configuration object."
        ::= { stnOspfNotification 16 }


END
