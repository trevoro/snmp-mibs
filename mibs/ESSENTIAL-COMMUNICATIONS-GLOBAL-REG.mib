--#########################################################################
ESSENTIAL-COMMUNICATIONS-GLOBAL-REG DEFINITIONS ::= BEGIN
--#########################################################################

--Summary for easy look up.
--See the EPS-16.mib file for the offical version.

IMPORTS
	enterprises
		FROM RFC1155-SMI;

--ecGlobalRegMod MODULE-IDENTITY
--	LAST-UPDATED	"9703210000Z"
--	ORGANIZATION	"Essential Communications"
--	CONTACT-INFO	"Marck Doppke
--					email: marck@esscom.com"
--	DESCRIPTION		
--					"Essential Communications central registration"
--	::= { enterprises 2159 1 1 1 1 }

--This module. Note that it is down inside the name space it is defining.
--ecGlobalRegMod          OBJECT IDENTIFIER ::= { enterprises 2159 1 1 1 1 }

--the root of the framework sub-tree for Essential Communications.
--This format follows one excepted convention for frameworks.
essentialCommunications OBJECT IDENTIFIER ::= { enterprises essCom(2159) }
ecRoot                  OBJECT IDENTIFIER ::= { essentialCommunications 1 }

--sub-tree for registrations, which includes modules.
--This holds the OBJECT INDENTIFERs used to identify pieces of harware as
--well as logical items such as agent resources.
ecRegistration OBJECT IDENTIFIER                  ::= { ecRoot 1 }
	
	--modules
	ecModules OBJECT IDENTIFIER          ::= { ecRegistration 1 } 

--sub-tree for company-wide objects and events.
ecGeneric OBJECT IDENTIFIER              ::= { ecRoot 2 } 

--sub-tree for product-specific objects and events.
ecProducts  OBJECT IDENTIFIER            ::= { ecRoot 3 } 

--sub-tree for agent profiles
ecAgentProfiles OBJECT IDENTIFIER                 ::= { ecRoot 4 } 

--sub-tree for requirement specifications
ecRequirements OBJECT IDENTIFIER                 ::= { ecRoot 5 } 

--sub-tree for experiments
ecExperimental OBJECT IDENTIFIER                 ::= { ecRoot 6 } 

--product families
ecNICReg OBJECT IDENTIFIER       ::= { ecRegistration 2 } 
ecMICReg OBJECT IDENTIFIER       ::= { ecRegistration 3 } 
ecSwitchReg OBJECT IDENTIFIER    ::= { ecRegistration 4 } 

--Products
--The registration of the actual hardware.
pmicHIPPIReg	OBJECT IDENTIFIER
--	STATUS		mandatory
--	DESCRIPTION	"The parrallel HIPPI card."
	::= { ecMICReg 1 } 

smicHIPPISWLReg 	OBJECT IDENTIFIER
--	STATUS		mandatory
--	DESCRIPTION	"The short wave length serial HIPPI card."
	::= { ecMICReg 2 } 

smicHIPPILWLReg 	OBJECT IDENTIFIER
--	STATUS		mandatory
--	DESCRIPTION	"The long wave length serial HIPPI card."
	::= { ecMICReg 3 } 

ecEPS16Reg 			OBJECT IDENTIFIER 
--	STATUS			mandatory
--	DESCRIPTION		"The EPS-16 HIPPI switch."
	::= { ecSwitchReg 1 } 

END
