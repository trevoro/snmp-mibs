ChrComPmSonetSNT-L-Current-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmSonet				FROM  Chromatis-MIB
	chrComIfifIndex					FROM  ChrComIfifTable-MIB
	TruthValue				FROM  ChrTyp-MIB
	Gauge32				FROM  SNMPv2-SMI;

-- chrComPmSonetSNT-L-Current Table

chrComPmSonetSNT-L-CurrentTable		OBJECT-TYPE
	SYNTAX		SEQUENCE OF ChrComPmSonetSNT-L-CurrentEntry
	MAX-ACCESS	not-accessible
	STATUS		current
	DESCRIPTION
	""
	::= { chrComPmSonet 4}

chrComPmSonetSNT-L-CurrentEntry		OBJECT-TYPE
	SYNTAX		ChrComPmSonetSNT-L-CurrentEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "SNT-L-Current"
	::= { chrComPmSonetSNT-L-CurrentTable  1 }

ChrComPmSonetSNT-L-CurrentEntry  ::=
	SEQUENCE  {
	chrComPmSonetSuspectedInterval	TruthValue,
	chrComPmSonetElapsedTime		Unsigned32	(0..4294967295),
	chrComPmSonetSuppressedIntrvls	Gauge32			(0..4294967295),
	chrComPmSonetStatus			Gauge32			(0..4294967295),
	chrComPmSonetES			Gauge32			(0..4294967295),
	chrComPmSonetSES			Gauge32			(0..4294967295),
	chrComPmSonetCV			Gauge32			(0..4294967295),
	chrComPmSonetUAS			Gauge32			(0..4294967295),
	chrComPmSonetThresholdProfIndex	Unsigned32	(0..4294967295),
	chrComPmSonetResetPmCountersAction	TruthValue
}

chrComPmSonetSuspectedInterval 	OBJECT-TYPE
	SYNTAX		TruthValue
	MAX-ACCESS 	read-only
	STATUS 		current
	DESCRIPTION
	""
	::= { chrComPmSonetSNT-L-CurrentEntry  1 }

chrComPmSonetElapsedTime 	OBJECT-TYPE
	SYNTAX		Unsigned32	(0..4294967295)
	MAX-ACCESS 	read-only
	STATUS 		current
	DESCRIPTION
	""
	::= { chrComPmSonetSNT-L-CurrentEntry  2 }

chrComPmSonetSuppressedIntrvls 	OBJECT-TYPE
	SYNTAX		Gauge32			(0..4294967295)
	MAX-ACCESS 	read-only
	STATUS 		current
	DESCRIPTION
	""
	::= { chrComPmSonetSNT-L-CurrentEntry  3 }

chrComPmSonetStatus 	OBJECT-TYPE
	SYNTAX		Gauge32			(0..4294967295)
	MAX-ACCESS 	read-only
	STATUS 		current
	DESCRIPTION
	""
	::= { chrComPmSonetSNT-L-CurrentEntry  4 }

chrComPmSonetES 	OBJECT-TYPE
	SYNTAX		Gauge32			(0..4294967295)
	MAX-ACCESS 	read-only
	STATUS 		current
	DESCRIPTION
	""
	::= { chrComPmSonetSNT-L-CurrentEntry  5 }

chrComPmSonetSES 	OBJECT-TYPE
	SYNTAX		Gauge32			(0..4294967295)
	MAX-ACCESS 	read-only
	STATUS 		current
	DESCRIPTION
	""
	::= { chrComPmSonetSNT-L-CurrentEntry  6 }

chrComPmSonetCV 	OBJECT-TYPE
	SYNTAX		Gauge32			(0..4294967295)
	MAX-ACCESS 	read-only
	STATUS 		current
	DESCRIPTION
	""
	::= { chrComPmSonetSNT-L-CurrentEntry  7 }

chrComPmSonetUAS 	OBJECT-TYPE
	SYNTAX		Gauge32			(0..4294967295)
	MAX-ACCESS 	read-only
	STATUS 		current
	DESCRIPTION
	""
	::= { chrComPmSonetSNT-L-CurrentEntry  8 }

chrComPmSonetThresholdProfIndex 	OBJECT-TYPE
	SYNTAX		Unsigned32	(0..4294967295)
	MAX-ACCESS 	read-only
	STATUS 		current
	DESCRIPTION
	""
	::= { chrComPmSonetSNT-L-CurrentEntry  9 }

chrComPmSonetResetPmCountersAction 	OBJECT-TYPE
	SYNTAX		TruthValue
	MAX-ACCESS 	read-write
	STATUS 		current
	DESCRIPTION
	""
	::= { chrComPmSonetSNT-L-CurrentEntry  10 }


END
