--			Ascend mibss7nmi MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSS7NMI-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsS7Profile  OBJECT IDENTIFIER ::= { configuration 121}
    mibpRITunlStatProfile  OBJECT IDENTIFIER ::= { configuration 158}

	-- The mibsS7Profile table
	--
	-- This table contains parameters for the mibsS7Profile profile
	--

    mibsS7ProfileTable	OBJECT-TYPE
	SYNTAX		SEQUENCE OF MibsS7ProfileEntry
	ACCESS		not-accessible
	STATUS		mandatory
	DESCRIPTION	"A list of mibsS7Profile profile entries."
	::= { mibsS7Profile 1 }

    mibsS7ProfileEntry	OBJECT-TYPE
	SYNTAX		MibsS7ProfileEntry
	ACCESS		not-accessible
	STATUS		mandatory
	DESCRIPTION	"A mibsS7Profile entry containing objects that
			 maps to the parameters of mibsS7Profile profile."
	INDEX		{ sS7Profile-Index-o }
	::= { mibsS7ProfileTable 1 }

    MibsS7ProfileEntry ::=
	SEQUENCE {
	    sS7Profile-Index-o
		INTEGER,
	    sS7Profile-Enabled
		INTEGER,
	    sS7Profile-ControlProtocol
		INTEGER,
	    sS7Profile-PrimaryIpAddress
		IpAddress,
	    sS7Profile-PrimaryTcpPort
		INTEGER,
	    sS7Profile-SecondaryIpAddress
		IpAddress,
	    sS7Profile-SecondaryTcpPort
		INTEGER,
	    sS7Profile-BayId
		DisplayString,
	    sS7Profile-SystemType
		DisplayString,
	    sS7Profile-TransportOptions-Type
		INTEGER,
	    sS7Profile-TransportOptions-DeviceId
		INTEGER,
	    sS7Profile-TransportOptions-T1Duration
		INTEGER,
	    sS7Profile-TransportOptions-T2Duration
		INTEGER,
	    sS7Profile-TransportOptions-T3Duration
		INTEGER,
	    sS7Profile-TransportOptions-WindowSize
		INTEGER,
	    sS7Profile-TransportOptions-AckThreshold
		INTEGER,
	    sS7Profile-TransportOptions-HeartBeat
		INTEGER,
	    sS7Profile-TransportOptions-Tos-Active
		INTEGER,
	    sS7Profile-TransportOptions-Tos-Precedence
		INTEGER,
	    sS7Profile-TransportOptions-Tos-TypeOfService
		INTEGER,
	    sS7Profile-TransportOptions-Tos-ApplyTo
		INTEGER,
	    sS7Profile-TransportOptions-Tos-MarkingType
		INTEGER,
	    sS7Profile-TransportOptions-Tos-Dscp
		DisplayString,
	    sS7Profile-UseSystemIpAddressAsSource
		INTEGER,
	    sS7Profile-IpdcSourceAdddress
		IpAddress,
	    sS7Profile-Vrouter
		DisplayString,
	    sS7Profile-CongestionControl-CongestionControlType
		INTEGER,
	    sS7Profile-CongestionControl-Cl1Level
		INTEGER,
	    sS7Profile-CongestionControl-Cl1Action
		INTEGER,
	    sS7Profile-CongestionControl-Cl2Level
		INTEGER,
	    sS7Profile-CongestionControl-Cl2Action
		INTEGER,
	    sS7Profile-SignalingHeartbeat-Enabled
		INTEGER,
	    sS7Profile-SignalingHeartbeat-Interval
		INTEGER,
	    sS7Profile-ResilienceOptions-Type
		INTEGER,
	    sS7Profile-ResilienceOptions-Duration
		INTEGER,
	    sS7Profile-PriTunnelingOptions-Enabled
		INTEGER,
	    sS7Profile-PriTunnelingOptions-Duration
		INTEGER,
	    sS7Profile-Action-o
		INTEGER
	}

    sS7Profile-Index-o	OBJECT-TYPE
	SYNTAX	INTEGER
	ACCESS	read-only
	STATUS	mandatory
	DESCRIPTION	""
	::= { mibsS7ProfileEntry 1 }

    sS7Profile-Enabled	OBJECT-TYPE
	SYNTAX	INTEGER {
		    no (1),
		    yes (2)
		}
	ACCESS	read-write
	STATUS	mandatory
	DESCRIPTION	"When set to 'no', interface to the SS7 gateway is disabled."
	::= { mibsS7ProfileEntry 2 }

    sS7Profile-ControlProtocol	OBJECT-TYPE
	SYNTAX	INTEGER {
		    asgcp (1),
		    ipdc0X (2),
		    q931Plus (3)
		}
	ACCESS	read-write
	STATUS	mandatory
	DESCRIPTION	"Control protocol between the access server and the signaling gateway."
	::= { mibsS7ProfileEntry 3 }

    sS7Profile-PrimaryIpAddress	OBJECT-TYPE
	SYNTAX	IpAddress
	ACCESS	read-write
	STATUS	mandatory
	DESCRIPTION	"IP address of the primary SS7 gateway."
	::= { mibsS7ProfileEntry 4 }

    sS7Profile-PrimaryTcpPort	OBJECT-TYPE
	SYNTAX	INTEGER
	ACCESS	read-write
	STATUS	mandatory
	DESCRIPTION	"TCP port on primary SS7 gateway."
	::= { mibsS7ProfileEntry 5 }

    sS7Profile-SecondaryIpAddress	OBJECT-TYPE
	SYNTAX	IpAddress
	ACCESS	read-write
	STATUS	mandatory
	DESCRIPTION	"IP address of the secondary SS7 gateway."
	::= { mibsS7ProfileEntry 6 }

    sS7Profile-SecondaryTcpPort	OBJECT-TYPE
	SYNTAX	INTEGER
	ACCESS	read-write
	STATUS	mandatory
	DESCRIPTION	"TCP port on the secondary SS7 gateway."
	::= { mibsS7ProfileEntry 7 }

    sS7Profile-BayId	OBJECT-TYPE
	SYNTAX	DisplayString
	ACCESS	read-write
	STATUS	mandatory
	DESCRIPTION	"Bay ID defines the bay this device belongs to. Used for registration purposes only. The content of this field is reported to the gateway during the device registration process."
	::= { mibsS7ProfileEntry 8 }

    sS7Profile-SystemType	OBJECT-TYPE
	SYNTAX	DisplayString
	ACCESS	read-write
	STATUS	mandatory
	DESCRIPTION	"Model ID and/or type of equipment. Used for device registration only. Must be listed in the database on the Gateway."
	::= { mibsS7ProfileEntry 9 }

    sS7Profile-TransportOptions-Type	OBJECT-TYPE
	SYNTAX	INTEGER {
		    ascend (1),
		    tcpEncaps2 (2)
		}
	ACCESS	read-write
	STATUS	mandatory
	DESCRIPTION	"The type of transport layer that is to be used"
	::= { mibsS7ProfileEntry 10 }

    sS7Profile-TransportOptions-DeviceId	OBJECT-TYPE
	SYNTAX	INTEGER
	ACCESS	read-write
	STATUS	mandatory
	DESCRIPTION	"A code that uniquely identifies this device to the Gateway. If multiple remote access servers are configured to use the same signaling gateway, every one of those servers must be assigned an identifier that is unique within the group."
	::= { mibsS7ProfileEntry 11 }

    sS7Profile-TransportOptions-T1Duration	OBJECT-TYPE
	SYNTAX	INTEGER
	ACCESS	read-write
	STATUS	mandatory
	DESCRIPTION	"Value of the ACK delay timer in milliseconds. This timer specifies the maximum delay for an acknowledgement when an I-frame is received. Default value is 1000 (1 second). The value must be less than T2 on the peer."
	::= { mibsS7ProfileEntry 12 }

    sS7Profile-TransportOptions-T2Duration	OBJECT-TYPE
	SYNTAX	INTEGER
	ACCESS	read-write
	STATUS	mandatory
	DESCRIPTION	"Value of the transmission timeout timer in milliseconds. This timer specifies how long this endpoint should wait for an acknowledgement. Default value is 3000 (3 seconds). The value must be greater than T1 on the peer."
	::= { mibsS7ProfileEntry 13 }

    sS7Profile-TransportOptions-T3Duration	OBJECT-TYPE
	SYNTAX	INTEGER
	ACCESS	read-write
	STATUS	mandatory
	DESCRIPTION	"Value of the persistent error timer in milliseconds. This timer specifies the maximum duration of attempts to re-establish a link before the transport layer flushes the data queues and sends an error indication up. Default value is 30000 (30 seconds)."
	::= { mibsS7ProfileEntry 14 }

    sS7Profile-TransportOptions-WindowSize	OBJECT-TYPE
	SYNTAX	INTEGER
	ACCESS	read-write
	STATUS	mandatory
	DESCRIPTION	"Maximum number of sequentially numbered data packets that can be sent while pending acknowledgement at any given time. Default value is 7."
	::= { mibsS7ProfileEntry 15 }

    sS7Profile-TransportOptions-AckThreshold	OBJECT-TYPE
	SYNTAX	INTEGER
	ACCESS	read-write
	STATUS	mandatory
	DESCRIPTION	"The threshold for triggering an acknowledgement while receiving data packets. As soon as the specified number of packets is received, an ACK is sent back regardless of the value of T1 timer. The value of this parameter may not be greater than the window size. Default value is 6."
	::= { mibsS7ProfileEntry 16 }

    sS7Profile-TransportOptions-HeartBeat	OBJECT-TYPE
	SYNTAX	INTEGER {
		    no (1),
		    yes (2)
		}
	ACCESS	read-write
	STATUS	mandatory
	DESCRIPTION	"When set to 'no', layer 2 heartbeat mechanism is not enabled."
	::= { mibsS7ProfileEntry 17 }

    sS7Profile-TransportOptions-Tos-Active	OBJECT-TYPE
	SYNTAX	INTEGER {
		    no (1),
		    yes (2)
		}
	ACCESS	read-write
	STATUS	mandatory
	DESCRIPTION	"Activate type of service for this connection."
	::= { mibsS7ProfileEntry 34 }

    sS7Profile-TransportOptions-Tos-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibsS7ProfileEntry 35 }

    sS7Profile-TransportOptions-Tos-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibsS7ProfileEntry 36 }

    sS7Profile-TransportOptions-Tos-ApplyTo	OBJECT-TYPE
	SYNTAX	INTEGER {
		    incoming (1025),
		    outgoing (2049),
		    both (3073)
		}
	ACCESS	read-write
	STATUS	mandatory
	DESCRIPTION	"Define how the type-of-service applies to data flow for this connection."
	::= { mibsS7ProfileEntry 37 }

    sS7Profile-TransportOptions-Tos-MarkingType	OBJECT-TYPE
	SYNTAX	INTEGER {
		    precedenceTos (1),
		    dscp (2)
		}
	ACCESS	read-write
	STATUS	mandatory
	DESCRIPTION	"Select type of packet marking."
	::= { mibsS7ProfileEntry 38 }

    sS7Profile-TransportOptions-Tos-Dscp	OBJECT-TYPE
	SYNTAX	DisplayString
	ACCESS	read-write
	STATUS	mandatory
	DESCRIPTION	"DSCP tag to be used in marking of the packets (if marking-type = dscp)."
	::= { mibsS7ProfileEntry 39 }

    sS7Profile-UseSystemIpAddressAsSource	OBJECT-TYPE
	SYNTAX	INTEGER {
		    no (1),
		    yes (2)
		}
	ACCESS	read-write
	STATUS	mandatory
	DESCRIPTION	"When set to 'yes', use configured System IP Address as source ip address. When set to 'no', use IP Address of outgoing interface as source ip address."
	::= { mibsS7ProfileEntry 18 }

    sS7Profile-IpdcSourceAdddress	OBJECT-TYPE
	SYNTAX	IpAddress
	ACCESS	read-write
	STATUS	mandatory
	DESCRIPTION	"IP address to be used on the private network"
	::= { mibsS7ProfileEntry 32 }

    sS7Profile-Vrouter	OBJECT-TYPE
	SYNTAX	DisplayString
	ACCESS	read-write
	STATUS	mandatory
	DESCRIPTION	"Specifies the virtual router to be used."
	::= { mibsS7ProfileEntry 33 }

    sS7Profile-CongestionControl-CongestionControlType	OBJECT-TYPE
	SYNTAX	INTEGER {
		    none (1),
		    l3QueueDepth (2)
		}
	ACCESS	read-write
	STATUS	mandatory
	DESCRIPTION	"Type of the congestion control algorithm to use."
	::= { mibsS7ProfileEntry 19 }

    sS7Profile-CongestionControl-Cl1Level	OBJECT-TYPE
	SYNTAX	INTEGER
	ACCESS	read-write
	STATUS	mandatory
	DESCRIPTION	"The level at which 'congestion level 1' indication will be issued. The value is interpreted according to the configured congestion control 'type'."
	::= { mibsS7ProfileEntry 20 }

    sS7Profile-CongestionControl-Cl1Action	OBJECT-TYPE
	SYNTAX	INTEGER {
		    ignore (1),
		    sendInfoToMgc (2)
		}
	ACCESS	read-write
	STATUS	mandatory
	DESCRIPTION	"Action taken when congestion level 1 (defined by the value of cl1-level) is reached."
	::= { mibsS7ProfileEntry 21 }

    sS7Profile-CongestionControl-Cl2Level	OBJECT-TYPE
	SYNTAX	INTEGER
	ACCESS	read-write
	STATUS	mandatory
	DESCRIPTION	"The level at which 'congestion level 2' indication will be issued. The value is interpreted according to the configured congestion control 'type'."
	::= { mibsS7ProfileEntry 22 }

    sS7Profile-CongestionControl-Cl2Action	OBJECT-TYPE
	SYNTAX	INTEGER {
		    ignore (1),
		    sendInfoToMgc (2),
		    rejectNewCall (3)
		}
	ACCESS	read-write
	STATUS	mandatory
	DESCRIPTION	"Action taken when congestion level 2 (defined by the value of cl2-level) is reached."
	::= { mibsS7ProfileEntry 23 }

    sS7Profile-SignalingHeartbeat-Enabled	OBJECT-TYPE
	SYNTAX	INTEGER {
		    no (1),
		    yes (2)
		}
	ACCESS	read-write
	STATUS	mandatory
	DESCRIPTION	"When set to yes, TNT will generate signaling heartbeat to MGC based on the interval configured in signaling-heartbeat interval."
	::= { mibsS7ProfileEntry 24 }

    sS7Profile-SignalingHeartbeat-Interval	OBJECT-TYPE
	SYNTAX	INTEGER
	ACCESS	read-write
	STATUS	mandatory
	DESCRIPTION	"The time interval in seconds for layer 3 heartbeat messages."
	::= { mibsS7ProfileEntry 25 }

    sS7Profile-ResilienceOptions-Type	OBJECT-TYPE
	SYNTAX	INTEGER {
		    releaseAll (1),
		    maintainActive (2),
		    timedRelease (3)
		}
	ACCESS	read-write
	STATUS	mandatory
	DESCRIPTION	"The type of resilience action required when line state changes."
	::= { mibsS7ProfileEntry 27 }

    sS7Profile-ResilienceOptions-Duration	OBJECT-TYPE
	SYNTAX	INTEGER
	ACCESS	read-write
	STATUS	mandatory
	DESCRIPTION	"The duration in milli seconds for which calls should be maintained when line state changes. Valid only if the type is configured as timed-release."
	::= { mibsS7ProfileEntry 28 }

    sS7Profile-PriTunnelingOptions-Enabled	OBJECT-TYPE
	SYNTAX	INTEGER {
		    no (1),
		    yes (2)
		}
	ACCESS	read-write
	STATUS	mandatory
	DESCRIPTION	"When set to yes, we will synchronize the d-channel status with the IPDC signaling link state."
	::= { mibsS7ProfileEntry 29 }

    sS7Profile-PriTunnelingOptions-Duration	OBJECT-TYPE
	SYNTAX	INTEGER
	ACCESS	read-write
	STATUS	mandatory
	DESCRIPTION	"The duration in milliseconds after which bringing down D-channel of tunneled-pri-signaling lines will be initiated."
	::= { mibsS7ProfileEntry 30 }

    sS7Profile-Action-o	OBJECT-TYPE
	SYNTAX	INTEGER {
		    noAction (1),
		    createProfile (2),
		    deleteProfile (3)
		}
	ACCESS	read-write
	STATUS	mandatory
	DESCRIPTION	""
	::= { mibsS7ProfileEntry 26 }


	-- The mibpRITunlStatProfile table
	--
	-- This table contains parameters for the mibpRITunlStatProfile profile
	--

    mibpRITunlStatProfileTable	OBJECT-TYPE
	SYNTAX		SEQUENCE OF MibpRITunlStatProfileEntry
	ACCESS		not-accessible
	STATUS		mandatory
	DESCRIPTION	"A list of mibpRITunlStatProfile profile entries."
	::= { mibpRITunlStatProfile 1 }

    mibpRITunlStatProfileEntry	OBJECT-TYPE
	SYNTAX		MibpRITunlStatProfileEntry
	ACCESS		not-accessible
	STATUS		mandatory
	DESCRIPTION	"A mibpRITunlStatProfile entry containing objects that
			 maps to the parameters of mibpRITunlStatProfile profile."
	INDEX		{ pRITunlStatProfile-Index-o }
	::= { mibpRITunlStatProfileTable 1 }

    MibpRITunlStatProfileEntry ::=
	SEQUENCE {
	    pRITunlStatProfile-Index-o
		INTEGER,
	    pRITunlStatProfile-Action-o
		INTEGER
	}

    pRITunlStatProfile-Index-o	OBJECT-TYPE
	SYNTAX	INTEGER
	ACCESS	read-only
	STATUS	mandatory
	DESCRIPTION	""
	::= { mibpRITunlStatProfileEntry 1 }

    pRITunlStatProfile-Action-o	OBJECT-TYPE
	SYNTAX	INTEGER {
		    noAction (1),
		    createProfile (2),
		    deleteProfile (3)
		}
	ACCESS	read-write
	STATUS	mandatory
	DESCRIPTION	""
	::= { mibpRITunlStatProfileEntry 2 }

END
