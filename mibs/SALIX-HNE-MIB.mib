SALIX-HNE-MIB DEFINITIONS ::= BEGIN

-- Note: Compile with SMICNG using options below to product intermediate
--       file output.
--
--        SMICNG /Y /Z /F <filename.imf> hne.inc

IMPORTS
     MODULE-IDENTITY, OBJECT-TYPE,
     Integer32, Unsigned32, Counter64, 
     Gauge32, IpAddress                         FROM SNMPv2-SMI

     TEXTUAL-CONVENTION, DisplayString,
     RowStatus, TruthValue, DateAndTime                      FROM SNMPv2-TC

     MODULE-COMPLIANCE, OBJECT-GROUP            FROM SNMPv2-CONF
     InterfaceIndex, ifIndex                    FROM IF-MIB

     sonetMediumEntry, 
     sonetPathCurrentEntry,
     sonetLineCurrentEntry, 
     sonetSectionCurrentEntry,       
     sonetPathIntervalEntry,
     sonetLineIntervalEntry, 
     sonetSectionIntervalEntry                  FROM SONET-MIB


--   AtmTrafficDescrParamIndex                  FROM ATM-TC-MIB

     AtmTrafficDescrParamIndex,
     atmInterfaceConfEntry,
     atmVplEntry, atmVclEntry,
     atmVclVci, atmVclVpi, atmVplVpi            FROM ATM-MIB
     
                        

--   atmfM4AlarmSevProfileEntry,
     atmfM4TcAdaptorEntry, atmfM4EquipHolderEntry,
     atmfM4PlugInUnitEntry, 
     atmfM4CellProtoHistIndex                   FROM ATM-FORUM-M4-MIB

     entPhysicalIndex, PhysicalIndex            FROM ENTITY-MIB

     hrSWInstalledEntry, 
     hrSWInstalledIndex                         FROM HOST-RESOURCES-MIB

     hybridSwitch                          FROM SALIX-MIB;
     
  


-- Define the SALIX Technologies node and define the HNE MIB beneath it

hneMIB MODULE-IDENTITY
     LAST-UPDATED "9808170000Z"
     ORGANIZATION "SALIX Technologies"
     CONTACT-INFO "904 Wind River Lane
                   Suite 101
                   Gaithersburg, MD  20878
                   (301)-417-0017"
     DESCRIPTION  "The HNE enterprise specific MIB"
     ::= { hybridSwitch 1 }

-- HNE object identification groups

-- Textual conventions

  HnePlugInUnitType ::= TEXTUAL-CONVENTION
       STATUS     current
       DESCRIPTION
            "HNE hardware plug-in unit types:
             unknown(0)     - Unknown plug-in unit type
             mpu(1)         - Management Processor Unit
             dpu(2)         - Data Processor Unit
             smu(3)         - Sync Module Unit
             liu(4)         - Line Interface Unit
             hsf(5)         - Hybrid Switch Fabric Unit
             powerSupply(6) - Power supply
             fan(7)         - Fan Unit
             hardDrive(8)   - Hard drive"

       SYNTAX     INTEGER { unknown(0),
                            mpu(1),
                            dpu(2), 
                            smu(3), 
                            liu(4), 
                            hsf(5),
                            powerSupply(6), 
                            fan(7), 
                            hardDrive(8) }

-- Groups under HneMIB

  hneMIBObjects      OBJECT IDENTIFIER ::= { hneMIB 1 }
  hneMIBTraps        OBJECT IDENTIFIER ::= { hneMIB 2 }
  hneMIBCompliance   OBJECT IDENTIFIER ::= { hneMIB 3 }
  hneMIBStats        OBJECT IDENTIFIER ::= { hneMIB 4 }

-- Groups in the HNE MIB module

  hneSystem          OBJECT IDENTIFIER ::=  { hneMIBObjects 1 }

  hneSonet           OBJECT IDENTIFIER ::=  { hneMIBObjects 2 }

  hneTdm             OBJECT IDENTIFIER ::=  { hneMIBObjects 3 }

  hneAtm             OBJECT IDENTIFIER ::=  { hneMIBObjects 4 }

  hneAtmfM4          OBJECT IDENTIFIER ::=  { hneMIBObjects 5 }

  hnePlugInUnit      OBJECT IDENTIFIER ::=  { hneMIBObjects 6 }

  -- Sub-groups of the hneSystem group

  hneSystemHost      OBJECT IDENTIFIER ::=  { hneSystem 1 }

  hneSystemSync      OBJECT IDENTIFIER ::=  { hneSystem 2 }

  hneSystemHsf       OBJECT IDENTIFIER ::=  { hneSystem 3 }


-- HNE System Objects
       
  -- HNE System Sync Objects

  hneSysSyncTimingMode OBJECT-TYPE
       SYNTAX     INTEGER { internal(1), line(2), external(3) }
       MAX-ACCESS read-write
       STATUS     current
       DESCRIPTION
            "An identification of the source from which timing is derived by
             the working sync module within the HNE.  Possible values are:

             internal(1) - the internal oscillator on the sync module will be
                           used as the master clock for system synchronization.
             line(2)     - the sync module is synchronizing with the receive
                           line timing from a signal received by an LIU.
             external(3) - the Building Integrated Timing System (BITS)
                           available on a T1 line plugged into an LIU will be
                           used as the master clock for system synchronization."
       DEFVAL { internal }
       ::= { hneSystemSync 1 }

  hneSysSyncPrimaryRefLine OBJECT-TYPE
       SYNTAX     InterfaceIndex
       MAX-ACCESS read-write
       STATUS     current
       DESCRIPTION
            "The interface index of the primary physical line termination
             point (SONET line) from which the sync module can derive timing.
             This is used only if the hneSysSyncTimingMode is set to 'line'."
       ::= { hneSystemSync 2 }

  hneSysSyncSecondaryRefLine OBJECT-TYPE
       SYNTAX     InterfaceIndex
       MAX-ACCESS read-write
       STATUS     current
       DESCRIPTION
            "The interface index of the secondary physical line termination
             point (SONET line) from which the sync module can derive timing.
             This is used only if the hneSysSyncTimingMode is set to 'line',
             and the primary reference is unavailable or out of a valid
             frequency range."
       ::= { hneSystemSync 3 }

  hneSysSyncRevertiveSwitch OBJECT-TYPE
       SYNTAX     TruthValue
       MAX-ACCESS read-write
       STATUS     current
       DESCRIPTION
            "Indication of whether or not the active reference should revert
             to primary if that reference becomes available after a failure
             is cleared.

             true(1)  - reference switching is revertive
             false(2) - reference switching is non-revertive"
       DEFVAL { false }
       ::= { hneSystemSync 4 }

  hneSysSyncClockMode OBJECT-TYPE
       SYNTAX     INTEGER { freeRun(1),
                            normal(2),
                            holdover(3),
                            fastStart(4)
                          }
       MAX-ACCESS read-only
       STATUS     current
       DESCRIPTION
            "Indication of the clock mode of the 'working' sync module.

             freeRun(1)  - mode in which the clock is synchronized to the
                           module's internal oscillator.
             normal(2)   - mode in which the clock is synchronized to an
                           external reference.
             holdover(3) - mode in which the clock, after having been
                           synchronized to an external reference, loses that
                           reference and all other external references.
             fastStart(4) - mode in which the clock is in the process of
                           synchronizing to a reference."
       ::= { hneSystemSync 5 }

  hneSysSyncConfiguredActiveRef OBJECT-TYPE
       SYNTAX     INTEGER { primary(1), secondary(2) }
       MAX-ACCESS read-write
       STATUS     current
       DESCRIPTION
            "The configured active reference line from which the sync
             module should deriving its timing.  This object is relevant if 
             the hneSysSyncTimingMode is set to 'line' or 'external'.  Writing 
             a value that is different from its current value will force the
             Sync module to switch to using the specified reference line.

             primary(1)    -  The hneSysSyncPrimaryRefLine is the active
                              reference line
             secondary (2) -  The hneSysSyncSecondaryRefLine is the active
                              reference line"
       ::= { hneSystemSync 6 }

  hneSysSyncAutoRefSwitch OBJECT-TYPE
       SYNTAX     TruthValue
       MAX-ACCESS read-write
       STATUS     current
       DESCRIPTION
            "Indication of automatic reference switching being enabled or
             disabled.

             true(1)  - Auto reference switching is enabled
             false(2) - Auto reference switching is disabled"
       DEFVAL { true }
       ::= { hneSystemSync 7 }

  hneSysSyncFreeRunAlarm OBJECT-TYPE
       SYNTAX  TruthValue
       MAX-ACCESS      read-write
       STATUS     current
       DESCRIPTION
            "Indication of alarm associated with free-run mode being
             enabled or disabled.

             true(1)  - Alarm is enabled
             false(2) - Alarm is disabled"
       DEFVAL { true }
       ::= { hneSystemSync 8 }

  hneSysSyncWorking OBJECT-TYPE
       SYNTAX     PhysicalIndex
       MAX-ACCESS read-write
       STATUS     current
       DESCRIPTION
            "The entPhysicalIndex of the sync module plug-in unit that is
             providing the system synchronizaton signal.  Writing a new value
             to this object, a value not equal to the current value, will:

             - update the hneSysSyncProtect object with the current value
               of the hneSysSyncWorking object and

             - activate the specified sync module to start providing the
               system synchronization signal.

             A value of 0 indicates that there are no operational or not
             installed sync modules in the system.  Writing zero, an invalid
             index, or the current value to this object will have no effect.

             If the working sync module fails, the system will automatically
             switch to the sync module specified in the hneSysSyncProtect
             object."
       ::= { hneSystemSync 9 }

  hneSysSyncProtect OBJECT-TYPE
       SYNTAX     PhysicalIndex
       MAX-ACCESS read-only
       STATUS     current
       DESCRIPTION
            "The entPhysicalIndex of the sync module plug-in unit
             that is protecting or on standby to the working sync module.
             A value of 0 indicates that there is no redundant sync module
             available or provisioned as a protect module."
       ::= { hneSystemSync 10 }

  hneSysSyncPrimaryRefLineState OBJECT-TYPE
       SYNTAX     INTEGER { unknown(0),
                            valid(1),
                            lossOfSignalError(2),
                            frequencyOffsetError(3)
                          }
       MAX-ACCESS read-only
       STATUS     current
       DESCRIPTION
            "This variable indicates the state of the primary reference
             line termination point (SONET line) to be used as a timing 
             source by the sync module.  This object is relevant if the 
             hneSysSyncTimingMode is set to 'line' and the 
             hneSysSyncPrimaryRefLine is configured.
             
             unknown(0)           - the state of the line has not been 
                                    determined. 
             valid(1)             - the line is operating within the 
                                    frequency specification.
             lossOfSignalError    - loss of signal was detected from the
                                    line and has failed the health check.
             frequencyOffsetError - frequency errors were detected from
                                    the line and has failed the health check"
                                    
       ::= { hneSystemSync 11 }

  hneSysSyncSecondaryRefLineState OBJECT-TYPE
       SYNTAX     INTEGER { unknown(0),
                            valid(1),
                            lossOfSignalError(2),
                            frequencyOffsetError(3)
                          }
       MAX-ACCESS read-only
       STATUS     current
       DESCRIPTION
            "This variable indicates the state of the secondary reference
             line termination point (SONET line) to be used as a timing 
             source by the sync module.  This object is relevant if the 
             'hneSysSyncTimingMode' is set to 'line' and the 
             'hneSysSyncPrimaryRefLine' is configured.
             
             unknown(0)           - the state of the line has not been 
                                    determined. 
             valid(1)             - the line is operating within 
                                    frequency specification.
             lossOfSignalError    - loss of signal was detected from the
                                    line and has failed the health check.
             frequencyOffsetError - frequency errors were detected from
                                    the line and has failed the health check"
                                    
       ::= { hneSystemSync 12 }

  hneSysSyncCurrentActiveRef OBJECT-TYPE
       SYNTAX     INTEGER { primary(1), secondary(2) }
       MAX-ACCESS read-only
       STATUS     current
       DESCRIPTION
            "Indication of the active reference line from which the sync
             module is deriving its timing.  This object is relevant if the
             hneSysSyncTimingMode is set to 'line' or 'external'.  The 
             value of this variable can differ from the 
             'hneSysSyncConfiguredActiveRef' if the sync module determine an
             error condition with the 'hneSysSyncConfiguredActiveRef' and
             has switched to using another SONET line as the active reference.

             primary(1)    -  The hneSysSyncPrimaryRefLine is the current
                              active reference line
             secondary (2) -  The hneSysSyncSecondaryRefLine is the current
                              active reference line"
       ::= { hneSystemSync 13 }

  hneSysSyncForcedState OBJECT-TYPE
       SYNTAX     INTEGER { none(0),
                            revertiveSwitchInhibit(1),
                            autoReferenceSwitchInhbit(2)
                          }
       MAX-ACCESS read-only
       STATUS     current
       DESCRIPTION
            "This variable indicates the state of the sync module with
             regard to switching between the configured active reference, 
             the value of the 'hneSysSyncConfiguredActiveRef' variable, and  
             the alternate active reference.  The alternate active 
             reference is identified by the 'hneSysSyncPrimaryRefLine' or
             'hneSysSyncSecondaryRefLine' that is not configured as the
             'hneSysSyncConfiguredActiveRef'.
             
             none(0) - the sync module is in a state where it is free
                       to switch between the configured active reference
                       the alternate active reference.
                                          
             revertiveSwitchInhibit - the state of the sync module after 
                       switching from the 'hneSysSyncConfiguredActiveRef'
                       to the 'hneSysSyncCurrentActiveRef' when the 
                       'hneSysSyncRevertiveSwitch' is configured as 'false'.
                       In this state the sync module will not revert back
                       to using the 'hneSysSyncConfiguredActiveRef' unless
                       the 'hneSysSyncCurrentActiveRef' has failed and the 
                       state of the active reference defined by the 
                       'hneSysSyncConfiguredActiveRef' variable is 'valid'.
                       
             autoReferenceSwitchInhibit - the state of the sync module when
                       the 'hneSysSyncAutoReferenceSwitch' variable is 
                       configured as 'false'. In this state the sync module 
                       will not switch to using the alternate active reference
                       unless the 'hneSysSyncCurrentActiveRef' has failed and
                       the state of the alternate active reference is 'valid'."
       ::= { hneSystemSync 14 }

  -- HNE System Hybrid Switch Fabric (HSF) Objects
       
  hneSysHsfWorking OBJECT-TYPE
       SYNTAX     PhysicalIndex
       MAX-ACCESS read-write
       STATUS     current
       DESCRIPTION
            "The PhysicalIndex of the Hybrid Switch Fabric (HSF) module
             plug-in unit that is performing switching in the HNE.
             Writing a new value to this variable will:

             - update the hneHsfProtect object with the current
               value of the hneHsfWorking object and

             - activate the specified HSF module to start performing
               ATM and TDM switching in the system.

               A value of 0 indicates that there is no operational switch
               fabric installed in the HNE. Writing zero, an invalid index,
               or the current value to this object will have no effect.

               If the working HSF module fails, the system will automatically
               switch to the HSF module specified in the hneHsfProtect object."
       ::= { hneSystemHsf 1 }


  hneSysHsfProtect OBJECT-TYPE
       SYNTAX     PhysicalIndex
       MAX-ACCESS read-only
       STATUS     current
       DESCRIPTION
            "The entPhysicalIndex of the Hybrid Switch Fabric (HSF) module
             plug-in unit that is protecting or on standby to the working
             HSF module, hneHSFWorking.  A value of 0 indicates that there
             are no operational or no additional HSF modules present for
             redundancy."
       ::= { hneSystemHsf 2 }


-- HNE SONET Objects (SONET-MIB Extenstions)

  -- HNE Sonet Line Table

  hneSonetLineTable OBJECT-TYPE
       SYNTAX     SEQUENCE OF    HneSonetLineEntry
       MAX-ACCESS not-accessible
       STATUS     current
       DESCRIPTION
            "The HNE sonet line table.  This table augments the
             sonetMediumTable defined in the Sonet / SDH MIB."
       ::= { hneSonet 1 }

  hneSonetLineEntry OBJECT-TYPE
       SYNTAX     HneSonetLineEntry
       MAX-ACCESS not-accessible
       STATUS     current
       DESCRIPTION
            "An entry in the HNE sonet line table.  An entry contains
             HNE specific sonet line information not found in the
             Sonet / SDH MIB."
       AUGMENTS { sonetMediumEntry }
       ::= { hneSonetLineTable 1 }

  HneSonetLineEntry ::= SEQUENCE {
            hneSonetLineTimingSource                   INTEGER,
            hneSonetLineDccSelection                   INTEGER,
            hneSonetLineOverheadLoopThroughModeEnabled TruthValue
       }

  hneSonetLineTimingSource OBJECT-TYPE
       SYNTAX      INTEGER { sync(1), loop(2) }
       MAX-ACCESS  read-write
       STATUS      current
       DESCRIPTION
            "The source of timing for the transmitted signal.  This must be
             set to 'loop' in the 'value added' mode of operation.

             sync(1) - line timing signal generated by the sync module
             loop(2) - line timing generated by a line looped back to the
                       line input"
       DEFVAL { sync }
       ::= { hneSonetLineEntry 1 }

  hneSonetLineDccSelection OBJECT-TYPE
       SYNTAX     INTEGER { section(1), line(2) }
       MAX-ACCESS read-write
       STATUS     current
       DESCRIPTION
            "The selection of which DCC to transmit and receive management
             traffic on. Only one of the two will be used by the HNE at a
             time.  Possible selections are:

             section(1) - section overhead will carry the DCC
             line(2)    - line overhead will carry the DCC"

       DEFVAL { section }
       ::= { hneSonetLineEntry 2 }

  hneSonetLineOverheadLoopThroughModeEnabled OBJECT-TYPE
       SYNTAX     TruthValue
       MAX-ACCESS read-write
       STATUS     current
       DESCRIPTION
            "Indicates whether or not the line overhead bytes of a connection
             should be looped back through to the outbound path.

             true(1)  - loop through mode is enabled
             false(2) - loop through mode is not enabled"
       DEFVAL { false }
       ::= { hneSonetLineEntry 3 }

  -- HNE SONET Protection Switching Table

  hneSonetProtectionTable OBJECT-TYPE
       SYNTAX     SEQUENCE OF    HneSonetProtectionEntry
       MAX-ACCESS not-accessible
       STATUS     current
       DESCRIPTION
            "Table giving information about SONET protection switching
             relationships for signals attached to the HNE.  Each record
             describes a relationship between two SONET lines where one
             is functioning as the backup for the other."
       ::= { hneSonet 2 }

  hneSonetProtectionEntry OBJECT-TYPE
       SYNTAX     HneSonetProtectionEntry
       MAX-ACCESS not-accessible
       STATUS     current
       DESCRIPTION
            "An entry in the HNE protection switching table.
             An entry contains configuration switching information for the
             high and low protected interface pair."
       INDEX { hneSonetProtectionInterfaceHigh, hneSonetProtectionInterfaceLow }
       ::= { hneSonetProtectionTable 1 }

  HneSonetProtectionEntry ::= SEQUENCE {
            hneSonetProtectionInterfaceHigh         InterfaceIndex,
            hneSonetProtectionInterfaceLow          InterfaceIndex,
            hneSonetProtectionInterfaceWorking      InterfaceIndex,
            hneSonetProtectionConfig                INTEGER,
            hneSonetProtectionRevertive             TruthValue,
            hneSonetProtectionBiDirectional         TruthValue
       }

  hneSonetProtectionInterfaceHigh OBJECT-TYPE
       SYNTAX     InterfaceIndex
       MAX-ACCESS not-accessible
       STATUS     current
       DESCRIPTION
            "The ifIndex of one of the SONET lines involved in the
             relationship."
       ::= { hneSonetProtectionEntry 1 }

  hneSonetProtectionInterfaceLow OBJECT-TYPE
       SYNTAX     InterfaceIndex
       MAX-ACCESS not-accessible
       STATUS     current
       DESCRIPTION
            "The ifIndex of the other SONET lines involved in the
             relationship."
       ::= { hneSonetProtectionEntry 2 }

  hneSonetProtectionInterfaceWorking OBJECT-TYPE
       SYNTAX     InterfaceIndex
       MAX-ACCESS read-write
       STATUS     current
       DESCRIPTION
            "The ifIndex of the SONET line which is currently carrying
             live traffic, termed the working or active interface.  Writing
             the value of the protect ifIndex to this value will cause a
             protection switch."
       ::= { hneSonetProtectionEntry 3 }

  hneSonetProtectionConfig OBJECT-TYPE
       SYNTAX     INTEGER { none(0), onePlusOne(1), oneToOne(2), oneToN(3) }
       MAX-ACCESS read-write
       STATUS     current
       DESCRIPTION
            "The linear APS configuration for the protection relationship.
             See GR-253-CORE for details."
       DEFVAL { onePlusOne }
       ::= { hneSonetProtectionEntry 4 }

  hneSonetProtectionRevertive OBJECT-TYPE
       SYNTAX     TruthValue
       MAX-ACCESS read-write
       STATUS     current
       DESCRIPTION
            "Indication of whether or not the role of 'working' should
             return after a failure is cleared. See GR-253-CORE.

             true(1)  - protection switching is revertive
             false(2) - protection switching is non-revertive"
       DEFVAL { false }
       ::= { hneSonetProtectionEntry 5 }

  hneSonetProtectionBiDirectional OBJECT-TYPE
       SYNTAX     TruthValue
       MAX-ACCESS read-write
       STATUS     current
       DESCRIPTION
            "Indication of whether or not protection switching is coordinated
             on an end-to-end basis or not.  If bi-directional, both the
             east-west and west-east fibers are switched simultaneously.
             If not, switching on the two fibers is totally independant.

             true(1)  - protection switching is bi-directional
             false(2) - protection switching is uni-directional"
       DEFVAL { false }
       ::= { hneSonetProtectionEntry 6 }

  -- HNE Sonet Path Table

  hneSonetPathTable OBJECT-TYPE
       SYNTAX     SEQUENCE OF    HneSonetPathEntry
       MAX-ACCESS not-accessible
       STATUS     current
       DESCRIPTION
            "The HNE sonet path table.  This table augments the
             sonetPathCurrentTable defined in the Sonet / SDH MIB."
       ::= { hneSonet 3 }

  hneSonetPathEntry OBJECT-TYPE
       SYNTAX     HneSonetPathEntry
       MAX-ACCESS not-accessible
       STATUS     current
       DESCRIPTION
            "An entry in the HNE sonet path table.  An entry contains
             HNE specific sonet path information not found in the
             Sonet / SDH MIB."
       AUGMENTS { sonetPathCurrentEntry }
       ::= { hneSonetPathTable 1 }

  HneSonetPathEntry ::= SEQUENCE {
            hneSonetPathContentType                    INTEGER,
            hneSonetPathOverheadLoopThroughModeEnabled TruthValue,
            hneSonetPathSpeMicMode                     INTEGER,
            hneSonetPathReceiveTraceMessage            DisplayString,
            hneSonetPathTransmitTraceMessage           DisplayString,
            hneSonetPathRowStatus                      RowStatus
       }

  hneSonetPathContentType OBJECT-TYPE
       SYNTAX     INTEGER { atm(1),
                            atmVam(2),
                            notTerminated(3),
                            terminatedNotSpecified(4) }
       MAX-ACCESS read-create
       STATUS     current
       DESCRIPTION
            "The type of traffic that is being carried by the sonet path

             atm(1)           - atm cells
             atmVam(2)        - atm value added mode
             notTerminated(3) - the path is cross-connected through the HNE
                                without being terminated.
             terminatedNotSpecified(4) - payload of the path is unknown."
       ::= { hneSonetPathEntry 1 }

  hneSonetPathOverheadLoopThroughModeEnabled OBJECT-TYPE
       SYNTAX     TruthValue
       MAX-ACCESS read-only
       STATUS     current
       DESCRIPTION
            "Indicates whether or not the path overhead bytes of a connection
             should be looped back through to the outbound path.

             true(1)  - loop through mode is enabled
             false(2) - loop through mode is not enabled"
       ::= { hneSonetPathEntry 2 }

  hneSonetPathSpeMicMode OBJECT-TYPE
       SYNTAX     INTEGER { none(0),
                            receive(1),
                            transmit(2),
                            receiveTransmit(3) }
       MAX-ACCESS read-create
       STATUS     current
       DESCRIPTION
            "Indicates whether or not the SPE MIC should be calculated
             and inserted in the F2 user byte of the Path overhead.

             none(0)            - SPE MIC is insertion is disabled
             receive(1)         - SPE MIC is inserted only in the receive path
             transmit(2)        - SPE MIC is inserted only in the transmit path
             receiveTransmit(3) - SPE MIC is inserted in both receive and 
                                  transmit paths."
       DEFVAL { none }
       ::= { hneSonetPathEntry 3 }
							  
  hneSonetPathReceiveTraceMessage OBJECT-TYPE
       SYNTAX     DisplayString (SIZE(0..64))
       MAX-ACCESS read-create
       STATUS     current
       DESCRIPTION
            "The 64 byte character path trace message expected to be 
             received in the sonet frame path overhead (J1 byte)."
       DEFVAL { "" }
       ::= { hneSonetPathEntry 4 }

  hneSonetPathTransmitTraceMessage OBJECT-TYPE
       SYNTAX     DisplayString (SIZE(0..64))
       MAX-ACCESS read-create
       STATUS     current
       DESCRIPTION
            "The 64 byte character path trace message to be sent in
             the sonet frame path overhead (J1 byte)."
       DEFVAL { "" }
       ::= { hneSonetPathEntry 5 }

  hneSonetPathRowStatus OBJECT-TYPE
       SYNTAX     RowStatus
       MAX-ACCESS read-create
       STATUS     current
       DESCRIPTION
            "The status of this entry in the hneSonetPathTable.
             This object is used to create or delete a hneSonetPathTable
             entry and the corresponding sonetPathCurrentTable entry
             defined in the Sonet / SDH MIB.

             This object must be set to 'createAndGo' to create a new
             entry in this table.  Row status values:

             active(1)       - set by the agent after this entry is created
             notInService(2) - not applicable
             notReady(3)     - not applicable
             createAndGo(4)  - set by management entity when creating entry
             createAndWait(5)- not applicable
             destroy(6)      - set by the management entity to destroy entry"
       ::= { hneSonetPathEntry 6 }

-- HNE TDM Objects

  -- HNE TDM Cross Connect Table

  hneTdmCrossConnectTable OBJECT-TYPE
       SYNTAX     SEQUENCE OF    HneTdmCrossConnectEntry
       MAX-ACCESS not-accessible
       STATUS     current
       DESCRIPTION
            "The HNE TDM cross connect table."
       ::= { hneTdm 1 }

  hneTdmCrossConnectEntry OBJECT-TYPE
       SYNTAX     HneTdmCrossConnectEntry
       MAX-ACCESS not-accessible
       STATUS     current
       DESCRIPTION
            "An entry in the HNE TDM cross connect table."
       INDEX { hneTdmCrossConnectPathTerminationPoint1,
               hneTdmCrossConnectPathTerminationPoint2
             }
       ::= { hneTdmCrossConnectTable 1 }

  HneTdmCrossConnectEntry ::= SEQUENCE {
            hneTdmCrossConnectPathTerminationPoint1 InterfaceIndex,
            hneTdmCrossConnectPathTerminationPoint2 InterfaceIndex,
            hneTdmCrossConnectOperStatus            INTEGER,
            hneTdmCrossConnectRowStatus             RowStatus
       }

  hneTdmCrossConnectPathTerminationPoint1 OBJECT-TYPE
       SYNTAX     InterfaceIndex
       MAX-ACCESS not-accessible
       STATUS     current
       DESCRIPTION
            "The physical path termination point carrying TDM data
             to be cross-connected to the second physical path termination
             point.  The hneTdmCrossConnectPathTerminationPoint1 has a
             lower ifIndex then the hneTdmCrossConnectPathTerminationPoint2."
       ::= { hneTdmCrossConnectEntry 1 }

  hneTdmCrossConnectPathTerminationPoint2 OBJECT-TYPE
       SYNTAX     InterfaceIndex
       MAX-ACCESS not-accessible
       STATUS     current
       DESCRIPTION
            "The second physical path termination point carrying TDM data
             to be cross- connected to the first physical path termination
             point.  The hneTdmCrossConnectPathTerminationPoint2 has a
             higher ifIndex then the hneTdmCrossConnectPathTerminationPoint1."
       ::= { hneTdmCrossConnectEntry 2 }

  hneTdmCrossConnectOperStatus OBJECT-TYPE
       SYNTAX     INTEGER { up(1),
                            down(2),
                            unknown(3) }
       MAX-ACCESS read-only
       STATUS     current
       DESCRIPTION
          "This attribute indicates the operational state of the 
           TDM cross connection."
       ::= { hneTdmCrossConnectEntry 3 }

  hneTdmCrossConnectRowStatus OBJECT-TYPE
       SYNTAX     RowStatus
       MAX-ACCESS read-create
       STATUS     current
       DESCRIPTION
            "The status of this entry in the hneTdmCrossConnectTable.
             This object is used to create or delete a hneTdmCrossConnectTable
             entry.

             This object must be set to 'createAndGo' to create a new
             entry in this table.  Row status values:

             active(1)       - set by the agent after this entry is created
             notInService(2) - not applicable
             notReady(3)     - not applicable
             createAndGo(4)  - set by management entity when creating entry
             createAndWait(5)- not applicable
             destroy(6)      - set by the management entity to destroy entry"
       ::= { hneTdmCrossConnectEntry 4 }

-- ATM Interface Objects (ATM-MIB Extensions)

  -- HNE ATM Interface Configuration Table

  hneAtmInterfaceConfTable OBJECT-TYPE
       SYNTAX     SEQUENCE OF    HneAtmInterfaceConfEntry
       MAX-ACCESS not-accessible
       STATUS     current
       DESCRIPTION
            "The HNE ATM interface configuration table.  This table
             augments the atmInterfaceConfEntry defined in the ATM MIB."
       ::= { hneAtm 1 }

  hneAtmInterfaceConfEntry OBJECT-TYPE
       SYNTAX     HneAtmInterfaceConfEntry
       MAX-ACCESS not-accessible
       STATUS     current
       DESCRIPTION
            "An entry in the HNE ATM interface configuration table.
             An entry contains HNE specific ATM interface information
             not found in the ATM MIB."
       AUGMENTS { atmInterfaceConfEntry }
       ::= { hneAtmInterfaceConfTable 1 }

  HneAtmInterfaceConfEntry ::= SEQUENCE {
            hneAtmInterfaceValueAddedModeEnabled TruthValue
       }

  hneAtmInterfaceValueAddedModeEnabled OBJECT-TYPE
       SYNTAX     TruthValue
       MAX-ACCESS read-only
       STATUS     current
       DESCRIPTION
            "An indication of whether or not value added mode is
             enabled at the ATM interface.  If enabled, received or
             transmitted cells are routed to the data processor before
             being forwarded by a Line Interface Unit.

             true(1)           - value added mode is enabled
             false(2)          - value added mode is disabled"
       DEFVAL { false }
       ::= { hneAtmInterfaceConfEntry 2 }

  -- HNE Next ATM Traffic Descripter Profile Index Next

  hneAtmTrafficDescrParamIndexNext OBJECT-TYPE
       SYNTAX     AtmTrafficDescrParamIndex
       MAX-ACCESS read-only
       STATUS     current
       DESCRIPTION
            "The value to be used when creating an atmTrafficDescrParaEntry.
             To obtain the index value for a new entry, the manager
             issues a management protocol retrieval operation to obtain
             the current value of this object.  After each retrieval, the
             agent should modify the value to the next unassigned index
             (or -1).  A value of -1 indicates that all available entries
             are assigned."
       ::= { hneAtm 3 }

  -- HNE Virtual Path Link (VPL) Table

  hneAtmVplTable OBJECT-TYPE
       SYNTAX     SEQUENCE OF    HneAtmVplEntry
       MAX-ACCESS not-accessible
       STATUS     current
       DESCRIPTION
            "The HNE Virtual Path Link (VPL) table.  This table augments
             the atmVplTable defined in the ATM-MIB."
       ::= { hneAtm 4 }

  hneAtmVplEntry OBJECT-TYPE
       SYNTAX     HneAtmVplEntry
       MAX-ACCESS not-accessible
       STATUS     current
       DESCRIPTION
            "An entry in the HNE ATM Virtual Path Link Table. This table
             contains information specific to the HNE implementation."
       AUGMENTS { atmVplEntry }
       ::= { hneAtmVplTable 1 }

  HneAtmVplEntry ::= SEQUENCE {
            hneAtmVplVamMode INTEGER 
       }            

  hneAtmVplVamMode OBJECT-TYPE
       SYNTAX     INTEGER { none(0),
                            hostTerminated(1) }
       MAX-ACCESS read-create
       STATUS     current
       DESCRIPTION
            "The operational mode of a Value Added Mode VPL that is
             terminated at a virtual proprietary interface on a 
             Data Processor.  The operational modes are: 
             
             none(0)           - Normal loopback mode
             hostTerminated(1) - Cells received at the Virtual Path Link
                                 termination point are routed to the 
                                 Data Processor in addition to being looped
                                 back."
       DEFVAL { none }
       ::= { hneAtmVplEntry 1 }

-- HNE ATM M4 Objects (ATM-FORUM-M4-MIB Extensions)

  -- HNE TC Adaptor Table

  hneAtmfM4TcAdaptorTable OBJECT-TYPE
       SYNTAX     SEQUENCE OF    HneAtmfM4TcAdaptorEntry
       MAX-ACCESS not-accessible
       STATUS     current
       DESCRIPTION
            "The HNE sonet path table.  This table augments the
             atmfM4TcAdapterTable defined in the ATM-FORUM-M4-MIB."
       ::= { hneAtmfM4 1 }

  hneAtmfM4TcAdaptorEntry OBJECT-TYPE
       SYNTAX     HneAtmfM4TcAdaptorEntry
       MAX-ACCESS not-accessible
       STATUS     current
       DESCRIPTION
            "An entry in the HNE TC adapter table. An entry
             contains HNE specific TC adapter information."
       AUGMENTS { atmfM4TcAdaptorEntry }
       ::= { hneAtmfM4TcAdaptorTable 1 }

  HneAtmfM4TcAdaptorEntry ::= SEQUENCE {
            hneAtmfM4TcHecErroredCellAction  INTEGER
       }

  hneAtmfM4TcHecErroredCellAction OBJECT-TYPE
       SYNTAX     INTEGER { pass(1), drop(2) }
       MAX-ACCESS read-write
       STATUS     current
       DESCRIPTION
            "The action to take when HEC errored cells are detected:

             pass(1) - forward cells containing HEC errors
             drop(2) - drop cells containing HEC errors"
       DEFVAL { drop }
       ::= { hneAtmfM4TcAdaptorEntry 1 }

-- Conformance Statements

hneGroups          OBJECT IDENTIFIER    ::= {hneMIBCompliance 1 }
hneCompliances     OBJECT IDENTIFIER    ::= {hneMIBCompliance 2 }

-- Compliance Statements

hneCompliance MODULE-COMPLIANCE
     STATUS       current
     DESCRIPTION
                  "The basic implementation requirements for the HNE MIB."
     MODULE       -- This module
     MANDATORY-GROUPS { hneSystemGroup }
     ::= { hneCompliances 1 }

-- Units of conformance

  hneSystemGroup     OBJECT-GROUP
       OBJECTS {
                    hneSysSyncTimingMode,
                    hneSysSyncPrimaryRefLine,
                    hneSysSyncSecondaryRefLine,
                    hneSysSyncRevertiveSwitch,
                    hneSysSyncClockMode,
                    hneSysSyncConfiguredActiveRef,
                    hneSysSyncAutoRefSwitch,
                    hneSysSyncFreeRunAlarm,
                    hneSysSyncWorking,
                    hneSysSyncProtect,
                    hneSysSyncPrimaryRefLineState,
                    hneSysSyncSecondaryRefLineState,
                    hneSysSyncCurrentActiveRef,
                    hneSysSyncForcedState,
                    hneSysHsfWorking,
                    hneSysHsfProtect
               }
       STATUS       current
       DESCRIPTION  "Additional HNE specific objects to the mib-2 system
                     group."
       ::= {hneGroups 1}

  hneSonetGroup      OBJECT-GROUP
       OBJECTS {
                     hneSonetLineTimingSource,
                     hneSonetLineDccSelection,
                     hneSonetLineOverheadLoopThroughModeEnabled,
                     hneSonetProtectionInterfaceWorking,
                     hneSonetProtectionConfig,
                     hneSonetProtectionRevertive,
                     hneSonetProtectionBiDirectional,
                     hneSonetPathContentType,
                     hneSonetPathOverheadLoopThroughModeEnabled,
                     hneSonetPathSpeMicMode,
                     hneSonetPathReceiveTraceMessage,
                     hneSonetPathTransmitTraceMessage,
                     hneSonetPathRowStatus
               }
       STATUS       current
       DESCRIPTION  "Additional HNE specific objects to the SONET-MIB."
       ::= {hneGroups 2}

  hneTdmGroup        OBJECT-GROUP
       OBJECTS {
                     hneTdmCrossConnectRowStatus,
                     hneTdmCrossConnectOperStatus
               }
       STATUS       current
       DESCRIPTION  "HNE TDM objects."
       ::= {hneGroups 3}

  hneAtmGroup        OBJECT-GROUP
       OBJECTS {
                     hneAtmInterfaceValueAddedModeEnabled,
                     hneAtmTrafficDescrParamIndexNext,
                     hneAtmVplVamMode
               }
       STATUS       current
       DESCRIPTION  "Additional HNE specific objects to the ATM-MIB."
       ::= {hneGroups 4}

  hneAtmfM4Group     OBJECT-GROUP
       OBJECTS {
                     hneAtmfM4TcHecErroredCellAction
               }
       STATUS       current
       DESCRIPTION  "Additional HNE specific objects to the ATM-FORUM-M4-MIB."
       ::= {hneGroups 5}

-- HNE Statistic Objects  hneMIBStats

-- HNE SONET Statistic Objects (SONET-MIB Extensions)



  -- HNE SONET/SDH Path Current Table

  -- HNE SONET/SDH Path Current table contains 
  -- various statistics being collected for the 
  -- current 15 minute interval.
  
  hneSonetPathCurrentTable OBJECT-TYPE
       SYNTAX     SEQUENCE OF    HneSonetPathCurrentEntry
       MAX-ACCESS not-accessible
       STATUS     current
       DESCRIPTION
            "The HNE SONET/SDH Path Current table."
       ::= { hneMIBStats 5 } 
    
  hneSonetPathCurrentEntry OBJECT-TYPE
       SYNTAX  HneSonetPathCurrentEntry
       MAX-ACCESS  not-accessible
       STATUS  current
       DESCRIPTION
         "An entry in the HNE sonet path current table.  An entry 
          contains HNE specific sonet path information not found 
          in the SONET / SDH MIB."
       AUGMENTS { sonetPathCurrentEntry }   
       ::= { hneSonetPathCurrentTable 1}
          
       HneSonetPathCurrentEntry ::= SEQUENCE {
           hneSonetPathCurrentRxPosPointerJustCount   Gauge32,
           hneSonetPathCurrentRxNegPointerJustCount   Gauge32,
           hneSonetPathCurrentTxPosPointerJustCount   Gauge32,
           hneSonetPathCurrentTxNegPointerJustCount   Gauge32
       }
       
  hneSonetPathCurrentRxPosPointerJustCount OBJECT-TYPE
	    SYNTAX	   Gauge32
	    MAX-ACCESS	read-only
	    STATUS	   current
	    DESCRIPTION
		      "The counter associated with the number of 
		       positive pointer justification events that occurred
		       on the receive side of a SONET/SDH path 
		       in the current 15 minute interval."
       ::= { hneSonetPathCurrentEntry 1 }        
       
  hneSonetPathCurrentRxNegPointerJustCount OBJECT-TYPE
	    SYNTAX	   Gauge32
	    MAX-ACCESS	read-only
	    STATUS	   current
	    DESCRIPTION
		      "The counter associated with the number of 
		       negative pointer justification events that occurred
		       on the receive side of a SONET/SDH path 
		       in the current 15 minute interval."
       ::= { hneSonetPathCurrentEntry 2 }    

  hneSonetPathCurrentTxPosPointerJustCount OBJECT-TYPE
	    SYNTAX	   Gauge32
	    MAX-ACCESS	read-only
	    STATUS	   current
	    DESCRIPTION
		      "The counter associated with the number of 
		       positive pointer justification events that occurred
		       on the transmit side of a SONET/SDH path 
		       in the current 15 minute interval."
       ::= { hneSonetPathCurrentEntry 3 }        
       
  hneSonetPathCurrentTxNegPointerJustCount OBJECT-TYPE
	    SYNTAX	   Gauge32
	    MAX-ACCESS	read-only
	    STATUS	   current
	    DESCRIPTION
		      "The counter associated with the number of 
		       negative pointer justification events that occurred
		       on the transmit side of a SONET/SDH path 
		       in the current 15 minute interval."
       ::= { hneSonetPathCurrentEntry 4 }                   


  -- the HNE SONET/SDH Path Interval Table
   
  -- The HNE SONET/SDH Path Interval Table
  -- contains various statistics
  -- collected by each system over a maximum
  -- of the previous 24 hours of
  -- operation.  The past 24 hours may be broken into 96
  -- completed 15 minute intervals.
  -- A system is required to store at
  -- least 4 completed 15 minute interval.
  -- The default value is 32 intervals.      
  
  
  hneSonetPathIntervalTable OBJECT-TYPE
       SYNTAX     SEQUENCE OF    HneSonetPathIntervalEntry
       MAX-ACCESS not-accessible
       STATUS     current
       DESCRIPTION
            "The HNE SONET/SDH Path Interval table."
       ::= { hneMIBStats 6 } 
    
  hneSonetPathIntervalEntry OBJECT-TYPE
       SYNTAX  HneSonetPathIntervalEntry
       MAX-ACCESS  not-accessible
       STATUS  current
       DESCRIPTION
         "An entry in the HNE sonet path interval table.  An entry 
          contains HNE specific sonet path information not found 
          in the SONET / SDH MIB."
       AUGMENTS { sonetPathIntervalEntry }   
       ::= { hneSonetPathIntervalTable 1}
          
       HneSonetPathIntervalEntry ::= SEQUENCE {
           hneSonetPathIntervalRxPosPointerJustCount   Gauge32,
           hneSonetPathIntervalRxNegPointerJustCount   Gauge32,
           hneSonetPathIntervalTxPosPointerJustCount   Gauge32,
           hneSonetPathIntervalTxNegPointerJustCount   Gauge32
       }
       
  hneSonetPathIntervalRxPosPointerJustCount OBJECT-TYPE
	    SYNTAX	   Gauge32
	    MAX-ACCESS	read-only
	    STATUS	   current
	    DESCRIPTION
		      "The counter associated with the number of 
		       positive pointer justification events that occurred
		       on the receive side of a SONET/SDH path 
		       in a particular 15-minute interval 
		       in the past 24 hours."
       ::= { hneSonetPathIntervalEntry 1 }        
       
  hneSonetPathIntervalRxNegPointerJustCount OBJECT-TYPE
	    SYNTAX	   Gauge32
	    MAX-ACCESS	read-only
	    STATUS	   current
	    DESCRIPTION
		      "The counter associated with the number of 
		       negative pointer justification events that occurred
		       on the receive side of a SONET/SDH path 
		       in a particular 15-minute interval 
		       in the past 24 hours."
       ::= { hneSonetPathIntervalEntry 2 }    

  hneSonetPathIntervalTxPosPointerJustCount OBJECT-TYPE
	    SYNTAX	   Gauge32
	    MAX-ACCESS	read-only
	    STATUS	   current
	    DESCRIPTION
		      "The counter associated with the number of 
		       positive pointer justification events that occurred
		       on the transmit side of a SONET/SDH path 
		       in a particular 15-minute interval 
		       in the past 24 hours."
       ::= { hneSonetPathIntervalEntry 3 }        
       
  hneSonetPathIntervalTxNegPointerJustCount OBJECT-TYPE
	    SYNTAX	   Gauge32
	    MAX-ACCESS	read-only
	    STATUS	   current
	    DESCRIPTION
		      "The counter associated with the number of 
		       negative pointer justification events that occurred
		       on the transmit side of a SONET/SDH path 
             in a particular 15-minute interval 
		       in the past 24 hours."
       ::= { hneSonetPathIntervalEntry 4 }         

  -- HNE ATM LIU Current Table

  -- HNE ATM Line Interface Unit Current Table contains 
  -- various ATM traffic statistics on a line interface
  -- unit being collected for the 
  -- current 15 minute interval.
  
  hneAtmLiuCurrentTable OBJECT-TYPE
       SYNTAX     SEQUENCE OF    HneAtmLiuCurrentEntry
       MAX-ACCESS not-accessible
       STATUS     current
       DESCRIPTION
            "The HNE ATM Current table."
       ::= { hneMIBStats 7 } 
    
  hneAtmLiuCurrentEntry OBJECT-TYPE
       SYNTAX     HneAtmLiuCurrentEntry
       MAX-ACCESS not-accessible
       STATUS     current
       DESCRIPTION
         "An entry in the HNE line interface unit current entry table.  An entry 
          contains atm statistics for an entire line interface unit"
       INDEX   { ifIndex }    
       ::= { hneAtmLiuCurrentTable 1}
          
       HneAtmLiuCurrentEntry ::= SEQUENCE {           
           hneAtmLiuCurrentPhysLayerCellCount         Gauge32,
           hneAtmLiuCurrentRxCellCount                Counter64,
           hneAtmLiuCurrentTxCellCount                Gauge32,
           hneAtmLiuCurrentCongestionDroppedCount     Gauge32,
           hneAtmLiuCurrentInvalidCellCount           Gauge32,
           hneAtmLiuCurrentErroredOAMCellCount        Gauge32,
           hneAtmLiuCurrentValidOAMCellCount          Gauge32,
           hneAtmLiuCurrentTxOverrunCount             Gauge32,         
           hneAtmLiuCurrentMissingHeaderCellCount     Gauge32,
           hneAtmLiuCurrentNonRoutableCellCount       Gauge32,
           hneAtmLiuCurrentVcSearchFailedCount        Gauge32,
           hneAtmLiuCurrentInternalParityErrorCount   Gauge32  
       }   

  hneAtmLiuCurrentPhysLayerCellCount     OBJECT-TYPE
	    SYNTAX	   Gauge32
	    MAX-ACCESS	read-only
	    STATUS	   current
	    DESCRIPTION
		      "The counter associated with the number of  
		       physical layer cells encountered on all atm interfaces 
		       on a line interface unit in the current 15 minute interval."
       ::= { hneAtmLiuCurrentEntry 1 }         

  hneAtmLiuCurrentRxCellCount     OBJECT-TYPE
	    SYNTAX	   Counter64
	    MAX-ACCESS	read-only
	    STATUS	   current
	    DESCRIPTION
            "The counter associated with the number of cells  
		       received on all atm interfaces on a line interface unit 
		       in the current 15 minute interval."		    
       ::= { hneAtmLiuCurrentEntry 2 }    
       
  hneAtmLiuCurrentTxCellCount    OBJECT-TYPE
	    SYNTAX	   Gauge32
	    MAX-ACCESS	read-only
	    STATUS	   current
	    DESCRIPTION
		      "The counter associated with the number of cells 
		       transmitted on all atm interfaces on a line interface unit 
		       in the current 15 minute interval."
       ::= { hneAtmLiuCurrentEntry 3 }                

  hneAtmLiuCurrentCongestionDroppedCount     OBJECT-TYPE
	    SYNTAX	   Gauge32
	    MAX-ACCESS	read-only
	    STATUS	   current
	    DESCRIPTION
		      "The counter associated with the number of 
		       cells dropped due to congestion on all atm interfaces 
		       on a line interface unit in the current 15 minute interval."
       ::= { hneAtmLiuCurrentEntry 4 }                 

  hneAtmLiuCurrentInvalidCellCount    OBJECT-TYPE
	    SYNTAX	   Gauge32
	    MAX-ACCESS	read-only
	    STATUS	   current
	    DESCRIPTION
		      "The counter associated with the number of 
		       invalid cells encountered on all atm interfaces on a line 
		       interface unit in the current 15 minute interval."
       ::= { hneAtmLiuCurrentEntry 5 }                 

  hneAtmLiuCurrentErroredOAMCellCount    OBJECT-TYPE
	    SYNTAX	   Gauge32
	    MAX-ACCESS	read-only
	    STATUS	   current
	    DESCRIPTION
		      "The counter associated with the number of 
		       errored OAM cells encountered on all atm interfaces 
		       on a line interface unit 
		       in the current 15 minute interval."
       ::= { hneAtmLiuCurrentEntry 6 }          
       
 hneAtmLiuCurrentValidOAMCellCount             OBJECT-TYPE
	    SYNTAX	   Gauge32
	    MAX-ACCESS	read-only
	    STATUS	   current
	    DESCRIPTION
		      "The counter associated with the number of 
		       valid OAM cells encountered on all atm interfaces 
		       on a line interface unit 
		       in the current 15 minute interval."
       ::= { hneAtmLiuCurrentEntry 7 }         
      
  hneAtmLiuCurrentTxOverrunCount  OBJECT-TYPE
     SYNTAX	      Gauge32
     MAX-ACCESS	read-only
     STATUS	      current
     DESCRIPTION
	         "The counter associated with the number of times the output 
	         queue of the atm interfaces on a line interface unit 
	         was overrun in the current 15 minute interval."
     ::= { hneAtmLiuCurrentEntry 8 }   
 
  hneAtmLiuCurrentMissingHeaderCellCount  OBJECT-TYPE
	    SYNTAX	   Gauge32
	    MAX-ACCESS	read-only
	    STATUS	   current
	    DESCRIPTION
		      "The counter associated with the number of times a   
		       physical cell is found missing an internal header in the
		       current 15 minute interval."
       ::= { hneAtmLiuCurrentEntry 9 }    
       
  hneAtmLiuCurrentNonRoutableCellCount  OBJECT-TYPE
	    SYNTAX	   Gauge32
	    MAX-ACCESS	read-only
	    STATUS	   current
	    DESCRIPTION
		      "The counter associated with the number of 
		       non routable cells encountered on all of the 
		       atm interfaces on a line interface unit 
		       in the current 15 minute interval."
       ::= { hneAtmLiuCurrentEntry 10}    

  hneAtmLiuCurrentVcSearchFailedCount  OBJECT-TYPE
	    SYNTAX	   Gauge32
	    MAX-ACCESS	read-only
	    STATUS	   current
	    DESCRIPTION
		      "The counter associated with the number of 
		       virtual ciruit search failures encountered 
		       on all of the atm interfaces on a line interface unit 
		       in the current 15 minute interval."
       ::= { hneAtmLiuCurrentEntry 11 }    

  hneAtmLiuCurrentInternalParityErrorCount OBJECT-TYPE
	    SYNTAX	   Gauge32
	    MAX-ACCESS	read-only
	    STATUS	   current
	    DESCRIPTION
		      "The counter associated with the number of 
		       internal parity errors encountered 
		       in the current 15 minute interval."
       ::= { hneAtmLiuCurrentEntry 12 }    

  -- The HNE ATM LIU History Table
   
  -- The HNE ATM Line Interface Unit History Table
  -- contains various statistics
  -- collected by each system over a maximum
  -- of the previous 24 hours of
  -- operation.  The past 24 hours may be broken into 96
  -- completed 15 minute intervals.
  -- A system is required to store at
  -- least 4 completed 15 minute interval.
  -- The default value is 32 intervals.      
  
  hneAtmLiuHistoryTable OBJECT-TYPE
       SYNTAX     SEQUENCE OF    HneAtmLiuHistoryEntry
       MAX-ACCESS not-accessible
       STATUS     current
       DESCRIPTION
            "The HNE ATM Line Interface Unit History table."
       ::= { hneMIBStats 8 } 
    
  hneAtmLiuHistoryEntry OBJECT-TYPE
       SYNTAX     HneAtmLiuHistoryEntry
       MAX-ACCESS not-accessible
       STATUS     current
       DESCRIPTION
         "An entry in the HNE line interface unit history entry table.  An entry 
          contains ATM statistics associated with a 
          sonet line."
       INDEX   { ifIndex,
                 atmfM4CellProtoHistIndex }    
       ::= { hneAtmLiuHistoryTable 1}
          
       HneAtmLiuHistoryEntry ::= SEQUENCE {           
           hneAtmLiuHistoryPhysLayerCellCount         Gauge32,
           hneAtmLiuHistoryRxCellCount                Counter64,
           hneAtmLiuHistoryTxCellCount                Gauge32,
           hneAtmLiuHistoryCongestionDroppedCount     Gauge32,
           hneAtmLiuHistoryInvalidCellCount           Gauge32,
           hneAtmLiuHistoryErroredOAMCellCount        Gauge32,
           hneAtmLiuHistoryValidOAMCellCount          Gauge32,
           hneAtmLiuHistoryTxOverrunCount             Gauge32,         
           hneAtmLiuHistoryMissingHeaderCellCount     Gauge32,
           hneAtmLiuHistoryNonRoutableCellCount       Gauge32,
           hneAtmLiuHistoryVcSearchFailedCount        Gauge32,
           hneAtmLiuHistoryInternalParityErrorCount   Gauge32  
       }   

  hneAtmLiuHistoryPhysLayerCellCount     OBJECT-TYPE
	    SYNTAX	   Gauge32
	    MAX-ACCESS	read-only
	    STATUS	   current
	    DESCRIPTION
		      "The counter associated with the number of  
		       physical layer cells encountered on all ATM 
		       interfaces on a line interface unit in a particular 15-minute interval 
		       in the past 24 hours."
       ::= { hneAtmLiuHistoryEntry 1 }         

  hneAtmLiuHistoryRxCellCount     OBJECT-TYPE
	    SYNTAX	   Counter64
	    MAX-ACCESS	read-only
	    STATUS	   current
	    DESCRIPTION
            "The counter associated with the number of cells  
		       received on all ATM interfaces on a line interface unit 
		       in a particular 15-minute interval 
		       in the past 24 hours."
       ::= { hneAtmLiuHistoryEntry 2 }    
       
  hneAtmLiuHistoryTxCellCount    OBJECT-TYPE
	    SYNTAX	   Gauge32
	    MAX-ACCESS	read-only
	    STATUS	   current
	    DESCRIPTION
		      "The counter associated with the number of cells 
		       transmitted on all ATM interfaces on a line interface 
		       unit in a particular 15-minute interval 
		       in the past 24 hours."
       ::= { hneAtmLiuHistoryEntry 3 }                

  hneAtmLiuHistoryCongestionDroppedCount     OBJECT-TYPE
	    SYNTAX	   Gauge32
	    MAX-ACCESS	read-only
	    STATUS	   current
	    DESCRIPTION
		      "The counter associated with the number of 
		       cells dropped due to congestion on all ATM interfaces 
		       on a line interface unit in a particular 15-minute interval 
		       in the past 24 hours."
       ::= { hneAtmLiuHistoryEntry 4 }                 

  hneAtmLiuHistoryInvalidCellCount    OBJECT-TYPE
	    SYNTAX	   Gauge32
	    MAX-ACCESS	read-only
	    STATUS	   current
	    DESCRIPTION
		      "The counter associated with the number of 
		       invalid cells encountered on all ATM interfaces 
		       on a line interface unit in a particular 15-minute interval 
		       in the past 24 hours."
       ::= { hneAtmLiuHistoryEntry 5 }                 

  hneAtmLiuHistoryErroredOAMCellCount    OBJECT-TYPE
	    SYNTAX	   Gauge32
	    MAX-ACCESS	read-only
	    STATUS	   current
	    DESCRIPTION
		      "The counter associated with the number of 
		       errored OAM cells encountered on all ATM interfaces 
		       on a line interface unit in a particular 
		       15-minute interval in the past 24 hours."
       ::= { hneAtmLiuHistoryEntry 6 }          
       
  hneAtmLiuHistoryValidOAMCellCount             OBJECT-TYPE
	    SYNTAX	   Gauge32
	    MAX-ACCESS	read-only
	    STATUS	   current
	    DESCRIPTION
		      "The counter associated with the number of 
		       valid OAM cells encountered on all ATM interfaces 
		       on a line interface unit in a particular 
		       15-minute interval in the past 24 hours."
       ::= { hneAtmLiuHistoryEntry 7 }         
      
  hneAtmLiuHistoryTxOverrunCount  OBJECT-TYPE
       SYNTAX	   Gauge32
       MAX-ACCESS	read-only
       STATUS	   current
       DESCRIPTION
	       "The counter associated with the number of times the output 
	        queue of the ATM interfaces on a line interface unit 
	        was overrun in a particular 15-minute interval 
           in the past 24 hours."
     ::= { hneAtmLiuHistoryEntry 8 }   
 
  hneAtmLiuHistoryMissingHeaderCellCount  OBJECT-TYPE
	    SYNTAX	   Gauge32
	    MAX-ACCESS	read-only
	    STATUS	   current
	    DESCRIPTION
      	    "The counter associated with the number of times a   
		       physical cell is found missing an internal header 
		       in a particular 15-minute interval in the 
		       past 24 hours."
       ::= { hneAtmLiuHistoryEntry 9 }    
       
  hneAtmLiuHistoryNonRoutableCellCount  OBJECT-TYPE
	    SYNTAX	   Gauge32
	    MAX-ACCESS	read-only
	    STATUS	   current
	    DESCRIPTION
		      "The counter associated with the number of 
		       non routable cells encountered on all of the 
		       ATM interfaces on a line interface unit in a 
		       particular 15-minute interval 
		       in the past 24 hours."
       ::= { hneAtmLiuHistoryEntry 10}    

  hneAtmLiuHistoryVcSearchFailedCount  OBJECT-TYPE
	    SYNTAX	   Gauge32
	    MAX-ACCESS	read-only
	    STATUS	   current
	    DESCRIPTION
		      "The counter associated with the number of 
		       virtual ciruit search failures encountered 
		       on all of the ATM interfaces on a line interface unit 
		       in a particular 15-minute 
		       interval in the past 24 hours."
       ::= { hneAtmLiuHistoryEntry 11 }    

  hneAtmLiuHistoryInternalParityErrorCount OBJECT-TYPE
	    SYNTAX	   Gauge32
	    MAX-ACCESS	read-only
	    STATUS	   current
	    DESCRIPTION
		      "The counter associated with the number of 
		       internal parity errors encountered 
		       in a particular 15-minute interval 
		       in the past 24 hours."
       ::= { hneAtmLiuHistoryEntry 12 }    

  -- HNE ATM Virtual Channel Link Current Table

  -- HNE ATM Virtual Channel Link Current table contains 
  -- various statistics being collected for the 
  -- current 15 minute interval.
  
  hneVclCurrentTable OBJECT-TYPE
       SYNTAX     SEQUENCE OF    HneVclCurrentEntry
       MAX-ACCESS not-accessible
       STATUS     current
       DESCRIPTION
            "The HNE ATM Virtual Channel Link Current table."
       ::= { hneMIBStats 9 } 
    
  hneVclCurrentEntry OBJECT-TYPE
       SYNTAX     HneVclCurrentEntry
       MAX-ACCESS not-accessible
       STATUS     current
       DESCRIPTION
         "An entry in the HNE vitual channel link current entry table.  
          An entry contains virtual channel statistics."
       INDEX   { ifIndex,
                 atmVclVpi,
                 atmVclVci }    
       ::= { hneVclCurrentTable 1}
          
       HneVclCurrentEntry ::= SEQUENCE {           
            hneVclCurrentBIP16Count                 Gauge32,
            hneVclCurrentRxSECBCount                Gauge32,   
            hneVclCurrentRxLostCellCount            Gauge32,
            hneVclCurrentRxMisinsertedCellCount     Gauge32,
            hneVclCurrentRxBIPVCount                Gauge32,
            hneVclCurrentTxSECBCount                Gauge32,
            hneVclCurrentTxLostCellCount            Gauge32,
            hneVclCurrentTxMisinsertedCellCount     Gauge32,
            hneVclCurrentTxBIPVCount                Gauge32
      }   

  
  hneVclCurrentBIP16Count                  OBJECT-TYPE
	    SYNTAX	   Gauge32
	    MAX-ACCESS	read-only
	    STATUS	   current
	    DESCRIPTION
		       "The counter associated with the number of virtual 
		       channel cells with a Bit Interleave Parity (BIP) error 
		       in the current 15 minute interval."
       ::= { hneVclCurrentEntry 5 }   
  
  hneVclCurrentRxSECBCount           OBJECT-TYPE
	    SYNTAX	   Gauge32
	    MAX-ACCESS	read-only
	    STATUS	   current
	    DESCRIPTION
		      "The counter associated with the number of 
		       Severely Errored Cell Blocks (SECB) received within 
		       virtual channel cells in the current 
		       15 minute interval."
       ::= { hneVclCurrentEntry 6 }   
  
  hneVclCurrentRxLostCellCount       OBJECT-TYPE
	    SYNTAX	   Gauge32
	    MAX-ACCESS	read-only
	    STATUS	   current
	    DESCRIPTION
		      "The counter associated with the number of 
		       received cells lost within an ingress virtual channel 
		       in the current 15 minute interval."
       ::= { hneVclCurrentEntry 7 }   
  
  hneVclCurrentRxMisinsertedCellCount     OBJECT-TYPE
	    SYNTAX	   Gauge32
	    MAX-ACCESS	read-only
	    STATUS	   current
	    DESCRIPTION
		      "The counter associated with the number of 
		       received cells misinserted in an igress virtual channel 
		       in the current 15 minute interval."
       ::= { hneVclCurrentEntry 8 }   
  
  hneVclCurrentRxBIPVCount           OBJECT-TYPE
	    SYNTAX	   Gauge32
	    MAX-ACCESS	read-only
	    STATUS	   current
	    DESCRIPTION
		       "The counter associated with the number of 
		       Bit Interleave Parity Violations (BIPV) received
		       in virtual channel in the current 15 minute interval."
       ::= { hneVclCurrentEntry 9 }   
  
  hneVclCurrentTxSECBCount            OBJECT-TYPE
	    SYNTAX	   Gauge32
	    MAX-ACCESS	read-only
	    STATUS	   current
	    DESCRIPTION
		      "The counter associated with the number of 
		       Severely Errored Cell Blocks (SECB) virtual channel 
		       cells transmitted in the current 15 minute interval."
       ::= { hneVclCurrentEntry 10 }   
  
  hneVclCurrentTxLostCellCount        OBJECT-TYPE
	    SYNTAX	   Gauge32
	    MAX-ACCESS	read-only
	    STATUS	   current
	    DESCRIPTION
		      "The counter associated with the number of 
		       transmitted cells lost within an eggress virtual channel 
		       in the current 15 minute interval."
       ::= { hneVclCurrentEntry 11 }   
  
  hneVclCurrentTxMisinsertedCellCount OBJECT-TYPE
	    SYNTAX	   Gauge32
	    MAX-ACCESS	read-only
	    STATUS	   current
	    DESCRIPTION
		      "The counter associated with the number of 
		       transmitted cells misinserted within a eggress virtual channel 
		       in the current 15 minute interval."
       ::= { hneVclCurrentEntry 12 }   
  
  hneVclCurrentTxBIPVCount            OBJECT-TYPE
	    SYNTAX	   Gauge32
	    MAX-ACCESS	read-only
	    STATUS	   current
	    DESCRIPTION
		      "The counter associated with the number of 
		       Bit Interleave Parity Violations (BIPV)  
		       virtual channel cells transmitted 
		       in the current 15 minute interval."
       ::= { hneVclCurrentEntry 13 }   

  -- the HNE Virtual Channel Link History Table
   
  -- The HNE Virtual Channel Link History Table
  -- contains various statistics
  -- collected by each system over a maximum
  -- of the previous 24 hours of
  -- operation.  The past 24 hours may be broken into 96
  -- completed 15 minute intervals.
  -- A system is required to store at
  -- least 4 completed 15 minute interval.
  -- The default value is 32 intervals.      
  

  hneVclHistoryTable OBJECT-TYPE
       SYNTAX     SEQUENCE OF    HneVclHistoryEntry
       MAX-ACCESS not-accessible
       STATUS     current
       DESCRIPTION
            "The HNE ATM Virtual Channel Link History table."
       ::= { hneMIBStats 10 } 
    
  hneVclHistoryEntry OBJECT-TYPE
       SYNTAX     HneVclHistoryEntry
       MAX-ACCESS not-accessible
       STATUS     current
       DESCRIPTION
         "An entry in the HNE vitual channel link history entry table.  
          An entry contains virtual channel link statistics."
       INDEX   { ifIndex,
                 atmVclVpi,
                 atmVclVci,
                 atmfM4CellProtoHistIndex}    
       ::= { hneVclHistoryTable 1}
          
       HneVclHistoryEntry ::= SEQUENCE {       
            hneVclHistoryBIP16Count                       Gauge32,
            hneVclHistoryRxSECBCount                      Gauge32,   
            hneVclHistoryRxLostCellCount                  Gauge32,
            hneVclHistoryRxMisinsertedCellCount           Gauge32,
            hneVclHistoryRxBIPVCount                      Gauge32,
            hneVclHistoryTxSECBCount                      Gauge32,
            hneVclHistoryTxLostCellCount                  Gauge32,
            hneVclHistoryTxMisinsertedCellCount           Gauge32,
            hneVclHistoryTxBIPVCount                      Gauge32
      }   

  
  hneVclHistoryBIP16Count                  OBJECT-TYPE
	    SYNTAX	   Gauge32
	    MAX-ACCESS	read-only
	    STATUS	   current
	    DESCRIPTION
		       "The counter associated with the number of virtual 
		       channel cells with a Bit Interleave Parity (BIP) error 
		       in a particular 15-minute interval 
		       in the past 24 hours."
       ::= { hneVclHistoryEntry 5 }   
  
  hneVclHistoryRxSECBCount           OBJECT-TYPE
	    SYNTAX	   Gauge32
	    MAX-ACCESS	read-only
	    STATUS	   current
	    DESCRIPTION
		      "The counter associated with the number of 
		       Severely Errored Cell Blocks (SECB) received within 
		       virtual channel cells in a particular 15-minute interval 
		       in the past 24 hours."
       ::= { hneVclHistoryEntry 6 }   
  
  hneVclHistoryRxLostCellCount       OBJECT-TYPE
	    SYNTAX	   Gauge32
	    MAX-ACCESS	read-only
	    STATUS	   current
	    DESCRIPTION
		      "The counter associated with the number of 
		       received cells lost within an ingress virtual channel 
		       in a particular 15-minute interval 
		       in the past 24 hours."
       ::= { hneVclHistoryEntry 7 }   
  
  hneVclHistoryRxMisinsertedCellCount     OBJECT-TYPE
	    SYNTAX	   Gauge32
	    MAX-ACCESS	read-only
	    STATUS	   current
	    DESCRIPTION
		      "The counter associated with the number of 
		       received cells misinserted within an igress virtual channel 
		       in a particular 15-minute interval 
		       in the past 24 hours."
       ::= { hneVclHistoryEntry 8 }   
  
  hneVclHistoryRxBIPVCount           OBJECT-TYPE
	    SYNTAX	   Gauge32
	    MAX-ACCESS	read-only
	    STATUS	   current
	    DESCRIPTION
		       "The counter associated with the number of 
		       Bit Interleave Parity Violations (BIPV) received
		       in virtual channel in a particular 15-minute interval 
		       in the past 24 hours."
       ::= { hneVclHistoryEntry 9 }   
  
  hneVclHistoryTxSECBCount            OBJECT-TYPE
	    SYNTAX	   Gauge32
	    MAX-ACCESS	read-only
	    STATUS	   current
	    DESCRIPTION
		      "The counter associated with the number of 
		       Severely Errored Cell Blocks (SECB) virtual channel 
		       cells transmitted in a particular 15-minute interval 
		       in the past 24 hours."
       ::= { hneVclHistoryEntry 10 }   
  
  hneVclHistoryTxLostCellCount        OBJECT-TYPE
	    SYNTAX	   Gauge32
	    MAX-ACCESS	read-only
	    STATUS	   current
	    DESCRIPTION
		      "The counter associated with the number of 
		       transmitted cells lost within an eggress virtual channel 
		       in a particular 15-minute interval 
		       in the past 24 hours."
       ::= { hneVclHistoryEntry 11 }   
  
  hneVclHistoryTxMisinsertedCellCount OBJECT-TYPE
	    SYNTAX	   Gauge32
	    MAX-ACCESS	read-only
	    STATUS	   current
	    DESCRIPTION
		      "The counter associated with the number of 
		       transmitted cells misinserted within a eggress virtual channel 
		       in a particular 15-minute interval 
		       in the past 24 hours."
       ::= { hneVclHistoryEntry 12 }   
  
  hneVclHistoryTxBIPVCount            OBJECT-TYPE
	    SYNTAX	   Gauge32
	    MAX-ACCESS	read-only
	    STATUS	   current
	    DESCRIPTION
		      "The counter associated with the number of 
		       Bit Interleave Parity Violations (BIPV)  
		       virtual channel cells transmitted 
		       in a particular 15-minute interval 
		       in the past 24 hours."
       ::= { hneVclHistoryEntry 13 }   

  -- HNE ATM Virtual Path Link Current Table

  -- HNE ATM Virtual Path Link Current table contains 
  -- various statistics being collected for the 
  -- current 15 minute interval.
  
  hneVplCurrentTable OBJECT-TYPE
       SYNTAX     SEQUENCE OF    HneVplCurrentEntry
       MAX-ACCESS not-accessible
       STATUS     current
       DESCRIPTION
            "The HNE ATM Virtual Path Link Current table."
       ::= { hneMIBStats 11} 
    
  hneVplCurrentEntry OBJECT-TYPE
       SYNTAX     HneVplCurrentEntry
       MAX-ACCESS not-accessible
       STATUS     current
       DESCRIPTION
         "An entry in the HNE vitual path link current entry table.  
          An entry contains virtual path statistics."
       INDEX   { ifIndex,
                 atmVplVpi }    
       ::= { hneVplCurrentTable 1}
          
       HneVplCurrentEntry ::= SEQUENCE {           
            hneVplCurrentBIP16Count                       Gauge32,
            hneVplCurrentRxSECBCount                      Gauge32,   
            hneVplCurrentRxLostCellCount                  Gauge32,
            hneVplCurrentRxMisinsertedCellCount           Gauge32,
            hneVplCurrentRxBIPVCount                      Gauge32,
            hneVplCurrentTxSECBCount                      Gauge32,
            hneVplCurrentTxLostCellCount                  Gauge32,
            hneVplCurrentTxMisinsertedCellCount           Gauge32,
            hneVplCurrentTxBIPVCount                      Gauge32
      }   
  
  hneVplCurrentBIP16Count                  OBJECT-TYPE
	    SYNTAX	   Gauge32
	    MAX-ACCESS	read-only
	    STATUS	   current
	    DESCRIPTION
		       "The counter associated with the number of virtual 
		       path cells with a Bit Interleave Parity error (BIP)
		       in the current 15 minute interval."
       ::= { hneVplCurrentEntry 5 }   
  
  hneVplCurrentRxSECBCount           OBJECT-TYPE
	    SYNTAX	   Gauge32
	    MAX-ACCESS	read-only
	    STATUS	   current
	    DESCRIPTION
		      "The counter associated with the number of 
		       Severely Errored Cell Blocks (SECB) received within 
		       virtual path cells in the current 
		       15 minute interval."
       ::= { hneVplCurrentEntry 6 }   
  
  hneVplCurrentRxLostCellCount       OBJECT-TYPE
	    SYNTAX	   Gauge32
	    MAX-ACCESS	read-only
	    STATUS	   current
	    DESCRIPTION
		      "The counter associated with the number of 
		       received cells lost within an ingress virtual path 
		       in the current 15 minute interval."
       ::= { hneVplCurrentEntry 7 }   
  
  hneVplCurrentRxMisinsertedCellCount     OBJECT-TYPE
	    SYNTAX	   Gauge32
	    MAX-ACCESS	read-only
	    STATUS	   current
	    DESCRIPTION
		      "The counter associated with the number of 
		       received cells misinserted within an igress virtual path 
		       in the current 15 minute interval."
       ::= { hneVplCurrentEntry 8 }   
  
  hneVplCurrentRxBIPVCount           OBJECT-TYPE
	    SYNTAX	   Gauge32
	    MAX-ACCESS	read-only
	    STATUS	   current
	    DESCRIPTION
		       "The counter associated with the number of 
		       Bit Interleave Parity Violations (BIPV) received
		       in virtual path in the current 15 minute interval."
       ::= { hneVplCurrentEntry 9 }   
  
  hneVplCurrentTxSECBCount            OBJECT-TYPE
	    SYNTAX	   Gauge32
	    MAX-ACCESS	read-only
	    STATUS	   current
	    DESCRIPTION
		      "The counter associated with the number of 
		       Severely Errored Cell Blocks (SECB) virtual path 
		       cells transmitted in the current 15 minute interval."
       ::= { hneVplCurrentEntry 10 }   
  
  hneVplCurrentTxLostCellCount        OBJECT-TYPE
	    SYNTAX	   Gauge32
	    MAX-ACCESS	read-only
	    STATUS	   current
	    DESCRIPTION
		      "The counter associated with the number of 
		       transmitted cells lost within an eggress virtual path 
		       in the current 15 minute interval."
       ::= { hneVplCurrentEntry 11 }   
  
  hneVplCurrentTxMisinsertedCellCount OBJECT-TYPE
	    SYNTAX	   Gauge32
	    MAX-ACCESS	read-only
	    STATUS	   current
	    DESCRIPTION
		      "The counter associated with the number of 
		       transmitted cells misinserted within a eggress virtual path 
		       in the current 15 minute interval."
       ::= { hneVplCurrentEntry 12 }   
  
  hneVplCurrentTxBIPVCount            OBJECT-TYPE
	    SYNTAX	   Gauge32
	    MAX-ACCESS	read-only
	    STATUS	   current
	    DESCRIPTION
		      "The counter associated with the number of 
		       Bit Interleave Parity Violations (BIPV)  
		       virtual path cells transmitted 
		       in the current 15 minute interval."
       ::= { hneVplCurrentEntry 13 }   

  -- the HNE Virtual Path Link History Table
   
  -- The HNE Virtual Path Link History Table
  -- contains various statistics
  -- collected by each system over a maximum
  -- of the previous 24 hours of
  -- operation.  The past 24 hours may be broken into 96
  -- completed 15 minute intervals.
  -- A system is required to store at
  -- least 4 completed 15 minute interval.
  -- The default value is 32 intervals.      
  

  hneVplHistoryTable OBJECT-TYPE
       SYNTAX     SEQUENCE OF    HneVplHistoryEntry
       MAX-ACCESS not-accessible
       STATUS     current
       DESCRIPTION
            "The HNE ATM Virtual Path Link History table."
       ::= { hneMIBStats 12 } 
    
  hneVplHistoryEntry OBJECT-TYPE
       SYNTAX     HneVplHistoryEntry
       MAX-ACCESS not-accessible
       STATUS     current
       DESCRIPTION
         "An entry in the HNE vitual path link history entry table.  
          An entry contains virtual path statistics."
       INDEX   { ifIndex,
                 atmVplVpi,  
                 atmfM4CellProtoHistIndex}   
       ::= { hneVplHistoryTable 1}
          
       HneVplHistoryEntry ::= SEQUENCE {           
            hneVplHistoryBIP16Count                       Gauge32,
            hneVplHistoryRxSECBCount                      Gauge32,   
            hneVplHistoryRxLostCellCount                  Gauge32,
            hneVplHistoryRxMisinsertedCellCount           Gauge32,
            hneVplHistoryRxBIPVCount                      Gauge32,
            hneVplHistoryTxSECBCount                      Gauge32,
            hneVplHistoryTxLostCellCount                  Gauge32,
            hneVplHistoryTxMisinsertedCellCount           Gauge32,
            hneVplHistoryTxBIPVCount                      Gauge32
      }   
  
  hneVplHistoryBIP16Count                  OBJECT-TYPE
	    SYNTAX	   Gauge32
	    MAX-ACCESS	read-only
	    STATUS	   current
	    DESCRIPTION
		       "The counter associated with the number of virtual 
		       path cells with a Bit Interleave Parity error (BIP)
		       in a particular 15-minute interval 
		       in the past 24 hours."
       ::= { hneVplHistoryEntry 5 }   
  
  hneVplHistoryRxSECBCount           OBJECT-TYPE
	    SYNTAX	   Gauge32
	    MAX-ACCESS	read-only
	    STATUS	   current
	    DESCRIPTION
		      "The counter associated with the number of 
		       Severely Errored Cell Blocks (SECB) received within 
		       virtual path cells in a particular 15-minute interval 
		       in the past 24 hours."
       ::= { hneVplHistoryEntry 6 }   
  
  hneVplHistoryRxLostCellCount       OBJECT-TYPE
	    SYNTAX	   Gauge32
	    MAX-ACCESS	read-only
	    STATUS	   current
	    DESCRIPTION
		      "The counter associated with the number of 
		       received cells lost within an ingress virtual path 
		       in a particular 15-minute interval 
		       in the past 24 hours."
       ::= { hneVplHistoryEntry 7 }   
  
  hneVplHistoryRxMisinsertedCellCount     OBJECT-TYPE
	    SYNTAX	   Gauge32
	    MAX-ACCESS	read-only
	    STATUS	   current
	    DESCRIPTION
		      "The counter associated with the number of 
		       received cells misinserted within an igress virtual path 
		       in a particular 15-minute interval 
		       in the past 24 hours."
       ::= { hneVplHistoryEntry 8 }   
  
  hneVplHistoryRxBIPVCount           OBJECT-TYPE
	    SYNTAX	   Gauge32
	    MAX-ACCESS	read-only
	    STATUS	   current
	    DESCRIPTION
		       "The counter associated with the number of 
		       Bit Interleave Parity Violations (BIPV) received
		       in virtual path in a particular 15-minute interval 
		       in the past 24 hours."
       ::= { hneVplHistoryEntry 9 }   
  
  hneVplHistoryTxSECBCount            OBJECT-TYPE
	    SYNTAX	   Gauge32
	    MAX-ACCESS	read-only
	    STATUS	   current
	    DESCRIPTION
		      "The counter associated with the number of 
		       Severely Errored Cell Blocks (SECB) virtual path 
		       cells transmitted in a particular 15-minute interval 
		       in the past 24 hours."
       ::= { hneVplHistoryEntry 10 }   
  
  hneVplHistoryTxLostCellCount        OBJECT-TYPE
	    SYNTAX	   Gauge32
	    MAX-ACCESS	read-only
	    STATUS	   current
	    DESCRIPTION
		      "The counter associated with the number of 
		       transmitted cells lost within an eggress virtual path 
		       in a particular 15-minute interval 
		       in the past 24 hours."
       ::= { hneVplHistoryEntry 11 }   
  
  hneVplHistoryTxMisinsertedCellCount OBJECT-TYPE
	    SYNTAX	   Gauge32
	    MAX-ACCESS	read-only
	    STATUS	   current
	    DESCRIPTION
		      "The counter associated with the number of 
		       transmitted cells misinserted within a eggress virtual path 
		       in a particular 15-minute interval 
		       in the past 24 hours."
       ::= { hneVplHistoryEntry 12 }   
  
  hneVplHistoryTxBIPVCount            OBJECT-TYPE
	    SYNTAX	   Gauge32
	    MAX-ACCESS	read-only
	    STATUS	   current
	    DESCRIPTION
		      "The counter associated with the number of 
		       Bit Interleave Parity Violations (BIPV)  
		       virtual path cells transmitted 
		       in a particular 15-minute interval 
		       in the past 24 hours."
       ::= { hneVplHistoryEntry 13 }   
       
       END
