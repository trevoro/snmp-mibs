ISPGRPEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, RowStatus
			FROM SNMPv2-TC
		ispgrpExt
			FROM APENT-MIB;

--ISPGRPEXT MIB

    apIspgrpExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  ISP interface information"
      ::= { ispgrpExt 1}

apIspgrpTable OBJECT-TYPE
	SYNTAX          SEQUENCE OF APIspgrpEntry
	MAX-ACCESS      not-accessible
	STATUS          current
	DESCRIPTION
		"A list of Interfaces configured as uplinks to the specified ISP."
	::= { ispgrpExt 2 }

apIspgrpEntry OBJECT-TYPE
	SYNTAX          APIspgrpEntry
	MAX-ACCESS      not-accessible
	STATUS          current
	DESCRIPTION
		"A group of information to uniquely identify the uplinks to one 
		or more ISPs."
	INDEX   { apIspgrpName }
	--DEFAULT apjam-group apUplinkGroupInst, apIspgrpName
	--DEFAULT apjam-popup-def apUplinkGroupInst, Properties, local
	--DEFAULT apjam-popup-def apUplinkGroupInst, Statistics, local
	::= { apIspgrpTable 1 }

APIspgrpEntry ::= SEQUENCE {
		apIspgrpName                    DisplayString,
		apIspgrpIndex                   Integer32,
		apIspgrpTotalBwdth              Integer32,
		apIspgrpWebHostPipeBwdth        Integer32,
		apIspgrpMode                    Integer32,
	 	apIspgrpStatus 		            RowStatus
}

apIspgrpName OBJECT-TYPE
	SYNTAX          DisplayString (SIZE(1..16))
	MAX-ACCESS      read-create
	STATUS          current
	DESCRIPTION     
			"The name of the ISP connected to this composer."
	--DEFAULT ap-display-name	Group Name
	--DEFAULT apjam-popup-ref apUplinkGroupInst, Properties
	::= {apIspgrpEntry 1}

apIspgrpIndex OBJECT-TYPE
	SYNTAX          Integer32
	MAX-ACCESS      read-only
	STATUS  		current
	DESCRIPTION     
		"The unique index for each ISP defined."
	::= {apIspgrpEntry 2}

apIspgrpTotalBwdth OBJECT-TYPE
	SYNTAX          Integer32 
	MAX-ACCESS      read-only
	STATUS  		current
	DESCRIPTION     
		"The Total Bandwidth connected to the specified ISP."
	DEFVAL { 0 }
	--DEFAULT ap-display-name	Total Bandwidth
	--DEFAULT apjam-popup-ref apUplinkGroupInst, Statistics
	::= {apIspgrpEntry 3}

apIspgrpWebHostPipeBwdth OBJECT-TYPE
	SYNTAX          Integer32 
	MAX-ACCESS      read-only
	STATUS  		current
	DESCRIPTION     
		"The amount of Bandwidth reserved for flow pipes to configured
		web hosts."
	DEFVAL { 0 }
	--DEFAULT ap-display-name	Flow Pipe Bandwidth
	--DEFAULT apjam-popup-ref apUplinkGroupInst, Statistics
	::= {apIspgrpEntry 4}

apIspgrpMode OBJECT-TYPE
	SYNTAX          Integer32 
	MAX-ACCESS      read-create
	STATUS  		current
	DESCRIPTION     
		"This field signifies whether this ISP is considered the primary connection to the Internet or is a backup used only if the primary fails."

	DEFVAL { 1 }
	::= {apIspgrpEntry 5}

apIspgrpStatus OBJECT-TYPE
	SYNTAX          RowStatus
	MAX-ACCESS      read-create
	STATUS          current
	DESCRIPTION      
		"Status entry for this row "
	::= {apIspgrpEntry 6}


apIspLinkTable OBJECT-TYPE
	SYNTAX          SEQUENCE OF APIspLinkEntry
	MAX-ACCESS      not-accessible
	STATUS          current
	DESCRIPTION
		"A list of uplinks connected to a specified ISP."
	::= { ispgrpExt 3 }

apIspLinkEntry OBJECT-TYPE
	SYNTAX          APIspLinkEntry
	MAX-ACCESS      not-accessible
	STATUS          current
	DESCRIPTION
		"A record to describe each uplink to a specified ISP."
	INDEX   { apIspName, apIspLinkifIndex }
	--DEFAULT apjam-group apLinkInst, apIspLinkifIndex
	--DEFAULT apjam-popup-def apLinkInst, Properties, local
	::= { apIspLinkTable 1 }

APIspLinkEntry ::= SEQUENCE {
		apIspName                    DisplayString,
		apIspLinkIndex               Integer32,
		apIspLinkifIndex             Integer32,
	   apIspLinkBwdthAlloc          Integer32,
      apIspLinkBEBwdthAlloc        Integer32,
	 	apIspLinkStatus 				  RowStatus
}

apIspName OBJECT-TYPE
	SYNTAX          DisplayString (SIZE(1..16))
	MAX-ACCESS      read-create
	STATUS          current
	DESCRIPTION     
			"The name of the ISP which this uplink connects to."
	::= {apIspLinkEntry 1}

apIspLinkIndex OBJECT-TYPE
	SYNTAX          Integer32
	MAX-ACCESS      read-only
	STATUS  		current
	DESCRIPTION     
		"The unique index for each ISP link configured on this box."
	::= {apIspLinkEntry 2}

apIspLinkifIndex OBJECT-TYPE
	SYNTAX          Integer32
	MAX-ACCESS      read-create
	STATUS  		current
	DESCRIPTION     
		"The If Index of the link being specified as an uplink."
	--DEFAULT apjam-popup-ref apLinkInst, Properties
	::= {apIspLinkEntry 3}

apIspLinkBwdthAlloc		OBJECT-TYPE
			SYNTAX          Integer32 
			MAX-ACCESS      read-only
			STATUS  		current
	DESCRIPTION     
		"The statistics of allocated Bandwidth for this link."
	DEFVAL { 0 }
	::= {apIspLinkEntry 4}

apIspLinkBEBwdthAlloc		OBJECT-TYPE
			SYNTAX          Integer32 
			MAX-ACCESS      read-only
			STATUS  		current
	DESCRIPTION     
		"The amount of best effort traffic allocated on this link."
	DEFVAL { 0 }
	::= {apIspLinkEntry 5}

apIspLinkStatus OBJECT-TYPE
	SYNTAX          RowStatus
	MAX-ACCESS      read-create
	STATUS          current
	DESCRIPTION      
		"Status entry for this row "
	::= {apIspLinkEntry 6}

END
