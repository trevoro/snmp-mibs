Wellfleet-FNTS-ATM-MIB DEFINITIONS ::= BEGIN

-- Created by mdl2asn version 3.1
-- Creation date: Wed Aug 30 16:39:16 EDT 1995


    IMPORTS

      Counter, IpAddress
        FROM RFC1155-SMI
      OBJECT-TYPE
        FROM RFC-1212
      wfFntsAtmGroup
        FROM Wellfleet-COMMON-MIB;

    wfFntsAtmTable OBJECT-TYPE
        SYNTAX	SEQUENCE OF WfFntsAtmEntry
        ACCESS	not-accessible
        STATUS	mandatory
        DESCRIPTION
                "Fnts Atm line record"
        ::= { wfFntsAtmGroup 1 }

    wfFntsAtmEntry OBJECT-TYPE
        SYNTAX	WfFntsAtmEntry
        ACCESS	not-accessible
        STATUS	mandatory
        DESCRIPTION
                "An entry in the FntsAtm table"
        INDEX	{ wfFntsAtmSlot,
    		  wfFntsAtmConnector }
        ::= { wfFntsAtmTable 1 }


    WfFntsAtmEntry ::= SEQUENCE {
    	    wfFntsAtmDelete
    		INTEGER,
    	    wfFntsAtmDisable
    		INTEGER,
    	    wfFntsAtmState
    		INTEGER,
    	    wfFntsAtmSlot
    		INTEGER,
    	    wfFntsAtmConnector
    		INTEGER,
    	    wfFntsAtmCct
    		INTEGER,
    	    wfFntsAtmMtu
    		INTEGER,
    	    wfFntsAtmMadr
    		OCTET STRING,
	    wfFntsAtmIpAdr
        	IpAddress,
	    wfFntsAtmAtmState
    		INTEGER,
	    wfFntsAtmSpeed
    		INTEGER,
	    wfFntsAtmRxOctets
    		Counter,
	    wfFntsAtmRxFrames
    		Counter,
	    wfFntsAtmTxOctets
    		Counter,
	    wfFntsAtmTxFrames
    		Counter,
	    wfFntsAtmLackRescErrorRx
    		Counter,
	    wfFntsAtmInErrors
    		Counter,
	    wfFntsAtmOutErrors
    		Counter,
	    wfFntsAtmRxLongFrames
    		Counter,
	    wfFntsAtmTxClipFrames
    		Counter,
	    wfFntsAtmRxReplenMisses
    		Counter,
	    wfFntsAtmRxOverruns
    		Counter,
	    wfFntsAtmRxRingErrors
    		Counter,
	    wfFntsAtmTxRingErrors
    		Counter,
	    wfFntsAtmOpErrors
    		Counter,
	    wfFntsAtmRxProcessings
    		Counter,
	    wfFntsAtmTxProcessings
    		Counter,
	    wfFntsAtmTxCmplProcessings
    		Counter,
	    wfFntsAtmIntrProcessings
    		Counter,
	    wfFntsAtmSintProcessings
    		Counter,
	    wfFntsAtmPintProcessings
    		Counter,
	    wfFntsAtmRxRingLength
    		INTEGER,
	    wfFntsAtmTxRingLength
    		INTEGER,
	    wfFntsAtmCfgRxQueueLength
    		INTEGER,
	    wfFntsAtmCfgTxQueueLength
    		INTEGER,
	    wfFntsAtmLineNumber
    		INTEGER
        }

    wfFntsAtmDelete OBJECT-TYPE
        SYNTAX	INTEGER {
    		    create(1),
    		    delete(2)
    		}
        ACCESS	read-write
        STATUS	mandatory
        DESCRIPTION
                "create/delete parameter, dflt = created"
        DEFVAL	{ create }
        ::= { wfFntsAtmEntry 1 }

    wfFntsAtmDisable OBJECT-TYPE
        SYNTAX	INTEGER {
    		    enable(1),
    		    disable(2)
    		}
        ACCESS	read-write
        STATUS	mandatory
        DESCRIPTION
                "enable/disable parameter, dflt = enabled"
        DEFVAL	{ enable }
        ::= { wfFntsAtmEntry 2 }

    wfFntsAtmState OBJECT-TYPE
        SYNTAX	INTEGER {
    		    up(1),
    		    down(2),
    		    init(3),
    		    notpresent(4)
    		}
        ACCESS	read-only
        STATUS	mandatory
        DESCRIPTION
                "line driver state variable, Not Present, Init, Down, Up"
        DEFVAL	{ notpresent }
        ::= { wfFntsAtmEntry 3 }

    wfFntsAtmSlot OBJECT-TYPE
        SYNTAX	INTEGER(1..14)
        ACCESS	read-only
        STATUS	mandatory
        DESCRIPTION
                "instance ID Slot, filled in by driver"
        ::= { wfFntsAtmEntry 4 }

    wfFntsAtmConnector OBJECT-TYPE
        SYNTAX	INTEGER(1..44)
        ACCESS	read-only
        STATUS	mandatory
        DESCRIPTION
                "instance ID Connector, filled in by driver. For the ASN
                this attribute is an encoded value and is equal to
                'module'*10 + 'connector'. Where 'module' is defined in
                attribute 42 and 'connector' is defined in attribute 43
                of this table. For non-ASN platforms this attribute is
                the physical connector number on the slot."
        ::= { wfFntsAtmEntry 5 }

    wfFntsAtmCct OBJECT-TYPE
        SYNTAX	INTEGER(1..1023)
        ACCESS	read-write
        STATUS	mandatory
        DESCRIPTION
                "cct number for this line instance"
        ::= { wfFntsAtmEntry 6 }

    wfFntsAtmMtu OBJECT-TYPE
        SYNTAX	INTEGER {
    		    default(4508)
    		}
        ACCESS	read-write
        STATUS	mandatory
        DESCRIPTION
                "mtu parameter, fixed"
        DEFVAL	{ default }
        ::= { wfFntsAtmEntry 7 }

    wfFntsAtmMadr OBJECT-TYPE
        SYNTAX	OCTET STRING
        ACCESS	read-only
        STATUS	mandatory
        DESCRIPTION
                "line MAC address, fixed - line driver fills in"
        ::= { wfFntsAtmEntry 8 }

    wfFntsAtmIpAdr OBJECT-TYPE
        SYNTAX	IpAddress
        ACCESS	read-only
        STATUS	mandatory
        DESCRIPTION
                "Ip Address, for the Sonet RPU"
        ::= { wfFntsAtmEntry 9 }

    wfFntsAtmAtmState OBJECT-TYPE
        SYNTAX	INTEGER {
    		    notready(1),
    		    init(2),
		    intloop(3),
		    extloop(4),
		    reset(5),
		    down(6),
		    up(7),
    		    notpresent(9)
    		}
        ACCESS	read-only
        STATUS	mandatory
        DESCRIPTION
                "line driver state variable, Not Present, Init, Down, Up"
        DEFVAL	{ notpresent }
        ::= { wfFntsAtmEntry 10 }

    wfFntsAtmSpeed OBJECT-TYPE
        SYNTAX	INTEGER {
    		    default(50)
    		}
        ACCESS	read-only
        STATUS	mandatory
        DESCRIPTION
                "Atm Interface speed in Meg bps."
        DEFVAL	{ default }
        ::= { wfFntsAtmEntry 11 }

    wfFntsAtmRxOctets OBJECT-TYPE
        SYNTAX	Counter
        ACCESS	read-only
        STATUS	mandatory
        DESCRIPTION
                "counts the number of bytes received from the Atm interface."
        ::= { wfFntsAtmEntry 12 }

    wfFntsAtmRxFrames OBJECT-TYPE
        SYNTAX	Counter
        ACCESS	read-only
        STATUS	mandatory
        DESCRIPTION
                "counts the number of frames received from the Atm interface."
        ::= { wfFntsAtmEntry 13 }

    wfFntsAtmTxOctets OBJECT-TYPE
        SYNTAX	Counter
        ACCESS	read-only
        STATUS	mandatory
        DESCRIPTION
                "counts the number of bytes sent to the Atm interface."
        ::= { wfFntsAtmEntry 14 }

    wfFntsAtmTxFrames OBJECT-TYPE
        SYNTAX	Counter
        ACCESS	read-only
        STATUS	mandatory
        DESCRIPTION
                "counts the number of frames sent to the Atm interface."
        ::= { wfFntsAtmEntry 15 }

    wfFntsAtmLackRescErrorRx OBJECT-TYPE
        SYNTAX	Counter
        ACCESS	read-only
        STATUS	mandatory
        DESCRIPTION
                "counts the number of requested buffers not available to the 
                 driver."
        ::= { wfFntsAtmEntry 16 }

    wfFntsAtmInErrors OBJECT-TYPE
        SYNTAX	Counter
        ACCESS	read-only
        STATUS	mandatory
        DESCRIPTION
               "counts the number of errors on the receive side of the driver."
        ::= { wfFntsAtmEntry 17 }

    wfFntsAtmOutErrors OBJECT-TYPE
        SYNTAX	Counter
        ACCESS	read-only
        STATUS	mandatory
        DESCRIPTION
                "counts the number of errors on the transmit side of the 
                 driver."
        ::= { wfFntsAtmEntry 18 }

    wfFntsAtmRxLongFrames OBJECT-TYPE
        SYNTAX	Counter
        ACCESS	read-only
        STATUS	mandatory
        DESCRIPTION
                "counts the number of received frames too long."
        ::= { wfFntsAtmEntry 19 }

    wfFntsAtmTxClipFrames OBJECT-TYPE
        SYNTAX	Counter
        ACCESS	read-only
        STATUS	mandatory
        DESCRIPTION
                "counts the number of transmit frames dropped because of no 
                 transmit queue space."
        ::= { wfFntsAtmEntry 20 }

    wfFntsAtmRxReplenMisses OBJECT-TYPE
        SYNTAX	Counter
        ACCESS	read-only
        STATUS	mandatory
        DESCRIPTION
                "counts the number of the buffer requests without response."
        ::= { wfFntsAtmEntry 21 }

    wfFntsAtmRxOverruns OBJECT-TYPE
        SYNTAX	Counter
        ACCESS	read-only
        STATUS	mandatory
        DESCRIPTION
                "counts the number of receiver overruns."
        ::= { wfFntsAtmEntry 22 }

    wfFntsAtmRxRingErrors OBJECT-TYPE
        SYNTAX	Counter
        ACCESS	read-only
        STATUS	mandatory
        DESCRIPTION
                "counts the number of receiver ring errors."
        ::= { wfFntsAtmEntry 23 }

    wfFntsAtmTxRingErrors OBJECT-TYPE
        SYNTAX	Counter
        ACCESS	read-only
        STATUS	mandatory
        DESCRIPTION
                "counts the number of transmit ring errors."
        ::= { wfFntsAtmEntry 24 }

    wfFntsAtmOpErrors OBJECT-TYPE
        SYNTAX	Counter
        ACCESS	read-only
        STATUS	mandatory
        DESCRIPTION
                "counts the number of operational driver errors."
        ::= { wfFntsAtmEntry 25 }

    wfFntsAtmRxProcessings OBJECT-TYPE
        SYNTAX	Counter
        ACCESS	read-only
        STATUS	mandatory
        DESCRIPTION
                "counts the number of times the receive processing 
                has been called."
        ::= { wfFntsAtmEntry 26 }

    wfFntsAtmTxProcessings OBJECT-TYPE
        SYNTAX	Counter
        ACCESS	read-only
        STATUS	mandatory
        DESCRIPTION
                "counts the number of times the transmit processing 
                has been called."
        ::= { wfFntsAtmEntry 27 }

    wfFntsAtmTxCmplProcessings OBJECT-TYPE
        SYNTAX	Counter
        ACCESS	read-only
        STATUS	mandatory
        DESCRIPTION
                "counts the number of times the transmit complete processing 
                has been called."
        ::= { wfFntsAtmEntry 28 }

    wfFntsAtmIntrProcessings OBJECT-TYPE
        SYNTAX	Counter
        ACCESS	read-only
        STATUS	mandatory
        DESCRIPTION
                "counts the number of times the interrupt service routine
                has been called"
        ::= { wfFntsAtmEntry 29 }

    wfFntsAtmSintProcessings OBJECT-TYPE
        SYNTAX	Counter
        ACCESS	read-only
        STATUS	mandatory
        DESCRIPTION
                "counts the number of times the change state interrupt 
                has been called."
        ::= { wfFntsAtmEntry 30 
}

    wfFntsAtmPintProcessings OBJECT-TYPE
        SYNTAX	Counter
        ACCESS	read-only
        STATUS	mandatory
        DESCRIPTION
                "counts the number of times the primitive interrupt service 
                routine has been called."
        ::= { wfFntsAtmEntry 31 }

    wfFntsAtmRxRingLength OBJECT-TYPE
        SYNTAX	INTEGER {
    		    default(63)
    		}
        ACCESS	read-write
        STATUS	mandatory
        DESCRIPTION
                "Atm Interface Receiver Ring Length."
        DEFVAL	{ default }
        ::= { wfFntsAtmEntry 32 }

    wfFntsAtmTxRingLength OBJECT-TYPE
        SYNTAX	INTEGER {
    		    default(63)
    		}
        ACCESS	read-write
        STATUS	mandatory
        DESCRIPTION
                "Atm Interface Transmit Ring Length."
        DEFVAL	{ default }
        ::= { wfFntsAtmEntry 33 }

    wfFntsAtmCfgRxQueueLength OBJECT-TYPE
        SYNTAX	INTEGER {
    		    default(127)
    		}
        ACCESS	read-write
        STATUS	mandatory
        DESCRIPTION
                "Atm Configurable receive queue length."
        DEFVAL	{ default }
        ::= { wfFntsAtmEntry 34 }

    wfFntsAtmCfgTxQueueLength OBJECT-TYPE
        SYNTAX	INTEGER {
    		    default(127)
    		}
        ACCESS	read-write
        STATUS	mandatory
        DESCRIPTION
                "Atm Configurable transmit queue length."
        DEFVAL	{ default }
        ::= { wfFntsAtmEntry 35 }

    wfFntsAtmLineNumber OBJECT-TYPE
        SYNTAX	INTEGER
        ACCESS	read-write
        STATUS	mandatory
        DESCRIPTION
                "Unique number identifying this interface."
        ::= { wfFntsAtmEntry 36 }

  END  -- Wellfleet-FNTS-ATM-MIB
