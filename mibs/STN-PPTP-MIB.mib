-- *****************************************************************
--
-- STN-PPTP.mib:  
--      Spring Tide Networks PPTP MIB file.
--
--
--      Copyright (c) 1999, 2000 by Spring Tide Networks, Inc.
--                      ALL RIGHTS RESERVED       
--
-- *****************************************************************
   
   STN-PPTP-MIB DEFINITIONS ::= BEGIN

   IMPORTS
        Integer32, Counter32, Gauge32, IpAddress,
        MODULE-IDENTITY, OBJECT-TYPE, NOTIFICATION-TYPE
            FROM SNMPv2-SMI

        TEXTUAL-CONVENTION, DisplayString, RowStatus, TruthValue
            FROM SNMPv2-TC

        OBJECT-GROUP, MODULE-COMPLIANCE
               FROM SNMPv2-CONF

        InterfaceIndex
               FROM IF-MIB

        stnTmpProtocols
               FROM SPRING-TIDE-NETWORKS-SMI

	StnDomainMapType
               FROM SPRING-TIDE-NETWORKS-TC;


   stnPptp    MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
       DESCRIPTION
          "The MIB module that describes managed objects of
           general use by the Point-to-Point Transport Protocol."
       ::= { stnTmpProtocols 10 }


   --
   -- Top Level STN PPTP MIB Objects
   --
   stnPptpObjects         OBJECT IDENTIFIER  ::= { stnPptp 1 }
   stnPptpMibConformance  OBJECT IDENTIFIER  ::= { stnPptp 2 }
   stnPptpTraps           OBJECT IDENTIFIER  ::= { stnPptp 3 }

   --
   --      Definitions of significant branches under stnPptpObjects
   --
   stnPptpScalar          OBJECT IDENTIFIER  ::= { stnPptpObjects 1 }
   stnPptpConfig          OBJECT IDENTIFIER  ::= { stnPptpScalar 1 }
   stnPptpStats           OBJECT IDENTIFIER  ::= { stnPptpScalar 2 }

 
   --
   --      Textual Conventions
   --

   MilliSeconds ::=  TEXTUAL-CONVENTION
           DISPLAY-HINT    "d-3"
           STATUS          current
           DESCRIPTION
              "A period of time measured in units of .001 of seconds
               when used in conjunction with the DISPLAY-HINT will
               show seconds and fractions of second with a resolution
               of .001 of a second."
           SYNTAX          Integer32 (0..2147483646)


   --
   --      The PPTP Scalar Configuration Group
   --
   --      This group of objects is used to manage configuration
   --      of the PPTP protocol environment.

   stnPptpAdminState           OBJECT-TYPE
           SYNTAX          INTEGER {
                               enabled(1),
                               disabled(2),
                               drain(3)
                           }
           MAX-ACCESS      read-write
           STATUS          current
           DESCRIPTION
              "This object defines the administrative state of
               this PPTP tunnel domain. Setting this object to
               'disabled' causes all tunnels to be immediately
               disconnected and no further tunnels to be either
               initiated or accepted. "
           DEFVAL { enabled }
           ::= { stnPptpConfig 1 }

   --
   --      The PPTP Scalar Status and Statistics Group
   --
   --      This group of objects describe the current state and
   --      statistics of PPTP.

   stnPptpProtocolVersion     OBJECT-TYPE
           SYNTAX          OCTET STRING (SIZE(2..256))
           MAX-ACCESS      read-only
           STATUS          current
           DESCRIPTION
               "Vector of supported PPTP protocol version and
                revision numbers. Supported versions are identified
                via a two octet pairing where the first octet indicates
                the version and the second octet contains the revision."
           ::= { stnPptpStats 1 }

   stnPptpVendorName          OBJECT-TYPE
           SYNTAX          DisplayString
           MAX-ACCESS      read-only
           STATUS          current
           DESCRIPTION
              "This object identifies the Vendor name of the PPTP
               protocol stack."
           ::= { stnPptpStats 2 }

   stnPptpFirmwareRev         OBJECT-TYPE
           SYNTAX          Integer32
           MAX-ACCESS      read-only
           STATUS          current
           DESCRIPTION
              "This object defines the firmware revision for the
               PPTP protocol stack."
           ::= { stnPptpStats 3 }

   --
   --      The PPTP Domain Configuration Table
   --
   --      This table contains objects that can be used to
   --      configure the operational characteristics of a tunnel
   --      domain.

   stnPptpDomainConfigTable   OBJECT-TYPE
           SYNTAX          SEQUENCE OF StnPptpDomainConfigEntry
           MAX-ACCESS      not-accessible
           STATUS          current
           DESCRIPTION
              "The PPTP Domain configuration table."
           ::= { stnPptpObjects 2 }

   stnPptpDomainConfigEntry   OBJECT-TYPE
           SYNTAX          StnPptpDomainConfigEntry
           MAX-ACCESS      not-accessible
           STATUS          current
           DESCRIPTION
              "An PPTP Domain configuration entry. An entry in this
               table may correspond to a single endpoint or a group
               of tunnel endpoints."
           INDEX { stnPptpDomainConfigIdentifier }
           ::= { stnPptpDomainConfigTable 1 }

   StnPptpDomainConfigEntry ::=
           SEQUENCE {
               stnPptpDomainConfigIdentifier
                   DisplayString,
               stnPptpDomainConfigAdminState
                   INTEGER,
               stnPptpDomainConfigAuthentication
                   INTEGER,
               stnPptpDomainConfigSecret
                   OCTET STRING,
               stnPptpDomainConfigTunnelSecurity
                   INTEGER,
               stnPptpDomainConfigTunnelHelloInterval
                   Integer32,
               stnPptpDomainConfigTunnelIdleTimeout
                   Integer32,
               stnPptpDomainConfigControlRWS
                   Integer32,
               stnPptpDomainConfigControlRetransmissions
                   Integer32,
               stnPptpDomainConfigPayloadSequencing
                   TruthValue,
               stnPptpDomainConfigPayloadRWS
                   Integer32,
               stnPptpDomainConfigDelayedAckTimeout
                   MilliSeconds,
               stnPptpDomainConfigReassemblyTimeout
                   MilliSeconds,
               stnPptpDomainConfigStatus
                   RowStatus
           }

   stnPptpDomainConfigIdentifier  OBJECT-TYPE
           SYNTAX          DisplayString
           MAX-ACCESS      not-accessible
           STATUS          current
           DESCRIPTION
              "This object is not used."
           ::= { stnPptpDomainConfigEntry 1 }

   stnPptpDomainConfigAdminState  OBJECT-TYPE
           SYNTAX          INTEGER {
                               enabled(1),
                               disabled(2),
                               drain(3)
                           }
           MAX-ACCESS      read-create
           STATUS          current
           DESCRIPTION
              "This object is not used."
           DEFVAL { enabled }
           ::= { stnPptpDomainConfigEntry 2 }

   stnPptpDomainConfigAuthentication  OBJECT-TYPE
           SYNTAX          INTEGER {
                               none(1),
                               simple(2),
                               challenge(3)
                           }
           MAX-ACCESS      read-create
           STATUS          current
           DESCRIPTION
              "This object is not used"
           DEFVAL { none }
           ::= { stnPptpDomainConfigEntry 3 }

   stnPptpDomainConfigSecret  OBJECT-TYPE
           SYNTAX          OCTET STRING (SIZE(0..255))
           MAX-ACCESS      read-create
           STATUS          current
           DESCRIPTION
              "This object is not used "
           ::= { stnPptpDomainConfigEntry 4 }

   stnPptpDomainConfigTunnelSecurity  OBJECT-TYPE
           SYNTAX          INTEGER {
                               none(1),
                               other(2),
                               ipSec(3)
                           }
           MAX-ACCESS      read-create
           STATUS          current
           DESCRIPTION
              "This object is not used."
           DEFVAL { none }
           ::= { stnPptpDomainConfigEntry 5 }

   stnPptpDomainConfigTunnelHelloInterval  OBJECT-TYPE
           SYNTAX          Integer32 (0..3600)
           MAX-ACCESS      read-create
           STATUS          current
           DESCRIPTION
              "This object is not used."
           DEFVAL { 60 }
           ::= { stnPptpDomainConfigEntry 6 }

   stnPptpDomainConfigTunnelIdleTimeout  OBJECT-TYPE
           SYNTAX          Integer32 (0..86400)
           MAX-ACCESS      read-create
           STATUS          current
           DESCRIPTION
              "This object is not used."
           DEFVAL { 0 }
           ::= { stnPptpDomainConfigEntry 7 }

   stnPptpDomainConfigControlRWS  OBJECT-TYPE
           SYNTAX          Integer32 (1..64)
           MAX-ACCESS      read-create
           STATUS          current
           DESCRIPTION
              "This object is not used."
           DEFVAL { 4 }
           ::= { stnPptpDomainConfigEntry 8 }

   stnPptpDomainConfigControlRetransmissions  OBJECT-TYPE
           SYNTAX          Integer32 (0..32)
           MAX-ACCESS      read-create
           STATUS          current
           DESCRIPTION
              "This object is not used."
           DEFVAL { 4 }
           ::= { stnPptpDomainConfigEntry 9 }

   stnPptpDomainConfigPayloadSequencing  OBJECT-TYPE
           SYNTAX          TruthValue
           MAX-ACCESS      read-create
           STATUS          current
           DESCRIPTION
              "This object is not used."
           DEFVAL { false }
           ::= { stnPptpDomainConfigEntry 10 }

   stnPptpDomainConfigPayloadRWS  OBJECT-TYPE
           SYNTAX          Integer32 (0..65535)
           MAX-ACCESS      read-create
           STATUS          current
           DESCRIPTION
              "This object is not used."
           DEFVAL { 0 }
           ::= { stnPptpDomainConfigEntry 11 }

   stnPptpDomainConfigDelayedAckTimeout  OBJECT-TYPE
           SYNTAX          MilliSeconds
           MAX-ACCESS      read-create
           STATUS          current
           DESCRIPTION
              "This object is not used."
           DEFVAL { 0 }
           ::= { stnPptpDomainConfigEntry 12 }

   stnPptpDomainConfigReassemblyTimeout  OBJECT-TYPE
           SYNTAX          MilliSeconds
           MAX-ACCESS      read-create
           STATUS          current
           DESCRIPTION
              "This object is not used."
           DEFVAL { 0 }
           ::= { stnPptpDomainConfigEntry 13 }

   stnPptpDomainConfigStatus  OBJECT-TYPE
           SYNTAX          RowStatus
           MAX-ACCESS      read-create
           STATUS          current
           DESCRIPTION
              "This object is not used."
           ::= { stnPptpDomainConfigEntry 14 }

   --
   --      The PPTP Domain Status and Statistics Table
   --
   --      This table contains objects that can be used to desribe
   --      the current status and statistics of a tunnel domain.

   stnPptpDomainStatsTable OBJECT-TYPE
           SYNTAX          SEQUENCE OF StnPptpDomainStatsEntry
           MAX-ACCESS      not-accessible
           STATUS          current
           DESCRIPTION
              "The PPTP Domain Status and Statistics table."
           ::= { stnPptpObjects 3 }

   stnPptpDomainStatsEntry OBJECT-TYPE
           SYNTAX          StnPptpDomainStatsEntry
           MAX-ACCESS      not-accessible
           STATUS          current
           DESCRIPTION
              "An PPTP Domain Stats entry. An entry in this table
               may correspond to a single endpoint or a group of
               tunnel endpoints."
           INDEX { stnPptpDomainStatsIdentifier }
           ::= { stnPptpDomainStatsTable 1 }

   StnPptpDomainStatsEntry ::=
           SEQUENCE {
               stnPptpDomainStatsIdentifier
                   DisplayString,
               stnPptpDomainStatsTotalTunnels
                   Counter32,
               stnPptpDomainStatsFailedTunnels
                   Counter32,
               stnPptpDomainStatsFailedAuthentications
                   Counter32,
               stnPptpDomainStatsActiveTunnels
                   Gauge32,
               stnPptpDomainStatsTotalSessions
                   Counter32,
               stnPptpDomainStatsFailedSessions
                   Counter32,
               stnPptpDomainStatsActiveSessions
                   Gauge32,
               stnPptpDomainStatsControlRecvOctets
                   Counter32,
               stnPptpDomainStatsControlRecvPackets
                   Counter32,
               stnPptpDomainStatsControlSendOctets
                   Counter32,
               stnPptpDomainStatsControlSendPackets
                   Counter32,
               stnPptpDomainStatsPayloadRecvOctets
                   Counter32,
               stnPptpDomainStatsPayloadRecvPackets
                   Counter32,
               stnPptpDomainStatsPayloadRecvDiscards
                   Counter32,
               stnPptpDomainStatsPayloadSendOctets
                   Counter32,
               stnPptpDomainStatsPayloadSendPackets
                   Counter32
           }

   stnPptpDomainStatsIdentifier  OBJECT-TYPE
           SYNTAX          DisplayString
           MAX-ACCESS      not-accessible
           STATUS          current
           DESCRIPTION
              "The identifier, usually in the form of a Domain
               Name (full or partial), describing a single tunnel
               endpoint or a domain of tunnel endpoints."
           ::= { stnPptpDomainStatsEntry 1 }

   stnPptpDomainStatsTotalTunnels  OBJECT-TYPE
           SYNTAX          Counter32
           MAX-ACCESS      read-only
           STATUS          current
           DESCRIPTION
              "This object returns the total number of tunnels
               that have successfully reached the established
               state for this tunnel domain."
           ::= { stnPptpDomainStatsEntry 2 }

   stnPptpDomainStatsFailedTunnels  OBJECT-TYPE
           SYNTAX          Counter32
           MAX-ACCESS      read-only
           STATUS          current
           DESCRIPTION
              "This object returns the number of tunnels that
               failed to reach the established state for this
               tunnel domain."
           ::= { stnPptpDomainStatsEntry 3 }

   stnPptpDomainStatsFailedAuthentications OBJECT-TYPE
           SYNTAX          Counter32
           MAX-ACCESS      read-only
           STATUS          current
           DESCRIPTION
              "This object is not used."
           ::= { stnPptpDomainStatsEntry 4 }

   stnPptpDomainStatsActiveTunnels  OBJECT-TYPE
           SYNTAX          Gauge32
           MAX-ACCESS      read-only
           STATUS          current
           DESCRIPTION
              "This object returns the number of tunnels that
               are currently active for this domain."
           ::= { stnPptpDomainStatsEntry 5 }

   stnPptpDomainStatsTotalSessions  OBJECT-TYPE
           SYNTAX          Counter32
           MAX-ACCESS      read-only
           STATUS          current
           DESCRIPTION
              "This object returns the total number of sessions
               that have successfully reached the established state
               for this tunnel domain."
           ::= { stnPptpDomainStatsEntry 6 }

   stnPptpDomainStatsFailedSessions  OBJECT-TYPE
           SYNTAX          Counter32
           MAX-ACCESS      read-only
           STATUS          current
           DESCRIPTION
              "This object returns the number of sessions that
               failed to reach the established state for this
               tunnel domain."
           ::= { stnPptpDomainStatsEntry 7 }

   stnPptpDomainStatsActiveSessions  OBJECT-TYPE
           SYNTAX          Gauge32
           MAX-ACCESS      read-only
           STATUS          current
           DESCRIPTION
              "This object returns the number of sessions that
               are currently active for this domain."
           ::= { stnPptpDomainStatsEntry 8 }

   stnPptpDomainStatsControlRecvOctets  OBJECT-TYPE
           SYNTAX          Counter32
           MAX-ACCESS      read-only
           STATUS          current
           DESCRIPTION
              "This object returns the number of control channel
               octets received for this tunnel domain."
           ::= { stnPptpDomainStatsEntry 9 }

   stnPptpDomainStatsControlRecvPackets  OBJECT-TYPE
           SYNTAX          Counter32
           MAX-ACCESS      read-only
           STATUS          current
           DESCRIPTION
              "This object returns the number of control packets
               received for this tunnel domain."
           ::= { stnPptpDomainStatsEntry 10 }

   stnPptpDomainStatsControlSendOctets  OBJECT-TYPE
           SYNTAX          Counter32
           MAX-ACCESS      read-only
           STATUS          current
           DESCRIPTION
              "This object returns the number of control channel
               octets that were transmitted to tunnel endpoints
               for this domain."
           ::= { stnPptpDomainStatsEntry 11 }

   stnPptpDomainStatsControlSendPackets  OBJECT-TYPE
           SYNTAX          Counter32
           MAX-ACCESS      read-only
           STATUS          current
           DESCRIPTION
              "This object returns the number of control packets
               that were transmitted to tunnel endpoints for
               this domain."
           ::= { stnPptpDomainStatsEntry 12 }

   stnPptpDomainStatsPayloadRecvOctets  OBJECT-TYPE
           SYNTAX          Counter32
           MAX-ACCESS      read-only
           STATUS          current
           DESCRIPTION
              "This object returns the number of payload channel
               octets that were received for this tunnel domain."
           ::= { stnPptpDomainStatsEntry 13 }

   stnPptpDomainStatsPayloadRecvPackets  OBJECT-TYPE
           SYNTAX          Counter32
           MAX-ACCESS      read-only
           STATUS          current
           DESCRIPTION
              "This object returns the number of payload packets
               that were received for this tunnel domain."
           ::= { stnPptpDomainStatsEntry 14 }

   stnPptpDomainStatsPayloadRecvDiscards  OBJECT-TYPE
           SYNTAX          Counter32
           MAX-ACCESS      read-only
           STATUS          current
           DESCRIPTION
              "This object returns the number of received payload
               packets that were discarded by this this tunnel
               domain."
           ::= { stnPptpDomainStatsEntry 15 }

   stnPptpDomainStatsPayloadSendOctets  OBJECT-TYPE
           SYNTAX          Counter32
           MAX-ACCESS      read-only
           STATUS          current
           DESCRIPTION
              "This object returns the number of payload channel
               octets that were transmitted to tunnel peers
               within this tunnel domain."
           ::= { stnPptpDomainStatsEntry 16 }

   stnPptpDomainStatsPayloadSendPackets  OBJECT-TYPE
           SYNTAX          Counter32
           MAX-ACCESS      read-only
           STATUS          current
           DESCRIPTION
              "This object returns the number of payload packets
               that were transmitted to tunnel peers within
               this tunnel domain."
           ::= { stnPptpDomainStatsEntry 17 }

   --
   --      The PPTP Tunnel Configuration Table
   --
   --      This table contains objects that can be used to
   --      (re)configure the operational characteristics of a
   --      single PPTP tunnel.

   stnPptpTunnelConfigTable   OBJECT-TYPE
           SYNTAX          SEQUENCE OF StnPptpTunnelConfigEntry
           MAX-ACCESS      not-accessible
           STATUS          current
           DESCRIPTION
              "The PPTP tunnel configuration table."
           ::= { stnPptpObjects 4 }

   stnPptpTunnelConfigEntry   OBJECT-TYPE
           SYNTAX          StnPptpTunnelConfigEntry
           MAX-ACCESS      not-accessible
           STATUS          current
           DESCRIPTION
              "A PPTP tunnel interface configuration entry."
           INDEX { stnPptpTunnelConfigIfIndex }
           ::= { stnPptpTunnelConfigTable 1 }

   StnPptpTunnelConfigEntry ::=
           SEQUENCE {
               stnPptpTunnelConfigIfIndex
                   InterfaceIndex,
               stnPptpTunnelConfigAuthentication
                   INTEGER,
               stnPptpTunnelConfigSecret
                   OCTET STRING,
               stnPptpTunnelConfigSecurity
                   INTEGER,
               stnPptpTunnelConfigHelloInterval
                   Integer32,
               stnPptpTunnelConfigIdleTimeout
                   Integer32,
               stnPptpTunnelConfigControlRWS
                   Integer32,
               stnPptpTunnelConfigControlRetransmissions
                   Integer32,
               stnPptpTunnelConfigPayloadSequencing
                   TruthValue,
               stnPptpTunnelConfigPayloadRWS
                   Integer32,
               stnPptpTunnelConfigDelayedAckTimeout
                   MilliSeconds,
               stnPptpTunnelConfigReassemblyTimeout
                   MilliSeconds,
               stnPptpTunnelConfigTransport
                   INTEGER
           }

   stnPptpTunnelConfigIfIndex OBJECT-TYPE
           SYNTAX          InterfaceIndex
           MAX-ACCESS      read-only
           STATUS          current
           DESCRIPTION
              "This value for this object is equal to the value
               of ifIndex of the Interfaces MIB for tunnel
               interfaces of type PPTP."
           ::= { stnPptpTunnelConfigEntry 1 }

   stnPptpTunnelConfigAuthentication  OBJECT-TYPE
           SYNTAX          INTEGER {
                               none(1),
                               simple(2),
                               challenge(3)
                           }
           MAX-ACCESS      read-write
           STATUS          current
           DESCRIPTION
              "This object is not used."
           DEFVAL { none }
           ::= { stnPptpTunnelConfigEntry 2 }

   stnPptpTunnelConfigSecret  OBJECT-TYPE
           SYNTAX          OCTET STRING (SIZE(0..255))
           MAX-ACCESS      read-write
           STATUS          current
           DESCRIPTION
              "This object is not used."
           ::= { stnPptpTunnelConfigEntry 3 }

   stnPptpTunnelConfigSecurity  OBJECT-TYPE
           SYNTAX          INTEGER {
                               none(1),
                               other(2),
                               ipsec(3)
                           }
           MAX-ACCESS      read-write
           STATUS          current
           DESCRIPTION
              "This object is not used."
           DEFVAL { none }
           ::= { stnPptpTunnelConfigEntry 4 }

   stnPptpTunnelConfigHelloInterval  OBJECT-TYPE
           SYNTAX          Integer32  (0..3600)
           MAX-ACCESS      read-write
           STATUS          current
           DESCRIPTION
              "This object is not used."
           DEFVAL { 60 }
           ::= { stnPptpTunnelConfigEntry 5 }

   stnPptpTunnelConfigIdleTimeout  OBJECT-TYPE
           SYNTAX          Integer32 (0..86400)
           MAX-ACCESS      read-write
           STATUS          current
           DESCRIPTION
              "This object is not used."
           DEFVAL { 0 }
           ::= { stnPptpTunnelConfigEntry 6 }

   stnPptpTunnelConfigControlRWS  OBJECT-TYPE
           SYNTAX          Integer32 (1..64)
           MAX-ACCESS      read-write
           STATUS          current
           DESCRIPTION
              "This object is not used."
           DEFVAL { 4 }
           ::= { stnPptpTunnelConfigEntry 7 }

   stnPptpTunnelConfigControlRetransmissions  OBJECT-TYPE
           SYNTAX          Integer32 (0..32)
           MAX-ACCESS      read-write
           STATUS          current
           DESCRIPTION
              "This object is not used."
           DEFVAL { 4 }
           ::= { stnPptpTunnelConfigEntry 8 }

   stnPptpTunnelConfigPayloadSequencing  OBJECT-TYPE
           SYNTAX          TruthValue
           MAX-ACCESS      read-write
           STATUS          current
           DESCRIPTION
              "This object is not used."
           DEFVAL { false }
           ::= { stnPptpTunnelConfigEntry 9 }

   stnPptpTunnelConfigPayloadRWS  OBJECT-TYPE
           SYNTAX          Integer32 (0..65535)
           MAX-ACCESS      read-write
           STATUS          current
           DESCRIPTION
              "This object is not used."
           DEFVAL { 0 }
           ::= { stnPptpTunnelConfigEntry 10 }

   stnPptpTunnelConfigDelayedAckTimeout  OBJECT-TYPE
           SYNTAX          MilliSeconds
           MAX-ACCESS      read-write
           STATUS          current
           DESCRIPTION
              "This object is not used."
           DEFVAL { 0 }
           ::= { stnPptpTunnelConfigEntry 11 }

   stnPptpTunnelConfigReassemblyTimeout  OBJECT-TYPE
           SYNTAX          MilliSeconds
           MAX-ACCESS      read-write
           STATUS          current
           DESCRIPTION
              "This object is not used."
           DEFVAL { 0 }
           ::= { stnPptpTunnelConfigEntry 12 }

   stnPptpTunnelConfigTransport  OBJECT-TYPE
           SYNTAX          INTEGER {
                              ipGre(1)
                           }
           MAX-ACCESS      read-write
           STATUS          current
           DESCRIPTION
              "This object defines the underlying transport media
               that is in use for this tunnel entry. Different tunnel
               transports may define MIB extensions to the PPTP tunnel
               table to realize the transport layer."
           ::= { stnPptpTunnelConfigEntry 13 }

   --
   --      The PPTP Tunnel Status and Statisticss Table
   --
   --      This table contains objects that can be used to describe
   --      the current status and statistics of a single PPTP tunnel.


   stnPptpTunnelStatsTable    OBJECT-TYPE
           SYNTAX          SEQUENCE OF StnPptpTunnelStatsEntry
           MAX-ACCESS      not-accessible
           STATUS          current
           DESCRIPTION
              "The PPTP tunnel status and statistics table."
           ::= { stnPptpObjects 5 }

   stnPptpTunnelStatsEntry    OBJECT-TYPE
           SYNTAX          StnPptpTunnelStatsEntry
           MAX-ACCESS      not-accessible
           STATUS          current
           DESCRIPTION
              "An PPTP tunnel interface stats entry."
           INDEX { stnPptpTunnelStatsIfIndex }
           ::= { stnPptpTunnelStatsTable 1 }

   StnPptpTunnelStatsEntry ::=
           SEQUENCE {
               stnPptpTunnelStatsIfIndex
                   InterfaceIndex,
               stnPptpTunnelStatsLocalTID
                   Integer32,
               stnPptpTunnelStatsState
                   INTEGER,
               stnPptpTunnelStatsInitiated
                   INTEGER,
               stnPptpTunnelStatsRemoteHostName
                   DisplayString,
               stnPptpTunnelStatsRemoteVendorName
                   DisplayString,
               stnPptpTunnelStatsRemoteFirmwareRevision
                   Integer32,
               stnPptpTunnelStatsRemoteProtocolVersion
                   OCTET STRING,
               stnPptpTunnelStatsBearerCapabilities
                   INTEGER,
               stnPptpTunnelStatsFramingCapabilities
                   INTEGER,
               stnPptpTunnelStatsControlRecvPackets
                   Counter32,
               stnPptpTunnelStatsControlSendPackets
                   Counter32,
               stnPptpTunnelStatsTotalSessions
                   Counter32,
               stnPptpTunnelStatsFailedSessions
                   Counter32,
               stnPptpTunnelStatsActiveSessions
                   Gauge32,
               stnPptpTunnelStatsLastResultCode
                   Integer32,
               stnPptpTunnelStatsLastErrorCode
                   Integer32,
               stnPptpTunnelStatsLastErrorMessage
                   DisplayString
           }

   stnPptpTunnelStatsIfIndex  OBJECT-TYPE
           SYNTAX          InterfaceIndex
           MAX-ACCESS      read-only
           STATUS          current
           DESCRIPTION
              "This value for this object is equal to the value
               of ifIndex of the Interfaces MIB for tunnel
               interfaces of type PPTP."
           ::= { stnPptpTunnelStatsEntry 1 }

   stnPptpTunnelStatsLocalTID OBJECT-TYPE
           SYNTAX          Integer32 (0..65535)
           MAX-ACCESS      read-only
           STATUS          current
           DESCRIPTION
              "This object contains the local tunnel Identifier."
           ::= { stnPptpTunnelStatsEntry 2 }

   stnPptpTunnelStatsState    OBJECT-TYPE
           SYNTAX          INTEGER {
                               tunnelIdle(1),
                               tunnelConnecting(2),
                               tunnelEstablished(3),
                               tunnelDisconnecting(4)
                           }
           MAX-ACCESS      read-only
           STATUS          current
           DESCRIPTION
              "This field contains the current state of the control
               tunnel."
           ::= { stnPptpTunnelStatsEntry 3 }

   stnPptpTunnelStatsInitiated  OBJECT-TYPE
           SYNTAX          INTEGER {
                               locally(1),
                               remotely(2)
                           }
           MAX-ACCESS      read-only
           STATUS          current
           DESCRIPTION
              "This object indicates whether the tunnel was
               initiated locally or by the remote tunnel peer."
           ::= { stnPptpTunnelStatsEntry 4 }

   stnPptpTunnelStatsRemoteHostName  OBJECT-TYPE
           SYNTAX          DisplayString
           MAX-ACCESS      read-only
           STATUS          current
           DESCRIPTION
              "This object contains the host name as discovered
               during the tunnel establishment phase "
           ::= { stnPptpTunnelStatsEntry 5 }

   stnPptpTunnelStatsRemoteVendorName  OBJECT-TYPE
           SYNTAX          DisplayString
           MAX-ACCESS      read-only
           STATUS          current
           DESCRIPTION
              "This object identifies the vendor name of the peer's
               PPTP implementation. "
           ::= { stnPptpTunnelStatsEntry 6 }

   stnPptpTunnelStatsRemoteFirmwareRevision  OBJECT-TYPE
           SYNTAX          Integer32
           MAX-ACCESS      read-only
           STATUS          current
           DESCRIPTION
              "This object contains the tunnel peer's firmware
               revision number."
           ::= { stnPptpTunnelStatsEntry 7 }

   stnPptpTunnelStatsRemoteProtocolVersion  OBJECT-TYPE
           SYNTAX          OCTET STRING (SIZE(2))
           MAX-ACCESS      read-only
           STATUS          current
           DESCRIPTION
              "This object describes the protocol version and
               revision of the tunnel peers implementation. The
               first octet contains the protocol version. The
               second octet contains the protocol revision."
           ::= { stnPptpTunnelStatsEntry 8 }

   stnPptpTunnelStatsBearerCapabilities  OBJECT-TYPE
           SYNTAX          INTEGER {
                               none(1),
                               digital(2),
                               analog(3),
                               digitalAnalog(4)
                           }
           MAX-ACCESS      read-only
           STATUS          current
           DESCRIPTION
              "This object describes the Bearer Capabilities of
               the tunnel peer."
           ::= { stnPptpTunnelStatsEntry 9 }

   stnPptpTunnelStatsFramingCapabilities  OBJECT-TYPE
           SYNTAX          INTEGER {
                               none(1),
                               sync(2),
                               async(3),
                               syncAsync(4)
                           }
           MAX-ACCESS      read-only
           STATUS          current
           DESCRIPTION
              "This object describes the Framing Capabilities of
               the tunnel peer."
           ::= { stnPptpTunnelStatsEntry 10 }

   stnPptpTunnelStatsControlRecvPackets  OBJECT-TYPE
           SYNTAX          Counter32
           MAX-ACCESS      read-only
           STATUS          current
           DESCRIPTION
              "This object contains the number of control packets
               received on the tunnel."
           ::= { stnPptpTunnelStatsEntry 11 }

   stnPptpTunnelStatsControlSendPackets  OBJECT-TYPE
           SYNTAX          Counter32
           MAX-ACCESS      read-only
           STATUS          current
           DESCRIPTION
              "This object contains the number of control
               packets that were transmitted to the tunnel
               peer."
           ::= { stnPptpTunnelStatsEntry 12 }

   stnPptpTunnelStatsTotalSessions  OBJECT-TYPE
           SYNTAX          Counter32
           MAX-ACCESS      read-only
           STATUS          current
           DESCRIPTION
              "This object contains the total number of sessions
               that this tunnel has successfully connected through
               to its tunnel peer since this tunnel was created."
           ::= { stnPptpTunnelStatsEntry 13 }

   stnPptpTunnelStatsFailedSessions  OBJECT-TYPE
           SYNTAX          Counter32
           MAX-ACCESS      read-only
           STATUS          current
           DESCRIPTION
              "This object contains the total number of sessions
               that were initiated but failed to reach the
               established phase."
           ::= { stnPptpTunnelStatsEntry 14 }

   stnPptpTunnelStatsActiveSessions  OBJECT-TYPE
           SYNTAX          Gauge32
           MAX-ACCESS      read-only
           STATUS          current
           DESCRIPTION
              "This object contains the total number of sessions
               in the established state for this tunnel."
           ::= { stnPptpTunnelStatsEntry 15 }

   stnPptpTunnelStatsLastResultCode  OBJECT-TYPE
           SYNTAX          Integer32 (0..65535)
           MAX-ACCESS      read-only
           STATUS          current
           DESCRIPTION
              "This object contains the last value of the result
               code as described in the Result Code which
               caused the tunnel to disconnect."
           ::= { stnPptpTunnelStatsEntry 16 }

   stnPptpTunnelStatsLastErrorCode  OBJECT-TYPE
           SYNTAX          Integer32 (0..65535)
           MAX-ACCESS      read-only
           STATUS          current
           DESCRIPTION
              "This object contains the last value of the error
               code as described in the Result Code which
               caused the tunnel to disconnect."
           ::= { stnPptpTunnelStatsEntry 17 }

   stnPptpTunnelStatsLastErrorMessage  OBJECT-TYPE
           SYNTAX          DisplayString
           MAX-ACCESS      read-only
           STATUS          current
           DESCRIPTION
              "This object contains the last value of the optional
               message as described in the Result Code which
               caused the tunnel to disconnect."
           ::= { stnPptpTunnelStatsEntry 18 }

   --
   --      { stnPptpObjects 6 } reserved for future use
   --
   --
   --      The PPTP Session Status and Statistics Table
   --
   --      This table contains the objects that can be used to
   --      describe the current status and statistics of a single
   --      PPTP tunneled session.


   stnPptpSessionStatsTable   OBJECT-TYPE
           SYNTAX          SEQUENCE OF StnPptpSessionStatsEntry
           MAX-ACCESS      not-accessible
           STATUS          current
           DESCRIPTION
              "The PPTP session status and statistics table."
           ::= { stnPptpObjects 7 }

   stnPptpSessionStatsEntry   OBJECT-TYPE
           SYNTAX          StnPptpSessionStatsEntry
           MAX-ACCESS      not-accessible
           STATUS          current
           DESCRIPTION
              "An PPTP session interface stats entry."
           INDEX { stnPptpSessionStatsTunnelIfIndex, stnPptpSessionStatsLocalCID }
           ::= { stnPptpSessionStatsTable 1 }

   StnPptpSessionStatsEntry ::=
           SEQUENCE {
               stnPptpSessionStatsTunnelIfIndex
                   InterfaceIndex,
               stnPptpSessionStatsHLIfIndex
                   InterfaceIndex,
               stnPptpSessionStatsLocalCID
                   Integer32,
               stnPptpSessionStatsRemoteCID
                   Integer32,
               stnPptpSessionStatsUserName
                   DisplayString,
               stnPptpSessionStatsState
                   INTEGER,
               stnPptpSessionStatsCallType
                   INTEGER,
               stnPptpSessionStatsCallSerialNumber
                   Integer32,
               stnPptpSessionStatsTxConnectSpeed
                   Integer32,
               stnPptpSessionStatsRxConnectSpeed
                   Integer32,
               stnPptpSessionStatsCallBearerType
                   INTEGER,
               stnPptpSessionStatsFramingType
                   INTEGER,
               stnPptpSessionStatsPhysChanId
                   Integer32,
               stnPptpSessionStatsDNIS
                   DisplayString,
               stnPptpSessionStatsCLID
                   DisplayString,
               stnPptpSessionStatsSubAddress
                   DisplayString,
               stnPptpSessionStatsPrivateGroupID
                   DisplayString,
               stnPptpSessionStatsLocalRWS
                   Integer32,
               stnPptpSessionStatsRemoteInitialRWS
                   Integer32,
               stnPptpSessionStatsRemotePPD
                   Integer32,
               stnPptpSessionStatsRecvZLB
                   Counter32,
               stnPptpSessionStatsOutSequence
                   Counter32,
               stnPptpSessionStatsSendZLB
                   Counter32,
               stnPptpSessionStatsAckTimeouts
                   Counter32,
               stnPptpSesssionStatsCurrentRemoteRWS
                   Gauge32,
               stnPptpSessionStatsSendSeq
                   Integer32,
               stnPptpSessionStatsSendSeqAck
                   Integer32,
               stnPptpSessionStatsRecvSeq
                   Integer32,
               stnPptpSessionStatsRecvSeqAck
                   Integer32
           }

   stnPptpSessionStatsTunnelIfIndex OBJECT-TYPE
           SYNTAX          InterfaceIndex
           MAX-ACCESS      read-only
           STATUS          current
           DESCRIPTION
              "This object identifies the sessions associated
               PPTP tunnel ifIndex value."
           ::= { stnPptpSessionStatsEntry 1 }

   stnPptpSessionStatsHLIfIndex OBJECT-TYPE
           SYNTAX          InterfaceIndex
           MAX-ACCESS      read-only
           STATUS          current
           DESCRIPTION
              "This object identifies the ifIndex value of the
               interface that is either below (Lower) the tunnel
               (if this tunnel endpoint is a PAC) or above
               (Higher) the tunnel (if this tunnel endpoint is a
               PNS). For example this could be a DS0 ifIndex on a
               PAC or it would be the PPP ifIndex on the PNS."
           ::= { stnPptpSessionStatsEntry 2 }

   stnPptpSessionStatsLocalCID  OBJECT-TYPE
           SYNTAX          Integer32 (0..65535)
           MAX-ACCESS      read-only
           STATUS          current
           DESCRIPTION
              "This object contains the local call identifier
               for the session."
           ::= { stnPptpSessionStatsEntry 3 }

   stnPptpSessionStatsRemoteCID  OBJECT-TYPE
           SYNTAX          Integer32  (0..65535)
           MAX-ACCESS      read-only
           STATUS          current
           DESCRIPTION
              "This object is not used."
           ::= { stnPptpSessionStatsEntry 4 }

   stnPptpSessionStatsUserName  OBJECT-TYPE
           SYNTAX          DisplayString
           MAX-ACCESS      read-only
           STATUS          current
           DESCRIPTION
              "This object identifies the peer session name on
               this interface. This is typically the login name
               of the remote user. If the user name is unknown to
               the local tunnel peer then this object will contain
               a null string."
           ::= { stnPptpSessionStatsEntry 5 }

   stnPptpSessionStatsState   OBJECT-TYPE
           SYNTAX          INTEGER {
                               sessionIdle(1),
                               sessionConnecting(2),
                               sessionEstablished(3),
                               sessionDisconnecting(4)
                           }
           MAX-ACCESS      read-only
           STATUS          current
           DESCRIPTION
              "This object contains the current state of the
               session."
           ::= { stnPptpSessionStatsEntry 6 }

   stnPptpSessionStatsCallType  OBJECT-TYPE
           SYNTAX          INTEGER {
                               pacIncoming(1),
                               pnsIncoming(2),
                               pacOutgoing(3),
                               pnsOutgoing(4)
                           }
           MAX-ACCESS      read-only
           STATUS          current
           DESCRIPTION
              "This object indicates the type of call and the
               role this tunnel peer is providing for this
               session. For example, pacIncoming(1) indicates
               that this tunnel peer is acting as a PAC and
               generated a Incoming-Call-Request to the tunnel
               peer (the PNS). Note that tunnel peers can be
               both PAC and PNS simultaneously."
           ::= { stnPptpSessionStatsEntry 7 }

   stnPptpSessionStatsCallSerialNumber  OBJECT-TYPE
           SYNTAX          Integer32
           MAX-ACCESS      read-only
           STATUS          current
           DESCRIPTION
              "This object contains the serial number that has
               been assigned to this  session."
           ::= { stnPptpSessionStatsEntry 8 }

   stnPptpSessionStatsTxConnectSpeed  OBJECT-TYPE
           SYNTAX          Integer32
           MAX-ACCESS      read-only
           STATUS          current
           DESCRIPTION
              "This object returns the last known transmit
               baud rate for this session."
           ::= { stnPptpSessionStatsEntry 9 }

   stnPptpSessionStatsRxConnectSpeed  OBJECT-TYPE
           SYNTAX          Integer32
           MAX-ACCESS      read-only
           STATUS          current
           DESCRIPTION
              "This object returns the last known receive
               baud rate for this session established."
           ::= { stnPptpSessionStatsEntry 10 }

   stnPptpSessionStatsCallBearerType    OBJECT-TYPE
           SYNTAX          INTEGER {
                               none(1),
                               digital(2),
                               analog(3)
                           }
           MAX-ACCESS      read-only
           STATUS          current
           DESCRIPTION
              "This object describes the bearer type of this
               session."
           ::= { stnPptpSessionStatsEntry 11 }

   stnPptpSessionStatsFramingType  OBJECT-TYPE
           SYNTAX          INTEGER {
                               none(1),
                               sync(2),
                               async(3)
                           }
           MAX-ACCESS      read-only
           STATUS          current
           DESCRIPTION
              "This object describes the framing type of this
               session."
           ::= { stnPptpSessionStatsEntry 12 }

   stnPptpSessionStatsPhysChanId   OBJECT-TYPE
           SYNTAX          Integer32
           MAX-ACCESS      read-only
           STATUS          current
           DESCRIPTION
              "This object contains the physical channel
               identifier for the session."
           ::= { stnPptpSessionStatsEntry 13 }

   stnPptpSessionStatsDNIS    OBJECT-TYPE
           SYNTAX          DisplayString
           MAX-ACCESS      read-only
           STATUS          current
           DESCRIPTION
              "This object identifies the Dialed Number
               Information String that the PAC obtained from
               the network for the session. If no DNIS was
               provided then a null string will be returned."
           ::= { stnPptpSessionStatsEntry 14 }

   stnPptpSessionStatsCLID    OBJECT-TYPE
           SYNTAX          DisplayString
           MAX-ACCESS      read-only
           STATUS          current
           DESCRIPTION
              "This object identifies the Calling Line ID
               that the PAC obtained from the network for
               the session. If no CLID was provided then a
               null string will be returned."
           ::= { stnPptpSessionStatsEntry 15 }

   stnPptpSessionStatsSubAddress  OBJECT-TYPE
           SYNTAX          DisplayString
           MAX-ACCESS      read-only
           STATUS          current
           DESCRIPTION
              "This object identifies the Sub Address that
               the PAC obtained from the network for the
               session. If no Sub Address was provided then
               a null string will be returned."
           ::= { stnPptpSessionStatsEntry 16 }

   stnPptpSessionStatsPrivateGroupID  OBJECT-TYPE
           SYNTAX          DisplayString
           MAX-ACCESS      read-only
           STATUS          current
           DESCRIPTION
              "This object identifies the Private Group
               Identifier used for this tunneled session.
               If no Private Group Identifier was provided
               then a null string will be returned."
           ::= { stnPptpSessionStatsEntry 17 }

   stnPptpSessionStatsLocalRWS  OBJECT-TYPE
           SYNTAX          Integer32 (0..65535)
           MAX-ACCESS      read-only
           STATUS          current
           DESCRIPTION
              "This object returns the local send window size
               for this session. "
           ::= { stnPptpSessionStatsEntry 18 }

   stnPptpSessionStatsRemoteInitialRWS  OBJECT-TYPE
           SYNTAX          Integer32 (0..65535)
           MAX-ACCESS      read-only
           STATUS          current
           DESCRIPTION
              "This object returns the initial remote send
               window size for this session. "
           ::= { stnPptpSessionStatsEntry 19 }

   stnPptpSessionStatsRemotePPD  OBJECT-TYPE
           SYNTAX          Integer32
           MAX-ACCESS      read-only
           STATUS          current
           DESCRIPTION
              "This object contains the Packet Processing Delay
               for the session.  "
           ::= { stnPptpSessionStatsEntry 20 }

   stnPptpSessionStatsRecvZLB  OBJECT-TYPE
           SYNTAX          Counter32
           MAX-ACCESS      read-only
           STATUS          current
           DESCRIPTION
              "This object returns the total number of Zero Length
               Body acknowlegement payload packets received for
               this session."
           ::= { stnPptpSessionStatsEntry 21 }

   stnPptpSessionStatsOutSequence  OBJECT-TYPE
           SYNTAX          Counter32
           MAX-ACCESS      read-only
           STATUS          current
           DESCRIPTION
              "This object returns the total number of packets
               received for this session which were received out
               of sequence."
           ::= { stnPptpSessionStatsEntry 22 }

   stnPptpSessionStatsSendZLB OBJECT-TYPE
           SYNTAX          Counter32
           MAX-ACCESS      read-only
           STATUS          current
           DESCRIPTION
              "This object returns the total number of Zero
               Length Body acknowledgement packets transmitted
               on this session."
           ::= { stnPptpSessionStatsEntry 23 }

   stnPptpSessionStatsAckTimeouts  OBJECT-TYPE
           SYNTAX          Counter32
           MAX-ACCESS      read-only
           STATUS          current
           DESCRIPTION
              "This object returns the total number of
               acknowledgement timeouts seen on payload
               packets for this session."
           ::= { stnPptpSessionStatsEntry 24 }

   stnPptpSesssionStatsCurrentRemoteRWS  OBJECT-TYPE
           SYNTAX          Gauge32 (0..65535)
           MAX-ACCESS      read-only
           STATUS          current
           DESCRIPTION
              "This object contains the current remote receive
               window size as determined by the local flow
               control mechanism employed."
           ::= { stnPptpSessionStatsEntry 25 }

   stnPptpSessionStatsSendSeq OBJECT-TYPE
           SYNTAX          Integer32 (0..65535)
           MAX-ACCESS      read-only
           STATUS          current
           DESCRIPTION
              "This object contains the next send sequence number
               for for this session."
           ::= { stnPptpSessionStatsEntry 26 }

   stnPptpSessionStatsSendSeqAck  OBJECT-TYPE
           SYNTAX          Integer32 (0..65535)
           MAX-ACCESS      read-only
           STATUS          current
           DESCRIPTION
              "This object contains the send sequence number
               that the tunnel peer has acknowledged for the
               payload channel. The flow control state can be
               determined by subtracting the stnPptpSessionStatsSendSeq
               from stnPptpSessionStatsSendSeqAck and comparing this
               value to stnPptpSesssionStatsCurrentRemoteRWS."
           ::= { stnPptpSessionStatsEntry 27 }

   stnPptpSessionStatsRecvSeq OBJECT-TYPE
           SYNTAX          Integer32 (0..65535)
           MAX-ACCESS      read-only
           STATUS          current
           DESCRIPTION
              "This object contains the next receive sequence
               number expected to be received on this session."
           ::= { stnPptpSessionStatsEntry 28 }

   stnPptpSessionStatsRecvSeqAck  OBJECT-TYPE
           SYNTAX          Integer32 (0..65535)
           MAX-ACCESS      read-only
           STATUS          current
           DESCRIPTION
              "This object contains the last receive sequence
               number that was acknowledged back to the tunnel
               peer for the session."
           ::= { stnPptpSessionStatsEntry 29 }

   --
   --      The PPTP Tunnel Mapping Table
   --
   --      This table is intended to assist management
   --      applications to quickly determine what the ifIndex
   --      value is for a given local tunnel identifier.

   stnPptpTunnelMapTable OBJECT-TYPE
           SYNTAX	    SEQUENCE OF StnPptpTunnelMapEntry
           MAX-ACCESS	    not-accessible
           STATUS current
           DESCRIPTION
              "The PPTP Tunnel index mapping table."
           ::= { stnPptpObjects 8 }

   stnPptpTunnelMapEntry OBJECT-TYPE
           SYNTAX          StnPptpTunnelMapEntry
           MAX-ACCESS      not-accessible
           STATUS          current
           DESCRIPTION
              "An PPTP tunnel index map entry."
           INDEX { stnPptpTunnelMapLocalTID }
           ::= { stnPptpTunnelMapTable 1 }

   StnPptpTunnelMapEntry ::=
           SEQUENCE {
               stnPptpTunnelMapLocalTID
                   Integer32,
               stnPptpTunnelMapIfIndex
                   InterfaceIndex
           }

   stnPptpTunnelMapLocalTID OBJECT-TYPE
           SYNTAX	    Integer32 (0..65535)
           MAX-ACCESS	    read-only
           STATUS	    current
           DESCRIPTION
              "This object contains the local tunnel Identifier."
           ::= { stnPptpTunnelMapEntry 1 }

   stnPptpTunnelMapIfIndex  OBJECT-TYPE
           SYNTAX	    InterfaceIndex
           MAX-ACCESS	    read-only
           STATUS	    current
           DESCRIPTION
              "This value for this object is equal to the value
               of ifIndex of the Interfaces MIB for tunnel
               interfaces of type PPTP."
           ::= { stnPptpTunnelMapEntry 2 }


   --
   --      The PPTP Session Mapping Table
   --
   --      This table is intended to assist management
   --      applications to quickly determine what the instance
   --      value is for a given upper or lower ifIndex.

    stnPptpSessionMapTable OBJECT-TYPE
	    SYNTAX		SEQUENCE OF StnPptpSessionMapEntry
        MAX-ACCESS	not-accessible
        STATUS		current
        DESCRIPTION	"The PPTP Session index mapping table."
        ::= { stnPptpObjects 9 }

    stnPptpSessionMapEntry OBJECT-TYPE
	    SYNTAX		StnPptpSessionMapEntry
        MAX-ACCESS	not-accessible
        STATUS		current
        DESCRIPTION	"An PPTP Session index map entry."
        INDEX		{ stnPptpSessionMapHLIfIndex }
        ::= { stnPptpSessionMapTable 1 }

    StnPptpSessionMapEntry ::=
	    SEQUENCE {
	        stnPptpSessionMapHLIfIndex	    InterfaceIndex,
            stnPptpSessionMapTunnelIfIndex  InterfaceIndex,
            stnPptpSessionMapLocalCID	    Integer32
	}

    stnPptpSessionMapHLIfIndex OBJECT-TYPE
	    SYNTAX		InterfaceIndex
        MAX-ACCESS	read-only
        STATUS		current
        DESCRIPTION 
		        "This object identifies the ifIndex value of the interface 
                 that is either below (Lower) the tunnel (if this tunnel 
                 endpoint is a PAC) or above (Higher) the tunnel (if this 
                 tunnel endpoint is a PNS). For example this could be a DS0 
                 ifIndex on a PAC or it would be the PPP ifIndex on the PNS."
	    ::= { stnPptpSessionMapEntry 1 }

    stnPptpSessionMapTunnelIfIndex OBJECT-TYPE
	    SYNTAX          InterfaceIndex
        MAX-ACCESS      read-only
        STATUS          current
        DESCRIPTION	"This object identifies the sessions associated PPTP 
			         tunnel ifIndex value."
	    ::= { stnPptpSessionMapEntry 2 }

    stnPptpSessionMapLocalCID  OBJECT-TYPE
	    SYNTAX          Integer32 (0..65535)
        MAX-ACCESS      read-only
        STATUS          current
        DESCRIPTION	"This object contains the local call identifier for 
			         the session."
	    ::= { stnPptpSessionMapEntry 3 }



    --
    --      The PPTP Domain Mapping Table
    --

    stnPptpDomainMapTable OBJECT-TYPE
	    SYNTAX          SEQUENCE OF StnPptpDomainMapTableEntry
	    MAX-ACCESS      not-accessible
	    STATUS          current
	    DESCRIPTION	"This table provides a mapping between PPTP Domain
			         identifiers, hostnames, and IP-ATM information"
	    ::= { stnPptpObjects 10 }

    stnPptpDomainMapTableEntry OBJECT-TYPE
	    SYNTAX          StnPptpDomainMapTableEntry
	    MAX-ACCESS      not-accessible
	    STATUS          current
	    DESCRIPTION	"An entry within the STN PPTP Map Table."
	    INDEX		{ stnPptpDomainMapIdentifier }
	    ::= { stnPptpDomainMapTable 1 }

    StnPptpDomainMapTableEntry ::= SEQUENCE {
	    stnPptpDomainMapIdentifier	DisplayString,
        stnPptpDomainMapHostName	DisplayString,
        stnPptpDomainMapType		StnDomainMapType,
        stnPptpDomainMapTypeInfo	DisplayString
    }

    stnPptpDomainMapIdentifier OBJECT-TYPE
	    SYNTAX          DisplayString
	    MAX-ACCESS      not-accessible
	    STATUS          current
	    DESCRIPTION     "PPTP Domain Identifier."
	    ::= { stnPptpDomainMapTableEntry 1 }

    stnPptpDomainMapHostName OBJECT-TYPE
	    SYNTAX          DisplayString
	    MAX-ACCESS      read-only
	    STATUS          current
	    DESCRIPTION	"The hostname that maps to the PPTP Domain Identifier."
	    ::= { stnPptpDomainMapTableEntry 2 }

    stnPptpDomainMapType OBJECT-TYPE
	    SYNTAX		StnDomainMapType
	    MAX-ACCESS	read-only
	    STATUS		current
	    DESCRIPTION     "Identifiers whether the PPTP Domain maps to an IP 
			     subnet or an ATM circuit."
	    ::= { stnPptpDomainMapTableEntry 3 }

    stnPptpDomainMapTypeInfo OBJECT-TYPE
	    SYNTAX		DisplayString
	    MAX-ACCESS	read-only
	    STATUS		current
	    DESCRIPTION	"Provides either IP or ATM specific display info."
	    ::= { stnPptpDomainMapTableEntry 4 }


   --
   --      conformance information
   --

   stnPptpGroups      OBJECT IDENTIFIER ::= { stnPptpMibConformance 1 }
   stnPptpCompliances OBJECT IDENTIFIER ::= { stnPptpMibConformance 2 }

   --
   --      compliance statements
   --

   stnPptpCompliance MODULE-COMPLIANCE
           STATUS          current
           DESCRIPTION
              "The compliance statement for SNMPv2 entities
               which implement the PPTP MIB."

           MODULE          -- this module

        -- unconditionally mandatory groups
           MANDATORY-GROUPS {
                               stnPptpConfigGroup,
                               stnPptpStatsGroup
                            }

        -- optional groups
           GROUP           stnPptpDomainGroup
           DESCRIPTION
              "This group is optional for PPTP devices that desire
               to group tunnel endpoints into tunnel domains."

           GROUP           stnPptpMappingGroup
           DESCRIPTION
              "This group is optional for PPTP devices that wish
               to provide index mapping."

           ::= { stnPptpCompliances 1 }


   -- units of conformance

   stnPptpConfigGroup OBJECT-GROUP
           OBJECTS {
               stnPptpAdminState,
               stnPptpTunnelConfigAuthentication,
               stnPptpTunnelConfigSecret,
               stnPptpTunnelConfigSecurity,
               stnPptpTunnelConfigHelloInterval,
               stnPptpTunnelConfigIdleTimeout,
               stnPptpTunnelConfigControlRWS,
               stnPptpTunnelConfigControlRetransmissions,
               stnPptpTunnelConfigPayloadSequencing,
               stnPptpTunnelConfigPayloadRWS,
               stnPptpTunnelConfigDelayedAckTimeout,
               stnPptpTunnelConfigReassemblyTimeout,
               stnPptpTunnelConfigTransport
           }
           STATUS          current
           DESCRIPTION
              "A collection of objects providing configuration
               information of the PPTP protocol, tunnels and sessions."
           ::= { stnPptpGroups 1 }

   stnPptpStatsGroup OBJECT-GROUP
           OBJECTS {
               stnPptpProtocolVersion,
               stnPptpVendorName,
               stnPptpFirmwareRev,
               stnPptpTunnelStatsIfIndex,
               stnPptpTunnelStatsLocalTID,
               stnPptpTunnelStatsState,
               stnPptpTunnelStatsInitiated,
               stnPptpTunnelStatsRemoteHostName,
               stnPptpTunnelStatsRemoteVendorName,
               stnPptpTunnelStatsRemoteFirmwareRevision,
               stnPptpTunnelStatsRemoteProtocolVersion,
               stnPptpTunnelStatsBearerCapabilities,
               stnPptpTunnelStatsFramingCapabilities,
               stnPptpTunnelStatsControlRecvPackets,
               stnPptpTunnelStatsControlSendPackets,
               stnPptpTunnelStatsTotalSessions,
               stnPptpTunnelStatsFailedSessions,
               stnPptpTunnelStatsActiveSessions,
               stnPptpTunnelStatsLastResultCode,
               stnPptpTunnelStatsLastErrorCode,
               stnPptpTunnelStatsLastErrorMessage,
               stnPptpSessionStatsTunnelIfIndex,
               stnPptpSessionStatsHLIfIndex,
               stnPptpSessionStatsLocalCID,
               stnPptpSessionStatsRemoteCID,
               stnPptpSessionStatsUserName,
               stnPptpSessionStatsState,
               stnPptpSessionStatsCallType,
               stnPptpSessionStatsCallSerialNumber,
               stnPptpSessionStatsTxConnectSpeed,
               stnPptpSessionStatsRxConnectSpeed,
               stnPptpSessionStatsCallBearerType,
               stnPptpSessionStatsFramingType,
               stnPptpSessionStatsPhysChanId,
               stnPptpSessionStatsDNIS,
               stnPptpSessionStatsCLID,
               stnPptpSessionStatsSubAddress,
               stnPptpSessionStatsPrivateGroupID,
               stnPptpSessionStatsLocalRWS,
               stnPptpSessionStatsRemoteInitialRWS,
               stnPptpSessionStatsRemotePPD,
               stnPptpSessionStatsRecvZLB,
               stnPptpSessionStatsOutSequence,
               stnPptpSessionStatsSendZLB,
               stnPptpSessionStatsAckTimeouts,
               stnPptpSesssionStatsCurrentRemoteRWS,
               stnPptpSessionStatsSendSeq,
               stnPptpSessionStatsSendSeqAck,
               stnPptpSessionStatsRecvSeq,
               stnPptpSessionStatsRecvSeqAck
           }
           STATUS          current
           DESCRIPTION
              "A collection of objects providing status and
               statistics of the PPTP protocol, tunnels and
               sessions."
           ::= { stnPptpGroups 2 }

   stnPptpDomainGroup OBJECT-GROUP
           OBJECTS {
               stnPptpDomainConfigAdminState,
               stnPptpDomainConfigAuthentication,
               stnPptpDomainConfigSecret,
               stnPptpDomainConfigTunnelSecurity,
               stnPptpDomainConfigTunnelHelloInterval,
               stnPptpDomainConfigTunnelIdleTimeout,
               stnPptpDomainConfigControlRWS,
               stnPptpDomainConfigControlRetransmissions,
               stnPptpDomainConfigPayloadSequencing,
               stnPptpDomainConfigPayloadRWS,
               stnPptpDomainConfigDelayedAckTimeout,
               stnPptpDomainConfigReassemblyTimeout,
               stnPptpDomainConfigStatus,
               stnPptpDomainStatsTotalTunnels,
               stnPptpDomainStatsFailedTunnels,
               stnPptpDomainStatsFailedAuthentications,
               stnPptpDomainStatsActiveTunnels,
               stnPptpDomainStatsTotalSessions,
               stnPptpDomainStatsFailedSessions,
               stnPptpDomainStatsActiveSessions,
               stnPptpDomainStatsControlRecvOctets,
               stnPptpDomainStatsControlRecvPackets,
               stnPptpDomainStatsControlSendOctets,
               stnPptpDomainStatsControlSendPackets,
               stnPptpDomainStatsPayloadRecvOctets,
               stnPptpDomainStatsPayloadRecvPackets,
               stnPptpDomainStatsPayloadRecvDiscards,
               stnPptpDomainStatsPayloadSendOctets,
               stnPptpDomainStatsPayloadSendPackets
           }
           STATUS          current
           DESCRIPTION
              "A collection of objects providing configuration,
               status and statistics of PPTP tunnel domains."
           ::= { stnPptpGroups 4 }

   stnPptpMappingGroup OBJECT-GROUP
           OBJECTS {
               stnPptpTunnelMapLocalTID,
               stnPptpTunnelMapIfIndex,
               stnPptpSessionMapHLIfIndex,
               stnPptpSessionMapTunnelIfIndex,
               stnPptpSessionMapLocalCID
           }
           STATUS          current
           DESCRIPTION
              "A collection of objects providing index mapping."
           ::= { stnPptpGroups 5 }


END
