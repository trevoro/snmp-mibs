DECHUB900-PTRM-MIB-V3-0 DEFINITIONS ::= BEGIN

--
--  Definitions of Managed Objects for Digital Equipment Corporation's
--                     DEChub900 Token Ring Linecards
--                     ==============================
--
--
--
--                Name:    ptrm3-0.txt
--                Version: Version 3.0
--                Date:    April, 1997
--                Company: Digital Equipment Corporation
--                Mail:    hub900-support@lkg.dec.com
--
--
--  
--  This Digital Equipment  Corporation  SNMP  Management  Information  Base
--  Specification  embodies Digital Equipment Corporation's confidential and
--  proprietary  intellectual  property.   Digital   Equipment   Corporation
--  retains  all  title  and  ownership  in the Specification, including any
--  revisions.
--  
--  It is Digital Equipment Corporation's intent to encourage the widespread
--  use  of  this Specification in connection with the management of Digital
--  Equipment Corporation products.
--  
--  Digital Equipment  Corporation  grants  vendors,  end-users,  and  other
--  interested  parties a non-exclusive license to use this Specification in
--  connection  with  the  management  of  Digital   Equipment   Corporation
--  products.
--  
--  Digital Equipment Corporation reserves the right to make changes in this
--  specification  and  other information contained in this document without
--  prior notice.
--  
--  Digital Equipment Corporation makes no  warranty,  either  expressed  or
--  implied,  as  to  the  use,  operation, condition, or performance of the
--  Specification.  In no  event  shall  Digital  Equipment  Corporation  be
--  liable  for  any incidental, indirect, special, or consequential damages
--  whatsoever (including but not limited to loss of profits) arising out of
--  or related to this document or the information contained in it.
--
--
--
--
--
--
--  1  Status of This Memo
--
--  This MIB module provides definitions for Digital Equipment Corporation's
--  DEChub900 MultiSwitch token ring products.  This MIB is implemented by 
--  the DEChub900's Hub Manager.
--
--  Digital posts product MIBs on web sites at:
--
--            http://www.networks.digital.com/
--            http://www.networks.europe.digital.com/
--            http://www.networks.digital.com.au/
--  
--  This particular MIB is kept in:
--            
--            http://www.networks.digital.com/dr/hubs/mibs
--
--
--  Inquiries about the contents and use of this MIB may be sent to 
--  hub900-support@lkg.dec.com.
--
--
--
--  2  Relationship To Other MIBs
--
--  The  objects  defined  in  this   MIB   are   located   under   the
--  private.enterprises subtree as shown below:
--
--                    iso(1).org(3).dod(6).internet(1)
--                                 |
--                              private(4)
--                                 |
--                              enterprises(1)
--                                 |
--                              dec(36)
--                                 |
--                              ema(2)
--                                 |
--                              decMIBextension(18)
--                                 |
--                              decHub900(11)
--                                 |
--            .==============.============.==============// ...etc...
--            |              |            |
--            |              |        .=========.
--       mgmtAgent(1)     common(2)   | ptrm(3) |
--                                    |=========|
--
--
--
--
--  3  Abstract
--
--
--  This module contains definitions for Digitial Equipment Corporation's
--  DEChub900 Token Ring products.  This MIB is implemented by the 
--  DEChub900's Hub Manager.
--
--
--
--  4  References
--
--
--  [1]  RFC 1213.  McCloghrie, K., and M. Rose, "Management Information Base 
--       for Network Management of TCP/IP-based Internets".  March, 1991.
--
--  [2]  RFC 1155.  Rose, M., and K. McCloghrie, "Structure and Identification 
--       of Management Information for TCP/IP-based Internets".  May, 1990.
--
--
--
--  5  Object Synopsis
--
--
--
--  Object Name                             Object ID            Non-Vol
--  =================================       =================    ========
--
--  p = 1.3.6.1.4.1.36.2.18.decHub900(11).ptrm(3)
--
--  ptrm                                    p
--    ptrmBase                              p.1
--      ptrmBaseForceSpeed                  p.1.2.0              Yes
--      ptrmBaseSpeed                       p.1.3.0              
--      ptrmBaseNumLobes                    p.1.4.0
--    ptrmTrunkTable                        p.2
--      ptrmTrunkEntry                      p.2.1
--        ptrmTrunkType                     p.2.1.1.n
--        ptrmTrunkOperStatus               p.2.1.2.n
--        ptrmTrunkAdminStatus              p.2.1.3.n            Yes
--        ptrmTrunkMedia                    p.2.1.4.n
--        ptrmTrunkAutoWrapEnable           p.2.1.5.n            Yes
--        ptrmTrunkAutoPartitionStatus      p.2.1.6.n
--        ptrmTrunkDetectedSpeed            p.2.1.7.n
--        ptrmTrunkPhantomDrive             p.2.1.8.n
--        ptrmTrunkPhantomDetect            p.2.1.9.n
--    ptrmLobeTable                         p.3
--      ptrmLobeEntry                       p.3.1
--        ptrmLobeIndex                     p.3.1.1.n
--        ptrmLobeOperStatus                p.3.1.2.n
--        ptrmLobeAdminStatus               p.3.1.3.n            Yes
--        ptrmLobeMedia                     p.3.1.4.n
--        ptrmLobeAutoWrapEnable            p.3.1.5.n            Yes
--        ptrmLobeAutoPartitionStatus       p.3.1.6.n
--        ptrmLobeDetectedSpeed             p.3.1.7.n
--        ptrmLobePhantomDrive              p.3.1.8.n
--        ptrmLobePhantomDetect             p.3.1.9.n
--
--   ptrmMacTable                           p.4
--     ptrmMacEntry                         p.4.1 
--       ptrmMacIndex                       p.4.1.1.n
--       ptrmMacRingInterface               p.4.1.2.n
--       ptrmMacAddress                     p.4.1.3.n
--       ptrmMacPosition                    p.4.1.4.n
--
--   ptrmMultiBp                            p.5
--      ptrmNumBackplanePorts               p.5.1
--      ptrmNumLobePorts                    p.5.2
--      ptrmMultiBpPortTable                p.5.3
--        ptrmMultiBpPortEntry              p.5.3.1
--          ptrmMultiBpPortIndex            p.5.3.1.1.n 
--          ptrmMultiBpPortSpeed            p.5.3.1.2.n      (Trapped)
--          ptrmMultiBpPortForceSpeed       p.5.3.1.3.n      (Non Volatile)
--
--

IMPORTS
    enterprises
        FROM RFC1155-SMI
    OBJECT-TYPE
        FROM RFC-1212;

--  Path to the Token Ring MIB.

dec               OBJECT IDENTIFIER ::= { enterprises 36 }
ema               OBJECT IDENTIFIER ::= { dec 2 }
decMIBextension   OBJECT IDENTIFIER ::= { ema 18 }
decHub900         OBJECT IDENTIFIER ::= { decMIBextension 11 }

--  The Token Ring linecard MIB.

ptrm              OBJECT IDENTIFIER ::= { decHub900 3 }

--
--  The ptrm Base Group.
--

ptrmBase OBJECT IDENTIFIER ::= { ptrm 1 }

-- Object is deleted from this MIB. This VID cannot be reused
-- ptrmBaseAdminStatus OBJECT-TYPE
--    SYNTAX  INTEGER {
--                enable(1), 
--                disable(2) 
--                }
--    ACCESS  read-write
--    STATUS  deprecated
--    DESCRIPTION 
--        "A global master action variable to disable(2) all ports
--         on the linecard.  This object is provided for network 
--         troubleshooting.
--         This object must be set to enable(1) for normal operation.
--
--         The value of this object is maintained across power cycles
--         and resets."
--    ::= { ptrmBase 1 }

ptrmBaseForceSpeed OBJECT-TYPE
    SYNTAX  INTEGER {
                notForced(1),
                force-4Mbps(2),
                force-16Mbps(3)
                }
    ACCESS  read-write
    STATUS  mandatory
    DESCRIPTION
        "This object selects the speed at which to token ring linecard
         operates.  When set to notForced(1), the linecard will not be forced.

         Based on the line-card its speed may change by a voting algorithm
         on its lobe ports or by console selection.

         Forcing the speed to 4 or 16 only applies when stand-alone; 
         in a hub, the ring to which the module is forced determines the
         speed at which it operates.

         The value of this object is maintained across power cycles
         and resets."
    ::= { ptrmBase 2 }

ptrmBaseSpeed OBJECT-TYPE
    SYNTAX  INTEGER {
                autoBauding(1),
                speed-4Mbps(2),
                speed-16Mbps(3)
                }
    ACCESS  read-only
    STATUS  mandatory
    DESCRIPTION
        "Indicates the speed at which the linecard is operating.  
         Devices like the DECmau 900TL autobaud when they are not forced 
         via ptrmBaseForceSpeed and if there are no stations plugged into the
         lobe ports.
         Devices like the DECmau 900TH (Dtmxm) have a default speed of 16Mbps
         which can also be changed via a console interface."

    ::= { ptrmBase 3 }

ptrmBaseNumLobes OBJECT-TYPE
    SYNTAX  INTEGER (0..99)
    ACCESS  read-only
    STATUS  mandatory
    DESCRIPTION
        "The number of end station lobes supported by this module.
         This is the number of rows in the ptrmLobeTable.  This 
         variable is zero for repeaters."
    ::= { ptrmBase 4 }

--
--  The Trunk Table
--

ptrmTrunkTable OBJECT-TYPE
    SYNTAX  SEQUENCE OF PtrmTrunkEntry
    ACCESS  not-accessible
    STATUS  mandatory
    DESCRIPTION
        "Defines a table with rows for each token ring connection 
         not otherwise associated with an end-user 'lobe' port. 
         The following rows are implemented:

                ptrmTrunkType   Leaf VIDs       Port
                ------------    ----------      ----
                RingIn  (1)     3.2.1.x.1       Copper Ring In
                RingOut (2)     3.2.1.x.2       Copper Ring Out
                HubA-1  (3)     3.2.1.x.3       Hub token ring A port 1
                HubB-1  (4)     3.2.1.x.4       Hub token ring B port 1
                FibreIn (5)     3.2.1.x.5       FibreRingIn
                FibreOut(6)     3.2.1.x.6       FibreRingOut
                HubA-2  (7)     3.2.1.x.3       Hub token ring A port 2
                HubB-2  (8)     3.2.1.x.4       Hub token ring B port 2

                "
    ::= { ptrm 2 }

ptrmTrunkEntry OBJECT-TYPE
    SYNTAX  PtrmTrunkEntry
    ACCESS  not-accessible
    STATUS  mandatory
    DESCRIPTION
        "A collection of trunk objects."
    INDEX { ptrmTrunkType }
    ::= { ptrmTrunkTable 1 }

--
-- Not all variables apply to all trunks.  Comments below indicate
-- which vars are applicable
--                                             Trunk Type
--                                          RI      RO      HubA-1/2,HubB-1/2
PtrmTrunkEntry ::= SEQUENCE {
    ptrmTrunkType                        --  X       X       X
        INTEGER,
    ptrmTrunkOperStatus                  --  X       X       X
        INTEGER,
    ptrmTrunkAdminStatus                 --  X       X       X
        INTEGER,
    ptrmTrunkMedia                       --  X       X
        INTEGER,
    ptrmTrunkAutoWrapEnable              --  X       X
        INTEGER,
    ptrmTrunkAutoPartitionStatus         --  X       X       X
        INTEGER,
    ptrmTrunkDetectedSpeed               --  X       X
        INTEGER,
    ptrmTrunkPhantomDrive                --  X       
        INTEGER,
    ptrmTrunkPhantomDetect               --  X       X
        INTEGER
-- Object is deleted from this MIB. This VID cannot be reused
--   DEPRECATED          
--    ptrmTrunkPollResponse                
--        INTEGER,
--   DEPRECATED       
--    ptrmTrunkHlapOperSpeed               
--        INTEGER
    }

ptrmTrunkType OBJECT-TYPE
    SYNTAX  INTEGER {
                copperRingIn(1),
                copperRingOut(2),
                hubA(3),
                hubB(4),
                fiberRingIn(5),
                fiberRingOut(6)
                }
    ACCESS  read-only
    STATUS  mandatory
    DESCRIPTION 
        "Identifies a trunk (i.e. non-lobe) port.  All token ring
         modules implement all four rows defined by the ptrmTrunkType 
         values.  If a module's configuration does not allow it to
         implement the particular trunk ptrmTrunkOperStatus is
         notPresent(3).  For example, linecards in a hub do not have a 
         RingIn or RingOut port and therefore contain the value
         notPreset(3) as the ptrmTrunkOperStatus for ringIn(1) and 
         ringOut(2) rows of the trunk table.

         Linecards that do not have a fiber interface need not implement
         rows FiberIn(5) and FiberOut(6).
         NOTE - If a Trunk is notPresent, the rest of the values in this
         table are to be ignored."
    ::= { ptrmTrunkEntry 1 }

ptrmTrunkOperStatus OBJECT-TYPE                         -- TRAPPED
    SYNTAX  INTEGER {
                inserted(1),
                wrapped(2),
                notPresent(3),
                badSpeed(4)
                }
    ACCESS  read-only
    STATUS  mandatory
    DESCRIPTION
        "Indicates whether the trunk port is wrapped or inserted 
         into the linecard's internal ring. If the trunk port is not
         implemented in the linecard's current configuration, then
         this is notPresent(3).  If a trunk is notPresent(3), then
         the values read from all other columns of the row are 
         undefined.

         If the port is enabled and an incompatible speed is
         detected, the value of this object is 'badSpeed(4)'.
         The trunk TCU is wrapped when in the badSpeed state.
         When there is a change in this object, a csnmp Trap is
         sent to the MAM."
    ::= { ptrmTrunkEntry 2 }

ptrmTrunkAdminStatus OBJECT-TYPE
    SYNTAX  INTEGER {
                enabled(1),
                disabled(2)
                }
    ACCESS  read-write
    STATUS  mandatory        
    DESCRIPTION
        "Used to disable the trunk port of the linecard during 
         operation. When disabled, the trunk port is forced to wrap.

         The value of this object is maintained across power cycles
         and resets."
        ::= { ptrmTrunkEntry 3 }

ptrmTrunkMedia OBJECT-TYPE
    SYNTAX  INTEGER {
                otherMedia(1),          -- A media type not listed below
                utpMedia(2),            -- unshielded twisted pair
                stpMedia(3),            -- RJ45 shielded twisted pair
                ibmMedia(4),            -- IBM Data Connector (stp)
                fiberMedia(5),          -- Fiber connection
                hubDirect(6),           -- Hub direct connection (100 ohm)
                                        -- No TCU on Module
                hubTCU(7)               -- Hub connection (TCU on module)
                }
    ACCESS  read-only                
    STATUS  mandatory        
    DESCRIPTION
        "The media type of the trunk port. Different module types have
         different trunk connectors.  If a module implements an 
         STP/UTP switch, this variable indicates the setting of that
         switch.

         linecards feature Trunk Coupling Units (TCUs) on the module for 
         their hub trunk connection, so they have 'media' type hubTCU(7).
         Repeaters have a direct connection to the hub backplane, so
         their hub trunk 'media' type is hubDirect(6)."
    ::= { ptrmTrunkEntry 4 }

ptrmTrunkAutoWrapEnable OBJECT-TYPE
    SYNTAX  INTEGER { 
                on(1), 
                off(2),
                notApplicable(3)
                }
    ACCESS  read-write
    STATUS  mandatory
    DESCRIPTION
        "The value of the physical Auto Wrap Enable (AWE) switch for the 
         trunk port.  AWE is provided only for RingIn and RingOut trunks.
         AWE should be set ON for connection to DEChub token
         ring linecards.  It should be set OFF when an
         IBM 8228 or equivalent 'dumb' linecard is connected.  It MUST be
         physically switched to ON when no cable is inserted into
         the RI port, in order to cause RI to wrap.

         This value of this object is notApplicable(3) for hub trunks.

         The value of this object is maintained across power cycles
         and resets."
    ::= { ptrmTrunkEntry 5 }

ptrmTrunkAutoPartitionStatus OBJECT-TYPE
    SYNTAX  INTEGER { 
                notAutoPartitioned(1),
                autoPartitioned(2)
                }
    ACCESS  read-only
    STATUS  mandatory
    DESCRIPTION
        "Indicates whether the trunk port has been auto-partitioned.
         When autopartitioned(2) a trunk is automatically wrapped."
    ::= { ptrmTrunkEntry 6 }

ptrmTrunkDetectedSpeed OBJECT-TYPE
    SYNTAX  INTEGER {
                invalid(1),
                speed-4Mbps(2),
                speed-16Mbps(3),
                notApplicable(4)
                }
    ACCESS  read-only        
    STATUS  mandatory
    DESCRIPTION
        "Indicates the speed detected on the incoming data pair.
         invalid(1) indicates that a valid token ring speed was not 
         detected.  notApplicable(4) indicates that the trunk port 
         does not implement speed detect.  Hub trunks do not detect 
         speed."
    ::= { ptrmTrunkEntry 7 }

ptrmTrunkPhantomDrive OBJECT-TYPE
    SYNTAX  INTEGER {
                notApplicable(1),
                noDrive(2),
                driveReceive(3),
                wireFault(4) 
                }
    ACCESS  read-only
    STATUS  mandatory
    DESCRIPTION
        "Indicates the state of the RingIn port's phantom current drive 
         and return detect circuits.  It is notApplicable(1) on all other
         trunk types.  The noDrive(2) status indicates RingIn is not
         driving phantom current.  driveReceive(3) is the normal case
         where an active linecard drives phantom current on RingIn and 
         it is returned correctly from the upstream linecard.  wireFault(4)
         indicates the linecard is driving phantom current but the current
         is not returned correctly, due to either an open or short
         circuit."
    ::= { ptrmTrunkEntry 8 }

ptrmTrunkPhantomDetect OBJECT-TYPE
    SYNTAX  INTEGER {
                notApplicable(1),
                noDetectPhantom(2),
                detectPhantom(3)
                }
    ACCESS  read-only
    STATUS  mandatory
    DESCRIPTION
        "Indicates the state of the incoming phantom current detect circuit
         for the RingIn/RingOut Trunk.  It is notApplicable(1) to all other
         trunk types."
    ::= { ptrmTrunkEntry 9 }

-- Object is deleted from this MIB. This VID cannot be reused
-- ptrmTrunkPollResponse OBJECT-TYPE
--     SYNTAX  INTEGER {
--                notApplicable(1),
--                noPollResponse(2),
--                pollResponse(3)
--                }
--    ACCESS  read-only
--    STATUS  deprecated
--    DESCRIPTION
--        "Indicates whether a satellite linecard or repeater has responded
--         to polls sent on the management channel of copper repeater 
--         Ring Out ports.  It is not applicable to all other trunk 
--         types, including a linecard RingOut port."
--    ::= { ptrmTrunkEntry 10 }

-- Object is deleted from this MIB. This VID cannot be reused
--
-- ptrmTrunkHlapOperSpeed OBJECT-TYPE
--    SYNTAX  INTEGER (0..255)
--    ACCESS  read-only
--    STATUS  deprecated
--    DESCRIPTION
--        "This variable indicates the speed of a remote management
--         link along the RingOut port of a device.  The value may
--         be one of the following:
--
--                not-applicable(0),
--                speed-9600bps(1),
--                speed-19200bps(2),
--                speed-38400bps(3),
--                speed-56000bps(4),
--                speed-1200000bps(5)
--
--         At this time, the only usage of a management link along
--         RingOut is for the case of a standalone token DecRepeater.
--         For all other cases, the value of this variable is 
--         not-applicable(0)."
--    ::= { ptrmTrunkEntry 11  } 

--
-- Lobe Management
--

ptrmLobeTable OBJECT-TYPE
    SYNTAX  SEQUENCE OF PtrmLobeEntry
    ACCESS  not-accessible
    STATUS  mandatory
    DESCRIPTION
        "A table with entries to manage individual end station lobe 
         ports of the linecard."
    ::= { ptrm 3 }

ptrmLobeEntry OBJECT-TYPE
    SYNTAX  PtrmLobeEntry
    ACCESS  not-accessible
    STATUS  mandatory
    DESCRIPTION
        "A lobe entry."
    INDEX { ptrmLobeIndex }
    ::= { ptrmLobeTable 1 }

PtrmLobeEntry ::=
    SEQUENCE {
        ptrmLobeIndex                    
            INTEGER,
        ptrmLobeOperStatus               
            INTEGER,
        ptrmLobeAdminStatus              
            INTEGER,
        ptrmLobeMedia                    
            INTEGER,
        ptrmLobeAutoWrapEnable                
            INTEGER,
        ptrmLobeAutoPartitionStatus      
            INTEGER,
        ptrmLobeDetectedSpeed            
            INTEGER,
        ptrmLobePhantomDrive                     
            INTEGER,
        ptrmLobePhantomDetect            
            INTEGER
-- Object is deleted from this MIB. This VID cannot be reused
--        ptrmLobePollResponse
--            INTEGER,
--        ptrmLobeHlapOperSpeed
--            INTEGER
    }

ptrmLobeIndex OBJECT-TYPE
    SYNTAX  INTEGER (1..65535)
    ACCESS  read-only
    STATUS  mandatory
    DESCRIPTION 
        "Port number for the lobe, as it appears externally to the
         user, i.e. 1 for the port labeled '1'."
    ::= { ptrmLobeEntry 1 }

ptrmLobeOperStatus OBJECT-TYPE                          -- TRAPPED
    SYNTAX  INTEGER {
                inserted(1),
                wrapped(2),
                notPresent(3),
                badSpeed(4)
                }
    ACCESS  read-only
    STATUS  mandatory
    DESCRIPTION
        "Indicates whether the lobe port is wrapped or inserted 
         into the linecard's internal ring.  If the lobe port is not
         implemented in the linecard's current configuration the value
         of this object is notPresent(3).  If a lobe is notPresent(3)
         then the values of other variables in the row are undefined. 

         If the port is enabled and an incompatible speed is
         detected, this variable becomes 'badSpeed(4)'.
         The lobe TCU is wrapped when in the badSpeed state.
         When there is a change in this object, a CSNMP trap is sent to
         the MAM."
    ::= { ptrmLobeEntry 2 }

ptrmLobeAdminStatus OBJECT-TYPE
    SYNTAX  INTEGER {
                enabled(1),
                disabled(2)
                }
    ACCESS  read-write
    STATUS  mandatory        
    DESCRIPTION
        "Used to disable the lobe port during network troubleshooting.
         If set to disabled(2), the lobe port is forced to wrap.  
         This object must be set to enabled(1) for normal operation.

         The value of this object is maintained across power cycles
         and resets."
    ::= { ptrmLobeEntry 3 }

ptrmLobeMedia OBJECT-TYPE
    SYNTAX  INTEGER {
                otherMedia(1),          -- A media type not listed below
                utpMedia(2),            -- RJ45 unshielded twisted pair
                stpMedia(3),            -- RJ45 shielded twisted pair
                ibmMedia(4),            -- IBM Data Connector (stp)
                fiberMedia(5)           -- Fiber connection
                }
    ACCESS  read-only                
    STATUS  mandatory        
    DESCRIPTION
        "The media type of the lobe port.  Different module types have
         different lobe connectors.  If a module implements an 
         STP/UTP switch for lobes, this variable indicates the setting
         of that switch."
    ::= { ptrmLobeEntry 4 }

ptrmLobeAutoWrapEnable OBJECT-TYPE
    SYNTAX  INTEGER { 
                on(1),
                off(2) 
                }
    ACCESS  read-write
    STATUS  mandatory
    DESCRIPTION 
        "Software configuration variable set by network management.

         Auto Wrap Enabled (AWE) should be set on(1) for connection to 
         end stations and the RingIn ports of DEC token ring products.  
         It may be set off(2) for lobe connection to IBM 8228 or 
         equivalent 'dumb' linecards  which do not drive phantom current.
         The factory default is on(1).

         The value of this object is maintained across power cycles
         and resets."
    ::= { ptrmLobeEntry 5 }

ptrmLobeAutoPartitionStatus OBJECT-TYPE
    SYNTAX  INTEGER { 
                notAutoPartitioned(1),
                autoPartitioned(2)
                }
    ACCESS  read-only
    STATUS  mandatory
    DESCRIPTION
        "Indicates whether the lobe port has been auto-partitioned.
         When autoPartitioned(2), a lobe is automatically wrapped."
    ::= { ptrmLobeEntry 6 }

ptrmLobeDetectedSpeed OBJECT-TYPE
    SYNTAX  INTEGER {
                invalid(1),
                speed-4Mbps(2),
                speed-16Mbps(3),
                notApplicable(4)
                }
    ACCESS  read-only        
    STATUS  mandatory
    DESCRIPTION
        "Indicates the speed detected on the incoming data pair.
         If invalid(1) a valid token ring speed was not detected.
         If notApplicable(4), the lobe port does not implement 
         speed detect."
    ::= { ptrmLobeEntry 7 }

ptrmLobePhantomDrive OBJECT-TYPE
    SYNTAX  INTEGER {
                notApplicable(1)                
                }
    ACCESS  read-only
    STATUS  mandatory
    DESCRIPTION
        "This variable is not applicable to lobe ports, and is 
         defined only as a place holder for the corresponding trunk
         variable."
    ::= { ptrmLobeEntry 8 }

ptrmLobePhantomDetect OBJECT-TYPE
    SYNTAX  INTEGER {
                notApplicable(1),
                noDetectPhantom(2),
                detectPhantom(3)
                }
    ACCESS  read-only
    STATUS  mandatory
    DESCRIPTION
        "Indicates the state of the incoming phantom current detect 
         circuit for the lobe port.  Lobe ports are required to implement
         phantom detect circuitry; the notApplicable code is provided
         only for the corresponding trunk port variable."
    ::= { ptrmLobeEntry 9 }

-- Object is deleted from this MIB. This VID cannot be reused

-- ptrmLobePollResponse OBJECT-TYPE
--     SYNTAX  INTEGER {
--                notApplicable(1),
--                noPollResponse(2),
--                pollResponse(3)
--                }
--    ACCESS  read-only
--    STATUS  deprecated
--    DESCRIPTION
--        "Indicates whether a satellite linecard or repeater has responded
--         to polls sent on the management channel of the lobe port."
--    ::= { ptrmLobeEntry 10 }
--

-- Object is deleted from this MIB. This VID cannot be reused

-- ptrmLobeHlapOperSpeed OBJECT-TYPE
--    SYNTAX  INTEGER (0..255)
--    ACCESS  read-only
--    STATUS  deprecated
--    DESCRIPTION
--        "This variable indicates the speed of a remote management
--         link along a lobe port of a device.  The value may be one 
--         of the following:
--          
--                not-applicable(0),
--                speed-9600bps(1),
--                speed-19200bps(2),
--                speed-38400bps(3),
--                speed-56000bps(4),
--                speed-1200000bps(5)
--
--         If the token ring module does not support remote
--         management links out its lobes, the value of this
--         variable is not-applicable(0)."
--     ::= { ptrmLobeEntry 11  } 

--
-- Mac Table
-- This table is mandatory for ALL DEC token ring products that have their
-- own Mac. It need not be implemented by products that have no MAC ie.
-- DECmau900 TL.
-- This group gives important information to TR Agent modules that offer
-- services like Ring Mapping. 
--

ptrmMacTable OBJECT-TYPE
    SYNTAX  SEQUENCE OF PtrmMacEntry
    ACCESS  not-accessible
    STATUS  mandatory
    DESCRIPTION
        "A table with entries. The table has 1 entry per MAC chip it contains.
        "
    ::= { ptrm 4 }

ptrmMacEntry OBJECT-TYPE
    SYNTAX  PtrmMacEntry
    ACCESS  not-accessible
    STATUS  mandatory
    DESCRIPTION
        "An entry for the Mac ."
    INDEX { ptrmMacIndex }
    ::= { ptrmMacTable 1 }

PtrmMacEntry ::=
    SEQUENCE {
        ptrmMacIndex                    
            INTEGER,
        ptrmMacRingInterface               
            INTEGER,
        ptrmMacAddress              
            OCTET STRING,
        ptrmMacPosition                    
            INTEGER
    }

ptrmMacIndex OBJECT-TYPE
    SYNTAX  INTEGER (1..65535)
    ACCESS  read-only
    STATUS  mandatory
    DESCRIPTION 
        "An index into the table. There is 1 entry in the table per MAC chip"
    ::= { ptrmMacEntry 1 }

ptrmMacRingInterface OBJECT-TYPE
    SYNTAX  INTEGER 
    ACCESS  read-only
    STATUS  mandatory
    DESCRIPTION
         "Indicates the Ring Interface number corresponding to this MAC.

          Typically single-ring devices will have only 1 Ring Interface.
          Devices like the Active Retimed concentartor which suppport 
          multiple segements may have more than 1 ring interface.
          Note - the interface number must match that reported in the
          dot5.mib"
    ::= { ptrmMacEntry 2 }

ptrmMacAddress OBJECT-TYPE
    SYNTAX  OCTET STRING (SIZE (6))
    ACCESS  read-only
    STATUS  mandatory        
    DESCRIPTION
        "The Mac address in MSB form for this interface."
    ::= { ptrmMacEntry 3 }

ptrmMacPosition OBJECT-TYPE
    SYNTAX  INTEGER (1..255)
    ACCESS  read-only                
    STATUS  mandatory        
    DESCRIPTION
        "This is the position of the Mac Chip.
         For modules like the DTMXM, the position of the MAC is settable 
         via software. It can be either before port 1 (MacForward) or 
         after its last port (MacBackward)
         This makes it easy to partition the ports on its own ring 
         for an accurate ring map. 

         Modules that are end-stations and hence have no lobe ports may
         report Mac position as 1.

         if the Mac is in MacForward position the ptrmMacPosition should be
         reported as 255.

         For all other Ports, if the Mac is between port A and port B,
         the Mac postion should be reported as port A."
    ::= { ptrmMacEntry 4 }

ptrmMultiBp OBJECT IDENTIFIER ::= { ptrm 5 }

ptrmNumBackplanePorts OBJECT-TYPE
    SYNTAX  INTEGER
    ACCESS  read-only
    STATUS  mandatory
    DESCRIPTION
        "
         Number of physical TokenRing backplane ports.
        " 
    ::= { ptrmMultiBp 1 }                               -- p.5.1

ptrmNumLobePorts OBJECT-TYPE
    SYNTAX  INTEGER
    ACCESS  read-only
    STATUS  mandatory
    DESCRIPTION
        "
         Number of lobe ports the linecard has
        " 
    ::= { ptrmMultiBp 2 }                               -- p.5.2

ptrmMultiBpPortTable OBJECT-TYPE
    SYNTAX  SEQUENCE OF PtrmMultiBpPortEntry
    ACCESS  not-accessible
    STATUS  mandatory
    DESCRIPTION
        "
         This table MUST be supported by TR linecards like the MIPPY, which
         support multiple physical Token Ring backplane ports. 
         The number of rows in ptrmMultiBpPortTable will be
         ptrmNumBackplanePorts 
         The ptrmBase group does not have to supported in this
         configuration. 

        "
    ::= { ptrmMultiBp 3 }                               -- p.5.3

ptrmMultiBpPortEntry OBJECT-TYPE
    SYNTAX  PtrmMultiBpPortEntry
    ACCESS  not-accessible
    STATUS  mandatory
    DESCRIPTION
        "
        "
    INDEX  { ptrmMultiBpPortIndex }
    ::= { ptrmMultiBpPortTable 1 }                      -- p.5.3.1

PtrmMultiBpPortEntry ::=
    SEQUENCE {
      ptrmMultiBpPortIndex
        INTEGER,  
      ptrmMultiBpPortSpeed
        INTEGER,
      ptrmMultiBpPortForceSpeed
        INTEGER
        }

ptrmMultiBpPortIndex OBJECT-TYPE
    SYNTAX  INTEGER
    ACCESS  read-only
    STATUS  mandatory
    DESCRIPTION
        "
         Index into the table. Corresponds to backplane port number.
        "                                       
    ::= { ptrmMultiBpPortEntry 1 }              -- p.5.3.1.1.n

ptrmMultiBpPortSpeed OBJECT-TYPE
    SYNTAX  INTEGER {
                speed-4Mbps(2),
                speed-16Mbps(3)
             }
    ACCESS  read-only
    STATUS  mandatory
    DESCRIPTION
        "
         Indicates the speed at which the backplane port is operating.  

         The port MUST have a default speed of 4Mbps or 16Mbps 
         to support plug and play operation
        "
    ::= { ptrmMultiBpPortEntry 2 }              -- p.5.3.1.2.n

ptrmMultiBpPortForceSpeed OBJECT-TYPE
    SYNTAX  INTEGER {
                notForced(1),
                force-4Mbps(2),
                force-16Mbps(3)
             }
    ACCESS  read-write
    STATUS  mandatory
    DESCRIPTION
        "
         This is used only for STANDALONE operation.
         This object selects the speed at which to token ring port
         operates.  

         The value of this object is maintained across power cycles
         and resets.

        "
    ::= { ptrmMultiBpPortEntry 3 }              -- p.5.3.1.3.n NV

END
