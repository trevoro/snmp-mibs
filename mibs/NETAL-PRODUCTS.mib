NETAL-PRODUCTS DEFINITIONS ::= BEGIN

IMPORTS
	networkAlchemy, netalProducts, netalModules     FROM NETAL-SMI
	MODULE-IDENTITY,OBJECT-IDENTITY, enterprises	FROM SNMPv2-SMI;

netalProductsMIB MODULE-IDENTITY
    LAST-UPDATED "200101160000Z"
    ORGANIZATION "Network Alchemy, Inc."
    CONTACT-INFO 
		 "	Network Alchemy
			Customer Support
		Postal: 1538 Pacific Av.
			Santa Cruz, CA 95060
			USA
	        E-Mail: snmp-contact@network-alchemy.com"
    DESCRIPTION
             "The Network Alchemy products MIB module."
    ::= { netalModules 1 }

netalHardwareUnknown OBJECT-IDENTITY
        STATUS  current
        DESCRIPTION
                "Unknown hardware."
        ::= { netalProducts 1 }

netalKiltlifterUnknown OBJECT-IDENTITY
        STATUS  current
        DESCRIPTION
                "Kiltlifter UNKNOWN."
        ::= { netalProducts 2 }

netalStingrayUnknown OBJECT-IDENTITY
        STATUS  current
        DESCRIPTION
                "Stingray UNKNOWN."
        ::= { netalProducts 3 }

netalCryptoCluster500 OBJECT-IDENTITY
        STATUS  current
        DESCRIPTION
                "CryptoCluster 500."
        ::= { netalProducts 4 }

netalCryptoCluster5010 OBJECT-IDENTITY
        STATUS  current
        DESCRIPTION
                "CryptoCluster 5010."
        ::= { netalProducts 5 }

netalCryptoCluster501 OBJECT-IDENTITY
        STATUS  current
        DESCRIPTION
                "CryptoCluster 501."
        ::= { netalProducts 8 }

netalCryptoCluster5000 OBJECT-IDENTITY
        STATUS  current
        DESCRIPTION
                "CryptoCluster 5000."
        ::= { netalProducts 10 }

netalCryptoCluster2500 OBJECT-IDENTITY
        STATUS  current
        DESCRIPTION
                "CryptoCluster 2500."
        ::= { netalProducts 11 }

netalCryptoCluster2501 OBJECT-IDENTITY
        STATUS  current
        DESCRIPTION
                "CryptoCluster 2501."
        ::= { netalProducts 12 }

netalFreeBSDApplication OBJECT-IDENTITY
        STATUS  current
        DESCRIPTION
                "FreeBSD application."
        ::= { netalProducts 13 }

netalCryptoCluster5200 OBJECT-IDENTITY
        STATUS  current
        DESCRIPTION
                "CryptoCluster 5200."
        ::= { netalProducts 15 }

netalCryptoCluster5205 OBJECT-IDENTITY
        STATUS  current
        DESCRIPTION
                "CryptoCluster 5205."
        ::= { netalProducts 16 }

netalCA200 OBJECT-IDENTITY
        STATUS  current
        DESCRIPTION
                "CA200."
        ::= { netalProducts 18 }

netalCA600 OBJECT-IDENTITY
        STATUS  current
        DESCRIPTION
                "CA600."
        ::= { netalProducts 19 }

netalChameleon100 OBJECT-IDENTITY
        STATUS  current
        DESCRIPTION
                "Chameleon 100."
        ::= { netalProducts 20 }


END
