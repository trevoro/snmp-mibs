Nortel-Magellan-Passport-X25TraceRcvrMIB
DEFINITIONS ::= BEGIN



IMPORTS

      OBJECT-TYPE
   FROM RFC-1212

      passportMIBs
   FROM Nortel-Magellan-Passport-UsefulDefinitionsMIB

      DisplayString,
      StorageType,
      RowStatus,
      Integer32,
      Unsigned32
   FROM Nortel-Magellan-Passport-StandardTextualConventionsMIB

      Hex,
      NonReplicated,
      HexString,
      EnterpriseDateAndTime,
      DigitString
   FROM Nortel-Magellan-Passport-TextualConventionsMIB

      traceSessionIndex,
      traceRcvrIndex,
      traceSession,
      traceIndex,
      traceRcvr
   FROM Nortel-Magellan-Passport-TraceBaseMIB;




-- LAST-UPDATED   "9702280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     X25TraceRcvr Enterprise MIB."

x25TraceRcvrMIB OBJECT IDENTIFIER ::= { passportMIBs 62 }










-- Trace Rcvr/<string> X25
-- This component identifies the access method used by the receiver of 
-- the trace data as X.25.

traceRcvrX25 OBJECT IDENTIFIER ::= { traceRcvr 2 }



traceRcvrX25RowStatusTable OBJECT-TYPE
   SYNTAX     SEQUENCE OF TraceRcvrX25RowStatusEntry
   ACCESS     not-accessible
   STATUS     mandatory
   DESCRIPTION
     "This entry controls the addition and deletion of 
      traceRcvrX25 components."
::= { traceRcvrX25 1 }

traceRcvrX25RowStatusEntry OBJECT-TYPE
   SYNTAX     TraceRcvrX25RowStatusEntry
   ACCESS     not-accessible
   STATUS     mandatory
   DESCRIPTION
     "A single entry in the table represents a single 
      traceRcvrX25 component."
   INDEX {
      traceIndex,
      traceRcvrIndex,
      traceRcvrX25Index }
::= { traceRcvrX25RowStatusTable 1 }

TraceRcvrX25RowStatusEntry ::= SEQUENCE {
   traceRcvrX25RowStatus
      RowStatus,
   traceRcvrX25ComponentName
      DisplayString,
   traceRcvrX25StorageType
      StorageType,
   traceRcvrX25Index
      NonReplicated }

traceRcvrX25RowStatus OBJECT-TYPE
   SYNTAX     RowStatus 
   ACCESS     read-write
   STATUS     mandatory
   DESCRIPTION
     "This variable is used as the basis for SNMP naming of
      traceRcvrX25 components.
      These components can be added and deleted."
::= { traceRcvrX25RowStatusEntry 1 }

traceRcvrX25ComponentName OBJECT-TYPE
   SYNTAX     DisplayString 
   ACCESS     read-only
   STATUS     mandatory
   DESCRIPTION
     "This variable provides the component's string name for
      use with the ASCII Console Interface"
::= { traceRcvrX25RowStatusEntry 2 }

traceRcvrX25StorageType OBJECT-TYPE
   SYNTAX     StorageType 
   ACCESS     read-only
   STATUS     mandatory
   DESCRIPTION
     "This variable represents the storage type value for the
      traceRcvrX25 tables."
::= { traceRcvrX25RowStatusEntry 4 }

traceRcvrX25Index OBJECT-TYPE
   SYNTAX     NonReplicated 
   ACCESS     not-accessible
   STATUS     mandatory
   DESCRIPTION
     "This variable represents the index for the traceRcvrX25 tables."
::= { traceRcvrX25RowStatusEntry 10 }


-- Trace Rcvr/<string> X25 DataNetworkAddress
-- This component defines the calling end of the trace connection. It 
-- includes the set of attributes which apply to a Vc connection to an 
-- X.25 trace receiver.

traceRcvrX25Dna OBJECT IDENTIFIER ::= { traceRcvrX25 2 }



traceRcvrX25DnaRowStatusTable OBJECT-TYPE
   SYNTAX     SEQUENCE OF TraceRcvrX25DnaRowStatusEntry
   ACCESS     not-accessible
   STATUS     mandatory
   DESCRIPTION
     "This entry controls the addition and deletion of 
      traceRcvrX25Dna components."
::= { traceRcvrX25Dna 1 }

traceRcvrX25DnaRowStatusEntry OBJECT-TYPE
   SYNTAX     TraceRcvrX25DnaRowStatusEntry
   ACCESS     not-accessible
   STATUS     mandatory
   DESCRIPTION
     "A single entry in the table represents a single 
      traceRcvrX25Dna component."
   INDEX {
      traceIndex,
      traceRcvrIndex,
      traceRcvrX25Index,
      traceRcvrX25DnaIndex }
::= { traceRcvrX25DnaRowStatusTable 1 }

TraceRcvrX25DnaRowStatusEntry ::= SEQUENCE {
   traceRcvrX25DnaRowStatus
      RowStatus,
   traceRcvrX25DnaComponentName
      DisplayString,
   traceRcvrX25DnaStorageType
      StorageType,
   traceRcvrX25DnaIndex
      NonReplicated }

traceRcvrX25DnaRowStatus OBJECT-TYPE
   SYNTAX     RowStatus 
   ACCESS     read-only
   STATUS     mandatory
   DESCRIPTION
     "This variable is used as the basis for SNMP naming of
      traceRcvrX25Dna components.
      These components cannot be added nor deleted."
::= { traceRcvrX25DnaRowStatusEntry 1 }

traceRcvrX25DnaComponentName OBJECT-TYPE
   SYNTAX     DisplayString 
   ACCESS     read-only
   STATUS     mandatory
   DESCRIPTION
     "This variable provides the component's string name for
      use with the ASCII Console Interface"
::= { traceRcvrX25DnaRowStatusEntry 2 }

traceRcvrX25DnaStorageType OBJECT-TYPE
   SYNTAX     StorageType 
   ACCESS     read-only
   STATUS     mandatory
   DESCRIPTION
     "This variable represents the storage type value for the
      traceRcvrX25Dna tables."
::= { traceRcvrX25DnaRowStatusEntry 4 }

traceRcvrX25DnaIndex OBJECT-TYPE
   SYNTAX     NonReplicated 
   ACCESS     not-accessible
   STATUS     mandatory
   DESCRIPTION
     "This variable represents the index for the traceRcvrX25Dna tables."
::= { traceRcvrX25DnaRowStatusEntry 10 }

traceRcvrX25DnaAddressTable OBJECT-TYPE
   SYNTAX     SEQUENCE OF TraceRcvrX25DnaAddressEntry
   ACCESS     not-accessible
   STATUS     mandatory
   DESCRIPTION
     "This group contains attributes common to all Dnas. This group is 
      composed of two attributes which define a Dna. These attributes are 
      used to interpret the format of the address digits."
::= { traceRcvrX25Dna 10 }

traceRcvrX25DnaAddressEntry OBJECT-TYPE
   SYNTAX     TraceRcvrX25DnaAddressEntry
   ACCESS     not-accessible
   STATUS     mandatory
   DESCRIPTION
     "An entry in the traceRcvrX25DnaAddressTable."
   INDEX {
      traceIndex,
      traceRcvrIndex,
      traceRcvrX25Index,
      traceRcvrX25DnaIndex }
::= { traceRcvrX25DnaAddressTable 1 }

TraceRcvrX25DnaAddressEntry ::= SEQUENCE {
   traceRcvrX25DnaNumberingPlanIndicator
      INTEGER,
   traceRcvrX25DnaDataNetworkAddress
      DigitString }

traceRcvrX25DnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. The address may belong to an E.164 or X.121 
      plan."
   DEFVAL     { x121 }
::= { traceRcvrX25DnaAddressEntry 1 }

traceRcvrX25DnaDataNetworkAddress OBJECT-TYPE
   SYNTAX     DigitString (SIZE (1..15))
   ACCESS     read-write
   STATUS     mandatory
   DESCRIPTION
     "The Dna attribute contains digits which form a unique identifier for 
      the calling end of the trace connection. Dna digits are selected and 
      assigned by network operators. The maximum Dna length is 15 
      digits."
::= { traceRcvrX25DnaAddressEntry 2 }

traceRcvrX25DnaOutgoingOptionsTable OBJECT-TYPE
   SYNTAX     SEQUENCE OF TraceRcvrX25DnaOutgoingOptionsEntry
   ACCESS     not-accessible
   STATUS     mandatory
   DESCRIPTION
     "This group defines call options for outgoing calls."
::= { traceRcvrX25Dna 11 }

traceRcvrX25DnaOutgoingOptionsEntry OBJECT-TYPE
   SYNTAX     TraceRcvrX25DnaOutgoingOptionsEntry
   ACCESS     not-accessible
   STATUS     mandatory
   DESCRIPTION
     "An entry in the traceRcvrX25DnaOutgoingOptionsTable."
   INDEX {
      traceIndex,
      traceRcvrIndex,
      traceRcvrX25Index,
      traceRcvrX25DnaIndex }
::= { traceRcvrX25DnaOutgoingOptionsTable 1 }

TraceRcvrX25DnaOutgoingOptionsEntry ::= SEQUENCE {
   traceRcvrX25DnaOutCalls
      INTEGER,
   traceRcvrX25DnaOutDefaultPriority
      INTEGER,
   traceRcvrX25DnaOutIntl
      INTEGER,
   traceRcvrX25DnaOutDefaultPathSensitivity
      INTEGER,
   traceRcvrX25DnaOutDefaultPathReliability
      INTEGER,
   traceRcvrX25DnaOutPathReliabilityOverRide
      INTEGER,
   traceRcvrX25DnaOutPathReliabilitySignal
      INTEGER,
   traceRcvrX25DnaOutAccess
      INTEGER }

traceRcvrX25DnaOutCalls OBJECT-TYPE
   SYNTAX     INTEGER  {
                 disallowed(0),
                 allowed(1) }
   ACCESS     read-only
   STATUS     mandatory
   DESCRIPTION
     "This attribute specifies that outgoing calls (from the DTE to the 
      network) can be made using this particular Dna component."
   DEFVAL     { allowed }
::= { traceRcvrX25DnaOutgoingOptionsEntry 1 }

traceRcvrX25DnaOutDefaultPriority OBJECT-TYPE
   SYNTAX     INTEGER  {
                 normal(0),
                 high(1) }
   ACCESS     read-write
   STATUS     mandatory
   DESCRIPTION
     "If this attribute is set to normal, then the default priority for 
      outgoing calls (from the DTE to the network) using this particular 
      Dna is normal priority when the priority is not specified in the call. 
      If this attribute is set to high then the default priority for outgoing 
      calls using this particular Dna is high priority."
   DEFVAL     { high }
::= { traceRcvrX25DnaOutgoingOptionsEntry 7 }

traceRcvrX25DnaOutIntl OBJECT-TYPE
   SYNTAX     INTEGER  {
                 disallowed(0),
                 allowed(1) }
   ACCESS     read-only
   STATUS     mandatory
   DESCRIPTION
     "This attribute specifies that outgoing international calls (from the 
      DTE to the network) can be made using this particular Dna.
      
      This attribute also controls access to another numbering plan, and 
      specifies that cross-numbering plan calls are allowed."
   DEFVAL     { allowed }
::= { traceRcvrX25DnaOutgoingOptionsEntry 8 }

traceRcvrX25DnaOutDefaultPathSensitivity OBJECT-TYPE
   SYNTAX     INTEGER  {
                 throughput(0),
                 delay(1) }
   ACCESS     read-only
   STATUS     obsolete
   DESCRIPTION
     "This attribute specifies the default class of routing (delay/
      throughput) for all outgoing calls (from the DTE to the network) 
      using this particular Dna. The chosen default class of routing 
      applies to all outgoing calls established using this Dna, and applies 
      to the packets travelling in both directions on all outgoing calls 
      (local to remote, and remote to local).
      This attribute, if set to a value of throughput, specifies that the 
      default class of routing is throughput sensitive. If set to a value of 
      delay, then the default class of routing is delay sensitive.
      
      This attribute is obsoleted. Please refer to defaultTransferPriority 
      for the corresponding new attribute."
   DEFVAL     { throughput }
::= { traceRcvrX25DnaOutgoingOptionsEntry 11 }

traceRcvrX25DnaOutDefaultPathReliability OBJECT-TYPE
   SYNTAX     INTEGER  {
                 high(0),
                 normal(1) }
   ACCESS     read-only
   STATUS     mandatory
   DESCRIPTION
     "This attribute specifies the default reliability class of routing for all 
      calls (from the DTE to the network) using this particular Dna. The 
      chosen default reliability class of routing normally applies to all 
      packets (including the call packets) travelling into the network.
      A value of high specifies that packets are to be overflowed or 
      retransmitted at various routing levels. Typically high reliability 
      results in duplication and disordering of packets in the network, 
      when errors are detected or during link congestion. The VC handles 
      the duplication and disordering to ensure that packets are delivered 
      to the interface in the proper sequence and without duplication."
   DEFVAL     { high }
::= { traceRcvrX25DnaOutgoingOptionsEntry 14 }

traceRcvrX25DnaOutPathReliabilityOverRide OBJECT-TYPE
   SYNTAX     INTEGER  {
                 no(0),
                 yes(1) }
   ACCESS     read-only
   STATUS     mandatory
   DESCRIPTION
     "This attribute specifies that the called end of the connection will not 
      use the calling end provisioning data for reliability class of routing 
      to override the provisioning data at the called end."
   DEFVAL     { no }
::= { traceRcvrX25DnaOutgoingOptionsEntry 15 }

traceRcvrX25DnaOutPathReliabilitySignal OBJECT-TYPE
   SYNTAX     INTEGER  {
                 disallowed(0),
                 allowed(1) }
   ACCESS     read-only
   STATUS     mandatory
   DESCRIPTION
     "This attribute specifies that reliability routing signaling is not used."
   DEFVAL     { disallowed }
::= { traceRcvrX25DnaOutgoingOptionsEntry 16 }

traceRcvrX25DnaOutAccess OBJECT-TYPE
   SYNTAX     INTEGER  {
                 disallowed(0),
                 allowed(1) }
   ACCESS     read-write
   STATUS     mandatory
   DESCRIPTION
     "This attribute is an extension of the Closed User Group (CUG) 
      facility. If this attribute is set to a value of allowed, it specifies that 
      outgoing calls (from the DTE to the network) to the open (non-
      CUG) part of the network are permitted. It also permits outgoing 
      calls to interfaces that have Incoming Access capabilities. If set to a 
      value of disallowed, then such calls cannot be made using this Dna 
      (the calls will be cleared by the local DCE).
      This attribute corresponds to the ITU-T 'Closed User Group with 
      Outgoing Access' feature."
   DEFVAL     { disallowed }
::= { traceRcvrX25DnaOutgoingOptionsEntry 17 }

traceRcvrX25DnaIncomingOptionsTable OBJECT-TYPE
   SYNTAX     SEQUENCE OF TraceRcvrX25DnaIncomingOptionsEntry
   ACCESS     not-accessible
   STATUS     mandatory
   DESCRIPTION
     "This group defines the call options for incoming calls."
::= { traceRcvrX25Dna 12 }

traceRcvrX25DnaIncomingOptionsEntry OBJECT-TYPE
   SYNTAX     TraceRcvrX25DnaIncomingOptionsEntry
   ACCESS     not-accessible
   STATUS     mandatory
   DESCRIPTION
     "An entry in the traceRcvrX25DnaIncomingOptionsTable."
   INDEX {
      traceIndex,
      traceRcvrIndex,
      traceRcvrX25Index,
      traceRcvrX25DnaIndex }
::= { traceRcvrX25DnaIncomingOptionsTable 1 }

TraceRcvrX25DnaIncomingOptionsEntry ::= SEQUENCE {
   traceRcvrX25DnaIncCalls
      INTEGER }

traceRcvrX25DnaIncCalls OBJECT-TYPE
   SYNTAX     INTEGER  {
                 disallowed(0),
                 allowed(1) }
   ACCESS     read-only
   STATUS     mandatory
   DESCRIPTION
     "This attribute specifies that incoming calls (from the network to the 
      DTE) cannot be made to this Dna."
   DEFVAL     { disallowed }
::= { traceRcvrX25DnaIncomingOptionsEntry 1 }

traceRcvrX25DnaCallOptionsTable OBJECT-TYPE
   SYNTAX     SEQUENCE OF TraceRcvrX25DnaCallOptionsEntry
   ACCESS     not-accessible
   STATUS     mandatory
   DESCRIPTION
     "The CallOptions group defines additional options for calls which 
      are not specific to the direction of the call."
::= { traceRcvrX25Dna 13 }

traceRcvrX25DnaCallOptionsEntry OBJECT-TYPE
   SYNTAX     TraceRcvrX25DnaCallOptionsEntry
   ACCESS     not-accessible
   STATUS     mandatory
   DESCRIPTION
     "An entry in the traceRcvrX25DnaCallOptionsTable."
   INDEX {
      traceIndex,
      traceRcvrIndex,
      traceRcvrX25Index,
      traceRcvrX25DnaIndex }
::= { traceRcvrX25DnaCallOptionsTable 1 }

TraceRcvrX25DnaCallOptionsEntry ::= SEQUENCE {
   traceRcvrX25DnaPacketSizes
      OCTET STRING,
   traceRcvrX25DnaDefaultRecvFrmNetworkPacketSize
      INTEGER,
   traceRcvrX25DnaDefaultSendToNetworkPacketSize
      INTEGER,
   traceRcvrX25DnaDefaultRecvFrmNetworkThruputClass
      Unsigned32,
   traceRcvrX25DnaDefaultSendToNetworkThruputClass
      Unsigned32,
   traceRcvrX25DnaDefaultRecvFrmNetworkWindowSize
      Unsigned32,
   traceRcvrX25DnaDefaultSendToNetworkWindowSize
      Unsigned32,
   traceRcvrX25DnaPacketSizeNegotiation
      INTEGER,
   traceRcvrX25DnaCugFormat
      INTEGER }

traceRcvrX25DnaPacketSizes OBJECT-TYPE
   SYNTAX     OCTET STRING (SIZE (2))
   ACCESS     read-only
   STATUS     mandatory
   DESCRIPTION
     "This attribute specifies the allowable packet sizes supported for calls 
      using this Dna.

      Description of bits:
      n16(0)
      n32(1)
      n64(2)
      n128(3)
      n256(4)
      n512(5)
      n1024(6)
      n2048(7)
      n4096(8)"
   DEFVAL     { '0100'H }
::= { traceRcvrX25DnaCallOptionsEntry 2 }

traceRcvrX25DnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local receive packet size from 
      network to DTE for calls using this particular Dna."
   DEFVAL     { n2048 }
::= { traceRcvrX25DnaCallOptionsEntry 3 }

traceRcvrX25DnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local send packet size from DTE 
      to network for all calls using this particular Dna."
   DEFVAL     { n2048 }
::= { traceRcvrX25DnaCallOptionsEntry 4 }

traceRcvrX25DnaDefaultRecvFrmNetworkThruputClass OBJECT-TYPE
   SYNTAX     Unsigned32 (0..15)
   ACCESS     read-write
   STATUS     mandatory
   DESCRIPTION
     "This attribute specifies the default receive throughput class, 
      (towards the interface) for all calls using this particular Dna."
   DEFVAL     { 10 }
::= { traceRcvrX25DnaCallOptionsEntry 5 }

traceRcvrX25DnaDefaultSendToNetworkThruputClass OBJECT-TYPE
   SYNTAX     Unsigned32 (0..15)
   ACCESS     read-write
   STATUS     mandatory
   DESCRIPTION
     "This attribute specifies the default send throughput class (towards 
      the network) for all calls using this particular Dna."
   DEFVAL     { 10 }
::= { traceRcvrX25DnaCallOptionsEntry 6 }

traceRcvrX25DnaDefaultRecvFrmNetworkWindowSize OBJECT-TYPE
   SYNTAX     Unsigned32 (1..7)
   ACCESS     read-only
   STATUS     mandatory
   DESCRIPTION
     "This attribute specifies the default value for the number of data 
      packets that can be send to the interface before any 
      acknowledgment."
   DEFVAL     { 1 }
::= { traceRcvrX25DnaCallOptionsEntry 7 }

traceRcvrX25DnaDefaultSendToNetworkWindowSize OBJECT-TYPE
   SYNTAX     Unsigned32 (1..7)
   ACCESS     read-only
   STATUS     mandatory
   DESCRIPTION
     "This attribute specifies the default value for the number of data 
      packets that can be received from the interface before any 
      acknowledgment."
   DEFVAL     { 1 }
::= { traceRcvrX25DnaCallOptionsEntry 8 }

traceRcvrX25DnaPacketSizeNegotiation OBJECT-TYPE
   SYNTAX     INTEGER  {
                 endToEnd(0),
                 local(1) }
   ACCESS     read-only
   STATUS     mandatory
   DESCRIPTION
     "This attribute, if set to local specifies that packet sizes can be 
      negotiated locally at the interface irrespective of the setting at the 
      remote interface. If set to endtoEnd, then the packet size 
      negotiation is between the local and remote interface (i.e. packet 
      sizes are the same on both interfaces)."
   DEFVAL     { local }
::= { traceRcvrX25DnaCallOptionsEntry 9 }

traceRcvrX25DnaCugFormat OBJECT-TYPE
   SYNTAX     INTEGER  {
                 basic(0),
                 extended(1) }
   ACCESS     read-only
   STATUS     mandatory
   DESCRIPTION
     "This attribute specifies the format to signal CUG indices as basic or 
      extended. A basic CUG index format is two digits long. An 
      extended CUG index format is four digits long."
   DEFVAL     { basic }
::= { traceRcvrX25DnaCallOptionsEntry 10 }


-- Trace Rcvr/<string> X25 Dna ClosedUserGroup
-- The ClosedUserGroup component defines options associated with a 
-- national or international closed user group identifier. When a Dna is 
-- defined with a Cug, calls to other Dnas which do not have the same 
-- Cug interlockCode defined are refused. When a Dna is not defined 
-- with a Cug, calls to other Dnas which have any Cug interlockCode 
-- defined are refused. The Dna attributes outAccess and incAccess 
-- can override these rules.
-- If this component is present, the X.25 interface which connects to 
-- the X.25 trace receiver must be provisioned with the same Cug 
-- interlockCode.

traceRcvrX25DnaCug OBJECT IDENTIFIER ::= { traceRcvrX25Dna 2 }



traceRcvrX25DnaCugRowStatusTable OBJECT-TYPE
   SYNTAX     SEQUENCE OF TraceRcvrX25DnaCugRowStatusEntry
   ACCESS     not-accessible
   STATUS     mandatory
   DESCRIPTION
     "This entry controls the addition and deletion of 
      traceRcvrX25DnaCug components."
::= { traceRcvrX25DnaCug 1 }

traceRcvrX25DnaCugRowStatusEntry OBJECT-TYPE
   SYNTAX     TraceRcvrX25DnaCugRowStatusEntry
   ACCESS     not-accessible
   STATUS     mandatory
   DESCRIPTION
     "A single entry in the table represents a single 
      traceRcvrX25DnaCug component."
   INDEX {
      traceIndex,
      traceRcvrIndex,
      traceRcvrX25Index,
      traceRcvrX25DnaIndex,
      traceRcvrX25DnaCugIndex }
::= { traceRcvrX25DnaCugRowStatusTable 1 }

TraceRcvrX25DnaCugRowStatusEntry ::= SEQUENCE {
   traceRcvrX25DnaCugRowStatus
      RowStatus,
   traceRcvrX25DnaCugComponentName
      DisplayString,
   traceRcvrX25DnaCugStorageType
      StorageType,
   traceRcvrX25DnaCugIndex
      Integer32 }

traceRcvrX25DnaCugRowStatus OBJECT-TYPE
   SYNTAX     RowStatus 
   ACCESS     read-write
   STATUS     mandatory
   DESCRIPTION
     "This variable is used as the basis for SNMP naming of
      traceRcvrX25DnaCug components.
      These components can be added and deleted."
::= { traceRcvrX25DnaCugRowStatusEntry 1 }

traceRcvrX25DnaCugComponentName OBJECT-TYPE
   SYNTAX     DisplayString 
   ACCESS     read-only
   STATUS     mandatory
   DESCRIPTION
     "This variable provides the component's string name for
      use with the ASCII Console Interface"
::= { traceRcvrX25DnaCugRowStatusEntry 2 }

traceRcvrX25DnaCugStorageType OBJECT-TYPE
   SYNTAX     StorageType 
   ACCESS     read-only
   STATUS     mandatory
   DESCRIPTION
     "This variable represents the storage type value for the
      traceRcvrX25DnaCug tables."
::= { traceRcvrX25DnaCugRowStatusEntry 4 }

traceRcvrX25DnaCugIndex OBJECT-TYPE
   SYNTAX     Integer32 (1..1)
   ACCESS     not-accessible
   STATUS     mandatory
   DESCRIPTION
     "This variable represents the index for the traceRcvrX25DnaCug tables."
::= { traceRcvrX25DnaCugRowStatusEntry 10 }

traceRcvrX25DnaCugCugOptionsTable OBJECT-TYPE
   SYNTAX     SEQUENCE OF TraceRcvrX25DnaCugCugOptionsEntry
   ACCESS     not-accessible
   STATUS     mandatory
   DESCRIPTION
     "Attributes in this group define ClosedUserGroup options associated 
      with interlockCode. Dnas with the same CUG (interlockCode) can 
      make calls within this group. Various combinations of attributes are 
      defined under this option which permit or prevent calls in the same 
      CUG group."
::= { traceRcvrX25DnaCug 10 }

traceRcvrX25DnaCugCugOptionsEntry OBJECT-TYPE
   SYNTAX     TraceRcvrX25DnaCugCugOptionsEntry
   ACCESS     not-accessible
   STATUS     mandatory
   DESCRIPTION
     "An entry in the traceRcvrX25DnaCugCugOptionsTable."
   INDEX {
      traceIndex,
      traceRcvrIndex,
      traceRcvrX25Index,
      traceRcvrX25DnaIndex,
      traceRcvrX25DnaCugIndex }
::= { traceRcvrX25DnaCugCugOptionsTable 1 }

TraceRcvrX25DnaCugCugOptionsEntry ::= SEQUENCE {
   traceRcvrX25DnaCugType
      INTEGER,
   traceRcvrX25DnaCugDnic
      DigitString,
   traceRcvrX25DnaCugInterlockCode
      Unsigned32,
   traceRcvrX25DnaCugPreferential
      INTEGER,
   traceRcvrX25DnaCugOutCalls
      INTEGER,
   traceRcvrX25DnaCugIncCalls
      INTEGER,
   traceRcvrX25DnaCugPrivileged
      INTEGER }

traceRcvrX25DnaCugType OBJECT-TYPE
   SYNTAX     INTEGER  {
                 national(0),
                 international(1) }
   ACCESS     read-write
   STATUS     mandatory
   DESCRIPTION
     "This attribute specifies the CUG type as either national or 
      international. A national CUG has significance within the local 
      network only. An international CUG has significance across 
      network boundaries."
   DEFVAL     { national }
::= { traceRcvrX25DnaCugCugOptionsEntry 1 }

traceRcvrX25DnaCugDnic OBJECT-TYPE
   SYNTAX     DigitString (SIZE (4))
   ACCESS     read-write
   STATUS     mandatory
   DESCRIPTION
     "This attribute specifies the Data Network ID Code of the network 
      that is administering the international CUG. This attribute is not 
      used for a national CUG and should be left at its default value.
      The dnic value is not an arbitrary number. It is assigned by 
      international agreement and controlled by ITU-T."
   DEFVAL     { '30303030'H }  -- "0000"
::= { traceRcvrX25DnaCugCugOptionsEntry 2 }

traceRcvrX25DnaCugInterlockCode OBJECT-TYPE
   SYNTAX     Unsigned32 (0..65535)
   ACCESS     read-write
   STATUS     mandatory
   DESCRIPTION
     "This attribute specifies a numeric identifier of a national or 
      international closed user group. It is an arbitrary number. This 
      attribute may also be called CUG in some descriptions. Dnas 
      defined with this number can only make calls to Dnas defined with 
      the same interlockCode."
   DEFVAL     { 0 }
::= { traceRcvrX25DnaCugCugOptionsEntry 3 }

traceRcvrX25DnaCugPreferential OBJECT-TYPE
   SYNTAX     INTEGER  {
                 no(0),
                 yes(1) }
   ACCESS     read-only
   STATUS     mandatory
   DESCRIPTION
     "This attribute specifies that this Cug is to be used on all outgoing 
      calls to the X.25 trace receiver."
   DEFVAL     { yes }
::= { traceRcvrX25DnaCugCugOptionsEntry 4 }

traceRcvrX25DnaCugOutCalls OBJECT-TYPE
   SYNTAX     INTEGER  {
                 disallowed(0),
                 allowed(1) }
   ACCESS     read-only
   STATUS     mandatory
   DESCRIPTION
     "This attribute specifies that outgoing calls (from the DTE into the 
      network) can be made using this particular Cug."
   DEFVAL     { allowed }
::= { traceRcvrX25DnaCugCugOptionsEntry 5 }

traceRcvrX25DnaCugIncCalls OBJECT-TYPE
   SYNTAX     INTEGER  {
                 disallowed(0),
                 allowed(1) }
   ACCESS     read-only
   STATUS     mandatory
   DESCRIPTION
     "This attribute specifies that incoming calls (from the network to the 
      DTE) cannot be accepted using this Cug."
   DEFVAL     { disallowed }
::= { traceRcvrX25DnaCugCugOptionsEntry 6 }

traceRcvrX25DnaCugPrivileged OBJECT-TYPE
   SYNTAX     INTEGER  {
                 no(0),
                 yes(1) }
   ACCESS     read-write
   STATUS     mandatory
   DESCRIPTION
     "This attribute specifies that this Cug is privileged. For a call 
      between two closed user group Dnas to connect, at least one Dna 
      must have a privileged Cug."
   DEFVAL     { yes }
::= { traceRcvrX25DnaCugCugOptionsEntry 7 }


-- Trace Rcvr/<string> X25 DirectCall
-- This component defines direct call options for the call to the X.25 
-- trace receiver. The connection is initiated on receipt of a Start 
-- FrUni/n Trace command.

traceRcvrX25Dc OBJECT IDENTIFIER ::= { traceRcvrX25 3 }



traceRcvrX25DcRowStatusTable OBJECT-TYPE
   SYNTAX     SEQUENCE OF TraceRcvrX25DcRowStatusEntry
   ACCESS     not-accessible
   STATUS     mandatory
   DESCRIPTION
     "This entry controls the addition and deletion of 
      traceRcvrX25Dc components."
::= { traceRcvrX25Dc 1 }

traceRcvrX25DcRowStatusEntry OBJECT-TYPE
   SYNTAX     TraceRcvrX25DcRowStatusEntry
   ACCESS     not-accessible
   STATUS     mandatory
   DESCRIPTION
     "A single entry in the table represents a single 
      traceRcvrX25Dc component."
   INDEX {
      traceIndex,
      traceRcvrIndex,
      traceRcvrX25Index,
      traceRcvrX25DcIndex }
::= { traceRcvrX25DcRowStatusTable 1 }

TraceRcvrX25DcRowStatusEntry ::= SEQUENCE {
   traceRcvrX25DcRowStatus
      RowStatus,
   traceRcvrX25DcComponentName
      DisplayString,
   traceRcvrX25DcStorageType
      StorageType,
   traceRcvrX25DcIndex
      NonReplicated }

traceRcvrX25DcRowStatus OBJECT-TYPE
   SYNTAX     RowStatus 
   ACCESS     read-only
   STATUS     mandatory
   DESCRIPTION
     "This variable is used as the basis for SNMP naming of
      traceRcvrX25Dc components.
      These components cannot be added nor deleted."
::= { traceRcvrX25DcRowStatusEntry 1 }

traceRcvrX25DcComponentName OBJECT-TYPE
   SYNTAX     DisplayString 
   ACCESS     read-only
   STATUS     mandatory
   DESCRIPTION
     "This variable provides the component's string name for
      use with the ASCII Console Interface"
::= { traceRcvrX25DcRowStatusEntry 2 }

traceRcvrX25DcStorageType OBJECT-TYPE
   SYNTAX     StorageType 
   ACCESS     read-only
   STATUS     mandatory
   DESCRIPTION
     "This variable represents the storage type value for the
      traceRcvrX25Dc tables."
::= { traceRcvrX25DcRowStatusEntry 4 }

traceRcvrX25DcIndex OBJECT-TYPE
   SYNTAX     NonReplicated 
   ACCESS     not-accessible
   STATUS     mandatory
   DESCRIPTION
     "This variable represents the index for the traceRcvrX25Dc tables."
::= { traceRcvrX25DcRowStatusEntry 10 }

traceRcvrX25DcOptionsTable OBJECT-TYPE
   SYNTAX     SEQUENCE OF TraceRcvrX25DcOptionsEntry
   ACCESS     not-accessible
   STATUS     mandatory
   DESCRIPTION
     "The Options group defines attributes associated with the SVC direct 
      call."
::= { traceRcvrX25Dc 10 }

traceRcvrX25DcOptionsEntry OBJECT-TYPE
   SYNTAX     TraceRcvrX25DcOptionsEntry
   ACCESS     not-accessible
   STATUS     mandatory
   DESCRIPTION
     "An entry in the traceRcvrX25DcOptionsTable."
   INDEX {
      traceIndex,
      traceRcvrIndex,
      traceRcvrX25Index,
      traceRcvrX25DcIndex }
::= { traceRcvrX25DcOptionsTable 1 }

TraceRcvrX25DcOptionsEntry ::= SEQUENCE {
   traceRcvrX25DcRemoteNpi
      INTEGER,
   traceRcvrX25DcRemoteDna
      DigitString,
   traceRcvrX25DcType
      INTEGER,
   traceRcvrX25DcUserData
      HexString }

traceRcvrX25DcRemoteNpi OBJECT-TYPE
   SYNTAX     INTEGER  {
                 x121(0),
                 e164(1) }
   ACCESS     read-write
   STATUS     mandatory
   DESCRIPTION
     "This attribute indicates the numbering plan used for the remoteDna."
   DEFVAL     { x121 }
::= { traceRcvrX25DcOptionsEntry 3 }

traceRcvrX25DcRemoteDna OBJECT-TYPE
   SYNTAX     DigitString (SIZE (1..15))
   ACCESS     read-write
   STATUS     mandatory
   DESCRIPTION
     "This attribute specifies the Data Network Address of the remote end 
      of the connection. This is the DNA of the X.25 trace receiver which 
      will receive the trace data."
::= { traceRcvrX25DcOptionsEntry 4 }

traceRcvrX25DcType OBJECT-TYPE
   SYNTAX     INTEGER  {
                 switched(0),
                 permanentMaster(1),
                 permanentSlave(2),
                 permanentBackupSlave(3) }
   ACCESS     read-only
   STATUS     mandatory
   DESCRIPTION
     "This attribute specifies the type of call as switched. For a switched 
      call, no information is defined at the remote end about the local end 
      of the connection."
   DEFVAL     { switched }
::= { traceRcvrX25DcOptionsEntry 6 }

traceRcvrX25DcUserData OBJECT-TYPE
   SYNTAX     HexString (SIZE (0..16))
   ACCESS     read-write
   STATUS     mandatory
   DESCRIPTION
     "This attribute contains the user data. It is a 0 to 16 byte length string 
      which is appended to the call request packet that is presented to the 
      called (destination) DTE."
   DEFVAL     { ''H }  -- ""
::= { traceRcvrX25DcOptionsEntry 8 }

-- 
-- *** THIS SUBTREE CURRENTLY NOT IMPLEMENTED ***
-- 

-- Trace Session/<n> X25
-- This component identifies the access method used by the receiver of 
-- the trace data as X.25.

traceSessionX25 OBJECT IDENTIFIER ::= { traceSession 2 }



traceSessionX25RowStatusTable OBJECT-TYPE
   SYNTAX     SEQUENCE OF TraceSessionX25RowStatusEntry
   ACCESS     not-accessible
   STATUS     mandatory
   DESCRIPTION
     "*** THIS TABLE CURRENTLY NOT IMPLEMENTED ***

      This entry controls the addition and deletion of 
      traceSessionX25 components."
::= { traceSessionX25 1 }

traceSessionX25RowStatusEntry OBJECT-TYPE
   SYNTAX     TraceSessionX25RowStatusEntry
   ACCESS     not-accessible
   STATUS     mandatory
   DESCRIPTION
     "A single entry in the table represents a single 
      traceSessionX25 component."
   INDEX {
      traceIndex,
      traceSessionIndex,
      traceSessionX25Index }
::= { traceSessionX25RowStatusTable 1 }

TraceSessionX25RowStatusEntry ::= SEQUENCE {
   traceSessionX25RowStatus
      RowStatus,
   traceSessionX25ComponentName
      DisplayString,
   traceSessionX25StorageType
      StorageType,
   traceSessionX25Index
      NonReplicated }

traceSessionX25RowStatus OBJECT-TYPE
   SYNTAX     RowStatus 
   ACCESS     read-only
   STATUS     mandatory
   DESCRIPTION
     "This variable is used as the basis for SNMP naming of
      traceSessionX25 components.
      These components cannot be added nor deleted."
::= { traceSessionX25RowStatusEntry 1 }

traceSessionX25ComponentName OBJECT-TYPE
   SYNTAX     DisplayString 
   ACCESS     read-only
   STATUS     mandatory
   DESCRIPTION
     "This variable provides the component's string name for
      use with the ASCII Console Interface"
::= { traceSessionX25RowStatusEntry 2 }

traceSessionX25StorageType OBJECT-TYPE
   SYNTAX     StorageType 
   ACCESS     read-only
   STATUS     mandatory
   DESCRIPTION
     "This variable represents the storage type value for the
      traceSessionX25 tables."
::= { traceSessionX25RowStatusEntry 4 }

traceSessionX25Index OBJECT-TYPE
   SYNTAX     NonReplicated 
   ACCESS     not-accessible
   STATUS     mandatory
   DESCRIPTION
     "This variable represents the index for the traceSessionX25 tables."
::= { traceSessionX25RowStatusEntry 10 }

-- 
-- *** THIS SUBTREE CURRENTLY NOT IMPLEMENTED ***
-- 

-- ... Vc()
-- This component defines display of general Vc dynamic attributes

traceSessionX25Vc OBJECT IDENTIFIER ::= { traceSessionX25 2 }



traceSessionX25VcRowStatusTable OBJECT-TYPE
   SYNTAX     SEQUENCE OF TraceSessionX25VcRowStatusEntry
   ACCESS     not-accessible
   STATUS     mandatory
   DESCRIPTION
     "*** THIS TABLE CURRENTLY NOT IMPLEMENTED ***

      This entry controls the addition and deletion of 
      traceSessionX25Vc components."
::= { traceSessionX25Vc 1 }

traceSessionX25VcRowStatusEntry OBJECT-TYPE
   SYNTAX     TraceSessionX25VcRowStatusEntry
   ACCESS     not-accessible
   STATUS     mandatory
   DESCRIPTION
     "A single entry in the table represents a single 
      traceSessionX25Vc component."
   INDEX {
      traceIndex,
      traceSessionIndex,
      traceSessionX25Index,
      traceSessionX25VcIndex }
::= { traceSessionX25VcRowStatusTable 1 }

TraceSessionX25VcRowStatusEntry ::= SEQUENCE {
   traceSessionX25VcRowStatus
      RowStatus,
   traceSessionX25VcComponentName
      DisplayString,
   traceSessionX25VcStorageType
      StorageType,
   traceSessionX25VcIndex
      NonReplicated }

traceSessionX25VcRowStatus OBJECT-TYPE
   SYNTAX     RowStatus 
   ACCESS     read-only
   STATUS     mandatory
   DESCRIPTION
     "This variable is used as the basis for SNMP naming of
      traceSessionX25Vc components.
      These components cannot be added nor deleted."
::= { traceSessionX25VcRowStatusEntry 1 }

traceSessionX25VcComponentName OBJECT-TYPE
   SYNTAX     DisplayString 
   ACCESS     read-only
   STATUS     mandatory
   DESCRIPTION
     "This variable provides the component's string name for
      use with the ASCII Console Interface"
::= { traceSessionX25VcRowStatusEntry 2 }

traceSessionX25VcStorageType OBJECT-TYPE
   SYNTAX     StorageType 
   ACCESS     read-only
   STATUS     mandatory
   DESCRIPTION
     "This variable represents the storage type value for the
      traceSessionX25Vc tables."
::= { traceSessionX25VcRowStatusEntry 4 }

traceSessionX25VcIndex OBJECT-TYPE
   SYNTAX     NonReplicated 
   ACCESS     not-accessible
   STATUS     mandatory
   DESCRIPTION
     "This variable represents the index for the traceSessionX25Vc tables."
::= { traceSessionX25VcRowStatusEntry 10 }

traceSessionX25VcCadTable OBJECT-TYPE
   SYNTAX     SEQUENCE OF TraceSessionX25VcCadEntry
   ACCESS     not-accessible
   STATUS     mandatory
   DESCRIPTION
     "*** THIS TABLE CURRENTLY NOT IMPLEMENTED ***

      This group represents operational call data related to General Vc. It 
      can be displayed only for General Vc which is created by 
      application."
::= { traceSessionX25Vc 10 }

traceSessionX25VcCadEntry OBJECT-TYPE
   SYNTAX     TraceSessionX25VcCadEntry
   ACCESS     not-accessible
   STATUS     mandatory
   DESCRIPTION
     "An entry in the traceSessionX25VcCadTable."
   INDEX {
      traceIndex,
      traceSessionIndex,
      traceSessionX25Index,
      traceSessionX25VcIndex }
::= { traceSessionX25VcCadTable 1 }

TraceSessionX25VcCadEntry ::= SEQUENCE {
   traceSessionX25VcType
      INTEGER,
   traceSessionX25VcState
      INTEGER,
   traceSessionX25VcPreviousState
      INTEGER,
   traceSessionX25VcDiagnosticCode
      Unsigned32,
   traceSessionX25VcPreviousDiagnosticCode
      Unsigned32,
   traceSessionX25VcCalledNpi
      INTEGER,
   traceSessionX25VcCalledDna
      DigitString,
   traceSessionX25VcCalledLcn
      Unsigned32,
   traceSessionX25VcCallingNpi
      INTEGER,
   traceSessionX25VcCallingDna
      DigitString,
   traceSessionX25VcCallingLcn
      Unsigned32,
   traceSessionX25VcAccountingEnabled
      INTEGER,
   traceSessionX25VcFastSelectCall
      INTEGER,
   traceSessionX25VcLocalRxPktSize
      INTEGER,
   traceSessionX25VcLocalTxPktSize
      INTEGER,
   traceSessionX25VcLocalTxWindowSize
      Unsigned32,
   traceSessionX25VcLocalRxWindowSize
      Unsigned32,
   traceSessionX25VcPathReliability
      INTEGER,
   traceSessionX25VcAccountingEnd
      INTEGER,
   traceSessionX25VcPriority
      INTEGER,
   traceSessionX25VcSegmentSize
      Unsigned32,
   traceSessionX25VcSubnetTxPktSize
      INTEGER,
   traceSessionX25VcSubnetTxWindowSize
      Unsigned32,
   traceSessionX25VcSubnetRxPktSize
      INTEGER,
   traceSessionX25VcSubnetRxWindowSize
      Unsigned32,
   traceSessionX25VcMaxSubnetPktSize
      Unsigned32,
   traceSessionX25VcTransferPriorityToNetwork
      INTEGER,
   traceSessionX25VcTransferPriorityFromNetwork
      INTEGER }

traceSessionX25VcType OBJECT-TYPE
   SYNTAX     INTEGER  {
                 svc(0),
                 pvc(1) }
   ACCESS     read-only
   STATUS     mandatory
   DESCRIPTION
     "This attribute displays the type of call, pvc or svc. type is provided 
      at provisioning time."
::= { traceSessionX25VcCadEntry 1 }

traceSessionX25VcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { traceSessionX25VcCadEntry 2 }

traceSessionX25VcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { traceSessionX25VcCadEntry 3 }

traceSessionX25VcDiagnosticCode OBJECT-TYPE
   SYNTAX     Unsigned32 (0..255)
   ACCESS     read-only
   STATUS     mandatory
   DESCRIPTION
     "This attribute displays the internal substate of call control. It is used 
      to further refine state of call processing."
::= { traceSessionX25VcCadEntry 4 }

traceSessionX25VcPreviousDiagnosticCode OBJECT-TYPE
   SYNTAX     Unsigned32 (0..255)
   ACCESS     read-only
   STATUS     mandatory
   DESCRIPTION
     "This attribute displays the internal substate of call control. It is used 
      to further refine state of call processing."
::= { traceSessionX25VcCadEntry 5 }

traceSessionX25VcCalledNpi OBJECT-TYPE
   SYNTAX     INTEGER  {
                 x121(0),
                 e164(1) }
   ACCESS     read-only
   STATUS     mandatory
   DESCRIPTION
     "This attribute displays the Numbering Plan Indicator (NPI) of the 
      called end."
::= { traceSessionX25VcCadEntry 6 }

traceSessionX25VcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { traceSessionX25VcCadEntry 7 }

traceSessionX25VcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { traceSessionX25VcCadEntry 8 }

traceSessionX25VcCallingNpi OBJECT-TYPE
   SYNTAX     INTEGER  {
                 x121(0),
                 e164(1) }
   ACCESS     read-only
   STATUS     mandatory
   DESCRIPTION
     "This attribute displays the Numbering Plan Indicator (NPI) of the 
      calling end."
::= { traceSessionX25VcCadEntry 9 }

traceSessionX25VcCallingDna OBJECT-TYPE
   SYNTAX     DigitString (SIZE (1..15))
   ACCESS     read-only
   STATUS     mandatory
   DESCRIPTION
     "This attribute displays the Data Network Address (Dna) of the 
      calling end."
::= { traceSessionX25VcCadEntry 10 }

traceSessionX25VcCallingLcn OBJECT-TYPE
   SYNTAX     Unsigned32 (1..65535)
   ACCESS     read-only
   STATUS     mandatory
   DESCRIPTION
     "This attribute displays the Logical Channel Number of the calling 
      end."
::= { traceSessionX25VcCadEntry 11 }

traceSessionX25VcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { traceSessionX25VcCadEntry 12 }

traceSessionX25VcFastSelectCall OBJECT-TYPE
   SYNTAX     INTEGER  {
                 no(0),
                 yes(1) }
   ACCESS     read-only
   STATUS     mandatory
   DESCRIPTION
     "This attribute displays that this is a fast select call."
::= { traceSessionX25VcCadEntry 13 }

traceSessionX25VcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { traceSessionX25VcCadEntry 14 }

traceSessionX25VcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { traceSessionX25VcCadEntry 15 }

traceSessionX25VcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { traceSessionX25VcCadEntry 16 }

traceSessionX25VcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { traceSessionX25VcCadEntry 17 }

traceSessionX25VcPathReliability OBJECT-TYPE
   SYNTAX     INTEGER  {
                 high(0),
                 normal(1) }
   ACCESS     read-only
   STATUS     mandatory
   DESCRIPTION
     "This attribute displays the path reliability."
::= { traceSessionX25VcCadEntry 19 }

traceSessionX25VcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { traceSessionX25VcCadEntry 20 }

traceSessionX25VcPriority OBJECT-TYPE
   SYNTAX     INTEGER  {
                 normal(0),
                 high(1) }
   ACCESS     read-only
   STATUS     mandatory
   DESCRIPTION
     "This attribute displays whether the call is a normal or a high 
      priority call."
::= { traceSessionX25VcCadEntry 21 }

traceSessionX25VcSegmentSize OBJECT-TYPE
   SYNTAX     Unsigned32 (0..4096)
   ACCESS     read-only
   STATUS     mandatory
   DESCRIPTION
     "This attribute displays the segment size (in bytes) used on the call. 
      It is used to calculate the number of segments transmitted and 
      received."
::= { traceSessionX25VcCadEntry 22 }

traceSessionX25VcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { traceSessionX25VcCadEntry 23 }

traceSessionX25VcSubnetTxWindowSize OBJECT-TYPE
   SYNTAX     Unsigned32 (0..4096)
   ACCESS     read-only
   STATUS     mandatory
   DESCRIPTION
     "This attribute displays the current send window size of Vc."
::= { traceSessionX25VcCadEntry 24 }

traceSessionX25VcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { traceSessionX25VcCadEntry 25 }

traceSessionX25VcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { traceSessionX25VcCadEntry 26 }

traceSessionX25VcMaxSubnetPktSize OBJECT-TYPE
   SYNTAX     Unsigned32 (0..4096)
   ACCESS     read-only
   STATUS     mandatory
   DESCRIPTION
     "This attribute displays the maximum packet size allowed on Vc."
::= { traceSessionX25VcCadEntry 27 }

traceSessionX25VcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { traceSessionX25VcCadEntry 28 }

traceSessionX25VcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { traceSessionX25VcCadEntry 29 }

traceSessionX25VcIntdTable OBJECT-TYPE
   SYNTAX     SEQUENCE OF TraceSessionX25VcIntdEntry
   ACCESS     not-accessible
   STATUS     mandatory
   DESCRIPTION
     "*** THIS TABLE CURRENTLY NOT IMPLEMENTED ***

      This group defines display of interval data collected by Vc. Data in 
      this group is variable and may depend on time when this display 
      command is issued."
::= { traceSessionX25Vc 11 }

traceSessionX25VcIntdEntry OBJECT-TYPE
   SYNTAX     TraceSessionX25VcIntdEntry
   ACCESS     not-accessible
   STATUS     mandatory
   DESCRIPTION
     "An entry in the traceSessionX25VcIntdTable."
   INDEX {
      traceIndex,
      traceSessionIndex,
      traceSessionX25Index,
      traceSessionX25VcIndex }
::= { traceSessionX25VcIntdTable 1 }

TraceSessionX25VcIntdEntry ::= SEQUENCE {
   traceSessionX25VcCallReferenceNumber
      Hex,
   traceSessionX25VcElapsedTimeTillNow
      Unsigned32,
   traceSessionX25VcSegmentsRx
      Unsigned32,
   traceSessionX25VcSegmentsSent
      Unsigned32,
   traceSessionX25VcStartTime
      EnterpriseDateAndTime }

traceSessionX25VcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { traceSessionX25VcIntdEntry 1 }

traceSessionX25VcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { traceSessionX25VcIntdEntry 2 }

traceSessionX25VcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { traceSessionX25VcIntdEntry 3 }

traceSessionX25VcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { traceSessionX25VcIntdEntry 4 }

traceSessionX25VcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { traceSessionX25VcIntdEntry 5 }

traceSessionX25VcStatsTable OBJECT-TYPE
   SYNTAX     SEQUENCE OF TraceSessionX25VcStatsEntry
   ACCESS     not-accessible
   STATUS     mandatory
   DESCRIPTION
     "*** THIS TABLE CURRENTLY NOT IMPLEMENTED ***

      ... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { traceSessionX25Vc 12 }

traceSessionX25VcStatsEntry OBJECT-TYPE
   SYNTAX     TraceSessionX25VcStatsEntry
   ACCESS     not-accessible
   STATUS     mandatory
   DESCRIPTION
     "An entry in the traceSessionX25VcStatsTable."
   INDEX {
      traceIndex,
      traceSessionIndex,
      traceSessionX25Index,
      traceSessionX25VcIndex }
::= { traceSessionX25VcStatsTable 1 }

TraceSessionX25VcStatsEntry ::= SEQUENCE {
   traceSessionX25VcAckStackingTimeouts
      Unsigned32,
   traceSessionX25VcOutOfRangeFrmFromSubnet
      Unsigned32,
   traceSessionX25VcDuplicatesFromSubnet
      Unsigned32,
   traceSessionX25VcFrmRetryTimeouts
      Unsigned32,
   traceSessionX25VcPeakRetryQueueSize
      Unsigned32,
   traceSessionX25VcPeakOoSeqQueueSize
      Unsigned32,
   traceSessionX25VcPeakOoSeqFrmForwarded
      Unsigned32,
   traceSessionX25VcPeakStackedAcksRx
      Unsigned32,
   traceSessionX25VcSubnetRecoveries
      Unsigned32,
   traceSessionX25VcWindowClosuresToSubnet
      Unsigned32,
   traceSessionX25VcWindowClosuresFromSubnet
      Unsigned32,
   traceSessionX25VcWrTriggers
      Unsigned32 }

traceSessionX25VcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { traceSessionX25VcStatsEntry 1 }

traceSessionX25VcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { traceSessionX25VcStatsEntry 2 }

traceSessionX25VcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { traceSessionX25VcStatsEntry 3 }

traceSessionX25VcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { traceSessionX25VcStatsEntry 4 }

traceSessionX25VcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { traceSessionX25VcStatsEntry 5 }

traceSessionX25VcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { traceSessionX25VcStatsEntry 6 }

traceSessionX25VcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { traceSessionX25VcStatsEntry 7 }

traceSessionX25VcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { traceSessionX25VcStatsEntry 8 }

traceSessionX25VcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { traceSessionX25VcStatsEntry 9 }

traceSessionX25VcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { traceSessionX25VcStatsEntry 10 }

traceSessionX25VcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { traceSessionX25VcStatsEntry 11 }

traceSessionX25VcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { traceSessionX25VcStatsEntry 12 }




-- 
-- Version and Compliance statements
-- 



-- Object-Group Statement:
-- A list of all current accessible leaf objects.

-- OBJECTS { traceSessionX25VcPeakRetryQueueSize,
--           traceRcvrX25DnaOutCalls,
--           traceSessionX25VcCalledDna,
--           traceRcvrX25DnaCugPreferential,
--           traceSessionX25VcMaxSubnetPktSize,
--           traceRcvrX25DnaOutAccess,
--           traceRcvrX25DnaDefaultSendToNetworkWindowSize,
--           traceSessionX25VcPeakOoSeqFrmForwarded,
--           traceSessionX25VcStorageType,
--           traceSessionX25VcType,
--           traceSessionX25VcFrmRetryTimeouts,
--           traceRcvrX25DcComponentName,
--           traceSessionX25VcPriority,
--           traceSessionX25VcSubnetRxPktSize,
--           traceRcvrX25DnaDefaultRecvFrmNetworkPacketSize,
--           traceRcvrX25ComponentName,
--           traceSessionX25VcCallingLcn,
--           traceSessionX25VcPeakOoSeqQueueSize,
--           traceSessionX25VcCallingDna,
--           traceSessionX25VcRowStatus,
--           traceSessionX25VcCallingNpi,
--           traceRcvrX25DnaCugOutCalls,
--           traceSessionX25VcSubnetTxWindowSize,
--           traceSessionX25VcSegmentsSent,
--           traceSessionX25VcLocalRxPktSize,
--           traceRcvrX25DnaCugStorageType,
--           traceSessionX25VcLocalTxWindowSize,
--           traceSessionX25VcFastSelectCall,
--           traceRcvrX25DnaCugPrivileged,
--           traceRcvrX25DnaOutIntl,
--           traceSessionX25VcPathReliability,
--           traceRcvrX25DnaCugFormat,
--           traceRcvrX25DnaDefaultRecvFrmNetworkWindowSize,
--           traceRcvrX25DnaCugIncCalls,
--           traceRcvrX25DcUserData,
--           traceSessionX25VcTransferPriorityFromNetwork,
--           traceRcvrX25DnaStorageType,
--           traceRcvrX25DnaCugType,
--           traceSessionX25VcSegmentSize,
--           traceSessionX25StorageType,
--           traceSessionX25VcCallReferenceNumber,
--           traceSessionX25VcPeakStackedAcksRx,
--           traceRcvrX25DnaOutDefaultPriority,
--           traceRcvrX25DnaOutDefaultPathReliability,
--           traceRcvrX25DnaIncCalls,
--           traceSessionX25VcState,
--           traceSessionX25VcAckStackingTimeouts,
--           traceSessionX25VcWindowClosuresFromSubnet,
--           traceRcvrX25DnaDefaultSendToNetworkThruputClass,
--           traceSessionX25VcSegmentsRx,
--           traceRcvrX25DnaCugRowStatus,
--           traceSessionX25VcDuplicatesFromSubnet,
--           traceRcvrX25DnaPacketSizes,
--           traceRcvrX25DnaPacketSizeNegotiation,
--           traceSessionX25VcPreviousDiagnosticCode,
--           traceSessionX25VcSubnetTxPktSize,
--           traceSessionX25VcDiagnosticCode,
--           traceRcvrX25DnaRowStatus,
--           traceRcvrX25DnaDefaultSendToNetworkPacketSize,
--           traceRcvrX25DcStorageType,
--           traceSessionX25VcComponentName,
--           traceSessionX25VcLocalRxWindowSize,
--           traceSessionX25VcWrTriggers,
--           traceSessionX25VcSubnetRxWindowSize,
--           traceRcvrX25StorageType,
--           traceSessionX25VcWindowClosuresToSubnet,
--           traceSessionX25VcCalledLcn,
--           traceRcvrX25DnaCugComponentName,
--           traceSessionX25VcSubnetRecoveries,
--           traceRcvrX25DnaCugDnic,
--           traceSessionX25VcElapsedTimeTillNow,
--           traceSessionX25VcOutOfRangeFrmFromSubnet,
--           traceRcvrX25DcType,
--           traceRcvrX25DnaComponentName,
--           traceRcvrX25DnaCugInterlockCode,
--           traceRcvrX25DnaNumberingPlanIndicator,
--           traceRcvrX25DnaDataNetworkAddress,
--           traceSessionX25RowStatus,
--           traceSessionX25VcAccountingEnabled,
--           traceSessionX25ComponentName,
--           traceSessionX25VcAccountingEnd,
--           traceSessionX25VcTransferPriorityToNetwork,
--           traceRcvrX25DcRemoteNpi,
--           traceSessionX25VcPreviousState,
--           traceRcvrX25DcRowStatus,
--           traceRcvrX25DnaDefaultRecvFrmNetworkThruputClass,
--           traceRcvrX25DnaOutPathReliabilityOverRide,
--           traceSessionX25VcStartTime,
--           traceRcvrX25RowStatus,
--           traceSessionX25VcLocalTxPktSize,
--           traceRcvrX25DcRemoteDna,
--           traceSessionX25VcCalledNpi,
--           traceRcvrX25DnaOutPathReliabilitySignal }
-- STATUS  mandatory
-- DESCRIPTION
--   "A list of all current accessible leaf objects."

x25TraceRcvrGroup OBJECT IDENTIFIER ::= { x25TraceRcvrMIB 1 }
x25TraceRcvrGroupBD OBJECT IDENTIFIER ::= { x25TraceRcvrGroup 4 }
x25TraceRcvrGroupBD00 OBJECT IDENTIFIER ::= { x25TraceRcvrGroupBD 1 }
x25TraceRcvrGroupBD00A OBJECT IDENTIFIER ::= { x25TraceRcvrGroupBD00 2 }



-- Agent-Capabilities Statement:

-- PRODUCT-RELEASE "Passport Release 7.0 X25TraceRcvr."
-- STATUS          mandatory
-- DESCRIPTION     "X25TraceRcvr MIB: MIB Version BD00A,
--                  Software Version BG00S4C."
-- SUPPORTS        Nortel-Magellan-Passport-X25TraceRcvrMIB
--    INCLUDES     { x25TraceRcvrGroupBD00A }

x25TraceRcvrCapabilities OBJECT IDENTIFIER ::= { x25TraceRcvrMIB 3 }
x25TraceRcvrCapabilitiesBD OBJECT IDENTIFIER ::= { x25TraceRcvrCapabilities 4 }
x25TraceRcvrCapabilitiesBD00 OBJECT IDENTIFIER ::= { x25TraceRcvrCapabilitiesBD 1 }
x25TraceRcvrCapabilitiesBD00A OBJECT IDENTIFIER ::= { x25TraceRcvrCapabilitiesBD00 2 }





END
