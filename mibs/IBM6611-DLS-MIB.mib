-- Copyright 1995 by 3Com Corporation.  All rights reserved.
-- MIB file name:  dlsw.mib
-- available in these 3Com devices:  NETBuilder routers
-- For support or more info, check 3Com's web page at http://www.3com.com

 
------------------------------------------------------------------------
-- The IBM 6611 Data Link Switch (DLS) Extension                       -
------------------------------------------------------------------------
 
IBM6611-DLS-MIB DEFINITIONS ::= BEGIN
 
IMPORTS
          enterprises, Counter, IpAddress
                  FROM RFC1155-SMI
          DisplayString
                  FROM SNMPv2-TC
          OBJECT-TYPE
                  FROM RFC-1212;
 
  ibm                            OBJECT IDENTIFIER ::= { enterprises 2 }
  ibmProd                        OBJECT IDENTIFIER ::= { ibm 6 }
  ibm6611                        OBJECT IDENTIFIER ::= { ibmProd 2 }
  ibmappn                        OBJECT IDENTIFIER ::= { ibm6611 13 }
  ibmdls                         OBJECT IDENTIFIER ::= { ibm6611 9 }

--  This MIB module uses the extended OBJECT-TYPE macro as
--  defined in RFC 1212.
 
-- All representations of MAC addresses in this MIB Module use,
-- as a textual convention (i.e. this convention does not affect
-- their encoding), the data type:
 
MacAddress ::= OCTET STRING (SIZE(6))
 
 
-- All DLS filter tables use the following type to decide what
-- kind of filtering to do:
 
FilterType ::= INTEGER { deny(1), permit(2) }
 
 
--
-- Virtual Ring Segment Number
--
 
ibmdlsVirtualRingSegmentNumber OBJECT-TYPE
    SYNTAX  INTEGER (0..4095)
    ACCESS  read-only
    STATUS  mandatory
    DESCRIPTION
            "The token ring segment number used in all frames passed
            to or from the IBM 6611 Data Link Switching function."
    ::= { ibmdls 1 }
 
 
--
-- Filter types
--
 
ibmdlsFrameFilterType OBJECT-TYPE
    SYNTAX  FilterType
    ACCESS  read-only
    STATUS  mandatory
    DESCRIPTION
            "The type of SNA filtering applied using the
            ibmdlsLocalFrameFilterTable and ibmdlsRemoteFrameFilterTable.
 
            If this field = permit(2), then all filters defined
            for SNA use the action of permitting frames to be
            forwarded if they meet the criteria given by the
            source and destination address values.
 
            If this field = deny(1), then all filters defined
            for SNA use the action of denying frames to be
            forwarded if they meet the criteria given
            by the source and destination address values."
    ::= { ibmdls 2 }
 
 
ibmdlsNameFilterType OBJECT-TYPE
    SYNTAX  FilterType
    ACCESS  read-only
    STATUS  mandatory
    DESCRIPTION
            "The type of NetBIOS filtering applied using the
            ibmdlsLocalNameFilterTable and ibmdlsRemoteNameFilterTable.
 
            If this field = permit(2), then all filters defined
            for NetBIOS use the action of permitting frames
            to be forwarded if they meet the criteria given
            by the source and destination address values.
 
            If this field = deny(1), then all filters defined
            for NetBIOS use the action of denying frames
            to be forwarded if they meet the criteria given
            by the source and destination address values."
    ::= { ibmdls 3 }
 
 
------------------------------------------------------------------------
-- Participating Router Table
------------------------------------------------------------------------
 
ibmdlsRouterTable OBJECT-TYPE
    SYNTAX  SEQUENCE OF IbmdlsRouterEntry
    ACCESS  not-accessible
    STATUS  mandatory
    DESCRIPTION
            "A table of information regarding all routers
            participating in Data Link Switching."
 
    ::= { ibmdls 4 }
 
ibmdlsRouterEntry OBJECT-TYPE
    SYNTAX  IbmdlsRouterEntry
    ACCESS  not-accessible
    STATUS  mandatory
    DESCRIPTION
            "Information for a single participating router."
    INDEX   { ibmdlsRouterAddress }
    ::= { ibmdlsRouterTable 1 }
 
IbmdlsRouterEntry ::=
    SEQUENCE {
        ibmdlsRouterAddress
            IpAddress,
        ibmdlsRouterStatus
            INTEGER,
        ibmdlsRouterDefinedBy
            INTEGER
    }
 
ibmdlsRouterAddress OBJECT-TYPE
    SYNTAX  IpAddress
    ACCESS  read-only
    STATUS  mandatory
    DESCRIPTION
            "The IP address of the router participating in Data
            Link Switching."
    ::= { ibmdlsRouterEntry 1 }
 
ibmdlsRouterStatus OBJECT-TYPE
    SYNTAX  INTEGER {
                notActive(1),
                active(2)
            }
    ACCESS  read-only
    STATUS  mandatory
    DESCRIPTION
            "The current state of the remote connection"
    ::= { ibmdlsRouterEntry 2 }
 
ibmdlsRouterDefinedBy OBJECT-TYPE
    SYNTAX  INTEGER {
                user(1),
                system(2)
            }
    ACCESS  read-only
    STATUS  mandatory
    DESCRIPTION
            "The origin of this entry. user(1) indicates that
            this router is defined via the Configuration Program.
            system(2) indicates that this router was defined
            automatically as a result of a connection request from
            another router."
    ::= { ibmdlsRouterEntry 3 }
 
 
------------------------------------------------------------------------
-- SNA Local Frame Filter Table
------------------------------------------------------------------------
 
ibmdlsLocalFrameFilterTable OBJECT-TYPE
    SYNTAX  SEQUENCE OF IbmdlsLocalFrameFilterEntry
    ACCESS  not-accessible
    STATUS  mandatory
    DESCRIPTION
            "The SNA local frame filter table.  This table contains
            information regarding the filtering of SNA frames received
            from local LAN segments."
    ::= { ibmdls 5 }
 
ibmdlsLocalFrameFilterEntry OBJECT-TYPE
    SYNTAX  IbmdlsLocalFrameFilterEntry
    ACCESS  not-accessible
    STATUS  mandatory
    DESCRIPTION
            "Filter information for a MAC address source-destination pair."
    INDEX   { ibmdlsLocalFrameFilterID }
    ::= { ibmdlsLocalFrameFilterTable 1 }
 
IbmdlsLocalFrameFilterEntry ::=
    SEQUENCE {
        ibmdlsLocalFrameFilterID
            INTEGER,
        ibmdlsLocalFrameFilterSrcAddress
            MacAddress,
        ibmdlsLocalFrameFilterSrcMask
            MacAddress,
        ibmdlsLocalFrameFilterDestAddress
            MacAddress,
        ibmdlsLocalFrameFilterDestMask
            MacAddress
    }
 
ibmdlsLocalFrameFilterID OBJECT-TYPE
    SYNTAX  INTEGER (1..100)
    ACCESS  read-only
    STATUS  mandatory
    DESCRIPTION
            "A unique identifier for this filter."
    ::= { ibmdlsLocalFrameFilterEntry 1 }
 
ibmdlsLocalFrameFilterSrcAddress OBJECT-TYPE
    SYNTAX  MacAddress
    ACCESS  read-only
    STATUS  mandatory
    DESCRIPTION
            "The source MAC address that this filter is
            applied to."
    ::= { ibmdlsLocalFrameFilterEntry 2 }
 
ibmdlsLocalFrameFilterSrcMask OBJECT-TYPE
    SYNTAX  MacAddress
    ACCESS  read-only
    STATUS  mandatory
    DESCRIPTION
            "A mask indicating the bits of the source address
            considered significant when using the filter.
            For every bit equal to one in the mask, the same bit
            in the source address is considered significant."
    ::= { ibmdlsLocalFrameFilterEntry 3 }
 
ibmdlsLocalFrameFilterDestAddress OBJECT-TYPE
    SYNTAX  MacAddress
    ACCESS  read-only
    STATUS  mandatory
    DESCRIPTION
            "The destination MAC address that this filter is
            applied to."
    ::= { ibmdlsLocalFrameFilterEntry 4 }
 
ibmdlsLocalFrameFilterDestMask OBJECT-TYPE
    SYNTAX  MacAddress
    ACCESS  read-only
    STATUS  mandatory
    DESCRIPTION
            "A mask indicating the bits of the destination address
            considered significant when using the filter.
            For every bit equal to one in the mask, the same bit
            in the destination address is considered significant."
    ::= { ibmdlsLocalFrameFilterEntry 5 }
 
 
------------------------------------------------------------------------
-- SNA Remote Frame Filter Table
------------------------------------------------------------------------
 
ibmdlsRemoteFrameFilterTable OBJECT-TYPE
    SYNTAX  SEQUENCE OF IbmdlsRemoteFrameFilterEntry
    ACCESS  not-accessible
    STATUS  mandatory
    DESCRIPTION
            "The SNA remote frame filter table.  This table contains
            information regarding the filtering of SNA frames received
            from other participating DLS routers."
    ::= { ibmdls 6 }
 
ibmdlsRemoteFrameFilterEntry OBJECT-TYPE
    SYNTAX  IbmdlsRemoteFrameFilterEntry
    ACCESS  not-accessible
    STATUS  mandatory
    DESCRIPTION
            "Filter information for a MAC address source-destination pair."
    INDEX   { ibmdlsRemoteFrameFilterID }
    ::= { ibmdlsRemoteFrameFilterTable 1 }
 
IbmdlsRemoteFrameFilterEntry ::=
    SEQUENCE {
        ibmdlsRemoteFrameFilterID
            INTEGER,
        ibmdlsRemoteFrameFilterSrcAddress
            MacAddress,
        ibmdlsRemoteFrameFilterSrcMask
            MacAddress,
        ibmdlsRemoteFrameFilterDestAddress
            MacAddress,
        ibmdlsRemoteFrameFilterDestMask
            MacAddress
    }
 
ibmdlsRemoteFrameFilterID OBJECT-TYPE
    SYNTAX  INTEGER (1..100)
    ACCESS  read-only
    STATUS  mandatory
    DESCRIPTION
            "A unique identifier for this filter."
    ::= { ibmdlsRemoteFrameFilterEntry 1 }
 
ibmdlsRemoteFrameFilterSrcAddress OBJECT-TYPE
    SYNTAX  MacAddress
    ACCESS  read-only
    STATUS  mandatory
    DESCRIPTION
            "The source MAC address that this filter is
            applied to."
    ::= { ibmdlsRemoteFrameFilterEntry 2 }
 
ibmdlsRemoteFrameFilterSrcMask OBJECT-TYPE
    SYNTAX  MacAddress
    ACCESS  read-only
    STATUS  mandatory
    DESCRIPTION
            "A mask indicating the bits of the source address
            considered significant when using the filter.
            For every bit equal to one in the mask, the same bit
            in the source address is considered significant."
    ::= { ibmdlsRemoteFrameFilterEntry 3 }
 
ibmdlsRemoteFrameFilterDestAddress OBJECT-TYPE
    SYNTAX  MacAddress
    ACCESS  read-only
    STATUS  mandatory
    DESCRIPTION
            "The destination MAC address that this filter is
            applied to."
    ::= { ibmdlsRemoteFrameFilterEntry 4 }
 
ibmdlsRemoteFrameFilterDestMask OBJECT-TYPE
    SYNTAX  MacAddress
    ACCESS  read-only
    STATUS  mandatory
    DESCRIPTION
            "A mask indicating the bits of the destination address
            considered significant when using the filter.
            For every bit equal to one in the mask, the same bit
            in the destination address is considered significant."
    ::= { ibmdlsRemoteFrameFilterEntry 5 }
 
 
------------------------------------------------------------------------
-- NetBIOS Local Name Filter Table
------------------------------------------------------------------------
 
ibmdlsLocalNameFilterTable OBJECT-TYPE
    SYNTAX  SEQUENCE OF IbmdlsLocalNameFilterEntry
    ACCESS  not-accessible
    STATUS  mandatory
    DESCRIPTION
            "The NetBIOS local name filter table.  This table contains
            information regarding the filtering of NetBIOS frames
            received from local LAN segments."
    ::= { ibmdls 7 }
 
ibmdlsLocalNameFilterEntry OBJECT-TYPE
    SYNTAX  IbmdlsLocalNameFilterEntry
    ACCESS  not-accessible
    STATUS  mandatory
    DESCRIPTION
            "Filter information for a NetBIOS source-destination
            name pair."
    INDEX   { ibmdlsLocalNameFilterID }
    ::= { ibmdlsLocalNameFilterTable 1 }
 
IbmdlsLocalNameFilterEntry ::=
    SEQUENCE {
        ibmdlsLocalNameFilterID
            INTEGER,
        ibmdlsLocalNameFilterSrcAddress
            DisplayString,
        ibmdlsLocalNameFilterDestAddress
            DisplayString
    }
 
ibmdlsLocalNameFilterID OBJECT-TYPE
    SYNTAX  INTEGER (1..100)
    ACCESS  read-only
    STATUS  mandatory
    DESCRIPTION
            "A unique identifier for this filter."
    ::= { ibmdlsLocalNameFilterEntry 1 }
 
ibmdlsLocalNameFilterSrcAddress OBJECT-TYPE
    SYNTAX  DisplayString (SIZE (1..16))
    ACCESS  read-only
    STATUS  mandatory
    DESCRIPTION
            "The source NetBIOS name that this filter is
            applied to."
    ::= { ibmdlsLocalNameFilterEntry 2 }
 
ibmdlsLocalNameFilterDestAddress OBJECT-TYPE
    SYNTAX  DisplayString  (SIZE (1..16))
    ACCESS  read-only
    STATUS  mandatory
    DESCRIPTION
            "The destination NetBIOS name that this filter is
            applied to."
    ::= { ibmdlsLocalNameFilterEntry 3 }
 
 
------------------------------------------------------------------------
-- NetBIOS Remote Name Filter Table
------------------------------------------------------------------------
 
ibmdlsRemoteNameFilterTable OBJECT-TYPE
    SYNTAX  SEQUENCE OF IbmdlsRemoteNameFilterEntry
    ACCESS  not-accessible
    STATUS  mandatory
    DESCRIPTION
            "The NetBIOS name filter table.   This table contains
            information regarding the filtering of NetBIOS frames
            received from other participating DLS routers."
    ::= { ibmdls 8 }
 
ibmdlsRemoteNameFilterEntry OBJECT-TYPE
    SYNTAX  IbmdlsRemoteNameFilterEntry
    ACCESS  not-accessible
    STATUS  mandatory
    DESCRIPTION
            "Filter information for a NetBIOS source-destination
            name pair."
    INDEX   { ibmdlsRemoteNameFilterID }
    ::= { ibmdlsRemoteNameFilterTable 1 }
 
IbmdlsRemoteNameFilterEntry ::=
    SEQUENCE {
        ibmdlsRemoteNameFilterID
            INTEGER,
        ibmdlsRemoteNameFilterSrcAddress
            DisplayString,
        ibmdlsRemoteNameFilterDestAddress
            DisplayString
    }
 
ibmdlsRemoteNameFilterID OBJECT-TYPE
    SYNTAX  INTEGER (1..100)
    ACCESS  read-only
    STATUS  mandatory
    DESCRIPTION
            "A unique identifier for this filter."
    ::= { ibmdlsRemoteNameFilterEntry 1 }
 
ibmdlsRemoteNameFilterSrcAddress OBJECT-TYPE
    SYNTAX  DisplayString (SIZE (1..16))
    ACCESS  read-only
    STATUS  mandatory
    DESCRIPTION
            "The source NetBIOS name that this filter is
            applied to."
    ::= { ibmdlsRemoteNameFilterEntry 2 }
 
ibmdlsRemoteNameFilterDestAddress OBJECT-TYPE
    SYNTAX  DisplayString (SIZE (1..16))
    ACCESS  read-only
    STATUS  mandatory
    DESCRIPTION
            "The destination NetBIOS name that this filter is
            applied to."
    ::= { ibmdlsRemoteNameFilterEntry 3 }
 
 
------------------------------------------------------------------------
-- SNA Default Destination Table
------------------------------------------------------------------------
 
ibmdlsDefaultDestTable OBJECT-TYPE
    SYNTAX  SEQUENCE OF IbmdlsDefaultDestEntry
    ACCESS  not-accessible
    STATUS  mandatory
    DESCRIPTION
            "Table of default routers for MAC addresses."
    ::= { ibmdls 9 }
 
ibmdlsDefaultDestEntry OBJECT-TYPE
    SYNTAX  IbmdlsDefaultDestEntry
    ACCESS  not-accessible
    STATUS  mandatory
    DESCRIPTION
            "Mapping of a MAC address to a default router."
    INDEX   { ibmdlsDefaultDestAddress }
    ::= { ibmdlsDefaultDestTable 1 }
 
IbmdlsDefaultDestEntry ::=
    SEQUENCE {
        ibmdlsDefaultDestAddress
            MacAddress,
        ibmdlsDefaultRouterAddress
            IpAddress
    }
 
ibmdlsDefaultDestAddress OBJECT-TYPE
    SYNTAX  MacAddress
    ACCESS  read-only
    STATUS  mandatory
    DESCRIPTION
            "The destination address that this table entry applies
            to."
    ::= { ibmdlsDefaultDestEntry 1 }
 
ibmdlsDefaultRouterAddress OBJECT-TYPE
    SYNTAX  IpAddress
    ACCESS  read-only
    STATUS  mandatory
    DESCRIPTION
            "The default router used for reaching the destination
            address in ibmdlsDefaultDestAddress."
    ::= { ibmdlsDefaultDestEntry 2 }
 
 
------------------------------------------------------------------------
-- NetBios Default Destination Table
------------------------------------------------------------------------
 
ibmdlsDefaultNBDestTable OBJECT-TYPE
    SYNTAX  SEQUENCE OF IbmdlsDefaultNBDestEntry
    ACCESS  not-accessible
    STATUS  mandatory
    DESCRIPTION
            "Table of default routers for NetBIOS names."
    ::= { ibmdls 10 }
 
ibmdlsDefaultNBDestEntry OBJECT-TYPE
    SYNTAX  IbmdlsDefaultNBDestEntry
    ACCESS  not-accessible
    STATUS  mandatory
    DESCRIPTION
            "Mapping of a NetBIOS name to a default router."
    INDEX   { ibmdlsDefaultNBDestName }
    ::= { ibmdlsDefaultNBDestTable 1 }
 
IbmdlsDefaultNBDestEntry ::=
    SEQUENCE {
        ibmdlsDefaultNBDestName
            DisplayString,
        ibmdlsDefaultNBRouterAddress
            IpAddress
    }
 
ibmdlsDefaultNBDestName OBJECT-TYPE
    SYNTAX  DisplayString (SIZE (1..16))
    ACCESS  read-only
    STATUS  mandatory
    DESCRIPTION
            "The destination NetBIOS name that this table entry
            applies to."
    ::= { ibmdlsDefaultNBDestEntry 1 }
 
ibmdlsDefaultNBRouterAddress OBJECT-TYPE
    SYNTAX  IpAddress
    ACCESS  read-only
    STATUS  mandatory
    DESCRIPTION
            "The default router used for reaching the destination
            name in ibmdlsDefaultNBDestName."
    ::= { ibmdlsDefaultNBDestEntry 2 }
 
 
------------------------------------------------------------------------
-- SNA Station Table
------------------------------------------------------------------------
 
ibmdlsStationTable OBJECT-TYPE
    SYNTAX  SEQUENCE OF IbmdlsStationEntry
    ACCESS  not-accessible
    STATUS  mandatory
    DESCRIPTION
            "Table of configuration information on SNA stations
            attached to this router."
    ::= { ibmdls 11 }
 
ibmdlsStationEntry OBJECT-TYPE
    SYNTAX  IbmdlsStationEntry
    ACCESS  not-accessible
    STATUS  mandatory
    DESCRIPTION
            "Information on a single SNA station attached to this router."
    INDEX   { ibmdlsStationIfIndex, ibmdlsStationAddress }
    ::= { ibmdlsStationTable 1 }
 
IbmdlsStationEntry ::=
    SEQUENCE {
        ibmdlsStationIfIndex
            INTEGER,
        ibmdlsStationAddress
            INTEGER,
        ibmdlsStationTransmitWindowCount
            INTEGER,
        ibmdlsStationRetransmitCount
            INTEGER,
        ibmdlsStationRetransmitThreshold
            INTEGER,
        ibmdlsStationForceDisconnectTimeout
            INTEGER,
        ibmdlsStationMaxIfieldSize
            INTEGER,
        ibmdlsStationPrimaryRepollTimeout
            INTEGER,
        ibmdlsStationPrimaryRepollCount
            INTEGER,
        ibmdlsStationPrimaryRepollThreshold
            INTEGER,
        ibmdlsStationPrimarySlowListTimeout
            INTEGER,
        ibmdlsStationSrcAddress
            MacAddress,
        ibmdlsStationDestAddress
            MacAddress
    }
 
ibmdlsStationIfIndex OBJECT-TYPE
    SYNTAX  INTEGER
    ACCESS  read-only
    STATUS  mandatory
    DESCRIPTION
            "The value of IfIndex for the port to which this station
            is attached."
    ::= { ibmdlsStationEntry 1 }
 
ibmdlsStationAddress OBJECT-TYPE
    SYNTAX  INTEGER (1..255)
    ACCESS  read-only
    STATUS  mandatory
    DESCRIPTION
            "The SDLC address of this station."
    ::= { ibmdlsStationEntry 2 }
 
ibmdlsStationTransmitWindowCount OBJECT-TYPE
    SYNTAX  INTEGER (1..7)
    ACCESS  read-only
    STATUS  mandatory
    DESCRIPTION
            "The number of SDLC information frames to send to this
            station before turning the line around to get a response."
    DEFVAL  { 7 }
    ::= { ibmdlsStationEntry 3 }
 
ibmdlsStationRetransmitCount OBJECT-TYPE
    SYNTAX  INTEGER (1..50)
    ACCESS  read-only
    STATUS  mandatory
    DESCRIPTION
            "The number of contiguous information frame bursts that
            will be transmitted to this station before declaring a
            permanent transmission error."
    DEFVAL  { 10 }
    ::= { ibmdlsStationEntry 4 }
 
ibmdlsStationRetransmitThreshold OBJECT-TYPE
    SYNTAX  INTEGER (1..100)
    ACCESS  read-only
    STATUS  mandatory
    DESCRIPTION
            "The number of information frame transmissions allowed as
            a percentage of total information frame transmissions.
            The specified rate is the maximum rate of retransmissions
            allowed above which an error log entry will be make."
    DEFVAL  { 10 }
    ::= { ibmdlsStationEntry 5 }
 
ibmdlsStationForceDisconnectTimeout OBJECT-TYPE
    SYNTAX  INTEGER (1..600)
    ACCESS  read-only
    STATUS  mandatory
    DESCRIPTION
            "The number of seconds that the IBM 6611 will wait after
            requesting a disconnect from the link (DISC) before forcing
            a disconnect."
    DEFVAL  { 120 }
    ::= { ibmdlsStationEntry 6 }
 
ibmdlsStationMaxIfieldSize OBJECT-TYPE
    SYNTAX  INTEGER (265..30729)
    ACCESS  read-only
    STATUS  mandatory
    DESCRIPTION
            "The value in bytes of the maximum I-field size
            (a multiple of 256 plus 9)."
    DEFVAL  { 265 }
    ::= { ibmdlsStationEntry 7 }
 
ibmdlsStationPrimaryRepollTimeout OBJECT-TYPE
    SYNTAX  INTEGER (1..250)
    ACCESS  read-only
    STATUS  mandatory
    DESCRIPTION
            "The length of time (in tenths of seconds) that the primary
            station will wait for a response from the secondary station."
    DEFVAL  { 30 }
    ::= { ibmdlsStationEntry 8 }
 
ibmdlsStationPrimaryRepollCount OBJECT-TYPE
    SYNTAX  INTEGER (3..50)
    ACCESS  read-only
    STATUS  mandatory
    DESCRIPTION
            "The number of times that the primary station will poll
            the secondary station unsuccessfully before marking the
            station as not working."
    DEFVAL  { 15 }
    ::= { ibmdlsStationEntry 9 }
 
ibmdlsStationPrimaryRepollThreshold OBJECT-TYPE
    SYNTAX  INTEGER (1..100)
    ACCESS  read-only
    STATUS  mandatory
    DESCRIPTION
            "The number of repolls as a percentage of the total polls
            sent to the secondary station.  The specified percentage equals
            the maximum rate of repolls allowed, above which the IBM 6611
            declares that a temporary error has occurred and logs an
            entry in the system error log."
    DEFVAL  { 10 }
    ::= { ibmdlsStationEntry 10 }
 
ibmdlsStationPrimarySlowListTimeout OBJECT-TYPE
    SYNTAX  INTEGER (1..60)
    ACCESS  read-only
    STATUS  mandatory
    DESCRIPTION
            "The number of seconds that the primary station will wait
            between polls to stations on the slow list."
    DEFVAL  { 1 }
    ::= { ibmdlsStationEntry 11 }
 
ibmdlsStationSrcAddress OBJECT-TYPE
    SYNTAX  MacAddress
    ACCESS  read-only
    STATUS  mandatory
    DESCRIPTION
            "The token ring physical address used for this station."
    ::= { ibmdlsStationEntry 12 }
 
ibmdlsStationDestAddress OBJECT-TYPE
    SYNTAX  MacAddress
    ACCESS  read-only
    STATUS  mandatory
    DESCRIPTION
            "The token ring physical address to which this station
            should be connected.  If this information is not
            available the IBM 6611 Network Processor will return
            a length of zero for this object."
    ::= { ibmdlsStationEntry 13 }
 
 
------------------------------------------------------------------------
-- Circuit Table
------------------------------------------------------------------------
-- A unique circuit is identified by a port number (on a specific router),
-- source address, source SAP, destination address, and destination SAP.
-- In the DLS MIB, ifIndex is used instead of port number.
--
 
ibmdlsCirTable OBJECT-TYPE
    SYNTAX  SEQUENCE OF IbmdlsCirEntry
    ACCESS  not-accessible
    STATUS  mandatory
    DESCRIPTION
            "Table of information on DLS circuits active on this router."
    ::= { ibmdls 12 }
 
ibmdlsCirEntry OBJECT-TYPE
    SYNTAX  IbmdlsCirEntry
    ACCESS  not-accessible
    STATUS  mandatory
    DESCRIPTION
            "Information on a DLS circuit."
    INDEX   { ibmdlsCirIfIndex, ibmdlsCirSrcAddress,
              ibmdlsCirSrcSap, ibmdlsCirDestAddress,
              ibmdlsCirDestSap }
    ::= { ibmdlsCirTable 1 }
 
IbmdlsCirEntry ::=
    SEQUENCE {
        ibmdlsCirIfIndex
            INTEGER,
        ibmdlsCirSrcAddress
            MacAddress,
        ibmdlsCirSrcSap
            INTEGER,
        ibmdlsCirDestAddress
            MacAddress,
        ibmdlsCirDestSap
            INTEGER,
        ibmdlsCirPartnerRouterAddress
            IpAddress,
        ibmdlsCirLocalLinkState
            INTEGER,
        ibmdlsCirLocalLinkSubState
            INTEGER,
        ibmdlsCirLocalLinkRouting
            OCTET STRING,
        ibmdlsCirLocalLinkTestCmdsSent
            Counter,
        ibmdlsCirLocalLinkTestCmdsFail
            Counter,
        ibmdlsCirLocalLinkTestCmdsRcv
            Counter,
        ibmdlsCirLocalLinkDataPktSent
            Counter,
        ibmdlsCirLocalLinkDataPktResent
            Counter,
        ibmdlsCirLocalLinkMaxContResent
            Counter,
        ibmdlsCirLocalLinkDataPktRcv
            Counter,
        ibmdlsCirLocalLinkInvalidPktRcv
            Counter,
        ibmdlsCirLocalLinkAdpRcvErr
            Counter,
        ibmdlsCirLocalLinkAdpSendErr
            Counter,
        ibmdlsCirLocalLinkRcvInactiveTimeouts
            Counter,
        ibmdlsCirLocalLinkCmdPollsSent
            Counter,
        ibmdlsCirLocalLinkCmdRepollsSent
            Counter,
        ibmdlsCirLocalLinkCmdContRepolls
            Counter
    }
 
ibmdlsCirIfIndex OBJECT-TYPE
    SYNTAX  INTEGER
    ACCESS  read-only
    STATUS  mandatory
    DESCRIPTION
            "The value of IfIndex for the interface supporting this
             circuit."
    ::= { ibmdlsCirEntry 1 }
 
ibmdlsCirSrcAddress OBJECT-TYPE
    SYNTAX  MacAddress
    ACCESS  read-only
    STATUS  mandatory
    DESCRIPTION
            "The MAC address of the source of this circuit."
    ::= { ibmdlsCirEntry 2 }
 
ibmdlsCirSrcSap OBJECT-TYPE
    SYNTAX  INTEGER
    ACCESS  read-only
    STATUS  mandatory
    DESCRIPTION
            "The SAP identifier of the source of this circuit."
    ::= { ibmdlsCirEntry 3 }
 
ibmdlsCirDestAddress OBJECT-TYPE
    SYNTAX  MacAddress
    ACCESS  read-only
    STATUS  mandatory
    DESCRIPTION
            "The MAC address of the destination of this circuit."
    ::= { ibmdlsCirEntry 4 }
 
ibmdlsCirDestSap OBJECT-TYPE
    SYNTAX  INTEGER
    ACCESS  read-only
    STATUS  mandatory
    DESCRIPTION
            "The SAP identifier of the destination of this circuit."
    ::= { ibmdlsCirEntry 5 }
 
ibmdlsCirPartnerRouterAddress OBJECT-TYPE
    SYNTAX  IpAddress
    ACCESS  read-only
    STATUS  mandatory
    DESCRIPTION
            "The IP address of the partner router used by
            this circuit."
    ::= { ibmdlsCirEntry 6 }
 
ibmdlsCirLocalLinkState OBJECT-TYPE
    SYNTAX  INTEGER {
                opening(1),
                opened(2),
                closing(3),
                inactive(4)
            }
    ACCESS  read-only
    STATUS  mandatory
    DESCRIPTION
            "The state of the local link station used by
            this circuit."
    ::= { ibmdlsCirEntry 7 }
 
ibmdlsCirLocalLinkSubState OBJECT-TYPE
    SYNTAX  INTEGER {
                calling(1),
                listening(2),
                contacted(3),
                localBusy(4),
                remoteBusy(5)
            }
    ACCESS  read-only
    STATUS  mandatory
    DESCRIPTION
            "The sub-state of the local link station used by
            this circuit."
    ::= { ibmdlsCirEntry 8 }
 
ibmdlsCirLocalLinkRouting OBJECT-TYPE
    SYNTAX  OCTET STRING (SIZE (4..18))
    ACCESS  read-only
    STATUS  mandatory
    DESCRIPTION
            "The routing information field used by the
            local link portion of this circuit.  The routing
            information field consists of a 2-byte routing
            control field and up to eight 2-byte route
            designators."
    REFERENCE
            "IBM Token-ring Network:  Architecture Reference
            (SC30-3374), see 'Routing Information Field'."
    ::= { ibmdlsCirEntry 9 }
 
ibmdlsCirLocalLinkTestCmdsSent OBJECT-TYPE
    SYNTAX  Counter
    ACCESS  read-only
    STATUS  mandatory
    DESCRIPTION
            "The number of test commands sent by the
            local link station used by this circuit."
    ::= { ibmdlsCirEntry 10}
 
ibmdlsCirLocalLinkTestCmdsFail OBJECT-TYPE
    SYNTAX  Counter
    ACCESS  read-only
    STATUS  mandatory
    DESCRIPTION
            "The number of test commands failed by the
            local link station used by this circuit."
    ::= { ibmdlsCirEntry 11 }
 
ibmdlsCirLocalLinkTestCmdsRcv OBJECT-TYPE
    SYNTAX  Counter
    ACCESS  read-only
    STATUS  mandatory
    DESCRIPTION
            "The number of test commands received by the
            local link station used by this circuit."
    ::= { ibmdlsCirEntry 12 }
 
ibmdlsCirLocalLinkDataPktSent OBJECT-TYPE
    SYNTAX  Counter
    ACCESS  read-only
    STATUS  mandatory
    DESCRIPTION
            "The number of sequenced data packets sent
            by the local link station used by this circuit."
    ::= { ibmdlsCirEntry 13 }
 
ibmdlsCirLocalLinkDataPktResent OBJECT-TYPE
    SYNTAX  Counter
    ACCESS  read-only
    STATUS  mandatory
    DESCRIPTION
            "The number of sequenced data packets resent by
            the local link station used by this circuit."
    ::= { ibmdlsCirEntry 14 }
 
ibmdlsCirLocalLinkMaxContResent OBJECT-TYPE
    SYNTAX  Counter
    ACCESS  read-only
    STATUS  mandatory
    DESCRIPTION
            "The maximum number of contiguous resendings by
            the local link station used by this circuit."
    ::= { ibmdlsCirEntry 15 }
 
ibmdlsCirLocalLinkDataPktRcv OBJECT-TYPE
    SYNTAX  Counter
    ACCESS  read-only
    STATUS  mandatory
    DESCRIPTION
            "The number of sequenced data packets received
            by the local link station used by this circuit."
    ::= { ibmdlsCirEntry 16 }
 
ibmdlsCirLocalLinkInvalidPktRcv OBJECT-TYPE
    SYNTAX  Counter
    ACCESS  read-only
    STATUS  mandatory
    DESCRIPTION
            "The number of invalid packets received by
            the local link station used by this circuit."
    ::= { ibmdlsCirEntry 17 }
 
ibmdlsCirLocalLinkAdpRcvErr OBJECT-TYPE
    SYNTAX  Counter
    ACCESS  read-only
    STATUS  mandatory
    DESCRIPTION
            "The number of data-detected receive errors by
            the local link station used by this circuit."
    ::= { ibmdlsCirEntry 18 }
 
ibmdlsCirLocalLinkAdpSendErr OBJECT-TYPE
    SYNTAX  Counter
    ACCESS  read-only
    STATUS  mandatory
    DESCRIPTION
            "The number of data-detected transmit errors by
            the local link station used by this circuit."
    ::= { ibmdlsCirEntry 19 }
 
ibmdlsCirLocalLinkRcvInactiveTimeouts OBJECT-TYPE
    SYNTAX  Counter
    ACCESS  read-only
    STATUS  mandatory
    DESCRIPTION
            "The number of inactivity timeouts received by
            the local link station used by this circuit."
    ::= { ibmdlsCirEntry 20 }
 
ibmdlsCirLocalLinkCmdPollsSent OBJECT-TYPE
    SYNTAX  Counter
    ACCESS  read-only
    STATUS  mandatory
    DESCRIPTION
            "The number of command polls sent by
            the local link station used by this circuit."
    ::= { ibmdlsCirEntry 21 }
 
ibmdlsCirLocalLinkCmdRepollsSent OBJECT-TYPE
    SYNTAX  Counter
    ACCESS  read-only
    STATUS  mandatory
    DESCRIPTION
            "The number of command repolls sent by
            the local link station used by this circuit."
    ::= { ibmdlsCirEntry 22 }
 
ibmdlsCirLocalLinkCmdContRepolls OBJECT-TYPE
    SYNTAX  Counter
    ACCESS  read-only
    STATUS  mandatory
    DESCRIPTION
            "The number of continuous repolls sent by
            the local link station used by this circuit."
    ::= { ibmdlsCirEntry 23 }
 
 
-- Local Variables:
-- tab-width: 4
-- case-fold-search: nil
-- End:
 
END
