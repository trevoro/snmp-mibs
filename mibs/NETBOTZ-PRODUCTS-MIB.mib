NETBOTZ-PRODUCTS-MIB DEFINITIONS ::= BEGIN

IMPORTS
netBotz-products FROM NETBOTZ-MIB;


netBotz-prd-bot		 OBJECT IDENTIFIER
                     ::= { netBotz-products 10 }

netBotz-prd-crawlers OBJECT IDENTIFIER
                     ::= { netBotz-products 20 }

netBotz-prd-crltrap  OBJECT IDENTIFIER
                     ::= { netBotz-products 21 }


netBotz-prd-WallBotz-300	 OBJECT IDENTIFIER
                     ::= { netBotz-products 1000 }

netBotz-prd-RackBotz-300	 OBJECT IDENTIFIER
                     ::= { netBotz-products 1001 }

netBotz-prd-RackBotz-300U	 OBJECT IDENTIFIER
                     ::= { netBotz-products 1002 }

netBotz-prd-RackBotz-303	 OBJECT IDENTIFIER
                     ::= { netBotz-products 1006 }

END
