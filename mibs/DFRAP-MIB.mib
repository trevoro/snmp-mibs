-- Sync Research enterprise MIB for DFRAP                     =
--                                                            =
--                                                            =
--                      MIB VERSION 4.00                      =
--                                                            =
--                                                            =
-- internal version 4.00.16                                   =
--                                                            =
--                                                            =
-- This file contains MIB Definitions for extended management =
-- of Sync Research DFRAP Product (DDS product with integral  =
-- agent).                                                    =
--                                                            =
-- This MIB is copyrighted by Sync Research (1998, 1999).     =
-- Permission is granted to the general public to use this    =
-- file for management of TyLink Products.                    =
--                                                            =
-- Updates to this Enterprise MIB may be obtained from        =
-- Sync Research Customer Service 1-800-828-2780.             =
--                                                            =

DFRAP-MIB DEFINITIONS ::= BEGIN

   IMPORTS

      DisplayString
         FROM SNMPv2-TC
      Counter, TimeTicks, IpAddress, internet, Gauge
         FROM RFC1155-SMI
      TRAP-TYPE
         FROM RFC-1215
      OBJECT-TYPE
         FROM RFC-1212;

   --  This MIB module uses the extended OBJECT-TYPE macro.

   private     OBJECT IDENTIFIER ::= { internet 4 }
   enterprises OBJECT IDENTIFIER ::= { private 1 }
   sync        OBJECT IDENTIFIER ::= { enterprises 485 }
   dfrap       OBJECT IDENTIFIER ::= { sync 6 }


   -- textual conventions

       --DisplayString ::=
       --    OCTET STRING
       -- This data type is used to model textual information taken
       -- from the NVT ASCII character set.  By convention, objects
       -- with this syntax are declared as having
       --
       --      SIZE (0..255)


-- *********************************************************************
--                     DFRAP ENTERPRISE SPECIFIC MIB
-- *********************************************************************


-- ======================================================================
--
--  The DFRAP MIB Tree
--      This MIB covers the Sync Research DFRAP, a DDS CSU for dedicated
--      or frame relay (FR) applications.  This product is managed 
--      via an integral agent.
--
--  The DFRAP MIB consists of three groups (plus Traps):
--      The SYSTEM group
--      The CONFIGURATION group
--      The DIAGNOSTICS group
--      The STATUS group
--      The PERFORMANCE group
--      The TRAP EVENT LOG group
--
--  The SYSTEM group
--      This group provides system level attributes of the node.
--               
--      The group consists of the following tables:
--          dfrapSysTable       - System level attributes
--          dfrapSysFeatureTable    - System level features
--
--  The CONFIGURATION group
--      This group provides for configuration of the node.
--
--      The group consists of the following tables:
--          dfrapCfgMgmtTable     - Configuration of management features
--             dfrapCfgIpTable        - IP configuration
--             dfrapCfgTftpTable      - TFTP configuration
--             dfrapCfgSnmpTable      - SNMP configuration
--                dfrapCfgSnmpMgrTable    - SNMP managers (TRAP destinations)
--             dfrapCfgCommTable      - Communication port configuration
--             dfrapCfgFrDLCITable    - DLCI configuration
--          dfrapCfgAppTable      - Application level configuration
--          dfrapCfgDdsTable      - DDS port configuration
--          dfrapCfgDteTable      - DTE port configuration
--          dfrapCfgFrTable       - Frame Relay configuration
--          dfrapCfgVnipTable     - VNIP configuration
--          dfrapCfgFrPerf        - Frame Relay performance configuration
--             dfrapCfgFrPerfDlciNamesTable        - Table of DLCI names
--             dfrapCfgFrPerfTimers                - ST and LT stats timers
--             dfrapCfgFrPerfUserProtocolsTable    - User-specified protocols
--             dfrapCfgFrPerfLTDlciFilterTable     - LT stats: DLCI filter
--             dfrapCfgFrPerfLTProtocolFilterTable - LT stats: protocol filter
--          dfrapCfgSecurityTable - Security configuration
--              
--  The DIAGNOSTICS group
--      This group provides for run-time diagnostics/control of the node.
--
--      The group consists of the following tables:
--          dfrapDiagUnitTable  - Unit level Diagnostics
--          dfrapDiagDdsTable   - DDS Port Diagnostics
--          dfrapDiagDteTable   - DTE port diagnostics
--          dfrapDiagBertTable  - BERT diagnostics
--          
--  The STATUS group
--      This group provides status information.
--
--      The group consists of the following tables:
--          dfrapVnipTopologyTable - VNIP topology
--          dfrapStatusMgmtTable   - Status of management channel
--          dfrapStatusDteTable    - DTE status
--          dfrapStatusDdsTable    - DDS status
--          dfrapStatusLedTable    - LED status
--          
--  The PERFORMANCE group
--      This group provides statistical information.
--
--      The group consists of the following tables:
--          dfrapPerfMgmtIp           - IP protocol stack statistics
--             dfrapPerfMgmtIpIFStatsTable   - Interface statistics
--             dfrapPerfMgmtIpIPStatsTable   - IP statistics
--             dfrapPerfMgmtIpICMPStatsTable - ICMP statistics
--             dfrapPerfMgmtIpUDPStatsTable  - UDP statistics
--             dfrapPerfMgmtIpTCPStatsTable  - TCP statistics
--          dfrapPerfThruput          - Thruput statistics
--             dfrapPerfThruputPerDlciTable  - Thruput per DLCI
--             dfrapPerfThruputPerIntfTable  - Thruput per Interface
--          dfrapPerfNetworkShortTerm - Short term DLCI statistics
--             dfrapPerfNetwProtoPerDlciTable   - Network protocol stats per DLCI
--             dfrapPerfNetwProtoTotalTable     - Total network protocol stats
--             dfrapPerfIpPerDlciTable          - IP stats per DLCI
--             dfrapPerfIpTotalTable            - Total IP stats
--             dfrapPerfIcmpPerDlciTable        - ICMP stats per DLCI
--             dfrapPerfIcmpTotalTable          - Total ICMP stats
--             dfrapPerfApplicationPerDlciTable - Application stats per DLCI
--             dfrapPerfApplicationTotalTable   - Total application stats
--             dfrapPerfRoutingPerDlciTable     - Routing stats per DLCI
--             dfrapPerfRoutingTotalTable       - Total Routing stats
--             dfrapPerfIpxPerDlciTable         - IPX stats per DLCI
--             dfrapPerfIpxTotalTable           - Total IPX stats
--             dfrapPerfSnaPerDlciTable         - SNA stats per DLCI
--             dfrapPerfSnaTotalTable           - Total SNA stats
--             dfrapPerfArpPerDlciTable         - ARP stats per DLCI
--             dfrapPerfArpTotalTable           - Total ARP stats
--          dfrapPerfNetworkLongTerm  - Long term DLCI statistics
--             dfrapPerfNetwLongTermTable       - Long term stats
--             dfrapPerfNetwLongTermAltTable    - Alternate format LTS
--
--      The TRAP EVENT LOG group
--             smperEventTrapLogTable - Event Log database access
--             smperEventLogClear  - Event Log clearing
--
--  The MIB also contains enterprise trap information:
--          dfrapTrap
--
-- =======================================================================


-- ========================
-- ==   SYSTEM group     ==
-- ========================

dfrapSystem      OBJECT IDENTIFIER ::= { dfrap 1 }


--
--       The dfrapSysTable
--              This table contains the system attributes of the DFRAP CSU.
--
      
dfrapSysTable      OBJECT IDENTIFIER ::= { dfrapSystem 1 }

dfrapSysType       OBJECT-TYPE
     SYNTAX      DisplayString (SIZE (0..255))
     ACCESS      read-only
     STATUS      mandatory
     DESCRIPTION
        "A textual description of the system model identifier.
         for example: SYNC-DFRAP"
     ::= { dfrapSysTable 1 }

dfrapSysSoftRev    OBJECT-TYPE
     SYNTAX      DisplayString (SIZE (0..10))
     ACCESS      read-only
     STATUS      mandatory
     DESCRIPTION
        "Displays the Software Revision installed in this node."
     ::= { dfrapSysTable 2 }

dfrapSysHardRev    OBJECT-TYPE
     SYNTAX      DisplayString (SIZE (0..10))
     ACCESS      read-only
     STATUS      mandatory
     DESCRIPTION
        "Displays the Hardware Revision of the node."
     ::= { dfrapSysTable 3 }

dfrapSysNumT1Installed    OBJECT-TYPE
     SYNTAX      INTEGER (0..2)
     ACCESS      read-only
     STATUS      mandatory
     DESCRIPTION
        "The number of T1 ports that are installed."
     ::= { dfrapSysTable 4 }

dfrapSysNumDdsInstalled    OBJECT-TYPE
     SYNTAX      INTEGER (0..2)
     ACCESS      read-only
     STATUS      mandatory
     DESCRIPTION
        "The number of DDS ports that are installed."
     ::= { dfrapSysTable 11 }

dfrapSysNumDteInstalled    OBJECT-TYPE
     SYNTAX      INTEGER (0..2)
     ACCESS      read-only
     STATUS      mandatory
     DESCRIPTION
        "The number of DTE ports that are
         installed."
     ::= { dfrapSysTable 5 }

dfrapSysNumMaintInstalled    OBJECT-TYPE
     SYNTAX      INTEGER (0..2)
     ACCESS      read-only
     STATUS      mandatory
     DESCRIPTION
        "The number of Async Maintenance/Console ports that are 
         installed."
     ::= { dfrapSysTable 6 }

dfrapSysName       OBJECT-TYPE
     SYNTAX      DisplayString (SIZE (0..15))
     ACCESS      read-write
     STATUS      mandatory
     DESCRIPTION
        "The user supplied name of the node.  This object
         does not affect operation, but may be useful
         for network management."
     ::= { dfrapSysTable 7 }

dfrapSysSerialNo      OBJECT-TYPE
     SYNTAX      DisplayString (SIZE (0..12))
     ACCESS      read-only
     STATUS      mandatory
     DESCRIPTION
        "The serial number of the board."
     ::= { dfrapSysTable 8 }

dfrapSysResetNode    OBJECT-TYPE
     SYNTAX      INTEGER
     {
           reset-node (321)
     }
     ACCESS      write-only
     STATUS      mandatory
     DESCRIPTION
        "Command to reset the node. NODE WILL BE OFF-LINE AND 
         USER DATA WILL BE INTERRUPTED FOR APPROXIMATELY 15 
         SECONDS. Full network recovery may take longer. "
     ::= { dfrapSysTable 9 }

dfrapSysAmtMemoryInstalled    OBJECT-TYPE
     SYNTAX      INTEGER
     ACCESS      read-only
     STATUS      mandatory
     DESCRIPTION
        "The amount of memory (RAM) installed (in megabytes)."
     ::= { dfrapSysTable 10 }

dfrapSysLocation       OBJECT-TYPE
     SYNTAX  DisplayString (SIZE (0..15))
     ACCESS  read-write
     STATUS  mandatory
     DESCRIPTION
        "The user supplied location of the node.  This
         object does not affect operation, but may be
         useful for network management."
     ::= { dfrapSysTable 12 }

dfrapSysContact        OBJECT-TYPE
     SYNTAX      DisplayString (SIZE (0..15))
     ACCESS      read-write
     STATUS      mandatory
     DESCRIPTION
        "The user supplied contact information for the
         node.  This object does not affect operation,
         but may be useful for network management."
     ::= { dfrapSysTable 13 }

dfrapSysPrompt        OBJECT-TYPE
     SYNTAX      DisplayString (SIZE (0..8))
     ACCESS      read-write
     STATUS      mandatory
     DESCRIPTION
        "Configurable Command Line Interface (CLI) prompt. CLI
         is the User Interface protocol used for directly 
         attached VT100 terminal access as well as Remote
         access via Telnet."
     ::= { dfrapSysTable 15 }                                

dfrapSysBootRev    OBJECT-TYPE
          SYNTAX      DisplayString (SIZE (0..10))
          ACCESS      read-only
          STATUS      mandatory
          DESCRIPTION
             "Displays the bootblock Software Revision 
              installed in this node."
          ::= { dfrapSysTable 16 }


--       The dfrapSysFeatureTable
--              This table contains the system features of the DFRAP CSU.
--
--       This is a SUPERSET.  If using this as a model, after you copy
--       and paste, delete the ones that are inappropriate.

dfrapSysFeatureTable      OBJECT IDENTIFIER ::= { dfrapSystem 2 }

dfrapSysSLIPSupported     OBJECT-TYPE
     SYNTAX      DisplayString (SIZE (0..10))
     ACCESS      read-only
     STATUS      mandatory
     DESCRIPTION
        "Shows whether the unit has SLIP (Serial Line IP) capability.
         SLIP is a method for out-of-band management that connects
         through the asynchronous terminal port."
     ::= { dfrapSysFeatureTable 1 }

dfrapSysPPPSupported     OBJECT-TYPE
     SYNTAX      DisplayString (SIZE (0..10))
     ACCESS      read-only
     STATUS      mandatory
     DESCRIPTION
        "Shows whether the unit has PPP (Point to Point protocol)
         capability. PPP is a method for out-of-band management 
         that connects through the asynchronous terminal port."
     ::= { dfrapSysFeatureTable 2 }

dfrapSysRDOSupported     OBJECT-TYPE
     SYNTAX      DisplayString (SIZE (0..10))
     ACCESS      read-only
     STATUS      mandatory
     DESCRIPTION
        "Shows whether the unit has Remote Dial Out capability."
     ::= { dfrapSysFeatureTable 3 }

dfrapSysETHSupported     OBJECT-TYPE
     SYNTAX      DisplayString (SIZE (0..10))
     ACCESS      read-only
     STATUS      mandatory
     DESCRIPTION
        "Shows whether the unit has direct Ethernet capability."
     ::= { dfrapSysFeatureTable 4 }

dfrapSysTKRSupported     OBJECT-TYPE
     SYNTAX      DisplayString (SIZE (0..10))
     ACCESS      read-only
     STATUS      mandatory
     DESCRIPTION
        "Shows whether the unit has direct Token Ring capability."
     ::= { dfrapSysFeatureTable 5 }

dfrapSysExtTimSupported     OBJECT-TYPE
     SYNTAX      DisplayString (SIZE (0..10))
     ACCESS      read-only
     STATUS      mandatory
     DESCRIPTION
        "Shows whether the unit has External Timing capability.
         This is the ability to derive WAN timing from the DTE port."
     ::= { dfrapSysFeatureTable 6 }

dfrapSysBRISupported     OBJECT-TYPE
     SYNTAX      DisplayString (SIZE (0..10))
     ACCESS      read-only
     STATUS      mandatory
     DESCRIPTION
        "Shows whether the unit has BRI (ISDN Basic Rate) capability."
     ::= { dfrapSysFeatureTable 7 }

dfrapSysSelDTESupported     OBJECT-TYPE
     SYNTAX      DisplayString (SIZE (0..10))
     ACCESS      read-only
     STATUS      mandatory
     DESCRIPTION
        "Shows whether the unit has a Selectable DTE interface.
         This being the ability to select amongst various electrical 
         interface formats (V.35, RS449, RS232, etc.) via software."
     ::= { dfrapSysFeatureTable 8 }

dfrapSysMLSupported     OBJECT-TYPE
     SYNTAX      DisplayString (SIZE (0..10))
     ACCESS      read-only
     STATUS      mandatory
     DESCRIPTION
        "Shows whether the unit supports MLs (out-of-band management 
         links). N/A to frame relay networks."
     ::= { dfrapSysFeatureTable 9 }

dfrapSysNumDlcisSupported     OBJECT-TYPE
     SYNTAX      INTEGER
     ACCESS      read-only
     STATUS      mandatory
     DESCRIPTION
        "Shows how many DLCIs can be monitored for frame-based 
         statistics. The unit will pass an unlimited number of 
         DLCIs but will only collect statistics on this number 
         (first come first served)."
     ::= { dfrapSysFeatureTable 10 }

dfrapSysLTFNumDlcis     OBJECT-TYPE
     SYNTAX      INTEGER
     ACCESS      read-only
     STATUS      mandatory
     DESCRIPTION
        "Shows how many DLCIs can be specified
         in the Long Term Statistics Filter."
     ::= { dfrapSysFeatureTable 11 }

dfrapSysLTFNumProtocols     OBJECT-TYPE
     SYNTAX      INTEGER
     ACCESS      read-only
     STATUS      mandatory
     DESCRIPTION
        "Shows how many protocols can be specified
         in the Long Term Statistics Filter."
     ::= { dfrapSysFeatureTable 12 }

dfrapSysNumUserProtocols     OBJECT-TYPE
     SYNTAX      INTEGER
     ACCESS      read-only
     STATUS      mandatory
     DESCRIPTION
        "Shows how many protocols can be defined by the user.
         The user configures TCP/UDP ports which can be monitored
         as protocols.  They are available for short term or
         long term statistics monitoring."
     ::= { dfrapSysFeatureTable 13 }

dfrapSysNumSnmpMgrs     OBJECT-TYPE
     SYNTAX      INTEGER
     ACCESS      read-only
     STATUS      mandatory
     DESCRIPTION
        "Shows how many SNMP managers can be programmed in the
         table dfrapCfgSnmpMngrTable. These managers are sent TRAPs."
     ::= { dfrapSysFeatureTable 14 }

dfrapSysNumDlciNames     OBJECT-TYPE
     SYNTAX      INTEGER
     ACCESS      read-only
     STATUS      mandatory
     DESCRIPTION
        "Shows how many DLCI names can be defined by the user
         in the table dfrapCfgFrPerfDlciNamesTable."
     ::= { dfrapSysFeatureTable 15 }



-- =========================
-- == CONFIGURATION group ==
-- =========================

dfrapConfiguration   OBJECT IDENTIFIER ::= { dfrap 2 }


--
--       The Management Configuration Table
--              This table contains the management-related
---             Configuration information for the DFRAP DDS DSU.

dfrapCfgMgmtTable   OBJECT IDENTIFIER ::= { dfrapConfiguration 1 }


--
--       The IP Configuration Table
--              This table contains the Configuration for Maintenance Port
--              when in IP mode on the DFRAP DDS DSU.

dfrapCfgIpTable OBJECT IDENTIFIER ::= { dfrapCfgMgmtTable 1 }
 
dfrapCfgIpMyIP   OBJECT-TYPE
     SYNTAX      IpAddress
     ACCESS      read-write
     STATUS      mandatory
     DESCRIPTION
        "The IP address for this node."
     ::= { dfrapCfgIpTable 1 }
 
dfrapCfgIpPeerIP   OBJECT-TYPE
     SYNTAX      IpAddress
     ACCESS      read-write
     STATUS      mandatory
     DESCRIPTION
        "This parameter is not used internally by
         the unit. It is intended to identify either
         the device directly connected to the SLIP
         port or, in Frame Relay applications, the
         address of the primary network management 
         station."
     ::= {dfrapCfgIpTable 2 }
 
dfrapCfgIpMask   OBJECT-TYPE
     SYNTAX      IpAddress
     ACCESS      read-write
     STATUS      mandatory
     DESCRIPTION
        "The IP Subnet Mask (eg 255.255.255.0). This
         parameter should be consisent with the IP
         subnet address setting of the external
         internetworking equipment (router/frad)."
      ::= { dfrapCfgIpTable 3 }
 
dfrapCfgIpMaxMTU OBJECT-TYPE
     SYNTAX      INTEGER  (1..1500)
     ACCESS      read-write
     STATUS      mandatory
     DESCRIPTION
        "The Maximum Transmission Unit is the size of the
         largest IP packet supported (including header).
         This value should be set to the lowest value supported 
         by any equipment in the transmission path.
         For Frame Relay management the typical value is 1500. 
         For SLIP management the typical value is 1006."
     ::= { dfrapCfgIpTable 4 }

dfrapCfgIpChannel   OBJECT-TYPE
     SYNTAX      INTEGER
     {
           none           (1),
           slip-port      (2),
           in-band-dlci   (3)
      }
      ACCESS      read-only
      STATUS      mandatory
      DESCRIPTION
         "This is the method by which IP traffic is being carried.
          Either via the SLIP port or a DLCI.  This reflects how
          your Management scheme is configured (read only)."
      ::= { dfrapCfgIpTable 5 }

dfrapCfgIpTelnetEnable   OBJECT-TYPE
      SYNTAX      INTEGER
      {
           enable-telnet  (1),
           disable-telnet (2)
      }
      ACCESS      read-write
      STATUS      mandatory
      DESCRIPTION
         "Enables/Disables the telnet feature.
          (1) enable-telnet
          (2) disable-telnet"
      ::= { dfrapCfgIpTable 6 }

dfrapCfgIpTelnetAutoLogOut   OBJECT-TYPE
      SYNTAX      INTEGER
      {
          autologout-at-15-minutes (1),
          disable-autologout       (2),
          autologout-at-3-minutes  (3),
          autologout-at-5-minutes  (5),
          autologout-at-10-minutes (10),
          autologout-at-30-minutes (30),
          autologout-at-60-minutes (60)
      }
      ACCESS      read-write
      STATUS      mandatory
      DESCRIPTION
         "If Telnet Auto logout is enabled the unit
          will automatically disconnect from a Telnet
          session after a period of inactivity (absence 
          of key strokes from remote terminal). 
          (2) disables this feature
          (1) auto logout after 15 minutes inactivity
          (3) auto logout after 3 minutes inactivity
          (5) auto logout after 5 minutes inactivity
          (10) auto logout after 10 minutes inactivity
          (30) auto logout after 30 minutes inactivity
          (60) auto logout after 60 minutes inactivity"
       ::= { dfrapCfgIpTable 7 }


--
--       The TFTP Configuration Table
--              This table contains the Configuration for the TFTP
--              support on the DFRAP DDS DSU.

dfrapCfgTftpTable OBJECT IDENTIFIER ::= { dfrapCfgMgmtTable 2 }

dfrapCfgTftpInitiate OBJECT-TYPE
     SYNTAX DisplayString (SIZE (0..8))
     ACCESS write-only
     STATUS mandatory
     DESCRIPTION
        "Setting this object to a value that matches
         the TFTP Password will command the unit to
         attempt a TFTP file transfer. A TFTP profile
         including host ip address, dlci value, interface, 
         and file name must first be configured."
     ::= {dfrapCfgTftpTable 1}

dfrapCfgTftpIpAddress   OBJECT-TYPE
     SYNTAX     IpAddress
     ACCESS     read-write
     STATUS     mandatory
     DESCRIPTION
        "The IP address of the TFTP host with which
         the unit will attempt to establish a TFTP
         session when initiated."
     ::= {dfrapCfgTftpTable 2}
   
dfrapCfgTftpFilename OBJECT-TYPE
     SYNTAX DisplayString (SIZE (0..80))
     ACCESS read-write
     STATUS mandatory
     DESCRIPTION
        "The name of the file located on the TFTP host
         that will be transferred to the unit. Typically 
         this is a product-specific software image that
         will be programmed into unit FLASH. The unit 
         provides several levels of checking to verify 
         the validity and integrity of this file. 
         Note - depending upon the host, this file name 
         may be case sensitive."
     ::= {dfrapCfgTftpTable 3}

dfrapCfgTftpInterface OBJECT-TYPE
     SYNTAX      INTEGER
     {
          dte-interface  (1),
          dds-interface   (2),
          slip-interface (3)
     }
     ACCESS read-write
     STATUS mandatory
     DESCRIPTION
        "The physical interface out which the TFTP host
         is located. This parameter is only required for
         Piggyback and Bi-directional in-band frame relay
         managed applications. With Local and Remote in-band 
         and SLIP-based applications the interface is known
         and Sets to this will be ignored."
     ::= {dfrapCfgTftpTable 4}

dfrapCfgTftpDlci OBJECT-TYPE
     SYNTAX INTEGER (-1..63487)
     ACCESS read-write
     STATUS mandatory
     DESCRIPTION
        "The local DLCI value on which the TFTP host can be 
         reached. This DLCI should be active prior to 
         initiating the TFTP session. This parameter is only 
         required for Piggyback in-band frame relay managed 
         applications. With Private management (Local, Remote 
         or Bi-directional in-band applications) the DLCI is
         known and will be reported here (Sets will be ignored). 
         In SLIP-based applications the DLCI value is not 
         applicable and a value of -1 is reported (Sets will 
         be ignored)."
     ::= {dfrapCfgTftpTable 5}

dfrapCfgTftpStatus OBJECT-TYPE
     SYNTAX INTEGER
     {
          inactive          (1),
          requested         (2),
          transferring      (3),
          programming       (4),
          transfer-aborted  (5),
          host-no-reply     (6),
          file-not-found    (7),
          invalid-file      (8),
          corrupt-file      (9),
          successful        (10)
      }
      ACCESS read-write
      STATUS mandatory
      DESCRIPTION
         "The status of current or most recent TFTP operation.
          (1) TFTP inactive, sets to this value will abort the session
          (2) TFTP requested
          (3) TFTP transferring
          (4) TFTP programming FLASH - unit will reset 
          (5) TFTP fail: session aborted by user or error condition
          (6) TFTP fail: host no reply -  verify TFTP profile and host
          (7) TFTP fail: file not found - verify file name and location
          (8) TFTP fail: invalid file - file rejected by unit as inappropriate
          (9) TFTP fail: corrupt file - session terminated due to checksum error
          (10) TFTP transfer successful and file has been verified"
       ::= {dfrapCfgTftpTable 6}

dfrapCfgTftpNumBytes OBJECT-TYPE
          SYNTAX Counter
          ACCESS      read-only
          STATUS      mandatory
          DESCRIPTION
            "The number of Bytes from the ROM image that have been 
             TFTP'd to the unit"
          ::= {dfrapCfgTftpTable 7}


--
--       The SNMP Configuration Table
--              This table contains the Configuration for the SNMP
--              support on the DFRAP DDS DSU.

dfrapCfgSnmpTable OBJECT IDENTIFIER ::= { dfrapCfgMgmtTable 3 }

dfrapCfgSnmpFrTrap   OBJECT-TYPE
     SYNTAX      INTEGER
     {
         enabled        (1),
         disabled       (2)
     }
     ACCESS      read-write
     STATUS      mandatory
     DESCRIPTION
         "Controls whether or not the Frame Relay DLCI
          status change traps are issued.  These traps are
          dfrapDLCIActiveTrap and dfrapDLCIInactiveTrap.
          When dfrapCfgSnmpFrTrap is enabled (1), a trap
          will be sent each time an individual DLCI changes
          status between active and inactive. When
          dfrapCfgSnmpFrTrap is disabled (2), the traps
          are not sent."
     ::= { dfrapCfgSnmpTable 1 }
 
dfrapCfgSnmpTrapMuting    OBJECT-TYPE
     SYNTAX      INTEGER (0..10080)
     ACCESS      read-write
     STATUS      mandatory
     DESCRIPTION
        "Controls whether Traps are Sent or Muted. If traps
         are Muted then a single trap (#75) will be periodically
         issued by the unit at the programmed frequency. If Muting
         is Disabled then the full set of Trap events are reported
         accordingly.
         (0) Disable Trap Muting
         (30-10080) Trap Muting frequency in minutes."
     ::= { dfrapCfgSnmpTable 3 }

dfrapCfgSnmpUtilTrapEnable  OBJECT-TYPE
     SYNTAX  INTEGER
    {
        enable  (1),
        disable (2)
    }
     ACCESS  read-write
     STATUS  mandatory
     DESCRIPTION
        "Enables or disables the sending of per-DLCI
         utilization traps.
         (1) enable utilization traps
         (2) disable utilization traps "
     ::= { dfrapCfgSnmpTable 6 }
     
dfrapCfgSnmpMgrClearN   OBJECT-TYPE
        SYNTAX  INTEGER
        ACCESS  write-only
        STATUS  mandatory
        DESCRIPTION
           " Deletes the number of entries in the dfrapCfgSnmpMgrTable
             indicated by the value.  If the value is a positive number
             the entries will be deleted starting from the first entry.
             If the value is negative the entries will be deleted 
             starting from the last entry. "
        ::= { dfrapCfgSnmpTable 7 }
         
dfrapCfgSnmpMgrTable   OBJECT-TYPE
     SYNTAX   SEQUENCE OF DfrapCfgSnmpMgrEntry
     ACCESS   not-accessible
     STATUS   mandatory
     DESCRIPTION
        "The table of SNMP manager profiles to which
         traps are sent. In all managed modes an SNMP
         trap mangager's ip address is required as a 
         minimum. Additionally for Piggyback managed
         units the DLCI and interface must also be 
         configured appropriately. For Local, Remote
         and SLIP-based management, the DLCI and
         interface are implied and need not be 
         configured as part of this profile."
     ::= { dfrapCfgSnmpTable 2 }

dfrapCfgSnmpMgrEntry   OBJECT-TYPE
     SYNTAX   DfrapCfgSnmpMgrEntry
     ACCESS   not-accessible
     STATUS   mandatory
     DESCRIPTION
        "The SNMP trap manager profiles to which the unit
         sends TRAPs."
     INDEX { dfrapCfgSnmpMgrIndex }
     ::= { dfrapCfgSnmpMgrTable 1 }

DfrapCfgSnmpMgrEntry ::=
     SEQUENCE
     {
         dfrapCfgSnmpMgrIndex       INTEGER,
         dfrapCfgSnmpMgrIP          IpAddress,
         dfrapCfgSnmpMgrInterface   INTEGER,
         dfrapCfgSnmpMgrDlci        INTEGER
     }

dfrapCfgSnmpMgrIndex OBJECT-TYPE
     SYNTAX   INTEGER
     ACCESS   read-only
     STATUS   mandatory
     DESCRIPTION
        "The index to the list of SNMP managers receiving TRAPs."
     ::= { dfrapCfgSnmpMgrEntry 1 }

dfrapCfgSnmpMgrIP   OBJECT-TYPE
     SYNTAX      IpAddress
     ACCESS      read-write
     STATUS      mandatory
     DESCRIPTION
        "The IP address of a SNMP manager to receive this node's TRAPs.
         Setting this value to 0.0.0.0 will disable the issuance of
         traps to the indexed manager."
     ::= { dfrapCfgSnmpMgrEntry 2 }

dfrapCfgSnmpMgrInterface OBJECT-TYPE
     SYNTAX      INTEGER
     {
         dte-interface  (1),
         dds-interface  (2),
         slip-interface (3)
     }
     ACCESS      read-write
     STATUS      mandatory
     DESCRIPTION
            "The interface out which the indexed trap manager can be
         reached. This entry is required in Piggyback and Bi-directional 
         in-band managed applications. In Local, Remote and SLIP-based
         applications, the interface is known and this parameter is
         ignored.

             When the node is configured for SLIP, a GET on this MIB
         object will return slip-interface(3) and a SET of this MIB
         object to slip-interface(3) is allowed but unnecessary.

             When the node is not configured for SLIP, this MIB
         object can be SET to dte-interface(1) or dds-interface(2);
         slip-interface(3) would be rejected."
     ::= { dfrapCfgSnmpMgrEntry 3 }

dfrapCfgSnmpMgrDlci OBJECT-TYPE
     SYNTAX      INTEGER
     ACCESS      read-write
     STATUS      mandatory
     DESCRIPTION
        "The DLCI out which the indexed trap manager can be
         reached. This entry is required in Piggyback in-band 
         managed applications. In Private in-band applications
         the DLCI is known and Sets to this parameter will be 
         ignored. In SLIP mode the DLCI is not applicable,
         Sets will be ignored and a -1 will be returned as the 
         DLCI value."
     ::= { dfrapCfgSnmpMgrEntry 4 }



--
--       The Communications Port Configuration Table
--              This table contains the Configuration for the comm port.

dfrapCfgCommTable OBJECT IDENTIFIER ::= { dfrapCfgMgmtTable 4 }

dfrapCfgCommMode      OBJECT-TYPE
     SYNTAX      INTEGER
     {
         vt100     (1),
         slip      (2)
     }
     ACCESS      read-write
     STATUS      mandatory
     DESCRIPTION
        "The protocol running on the Maintenance/Comm port (console).
         Setting this to SLIP mode will automatically disable
         in-band management if it's enabled.
         (1) VT100 for directly attached async terminal
         (2) SLIP - Serial Line IP out-of-band management"
     ::= { dfrapCfgCommTable 1 }

dfrapCfgCommBaud OBJECT-TYPE
     SYNTAX      INTEGER
     {
         baud-2400   (2),
         baud-9600   (4),
         baud-19200  (5),
         baud-38400  (6)
     }
     ACCESS      read-write
     STATUS      mandatory
     DESCRIPTION
        "Asynchronous baud rate for the Maintenance/Comm port 
         (Console). This must be configured to match either the 
         VT100 compatible terminal or the SLIP Terminal Server 
         depending upon the Comm port mode. 
         (2) baud-2400 
         (4) baud-9600
         (5) baud-19200
         (6) baud-38400"
     ::= { dfrapCfgCommTable 2 }

dfrapCfgCommDataBits OBJECT-TYPE
     SYNTAX      INTEGER
     {
         databits-7 (1),
         databits-8 (2)
     }
     ACCESS      read-write
     STATUS      mandatory
     DESCRIPTION
        "Asynchronous data format for the Maintenance/Comm port 
         (Console). This must be configured to match either the 
         VT100 compatible terminal or the SLIP Terminal Server 
         depending upon the Comm port mode.
         (1) 7 databits per character
         (2) 8 databits per character"
     ::= { dfrapCfgCommTable 3 }

dfrapCfgCommStopBits OBJECT-TYPE
     SYNTAX      INTEGER
     {
         stopbits-1 (1),
         stopbits-1-5 (2),
         stopbits-2 (3)
     }
     ACCESS      read-write
     STATUS      mandatory
     DESCRIPTION
        "Asynchronous intercharacter protocol for the Maintenance/Comm 
         port (Console). This must be configured to match either the 
         VT100 compatible terminal or the SLIP Terminal Server 
         depending upon the Comm port mode.
         (1) 1 stopbit 
         (2) 1.5 stopbits 
         (3) 3 stopbits"
     ::= { dfrapCfgCommTable 4 }

dfrapCfgCommParity OBJECT-TYPE
     SYNTAX      INTEGER
     {
         no-parity   (1),
         odd-parity  (2),
         even-parity (3)
     }
     ACCESS      read-write
     STATUS      mandatory
     DESCRIPTION
        "Asynchronous parity checking protocol for the 
         Maintenance/Comm port (Console). This must be configured 
         to match either the VT100 compatible terminal or the SLIP 
         Terminal Server depending upon the Comm port mode.  
         (1) no parity
         (2) odd-parity 
         (3) even-parity"
     ::= { dfrapCfgCommTable 5 }

dfrapCfgCommFlowCtrl OBJECT-TYPE
     SYNTAX      INTEGER
     {
         no-flow-control (1)
     }
     ACCESS      read-write
     STATUS      mandatory
     DESCRIPTION
        "Flow Control for the Maintenance/Comm port (Console).  
         (1) no flow control supported."
     ::= { dfrapCfgCommTable 6 }



--
--       The DLCI Configuration Table
--              This table contains the Configuration for DLCI support.

dfrapCfgFrDLCITable OBJECT IDENTIFIER ::= { dfrapCfgMgmtTable 5 }

dfrapCfgFrDLCIMode  OBJECT-TYPE
     SYNTAX      INTEGER
     {
         inactive        (1),
         local           (2),
         remote          (3),
         bidirectional   (4),
         piggyback       (5),
         fixed-dce       (6)
     }
     ACCESS      read-write
     STATUS      mandatory
     DESCRIPTION
        "In-band Frame Relay management mode. A variety of options
         exist which are differentiated by how PVCs can be provisioned
         to manage the unit and the resulting impact to the logical
         processing of Link Management Protocol messages (LMI spoofing 
         and sourcing). The unit is designed to support these management 
         modes even in non-provisioned or failed frame relay networks.
         This setting also has implications upon how networking protocols 
         such as ARP and InARP are handled by the unit. 
         (1) inactive: in-band management is not enabled
         (2) local DLCI mode: in-band managed using a private dedicated DLCI 
             accessible via the DTE port only. A DLCI value is configured 
             which, through LMI spoofing, will only be visible to the DTE 
             equipment and need not be provisioned on the WAN. All traffic on
             this DLCI will be terminated by the unit.
         (3) remote DLCI mode: in-band managed using a private dedicated DLCI 
             accessible via the WAN port only. A DLCI value is configured 
             which, through LMI spoofing, will only be visible from the WAN 
             side and will not be seen by any DTE equipment. All traffic on
             this DLCI will be terminated by the unit.
         (4) bidirectional mode: in-band managed using a private dedicated DLCI 
             accessible through either port. A DLCI value is configured 
             which is expected to be fully provisioned in the frame relay 
             network but dedicated to the management function of this particular 
             unit. All traffic on this DLCI will be terminated by the unit.
         (5) piggyback mode: in-band managed using any DLCI on any interface. A
             DLCI value is defined that becomes the default DLCI that will be
             maintained by the unit during network or LMI failure conditions. 
             The unit will terminate and respond accordingly to management and
             networking data while transparently passing on user data.
         (6) fixed DCE mode: special mode of operation to support frame relay
             applications that do not include a switch (frame relay DCE). The 
             unit will independently respond to LMI requests on each interface
             and will provision the configured DLCI to each Frame Relay DTE device.
             Except for this, the unit behaves like piggyback."
          ::= { dfrapCfgFrDLCITable 1 }

dfrapCfgFrDLCIValue  OBJECT-TYPE
     SYNTAX      INTEGER (16..63487)
     ACCESS      read-write
     STATUS      mandatory
     DESCRIPTION
        "If in-band management is being used this DLCI value should be defined. 
         In all modes of in-band management with the LMI Sourcing feature enabled 
         the unit may provision this DLCI during LMI failure to facilitate management 
         access. In Private modes (Local, Remote, and Bidirectional) this is the 
         dedicated DLCI for management data and address resolution protocols - all 
         other traffic on this DLCI will be discarded. In Piggyback mode this DLCI 
         is treated like all others except during LMI failure sourcing when it may
         be provisioned by the unit. In Piggyback mode if InARP is enabled on a single 
         DLCI then this value defines that DLCI."
          ::= { dfrapCfgFrDLCITable 2 }

dfrapCfgFrDLCIEncap   OBJECT-TYPE
     SYNTAX      INTEGER
     {
         rfc1490        (1),
         rfc1490snap    (2),
         auto           (3),
         cisco          (4)
     }
     ACCESS      read-write
     STATUS      mandatory
     DESCRIPTION
        "This is the protocol used for enacapsulating and formatting
         ip data for Frame Relay transmission. This setting is specific to 
         management data to and from the unit.
         (1)RFC1490 - per IETF standard with Network Level 
            Protocol ID (NLPID) set for IP encapsulation.
         (2)RFC1490 SNAP/IP - per IETF standard with NLPID set 
            for Sub-Network Access Protocol (SNAP).
         (3)auto - adjusts to either of these encapsulation techniques
            as required. 
         (4)Cisco - proprietary encapsulation (4-byte header)."
          ::= { dfrapCfgFrDLCITable 3 }

dfrapCfgFrDLCIMgmtDE   OBJECT-TYPE
     SYNTAX      INTEGER
     {
         no-DE-bit-0     (1),
         yes-DE-bit-1    (2)
     }
     ACCESS      read-write
     STATUS      mandatory
     DESCRIPTION
        "Provides user control over the state of the Frame Relay Discard
         Eligibility bit of all management frames generated by
         the unit. Frames marked DE=1 are more likely to be dropped in a 
         congested Frame Relay network than those that are DE=0. Heavily 
         congested circumstances can cause both to be dropped. Additionally,
         frames marked DE=0 may get re-marked to DE=1 by intervening
         equipment.
         (1) DE bit cleared to 0: frame is not discard eligible
         (2) DE bit set to 1: frame is discard eligible"
          ::= { dfrapCfgFrDLCITable 4 }

--
--       The Application Configuration Table
--              This table contains the Application (system) Configuration.

dfrapCfgAppTable   OBJECT IDENTIFIER ::= { dfrapConfiguration 2 }

dfrapCfgAppClockSource OBJECT-TYPE
     SYNTAX      INTEGER
     {
         internal (1),
         network  (2),
         dte      (3)
     }
     ACCESS      read-write
     STATUS      mandatory
     DESCRIPTION
        "Timing source for transmission of data towards the WAN
         and for the generation of DTE clocking. There should be 
         only one source per end-to-end WAN link.  Unit is typically
         network timed in a point-to-network application.
         (1) internal: derive timing from a high-stability on-board
             crystal oscillator.
         (2) network: or Loop timing, derive timing from the signal
             received at the WAN interface
         (3) dte: derive timing from the clock presented by the DTE
             equipment on the Terminal Timing(TT)/Transmit Clock 
             External (TCE) leads. This setting expects the DTE timing 
             mode to be Loop 1 and the DTE device to be generating a 
             clock at the DTE data rate."  
     ::= { dfrapCfgAppTable 1 }

dfrapCfgAppCircuitId    OBJECT-TYPE
     SYNTAX      DisplayString (SIZE (0..29))
     ACCESS      read-write
     STATUS      mandatory
     DESCRIPTION
        "Alphanumeric circuit identifier may be provided by the service 
         provider for reference or assigned arbitrarily per user
         requirements."
     ::= { dfrapCfgAppTable 2 }

dfrapCfgAppType    OBJECT-TYPE
     SYNTAX      INTEGER
     {
         dedicated   (1),
         frame-relay (2)   
     } 
     ACCESS      read-write
     STATUS      mandatory
     DESCRIPTION
        "This unit provides many features specifically adapted 
         to Frame Relay transmission links; this includes diagnostic 
         utilities, statistical analysis, protocol trends, quality of 
         service reporting, and in-band SNMP management. If the unit 
         will be operating in a Frame Relay network the Application Type
         must be set to Frame Relay to enable these features. To 
         operate in a non-Frame Relay network or to bypass this feature
         set the unit may be placed in Dedicated mode and will emulate a
         more familiar DSU/CSU. Note - changing this value will 
         automatically change the Application Format setting and vice 
         versa.
         (1) dedicated: protocol-independent transparent DSU/CSU
         (2) Frame Relay: Frame and protocol aware DSU/CSU"
      ::= { dfrapCfgAppTable 3 }

dfrapCfgAppFormat OBJECT-TYPE
      SYNTAX      INTEGER
      {
          cbo         (1),
          hdlc        (2)
      }
      ACCESS      read-write
      STATUS      mandatory
      DESCRIPTION
          "Refer to Application Type. Frame Relay is based upon
           HDLC framing. To operate in a Frame Relay application
           the Format must be set for HDLC. To operate in a
           protocol-independent application the Format must be 
           set for Constant Bit Operation (CBO). Note - changing 
           this value will automatically change the Application 
           Type setting and vice versa
           (1) CBO: protocol-independent transparent DSU/CSU
           (2) HDLC: Frame and protocol aware DSU/CSU"
     ::= { dfrapCfgAppTable 4 }

dfrapCfgAppLpbkTimeout OBJECT-TYPE
     SYNTAX      INTEGER (0..1440)
     ACCESS      read-write
     STATUS      mandatory
     DESCRIPTION
        "The length of time a service-impacting loopback
         or diagnostic utility may run before automatically 
         returning to normal operation. This setting will
         override any alternatively timed tests (such as 
         VBERT).
         (0) Loopbak Timeout Disabled
         (1-1440) Loopback Timeout"
     ::= { dfrapCfgAppTable 5 }

dfrapCfgAppPerfBuffLimit OBJECT-TYPE
     SYNTAX      INTEGER (0..512)
     ACCESS      read-write
     STATUS      mandatory
     DESCRIPTION
        "This value controls the throttling mechanism
         used to determine the optimum level of statistical
         processing versus managability of the unit. The
         lower the value (1 - 128), the unit becomes more
         responsive to management commands during very heavy
         utilization at the possible expense of statistical 
         accuracy.  The larger the value (129 - 512), the more 
         accurate the DFRAP performs statistical analysis of the 
         frames but management may seem slow or unresponsive 
         during periods of very heavy link utilization.
         NOTE: A value of 0 disables statistical processing entirely."
     ::= { dfrapCfgAppTable 10 }

--
--       The DDS Configuration Table
--              This table contains the Configuration for the DDS port.

dfrapCfgDdsTable  OBJECT IDENTIFIER ::= { dfrapConfiguration 3 }

dfrapCfgDdsLoopRate OBJECT-TYPE
     SYNTAX      INTEGER
     {
         fifty-six      (1),
         sixty-four    (2)
     }
     ACCESS      read-write
     STATUS      mandatory
     DESCRIPTION
        "Provisioned DDS WAN data rate. This unit conforms
         to either 56K DDS service or 64K (72K with framing) 
         DDS service.
         (1) 56Kbps DDS 
         (2) 64Kbs DDS (72K loop rate)"
     ::= { dfrapCfgDdsTable 1 }

dfrapCfgDdsBPVThresholding OBJECT-TYPE
     SYNTAX      INTEGER 
     {
         thresholding-at-10E-4 (1),
         disable-thresholding (2)
     }
     ACCESS      read-write
     STATUS      mandatory
     DESCRIPTION
        "The unit may be configured to issue traps in response to
         Bipolar Violations (BPVs) received from the WAN. If enabled 
         the unit will issue a trap when more than 5 BPVs are detected 
         in a one-second interval and a follow-up trap when the BPV 
         threshold is no longer exceeded. BPVs that are part of network 
         control codes do not contribute to this feature.
         (1) BPV Trap Threshold is 10e-4
         (2) Disable BPV Traps"
     ::= { dfrapCfgDdsTable 2 }


--
--       The DTE Configuration Table
--              This table contains the DTE port Configuration
--              information.

dfrapCfgDteTable   OBJECT IDENTIFIER ::= { dfrapConfiguration 4 }

dfrapCfgDteIntfType    OBJECT-TYPE
     SYNTAX      INTEGER  
     {
         intf-v35       (3),
         intf-rs449     (4)
     }
     ACCESS        read-only
     STATUS        mandatory
     DESCRIPTION
        "The electrical interface for the DTE port
         (3) V.35 interface
         (4) RS-449 interface"
     ::= { dfrapCfgDteTable 1 }

dfrapCfgDteClockMode    OBJECT-TYPE
     SYNTAX      INTEGER  
     {
        clock-normal    (1),
        clock-invert    (2)
     }
     ACCESS        read-write
     STATUS        mandatory
     DESCRIPTION
        "This selection controls how the unit internally latches 
         the transmit data from the DTE. Normal will sample
         data with the rising edge of the selected TX Clock, 
         Invert will sample data with the falling edge of the 
         selected TX Clock. The TX Clock is selected using 
         CfgDteTiming. This clock invertion is most useful when 
         loop-2 timing is used - particularly at higher rates 
         and with long cable runs. Only in rare circumstances 
         will clock-invert be used with loop-1 timing. If the 
         DTE Interface TX statistics are indicating excessive 
         crc errors or aborts then changing this setting may have
         some benefit.
         (1) normal
         (2) invert"
     ::= { dfrapCfgDteTable 3 }

dfrapCfgDteTiming    OBJECT-TYPE
     SYNTAX      INTEGER  
     {
         loop-1  (1),
         loop-2  (2)
     }
     ACCESS        read-write
     STATUS        mandatory
     DESCRIPTION
        "Serial DTE Transmit Timing mode. Loop-1 (1) uses the clock  
         returned from the DTE (TT/TCE) to sample tx data, Loop-2 (2) 
         uses the clock (ST/TC) generated by the node to sample tx 
         data. Loop-1 is the preferred mode. Loop-2 timing could experience
         data errors at high rates or due to long DTE cable runs - may
         need to Invert the clock (see CfgDteClockMode).
         (1) Loop 1: external clock returned from DTE with data
         (2) Loop 2: internal clock used to sample incoming data"
     ::= { dfrapCfgDteTable 4 }


dfrapCfgDteRts         OBJECT-TYPE  
     SYNTAX       INTEGER
     {
         internal-held-active (1),
         external-from-dte (2)
     }
     ACCESS       read-write
     STATUS       mandatory
     DESCRIPTION
        "Controls the reporting of the status of the DTE's Request 
         to Send (RTS) control signal, specifically the generation 
         of traps in response to control signal state changes. If
         Internally Held Active, the unit will ignore the actual 
         status and always report this signal Active. If External, 
         the unit will reflect the status as driven by the DTE; as
         such, Traps will be generated due to change of state (these
         may be useful fora network manager's assessment of interface 
         status.
         (1) Internally Held Active     
         (2) Externally Presented from DTE"
     ::= { dfrapCfgDteTable 15 }

dfrapCfgDteDtr         OBJECT-TYPE  
     SYNTAX       INTEGER
     {
         internal-held-active (1),
         external-from-dte (2)
     }
     ACCESS       read-write
     STATUS       mandatory
     DESCRIPTION
        "Controls the reporting of the status of the DTE's Data 
         Terminal Ready (DTR) control signal, specifically the 
         generation of traps in response to control signal state 
         changes. If Internally Held Active, the unit will ignore 
         the actual status and always report this signal Active. If 
         External, the unit will reflect the status as driven by the 
         DTE; as such, Traps will be generated due to change of state 
         (these may be useful fora network manager's assessment of 
         interface status.
         (1) Internally Held Active     
         (2) Externally Presented from DTE"
     ::= { dfrapCfgDteTable 16 }

dfrapCfgDteDcdOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
        "Specifies the behavior of the Data Carrier Detect (DCD)
         control signal generated by the unit towards the DTE.
         (1) inactive always: signal is permanently INACTIVE.
         (2) active always: signal is permanently ACTIVE.
         (3) reflect WAN carrier: signal echoes the received signal status 
             from the WAN.
         (4) inactive with test mode: signal is ACTIVE during normal 
             data transfer and INACTIVE during diagnostic conditions 
             that interfere with data transfer from the DTE to the WAN.
         (5) follow RTS: signal echoes the status of RTS as processed 
             from the DTE. 
         (6) reflect carrier and RTS: signal is a logical AND between 
             RTS processed from the DTE and the received signal status 
             from the WAN. No signal received from the WAN or RTS INACTIVE 
             will cause this control signal to be asserted INACTIVE.
         (7) reflect sync and RTS: signal is a logical AND between RTS 
             processed from the DTE and the frame synchronization with the WAN. 
             Frame Synchronization is only applicable with 64K DDS service,
             otherwise this is equivalent to (6).
         (8) reflect LMI and carrier and RTS: signal is a logical AND 
             between RTS processed from the DTE and the carrier signal
             status from the WAN and LMI. If the unit is in an LMI 
             passthrough state then LMI is considered Active.
             LMI Inactivity timer must be non-zero for LMI to be declared 
             Inactive. In non-Frame Relay applications (type = dedicated)
             LMI will be presumed ACTIVE so this will setting is equivalent
             to (6).
         Note that there is a separate parameter for how the unit processes 
         RTS that is related to this function if options (4), (5), (6), or (7) 
         is selected, see CfgDteRts."
     ::= { dfrapCfgDteTable 18 }
 
dfrapCfgDteDsrOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
        "Specifies  the behavior of the Data Set Ready (DSR)
         control signal generated by the unit towards the DTE.
         (1) inactive always: signal is permanently INACTIVE.
         (2) active always: signal is permanently ACTIVE.
         (3) reflect WAN carrier: signal echoes the received signal status 
             from the WAN.
         (4) inactive with test mode: signal is ACTIVE during normal 
             data transfer and INACTIVE during diagnostic conditions 
             that interfere with data transfer from the DTE to the WAN.
         (5) follow RTS: signal echoes the status of RTS as processed 
             from the DTE. 
         (6) reflect carrier and RTS: signal is a logical AND between 
             RTS processed from the DTE and the received signal status 
             from the WAN. No signal received from the WAN or RTS INACTIVE 
             will cause this control signal to be asserted INACTIVE.
         (7) reflect sync and RTS: signal is a logical AND between RTS 
             processed from the DTE and the frame synchronization with the WAN. 
             Frame Synchronization is only applicable with 64K DDS service,
             otherwise this is equivalent to (6).
         (8) reflect LMI and carrier and RTS: signal is a logical AND 
             between RTS processed from the DTE and the carrier signal
             status from the WAN and LMI. If the unit is in an LMI 
             passthrough state then LMI is considered Active.
             LMI Inactivity timer must be non-zero for LMI to be declared 
             Inactive. In non-Frame Relay applications (type = dedicated)
             LMI will be presumed ACTIVE so this will setting is equivalent
             to (6).
         Note that there is a separate parameter for how the unit processes 
         RTS that is related to this function if options (4), (5), (6), or (7) 
         is selected, see CfgDteRts."
     ::= { dfrapCfgDteTable 19 }
 
dfrapCfgDteCtsOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
        "Specifies the behavior of the Clear to Send (CTS)
         control signal generated by the unit towards the DTE.
         (1) inactive always: signal is permanently INACTIVE.
         (2) active always: signal is permanently ACTIVE.
         (3) reflect WAN carrier: signal echoes the received signal status 
             from the WAN.
         (4) inactive with test mode: signal is ACTIVE during normal 
             data transfer and INACTIVE during diagnostic conditions 
             that interfere with data transfer from the DTE to the WAN.
         (5) follow RTS: signal echoes the status of RTS as processed 
             from the DTE. 
         (6) reflect carrier and RTS: signal is a logical AND between 
             RTS processed from the DTE and the received signal status 
             from the WAN. No signal received from the WAN or RTS INACTIVE 
             will cause this control signal to be asserted INACTIVE.
         (7) reflect sync and RTS: signal is a logical AND between RTS 
             processed from the DTE and the frame synchronization with the WAN. 
             Frame Synchronization is only applicable with 64K DDS service,
             otherwise this is equivalent to (6).
         (8) reflect LMI and carrier and RTS: signal is a logical AND 
             between RTS processed from the DTE and the carrier signal
             status from the WAN and LMI. If the unit is in an LMI 
             passthrough state then LMI is considered Active.
             LMI Inactivity timer must be non-zero for LMI to be declared 
             Inactive. In non-Frame Relay applications (type = dedicated)
             LMI will be presumed ACTIVE so this will setting is equivalent
             to (6).
         Note that there is a separate parameter for how the unit processes 
         RTS that is related to this function if options (4), (5), (6), or (7) 
         is selected, see CfgDteRts."
     ::= { dfrapCfgDteTable 20 }



--
--       The FrameRelay Configuration Table
--              This table contains the Configuration for the Frame Relay
--              support on the DFRAP DDS DSU.

dfrapCfgFrTable OBJECT IDENTIFIER ::= { dfrapConfiguration 5 }

dfrapCfgFrAddrLen  OBJECT-TYPE
     SYNTAX      INTEGER
     {
          twobytes       (1),
          threebytes     (2),
          fourbytes      (3)
     }
     ACCESS      read-write
     STATUS      mandatory
     DESCRIPTION
        "Shows the size that DLCI address field. This setting must
         correspond to the Frame Relay transmission format; typically
         Two bytes.
         (1) two byte DLCI address field
         (2) three byte DLCI address field
         (3) four byte DLCI address field"         
      ::= { dfrapCfgFrTable 1 }
 
dfrapCfgFrCrcMode  OBJECT-TYPE
     SYNTAX      INTEGER
     {
          discard        (1),
          passthru       (2)
     }
     ACCESS      read-write
     STATUS      mandatory
     DESCRIPTION
        "This defines the manner in which the unit handles HDLC
         protocol errors (crc errors) in a Frame Relay application. 
         If Discard is selected the unit will respond to an errored 
         frame by aborting the frame if transmission has begun; or 
         simply discarding it if transmission has not begun. If 
         Passthru is selected the unit transmit the entire frame but 
         will place an incorrect crc in it to preserve the error 
         indication.
         (1) discard
         (2) pasthru"
      ::= { dfrapCfgFrTable 2 }

dfrapCfgFrLmiType  OBJECT-TYPE
     SYNTAX      INTEGER
     {
          annexd         (1),
          annexa         (2),
          type1          (3),
          autosense      (4)
     }
      ACCESS      read-write
      STATUS      mandatory
      DESCRIPTION
        "The LMI type used in a Frame Relay application. This setting
         must match the attached Frame Relay device configuration. 
         Annex-A and Annex-D use DLCI 0, and Type 1 uses DLCI 1023.
         Type 1 is alternatively referred to as Cisco, Group of four, 
         or simply LMI. Annex-D may be referred to as ANSI T1.617.
         Annex-A may be referred to as ITU or CCITT Q.933. Auto-sense
         will either use the most recently detected LMI type or, in 
         the absence of any LMI, will attempt to instigate LMI 
         communications using each protocol.     
         (1) Annex-A: conforms to ITU (CCITT) Q.933 annex A
         (2) Annex-D: conforms to ANSI T1.617 annex D
         (3) Type 1: conforms to the original LMI as developed by 
             the Group of Four
         (4) Auto-sense: unit will attempt to detect and synchronize
             to the LMI type of the attached equipment."
       ::= { dfrapCfgFrTable 3 }

dfrapCfgFrLmiInactivityTimeout  OBJECT-TYPE
     SYNTAX      INTEGER (0..255)
     ACCESS      read-write
     STATUS      mandatory
     DESCRIPTION
        "Timer used by the unit to determine that an attached device is
         not participating in the LMI protocol and that the unit should 
         attempt to source LMI. This timer also controls the length of 
         time that the LMI sourcing state machine remains in a particular 
         state as it attempts to locate an LMI peer.
         (0) LMI Sourcing disabled
         (2-255) LMI Inactivity timeout"
       ::= { dfrapCfgFrTable 4 }

dfrapCfgFrLmiKeepaliveTimeout  OBJECT-TYPE
     SYNTAX      INTEGER (2..255)
     ACCESS      read-write
     STATUS      mandatory
     DESCRIPTION
        "Timer used by the unit to determine the frequency at which Status
         Enquiries are issued during LMI sourcing states where the unit is 
         emulating a Frame Relay DTE device.
         (2-255) length of time between sending enquiries (in seconds)"
       ::= { dfrapCfgFrTable 5 }

dfrapCfgFrAddrResMode OBJECT-TYPE
     SYNTAX      INTEGER
     {
         inactive (1),
         arp      (2),
         inarp    (3),
         both     (4)
     }
     ACCESS      read-write
     STATUS      mandatory
     DESCRIPTION
        "The ip-based Address Resolution protocol supported in the
         application. With ARP, requests are received and replies 
         are generated accordingly. With InARP, requests are received
         and replies are generated; additionally, InARP requests are 
         issued by the unit at the frequency defined by the InARP timer.
         Address Resolution will circumvent the need for static routes 
         and automatically log an associated dynamic entry into the 
         routing tables.
         (1) inactive: no address resolution support
         (2) ARP: only provide ARP responses. ARP is useful when the 
             router knows the unit's ip address but doesn't know the DLCI.
         (3) InARP: provide both InARP responses and InARP requests. InARP
             is useful when the router knows the DLCI but not the ip address.
         (4) Both ARP and InARP."
     ::= { dfrapCfgFrTable 6 }

dfrapCfgFrAddrResDlcis OBJECT-TYPE
     SYNTAX      INTEGER
     {
         single        (1),
         multiple      (2),
         ddsmulti      (3),
         dtemulti      (4)
     }
     ACCESS      read-write
     STATUS      mandatory
     DESCRIPTION
        "Address Resolution Dlcis determines which dlcis will
         support address resolution. In Private management 
         modes (Local, Remote, Bidirectional), address 
         resolution runs on the single defined management DLCI only
         (regardless of this setting). In Piggyback management
         the user has options based upon two models: Single, where the 
         address resolution protocols run only upon the defined 
         managment DLCI and Multiple, where its supported on all active 
         DLCIs recognized by the unit. 
         (1) Single - address resolution on the defined default DLCI on
             both ports
         (2) Multiple - address resolution on all active DLCIs on 
             both ports
         (3) DDSMulti - Single on DTE and Multiple on DDS
         (4) DTEMulti - Single on DDS and Multiple on DTE"
     ::= { dfrapCfgFrTable 9 }

dfrapCfgFrAddrResInarpTimer OBJECT-TYPE
     SYNTAX      INTEGER (5..86400)
     ACCESS      read-write
     STATUS      mandatory
     DESCRIPTION
        "If the unit is configured to support the InARP
         address resolution protocol, this is the frequency 
         of INARP requests that the unit will generate.
         (5-86400) - InARP Request Timer in seconds"
     ::= { dfrapCfgFrTable 7 }

dfrapCfgFrLmiFullStatus  OBJECT-TYPE
     SYNTAX      INTEGER (0..3600)
     ACCESS      read-write
     STATUS      mandatory
     DESCRIPTION
        "Timer used by the unit to determine if an LMI Full Status
         Report is missing. In the absence of a Full Status report
         for the duration defined by this timer, the unit will
         declared all DLCI's status INACTIVE and begin logging
         down time. Data passage is not interfered with.
         (0) Full Status Timer is disabled
         (20-3600) Full Status Report Timeout in seconds."
     ::= { dfrapCfgFrTable 8 }



--
--       The VNIP Configuration Table
--              This table contains the Configuration for the VNIP
--              protocol support on the DFRAP DDS DSU.

dfrapCfgVnipTable OBJECT IDENTIFIER ::= { dfrapConfiguration 6 }

dfrapCfgVnipMode OBJECT-TYPE
     SYNTAX      INTEGER
     {
         inactive (1),
         dte      (2),
         dds      (3),
         both     (4)
     }
     ACCESS      read-write
     STATUS      mandatory
     DESCRIPTION
        "This setting configures the unit for VNIP topology support on
         a per-interface basis. Establishing a VNIP topology is a
         fundamental prerequisite to applying the VNIP feature set which 
         includes PVC-based delay measurement, diagnostics, and congestion
         monitoring. With VNIP enabled on an interface the unit
         will attempt to locate VNIP peers out that port. As peers are 
         discovered and logged the unit will report the topology it has 
         learned on its opposite interface. If VNIP is inactive on one
         interface it will not engage in any VNIP dialog; however it will 
         continue to listen for topology messages on the inactive interface
         and will reflect these messages out the opposite interface if VNIP 
         is enabled. With VNIP inactive on both interfaces the unit will 
         transparently pass all VNIP messages. The topology database includes
         ip addresses, DLCI values, and the number of VNIP hops in between.
         (1) Topology Inactive: VNIP messages pass through unit
         (2) Topology Enabled on DTE only: unit logs VNIP peers seen
             out the DTE interface. Unit listens for topology reports
             from the WAN but doesn't generate any towards the WAN. Will 
             report learned WAN topology towards the DTE.
         (3) Topology Enabled on WAN only: unit logs VNIP peers seen
             out the WAN interface. Unit listens for topology reports
             from the DTE but doesn't generate any towards the DTE. Will 
             report learned DTE topology towards the WAN.
         (4) Topolgy Enabled on Both DTE and WAN: Unit logs VNIP peers
             seen out both interfaces and generates DTE topolgy reports 
             towards the WAN and vice versa."
     ::= { dfrapCfgVnipTable 1 }

   dfrapCfgVnipInitTimer OBJECT-TYPE
        SYNTAX      INTEGER (5..86400)
        ACCESS      read-write
        STATUS      mandatory
        DESCRIPTION
           "VNIP peer to peer communications are initiated following
            the detection of a VNIP Hello message. The unit will
            periodically issue this message out interfaces that have 
            VNIP enabled until a Hello response is received. Following 
            the reception of the Hello response, the unit will stop 
            issuing Hello messahges on that DLCI/interface and generate 
            periodic topology reports at the VNIP Keep Alive frequency. 
            The unit will generate periodic Hello messages, at the 
            InitTimer frequency if no Hello responses are ever detected 
            or a topology message not been detected within the time period 
            defined by the VNIP Inactivity timer.
            (5-86400) VNIP Hello frequency (in seconds)"
        ::= { dfrapCfgVnipTable 2 }

dfrapCfgVnipKeepAliveTimer OBJECT-TYPE
     SYNTAX      INTEGER (5..86400)
     ACCESS      read-write
     STATUS      mandatory
     DESCRIPTION
        "This is the frequency that topology reports are issued out 
         any interface that has VNIP enabled. Once a Hello exchange
         occurs, the unit will periodically issue a VNIP message which 
         reflects the topology it has learned on the opposite interface.
         This Keep Alive timer must be less than any peer unit's Inactivity
         timer.
         (5-86400) VNIP Topology Update frequency (in seconds)"
     ::= { dfrapCfgVnipTable 3 }

dfrapCfgVnipInactivityTimer OBJECT-TYPE
     SYNTAX      INTEGER (5..86400)
     ACCESS      read-write
     STATUS      mandatory
     DESCRIPTION
        "The length of time to wait before dropping a VNIP
         peer from the database and attempting tp reestablish
         communications by issuing the VNIP Hello message. If
         this timer expires then the entire topology database
         is reset. The Inactivity timers of any unit participating
         in a VNIP topology must be greater than the highest Keep 
         Alive timer in the topology.
         (5- 86400) VNIP Hello frequency (in seconds)"
     ::= { dfrapCfgVnipTable 4 }


dfrapCfgVnipTransitDelayFrequency OBJECT-TYPE
     SYNTAX      INTEGER (15..86400)
     ACCESS      read-write
     STATUS      mandatory
     DESCRIPTION
        "Transit Delay measurements may be enabled between any DLCI
         peers that have been logged through the topology protocol.
         Delay messages are issued at this frequency and results are
         recorded. Transit delay measures the round-trip network
         delay between two VNIP peers (internal unit latencies are
         not part of the measurement). Traps may be optionally generated 
         if a delay threshold is exceeded.
         (15-86400): Transit Delay message frequency (in seconds)"
     ::= { dfrapCfgVnipTable 5 }

dfrapCfgTransitDelayTable   OBJECT-TYPE
     SYNTAX   SEQUENCE OF DfrapCfgTransitDelayEntry
     ACCESS   not-accessible
     STATUS   mandatory
     DESCRIPTION
        "The table defining the transit delay measurement profile for
         each of the learned VNIP peers. As peers are located and 
         logged into the topology database, a default transit delay
         profile is assumed. The default is to enable transit delay
         to all hops located out the interface. A DLCI's transit
         delay profile cannot be modified unless the DLCI has been
         discovered through the VNIP topology protocol."
     ::= { dfrapCfgVnipTable 20 }

dfrapCfgTransitDelayEntry OBJECT-TYPE
     SYNTAX      DfrapCfgTransitDelayEntry
     ACCESS      not-accessible
     STATUS      mandatory
     DESCRIPTION
        "A VNIP Transit Delay configuration entry for a particular 
         DLCI on a particular interface. A DLCI's transit delay 
         profile cannot be modified unless the DLCI has been
         discovered through the VNIP topology protocol" 
     INDEX { dfrapCfgTransitDelayInterface, dfrapCfgTransitDelayDlciValue }
     ::= { dfrapCfgTransitDelayTable 1 }

DfrapCfgTransitDelayEntry ::=
     SEQUENCE
     {
         dfrapCfgTransitDelayInterface         INTEGER,
         dfrapCfgTransitDelayDlciValue         INTEGER,
         dfrapCfgTransitDelayNumHops           INTEGER,
         dfrapCfgTransitDelayRcvSummaryCancel  INTEGER,
         dfrapCfgTransitDelayThreshold         INTEGER
      }

dfrapCfgTransitDelayInterface OBJECT-TYPE
     SYNTAX      INTEGER
     {
         dte-interface (1),
         dds-interface (2)
     }
     ACCESS      read-write
     STATUS      mandatory
     DESCRIPTION
        "This is the interface being configured for VNIP Transit 
         Delay. If topology is enabled, each interface will contain 
         a database of VNIP peers organized by DLCI value and 
         Number of Hops.
         (1) DTE Interface
         (2) DDS Interface"
     ::= { dfrapCfgTransitDelayEntry 1 }

dfrapCfgTransitDelayDlciValue    OBJECT-TYPE
     SYNTAX      INTEGER 
     ACCESS      read-write
     STATUS      mandatory
     DESCRIPTION
        "This is the DLCI being configured for VNIP Transit 
         Delay. If topology is enabled, each interface will contain 
         a database of VNIP peers organized by DLCI value and 
         Number of Hops."
     ::= { dfrapCfgTransitDelayEntry 2 }

dfrapCfgTransitDelayNumHops    OBJECT-TYPE
     SYNTAX      INTEGER (0..255)
     ACCESS      read-write
     STATUS      mandatory
     DESCRIPTION
        "VNIP topolgy may include multiple units on a given
         DLCI/interface. The topology logs the number of 
         intermediate VNIP peers between units (Hops). This 
         setting determines which peers on a DLCI are participating
         in delay measurements.
         (0) All hops
         (1-254) individually addressable delay measurement
                 between any two peers.
         (255) Furthest hop only"
     ::= { dfrapCfgTransitDelayEntry 4 }

dfrapCfgTransitDelayRcvSummaryCancel    OBJECT-TYPE
     SYNTAX      INTEGER 
     {
         enable-rsc  (1),
         disable-rsc (2)
     }
     ACCESS      read-write
     STATUS      mandatory
     DESCRIPTION
        "Controls the Receive Summary Cancellation feature of VNIP 
         Transit Delay on this interface/DLCI. Every Transit Delay
         measurement exchange includes a follow-up message from the 
         initiator with the delay results. If RSC is enabled, a unit
         will log results based upon this summary message and will 
         not issue its next scheduled delay measurement. With RSC 
         disabled, the unit will not use the summary message and 
         will always issue its regularly scheduled message based on
         the delay frequency timer. The purpose of this feature is to
         reduce traffic introduced by VNIP. In a typical peer-to-peer
         transit delay measurement where both ends are concurrently
         conducting transit delay measurements it's recommended that 
         one end have RSC enabled and one end disabled."
     ::= { dfrapCfgTransitDelayEntry 5 }

dfrapCfgTransitDelayThreshold    OBJECT-TYPE
     SYNTAX      INTEGER (0..86400000)
     ACCESS      read-write
     STATUS      mandatory
     DESCRIPTION
        "Specifies a transit delay threshold for this DLCI/interface.
         When the transit delay exceeds the threshold, a TRAP is sent. 
         The threshold may be set from one millisecond to 24 hours.
         A value of 0 will prevent a TRAP from being sent.
         (0): Transit delay threshold trap disabled for this DLCI/interface
         (1-86400000): delay threshhold. Any delay measurements exceeding
            this result will generate a trap."
     ::= { dfrapCfgTransitDelayEntry 6 }


dfrapCfgTDDeleteTable   OBJECT-TYPE
     SYNTAX   SEQUENCE OF DfrapCfgTDDeleteEntry
     ACCESS   not-accessible
     STATUS   mandatory
     DESCRIPTION
        "The table allows the user to disable transit delay measurements
         for a specific DLCI on a particular interface."
     ::= { dfrapCfgVnipTable 21 }

dfrapCfgTDDeleteEntry OBJECT-TYPE
     SYNTAX      DfrapCfgTDDeleteEntry
     ACCESS      not-accessible
     STATUS      mandatory
     DESCRIPTION
        "Disables VNIP Transit Delay for a particular interface and DLCI." 
     INDEX { dfrapCfgTDDeleteInterface }
     ::= { dfrapCfgTDDeleteTable 1 }

DfrapCfgTDDeleteEntry ::=
     SEQUENCE
     {
          dfrapCfgTDDeleteInterface    INTEGER,
          dfrapCfgTDDeleteDlciValue    INTEGER
     }

dfrapCfgTDDeleteInterface OBJECT-TYPE
     SYNTAX      INTEGER
     {
         dte-interface (1),
         dds-interface (2)
     }
     ACCESS      not-accessible
     STATUS      mandatory
     DESCRIPTION
        "Transit delay can be disabled for a given DLCI on
         either interface. This indexes the interface. 
         Setting this index and the associated DLCI index
         will disable transit delay on that combination."
     ::= { dfrapCfgTDDeleteEntry 1 }

dfrapCfgTDDeleteDlciValue    OBJECT-TYPE
     SYNTAX      INTEGER 
     ACCESS      write-only
     STATUS      mandatory
     DESCRIPTION
        "Transit delay can be disabled for a given DLCI on
         either interface. This indexes the DLCI. Setting 
         this index and the associated interface index will
         disable transit delay on that combination."
     ::= { dfrapCfgTDDeleteEntry 2 }

   dfrapCfgTransitDelayTableClear  OBJECT-TYPE
         SYNTAX      INTEGER
         {
               clear-table   (1)
         }
         ACCESS      write-only
         STATUS      mandatory
         DESCRIPTION
              " The dfrapCfgTransitDelayTable is cleared.
                (1) clear the table "
         ::= { dfrapCfgVnipTable 22 }



--       The Frame Relay Performance Configuration
--              A group of configuration tables supporting frame relay
--              performance measurement on the DFRAP DDS DSU.

dfrapCfgFrPerf OBJECT IDENTIFIER ::= { dfrapConfiguration 7 }

dfrapCfgFrPerfDlciNamesTable   OBJECT-TYPE
          SYNTAX      SEQUENCE OF DFRAPCfgFrPerfDlciNamesEntry
          ACCESS      not-accessible
          STATUS      mandatory
          DESCRIPTION
             "This table allows the user to configure DLCI
              specific parameters such as Names, CIR, and EIR. 
              Additionally, any DLCIs configured with these
              parameters will be added into the Short Term 
              statistics database next time its cleared."
          ::= { dfrapCfgFrPerf 1 }

dfrapCfgFrPerfDlciNamesEntry OBJECT-TYPE
     SYNTAX      DFRAPCfgFrPerfDlciNamesEntry
     ACCESS      not-accessible
     STATUS      mandatory
     DESCRIPTION
        "A table entry indexed by DLCI, containing
         a DLCI, a DLCI name, a CIR, and how the
         CIR value was obtained." 
     INDEX { dfrapCfgFrPerfDlciNamesDlciValue }
     ::= { dfrapCfgFrPerfDlciNamesTable 1 }

DFRAPCfgFrPerfDlciNamesEntry ::=
     SEQUENCE
     {
          dfrapCfgFrPerfDlciNamesDlciValue   INTEGER,
          dfrapCfgFrPerfDlciNamesDlciName    DisplayString (SIZE (0..15)),
          dfrapCfgFrPerfDlciNamesCirValue    INTEGER,
          dfrapCfgFrPerfDlciNamesCirType     INTEGER,
          dfrapCfgFrPerfDlciNamesUtilThreshold INTEGER,
          dfrapCfgFrPerfDlciNamesEirValue    INTEGER
     } 

dfrapCfgFrPerfDlciNamesDlciValue    OBJECT-TYPE
     SYNTAX      INTEGER 
     ACCESS      read-write
     STATUS      mandatory
     DESCRIPTION
        "A DLCI selected for customized configuration and to 
         be added to short term statistics collection (if it
         wasn't already there)."
     ::= { dfrapCfgFrPerfDlciNamesEntry 1 }

dfrapCfgFrPerfDlciNamesDlciName   OBJECT-TYPE
     SYNTAX      DisplayString (SIZE (0..15))
     ACCESS      read-write
     STATUS      mandatory
     DESCRIPTION
        "A user-specifiable name for an individual DLCI."
     ::= { dfrapCfgFrPerfDlciNamesEntry 2 }

dfrapCfgFrPerfDlciNamesCirValue    OBJECT-TYPE
     SYNTAX      INTEGER 
     ACCESS      read-write
     STATUS      mandatory
     DESCRIPTION
        "The CIR value for an individual DLCI. This
         value is used in the calculation utilization
         as a percentage of CIR. If the CIR is reported 
         in the LMI message then the reported value will
         override this configured entry. In the absence
         of LMI CIR and a configured CIR, the unit will
         assume that teh CIR is the DTE Line Rate."
     ::= { dfrapCfgFrPerfDlciNamesEntry 3 }

dfrapCfgFrPerfDlciNamesCirType    OBJECT-TYPE
     SYNTAX      INTEGER 
     {
         cir-acquired-from-lmi  (1),
         cir-configured-by-user (2),
         cir-is-datarate        (3)
      }
      ACCESS      read-only
      STATUS      mandatory
      DESCRIPTION
         "The source of the CIR value for this DLCI.
          If CIR for a DLCI is part of the LMI message
          then this LMI supplied CIR will override any 
          defined CIR. If CIR is not part of LMI and
          has not been explicitly defined by the user
          it will default to the DTE Line Rate.
          (1) CIR reported in LMI Full Status message
          (2) CIR configured by user
          (3) CIR defaulted to DTE Line Rate"
      ::= { dfrapCfgFrPerfDlciNamesEntry 4 }

dfrapCfgFrPerfDlciNamesUtilThreshold  OBJECT-TYPE
     SYNTAX      INTEGER  (0..100) 
     ACCESS      read-write
     STATUS      mandatory
     DESCRIPTION
       "The threshold for generating a utilization 
       threshold trap as a percentage of the CIR.  
       If the utilization percentage is above this 
       threshold for more than 
       dfrapCfgFrPerfDlciUtilThreshold number of
       dfrapCfgFrPerfTimersSTInterval's a
       dfrapPvc(Rx/Tx)UtilizationExceeded trap
       will be issued.  If the If the utilization 
       percentage falls below this threshold for 
       more than dfrapCfgFrPerfDlciUtilThreshold 
       number of dfrapCfgFrPerfTimersSTInterval's a
       dfrapPvc(Rx/Tx)UtilizationExceeded trap
       will be issued."
     ::= { dfrapCfgFrPerfDlciNamesEntry 5}

dfrapCfgFrPerfDlciNamesEirValue    OBJECT-TYPE
     SYNTAX      INTEGER 
     ACCESS      read-write
     STATUS      mandatory
     DESCRIPTION
        "The EIR value for an individual DLCI. In the 
         absence of a configured EIR, the unit will
         assume that the EIR is the DTE Line Rate."
     ::= { dfrapCfgFrPerfDlciNamesEntry 6 }

         
dfrapCfgFrPerfDlciNamesDelete   OBJECT-TYPE
     SYNTAX      INTEGER 
     ACCESS      write-only
     STATUS      mandatory
     DESCRIPTION
        "Setting this object with a specific DLCI value
         will remove the DLCI form the DLCI-specific
         parameters database."
     ::= { dfrapCfgFrPerf 2 }

dfrapCfgFrPerfTimers OBJECT IDENTIFIER ::= { dfrapCfgFrPerf 3 }

dfrapCfgFrPerfTimersSTInterval   OBJECT-TYPE
     SYNTAX      INTEGER (3..60)
     ACCESS      read-write
     STATUS      mandatory
     DESCRIPTION
        "Short term statistics maintain cumulative counts, and
         counts for the current and previous short term windows.
         This value is the  window size for the short term statistics
         intervals.
         (3-60): short term statistics collection interval"
     ::= { dfrapCfgFrPerfTimers 1 }

dfrapCfgFrPerfTimersLTInterval   OBJECT-TYPE
     SYNTAX      INTEGER (4..3600)
     ACCESS      read-write
     STATUS      mandatory
     DESCRIPTION
        "Long term statistics maintain 96 contiguous intervals
         of configurable protocol per DLCI statistics. This value
         is the window size of each interval. Adjusting this value
         will change the overall length of time that the 96 intervals
         will span.
         (4-3600): long term statsistics collection interval"
     ::= { dfrapCfgFrPerfTimers 2 }

dfrapCfgFrPerfUserProtocolsTable   OBJECT-TYPE
     SYNTAX      SEQUENCE OF DFRAPCfgFrPerfUserProtocolsEntry
     ACCESS      not-accessible
     STATUS      mandatory
     DESCRIPTION
        "This table allows the user to select TCP/UDP ports 
         for statistics collection.  Tx and Rx byte counts
         will collected on the specified ports.  These ports
         are selectable as protocols in the long term
         statistics filter and are displayed with the other
         protocols in the short term statistics."
     ::= { dfrapCfgFrPerf 4 }

dfrapCfgFrPerfUserProtocolsEntry OBJECT-TYPE
     SYNTAX      DFRAPCfgFrPerfUserProtocolsEntry
     ACCESS      not-accessible
     STATUS      mandatory
     DESCRIPTION
        "An index and TCP/UDP port number pair." 
     INDEX { dfrapCfgFrPerfUserProtocolsIndex }
     ::= { dfrapCfgFrPerfUserProtocolsTable 1 }

DFRAPCfgFrPerfUserProtocolsEntry ::=
     SEQUENCE
     {
          dfrapCfgFrPerfUserProtocolsIndex     INTEGER,
          dfrapCfgFrPerfUserProtocolsPortNum   INTEGER
     } 

dfrapCfgFrPerfUserProtocolsIndex    OBJECT-TYPE
     SYNTAX      INTEGER 
     ACCESS      read-only
     STATUS      mandatory
     DESCRIPTION
        "An index. Beginning with index 1, the range is defined 
         in SysNumUserProtocols"
     ::= { dfrapCfgFrPerfUserProtocolsEntry 1 }

dfrapCfgFrPerfUserProtocolsPortNum   OBJECT-TYPE
     SYNTAX      INTEGER
     ACCESS      read-write
     STATUS      mandatory
     DESCRIPTION
        "Tx and Rx byte counts will be collected on
         the user-specifiable TCP/UDP port number.
         (0) port not defined
         (1-65535): IP TCP/UDP protocol port number."
     ::= { dfrapCfgFrPerfUserProtocolsEntry 2 }

dfrapCfgFrPerfLTDlciFilterTable       OBJECT-TYPE
     SYNTAX      SEQUENCE OF DFRAPCfgFrPerfLTDlciFilterEntry
     ACCESS      not-accessible
     STATUS      mandatory
     DESCRIPTION
        "Long term statistics can only be collected
         on a limited number of DLCIs. The value of
         SysLTFNumDlcis defines the maximum number of
         DLCIs that can be included in the Long Term
         Statistics. Once one or more DLCIs are added
         to Long Term Stats, the user may assign a 
         set of protocols that will be monitored across
         all of the Long Term DLCIs."
     ::= { dfrapCfgFrPerf 5 }

dfrapCfgFrPerfLTDlciFilterEntry OBJECT-TYPE
     SYNTAX      DFRAPCfgFrPerfLTDlciFilterEntry
     ACCESS      not-accessible
     STATUS      mandatory
     DESCRIPTION
        "An index and DLCI number pair." 
     INDEX { dfrapCfgFrPerfLTDlciFilterIndex }
     ::= { dfrapCfgFrPerfLTDlciFilterTable 1 }

DFRAPCfgFrPerfLTDlciFilterEntry ::=
     SEQUENCE
     {
          dfrapCfgFrPerfLTDlciFilterIndex     INTEGER,
          dfrapCfgFrPerfLTDlciFilterDlciNum   INTEGER
     } 

dfrapCfgFrPerfLTDlciFilterIndex    OBJECT-TYPE
     SYNTAX      INTEGER 
     ACCESS      read-only
     STATUS      mandatory
     DESCRIPTION
        "An index. Beginning with index 1, the maximum is 
         defined by the value of SysLTFNumDlcis."
     ::= { dfrapCfgFrPerfLTDlciFilterEntry 1 }

dfrapCfgFrPerfLTDlciFilterDlciNum   OBJECT-TYPE
     SYNTAX      INTEGER
     ACCESS      read-write
     STATUS      mandatory
     DESCRIPTION
        "Setting a DLCI value here will add that DLCI into
         the Long term statistics database (associated with 
         its index) and it will be monitored for the protocol 
         activity defined in the Long Term Protocol filter."
     ::= { dfrapCfgFrPerfLTDlciFilterEntry 2 }


dfrapCfgFrPerfLTProtocolFilterTable   OBJECT-TYPE
     SYNTAX      SEQUENCE OF DFRAPCfgFrPerfLTProtocolFilterEntry
     ACCESS      not-accessible
     STATUS      mandatory
     DESCRIPTION
        "Long term statistics can only be collected
         on a limited number of protocols. The maximum
         number of Long Term Protoocls are defined by 
         SysLTFNumProtocols. This table allows the user to 
         configure those protocols."
     ::= { dfrapCfgFrPerf 6 }

dfrapCfgFrPerfLTProtocolFilterEntry OBJECT-TYPE
     SYNTAX      DFRAPCfgFrPerfLTProtocolFilterEntry
     ACCESS      not-accessible
     STATUS      mandatory
     DESCRIPTION
        "An index and protocol pair." 
     INDEX { dfrapCfgFrPerfLTProtocolFilterIndex }
     ::= { dfrapCfgFrPerfLTProtocolFilterTable 1 }

DFRAPCfgFrPerfLTProtocolFilterEntry ::=
     SEQUENCE
     {
          dfrapCfgFrPerfLTProtocolFilterIndex      INTEGER,
          dfrapCfgFrPerfLTProtocolFilterProtocol   INTEGER
     } 

dfrapCfgFrPerfLTProtocolFilterIndex    OBJECT-TYPE
     SYNTAX      INTEGER 
     ACCESS      read-only
     STATUS      mandatory
     DESCRIPTION
        "An index. Beginning with index 1, the maximum is 
         defined by the value of SysLTFNumProtocols."
     ::= { dfrapCfgFrPerfLTProtocolFilterEntry 1 }

dfrapCfgFrPerfLTProtocolFilterProtocol   OBJECT-TYPE
     SYNTAX      INTEGER
     {
         ip-tx-bc                    (1),
         ip-rx-bc                    (2),
         tcp-ip-tx-bc                (3),
         tcp-ip-rx-bc                (4),
         ftp-tcp-ip-tx-bc            (5),
         ftp-tcp-ip-rx-bc            (6),
         telnet-tcp-ip-tx-bc         (7),
         telnet-tcp-ip-rx-bc         (8),
         smtp-tcp-ip-tx-bc           (9),
         smtp-tcp-ip-rx-bc           (10),
         tftp-tcp-ip-tx-bc           (11),
         tftp-tcp-ip-rx-bc           (12),
         http-tcp-ip-tx-bc           (13),
         http-tcp-ip-rx-bc           (14),
         netbios-ssn-tcp-ip-tx-bc    (15),
         netbios-ssn-tcp-ip-rx-bc    (16),
         snmp-tcp-ip-tx-bc           (17),
         snmp-tcp-ip-rx-bc           (18),
         snmptrap-tcp-ip-tx-bc       (19),
         snmptrap-tcp-ip-rx-bc       (20),
         udp-ip-tx-bc                (21),
         udp-ip-rx-bc                (22),
         ftp-udp-ip-tx-bc            (23),
         ftp-udp-ip-rx-bc            (24),
         telnet-udp-ip-tx-bc         (25),
         telnet-udp-ip-rx-bc         (26),
         smtp-udp-ip-tx-bc           (27),
         smtp-udp-ip-rx-bc           (28),
         tftp-udp-ip-tx-bc           (29),
         tftp-udp-ip-rx-bc           (30),
         http-udp-ip-tx-bc           (31),
         http-udp-ip-rx-bc           (32),
         netbios-dgm-udp-ip-tx-bc    (33),
         netbios-dgm-udp-ip-rx-bc    (34),
         snmp-udp-ip-tx-bc           (35),
         snmp-udp-ip-rx-bc           (36),
         snmptrap-udp-ip-tx-bc       (37),
         snmptrap-udp-ip-rx-bc       (38),
         rip-udp-ip-tx-bc            (39),
         rip-udp-ip-rx-bc            (40),
         icmp-ip-tx-bc               (41),
         icmp-ip-rx-bc               (42),
         echorep-icmp-ip-tx-bc       (43),
         echorep-icmp-ip-rx-bc       (44),
         dest-unr-icmp-ip-tx-bc      (45),
         dest-unr-icmp-ip-rx-bc      (46),
         src-quench-icmp-ip-tx-bc    (47),
         src-quench-icmp-ip-rx-bc    (48),
         redirect-icmp-ip-tx-bc      (49),
         redirect-icmp-ip-rx-bc      (50),
         echoreq-icmp-ip-tx-bc       (51),
         echoreq-icmp-ip-rx-bc       (52),
         time-excd-icmp-ip-tx-bc     (53),
         time-excd-icmp-ip-rx-bc     (54),
         param-prob-icmp-ip-tx-bc    (55),
         param-prob-icmp-ip-rx-bc    (56),
         timestamp-req-icmp-ip-tx-bc (57),
         timestamp-req-icmp-ip-rx-bc (58),
         timestamp-rep-icmp-ip-tx-bc (59),
         timestamp-rep-icmp-ip-rx-bc (60),
         addr-mask-req-icmp-ip-tx-bc (61),
         addr-mask-req-icmp-ip-rx-bc (62),
         addr-mask-rep-icmp-ip-tx-bc (63),
         addr-mask-rep-icmp-ip-rx-bc (64),
         pkt-too-big-icmp-ip-tx-bc   (65),
         pkt-too-big-icmp-ip-rx-bc   (66),
         gp-mem-query-icmp-ip-tx-bc  (67),
         gp-mem-query-icmp-ip-rx-bc  (68),
         gp-mem-report-icmp-ip-tx-bc (69),
         gp-mem-report-icmp-ip-rx-bc (70),
         gp-mem-reduct-icmp-ip-tx-bc (71),
         gp-mem-reduct-icmp-ip-rx-bc (72),
         ospf-ip-tx-bc               (73),
         ospf-ip-rx-bc               (74),
         other-ip-tx-bc              (75),
         other-ip-rx-bc              (76),
         ipx-tx-bc                   (77),
         ipx-rx-bc                   (78),
         spx-ipx-tx-bc               (79),
         spx-ipx-rx-bc               (80),
         ncp-ipx-tx-bc               (81),
         ncp-ipx-rx-bc               (82),
         sap-ipx-tx-bc               (83),
         sap-ipx-rx-bc               (84),
         rip-ipx-tx-bc               (85),
         rip-ipx-rx-bc               (86),
         netbios-ipx-tx-bc           (87),
         netbios-ipx-rx-bc           (88),
         other-ipx-tx-bc             (89),
         other-ipx-rx-bc             (90),
         arp-tx-bc                   (91),
         arp-rx-bc                   (92),
         arp-req-tx-bc               (93),
         arp-req-rx-bc               (94),
         arp-rep-tx-bc               (95),
         arp-rep-rx-bc               (96),
         rarp-req-tx-bc              (97),
         rarp-req-rx-bc              (98),
         rarp-rep-tx-bc              (99),
         rarp-rep-rx-bc              (100),
         inarp-req-tx-bc             (101),
         inarp-req-rx-bc             (102),
         inarp-rep-tx-bc             (103),
         inarp-rep-rx-bc             (104),
         sna-tx-bc                   (105),
         sna-rx-bc                   (106),
         sna-subarea-tx-bc           (107),
         sna-subarea-rx-bc           (108),
         sna-periph-tx-bc            (109),
         sna-periph-rx-bc            (110),
         sna-appn-tx-bc              (111),
         sna-appn-rx-bc              (112),
         sna-netbios-tx-bc           (113),
         sna-netbios-rx-bc           (114),
         cisco-tx-bc                 (115),
         cisco-rx-bc                 (116),
         other-tx-bc                 (117),
         other-rx-bc                 (118),
         user-defined-1-tx-bc        (119),
         user-defined-1-rx-bc        (120),
         user-defined-2-tx-bc        (121),
         user-defined-2-rx-bc        (122),
         user-defined-3-tx-bc        (123),
         user-defined-3-rx-bc        (124),
         user-defined-4-tx-bc        (125),
         user-defined-4-rx-bc        (126),
         thru-byte-tx-bc             (127),
         thru-byte-rx-bc             (128),
         thru-frame-tx-c             (129),
         thru-frame-rx-c             (130),
         thru-fecn-tx-c              (131),
         thru-fecn-rx-c              (132),
         thru-becn-tx-c              (133),
         thru-becn-rx-c              (134),
         thru-de-tx-c                (135),
         thru-de-rx-c                (136),
         cir-percent-range1-tx-bc    (137),
         cir-percent-range1-rx-bc    (138),
         cir-percent-range2-tx-bc    (139),
         cir-percent-range2-rx-bc    (140),
         cir-percent-range3-tx-bc    (141),
         cir-percent-range3-rx-bc    (142),
         cir-percent-range4-tx-bc    (143),
         cir-percent-range4-rx-bc    (144),
         cir-percent-range5-tx-bc    (145),
         cir-percent-range5-rx-bc    (146),
         cir-percent-range6-tx-bc    (147),
         cir-percent-range6-rx-bc    (148),
         cir-percent-range7-tx-bc    (149),
         cir-percent-range7-rx-bc    (150),
         cir-percent-range8-tx-bc    (151),
         cir-percent-range8-rx-bc    (152),
         lmi-tx-bc                   (153),
         lmi-rx-bc                   (154),
         lmi-livo-enq-tx-bc          (155),
         lmi-livo-enq-rx-bc          (156),
         lmi-livo-stat-tx-bc         (157),
         lmi-livo-stat-rx-bc         (158),
         lmi-full-enq-tx-bc          (159),
         lmi-full-enq-rx-bc          (160),
         lmi-full-stat-tx-bc         (161),
         lmi-full-stat-rx-bc         (162),
         lmi-other-tx-bc             (163),
         lmi-other-rx-bc             (164),
         total-uptime                (165),
         total-downtime              (166),
         igrp-tx-bc                  (167),
         igrp-rx-bc                  (168),
         vnip-tx-bc                  (169),
         vnip-rx-bc                  (170),
         annex-g-tx-bc               (171),
         annex-g-rx-bc               (172),

         delete-entry                (-1)
     }
     ACCESS      read-write
     STATUS      mandatory
     DESCRIPTION
            "Long term statistics will be collected on
             the user-specifiable protocol. Setting a -1 
             remove the indexed protocol from the filter."
     ::= { dfrapCfgFrPerfLTProtocolFilterEntry 2 }

dfrapCfgFrPerfDlciDefaultUtilThreshold  OBJECT-TYPE
     SYNTAX      INTEGER  (0..100) 
     ACCESS      read-write
     STATUS      mandatory
     DESCRIPTION
        "The default threshold for generating a 
         utilization threshold trap as a percentage 
         of the CIR. This value is used for 
         dfrapCfgFrPerfDlciNamesUtilThreshold when
         a DLCI is first discovered. "
     ::= { dfrapCfgFrPerf 7 }
      
dfrapCfgFrPerfDlciUtilDuration  OBJECT-TYPE
     SYNTAX      INTEGER (0..65535) 
     ACCESS      read-write
     STATUS      mandatory
     DESCRIPTION
        "The number of Short Term Intervals that a
         DLCI's utilization as a percentage of CIR
         must be above or below the value of
         dfrapCfgFrPerfDlciUtilThreshold before a
         dfrapPvc(Rx/Tx)UtilizationExceededTrap or
         dfrapPvc(Rx/Tx)UtilizationClearedTrap is
         issued. "
     ::= { dfrapCfgFrPerf 8 }

  dfrapCfgFrPerfDlciNamesTableClear  OBJECT-TYPE
         SYNTAX       INTEGER
         {            
            clear-table                (1),
            clear-table-keep-stats     (2)
         }
         ACCESS      write-only
         STATUS      mandatory
         DESCRIPTION
             "Clears the smperCfgFrPerfDlciNamesTable
              (1) clear the table or (2) clear the table
              but don't remove the dlcis from the short
              term statistics."
         ::= { dfrapCfgFrPerf 9 }
         
  dfrapCfgFrPerfUserProtocolsTableClear  OBJECT-TYPE
         SYNTAX       INTEGER
         {            
            clear-table     (1)
         }
         ACCESS      write-only
         STATUS      mandatory
         DESCRIPTION
            " Clears the dfrapCfgFrPerfUserProtocolsTable
              (1) clear the table "
         ::= { dfrapCfgFrPerf 10 }
         
  dfrapCfgFrPerfLTDlciFilterTableClear  OBJECT-TYPE
         SYNTAX       INTEGER
         {            
            clear-table     (1)
         }
         ACCESS      write-only
         STATUS      mandatory
         DESCRIPTION
            " Clears the dfrapCfgFrPerfLTDlciFilterTable
              (1) clear the table "
         ::= { dfrapCfgFrPerf 11 }
         
  dfrapCfgFrPerfLTProtocolFilterTableClear  OBJECT-TYPE
         SYNTAX       INTEGER
         {            
            clear-table     (1)
         }
         ACCESS      write-only
         STATUS      mandatory
         DESCRIPTION
            " Clears the dfrapCfgFrPerfLTProtocolFilterTable
              (1) clear the table "
         ::= { dfrapCfgFrPerf 12 }
         
  dfrapCfgFrPerfUnprovDlcisDelete  OBJECT-TYPE
         SYNTAX       INTEGER
         {            
            delete-unprov     (1)
         }
         ACCESS      write-only
         STATUS      mandatory
         DESCRIPTION
             "Delete all unprovisioned and Not-In-LMI dlcis
              (1) delete all unprovisioned "
         ::= { dfrapCfgFrPerf 13 }
         

dfrapCfgSecurityTable OBJECT IDENTIFIER ::= { dfrapConfiguration 8 }

dfrapCfgTelnetCliLcdPassword   OBJECT-TYPE
     SYNTAX      DisplayString (SIZE (0..8))
     ACCESS      read-write
     STATUS      mandatory
     DESCRIPTION
        "The password needed to start a
         CLI (Command Line Interface),
         Telnet or LCD session."
     ::= { dfrapCfgSecurityTable 1 }

dfrapCfgTftpPassword   OBJECT-TYPE
     SYNTAX      DisplayString (SIZE (0..8))
     ACCESS      read-write
     STATUS      mandatory
     DESCRIPTION
        "The password needed to initiate a TFTP download."
     ::= { dfrapCfgSecurityTable 2 }

dfrapCfgCliPassword   OBJECT-TYPE
     SYNTAX      DisplayString (SIZE (0..8))
     ACCESS      read-write
     STATUS      mandatory
     DESCRIPTION
        "OBSOLETE: The Telnet, CLI and LCD passwords
              are one and the same.  Use the above
              CfgTelnetCliLcdPassword to log into
              the CLI (Command Line Interface)."
     ::= { dfrapCfgSecurityTable 3 }

dfrapCfgLcdPassword   OBJECT-TYPE
     SYNTAX      DisplayString (SIZE (0..8))
     ACCESS      read-write
     STATUS      mandatory
     DESCRIPTION
        "OBSOLETE: The Telnet, CLI and LCD passwords
         are one and the same.  Use the above
         CfgTelnetCliLcdPassword to log into
         the LCD Interface."
     ::= { dfrapCfgSecurityTable 4 }

dfrapCfgGetCommunityString   OBJECT-TYPE
     SYNTAX      DisplayString (SIZE (0..15))
     ACCESS      read-write
     STATUS      mandatory
     DESCRIPTION
        "The community string for doing SNMP GETs. The unit
         will respond to GETs that use either this string or
         the SET community string. All others will be rejected
         and a trap will be generated. String is case sensitive."
     ::= { dfrapCfgSecurityTable 5 }

dfrapCfgSetCommunityString   OBJECT-TYPE
     SYNTAX      DisplayString (SIZE (0..15))
     ACCESS      read-write
     STATUS      mandatory
     DESCRIPTION
        "The community string for doing SNMP SETs. The unit 
         will reject SETs with any other coimmunity string
         and will generate a trap. String is case sensitive."
     ::= { dfrapCfgSecurityTable 6 }

dfrapCfgLock   OBJECT-TYPE
     SYNTAX      INTEGER (1..600)
     ACCESS      write-only
     STATUS      mandatory
     DESCRIPTION
        " Request to start configuration download and lock out any 
          other means of configuring the unit. The integer passed in
          represents the time out period  in seconds between sets. 
          A set to this object will fail if the unit is already in a 
          configuration locked state."
     ::= { dfrapConfiguration 12 }

dfrapCfgLockID   OBJECT-TYPE
     SYNTAX      IpAddress
     ACCESS      read-only
     STATUS      mandatory
     DESCRIPTION
        " Returns the IP Address of  the management station currently 
          in control of configuration. A unit that is not in a 
          configuration locked state will return  0.0.0.0" 
     ::= { dfrapConfiguration 13 }

dfrapCfgID   OBJECT-TYPE
     SYNTAX      DisplayString (SIZE (0..8))
     ACCESS      read-write
     STATUS      mandatory
     DESCRIPTION
        " A read of this object returns the Current Configuration ID 
          string. A write sets  the Configuration ID string. The 
          string contains a starting character to indicate the last 
          configuration source C = Envisage N = CLI/TELNET L = LCD 
          S= other SNMP management station  and a unique 7 integer 
          value to differentiate configurations between common sources. 
          A value of *STARTUP indicates the configuration has been 
          defaulted. A write will only be accepted from the management 
          station that has successfully obtained the configuration lock" 
     ::= { dfrapConfiguration 14 }

dfrapCfgStatus   OBJECT-TYPE
     SYNTAX      INTEGER
     {
          in-progress                (1),
          success                    (2),
          datarate-density-conflict  (3),
          bandwidth-allocation-error (4),
          general-error              (5),
          timeout                    (6),
          aborted-by-user            (7)
     }
     ACCESS      read-only
     STATUS      mandatory
     DESCRIPTION
        " The status of a configuration install is reported here.
          On startup, a status of success will be reported.
          (1) The configuration has been locked and an update or
              unlock command has not been received.
          (2) An update command has been received and the configuration
              has been validated as consistent; .
          (3) An update command has been received but the DTE port 
              datarate is not compatible with the density.
          (4) An update command has been received but the number of
              channels to be allocated will not fit in the available
              channels.
          (5) An update command has been received but there is an
              error in the configuration that is not a 
              datarate-density-conflict or bandwidth-allocation-error.
          (6) The time between consecutive set requests exceeded the
              timeout sent with the dfrapCfgLock command.
          (7) The user sent a dfrapCfgUnlock command before a 
              dfrapCfgUpdate command.  This usually means that one
              of the sets in the configuration failed. "
     ::= { dfrapConfiguration 15 }

dfrapCfgUnlock   OBJECT-TYPE
     SYNTAX      INTEGER 
     {
                 un-lock (1)
     }
     ACCESS      write-only
     STATUS      mandatory
     DESCRIPTION
        " The management station sets this variable to complete 
          the configuration install process. Un-lock (1) notifies 
          the agent to remove the lock on configuring the unit
          without updating the configuration."
     ::= { dfrapConfiguration 16 }


dfrapCfgUpdate   OBJECT-TYPE
     SYNTAX      INTEGER 
     {
                 update (1)
     }
     ACCESS      write-only
     STATUS      mandatory
     DESCRIPTION
        " The management station sets this variable to complete 
        the configuration install process. Update (1) notifies 
        the agent to start the update process within the unit."
     ::= { dfrapConfiguration 17 }




-- =============================
-- ==    DIAGNOSTIC group     ==
-- =============================

dfrapDiagnostics  OBJECT IDENTIFIER ::= { dfrap 3 }


--
--       The Diagnostics/Unit Table
--              This table contains the objects for unit level diagnostics
--              on the FRAP DDS DSU.

dfrapDiagUnitTable OBJECT IDENTIFIER ::= { dfrapDiagnostics 1 }

dfrapDiagUnitLocLoop OBJECT-TYPE
          SYNTAX      INTEGER 
          {
               enable-loopback-mode  (1),
               disable-loopback-mode (2)
          }
          ACCESS      read-write
          STATUS      mandatory
          DESCRIPTION
             "Controls a bi-directional unit loopback. Data 
              is received from either interface, processed, 
              and transmitted back towards the same interface. 
              When configured for Frame Relay operation the unit 
              will preserve the LMI path during this loopback. 
              In Frame Relay mode, only valid frames are looped 
              back (pseudorandom test patterns will be dropped).
              (1) enable unit loopback"
          ::= { dfrapDiagUnitTable 1 }

dfrapDiagUnitReset OBJECT-TYPE
     SYNTAX      INTEGER 
     {
          reset-unit (1)
     }
     ACCESS      write-only
     STATUS      mandatory
     DESCRIPTION
        "Enables the operator to remotely reset the unit.
         Using this command will cause the unit to terminate
         all its connections and drop data.
         (1): reset unit"
     ::= { dfrapDiagUnitTable 2 }

dfrapDiagUnitTimeRemaining OBJECT-TYPE
     SYNTAX      TimeTicks
     ACCESS      read-only
     STATUS      mandatory
     DESCRIPTION
        "The remaining time on the active loopback
         before the loopback times out. The time is
         in hundredths of seconds (TimeTicks)."
          ::= { dfrapDiagUnitTable 3 }

--
--       The DDS Diagnostics Table
--              This table contains the diagnostics for the DDS port.

dfrapDiagDdsTable     OBJECT IDENTIFIER ::= { dfrapDiagnostics 2 }

dfrapDiagDdsLclLpbk  OBJECT-TYPE
          SYNTAX      INTEGER
          {
               enable-loopback-mode  (1),
               disable-loopback-mode (2)
          }
          ACCESS      read-write
          STATUS      mandatory
          DESCRIPTION
             "Controls local network loopback. All data 
              received from the WAN, regardless of format or 
              content, is transmitted back out (line interface 
              loopback) while still being sent to the DTE. When 
              configured for Frame Relay operation the unit 
              will not preserve the LMI path during this loopback.
              (1) enable DDS line loopback
              (2) disable DDS line loopback"
          ::= { dfrapDiagDdsTable 2 }

dfrapDiagDdsRmtLpbk  OBJECT-TYPE
          SYNTAX      INTEGER
          {
               no-loop-from-remote  (1),
               simplex-current-loop (2),
               non-latching-loop    (3),
               latching-loopback    (4)
          }
          ACCESS      read-only
          STATUS      mandatory
          DESCRIPTION
             "Enables the operator to examine (ONLY) the 
             status of network loopbacks placed by external
             equipment, such as your local CO. Any of these 
             conditions will result in a DDS line loopback.
             (1) no remote loop up command
             (2) simplex current reversal loopback command
             (3) non-latching loopback command
             (4) latching loopback comamnd"
          ::= { dfrapDiagDdsTable 3 }

dfrapDiagDdsTimeRemaining OBJECT-TYPE
          SYNTAX      TimeTicks
          ACCESS      read-only
          STATUS      mandatory
          DESCRIPTION
             "The remaining time on the active loopback
              before the loopback times out. The time is
              in hundredths of seconds (TimeTicks)."
          ::= { dfrapDiagDdsTable 4 }


--
--       The dfrapDiagDteTable
--              This table contains the DTE level diagnostics.
--

dfrapDiagDteTable     OBJECT IDENTIFIER ::= { dfrapDiagnostics 3 }

dfrapDiagDteLclLpbk OBJECT-TYPE
          SYNTAX      INTEGER
          {
              enable-loopback-mode (1),
              disable-loopback-mode (2)
          }
          ACCESS      read-write
          STATUS      mandatory
          DESCRIPTION
             "Controls a bi-directional DTE loopback. All 
              data received at the DTE interface is looped 
              back regardless of format or content (line 
              loopback). All data received at the WAN interface 
              is looped back regardless of format or content (line 
              loopback). When configured for Frame Relay 
              operation the unit will not preserve the LMI 
              path during this loopback.
              (1) enable DTE loopback
              (2) disable DTE loopback"
          ::= { dfrapDiagDteTable 3 }
     
dfrapDiagDteV54Lpbk   OBJECT-TYPE
          SYNTAX      INTEGER
          {
               v54-received (1),
               v54-not-received (2)
          }
          ACCESS      read-only
          STATUS      mandatory
          DESCRIPTION
             "This selection displays the status of the DTE Channel
             V.54 Loopback for the channel.  This loopback is
             initiated by the remote node, causing this unit to enter
             a Local DTE loopback condition.
             (1) V54 loopback pattern received from WAN
             (2) V54 loopback pattern not received from WAN" 
          ::= { dfrapDiagDteTable 4 }

dfrapDiagDteRmtV54Lpbk   OBJECT-TYPE
          SYNTAX      INTEGER
          {
               transmit-code-enable  (3),
               transmit-code-disable (4)
          }
          ACCESS      write-only
          STATUS      mandatory
          DESCRIPTION
             "This selection controls the DTE Channel V.54 Remote Loopback.
              Transmit-code-enable (3) will cause the node to transmit 
              a V.54 code to the remote node which will then enter a Local
              DTE Loopback state.  transmit-code-disable (4) will transmit 
              the loopdown code and cause the remote unit to remove the 
              Local DTE Loopback path.
              (1) send remote V54 loop up command
              (2) send remote V54 loop down command" 
          ::= { dfrapDiagDteTable 5 }

dfrapDiagDteTimeRemaining OBJECT-TYPE
          SYNTAX      TimeTicks
          ACCESS      read-only
          STATUS      mandatory
          DESCRIPTION
             "The remaining time on the active loopback
              before the loopback times out. The time is
              in hundredths of seconds (TimeTicks)."
          ::= { dfrapDiagDteTable 13 }

--
--       The dfrapDiagBertTable
--              This table contains the BERT diagnostics.
--

dfrapDiagBertTable     OBJECT IDENTIFIER ::= { dfrapDiagnostics 5 }

dfrapDiagBertState   OBJECT-TYPE
     SYNTAX      INTEGER
     {
         start-test     (1),
         stop-test      (3),
         inject-error   (4),
         clear-error    (5)
     }
     ACCESS      write-only
     STATUS      mandatory
     DESCRIPTION
        " The unit is capable of sending a pseudorandom test pattern
          (511 or QRSS) out the WAN and monitoring the WAN received 
          data for the same pattern. This test may be ineffective in 
          certain frame relay applications as pseudorandom data lacks 
          appropriate framing. Refer to VLOOP and VBERT for PVC-based
          error-rate testing in a live frame relay network.
          (1) Start a BERT test
          (2) Stop a BERT test
          (4) Inject a single bit error into the outgoing pattern
          (5) Clear current BERT results"
    ::= { dfrapDiagBertTable 1 }

dfrapDiagBertStatus  OBJECT-TYPE
     SYNTAX      INTEGER 
     {
         bert-off         (1),
         bert-out-of-sync (2),
         bert-in-sync     (3)
     }
     ACCESS      read-only
     STATUS      mandatory
     DESCRIPTION
        "Displays the current BERT test sync status.
         (1) BERT is not running
         (2) BERT is running but is not in sync
         (3) BERT is running and has detected a received BERT"
     ::= { dfrapDiagBertTable 2 }

dfrapDiagBertErrors   OBJECT-TYPE
     SYNTAX      Counter
     ACCESS      read-only
     STATUS      mandatory
     DESCRIPTION
        "Displays the number of errors detected in Bert Test."
     ::= { dfrapDiagBertTable 3 }

dfrapDiagBertErrSec OBJECT-TYPE
     SYNTAX      Counter
     ACCESS      read-only
     STATUS      mandatory
     DESCRIPTION
        "Displays the number of seconds containing 1 or more errors
         in BERT Test."
     ::= { dfrapDiagBertTable 4 }

dfrapDiagBertTimeElaps OBJECT-TYPE
     SYNTAX      TimeTicks
     ACCESS      read-only
     STATUS      mandatory
     DESCRIPTION
        "Elapsed time since BERT test was started or last cleared."
     ::= { dfrapDiagBertTable 5 }

dfrapDiagBertResyncs OBJECT-TYPE
     SYNTAX      Counter
     ACCESS      read-only
     STATUS      mandatory
     DESCRIPTION
        "Displays the number of times BERT test has synched up
         on the pattern. The BERT will attempt to resynchronize
         in response to excessive errors. A running count here
         indicates that a clean BERT is not being received."
     ::= { dfrapDiagBertTable 6 }

dfrapDiagBertPattern OBJECT-TYPE
     SYNTAX      INTEGER
     {
         five11-pattern  (1),
         qrss            (2)
     }
     ACCESS      read-write
     STATUS      mandatory
     DESCRIPTION
             "The type of pseudorandom BERT pattern used. 
              (1) 511: 9-bit pseudorandom pattern
              (2) QRSS: 20-bit pseudorandom pattern with 
                        no more than 14 consecutive zeros" 
          ::= { dfrapDiagBertTable 7 }

--
--       The dfraDiagVnipTable
--              This table contains the VNIP level diagnostics of the DFRAP CSU.
--
--
dfrapDiagVnipTable  OBJECT-TYPE
      SYNTAX   SEQUENCE OF DFRAPDiagVnipEntry
      ACCESS   not-accessible
      STATUS   mandatory
      DESCRIPTION
         " Table of Diagnostics performed with the VNIP protocol"
      ::= { dfrapDiagnostics 6 }

    dfrapDiagVnipEntry OBJECT-TYPE
        SYNTAX   DFRAPDiagVnipEntry
        ACCESS   not-accessible
        STATUS   mandatory
        DESCRIPTION
           "VNIP VLOOP and VBERT diagnostic profile. Initiating
            these tests require an established and stable VNIP topology
            on an interface. Once the topology is in place, the user
            can execute a PVC-based diagnostic between this unit and
            any indexed entry in the topology table. The index into the 
            topology table for a particular interface is required."
        INDEX {dfrapDiagVnipInterface, dfrapDiagVnipIndex}
         ::= { dfrapDiagVnipTable 1 }

    DFRAPDiagVnipEntry ::=
          SEQUENCE
          {
                dfrapDiagVnipInterface          INTEGER,
                dfrapDiagVnipIndex              INTEGER,
                dfrapDiagVnipDlci               INTEGER,
                dfrapDiagVnipIpAddr             IpAddress,
                dfrapDiagVLOOP                  INTEGER,
                dfrapDiagVBERT                  INTEGER,
                dfrapDiagVBERTRate              INTEGER,
                dfrapDiagVBERTSize              INTEGER,
                dfrapDiagVBERTPktPercent        INTEGER,
                dfrapDiagVBERTTestPeriod        INTEGER
          }

dfrapDiagVnipInterface OBJECT-TYPE
   SYNTAX      INTEGER
   {
        dte-interface (1),
        t1-interface (2)
   }
   ACCESS      read-write
   STATUS      mandatory
   DESCRIPTION
        "The interface out which a PVC-based VNIP diagnostic
         will be run. This must be an interface with a valid 
         and stable VNIP topology for a VNIP Diagnostic."
   ::= { dfrapDiagVnipEntry 1 }

dfrapDiagVnipIndex OBJECT-TYPE
    SYNTAX      INTEGER
    ACCESS      read-write
    STATUS      mandatory
    DESCRIPTION
       "The index to the external VNIP peer as presented by the VNIP
        topology database for the given interface. Refer to 
        VnipTopologyTable to determine the index of the remote peer."
    ::= { dfrapDiagVnipEntry 2 }

dfrapDiagVnipDlci    OBJECT-TYPE
    SYNTAX      INTEGER
    ACCESS      read-only
    STATUS      mandatory
    DESCRIPTION
        "This is the DLCI value for the given interface/index
         combination. This comes from the VniptTopologyTable."
    ::= { dfrapDiagVnipEntry 3 }

dfrapDiagVnipIpAddr   OBJECT-TYPE
    SYNTAX      IpAddress
    ACCESS      read-only
    STATUS      mandatory
    DESCRIPTION
       "This is the ip address for the given interface/index
        combination. This comes from the VniptTopologyTable."
    ::= { dfrapDiagVnipEntry 4 }

dfrapDiagVLOOP OBJECT-TYPE
    SYNTAX      INTEGER
    {
         start-test         (1),
         stop-test          (2)
    }
    ACCESS      write-only
    STATUS      mandatory
    DESCRIPTION
       "Controls execution of the Vnip Logical Loopback (VLOOP) test. 
        VLOOP is designed as an intrusive test and customer data 
        on the DLCI-under-test will be discarded. The VLOOP test includes
        a timed VBERT test and is run using the profile configured within 
        this table.
        (1) start VLOOP test 
        (2) stop VLOOP test (override VBERT test duration)"
    ::= { dfrapDiagVnipEntry 5 }

 
dfrapDiagVBERT OBJECT-TYPE
    SYNTAX      INTEGER
    {
         start     (1),
         stop      (2)
    }
    ACCESS      write-only
    STATUS      mandatory
    DESCRIPTION
       "Controls execution of the Vnip Virtual Bit Eror Rate (VBERT) test. 
        VBERT is designed to be a non-intrusive test and will attempt to
        statistically multiplex VBERT test data and customer data on the
        DLCI-under-test. However, VBERT data is given priority over customer
        data when the selected VBERT volume causes internal congestion. 
        The test is run using the profile configured within this table.
        (1) start test 
        (2) stop test (override VBERT test duration)"
    ::= { dfrapDiagVnipEntry 6 }


dfrapDiagVBERTRate  OBJECT-TYPE
    SYNTAX      INTEGER (8000..64000)
    ACCESS      read-write
    STATUS      mandatory
    DESCRIPTION
       "Specifies the throughput bit rate applied by VBERT or 
        VLOOP to the DLCI-under-test. Any rate up to the 
        DTE line rate may be selected. Note that selecting 
        rates that approach line rate will impact neighboring DLCIs.
        (8000-64000): VBERT/VLOOP data rate (in bits per second)."
    ::= { dfrapDiagVnipEntry 7 }


dfrapDiagVBERTSize  OBJECT-TYPE
    SYNTAX      INTEGER
    {
         sixty-four-byte            (64),
         one-twenty-eight-byte      (128),
         two-fifty-six-byte         (256),
         five-hundred-twelve-byte   (512),
         thousand-twenty-four-byte  (1024),
         two-thous-forty-eight-byte (2048)
    }

    ACCESS      read-write
    STATUS      mandatory
    DESCRIPTION
       "Specifies the size of framed data that will be used
        during the VBERT test, measures in Bytes.
         (64) 64-byte frames
         (128) 128-byte frames
         (256) 256-byte frames
         (512) 512-byte frames
         (1024) 1024-byte frames
         (2048) 2048-byte frames"
    ::= { dfrapDiagVnipEntry 8 }


dfrapDiagVBERTPktPercent  OBJECT-TYPE
    SYNTAX      INTEGER 
    {
       zero-percent        (1),
       twentyFive-percent  (2),
       fifty-percent       (3),
       seventyFive-percent (4),
       oneHundred-percent  (5)
    }
    ACCESS      read-write
    STATUS      mandatory
    DESCRIPTION
        "Specifies percentage of VBERT packets that will have the
         Frame Relay Discard Eligibility bit set. Frames with this
         bit set may be more likley to get dropped in a congested
         network.
         (1) 0%  of the test frames are marked discard eligible
         (2) 25% of the test frames are marked discard eligible
         (3) 50% of the test frames are marked discard eligible
         (4) 75% of the test frames are marked discard eligible
         (5) 100% of the test frames are marked discard eligible"
    ::= { dfrapDiagVnipEntry 9 }

dfrapDiagVBERTTestPeriod  OBJECT-TYPE
    SYNTAX      INTEGER (10..1440)
    ACCESS      read-write
    STATUS      mandatory
    DESCRIPTION
       "Specifies the duration of a VBERT test. Note that VBERT is 
        subjected to the unit's Loopback Timer and will be terminated 
        by whichever timer expires first.
        (10-1440): VBERT time duration in seconds"
    ::= { dfrapDiagVnipEntry 10 }



-- =========================
-- ==    STATUS group     ==
-- =========================

dfrapStatus  OBJECT IDENTIFIER ::= { dfrap 4 }

--
--     Table of peers discovered by VNIP
--

dfrapVnipTopologyTable   OBJECT-TYPE
     SYNTAX   SEQUENCE OF DFRAPVnipTopologyEntry
     ACCESS   not-accessible
     STATUS   mandatory
     DESCRIPTION
        "VNIP topology is a feature that, for each interface, maps all 
         compatible VNIP peers, their DLCI value, ip address and relative 
         location. The topology is a fundamental prerequisite to applying 
         the VNIP feature set which includes PVC-based delay measurement, 
         diagnostics, and congestion monitoring. With VNIP enabled on an 
         interface the unit will attempt to locate VNIP peers out that port.
         As peers are discovered and logged the unit will report the topology
         it has learned on its opposite interface. If VNIP is inactive on 
         one interface it will not engage in any VNIP dialog; however it 
         will continue to listen for topology messages on the inactive 
         interface and will reflect these messages out the opposite interface
         if VNIP is enabled. With VNIP inactive on both interfaces the unit 
         will transparently pass all VNIP messages. The topology database 
         includes the interface, local DLCI value, remote peer DLCI value, 
         remote peer ip address, and the number of VNIP hops in between.
         This table also reports the status of other VNIP features as well." 
     ::= { dfrapStatus 2 }

dfrapVnipTopologyEntry OBJECT-TYPE
     SYNTAX   DFRAPVnipTopologyEntry
     ACCESS   not-accessible
     STATUS   mandatory
     DESCRIPTION
        "The DLCI, IP address, and number of hops for a particular 
         node, discovered via VNIP off of an interface.  The entry 
         may also have transit delay measurements and VBERT diagnostic
         status to report as well."
     INDEX { dfrapVnipTopologyInterface, dfrapVnipTopologyIndex }
     ::= { dfrapVnipTopologyTable 1 }

DFRAPVnipTopologyEntry ::=
     SEQUENCE
     {
          dfrapVnipTopologyInterface          INTEGER,
          dfrapVnipTopologyIndex              INTEGER,
          dfrapVnipTopologyDlci               INTEGER,
          dfrapVnipTopologyIpAddr             IpAddress,
          dfrapVnipTopologyNumHops            INTEGER,
          dfrapVnipTopologyLocalDlci          INTEGER,
          dfrapVnipTopoTDNumSamples           Counter,
          dfrapVnipTopoTDAvgDelay             Counter,
          dfrapVnipTopoTDMaxDelay             Counter,
          dfrapVnipTopoTDMinDelay             Counter,
          dfrapVnipTopoTDLastDelay            Counter,
          dfrapVnipTopoVLOOPStatus            INTEGER,
          dfrapVnipTopoVBERTStatus            INTEGER,
          dfrapVnipTopoVBertTxDESetFrames     Counter,
          dfrapVnipTopoVBertRxDESetFrames     Counter,
          dfrapVnipTopoVBertTxDEClrFrames     Counter,
          dfrapVnipTopoVBertRxDEClrFrames     Counter,
          dfrapVnipTopoVBertTransitDelayMax   Counter,
          dfrapVnipTopoVBertTransitDelayAvg   Counter,
          dfrapVnipTopoVBertTimeElapse        TimeTicks,
          dfrapVnipTopoVBertPerUtilCIR        INTEGER,
          dfrapVnipTopoVBertPerUtilEIR        INTEGER
     }

dfrapVnipTopologyInterface OBJECT-TYPE
     SYNTAX      INTEGER
     {
         dte-interface (1),
         dds-interface (2)
      }
      ACCESS      read-only
      STATUS      mandatory
      DESCRIPTION
         "The interface off of which the peer was
          discovered.  Topology is discovered by
          sending VNIP messages out each interface.
          Units discovered via a particular interface
          are kept in a list associated with that
          interface.
          (1) VNIP peers and status out DTE interface
          (2) VNIP peers and status out WAN interface"
     ::= { dfrapVnipTopologyEntry 1 }

dfrapVnipTopologyIndex OBJECT-TYPE
     SYNTAX      INTEGER
     ACCESS      read-only
     STATUS      mandatory
     DESCRIPTION
        "The number of this discovered peer in the list
         of nodes for this interface. For each interface,
         the nodes are numbered 1 through n. This index
         is required when disabling or enabling VBERT/VLOOP
         to a particular peer."
     ::= { dfrapVnipTopologyEntry 2 }

dfrapVnipTopologyDlci    OBJECT-TYPE
     SYNTAX      INTEGER 
     ACCESS      read-only
     STATUS      mandatory
     DESCRIPTION
        "The DLCI of the discovered neighboring peer.
         This may be different from the local DLCI."
     ::= { dfrapVnipTopologyEntry 3 }

dfrapVnipTopologyIpAddr   OBJECT-TYPE
     SYNTAX      IpAddress
     ACCESS      read-only
     STATUS      mandatory
     DESCRIPTION
        "The IP address for the discovered peer."
     ::= { dfrapVnipTopologyEntry 4 }
 
dfrapVnipTopologyNumHops OBJECT-TYPE
     SYNTAX      INTEGER
     ACCESS      read-only
     STATUS      mandatory
     DESCRIPTION
        "The discovered peer is this number of hops away. 
         Each hop is a VNIP peer."
     ::= { dfrapVnipTopologyEntry 5 }
 
dfrapVnipTopologyLocalDlci OBJECT-TYPE
     SYNTAX      INTEGER
     ACCESS      read-only
     STATUS      mandatory
     DESCRIPTION
        "The DLCI from this unit over which the remote peer
         was discovered."
     ::= { dfrapVnipTopologyEntry 6 }

dfrapVnipTopoTDNumSamples  OBJECT-TYPE
     SYNTAX      Counter
     ACCESS      read-only
     STATUS      mandatory
     DESCRIPTION
        "The number of transit delay samples collected."
     ::= { dfrapVnipTopologyEntry 10 }
 
dfrapVnipTopoTDAvgDelay  OBJECT-TYPE
     SYNTAX      Counter
     ACCESS      read-only
     STATUS      mandatory
     DESCRIPTION
        "The average transit delay between this
         unit and the remote peer (in milliseconds)."
     ::= { dfrapVnipTopologyEntry 11 }

dfrapVnipTopoTDMaxDelay  OBJECT-TYPE
     SYNTAX      Counter
     ACCESS      read-only
     STATUS      mandatory
     DESCRIPTION
        "The maximum transit delay between this
         unit and the remote peer (in milliseconds)."
     ::= { dfrapVnipTopologyEntry 12 }

dfrapVnipTopoTDMinDelay  OBJECT-TYPE
     SYNTAX      Counter
     ACCESS      read-only
     STATUS      mandatory
     DESCRIPTION
        "The minimum transit delay between this
         node and the remote peer (in milliseconds)."
     ::= { dfrapVnipTopologyEntry 13 }

dfrapVnipTopoTDLastDelay  OBJECT-TYPE
     SYNTAX      Counter
     ACCESS      read-only
     STATUS      mandatory
     DESCRIPTION
        "The most recent transit delay measured between
         this node and the remote peer (in milliseconds)."
     ::= { dfrapVnipTopologyEntry 14 }


dfrapVnipTopoVLOOPStatus   OBJECT-TYPE
     SYNTAX      INTEGER
     {
         loopback-enable (1),
         loopback-disable (2)
      }
      ACCESS      read-only
      STATUS      mandatory
      DESCRIPTION
         "This selection displays the status of the VNIP PVC
          Loopback for this entry. This loopback is initiated 
          by the remote node through the VLOOP utility, causing 
          this node to loop data back to the remote node."
      ::= { dfrapVnipTopologyEntry  15 }
      

dfrapVnipTopoVBERTStatus  OBJECT-TYPE
     SYNTAX      INTEGER
     {
          off            (1),
          testing        (2),
          test-failed    (3),
          test-completed (4),
          in-test        (5)
      }
      ACCESS      read-only
      STATUS      mandatory
      DESCRIPTION
         "Displays the current status of the VBERT/VLOOP test.
          (1) Off: no test has run or the entry has been cleared
          (2) Testing: the entry is generating VBERT test frames
          (3) Test Failed: the request for a test on this entry failed  
          (4) Test Completed: a test has run and is finished results 
              are complete
          (5) In Test: the entry is on the receiving end of VBERT packets"
       ::= { dfrapVnipTopologyEntry 16 }
  

dfrapVnipTopoVBertTxDESetFrames   OBJECT-TYPE
     SYNTAX      Counter
     ACCESS      read-only
     STATUS      mandatory
     DESCRIPTION
        "Displays the number of Frames transmitted during VBERT/VLOOP Test 
         that had the Discard Eligibility indicator bit set."
     ::= { dfrapVnipTopologyEntry  17 }

     
dfrapVnipTopoVBertRxDESetFrames OBJECT-TYPE
     SYNTAX      Counter
     ACCESS      read-only
     STATUS      mandatory
     DESCRIPTION
        "Displays the number of Frames received during VBERT/VLOOP Test 
         that had the Discard Eligibility indicator bit set."
     ::= { dfrapVnipTopologyEntry  18 }
   
      
dfrapVnipTopoVBertTxDEClrFrames   OBJECT-TYPE
     SYNTAX      Counter
     ACCESS      read-only
     STATUS      mandatory
     DESCRIPTION
        "Displays the number of Frames transmitted during VBERT/VLOOP Test 
         that had the Discard Eligibility indicator bit cleared."
     ::= { dfrapVnipTopologyEntry  19 }
      
      
dfrapVnipTopoVBertRxDEClrFrames OBJECT-TYPE
     SYNTAX      Counter
     ACCESS      read-only
     STATUS      mandatory
     DESCRIPTION
        "Displays the number of Frames received during VBERT/VLOOP Test 
         that had the Discard Eligibility indicator bit cleared."
     ::= { dfrapVnipTopologyEntry  20 }
      
dfrapVnipTopoVBertTransitDelayMax OBJECT-TYPE
     SYNTAX      Counter
     ACCESS      read-only
     STATUS      mandatory
     DESCRIPTION
        "The maximum transit delay between this
         node and the remote peer during the VBERT/VLOOP test."
     ::= { dfrapVnipTopologyEntry  21 }
      
       
dfrapVnipTopoVBertTransitDelayAvg OBJECT-TYPE
     SYNTAX      Counter
     ACCESS      read-only
     STATUS      mandatory
     DESCRIPTION
        "The average transit delay between this
         node and the remote peer during the VBERT/VLOOP test."
     ::= { dfrapVnipTopologyEntry  22 }
      
dfrapVnipTopoVBertTimeElapse OBJECT-TYPE
     SYNTAX      TimeTicks
     ACCESS      read-only
     STATUS      mandatory
     DESCRIPTION
        "Elapsed time since VBERT/VLOOP test was started or cleared."
     ::= { dfrapVnipTopologyEntry  23 }


dfrapVnipTopoVBertPerUtilCIR OBJECT-TYPE
    SYNTAX      INTEGER
    ACCESS      read-only
    STATUS      mandatory
    DESCRIPTION
       " The calculated percent of CIR utilization during a VBERT test,
         this value is only valid after a test is complete not during."
    ::= { dfrapVnipTopologyEntry 24 }


dfrapVnipTopoVBertPerUtilEIR OBJECT-TYPE
    SYNTAX      INTEGER
    ACCESS      read-only
    STATUS      mandatory
    DESCRIPTION
       " The calculated percent of EIR utilization during a VBERT test,
         this value is only valid after a test is complete not during."
    ::= { dfrapVnipTopologyEntry 25 }


dfrapVnipTransitDelayClear    OBJECT-TYPE
     SYNTAX      INTEGER
     {
         clear-transit-delay (1)
     }
     ACCESS      write-only
     STATUS      mandatory
     DESCRIPTION
        "Allows the user to clear all the VNIP Transit Delay
         data collected in the VNIP topology database.
         (1) Clear entire Transit Delay results database"
     ::= { dfrapStatus 5 }

dfrapLmiSourcing OBJECT-TYPE
     SYNTAX      INTEGER
     {
         initializing         (1),
         passthrough          (2),
         status-enqs-to-dte   (3),
         status-enqs-to-dds   (4),
         status-rspns-to-dte  (5),
         status-rspns-to-dds  (6),
         disabled             (7),
         status-rspns-both    (8)
     }
     ACCESS      read-only
     STATUS      mandatory
     DESCRIPTION
        "If configured for Frame Relay with a non-zero LMI inactivity timer
         the unit will monitor the status of LMI and, if proper messaging
         is not detected, will attempt to emulate either Frame Relay DTE or 
         DCE devices in attempt to restore LMI to any attached equipment and 
         provide managed access for diagnostic purposes. Typically frads/routers 
         are Frame Relay DTE while switches are Frame Relay DCE but this model
         may vary. In the absence of full-duplex LMI, the unit will cycle 
         through various states in attempt to adapt to an LMI partner.  The 
         unit will try each state for the duration of the LMI Inactivity timer 
         and then advance to the next one if satisfactory handshaking is not 
         established. While in any of these states if full-duplex LMI handshaking 
         does appear, the unit will immediately revert to the passthrough state.
         (1) initializing
         (2) Passthrough: not sourcing any LMI messages.
         (3) Status Enquiries out DTE interface: unit is emulating a Frame 
             Relay DTE device out the its (physical) DTE interface. 
         (4) Status Enquiries out WAN interface: unit is emulating a Frame 
             Relay DTE device out the its WAN interface.
         (5) Status Responses out the DTE interface: unit is emulating a 
             Frame Relay DCE device out the its (physical) DTE interface
             (provisioning the single default management DLCI).
         (6) Status Responses out the WAN interface: unit is emulating a 
             Frame Relay DCE device out the its WAN interface (provisioning 
             the single default management DLCI).
         (7) Disabled - LMI Inactivity timer is zero or unit not configured
             for a Frame Relay application.
         (8) Status Responses out both DTE and WAN interfaces: unit is 
             configured for Fixed DCE mode of management and emulates a Frame
             Relay DCE independently on both ports (provisioning 
             the single default management DLCI)."
     ::= { dfrapStatus 6 }

dfrapVBertClear    OBJECT-TYPE
     SYNTAX      INTEGER
     {
         clear-vbert (1)
     }
     ACCESS      write-only
     STATUS      mandatory
     DESCRIPTION
        "Allows the user to clear all the VBERT data
         collected in the VNIP topology database as long as 
         the entry is not in a test status.
         (1) Clear all VBERT/VLOOP status information"
     ::= { dfrapStatus 11 }

--
--      Management Status 
--
--         The current status of the InBand Mangement configuration. 
--         This section is intended to display information of how the
--         node is configured for InBand Management.
--

dfrapStatusMgmtTable   OBJECT IDENTIFIER ::= { dfrapStatus 3 }

dfrapStatusMgmtChannel   OBJECT-TYPE
     SYNTAX  INTEGER
     {
        none             (1),
        slip             (2), 
        private-dlci     (3),
        piggyback-dlci   (4)
     }
     ACCESS  read-only
     STATUS  mandatory
     DESCRIPTION
         "This is the method in which the unit is configured for
          SNMP management access.
          (1) None: SNMP management disabled
          (2) SLIP: out-of-band management via asynchronous Serial Line IP
          (3) Private DLCI: in-band management using a private DLCI that 
              is dedicated solely to this unit's management.
          (4) Piggyback DLCI: in-band management using any DLCI optionally
              multiplexing both management and user data."
    ::= {dfrapStatusMgmtTable 1}                

dfrapStatusMgmtInterface   OBJECT-TYPE
     SYNTAX  INTEGER
     {
        comm             (1),
        local-dte        (2), 
        remote-wan           (3),
        local-and-remote (4)
     }
     ACCESS  read-only
     STATUS  mandatory
     DESCRIPTION
        "This is the port(s) on which the management traffic will appear.
         (1) Async Maintenance(Comm)/Console port - SLIP mode
         (2) Local DTE interface: unit is configured for Private Local 
             DLCI mode
         (3) Remote WAN Interface: unit is confiogured for Private Remote
             DLCI mode
         (4) DTE and WAN Interfaces: unit is configured for either Piggyback
             Bidirectional mode."
     ::= {dfrapStatusMgmtTable 2}                

dfrapStatusMgmtInterfaceStatus   OBJECT-TYPE
     SYNTAX  INTEGER
     {
        active     (1),
        inactive   (2), 
        alarm      (3)
     }
     ACCESS  read-only
     STATUS  mandatory
     DESCRIPTION
        "This is the status of the port(s) on which
         the management traffic will appear.
         (1) Active: port is configured and status is okay
         (2) Inactive: port is declared out of service 
         (3) Alarm: port is experiencing an alarm condition that may
             interefere with management access  "
     ::= {dfrapStatusMgmtTable 3}                

dfrapStatusMgmtDefaultDLCINo   OBJECT-TYPE
     SYNTAX  INTEGER
     ACCESS  read-only
     STATUS  mandatory
     DESCRIPTION
        "This is the DLCI for the PVC that is defined for the
        Management port.  All traffic using this DLCI in the Frame
        Replay packet will be destined for the InBand Management task."
     ::= {dfrapStatusMgmtTable 4}                

dfrapStatusMgmtDefaultDLCIStatus   OBJECT-TYPE
     SYNTAX  INTEGER
     {
        na              (1),
        dlci-active     (2), 
        dlci-inactive   (3)
     }
     ACCESS  read-only
     STATUS  mandatory
     DESCRIPTION
        "This is the status of the default management DLCI.
         (1) not applicable: SLIP mode or management is disabled
         (2) DLCI Active: default DLCI is active in the LMI full 
             status response.
         (3) DLCI Inactive: default DLCI is not active in the LMI full 
             status response."
     ::= {dfrapStatusMgmtTable 5}                

dfrapStatusLmiAutosense   OBJECT-TYPE
     SYNTAX  INTEGER
     {
        disabled            (1),
        searching           (2),
        learned-annex-d     (3),
        learned-annex-a     (4),
        learned-type1       (5)
     }
     ACCESS  read-only
     STATUS  mandatory
     DESCRIPTION
        "This indicates the current status of LMI Auto Sensing if 
         it's enabled.
         (1) Disabled: LMI is configured as Type 1, Annex-D, or Annex-A
         (2) Searching: unit is attempting to determine the LMI type of
             the attached equipment by issuing LMI messages of each LMI 
             type and searching for responses.
         (3) Learned Annex-D: unit has successfully detected Annex-D LMI
             (ANSI T1.617 Annex D)
         (4) Learned Annex-A: unit has successfully detected Annex-A LMI
             (ITU/CCITT Q.933 Annex A)
         (5) Learned Type 1: unit has successfully detected Type 1 LMI
             (Cisco, Group of four, LMI)"
     ::= { dfrapStatus 12 }


--
--      DTE Status 
--
--         The current status of the DTE port.
--

dfrapStatusDteTable   OBJECT IDENTIFIER ::= { dfrapStatus 7 }

dfrapStatusDteMode   OBJECT-TYPE
     SYNTAX  INTEGER
     {
        no-connections (1),
        active         (2),
        test           (3)
     }
     ACCESS  read-only
     STATUS  mandatory
     DESCRIPTION
        "Status of the DTE port. 
         (1) No-connections: indicates the port is not completely 
             to pass data to/from the WAN.
         (2) Active: port is configured and ready to pass data.
         (3) Test: diagnostic condition in process."
     ::= { dfrapStatusDteTable 1 }

dfrapStatusDteRts   OBJECT-TYPE
     SYNTAX  INTEGER
     {
         on  (1),
         off (2)
     }
     ACCESS  read-only
     STATUS  mandatory
     DESCRIPTION
        "Status of the Request to Send (RTS) signal from the DTE port.
         (1) RTS Active
         (2) RTS Inactive"
     ::= { dfrapStatusDteTable 2 }

dfrapStatusDteDtr   OBJECT-TYPE
     SYNTAX  INTEGER
     {
         on  (1),
         off (2)
     }
     ACCESS  read-only
     STATUS  mandatory
     DESCRIPTION
        "Status of the Data Terminal Ready (DTR) signal from the DTE port.
         (1) DTR Active
         (2) DTR Inactive"
     ::= { dfrapStatusDteTable 3 }

dfrapStatusDteDcd OBJECT-TYPE
     SYNTAX      INTEGER
     {
          on   (1),
          off  (2)
     }
     ACCESS      read-only
     STATUS      mandatory
     DESCRIPTION
        "Status of the Data Carrier Detect (DCD) signal driven by this
         unit towards the DTE port
         (1) DCD Active
         (2) DCD Inactive"
     ::= { dfrapStatusDteTable 4 }

dfrapStatusDteDsr OBJECT-TYPE
     SYNTAX      INTEGER
     {
          on   (1),
          off  (2)
     }
     ACCESS      read-only
     STATUS      mandatory
     DESCRIPTION
        "Status of the Data Set Ready (DSR) signal driven by this
         unit towards the DTE port.
         (1) DSR Active
         (2) DSR Inactive"        
     ::= { dfrapStatusDteTable 5 }

dfrapStatusDteCts OBJECT-TYPE
     SYNTAX      INTEGER
     {
          on   (1),
          off  (2)
     }
     ACCESS      read-only
     STATUS      mandatory
     DESCRIPTION
        "Status of the Clear to Send (CTS) signal driven by this
         unit towards the DTE port
         (1) CTS Active
         (2) CTS Inactive"
     ::= { dfrapStatusDteTable 6 }



--
--       The DDS Status Table
--              This table contains the status of the DDS port.

dfrapStatusDdsTable   OBJECT IDENTIFIER ::= { dfrapStatus 8 }

dfrapStatusDdsLineStatus   OBJECT-TYPE
     SYNTAX      INTEGER 
     {
         in-sync                  (1),
         out-of-service           (2),
         out-of-frame             (3),
         bpv-threshold-failure    (4),
         loss-of-signal           (5),
         simplex-current-loopback (6)
     }
     ACCESS      read-only
     STATUS      mandatory
     DESCRIPTION
         "The Current status of the physical interface.
          Your network carrier can send Out-of-Service 
          or Maintenance Mode codes.
          (1) in sync
          (2) out of service
          (3) out of frame
          (4) bipolar violations
          (5) loss of signal
          (6) simplex current loopback"
     ::= { dfrapStatusDdsTable 1 }

dfrapStatusDdsLoopLength    OBJECT-TYPE
     SYNTAX      INTEGER
     {
         loss-40-50db (1),
         loss-39-44db (2),
         loss-33-38db (3),
         loss-27-32db (4),
         loss-21-26db (5),
         loss-15-20db (6),
         loss-8-14db  (7),
         loss-1-7db   (8),
         loss-0db     (9)
     }
     ACCESS      read-only
     STATUS      mandatory
     DESCRIPTION
             "The estimated line attenuation (signal loss) on the 
              DDS channel. Actual cable length can be estimated with 
              the assumption that a good quality data grade cable 
              is used. Use of lower quality cabling will produce 
              greater line attenuation on shorter cable runs.
              (1) est. between 40 and 50dB line loss, equivalent 
                  to roughly 8 to 9 Kilometers of nominal cable length.
              (2) est. between 39 and 44dB line loss, equivalent 
                  to roughly 7 to 8 Kilometers of nominal cable length.
              (3) est. between 33 and 38dB line loss, equivalent 
                  to roughly 6 to 7 Kilometers of nominal cable length.
              (4) est. between 27 and 22dB line loss, equivalent 
                  to roughly 5 to 6 Kilometers of nominal cable length.
              (5) est. between 21 and 26dB line loss, equivalent 
                  to roughly 4 to 5 Kilometers of nominal cable length.
              (6) est. between 15 and 20dB line loss, equivalent 
                  to roughly 3 to 4 Kilometers of nominal cable length
              (7) est. between 8 and 14dB line loss, equivalent 
                  to roughly 2 to 3 Kilometers of nominal cable length
              (8) est. between 1 and 7dB line loss, equivalent 
                  to roughly .5 to 2 Kilometers of nominal cable length
              (9) est. 0dB line loss, equivalent to less than 1Km nominal
                  cable length" 
          ::= { dfrapStatusDdsTable 2 }

--
--      LED Status
--
--         The current status of the front-panel LED indicators at 
--         the DFRAP node.
--

dfrapStatusLedTable   OBJECT IDENTIFIER ::= { dfrapStatus 4 }

dfrapStatusDteModeLED   OBJECT-TYPE
     SYNTAX  INTEGER
     {
         offLED-DTE-inactive               (1),
         greenLED-normal                   (2),
         yellowLED-test-mode               (3)
     }
     ACCESS  read-only
     STATUS  mandatory
     DESCRIPTION
        "Status of the DTE Mode LED.
         (1) DTE Mode LED off: Missing control signals
         (2) DTE Mode LED green: Normal
         (3) DTE Mode LED yellow: Test Mode"
     ::= { dfrapStatusLedTable 1 }

dfrapStatusDteStatusLED   OBJECT-TYPE
     SYNTAX  INTEGER
     {
         greenLED-active                   (2)
     }
     ACCESS  read-only
     STATUS  mandatory
     DESCRIPTION
        "Status of the DTE Status LED.
         (1) DTE Status LED green: normal"
     ::= { dfrapStatusLedTable 2 }

dfrapStatusDteTxLED   OBJECT-TYPE
     SYNTAX  INTEGER
     {
        offLED-inactive                   (1),
        greenLED-tx-data-transmitting     (2)
     }
     ACCESS  read-only
     STATUS  mandatory
     DESCRIPTION
        "Status of the DTE Tx Data LED. In Frame Relay mode, this LED is ON 
         (green) when the DTE is not sending HDLC Flags and is OFF when
         HDLC flags are being transmit. In CBO mode, the LED is ON (green) 
         for a SPACE and OFF for a MARK.
         (1) DTE Transmit LED OFF: inactive (HDLC flags or CBO marks)
         (2) DTE Transmit LED ON: active (HDLC frames or CBO spaces)"
     ::= { dfrapStatusLedTable 3 }

dfrapStatusDteRxLED   OBJECT-TYPE
     SYNTAX  INTEGER
     {
        offLED-inactive                   (1),
        greenLED-rx-data-receiving        (2)
     }
     ACCESS  read-only
     STATUS  mandatory
     DESCRIPTION
        "Status of the DTE Rx Data LED. In Frame Relay mode, this LED is ON 
         (green) when the WAN is receiving HDLC Flags and is OFF when
         HDLC flags are being received. In CBO mode, the LED is ON (green) 
         for a SPACE and OFF for a MARK.
         (1) DTE Receive LED OFF: inactive (HDLC flags or CBO marks)
         (2) DTE Receive LED ON: active (HDLC frames or CBO spaces)"      
     ::= { dfrapStatusLedTable 4 }

dfrapStatusDdsModeLED   OBJECT-TYPE
     SYNTAX  INTEGER
     {
        greenLED-normal                   (2),
        yellowLED-test-mode               (3)
     }
     ACCESS  read-only
     STATUS  mandatory
     DESCRIPTION
      "Status of the DDS Mode LED.
       (1) DDS Mode LED is green: normal data mode
       (2) DDS Mode LED is yellow: test mode"
     ::= { dfrapStatusLedTable 5 }

dfrapStatusDdsStatusLED   OBJECT-TYPE
     SYNTAX  INTEGER
     {
        offLED-DDS-no-signal              (1),
        greenLED-normal                   (2),
        yellowLED-remote-alarm            (3)
     }
     ACCESS  read-only
     STATUS  mandatory
     DESCRIPTION
        "Status of the DDS Status LED.
         (1) DDS Status LED is OFF: no signal received from WAN
         (2) DDS Status LED is green: normal
         (3) DDS Status LED is yellow: remote alarm"
     ::= { dfrapStatusLedTable 6 }

dfrapStatusAllLEDs   OBJECT-TYPE
     SYNTAX  DisplayString (SIZE (0..7))
     ACCESS  read-only
     STATUS  mandatory
     DESCRIPTION
      "Status of all six DFRAP LEDs, encoded in a string.
           'F'    off
           '5'    green
           '0'    yellow
           'A'    red
           '7'    blinking green and off
           '3'    blinking yellow and off
           'B'    blinking red and off
           '4'    blinking green and yellow
           '6'    blinking green and red
           '8'    blinking yellow and red

       Positionally, the 6 letters are DTE Mode, DTE status,
       Dte Tx, Dte Rx, DDS Mode, and DDS Status.  For example,
       '555550' would mean:  DTE in normal mode, active status,
       transmitting and receiving and DDS normal with remote alarm."
     ::= { dfrapStatusLedTable 7 }


-- =========================
-- ==  PERFORMANCE group  ==
-- =========================

dfrapPerformance  OBJECT IDENTIFIER ::= { dfrap 5 }

--
--    IP protocol stack statistics - a reflection of some MIB-2 variables
--

dfrapPerfMgmtIp   OBJECT IDENTIFIER ::= { dfrapPerformance 2 }

   dfrapPerfMgmtIpIFStatsTable OBJECT IDENTIFIER ::= { dfrapPerfMgmtIp 1 }

          dfrapPerfMgmtIpIFInOctets OBJECT-TYPE
              SYNTAX  Counter
              ACCESS  read-only
              STATUS  mandatory
              DESCRIPTION
                      "The count of all management octets received.
                       Same as ifInOctets in mib-2."
              ::= { dfrapPerfMgmtIpIFStatsTable 1 }

          dfrapPerfMgmtIpIFInErrors OBJECT-TYPE
              SYNTAX  Counter
              ACCESS  read-only
              STATUS  mandatory
              DESCRIPTION
                      "The count of management packets received that could
                       not be delivered because of errors. Same as 
                       ifInErrors in mib-2."
              ::= { dfrapPerfMgmtIpIFStatsTable 2 }

          dfrapPerfMgmtIpIFOutOctets OBJECT-TYPE
              SYNTAX  Counter
              ACCESS  read-only
              STATUS  mandatory
              DESCRIPTION
                      "The count of all management octets transmitted.
                       Same as ifOutOctets in mib-2."
              ::= { dfrapPerfMgmtIpIFStatsTable 3 }

          dfrapPerfMgmtIpIFOperStatus OBJECT-TYPE
              SYNTAX  INTEGER 
              {
                  up(1),
                  down(2),
                  testing(3)
              }
              ACCESS  read-only
              STATUS  mandatory
              DESCRIPTION
                      "The current operational state.
                       Same as ifOperStatus in mib-2.
                       (1) link up
                       (2) link down
                       (30 test"
              ::= { dfrapPerfMgmtIpIFStatsTable 4 }

   dfrapPerfMgmtIpIPStatsTable OBJECT IDENTIFIER ::= { dfrapPerfMgmtIp 2 }

          dfrapPerfMgmtIpIPInRcv OBJECT-TYPE
              SYNTAX  Counter
              ACCESS  read-only
              STATUS  mandatory
              DESCRIPTION
                      "The count of all management datagrams received.
                       Same as ipInReceives in mib-2."
              ::= { dfrapPerfMgmtIpIPStatsTable 1 }

          dfrapPerfMgmtIpIPInHdrErr OBJECT-TYPE
              SYNTAX  Counter
              ACCESS  read-only
              STATUS  mandatory
              DESCRIPTION
                      "The count of management datagrams received that were
                       discarded because of errors in their IP headers.
                       Same as ipInHdrErrors in mib-2."
              ::= { dfrapPerfMgmtIpIPStatsTable 2 }

          dfrapPerfMgmtIpIPInAddrErr OBJECT-TYPE
              SYNTAX  Counter
              ACCESS  read-only
              STATUS  mandatory
              DESCRIPTION
                      "The count of management datagrams received that were
                       discarded because unexpected or invalid IP
                       addresses in their IP headers.
                       Same as ipInAddrErrors in mib-2."
              ::= { dfrapPerfMgmtIpIPStatsTable 3 }

          dfrapPerfMgmtIpIPInProtUnk OBJECT-TYPE
              SYNTAX  Counter
              ACCESS  read-only
              STATUS  mandatory
              DESCRIPTION
                      "The count of management datagrams received that were
                       discarded because of unsupported protocols.
                       Same as ipInUnknownProtos in mib-2."
              ::= { dfrapPerfMgmtIpIPStatsTable 4 }

          dfrapPerfMgmtIpIPInDscrd OBJECT-TYPE
              SYNTAX  Counter
              ACCESS  read-only
              STATUS  mandatory
              DESCRIPTION
                      "The count of management datagrams received that were
                       discarded for reasons other than a problem with
                       the datagram. Same as ipInDiscards in mib-2."
              ::= { dfrapPerfMgmtIpIPStatsTable 5 }

          dfrapPerfMgmtIpIPInDlvrs OBJECT-TYPE
              SYNTAX  Counter
              ACCESS  read-only
              STATUS  mandatory
              DESCRIPTION
                      "The count of management datagrams received that were
                       delivered to IP client-protocols.
                       Same as ipInDelivers in mib-2."
              ::= { dfrapPerfMgmtIpIPStatsTable 6 }

          dfrapPerfMgmtIpIPOutRqst OBJECT-TYPE
              SYNTAX  Counter
              ACCESS  read-only
              STATUS  mandatory
              DESCRIPTION
                      "The count of all outgoing management datagrams
                       originating in this node.
                       Same as ipOutRequests in mib-2."
              ::= { dfrapPerfMgmtIpIPStatsTable 7 }

          dfrapPerfMgmtIpIPOutDscrd OBJECT-TYPE
              SYNTAX  Counter
              ACCESS  read-only
              STATUS  mandatory
              DESCRIPTION
                      "The count of outgoing management datagrams that were
                       discarded for reasons other than a problem with
                       the datagram. Same as ipOutDiscards in mib-2."
              ::= { dfrapPerfMgmtIpIPStatsTable 8 }

          dfrapPerfMgmtIpIPOutNoRt OBJECT-TYPE
              SYNTAX  Counter
              ACCESS  read-only
              STATUS  mandatory
              DESCRIPTION
                      "The count of outgoing management datagrams that were
                       discarded because no route could be found
                       for transmission.
                       Same as ipOutNoRoutes in mib-2."
              ::= { dfrapPerfMgmtIpIPStatsTable 9 }


   dfrapPerfMgmtIpICMPStatsTable OBJECT IDENTIFIER ::= { dfrapPerfMgmtIp 3 }

          dfrapPerfMgmtIpICMPInMsgs OBJECT-TYPE
              SYNTAX  Counter
              ACCESS  read-only
              STATUS  mandatory
              DESCRIPTION
                      "The count of all management ICMP messages received.
                       Same as icmpInMsgs in mib-2."
              ::= { dfrapPerfMgmtIpICMPStatsTable 1 }

          dfrapPerfMgmtIpICMPInErrors OBJECT-TYPE
              SYNTAX  Counter
              ACCESS  read-only
              STATUS  mandatory
              DESCRIPTION
                      "The count of management ICMP messages received with
                       errors. Same as icmpInErrors in mib-2."
              ::= { dfrapPerfMgmtIpICMPStatsTable 2 }

          dfrapPerfMgmtIpICMPInDestUnreachs OBJECT-TYPE
              SYNTAX  Counter
              ACCESS  read-only
              STATUS  mandatory
              DESCRIPTION
                      "The count of management ICMP Destination Unreachable
                       messages received.
                       Same as icmpInDestUnreachs in mib-2."
              ::= { dfrapPerfMgmtIpICMPStatsTable 3 }

          dfrapPerfMgmtIpICMPInTimeExcds OBJECT-TYPE
              SYNTAX  Counter
              ACCESS  read-only
              STATUS  mandatory
              DESCRIPTION
                      "The count of management ICMP Time Exceeded messages
                       received.
                       Same as icmpInTimeExcds in mib-2."
              ::= { dfrapPerfMgmtIpICMPStatsTable 4 }

          dfrapPerfMgmtIpICMPInParmProbs OBJECT-TYPE
              SYNTAX  Counter
              ACCESS  read-only
              STATUS  mandatory
              DESCRIPTION
                      "The count of management ICMP Parameter Problem messages
                       received.
                       Same as icmpInParmProbs in mib-2."
              ::= { dfrapPerfMgmtIpICMPStatsTable 5 }

          dfrapPerfMgmtIpICMPInRedirects OBJECT-TYPE
              SYNTAX  Counter
              ACCESS  read-only
              STATUS  mandatory
              DESCRIPTION
                      "The count of management ICMP Redirect messages received.
                       Same as icmpInRedirects in mib-2."
              ::= { dfrapPerfMgmtIpICMPStatsTable 6 }

          dfrapPerfMgmtIpICMPInEchos OBJECT-TYPE
              SYNTAX  Counter
              ACCESS  read-only
              STATUS  mandatory
              DESCRIPTION
                      "The count of management ICMP Echo messages received.
                       Same as icmpInEchos in mib-2."
              ::= { dfrapPerfMgmtIpICMPStatsTable 7 }

          dfrapPerfMgmtIpICMPInEchoReps OBJECT-TYPE
              SYNTAX  Counter
              ACCESS  read-only
              STATUS  mandatory
              DESCRIPTION
                      "The count of management ICMP Echo Reply messages received.
                       Same as icmpInEchoReps in mib-2."
              ::= { dfrapPerfMgmtIpICMPStatsTable 8 }

          dfrapPerfMgmtIpICMPOutMsgs OBJECT-TYPE
              SYNTAX  Counter
              ACCESS  read-only
              STATUS  mandatory
              DESCRIPTION
                      "The count of all outgoing management ICMP messages
                       originating in this node.
                       Same as icmpOutMsgs in mib-2."
              ::= { dfrapPerfMgmtIpICMPStatsTable 9 }

          dfrapPerfMgmtIpICMPOutErrors OBJECT-TYPE
              SYNTAX  Counter
              ACCESS  read-only
              STATUS  mandatory
              DESCRIPTION
                      "The count of outgoing management ICMP messages not
                       transmitted due problems found by the ICMP layer.                                        which this entity did
                       Same as icmpOutErrors in mib-2."
              ::= { dfrapPerfMgmtIpICMPStatsTable 10 }

          dfrapPerfMgmtIpICMPOutDestUnreachs OBJECT-TYPE
              SYNTAX  Counter
              ACCESS  read-only
              STATUS  mandatory
              DESCRIPTION
                      "The count of outgoing management ICMP Destination Unreachable
                       messages.
                       Same as icmpOutDestUnreachs in mib-2."
              ::= { dfrapPerfMgmtIpICMPStatsTable 11 }

          dfrapPerfMgmtIpICMPOutParmProbs OBJECT-TYPE
              SYNTAX  Counter
              ACCESS  read-only
              STATUS  mandatory
              DESCRIPTION
                      "The count of outgoing management ICMP Parameter Problem
                       messages.
                       Same as icmpOutParmProbs in mib-2."
              ::= { dfrapPerfMgmtIpICMPStatsTable 12 }

          dfrapPerfMgmtIpICMPOutRedirects OBJECT-TYPE
              SYNTAX  Counter
              ACCESS  read-only
              STATUS  mandatory
              DESCRIPTION
                      "The count of outgoing management ICMP Redirect messages.
                       Same as icmpOutRedirects in mib-2."
              ::= { dfrapPerfMgmtIpICMPStatsTable 13 }

          dfrapPerfMgmtIpICMPOutEchos OBJECT-TYPE
              SYNTAX  Counter
              ACCESS  read-only
              STATUS  mandatory
              DESCRIPTION
                      "The count of management outgoing ICMP Echo messages.
                       Same as icmpOutEchos in mib-2."
              ::= { dfrapPerfMgmtIpICMPStatsTable 14 }

          dfrapPerfMgmtIpICMPOutEchoReps OBJECT-TYPE
              SYNTAX  Counter
              ACCESS  read-only
              STATUS  mandatory
              DESCRIPTION
                      "The count of management outgoing ICMP Echo Reply messages.
                       Same as icmpOutEchoReps in mib-2."
              ::= { dfrapPerfMgmtIpICMPStatsTable 15 }

   dfrapPerfMgmtIpUDPStatsTable OBJECT IDENTIFIER ::= { dfrapPerfMgmtIp 4 }

          dfrapPerfMgmtIpUDPInDatagrams OBJECT-TYPE
              SYNTAX  Counter
              ACCESS  read-only
              STATUS  mandatory
              DESCRIPTION
                      "The count of all management UDP datagrams received.
                       Same as udpInDatagrams in mib-2."
              ::= { dfrapPerfMgmtIpUDPStatsTable 1 }

          dfrapPerfMgmtIpUDPOutDatagrams OBJECT-TYPE
              SYNTAX  Counter
              ACCESS  read-only
              STATUS  mandatory
              DESCRIPTION
                      "The count of all management UDP datagrams sent.
                       Same as udpOutDatagrams in mib-2."
              ::= { dfrapPerfMgmtIpUDPStatsTable 2 }

          dfrapPerfMgmtIpUDPNoPorts OBJECT-TYPE
              SYNTAX  Counter
              ACCESS  read-only
              STATUS  mandatory
              DESCRIPTION
                      "The count of all management UDP datagrams received
                       with no application at the destination port.
                       Same as udpNoPorts in mib-2."
              ::= { dfrapPerfMgmtIpUDPStatsTable 3 }


   dfrapPerfMgmtIpTCPStatsTable OBJECT IDENTIFIER ::= { dfrapPerfMgmtIp 5 }

          dfrapPerfMgmtIpTCPActiveOpens OBJECT-TYPE
              SYNTAX  Counter
              ACCESS  read-only
              STATUS  mandatory
              DESCRIPTION
                      "The count of the times management TCP connections
                       have made a direct state transition from CLOSED to 
                       SYN-SENT.
                       Same as tcpActiveOpens in mib-2."
              ::= { dfrapPerfMgmtIpTCPStatsTable 1 }

          dfrapPerfMgmtIpTCPPassiveOpens OBJECT-TYPE
              SYNTAX  Counter
              ACCESS  read-only
              STATUS  mandatory
              DESCRIPTION
                      "The count of the times management TCP connections 
                       have made a direct state transition from CLOSED to 
                       SYN-RCVD.
                       Same as tcpPassiveOpens in mib-2."
              ::= { dfrapPerfMgmtIpTCPStatsTable 2 }

          dfrapPerfMgmtIpTCPAttemptFails OBJECT-TYPE
              SYNTAX  Counter
              ACCESS  read-only
              STATUS  mandatory
              DESCRIPTION
                      "The count of the times management TCP connections
                       have made a direct state transition from SYN-SENT 
                       or SYN-RCVD to CLOSED state, plus the
                       count of the times TCP connections have made a
                       direct state transition from SYN-RCVD to LISTEN.
                       Same as tcpAttemptFails in mib-2."
              ::= { dfrapPerfMgmtIpTCPStatsTable 3 }

          dfrapPerfMgmtIpTCPCurrEstab OBJECT-TYPE
              SYNTAX  Gauge
              ACCESS  read-only
              STATUS  mandatory
              DESCRIPTION
                      "The count of the management TCP connections in state
                       ESTABLISHED or CLOSE-WAIT.
                       Same as tcpCurrEstab in mib-2."
              ::= { dfrapPerfMgmtIpTCPStatsTable 4 }

          dfrapPerfMgmtIpTCPInSegs OBJECT-TYPE
              SYNTAX  Counter
              ACCESS  read-only
              STATUS  mandatory
              DESCRIPTION
                      "The count of all the management segments received.
                       Same as tcpInSegs in mib-2."
              ::= { dfrapPerfMgmtIpTCPStatsTable 5 }

          dfrapPerfMgmtIpTCPOutSegs OBJECT-TYPE
              SYNTAX  Counter
              ACCESS  read-only
              STATUS  mandatory
              DESCRIPTION
                      "The count of all the management segments sent.
                       Same as tcpOutSegs in mib-2."
              ::= { dfrapPerfMgmtIpTCPStatsTable 6 }


--
--       The DFRAP Performance Thruput Table
--              This table contains interface Thruput statistics for 
--              the DTE port and the DDS port
--              This table does NOT contain any per-PVC statistics
--              
--

dfrapPerfThruput   OBJECT IDENTIFIER ::= { dfrapPerformance 3 }

--
--       The DLCI Statistics Table
--              This table contains the DLCI Statistics (layer 2).

   Index ::= INTEGER

dfrapPerfThruputPerIntfTable  OBJECT-TYPE
     SYNTAX  SEQUENCE OF DfrapPerfThruputPerIntfEntry
     ACCESS  not-accessible
     STATUS  mandatory
     DESCRIPTION
        "The throughput per interface table. These values are accumulated
         across all DLCIs."
     ::= { dfrapPerfThruput 1 }

dfrapPerfThruputPerIntfEntry  OBJECT-TYPE
     SYNTAX  DfrapPerfThruputPerIntfEntry
     ACCESS  not-accessible
     STATUS  mandatory
     DESCRIPTION
        "An entry in the throughput per interface table."
     INDEX   { dfrapPerfThruputPerIntfIndex }
     ::= { dfrapPerfThruputPerIntfTable 1 }

DfrapPerfThruputPerIntfEntry ::=
     SEQUENCE
     {
        dfrapPerfThruputPerIntfIndex       INTEGER, 
        dfrapPerfThruputPerIntfRxByteCnt   Counter,
        dfrapPerfThruputPerIntfTxByteCnt   Counter,
        dfrapPerfThruputPerIntfRxFrameCnt  Counter,
        dfrapPerfThruputPerIntfTxFrameCnt  Counter,
        dfrapPerfThruputPerIntfRxCrcErrCnt Counter,
        dfrapPerfThruputPerIntfRxAbortCnt  Counter,
        dfrapPerfThruputPerIntfRxBpvCnt    Counter
     }

   dfrapPerfThruputPerIntfIndex    OBJECT-TYPE
          SYNTAX      INTEGER
          {
             dte   (1),
             dds   (2)
          }
          ACCESS      read-only
          STATUS      mandatory
          DESCRIPTION
             "Interface for which the statistics apply.
              (1) DTE interface
              (2) DDS interface" 
          ::= { dfrapPerfThruputPerIntfEntry 1 }

   dfrapPerfThruputPerIntfRxByteCnt    OBJECT-TYPE
          SYNTAX      Counter 
          ACCESS      read-only
          STATUS      mandatory
          DESCRIPTION
             "The number of framed bytes that have been received
              on this interface."
          ::= { dfrapPerfThruputPerIntfEntry 2 }

   dfrapPerfThruputPerIntfTxByteCnt    OBJECT-TYPE
             SYNTAX      Counter
             ACCESS      read-only
             STATUS      mandatory
             DESCRIPTION
                "The number of framed bytes that have been transmit
                 on this interface."
             ::= { dfrapPerfThruputPerIntfEntry 3 }

   dfrapPerfThruputPerIntfRxFrameCnt    OBJECT-TYPE
             SYNTAX      Counter 
             ACCESS      read-only
             STATUS      mandatory
             DESCRIPTION
                "The number of frames that have been received
                 on this interface."
             ::= { dfrapPerfThruputPerIntfEntry 4 }

   dfrapPerfThruputPerIntfTxFrameCnt    OBJECT-TYPE
             SYNTAX      Counter 
             ACCESS      read-only
             STATUS      mandatory
             DESCRIPTION
                "The number of frames that have been transmit
                 on this interface."
             ::= { dfrapPerfThruputPerIntfEntry 5 }

   dfrapPerfThruputPerIntfRxCrcErrCnt  OBJECT-TYPE
             SYNTAX      Counter 
             ACCESS      read-only
             STATUS      mandatory
             DESCRIPTION
                "The number of frames with CRC errors received
                 on this interface."
            ::= { dfrapPerfThruputPerIntfEntry 6 }

   dfrapPerfThruputPerIntfRxAbortCnt   OBJECT-TYPE
             SYNTAX      Counter 
             ACCESS      read-only
             STATUS      mandatory
             DESCRIPTION
                "The number of aborted frames received
                 on this interface."
            ::= { dfrapPerfThruputPerIntfEntry 7 }

   dfrapPerfThruputPerIntfRxBpvCnt   OBJECT-TYPE
             SYNTAX      Counter 
             ACCESS      read-only
             STATUS      mandatory
             DESCRIPTION
                "The number of BPV errors received
                 on this interface."
            ::= { dfrapPerfThruputPerIntfEntry 8 }



   dfrapPerfThruputPerDlciTable OBJECT-TYPE
         SYNTAX   SEQUENCE OF DfrapPerfThruputPerDlciEntry
         ACCESS   not-accessible
         STATUS   mandatory
         DESCRIPTION
            "Layer 2 statistics on a per-DLCI basis. Transmit direction
             is from DTE to WAN and receive direction is from the WAN
             towards the DTE."
         ::= { dfrapPerfThruput 2 }

         dfrapPerfThruputPerDlciEntry OBJECT-TYPE
             SYNTAX   DfrapPerfThruputPerDlciEntry
             ACCESS   not-accessible
             STATUS   mandatory
             DESCRIPTION
                "The Statistics for a particular Data Link
                 Connection Management Interface (DLCI)."
            INDEX { dfrapPerfThruputPerDlciIndex,
                    dfrapPerfThruputPerDlciValue }
            ::= { dfrapPerfThruputPerDlciTable 1 }

         DfrapPerfThruputPerDlciEntry ::=
             SEQUENCE
             {
                 dfrapPerfThruputPerDlciIndex               Index,
                 dfrapPerfThruputPerDlciValue               INTEGER,
                 dfrapPerfThruputPerDlciCreateTime          INTEGER,
                 dfrapPerfThruputPerDlciChangeTime          INTEGER,
                 dfrapPerfThruputPerDlciRxByte              Counter,
                 dfrapPerfThruputPerDlciTxByte              Counter,
                 dfrapPerfThruputPerDlciRxFrame             Counter,
                 dfrapPerfThruputPerDlciTxFrame             Counter,
                 dfrapPerfThruputPerDlciRxFecn              Counter,
                 dfrapPerfThruputPerDlciRxBecn              Counter,
                 dfrapPerfThruputPerDlciRxDe                Counter,
                 dfrapPerfThruputPerDlciTxDe                Counter,
                 dfrapPerfThruputPerDlciRxThruput           INTEGER,
                 dfrapPerfThruputPerDlciTxThruput           INTEGER,
                 dfrapPerfThruputPerDlciCIR                 INTEGER,
                 dfrapPerfThruputPerDlciUptime              INTEGER,
                 dfrapPerfThruputPerDlciDowntime            INTEGER,
                 dfrapPerfThruputPerDlciCirType             INTEGER,
                 dfrapPerfThruputPerDlciPvcState            INTEGER,
                 dfrapPerfThruputPerDlciOutageCount         Counter,
                 dfrapPerfThruputPerDlciAvailability        INTEGER,
                 dfrapPerfThruputPerDlciMTBSO               INTEGER,
                 dfrapPerfThruputPerDlciMTTSR               INTEGER,
                 dfrapPerfThruputPerDlciEncapType           INTEGER,
                 dfrapPerfThruputPerDlciRxUtilizationStatus INTEGER,
                 dfrapPerfThruputPerDlciTxUtilizationStatus INTEGER,
                 dfrapPerfThruputPerDlciEIR                 INTEGER
             }

   dfrapPerfThruputPerDlciIndex OBJECT-TYPE
             SYNTAX   Index
             ACCESS   read-only
             STATUS   mandatory
             DESCRIPTION
                "This value must be in the range 1-3.
                 Other than that, this value is ignored as
                 all three will return the same result."
            ::= { dfrapPerfThruputPerDlciEntry 1 }

   dfrapPerfThruputPerDlciValue    OBJECT-TYPE
             SYNTAX      INTEGER 
             ACCESS      read-only
             STATUS      mandatory
             DESCRIPTION
                "The DLCI value in which the Statistics are associated."
            ::= { dfrapPerfThruputPerDlciEntry 2 }

   dfrapPerfThruputPerDlciCreateTime    OBJECT-TYPE
             SYNTAX      INTEGER 
             ACCESS      read-only
             STATUS      mandatory
             DESCRIPTION
                "The amount of time elapsed since this DLCI was first
                 detected through traffic sensing or in an LMI message 
                 (in seconds)."
            ::= { dfrapPerfThruputPerDlciEntry 3 }

   dfrapPerfThruputPerDlciChangeTime    OBJECT-TYPE
             SYNTAX      INTEGER 
             ACCESS      read-only
             STATUS      mandatory
             DESCRIPTION
                "The amount of elapsed time since this DLCI last
                 changed state from active to inactive or vice versa
                 (in seconds)."
            ::= { dfrapPerfThruputPerDlciEntry 4 }

   dfrapPerfThruputPerDlciRxByte    OBJECT-TYPE
             SYNTAX      Counter 
             ACCESS      read-only
             STATUS      mandatory
             DESCRIPTION
                "The number of bytes that have been received from
                 the WAN towards the DTE on this DLCI. This count
                 will include any frames that are terminated by the 
                 unit and do not pass through to the opposite interface 
                 (management and networking data)."
            ::= { dfrapPerfThruputPerDlciEntry 5 }

   dfrapPerfThruputPerDlciTxByte    OBJECT-TYPE
             SYNTAX      Counter
             ACCESS      read-only
             STATUS      mandatory
             DESCRIPTION
                "The number of bytes that have been transmit from the
                 DTE towards the WAN on this DLCI. This count
                 will include any frames that are terminated by the 
                 unit and do not pass through to the opposite interface 
                 (management and networking data)."
       ::= { dfrapPerfThruputPerDlciEntry 6 }

   dfrapPerfThruputPerDlciRxFrame    OBJECT-TYPE
             SYNTAX      Counter
             ACCESS      read-only
             STATUS      mandatory
             DESCRIPTION
                "The number of frames that have been received from
                 the WAN towards to the DTE on this DLCI. This count
                 will include any frames that are terminated by the 
                 unit and do not pass through to the opposite interface 
                 (management and networking data)."
            ::= { dfrapPerfThruputPerDlciEntry 7 }

   dfrapPerfThruputPerDlciTxFrame    OBJECT-TYPE
             SYNTAX      Counter
             ACCESS      read-only
             STATUS      mandatory
             DESCRIPTION
                "The number of frames that have been transmit from the
                 DTE towards the WAN on this DLCI. This count
                 will include any frames that are terminated by the 
                 unit and do not pass through to the opposite interface 
                 (management and networking data)."
            ::= { dfrapPerfThruputPerDlciEntry 8 }

   dfrapPerfThruputPerDlciRxFecn    OBJECT-TYPE
             SYNTAX      Counter
             ACCESS      read-only
             STATUS      mandatory
             DESCRIPTION
                "The number frames received from the WAN towards the DTE 
                 that have had the Forward Explict Congestion Notification 
                 (FECN) bit set on this DLCI. This count will include any 
                 frames that are terminated by the unit and do not pass 
                 through to the opposite interface (management and networking 
                 data)."
            ::= { dfrapPerfThruputPerDlciEntry 9 }

   dfrapPerfThruputPerDlciRxBecn    OBJECT-TYPE
             SYNTAX      Counter
             ACCESS      read-only
             STATUS      mandatory
             DESCRIPTION
                "The number frames received from the WAN towards the DTE 
                 that have had the Backward Explict Congestion Notification 
                 (BECN) bit set on this DLCI. This count will include any 
                 frames that are terminated by the unit and do not pass 
                 through to the opposite interface (management and networking 
                 data)."
            ::= { dfrapPerfThruputPerDlciEntry 10 }

   dfrapPerfThruputPerDlciRxDe    OBJECT-TYPE
             SYNTAX      Counter
             ACCESS      read-only
             STATUS      mandatory
             DESCRIPTION
                "The number frames received from the WAN towards the DTE 
                 that have had the Discard Eligibility (DE) bit set on 
                 this DLCI. This count will include any frames that are 
                 terminated by the unit and do not pass through to the 
                 opposite interface (management and networking data)."
            ::= { dfrapPerfThruputPerDlciEntry 11 }

   dfrapPerfThruputPerDlciTxDe    OBJECT-TYPE
             SYNTAX      Counter
             ACCESS      read-only
             STATUS      mandatory
             DESCRIPTION
                "The number frames transmit towards the WAN from the DTE 
                 that have had the Discard Eligibility (DE) bit set on 
                 this DLCI. This count will include any frames that are 
                 terminated by the unit and do not pass through to the 
                 opposite interface (management and networking data)."
            ::= { dfrapPerfThruputPerDlciEntry 12 }

   dfrapPerfThruputPerDlciRxThruput    OBJECT-TYPE
             SYNTAX      INTEGER
             ACCESS      read-only
             STATUS      mandatory
             DESCRIPTION
                "The number of bits/sec received from the WAN on this 
                 DLCI. This count will include any frames that are 
                 terminated by the unit and do not pass through to the 
                 opposite interface (management and networking data)."
            ::= { dfrapPerfThruputPerDlciEntry 13 }

   dfrapPerfThruputPerDlciTxThruput    OBJECT-TYPE
             SYNTAX      INTEGER
             ACCESS      read-only
             STATUS      mandatory
             DESCRIPTION
                "The number of bits/sec transmit to the WAN on this 
                 DLCI. This count will include any frames that are 
                 terminated by the unit and do not pass through to 
                 the opposite interface (management and networking data)."
            ::= { dfrapPerfThruputPerDlciEntry 14 }

   dfrapPerfThruputPerDlciCIR    OBJECT-TYPE
             SYNTAX      INTEGER
             ACCESS      read-only
             STATUS      mandatory
             DESCRIPTION
                "The Committed Information Rate (CIR) for this DLCI.
                 This can come form one of three sources: From the LMI
                 Full Status Response, configured by the user, or 
                 the DTE line rate (default)."
            ::= { dfrapPerfThruputPerDlciEntry 15 }

      dfrapPerfThruputPerDlciCirType    OBJECT-TYPE
             SYNTAX      INTEGER 
             {
               cir-acquired-from-lmi  (1),
               cir-configured-by-user (2),
               cir-is-dte-datarate    (3)
             }
             ACCESS      read-only
             STATUS      mandatory
             DESCRIPTION
               "The source of the CIR value for this DLCI. 
                (1) CIR acquired from LMI message. Will override user
                    configured CIR. This feature is not supported by all
                    Frame Relay DCE (switches).
                (2) CIR configured by user.
                (3) CIR is DTE Line Rate. Default if CIR is not set
                    by one of the other methods."
            ::= { dfrapPerfThruputPerDlciEntry 18 }

      dfrapPerfThruputPerDlciUptime    OBJECT-TYPE
             SYNTAX      INTEGER 
             ACCESS      read-only
             STATUS      mandatory
             DESCRIPTION
                "The total amount of time that the DLCI has been up as
                 reproted by the LMI Full Status Response (in seconds)."
            ::= { dfrapPerfThruputPerDlciEntry 16 }

      dfrapPerfThruputPerDlciDowntime    OBJECT-TYPE
             SYNTAX      INTEGER 
             ACCESS      read-only
             STATUS      mandatory
             DESCRIPTION
                "The total amount of time that the DLCI has been declared
                 down (in seconds). A DLCI is Down if it's explicitly 
                 declared Inactive through LMI or if it's missing from the 
                 LMI Full Status message or if there is no Full Status 
                 message at all."
            ::= { dfrapPerfThruputPerDlciEntry 17 }

   dfrapPerfThruputPerDlciPvcState   OBJECT-TYPE
          SYNTAX       INTEGER
          {
            pvc-active        (1),
            pvc-inactive      (2),
            pvc-unprovisioned (3),
            pvc-not-in-lmi    (4),
            pvc-lmi-timeout   (5),
            pvc-undetermined  (6)
          }
          ACCESS      read-only
          STATUS      mandatory
          DESCRIPTION
             "The current state of the DLCI:
            (1) DLCI marked active in last full status LMI
            (2) DLCI in last full status LMI but not marked active
            (3) DLCI has never been seen in a full status LMI
            (4) DLCI was seen at least once in a full status LMI
                but was not in the last full status LMI
            (5) the full status LMI has timed out; all previously
                active or inactive DLCIs are changed to this state
            (6) DLCI was detected in the traffic stream and a full
                status LMI has not been received so the state cannot
                be determined yet. "
         ::= { dfrapPerfThruputPerDlciEntry 19 }
         
   dfrapPerfThruputPerDlciOutageCount   OBJECT-TYPE
          SYNTAX      Counter
          ACCESS      read-only
          STATUS      mandatory
          DESCRIPTION
             "The number of times the smperPerfThruputPerDlciPvcState
             transitions from pvc-active or pvc-undetermined to one
             of the other (inactive) states. "
            ::= { dfrapPerfThruputPerDlciEntry 20 }

   dfrapPerfThruputPerDlciAvailability    OBJECT-TYPE
          SYNTAX      INTEGER
          ACCESS      read-only
          STATUS      mandatory
          DESCRIPTION
                "The measure of the percentage time the DLCI is
             available: UpTime/CreateTime or zero if CreateTime
             = 0. (in 1/1000 per cent; i.e. availability = 1000 
             converts to 1%). "
            ::= { dfrapPerfThruputPerDlciEntry 21 }

   dfrapPerfThruputPerDlciMTBSO    OBJECT-TYPE
          SYNTAX      INTEGER
          ACCESS      read-only
          STATUS      mandatory
          DESCRIPTION
             "Mean Time Between Service Outages: UpTime/OutageCount
             or zero if OutageCount = 0 (in seconds). "
            ::= { dfrapPerfThruputPerDlciEntry 22 }

   dfrapPerfThruputPerDlciMTTSR    OBJECT-TYPE
          SYNTAX      INTEGER
          ACCESS      read-only
          STATUS      mandatory
          DESCRIPTION
             "Mean Time to ServiceRestoral: DownTime/OutageCount
             or zero if OutageCount = 0 (in seconds). "
            ::= { dfrapPerfThruputPerDlciEntry 23 }

   dfrapPerfThruputPerDlciEncapType   OBJECT-TYPE
          SYNTAX      INTEGER
          {
            encap-na      (1),
            encap-1490    (2),
            encap-cisco   (3),
            encap-annex-g (4),
            encap-other   (5)
          }
          ACCESS      read-only
          STATUS      mandatory
          DESCRIPTION
             "The encapsulation protocol seen in the last frame
             analyzed on this DLCI:
             (1) DLCI is the LMI DLCI or no frames have been
                 analyzed
             (2) The encapsulation is per rfc1490
             (3) The encapsulation is per Cisco proprietary
             (4) The encapsulation is per Annex-G (X.25 over
                 frame relay)
             (5) The encapsulation is not one of the above. "
            ::= { dfrapPerfThruputPerDlciEntry 24 }

   dfrapPerfThruputPerDlciRxUtilizationStatus OBJECT-TYPE
             SYNTAX      INTEGER
             {
               clear                  (1),
               over-threshold         (2),
               alarm                  (3),
               alarm-under-threshold  (4)
             }
             ACCESS      read-only
             STATUS      mandatory
             DESCRIPTION
                " The status of the per-DLCI utilization
                  alarm in the receive direction.
                  (1) there is no alarm condition; utilization
                      is under the configured CIR percentage
                      threshold; if traps are enabled and the 
                      alarm had been previously triggered, a
                      utilization alarm clear trap will be sent.
                  (2) the utilization has been over the configured 
                      CIR percentage threshold for less than the
                      configured duration.
                  (3) the utilization has been over the configured 
                      CIR percentage threshold for more than the
                      configured duration; if traps are enabled
                      a utilization exceeded trap will be sent.
                  (4) the utilization has been under the configured 
                      CIR percentage threshold for less than the
                      configured duration. "
             ::= { dfrapPerfThruputPerDlciEntry 25 }
             
   dfrapPerfThruputPerDlciTxUtilizationStatus OBJECT-TYPE
             SYNTAX      INTEGER
             {
               clear                  (1),
               over-threshold         (2),
               alarm                  (3),
               alarm-under-threshold  (4)
             }
             ACCESS      read-only
             STATUS      mandatory
             DESCRIPTION
                " The status of the per-DLCI utilization
                  alarm in the transmit direction.
                  (1) there is no alarm condition; utilization
                      is under the configured CIR percentage
                      threshold; if traps are enabled and the 
                      alarm had been previously triggered, a
                      utilization alarm clear trap will be sent.
                  (2) the utilization has been over the configured 
                      CIR percentage threshold for less than the
                      configured duration.
                  (3) the utilization has been over the configured 
                      CIR percentage threshold for more than the
                      configured duration; if traps are enabled
                      a utilization exceeded trap will be sent.
                  (4) the utilization has been under the configured 
                      CIR percentage threshold for less than the
                      configured duration. "
             ::= { dfrapPerfThruputPerDlciEntry 26 }
             
   dfrapPerfThruputPerDlciEIR    OBJECT-TYPE
             SYNTAX      INTEGER
             ACCESS      read-only
             STATUS      mandatory
             DESCRIPTION
                "The Excess Information Rate.  This is defined to
                 be the maximum rate traffic is (supposed to be)
                 allowed to burst to."
            ::= { dfrapPerfThruputPerDlciEntry 27 }

dfrapPerfThruputCommands OBJECT IDENTIFIER ::= { dfrapPerfThruput 3 }

   dfrapPerfThruputCmdClearDteStats    OBJECT-TYPE
          SYNTAX      INTEGER
          {
              clear-statistics (1)
          }
          ACCESS      write-only
          STATUS      mandatory
          DESCRIPTION
             "Allows the user to zero out all the interface statistics in
              the DTE portion of the ThruputPerIntf statistics table.
              (1) Clear DTE interface statistics command."
          ::= { dfrapPerfThruputCommands 1 }

   dfrapPerfThruputCmdClearDdsStats    OBJECT-TYPE
          SYNTAX      INTEGER
          {
              clear-statistics (1)
          }
          ACCESS      write-only
          STATUS      mandatory
          DESCRIPTION
             "Allows the user to zero out all the interface statistics in
              the DDS portion of the ThruputPerIntf statistics table.
              (1) Clear WAN interface statistics command."
          ::= { dfrapPerfThruputCommands 2 }

   dfrapPerfThruputCmdClearAllIntfStats    OBJECT-TYPE
          SYNTAX      INTEGER
          {
              clear-statistics (1)
          }
          ACCESS      write-only
          STATUS      mandatory
          DESCRIPTION
             "Allows the user to zero out all the statistics in
              the ThruputPerIntf statistics table."
          ::= { dfrapPerfThruputCommands 3 }

   dfrapPerfThruputCmdClearDlciStats    OBJECT-TYPE
          SYNTAX      INTEGER
          {
              clear-statistics (1)
          }
          ACCESS      write-only
          STATUS      mandatory
          DESCRIPTION
             "Allows the user to zero out all the per-DLCI statistics
              in the ThruputPerDlci statistics table and the the short 
              term statistics tables.
              (1) Clear layer 2 per-DLCI statistics command."
          ::= { dfrapPerfThruputCommands 4 }

   dfrapPerfThruputCmdClearAllStats    OBJECT-TYPE
          SYNTAX      INTEGER
          {
              clear-statistics (1)
          }
          ACCESS      write-only
          STATUS      mandatory
          DESCRIPTION
             "Allows the user to zero out all the statistics
              in the ThruputPerIntf and ThruputPerDlci statistics
              tables and in the short term statistics tables.
              (1) Clear all interface and layer 2 per-DLCI statistics."
          ::= { dfrapPerfThruputCommands 5 }

   dfrapPerfThruputCmdRemoveStsDlci    OBJECT-TYPE
          SYNTAX      INTEGER
          ACCESS      write-only
          STATUS      mandatory
          DESCRIPTION
             "Allows the user to remove a Dlci from the short term 
              statistics tables."
          ::= { dfrapPerfThruputCommands 6 }

   dfrapPerfThruputCmdReplaceDlciTable    OBJECT-TYPE
          SYNTAX      SEQUENCE OF DfrapPerfThruputCmdReplaceDlciEntry
          ACCESS      not-accessible
          STATUS      mandatory
          DESCRIPTION
             "Allows the user to replace one DLCI in the short-term
              statistics table with another one."
          ::= { dfrapPerfThruputCommands 7 }

   dfrapPerfThruputCmdReplaceDlciEntry   OBJECT-TYPE
          SYNTAX  DfrapPerfThruputCmdReplaceDlciEntry
          ACCESS  not-accessible
          STATUS  mandatory
          DESCRIPTION
               "Allows the user to replace one DLCI in the short-term
                statistics table with another one."
          INDEX { dfrapPerfThruputCmdReplaceDlciValue }
          ::= { dfrapPerfThruputCmdReplaceDlciTable 1 }

      DfrapPerfThruputCmdReplaceDlciEntry ::=
          SEQUENCE {
             dfrapPerfThruputCmdReplaceDlciValue     INTEGER,
             dfrapPerfThruputCmdReplaceDlciNewValue  INTEGER
          }
            
          dfrapPerfThruputCmdReplaceDlciValue  OBJECT-TYPE
             SYNTAX  INTEGER
             ACCESS  read-only
             STATUS  mandatory
             DESCRIPTION
                "A Dlci that is in the short-term stats table.  Index by
                 this Dlci value to identify the statistics entry to be
                 replaced."
             ::= { dfrapPerfThruputCmdReplaceDlciEntry 1 }

          dfrapPerfThruputCmdReplaceDlciNewValue  OBJECT-TYPE
             SYNTAX  INTEGER
             ACCESS  write-only
             STATUS  mandatory
             DESCRIPTION
                "A Dlci that is to replace another in the short-term stats 
                 table.  Index by this Dlci value to identify the statistics 
                 entry to do the replacing."
             ::= { dfrapPerfThruputCmdReplaceDlciEntry 2 }

   dfrapPerfThruputCmdAvailabilityStsDlciReset    OBJECT-TYPE
          SYNTAX      INTEGER
          ACCESS      write-only
          STATUS      mandatory
          DESCRIPTION
             "Allows the user to reset the availability
              statistics of an individual Dlci within
              the short-term stats table."
          ::= { dfrapPerfThruputCommands 8 }

   dfrapPerfThruputCmdAvailabilityStsDlciResetAll    OBJECT-TYPE
          SYNTAX      INTEGER
          ACCESS      write-only
          STATUS      mandatory
          DESCRIPTION
             "Allows the user to reset the availability
              statistics of all Dlci's within the short-term
              stats table."
          ::= { dfrapPerfThruputCommands 9 }

   dfrapPerfThruputCmdCountsStsDlciReset    OBJECT-TYPE
          SYNTAX      INTEGER
          ACCESS      write-only
          STATUS      mandatory
          DESCRIPTION
             "Allows the user to reset the count 
              statistics of an individual Dlci within
              the short-term stats table."
          ::= { dfrapPerfThruputCommands 10 }

   dfrapPerfThruputCmdCountsStsDlciResetAll    OBJECT-TYPE
          SYNTAX      INTEGER
          ACCESS      write-only
          STATUS      mandatory
          DESCRIPTION
             "Allows the user to reset the count
              statistics of all Dlci's within the short-term
              stats table."
          ::= { dfrapPerfThruputCommands 11 }

   dfrapPerfThruputCmdAllStsDlciReset    OBJECT-TYPE
          SYNTAX      INTEGER
          ACCESS      write-only
          STATUS      mandatory
          DESCRIPTION
             "Allows the user to reset both the count 
              and availability statistics of an individual Dlci within
              the short-term stats table."
          ::= { dfrapPerfThruputCommands 12 }

   dfrapPerfThruputCmdAllStsDlciResetAll    OBJECT-TYPE
          SYNTAX      INTEGER
          ACCESS      write-only
          STATUS      mandatory
          DESCRIPTION
             "Allows the user to reset both the count and the
              availability statistics of all Dlci's within the short-term
              stats table."
          ::= { dfrapPerfThruputCommands 13 }



dfrapPerfNetworkShortTerm OBJECT IDENTIFIER ::= { dfrapPerformance 4 }

   --  Network Layer Short Term Statistics for each DLCI.

   dfrapPerfNetwProtoPerDlciTable OBJECT-TYPE
         SYNTAX   SEQUENCE OF DfrapPerfNetwProtoPerDlciEntry
         ACCESS   not-accessible
         STATUS   mandatory
         DESCRIPTION
            "The Short Term Statistics on the Network Layer
             protocol for each DLCI. These are protocol-based
             per-DLCI statistics. The Short Term model maintains
             three intervals: current, previous, and cumulative
             totals. Interval duration is defined by the Short Term
             Timer (CfgFrPerfTimersSTInterval)."
         ::= { dfrapPerfNetworkShortTerm 1 }

         dfrapPerfNetwProtoPerDlciEntry OBJECT-TYPE
             SYNTAX   DfrapPerfNetwProtoPerDlciEntry
             ACCESS   not-accessible
             STATUS   mandatory
             DESCRIPTION
                "The Network Layer Short Term Statistics
                 for a particular DLCI. This table organizes
                 statistics by high-layer network protocol."
            INDEX { dfrapPerfNetwProtoPerDlciInterval,
                    dfrapPerfNetwProtoPerDlciValue }
            ::= { dfrapPerfNetwProtoPerDlciTable 1 }

         DfrapPerfNetwProtoPerDlciEntry ::=
             SEQUENCE {
                 dfrapPerfNetwProtoPerDlciInterval  INTEGER,
                 dfrapPerfNetwProtoPerDlciValue     INTEGER,
                 dfrapPerfNetwProtoPerDlciRxTotal   Counter,
                 dfrapPerfNetwProtoPerDlciTxTotal   Counter,
                 dfrapPerfNetwProtoPerDlciRxIp      Counter,
                 dfrapPerfNetwProtoPerDlciTxIp      Counter,
                 dfrapPerfNetwProtoPerDlciRxIpx     Counter,
                 dfrapPerfNetwProtoPerDlciTxIpx     Counter,
                 dfrapPerfNetwProtoPerDlciRxSna     Counter,
                 dfrapPerfNetwProtoPerDlciTxSna     Counter,
                 dfrapPerfNetwProtoPerDlciRxArp     Counter,
                 dfrapPerfNetwProtoPerDlciTxArp     Counter,
                 dfrapPerfNetwProtoPerDlciRxCisco   Counter,
                 dfrapPerfNetwProtoPerDlciTxCisco   Counter,
                 dfrapPerfNetwProtoPerDlciRxOther   Counter,
                 dfrapPerfNetwProtoPerDlciTxOther   Counter,
                 dfrapPerfNetwProtoPerDlciRxVnip    Counter,
                 dfrapPerfNetwProtoPerDlciTxVnip    Counter,
                 dfrapPerfNetwProtoPerDlciRxAnnexG  Counter,
                 dfrapPerfNetwProtoPerDlciTxAnnexG  Counter
               }

      dfrapPerfNetwProtoPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfNetwProtoPerDlciEntry 1 }

      dfrapPerfNetwProtoPerDlciValue    OBJECT-TYPE
             SYNTAX      INTEGER 
             ACCESS      read-only
             STATUS      mandatory
             DESCRIPTION
                "The DLCI value with which the Statistics are associated."
            ::= { dfrapPerfNetwProtoPerDlciEntry 2 }

      dfrapPerfNetwProtoPerDlciRxTotal    OBJECT-TYPE
             SYNTAX      Counter 
             ACCESS      read-only
             STATUS      mandatory
             DESCRIPTION
                "The total number of received Network Layer bytes
                 that have been counted on this DLCI."
            ::= { dfrapPerfNetwProtoPerDlciEntry 3 }

      dfrapPerfNetwProtoPerDlciTxTotal    OBJECT-TYPE
             SYNTAX      Counter
             ACCESS      read-only
             STATUS      mandatory
             DESCRIPTION
                "The total number of transmitted Network Layer bytes
                 that have been counted on this DLCI."
            ::= { dfrapPerfNetwProtoPerDlciEntry 4 }

      dfrapPerfNetwProtoPerDlciRxIp    OBJECT-TYPE
             SYNTAX      Counter
             ACCESS      read-only
             STATUS      mandatory
             DESCRIPTION
                "The number of received IP bytes
                 that have been counted on this DLCI."
            ::= { dfrapPerfNetwProtoPerDlciEntry 5 }

      dfrapPerfNetwProtoPerDlciTxIp    OBJECT-TYPE
             SYNTAX      Counter
             ACCESS      read-only
             STATUS      mandatory
             DESCRIPTION
                "The number of transmitted IP bytes
                 that have been counted on this DLCI."
            ::= { dfrapPerfNetwProtoPerDlciEntry 6 }

      dfrapPerfNetwProtoPerDlciRxIpx    OBJECT-TYPE
             SYNTAX      Counter
             ACCESS      read-only
             STATUS      mandatory
             DESCRIPTION
                "The number of received IPX bytes
                 that have been counted on this DLCI."
            ::= { dfrapPerfNetwProtoPerDlciEntry 7 }

      dfrapPerfNetwProtoPerDlciTxIpx    OBJECT-TYPE
             SYNTAX      Counter
             ACCESS      read-only
             STATUS      mandatory
             DESCRIPTION
                "The number of transmitted IPX bytes
                 that have been counted on this DLCI."
            ::= { dfrapPerfNetwProtoPerDlciEntry 8 }

      dfrapPerfNetwProtoPerDlciRxSna    OBJECT-TYPE
             SYNTAX      Counter
             ACCESS      read-only
             STATUS      mandatory
             DESCRIPTION
                "The number of received SNA bytes
                 that have been counted on this DLCI."
            ::= { dfrapPerfNetwProtoPerDlciEntry 9 }

      dfrapPerfNetwProtoPerDlciTxSna    OBJECT-TYPE
             SYNTAX      Counter
             ACCESS      read-only
             STATUS      mandatory
             DESCRIPTION
                "The number of transmitted SNA bytes
                 that have been counted on this DLCI."
            ::= { dfrapPerfNetwProtoPerDlciEntry 10 }

      dfrapPerfNetwProtoPerDlciRxArp    OBJECT-TYPE
             SYNTAX      Counter
             ACCESS      read-only
             STATUS      mandatory
             DESCRIPTION
                "The number of received ARP bytes
                 that have been counted on this DLCI."
            ::= { dfrapPerfNetwProtoPerDlciEntry 11 }

      dfrapPerfNetwProtoPerDlciTxArp    OBJECT-TYPE
             SYNTAX      Counter
             ACCESS      read-only
             STATUS      mandatory
             DESCRIPTION
                "The number of transmitted ARP bytes
                 that have been counted on this DLCI."
            ::= { dfrapPerfNetwProtoPerDlciEntry 12 }

      dfrapPerfNetwProtoPerDlciRxCisco    OBJECT-TYPE
             SYNTAX      Counter
             ACCESS      read-only
             STATUS      mandatory
             DESCRIPTION
                "The number of received Cisco protocol bytes
                 that have been counted on this DLCI."
            ::= { dfrapPerfNetwProtoPerDlciEntry 13 }

      dfrapPerfNetwProtoPerDlciTxCisco    OBJECT-TYPE
             SYNTAX      Counter
             ACCESS      read-only
             STATUS      mandatory
             DESCRIPTION
                "The number of transmitted Cisco protocol bytes
                 that have been counted on this DLCI."
            ::= { dfrapPerfNetwProtoPerDlciEntry 14 }

      dfrapPerfNetwProtoPerDlciRxOther    OBJECT-TYPE
             SYNTAX      Counter
             ACCESS      read-only
             STATUS      mandatory
             DESCRIPTION
                "The number of received bytes on this DLCI
                 from protocols that are not counted elsewhere
                 in this table."
            ::= { dfrapPerfNetwProtoPerDlciEntry 15 }

      dfrapPerfNetwProtoPerDlciTxOther    OBJECT-TYPE
             SYNTAX      Counter
             ACCESS      read-only
             STATUS      mandatory
             DESCRIPTION
                "The number of transmitted bytes on this DLCI
                 from protocols that are not counted elsewhere
                 in this table."
            ::= { dfrapPerfNetwProtoPerDlciEntry 16 }

      dfrapPerfNetwProtoPerDlciRxVnip    OBJECT-TYPE
             SYNTAX      Counter 
             ACCESS      read-only
             STATUS      mandatory
             DESCRIPTION
                "The number of received VNIP protocol bytes
                 that have been counted on this DLCI."
            ::= { dfrapPerfNetwProtoPerDlciEntry 17 }

      dfrapPerfNetwProtoPerDlciTxVnip    OBJECT-TYPE
             SYNTAX      Counter 
             ACCESS      read-only
             STATUS      mandatory
             DESCRIPTION
                "The number of transmitted VNIP protocol bytes
                 that have been counted on this DLCI."
            ::= { dfrapPerfNetwProtoPerDlciEntry 18 }

      dfrapPerfNetwProtoPerDlciRxAnnexG  OBJECT-TYPE
             SYNTAX      Counter 
             ACCESS      read-only
             STATUS      mandatory
             DESCRIPTION
                "The number of received Annex G protocol 
                 bytes that have been counted on this DLCI."
            ::= { dfrapPerfNetwProtoPerDlciEntry 19 }

      dfrapPerfNetwProtoPerDlciTxAnnexG  OBJECT-TYPE
             SYNTAX      Counter 
             ACCESS      read-only
             STATUS      mandatory
             DESCRIPTION
                "The number of transmitted Annex G protocol 
                 bytes that have been counted on this DLCI."
            ::= { dfrapPerfNetwProtoPerDlciEntry 20 }



   --  Network Layer Short Term Statistics totals.

   dfrapPerfNetwProtoTotalTable OBJECT-TYPE
         SYNTAX   SEQUENCE OF DfrapPerfNetwProtoTotalEntry
         ACCESS   not-accessible
         STATUS   mandatory
         DESCRIPTION
            "The Short Term Statistics on Network Layer
            protocols summed across all DLCIs."
         ::= { dfrapPerfNetworkShortTerm 2 }

         dfrapPerfNetwProtoTotalEntry OBJECT-TYPE
             SYNTAX   DfrapPerfNetwProtoTotalEntry
             ACCESS   not-accessible
             STATUS   mandatory
             DESCRIPTION
                "The Network Layer Short Term Statistics
                 across all DLCIs."
             INDEX { dfrapPerfNetwProtoTotalInterval }
             ::= { dfrapPerfNetwProtoTotalTable 1 }

         DfrapPerfNetwProtoTotalEntry ::=
             SEQUENCE {
                 dfrapPerfNetwProtoTotalInterval  INTEGER,
                 dfrapPerfNetwProtoTotalRxTotal   Counter,
                 dfrapPerfNetwProtoTotalTxTotal   Counter,
                 dfrapPerfNetwProtoTotalRxIp      Counter,
                 dfrapPerfNetwProtoTotalTxIp      Counter,
                 dfrapPerfNetwProtoTotalRxIpx     Counter,
                 dfrapPerfNetwProtoTotalTxIpx     Counter,
                 dfrapPerfNetwProtoTotalRxSna     Counter,
                 dfrapPerfNetwProtoTotalTxSna     Counter,
                 dfrapPerfNetwProtoTotalRxArp     Counter,
                 dfrapPerfNetwProtoTotalTxArp     Counter,
                 dfrapPerfNetwProtoTotalRxCisco   Counter,
                 dfrapPerfNetwProtoTotalTxCisco   Counter,
                 dfrapPerfNetwProtoTotalRxOther   Counter,
                 dfrapPerfNetwProtoTotalTxOther   Counter,
                 dfrapPerfNetwProtoTotalRxVnip    Counter,
                 dfrapPerfNetwProtoTotalTxVnip    Counter,
                 dfrapPerfNetwProtoTotalRxAnnexG  Counter,
                 dfrapPerfNetwProtoTotalTxAnnexG  Counter
             }

      dfrapPerfNetwProtoTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfNetwProtoTotalEntry 1 }

      dfrapPerfNetwProtoTotalRxTotal    OBJECT-TYPE
             SYNTAX      Counter 
             ACCESS      read-only
             STATUS      mandatory
             DESCRIPTION
                "The total number of received Network Layer bytes
                 that have been counted across all DLCIs."
            ::= { dfrapPerfNetwProtoTotalEntry 3 }

      dfrapPerfNetwProtoTotalTxTotal    OBJECT-TYPE
             SYNTAX      Counter 
             ACCESS      read-only
             STATUS      mandatory
             DESCRIPTION
                "The total number of transmitted Network Layer bytes
                 that have been counted across all DLCIs."
            ::= { dfrapPerfNetwProtoTotalEntry 4 }

      dfrapPerfNetwProtoTotalRxIp    OBJECT-TYPE
             SYNTAX      Counter 
             ACCESS      read-only
             STATUS      mandatory
             DESCRIPTION
                "The number of received IP bytes
                 that have been counted across all DLCIs."
            ::= { dfrapPerfNetwProtoTotalEntry 5 }

      dfrapPerfNetwProtoTotalTxIp    OBJECT-TYPE
             SYNTAX      Counter
             ACCESS      read-only
             STATUS      mandatory
             DESCRIPTION
                "The number of transmitted IP bytes
                 that have been counted across all DLCIs."
            ::= { dfrapPerfNetwProtoTotalEntry 6 }

      dfrapPerfNetwProtoTotalRxIpx    OBJECT-TYPE
             SYNTAX      Counter
             ACCESS      read-only
             STATUS      mandatory
             DESCRIPTION
                "The number of received IPX bytes
                 that have been counted across all DLCIs."
            ::= { dfrapPerfNetwProtoTotalEntry 7 }

      dfrapPerfNetwProtoTotalTxIpx    OBJECT-TYPE
             SYNTAX      Counter
             ACCESS      read-only
             STATUS      mandatory
             DESCRIPTION
                "The number of transmitted IPX bytes
                 that have been counted across all DLCIs."
            ::= { dfrapPerfNetwProtoTotalEntry 8 }

      dfrapPerfNetwProtoTotalRxSna    OBJECT-TYPE
             SYNTAX      Counter
             ACCESS      read-only
             STATUS      mandatory
             DESCRIPTION
                "The number of received SNA bytes
                 that have been counted across all DLCIs."
            ::= { dfrapPerfNetwProtoTotalEntry 9 }

      dfrapPerfNetwProtoTotalTxSna    OBJECT-TYPE
             SYNTAX      Counter
             ACCESS      read-only
             STATUS      mandatory
             DESCRIPTION
                "The number of transmitted SNA bytes
                 that have been counted across all DLCIs."
            ::= { dfrapPerfNetwProtoTotalEntry 10 }

      dfrapPerfNetwProtoTotalRxArp    OBJECT-TYPE
             SYNTAX      Counter
             ACCESS      read-only
             STATUS      mandatory
             DESCRIPTION
                "The number of received ARP bytes
                 that have been counted across all DLCIs."
            ::= { dfrapPerfNetwProtoTotalEntry 11 }

      dfrapPerfNetwProtoTotalTxArp    OBJECT-TYPE
             SYNTAX      Counter
             ACCESS      read-only
             STATUS      mandatory
             DESCRIPTION
                "The number of transmitted ARP bytes
                 that have been counted across all DLCIs."
            ::= { dfrapPerfNetwProtoTotalEntry 12 }

      dfrapPerfNetwProtoTotalRxCisco    OBJECT-TYPE
             SYNTAX      Counter
             ACCESS      read-only
             STATUS      mandatory
             DESCRIPTION
                "The number of received Cisco protocol bytes
                 that have been counted across all DLCIs."
            ::= { dfrapPerfNetwProtoTotalEntry 13 }

      dfrapPerfNetwProtoTotalTxCisco    OBJECT-TYPE
             SYNTAX      Counter
             ACCESS      read-only
             STATUS      mandatory
             DESCRIPTION
                "The number of transmitted Cisco protocol bytes
                 that have been counted across all DLCIs."
            ::= { dfrapPerfNetwProtoTotalEntry 14 }

      dfrapPerfNetwProtoTotalRxOther    OBJECT-TYPE
             SYNTAX      Counter
             ACCESS      read-only
             STATUS      mandatory
             DESCRIPTION
                "The number of received bytes across all DLCIs
                 from protocols that are not counted elsewhere
                 in this table."
            ::= { dfrapPerfNetwProtoTotalEntry 15 }

      dfrapPerfNetwProtoTotalTxOther    OBJECT-TYPE
             SYNTAX      Counter
             ACCESS      read-only
             STATUS      mandatory
             DESCRIPTION
                "The number of transmitted bytes across all DLCIs
                 from protocols that are not counted elsewhere
                 in this table."
            ::= { dfrapPerfNetwProtoTotalEntry 16 }

      dfrapPerfNetwProtoTotalRxVnip    OBJECT-TYPE
             SYNTAX      Counter 
             ACCESS      read-only
             STATUS      mandatory
             DESCRIPTION
                "The number of received VNIP protocol bytes
                 that have been counted across all DLCIs."
            ::= { dfrapPerfNetwProtoTotalEntry 17 }

      dfrapPerfNetwProtoTotalTxVnip    OBJECT-TYPE
             SYNTAX      Counter 
             ACCESS      read-only
             STATUS      mandatory
             DESCRIPTION
                "The number of transmitted VNIP protocol bytes
                 that have been counted across all DLCIs."
            ::= { dfrapPerfNetwProtoTotalEntry 18 }

      dfrapPerfNetwProtoTotalRxAnnexG  OBJECT-TYPE
             SYNTAX      Counter 
             ACCESS      read-only
             STATUS      mandatory
             DESCRIPTION
                "The number of received Annex G protocol bytes
                 that have been counted across all DLCIs."
            ::= { dfrapPerfNetwProtoTotalEntry 19 }

      dfrapPerfNetwProtoTotalTxAnnexG  OBJECT-TYPE
             SYNTAX      Counter 
             ACCESS      read-only
             STATUS      mandatory
             DESCRIPTION
                "The number of transmitted Annex G protocol bytes
                 that have been counted across all DLCIs."
            ::= { dfrapPerfNetwProtoTotalEntry 20 }


   --  IP Short Term Statistics for each DLCI.

   dfrapPerfIpPerDlciTable OBJECT-TYPE
         SYNTAX   SEQUENCE OF DfrapPerfIpPerDlciEntry
         ACCESS   not-accessible
         STATUS   mandatory
         DESCRIPTION
            "The Short Term Statistics on the IP
            protocol for each DLCI."
         ::= { dfrapPerfNetworkShortTerm 3 }

         dfrapPerfIpPerDlciEntry OBJECT-TYPE
             SYNTAX   DfrapPerfIpPerDlciEntry
             ACCESS   not-accessible
             STATUS   mandatory
             DESCRIPTION
                "The IP Short Term Statistics for a particular DLCI."
             INDEX { dfrapPerfIpPerDlciInterval, dfrapPerfIpPerDlciValue }
             ::= { dfrapPerfIpPerDlciTable 1 }

         DfrapPerfIpPerDlciEntry ::=
             SEQUENCE {
                 dfrapPerfIpPerDlciInterval  INTEGER,
                 dfrapPerfIpPerDlciValue     INTEGER,
                 dfrapPerfIpPerDlciRxTotal   Counter,
                 dfrapPerfIpPerDlciTxTotal   Counter,
                 dfrapPerfIpPerDlciRxTcp     Counter,
                 dfrapPerfIpPerDlciTxTcp     Counter,
                 dfrapPerfIpPerDlciRxUdp     Counter,
                 dfrapPerfIpPerDlciTxUdp     Counter,
                 dfrapPerfIpPerDlciRxIcmp    Counter,
                 dfrapPerfIpPerDlciTxIcmp    Counter,
                 dfrapPerfIpPerDlciRxOther   Counter,
                 dfrapPerfIpPerDlciTxOther   Counter,
                 dfrapPerfIpPerDlciRxIgrp    Counter,
                 dfrapPerfIpPerDlciTxIgrp    Counter
             }

      dfrapPerfIpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfIpPerDlciEntry 1 }

      dfrapPerfIpPerDlciValue    OBJECT-TYPE
             SYNTAX      INTEGER 
             ACCESS      read-only
             STATUS      mandatory
             DESCRIPTION
                "The DLCI value with which the Statistics are associated."
            ::= { dfrapPerfIpPerDlciEntry 2 }

      dfrapPerfIpPerDlciRxTotal    OBJECT-TYPE
             SYNTAX      Counter 
             ACCESS      read-only
             STATUS      mandatory
             DESCRIPTION
                "The total number of received IP bytes
                 that have been counted on this DLCI."
            ::= { dfrapPerfIpPerDlciEntry 3 }

      dfrapPerfIpPerDlciTxTotal    OBJECT-TYPE
             SYNTAX      Counter
             ACCESS      read-only
             STATUS      mandatory
             DESCRIPTION
                "The total number of transmitted IP bytes
                 that have been counted on this DLCI."
            ::= { dfrapPerfIpPerDlciEntry 4 }

      dfrapPerfIpPerDlciRxTcp    OBJECT-TYPE
             SYNTAX      Counter
             ACCESS      read-only
             STATUS      mandatory
             DESCRIPTION
                "The number of received TCP over IP bytes
                 that have been counted on this DLCI."
            ::= { dfrapPerfIpPerDlciEntry 5 }

      dfrapPerfIpPerDlciTxTcp    OBJECT-TYPE
             SYNTAX      Counter
             ACCESS      read-only
             STATUS      mandatory
             DESCRIPTION
                "The number of transmitted TCP over IP bytes
                 that have been counted on this DLCI."
            ::= { dfrapPerfIpPerDlciEntry 6 }

      dfrapPerfIpPerDlciRxUdp    OBJECT-TYPE
             SYNTAX      Counter
             ACCESS      read-only
             STATUS      mandatory
             DESCRIPTION
                "The number of received UDP over IP bytes
                 that have been counted on this DLCI."
            ::= { dfrapPerfIpPerDlciEntry 7 }

      dfrapPerfIpPerDlciTxUdp    OBJECT-TYPE
             SYNTAX      Counter
             ACCESS      read-only
             STATUS      mandatory
             DESCRIPTION
                "The number of transmitted UDP over IP bytes
                 that have been counted on this DLCI."
            ::= { dfrapPerfIpPerDlciEntry 8 }

      dfrapPerfIpPerDlciRxIcmp    OBJECT-TYPE
             SYNTAX      Counter
             ACCESS      read-only
             STATUS      mandatory
             DESCRIPTION
                "The number of received ICMP over IP bytes
                 that have been counted on this DLCI."
            ::= { dfrapPerfIpPerDlciEntry 9 }

      dfrapPerfIpPerDlciTxIcmp    OBJECT-TYPE
             SYNTAX      Counter
             ACCESS      read-only
             STATUS      mandatory
             DESCRIPTION
                "The number of transmitted ICMP over IP bytes
                 that have been counted on this DLCI."
            ::= { dfrapPerfIpPerDlciEntry 10 }

      dfrapPerfIpPerDlciRxOther    OBJECT-TYPE
             SYNTAX      Counter
             ACCESS      read-only
             STATUS      mandatory
             DESCRIPTION
                "The number of received bytes on this DLCI
                 from protocols over IP that are not counted
                 elsewhere in this table."
            ::= { dfrapPerfIpPerDlciEntry 11 }

      dfrapPerfIpPerDlciTxOther    OBJECT-TYPE
             SYNTAX      Counter
             ACCESS      read-only
             STATUS      mandatory
             DESCRIPTION
                "The number of transmitted bytes on this DLCI
                 from protocols over IP that are not counted
                 elsewhere in this table."
            ::= { dfrapPerfIpPerDlciEntry 12 }

      dfrapPerfIpPerDlciRxIgrp    OBJECT-TYPE
             SYNTAX      Counter 
             ACCESS      read-only
             STATUS      mandatory
             DESCRIPTION
                "The number of received IGRP over IP bytes
                 that have been counted on this DLCI."
            ::= { dfrapPerfIpPerDlciEntry 13 }

      dfrapPerfIpPerDlciTxIgrp    OBJECT-TYPE
             SYNTAX      Counter 
             ACCESS      read-only
             STATUS      mandatory
             DESCRIPTION
                "The number of transmitted IGRP over IP bytes
                 that have been counted on this DLCI."
            ::= { dfrapPerfIpPerDlciEntry 14 }


   --  IP Short Term Statistics totals.

   dfrapPerfIpTotalTable OBJECT-TYPE
         SYNTAX   SEQUENCE OF DfrapPerfIpTotalEntry
         ACCESS   not-accessible
         STATUS   mandatory
         DESCRIPTION
            "The Short Term Statistics on the IP
            protocol for each DLCI."
         ::= { dfrapPerfNetworkShortTerm 4 }

         dfrapPerfIpTotalEntry OBJECT-TYPE
             SYNTAX   DfrapPerfIpTotalEntry
             ACCESS   not-accessible
             STATUS   mandatory
             DESCRIPTION
                "The IP Short Term Statistics across all DLCIs."
             INDEX { dfrapPerfIpTotalInterval }
             ::= { dfrapPerfIpTotalTable 1 }

         DfrapPerfIpTotalEntry ::=
             SEQUENCE {
                 dfrapPerfIpTotalInterval INTEGER,
                 dfrapPerfIpTotalRxTotal  Counter,
                 dfrapPerfIpTotalTxTotal  Counter,
                 dfrapPerfIpTotalRxTcp    Counter,
                 dfrapPerfIpTotalTxTcp    Counter,
                 dfrapPerfIpTotalRxUdp    Counter,
                 dfrapPerfIpTotalTxUdp    Counter,
                 dfrapPerfIpTotalRxIcmp   Counter,
                 dfrapPerfIpTotalTxIcmp   Counter,
                 dfrapPerfIpTotalRxOther  Counter,
                 dfrapPerfIpTotalTxOther  Counter,
                 dfrapPerfIpTotalRxIgrp   Counter,
                 dfrapPerfIpTotalTxIgrp   Counter
             }

      dfrapPerfIpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfIpTotalEntry 1 }

      dfrapPerfIpTotalRxTotal    OBJECT-TYPE
             SYNTAX      Counter
             ACCESS      read-only
             STATUS      mandatory
             DESCRIPTION
                "The total number of received IP bytes
                 that have been counted across all DLCIs."
            ::= { dfrapPerfIpTotalEntry 3 }

      dfrapPerfIpTotalTxTotal    OBJECT-TYPE
             SYNTAX      Counter
             ACCESS      read-only
             STATUS      mandatory
             DESCRIPTION
                "The total number of transmitted IP bytes
                 that have been counted across all DLCIs."
            ::= { dfrapPerfIpTotalEntry 4 }

      dfrapPerfIpTotalRxTcp    OBJECT-TYPE
             SYNTAX      Counter
             ACCESS      read-only
             STATUS      mandatory
             DESCRIPTION
                "The number of received TCP over IP bytes
                 that have been counted across all DLCIs."
            ::= { dfrapPerfIpTotalEntry 5 }

      dfrapPerfIpTotalTxTcp    OBJECT-TYPE
             SYNTAX      Counter
             ACCESS      read-only
             STATUS      mandatory
             DESCRIPTION
                "The number of transmitted TCP over IP bytes
                 that have been counted across all DLCIs."
            ::= { dfrapPerfIpTotalEntry 6 }

      dfrapPerfIpTotalRxUdp    OBJECT-TYPE
             SYNTAX      Counter
             ACCESS      read-only
             STATUS      mandatory
             DESCRIPTION
                "The number of received UDP over IP bytes
                 that have been counted across all DLCIs."
            ::= { dfrapPerfIpTotalEntry 7 }

      dfrapPerfIpTotalTxUdp    OBJECT-TYPE
             SYNTAX      Counter
             ACCESS      read-only
             STATUS      mandatory
             DESCRIPTION
                "The number of transmitted UDP over IP bytes
                 that have been counted across all DLCIs."
            ::= { dfrapPerfIpTotalEntry 8 }

      dfrapPerfIpTotalRxIcmp    OBJECT-TYPE
             SYNTAX      Counter
             ACCESS      read-only
             STATUS      mandatory
             DESCRIPTION
                "The number of received ICMP over IP bytes
                 that have been counted across all DLCIs."
            ::= { dfrapPerfIpTotalEntry 9 }

      dfrapPerfIpTotalTxIcmp    OBJECT-TYPE
             SYNTAX      Counter
             ACCESS      read-only
             STATUS      mandatory
             DESCRIPTION
                "The number of transmitted ICMP over IP bytes
                 that have been counted across all DLCIs."
            ::= { dfrapPerfIpTotalEntry 10 }

      dfrapPerfIpTotalRxOther    OBJECT-TYPE
             SYNTAX      Counter
             ACCESS      read-only
             STATUS      mandatory
             DESCRIPTION
                "The number of received bytes across all DLCIs
                 from protocols over IP that are not counted
                 elsewhere in this table."
            ::= { dfrapPerfIpTotalEntry 11 }

      dfrapPerfIpTotalTxOther    OBJECT-TYPE
             SYNTAX      Counter
             ACCESS      read-only
             STATUS      mandatory
             DESCRIPTION
                "The number of transmitted bytes across all DLCIs
                 from protocols over IP that are not counted
                 elsewhere in this table."
            ::= { dfrapPerfIpTotalEntry 12 }

      dfrapPerfIpTotalRxIgrp    OBJECT-TYPE
             SYNTAX      Counter 
             ACCESS      read-only
             STATUS      mandatory
             DESCRIPTION
                "The number of received IGRP over IP bytes
                 that have been counted across all DLCIs."
            ::= { dfrapPerfIpTotalEntry 13 }

      dfrapPerfIpTotalTxIgrp    OBJECT-TYPE
             SYNTAX      Counter 
             ACCESS      read-only
             STATUS      mandatory
             DESCRIPTION
                "The number of transmitted IGRP over IP bytes
                 that have been counted across all DLCIs."
            ::= { dfrapPerfIpTotalEntry 14 }


   --  ICMP Short Term Statistics for each DLCI.

   dfrapPerfIcmpPerDlciTable OBJECT-TYPE
         SYNTAX   SEQUENCE OF DfrapPerfIcmpPerDlciEntry
         ACCESS   not-accessible
         STATUS   mandatory
         DESCRIPTION
            "Short Term Statistics on the ICMP
             protocol for each DLCI."
         ::= { dfrapPerfNetworkShortTerm 5 }

         dfrapPerfIcmpPerDlciEntry OBJECT-TYPE
             SYNTAX   DfrapPerfIcmpPerDlciEntry
             ACCESS   not-accessible
             STATUS   mandatory
             DESCRIPTION
                "The ICMP Short Term Statistics for a particular DLCI."
             INDEX { dfrapPerfIcmpPerDlciInterval, dfrapPerfIcmpPerDlciValue }
             ::= { dfrapPerfIcmpPerDlciTable 1 }

         DfrapPerfIcmpPerDlciEntry ::=
             SEQUENCE {
                 dfrapPerfIcmpPerDlciInterval        INTEGER,
                 dfrapPerfIcmpPerDlciValue           INTEGER,
                 dfrapPerfIcmpPerDlciRxTotal         Counter,
                 dfrapPerfIcmpPerDlciTxTotal         Counter,
                 dfrapPerfIcmpPerDlciRxEchoRep       Counter,
                 dfrapPerfIcmpPerDlciTxEchoRep       Counter,
                 dfrapPerfIcmpPerDlciRxDestUnr       Counter,
                 dfrapPerfIcmpPerDlciTxDestUnr       Counter,
                 dfrapPerfIcmpPerDlciRxSrcQuench     Counter,
                 dfrapPerfIcmpPerDlciTxSrcQuench     Counter,
                 dfrapPerfIcmpPerDlciRxRedirect      Counter,
                 dfrapPerfIcmpPerDlciTxRedirect      Counter,
                 dfrapPerfIcmpPerDlciRxEchoReq       Counter,
                 dfrapPerfIcmpPerDlciTxEchoReq       Counter,
                 dfrapPerfIcmpPerDlciRxTimeExcd      Counter,
                 dfrapPerfIcmpPerDlciTxTimeExcd      Counter,
                 dfrapPerfIcmpPerDlciRxParamProb     Counter,
                 dfrapPerfIcmpPerDlciTxParamProb     Counter,
                 dfrapPerfIcmpPerDlciRxTimestpReq    Counter,
                 dfrapPerfIcmpPerDlciTxTimestpReq    Counter,
                 dfrapPerfIcmpPerDlciRxTimestpRep    Counter,
                 dfrapPerfIcmpPerDlciTxTimestpRep    Counter,
                 dfrapPerfIcmpPerDlciRxAddrMaskReq   Counter,
                 dfrapPerfIcmpPerDlciTxAddrMaskReq   Counter,
                 dfrapPerfIcmpPerDlciRxAddrMaskRep   Counter,
                 dfrapPerfIcmpPerDlciTxAddrMaskRep   Counter,
                 dfrapPerfIcmpPerDlciRxPktTooBig     Counter,
                 dfrapPerfIcmpPerDlciTxPktTooBig     Counter,
                 dfrapPerfIcmpPerDlciRxGmQuery       Counter,
                 dfrapPerfIcmpPerDlciTxGmQuery       Counter,
                 dfrapPerfIcmpPerDlciRxGmReport      Counter,
                 dfrapPerfIcmpPerDlciTxGmReport      Counter,
                 dfrapPerfIcmpPerDlciRxGmReduct      Counter,
                 dfrapPerfIcmpPerDlciTxGmReduct      Counter
             }

      dfrapPerfIcmpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfIcmpPerDlciEntry 1 }

      dfrapPerfIcmpPerDlciValue    OBJECT-TYPE
             SYNTAX      INTEGER 
            ACCESS      read-only
             STATUS      mandatory
             DESCRIPTION
                "The DLCI value in which the Statistics are associated."
            ::= { dfrapPerfIcmpPerDlciEntry 2 }

      dfrapPerfIcmpPerDlciRxTotal    OBJECT-TYPE
             SYNTAX      Counter
             ACCESS      read-only
             STATUS      mandatory
             DESCRIPTION
                "The total number of ICMP bytes that have been
                 counted on this DLCI."
            ::= { dfrapPerfIcmpPerDlciEntry 3 }

      dfrapPerfIcmpPerDlciTxTotal    OBJECT-TYPE
             SYNTAX      Counter
             ACCESS      read-only
               STATUS      mandatory
             DESCRIPTION
                "The total number of ICMP bytes that have been
                 counted on this DLCI."
            ::= { dfrapPerfIcmpPerDlciEntry 4 }

      dfrapPerfIcmpPerDlciRxEchoRep    OBJECT-TYPE
             SYNTAX      Counter
             ACCESS      read-only
             STATUS      mandatory
             DESCRIPTION
                "The number of bytes in ICMP ECHO repies
                 that have been counted on this DLCI."
            ::= { dfrapPerfIcmpPerDlciEntry 5 }

      dfrapPerfIcmpPerDlciTxEchoRep    OBJECT-TYPE
             SYNTAX      Counter
             ACCESS      read-only
               STATUS      mandatory
             DESCRIPTION
                "The number of bytes in ICMP ECHO repies
                 that have been counted on this DLCI."
            ::= { dfrapPerfIcmpPerDlciEntry 6 }

      dfrapPerfIcmpPerDlciRxDestUnr    OBJECT-TYPE
             SYNTAX      Counter
             ACCESS      read-only
             STATUS      mandatory
             DESCRIPTION
                "The number of bytes in ICMP destination unreachables
                 that have been counted on this DLCI."
            ::= { dfrapPerfIcmpPerDlciEntry 7 }

      dfrapPerfIcmpPerDlciTxDestUnr    OBJECT-TYPE
             SYNTAX      Counter
             ACCESS      read-only
               STATUS      mandatory
             DESCRIPTION
                "The number of bytes in ICMP destination unreachables
                 that have been counted on this DLCI."
            ::= { dfrapPerfIcmpPerDlciEntry 8 }

      dfrapPerfIcmpPerDlciRxSrcQuench    OBJECT-TYPE
             SYNTAX      Counter
             ACCESS      read-only
             STATUS      mandatory
             DESCRIPTION
                "The number of bytes in ICMP source quenches
                 that have been counted on this DLCI."
            ::= { dfrapPerfIcmpPerDlciEntry 9 }

      dfrapPerfIcmpPerDlciTxSrcQuench    OBJECT-TYPE
             SYNTAX      Counter
             ACCESS      read-only
             STATUS      mandatory
             DESCRIPTION
                "The number of bytes in ICMP source quenches
                 that have been counted on this DLCI."
            ::= { dfrapPerfIcmpPerDlciEntry 10 }

      dfrapPerfIcmpPerDlciRxRedirect    OBJECT-TYPE
             SYNTAX      Counter
             ACCESS      read-only
             STATUS      mandatory
             DESCRIPTION
                "The number of bytes in ICMP redirects
                 that have been counted on this DLCI."
            ::= { dfrapPerfIcmpPerDlciEntry 11 }

      dfrapPerfIcmpPerDlciTxRedirect    OBJECT-TYPE
             SYNTAX      Counter
             ACCESS      read-only
             STATUS      mandatory
             DESCRIPTION
                "The number of bytes in ICMP redirects
                 that have been counted on this DLCI."
            ::= { dfrapPerfIcmpPerDlciEntry 12 }

      dfrapPerfIcmpPerDlciRxEchoReq    OBJECT-TYPE
             SYNTAX      Counter
             ACCESS      read-only
             STATUS      mandatory
             DESCRIPTION
                "The number of bytes in ICMP ECHO requests
                 that have been counted on this DLCI."
            ::= { dfrapPerfIcmpPerDlciEntry 13 }

      dfrapPerfIcmpPerDlciTxEchoReq    OBJECT-TYPE
             SYNTAX      Counter
             ACCESS      read-only
             STATUS      mandatory
             DESCRIPTION
                "The number of bytes in ICMP ECHO requests
                 that have been counted on this DLCI."
            ::= { dfrapPerfIcmpPerDlciEntry 14 }

      dfrapPerfIcmpPerDlciRxTimeExcd    OBJECT-TYPE
             SYNTAX      Counter
             ACCESS      read-only
             STATUS      mandatory
             DESCRIPTION
                "The number of bytes in ICMP time exceededs
                 that have been counted on this DLCI."
            ::= { dfrapPerfIcmpPerDlciEntry 15 }

      dfrapPerfIcmpPerDlciTxTimeExcd    OBJECT-TYPE
             SYNTAX      Counter
             ACCESS      read-only
             STATUS      mandatory
             DESCRIPTION
                "The number of bytes in ICMP time exceededs
                 that have been counted on this DLCI."
            ::= { dfrapPerfIcmpPerDlciEntry 16 }

      dfrapPerfIcmpPerDlciRxParamProb    OBJECT-TYPE
             SYNTAX      Counter
             ACCESS      read-only
             STATUS      mandatory
             DESCRIPTION
                "The number of bytes in ICMP parameter problems
                 that have been counted on this DLCI."
            ::= { dfrapPerfIcmpPerDlciEntry 17 }

      dfrapPerfIcmpPerDlciTxParamProb    OBJECT-TYPE
             SYNTAX      Counter
             ACCESS      read-only
             STATUS      mandatory
             DESCRIPTION
                "The number of bytes in ICMP parameter problems
                 that have been counted on this DLCI."
            ::= { dfrapPerfIcmpPerDlciEntry 18 }

      dfrapPerfIcmpPerDlciRxTimestpReq    OBJECT-TYPE
             SYNTAX      Counter
             ACCESS      read-only
             STATUS      mandatory
             DESCRIPTION
                "The number of bytes in ICMP timestamp requests
                 that have been counted on this DLCI."
            ::= { dfrapPerfIcmpPerDlciEntry 19 }

      dfrapPerfIcmpPerDlciTxTimestpReq    OBJECT-TYPE
             SYNTAX      Counter
             ACCESS      read-only
             STATUS      mandatory
             DESCRIPTION
                "The number of bytes in ICMP timestamp requests
                 that have been counted on this DLCI."
            ::= { dfrapPerfIcmpPerDlciEntry 20 }

      dfrapPerfIcmpPerDlciRxTimestpRep    OBJECT-TYPE
             SYNTAX      Counter
             ACCESS      read-only
             STATUS      mandatory
             DESCRIPTION
                "The number of bytes in ICMP timestamp replies
                 that have been counted on this DLCI."
            ::= { dfrapPerfIcmpPerDlciEntry 21 }

      dfrapPerfIcmpPerDlciTxTimestpRep    OBJECT-TYPE
             SYNTAX      Counter
             ACCESS      read-only
             STATUS      mandatory
             DESCRIPTION
                "The number of bytes in ICMP timestamp replies
                 that have been counted on this DLCI."
            ::= { dfrapPerfIcmpPerDlciEntry 22 }

      dfrapPerfIcmpPerDlciRxAddrMaskReq    OBJECT-TYPE
             SYNTAX      Counter
             ACCESS      read-only
             STATUS      mandatory
             DESCRIPTION
                "The number of bytes in ICMP address mask requests
                 that have been counted on this DLCI."
            ::= { dfrapPerfIcmpPerDlciEntry 23 }

      dfrapPerfIcmpPerDlciTxAddrMaskReq    OBJECT-TYPE
             SYNTAX      Counter
             ACCESS      read-only
             STATUS      mandatory
             DESCRIPTION
                "The number of bytes in ICMP address mask requests
                 that have been counted on this DLCI."
            ::= { dfrapPerfIcmpPerDlciEntry 24 }

      dfrapPerfIcmpPerDlciRxAddrMaskRep    OBJECT-TYPE
             SYNTAX      Counter
             ACCESS      read-only
             STATUS      mandatory
             DESCRIPTION
                "The number of bytes in ICMP address mask replies
                 that have been counted on this DLCI."
            ::= { dfrapPerfIcmpPerDlciEntry 25 }

      dfrapPerfIcmpPerDlciTxAddrMaskRep    OBJECT-TYPE
             SYNTAX      Counter
             ACCESS      read-only
             STATUS      mandatory
             DESCRIPTION
                "The number of bytes in ICMP address mask replies
                 that have been counted on this DLCI."
            ::= { dfrapPerfIcmpPerDlciEntry 26 }

      dfrapPerfIcmpPerDlciRxPktTooBig    OBJECT-TYPE
             SYNTAX      Counter
             ACCESS      read-only
             STATUS      mandatory
             DESCRIPTION
                "The number of bytes in ICMP packet too bigs
                 that have been counted on this DLCI."
            ::= { dfrapPerfIcmpPerDlciEntry 27 }

      dfrapPerfIcmpPerDlciTxPktTooBig    OBJECT-TYPE
             SYNTAX      Counter
             ACCESS      read-only
             STATUS      mandatory
             DESCRIPTION
                "The number of bytes in ICMP packet too bigs
                 that have been counted on this DLCI."
            ::= { dfrapPerfIcmpPerDlciEntry 28 }

      dfrapPerfIcmpPerDlciRxGmQuery    OBJECT-TYPE
             SYNTAX      Counter
             ACCESS      read-only
             STATUS      mandatory
             DESCRIPTION
                "The number of bytes in ICMP group membership
                 queries that have been counted on this DLCI."
            ::= { dfrapPerfIcmpPerDlciEntry 29 }

      dfrapPerfIcmpPerDlciTxGmQuery    OBJECT-TYPE
             SYNTAX      Counter
             ACCESS      read-only
             STATUS      mandatory
             DESCRIPTION
                "The number of bytes in ICMP group membership
                 queries that have been counted on this DLCI."
            ::= { dfrapPerfIcmpPerDlciEntry 30 }

      dfrapPerfIcmpPerDlciRxGmReport    OBJECT-TYPE
             SYNTAX      Counter
             ACCESS      read-only
             STATUS      mandatory
             DESCRIPTION
                "The number of bytes in ICMP group membership
                 reports that have been counted on this DLCI."
            ::= { dfrapPerfIcmpPerDlciEntry 31 }

      dfrapPerfIcmpPerDlciTxGmReport    OBJECT-TYPE
             SYNTAX      Counter
             ACCESS      read-only
             STATUS      mandatory
             DESCRIPTION
                "The number of bytes in ICMP group membership
                 reports that have been counted on this DLCI."
            ::= { dfrapPerfIcmpPerDlciEntry 32 }

      dfrapPerfIcmpPerDlciRxGmReduct    OBJECT-TYPE
             SYNTAX      Counter
             ACCESS      read-only
             STATUS      mandatory
             DESCRIPTION
                "The number of bytes in ICMP group membership
                 reductions that have been counted on this DLCI."
            ::= { dfrapPerfIcmpPerDlciEntry 33 }

      dfrapPerfIcmpPerDlciTxGmReduct    OBJECT-TYPE
             SYNTAX      Counter
             ACCESS      read-only
             STATUS      mandatory
             DESCRIPTION
                "The number of bytes in ICMP group membership
                 reductions that have been counted on this DLCI."
            ::= { dfrapPerfIcmpPerDlciEntry 34 }


   --  ICMP Short Term Statistics totals.

   dfrapPerfIcmpTotalTable OBJECT-TYPE
         SYNTAX   SEQUENCE OF DfrapPerfIcmpTotalEntry
         ACCESS   not-accessible
         STATUS   mandatory
         DESCRIPTION
            "Short Term Statistics on the ICMP
             protocol across all DLCIs."
         ::= { dfrapPerfNetworkShortTerm 6 }

         dfrapPerfIcmpTotalEntry OBJECT-TYPE
             SYNTAX   DfrapPerfIcmpTotalEntry
             ACCESS   not-accessible
             STATUS   mandatory
             DESCRIPTION
                "The ICMP Short Term Statistics across all DLCIs."
             INDEX { dfrapPerfIcmpTotalInterval }
             ::= { dfrapPerfIcmpTotalTable 1 }

         DfrapPerfIcmpTotalEntry ::=
             SEQUENCE {
                 dfrapPerfIcmpTotalInterval        INTEGER,
                 dfrapPerfIcmpTotalRxTotal         Counter,
                 dfrapPerfIcmpTotalTxTotal         Counter,
                 dfrapPerfIcmpTotalRxEchoRep       Counter,
                 dfrapPerfIcmpTotalTxEchoRep       Counter,
                 dfrapPerfIcmpTotalRxDestUnr       Counter,
                 dfrapPerfIcmpTotalTxDestUnr       Counter,
                 dfrapPerfIcmpTotalRxSrcQuench     Counter,
                 dfrapPerfIcmpTotalTxSrcQuench     Counter,
                 dfrapPerfIcmpTotalRxRedirect      Counter,
                 dfrapPerfIcmpTotalTxRedirect      Counter,
                 dfrapPerfIcmpTotalRxEchoReq       Counter,
                 dfrapPerfIcmpTotalTxEchoReq       Counter,
                 dfrapPerfIcmpTotalRxTimeExcd      Counter,
                 dfrapPerfIcmpTotalTxTimeExcd      Counter,
                 dfrapPerfIcmpTotalRxParamProb     Counter,
                 dfrapPerfIcmpTotalTxParamProb     Counter,
                 dfrapPerfIcmpTotalRxTimestpReq    Counter,
                 dfrapPerfIcmpTotalTxTimestpReq    Counter,
                 dfrapPerfIcmpTotalRxTimestpRep    Counter,
                 dfrapPerfIcmpTotalTxTimestpRep    Counter,
                 dfrapPerfIcmpTotalRxAddrMaskReq   Counter,
                 dfrapPerfIcmpTotalTxAddrMaskReq   Counter,
                 dfrapPerfIcmpTotalRxAddrMaskRep   Counter,
                 dfrapPerfIcmpTotalTxAddrMaskRep   Counter,
                 dfrapPerfIcmpTotalRxPktTooBig     Counter,
                 dfrapPerfIcmpTotalTxPktTooBig     Counter,
                 dfrapPerfIcmpTotalRxGmQuery       Counter,
                 dfrapPerfIcmpTotalTxGmQuery       Counter,
                 dfrapPerfIcmpTotalRxGmReport      Counter,
                 dfrapPerfIcmpTotalTxGmReport      Counter,
                 dfrapPerfIcmpTotalRxGmReduct      Counter,
                 dfrapPerfIcmpTotalTxGmReduct      Counter
             }

      dfrapPerfIcmpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfIcmpTotalEntry 1 }

      dfrapPerfIcmpTotalRxTotal    OBJECT-TYPE
             SYNTAX      Counter
             ACCESS      read-only
             STATUS      mandatory
             DESCRIPTION
                "The total number of ICMP bytes that have been
                 counted across all DLCIs."
            ::= { dfrapPerfIcmpTotalEntry 3 }

      dfrapPerfIcmpTotalTxTotal    OBJECT-TYPE
             SYNTAX      Counter
             ACCESS      read-only
               STATUS      mandatory
             DESCRIPTION
                "The total number of ICMP bytes that have been
                 counted across all DLCIs."
            ::= { dfrapPerfIcmpTotalEntry 4 }

      dfrapPerfIcmpTotalRxEchoRep    OBJECT-TYPE
             SYNTAX      Counter
             ACCESS      read-only
             STATUS      mandatory
             DESCRIPTION
                "The number of bytes in ICMP ECHO repies
                 that have been counted across all DLCIs."
            ::= { dfrapPerfIcmpTotalEntry 5 }

      dfrapPerfIcmpTotalTxEchoRep    OBJECT-TYPE
             SYNTAX      Counter
             ACCESS      read-only
               STATUS      mandatory
             DESCRIPTION
                "The number of bytes in ICMP ECHO repies
                 that have been counted across all DLCIs."
            ::= { dfrapPerfIcmpTotalEntry 6 }

      dfrapPerfIcmpTotalRxDestUnr    OBJECT-TYPE
             SYNTAX      Counter
             ACCESS      read-only
             STATUS      mandatory
             DESCRIPTION
                "The number of bytes in ICMP destination unreachables
                 that have been counted across all DLCIs."
            ::= { dfrapPerfIcmpTotalEntry 7 }

      dfrapPerfIcmpTotalTxDestUnr    OBJECT-TYPE
             SYNTAX      Counter
             ACCESS      read-only
               STATUS      mandatory
             DESCRIPTION
                "The number of bytes in ICMP destination unreachables
                 that have been counted across all DLCIs."
            ::= { dfrapPerfIcmpTotalEntry 8 }

      dfrapPerfIcmpTotalRxSrcQuench    OBJECT-TYPE
             SYNTAX      Counter
             ACCESS      read-only
             STATUS      mandatory
             DESCRIPTION
                "The number of bytes in ICMP source quenches
                 that have been counted across all DLCIs."
            ::= { dfrapPerfIcmpTotalEntry 9 }

      dfrapPerfIcmpTotalTxSrcQuench    OBJECT-TYPE
             SYNTAX      Counter
             ACCESS      read-only
             STATUS      mandatory
             DESCRIPTION
                "The number of bytes in ICMP source quenches
                 that have been counted across all DLCIs."
            ::= { dfrapPerfIcmpTotalEntry 10 }

      dfrapPerfIcmpTotalRxRedirect    OBJECT-TYPE
             SYNTAX      Counter
             ACCESS      read-only
             STATUS      mandatory
             DESCRIPTION
                "The number of bytes in ICMP redirects
                 that have been counted across all DLCIs."
            ::= { dfrapPerfIcmpTotalEntry 11 }

      dfrapPerfIcmpTotalTxRedirect    OBJECT-TYPE
             SYNTAX      Counter
             ACCESS      read-only
             STATUS      mandatory
             DESCRIPTION
                "The number of bytes in ICMP redirects
                 that have been counted across all DLCIs."
            ::= { dfrapPerfIcmpTotalEntry 12 }

      dfrapPerfIcmpTotalRxEchoReq    OBJECT-TYPE
             SYNTAX      Counter
             ACCESS      read-only
             STATUS      mandatory
             DESCRIPTION
                "The number of bytes in ICMP ECHO requests
                 that have been counted across all DLCIs."
            ::= { dfrapPerfIcmpTotalEntry 13 }

      dfrapPerfIcmpTotalTxEchoReq    OBJECT-TYPE
             SYNTAX      Counter
             ACCESS      read-only
             STATUS      mandatory
             DESCRIPTION
                "The number of bytes in ICMP ECHO requests
                 that have been counted across all DLCIs."
            ::= { dfrapPerfIcmpTotalEntry 14 }

      dfrapPerfIcmpTotalRxTimeExcd    OBJECT-TYPE
             SYNTAX      Counter
             ACCESS      read-only
             STATUS      mandatory
             DESCRIPTION
                "The number of bytes in ICMP time exceededs
                 that have been counted across all DLCIs."
            ::= { dfrapPerfIcmpTotalEntry 15 }

      dfrapPerfIcmpTotalTxTimeExcd    OBJECT-TYPE
             SYNTAX      Counter
             ACCESS      read-only
             STATUS      mandatory
             DESCRIPTION
                "The number of bytes in ICMP time exceededs
                 that have been counted across all DLCIs."
            ::= { dfrapPerfIcmpTotalEntry 16 }

      dfrapPerfIcmpTotalRxParamProb    OBJECT-TYPE
             SYNTAX      Counter
             ACCESS      read-only
             STATUS      mandatory
             DESCRIPTION
                "The number of bytes in ICMP parameter problems
                 that have been counted across all DLCIs."
            ::= { dfrapPerfIcmpTotalEntry 17 }

      dfrapPerfIcmpTotalTxParamProb    OBJECT-TYPE
             SYNTAX      Counter
             ACCESS      read-only
             STATUS      mandatory
             DESCRIPTION
                "The number of bytes in ICMP parameter problems
                 that have been counted across all DLCIs."
            ::= { dfrapPerfIcmpTotalEntry 18 }

      dfrapPerfIcmpTotalRxTimestpReq    OBJECT-TYPE
             SYNTAX      Counter
             ACCESS      read-only
             STATUS      mandatory
             DESCRIPTION
                "The number of bytes in ICMP timestamp requests
                 that have been counted across all DLCIs."
            ::= { dfrapPerfIcmpTotalEntry 19 }

      dfrapPerfIcmpTotalTxTimestpReq    OBJECT-TYPE
             SYNTAX      Counter
             ACCESS      read-only
             STATUS      mandatory
             DESCRIPTION
                "The number of bytes in ICMP timestamp requests
                 that have been counted across all DLCIs."
            ::= { dfrapPerfIcmpTotalEntry 20 }

      dfrapPerfIcmpTotalRxTimestpRep    OBJECT-TYPE
             SYNTAX      Counter
             ACCESS      read-only
             STATUS      mandatory
             DESCRIPTION
                "The number of bytes in ICMP timestamp replies
                 that have been counted across all DLCIs."
            ::= { dfrapPerfIcmpTotalEntry 21 }

      dfrapPerfIcmpTotalTxTimestpRep    OBJECT-TYPE
             SYNTAX      Counter
             ACCESS      read-only
             STATUS      mandatory
             DESCRIPTION
                "The number of bytes in ICMP timestamp replies
                 that have been counted across all DLCIs."
            ::= { dfrapPerfIcmpTotalEntry 22 }

      dfrapPerfIcmpTotalRxAddrMaskReq    OBJECT-TYPE
             SYNTAX      Counter
             ACCESS      read-only
             STATUS      mandatory
             DESCRIPTION
                "The number of bytes in ICMP address mask requests
                 that have been counted across all DLCIs."
            ::= { dfrapPerfIcmpTotalEntry 23 }

      dfrapPerfIcmpTotalTxAddrMaskReq    OBJECT-TYPE
             SYNTAX      Counter
             ACCESS      read-only
             STATUS      mandatory
             DESCRIPTION
                "The number of bytes in ICMP address mask requests
                 that have been counted across all DLCIs."
            ::= { dfrapPerfIcmpTotalEntry 24 }

      dfrapPerfIcmpTotalRxAddrMaskRep    OBJECT-TYPE
             SYNTAX      Counter
             ACCESS      read-only
             STATUS      mandatory
             DESCRIPTION
                "The number of bytes in ICMP address mask replies
                 that have been counted across all DLCIs."
            ::= { dfrapPerfIcmpTotalEntry 25 }

      dfrapPerfIcmpTotalTxAddrMaskRep    OBJECT-TYPE
             SYNTAX      Counter
             ACCESS      read-only
             STATUS      mandatory
             DESCRIPTION
                "The number of bytes in ICMP address mask replies
                 that have been counted across all DLCIs."
            ::= { dfrapPerfIcmpTotalEntry 26 }

      dfrapPerfIcmpTotalRxPktTooBig    OBJECT-TYPE
             SYNTAX      Counter
             ACCESS      read-only
             STATUS      mandatory
             DESCRIPTION
                "The number of bytes in ICMP packet too bigs
                 that have been counted across all DLCIs."
            ::= { dfrapPerfIcmpTotalEntry 27 }

      dfrapPerfIcmpTotalTxPktTooBig    OBJECT-TYPE
             SYNTAX      Counter
             ACCESS      read-only
             STATUS      mandatory
             DESCRIPTION
                "The number of bytes in ICMP packet too bigs
                 that have been counted across all DLCIs."
            ::= { dfrapPerfIcmpTotalEntry 28 }

      dfrapPerfIcmpTotalRxGmQuery    OBJECT-TYPE
             SYNTAX      Counter
             ACCESS      read-only
             STATUS      mandatory
             DESCRIPTION
                "The number of bytes in ICMP group membership
                 queries that have been counted across all DLCIs."
            ::= { dfrapPerfIcmpTotalEntry 29 }

      dfrapPerfIcmpTotalTxGmQuery    OBJECT-TYPE
             SYNTAX      Counter
             ACCESS      read-only
             STATUS      mandatory
             DESCRIPTION
                "The number of bytes in ICMP group membership
                 queries that have been counted across all DLCIs."
            ::= { dfrapPerfIcmpTotalEntry 30 }

      dfrapPerfIcmpTotalRxGmReport    OBJECT-TYPE
             SYNTAX      Counter
             ACCESS      read-only
             STATUS      mandatory
             DESCRIPTION
                "The number of bytes in ICMP group membership
                 reports that have been counted across all DLCIs."
            ::= { dfrapPerfIcmpTotalEntry 31 }

      dfrapPerfIcmpTotalTxGmReport    OBJECT-TYPE
             SYNTAX      Counter
             ACCESS      read-only
             STATUS      mandatory
             DESCRIPTION
                "The number of bytes in ICMP group membership
                 reports that have been counted across all DLCIs."
            ::= { dfrapPerfIcmpTotalEntry 32 }

      dfrapPerfIcmpTotalRxGmReduct    OBJECT-TYPE
             SYNTAX      Counter
             ACCESS      read-only
             STATUS      mandatory
             DESCRIPTION
                "The number of bytes in ICMP group membership
                 reductions that have been counted across all DLCIs."
            ::= { dfrapPerfIcmpTotalEntry 33 }

      dfrapPerfIcmpTotalTxGmReduct    OBJECT-TYPE
             SYNTAX      Counter
             ACCESS      read-only
             STATUS      mandatory
             DESCRIPTION
                "The number of bytes in ICMP group membership
                 reductions that have been counted across all DLCIs."
            ::= { dfrapPerfIcmpTotalEntry 34 }

   --  Application-level Short Term Statistics for each DLCI.

   dfrapPerfApplicationPerDlciTable OBJECT-TYPE
         SYNTAX   SEQUENCE OF DfrapPerfApplicationPerDlciEntry
         ACCESS   not-accessible
         STATUS   mandatory
         DESCRIPTION
            "The Short Term Statistics on the Application
            protocol for each DLCI."
         ::= { dfrapPerfNetworkShortTerm 7 }

         dfrapPerfApplicationPerDlciEntry OBJECT-TYPE
             SYNTAX   DfrapPerfApplicationPerDlciEntry
             ACCESS   not-accessible
             STATUS   mandatory
             DESCRIPTION
                "The Application Short Term Statistics for a particular DLCI."
            INDEX { dfrapPerfApplicationPerDlciInterval, 
                    dfrapPerfApplicationPerDlciValue }
            ::= { dfrapPerfApplicationPerDlciTable 1 }

         DfrapPerfApplicationPerDlciEntry ::=
             SEQUENCE {
                 dfrapPerfApplicationPerDlciInterval   INTEGER,
                 dfrapPerfApplicationPerDlciValue      INTEGER,
                 dfrapPerfApplicationPerDlciRxSnmp     Counter,
                 dfrapPerfApplicationPerDlciTxSnmp     Counter,
                 dfrapPerfApplicationPerDlciRxSnmpTrap Counter,
                 dfrapPerfApplicationPerDlciTxSnmpTrap Counter,
                 dfrapPerfApplicationPerDlciRxHttp     Counter,
                 dfrapPerfApplicationPerDlciTxHttp     Counter,
                 dfrapPerfApplicationPerDlciRxTelnet   Counter,
                 dfrapPerfApplicationPerDlciTxTelnet   Counter,
                 dfrapPerfApplicationPerDlciRxSmtp     Counter,
                 dfrapPerfApplicationPerDlciTxSmtp     Counter,
                 dfrapPerfApplicationPerDlciRxFtp      Counter,
                 dfrapPerfApplicationPerDlciTxFtp      Counter,
                 dfrapPerfApplicationPerDlciRxTftp     Counter,
                 dfrapPerfApplicationPerDlciTxTftp     Counter,
                 dfrapPerfApplicationPerDlciRxCustom1  Counter,
                 dfrapPerfApplicationPerDlciTxCustom1  Counter,
                 dfrapPerfApplicationPerDlciRxCustom2  Counter,
                 dfrapPerfApplicationPerDlciTxCustom2  Counter,
                 dfrapPerfApplicationPerDlciRxCustom3  Counter,
                 dfrapPerfApplicationPerDlciTxCustom3  Counter,
                 dfrapPerfApplicationPerDlciRxCustom4  Counter,
                 dfrapPerfApplicationPerDlciTxCustom4  Counter
             }

      dfrapPerfApplicationPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfApplicationPerDlciEntry 1 }

      dfrapPerfApplicationPerDlciValue    OBJECT-TYPE
             SYNTAX      INTEGER 
             ACCESS      read-only
             STATUS      mandatory
             DESCRIPTION
                "The DLCI value with which the Statistics are associated."
            ::= { dfrapPerfApplicationPerDlciEntry 2 }

      dfrapPerfApplicationPerDlciRxSnmp    OBJECT-TYPE
             SYNTAX      Counter
             ACCESS      read-only
             STATUS      mandatory
             DESCRIPTION
                "The number of received SNMP bytes
                 that have been counted on this DLCI."
            ::= { dfrapPerfApplicationPerDlciEntry 3 }

      dfrapPerfApplicationPerDlciTxSnmp    OBJECT-TYPE
             SYNTAX      Counter
             ACCESS      read-only
             STATUS      mandatory
             DESCRIPTION
                "The number of transmitted SNMP bytes
                 that have been counted on this DLCI."
            ::= { dfrapPerfApplicationPerDlciEntry 4 }

      dfrapPerfApplicationPerDlciRxSnmpTrap    OBJECT-TYPE
             SYNTAX      Counter
             ACCESS      read-only
             STATUS      mandatory
             DESCRIPTION
                "The number of received SNMP TRAP bytes
                 that have been counted on this DLCI."
            ::= { dfrapPerfApplicationPerDlciEntry 5 }

      dfrapPerfApplicationPerDlciTxSnmpTrap    OBJECT-TYPE
             SYNTAX      Counter
             ACCESS      read-only
             STATUS      mandatory
             DESCRIPTION
                "The number of transmitted SNMP TRAP bytes
                 that have been counted on this DLCI."
            ::= { dfrapPerfApplicationPerDlciEntry 6 }

      dfrapPerfApplicationPerDlciRxHttp    OBJECT-TYPE
             SYNTAX      Counter
             ACCESS      read-only
             STATUS      mandatory
             DESCRIPTION
                "The number of received HTTP bytes
                 that have been counted on this DLCI."
            ::= { dfrapPerfApplicationPerDlciEntry 7 }

      dfrapPerfApplicationPerDlciTxHttp    OBJECT-TYPE
             SYNTAX      Counter
             ACCESS      read-only
             STATUS      mandatory
             DESCRIPTION
                "The number of transmitted HTTP bytes
                 that have been counted on this DLCI."
            ::= { dfrapPerfApplicationPerDlciEntry 8 }

      dfrapPerfApplicationPerDlciRxTelnet    OBJECT-TYPE
             SYNTAX      Counter
             ACCESS      read-only
             STATUS      mandatory
             DESCRIPTION
                "The number of received Telnet bytes
                 that have been counted on this DLCI."
            ::= { dfrapPerfApplicationPerDlciEntry 9 }

      dfrapPerfApplicationPerDlciTxTelnet    OBJECT-TYPE
             SYNTAX      Counter
             ACCESS      read-only
             STATUS      mandatory
             DESCRIPTION
                "The number of transmitted Telnet bytes
                 that have been counted on this DLCI."
            ::= { dfrapPerfApplicationPerDlciEntry 10 }

      dfrapPerfApplicationPerDlciRxSmtp    OBJECT-TYPE
             SYNTAX      Counter
             ACCESS      read-only
             STATUS      mandatory
             DESCRIPTION
                "The number of received SMTP bytes
                 that have been counted on this DLCI."
            ::= { dfrapPerfApplicationPerDlciEntry 11 }

      dfrapPerfApplicationPerDlciTxSmtp    OBJECT-TYPE
             SYNTAX      Counter
             ACCESS      read-only
             STATUS      mandatory
             DESCRIPTION
                "The number of transmitted SMTP bytes
                 that have been counted on this DLCI."
            ::= { dfrapPerfApplicationPerDlciEntry 12 }

      dfrapPerfApplicationPerDlciRxFtp    OBJECT-TYPE
             SYNTAX      Counter
             ACCESS      read-only
             STATUS      mandatory
             DESCRIPTION
                "The number of received FTP bytes
                 that have been counted on this DLCI."
            ::= { dfrapPerfApplicationPerDlciEntry 13 }

      dfrapPerfApplicationPerDlciTxFtp    OBJECT-TYPE
             SYNTAX      Counter
             ACCESS      read-only
             STATUS      mandatory
             DESCRIPTION
                "The number of transmitted FTP bytes
                 that have been counted on this DLCI."
            ::= { dfrapPerfApplicationPerDlciEntry 14 }

      dfrapPerfApplicationPerDlciRxTftp    OBJECT-TYPE
             SYNTAX      Counter
             ACCESS      read-only
             STATUS      mandatory
             DESCRIPTION
                "The number of received TFTP bytes
                 that have been counted on this DLCI."
            ::= { dfrapPerfApplicationPerDlciEntry 15 }

      dfrapPerfApplicationPerDlciTxTftp    OBJECT-TYPE
             SYNTAX      Counter
             ACCESS      read-only
             STATUS      mandatory
             DESCRIPTION
                "The number of transmitted TFTP bytes
                 that have been counted on this DLCI."
            ::= { dfrapPerfApplicationPerDlciEntry 16 }

      dfrapPerfApplicationPerDlciRxCustom1    OBJECT-TYPE
             SYNTAX      Counter
             ACCESS      read-only
             STATUS      mandatory
             DESCRIPTION
                "The number of received bytes of
                 User Defined Protocol #1 that have
                 been counted on this DLCI."
            ::= { dfrapPerfApplicationPerDlciEntry 17 }

      dfrapPerfApplicationPerDlciTxCustom1    OBJECT-TYPE
             SYNTAX      Counter
             ACCESS      read-only
             STATUS      mandatory
             DESCRIPTION
                "The number of transmitted bytes of
                 User Defined Protocol #1 that have
                 been counted on this DLCI."
            ::= { dfrapPerfApplicationPerDlciEntry 18 }

      dfrapPerfApplicationPerDlciRxCustom2    OBJECT-TYPE
             SYNTAX      Counter
             ACCESS      read-only
             STATUS      mandatory
             DESCRIPTION
                "The number of received bytes of
                 User Defined Protocol #2 that have
                 been counted on this DLCI."
            ::= { dfrapPerfApplicationPerDlciEntry 19 }

      dfrapPerfApplicationPerDlciTxCustom2    OBJECT-TYPE
             SYNTAX      Counter
             ACCESS      read-only
             STATUS      mandatory
             DESCRIPTION
                "The number of transmitted bytes of
                 User Defined Protocol #2 that have
                 been counted on this DLCI."
            ::= { dfrapPerfApplicationPerDlciEntry 20 }

      dfrapPerfApplicationPerDlciRxCustom3    OBJECT-TYPE
             SYNTAX      Counter
             ACCESS      read-only
             STATUS      mandatory
             DESCRIPTION
                "The number of received bytes of
                 User Defined Protocol #3 that have
                 been counted on this DLCI."
            ::= { dfrapPerfApplicationPerDlciEntry 21 }

      dfrapPerfApplicationPerDlciTxCustom3    OBJECT-TYPE
             SYNTAX      Counter
             ACCESS      read-only
             STATUS      mandatory
             DESCRIPTION
                "The number of transmitted bytes of
                 User Defined Protocol #3 that have
                 been counted on this DLCI."
            ::= { dfrapPerfApplicationPerDlciEntry 22 }

      dfrapPerfApplicationPerDlciRxCustom4    OBJECT-TYPE
             SYNTAX      Counter
             ACCESS      read-only
             STATUS      mandatory
             DESCRIPTION
                "The number of received bytes of
                 User Defined Protocol #4 that have
                 been counted on this DLCI."
            ::= { dfrapPerfApplicationPerDlciEntry 23 }

      dfrapPerfApplicationPerDlciTxCustom4    OBJECT-TYPE
             SYNTAX      Counter
             ACCESS      read-only
             STATUS      mandatory
             DESCRIPTION
                "The number of transmitted bytes of
                 User Defined Protocol #4 that have
                 been counted on this DLCI."
            ::= { dfrapPerfApplicationPerDlciEntry 24 }



   --  Application-level Short Term Statistics totals.

   dfrapPerfApplicationTotalTable OBJECT-TYPE
         SYNTAX   SEQUENCE OF DfrapPerfApplicationTotalEntry
         ACCESS   not-accessible
         STATUS   mandatory
         DESCRIPTION
            "The Short Term Statistics on the Application
            protocol across all DLCIs."
         ::= { dfrapPerfNetworkShortTerm 8 }

         dfrapPerfApplicationTotalEntry OBJECT-TYPE
             SYNTAX   DfrapPerfApplicationTotalEntry
             ACCESS   not-accessible
             STATUS   mandatory
             DESCRIPTION
                "The Application Short Term Statistics across all DLCIs.."
             INDEX { dfrapPerfApplicationTotalInterval }
             ::= { dfrapPerfApplicationTotalTable 1 }

         DfrapPerfApplicationTotalEntry ::=
             SEQUENCE {
                 dfrapPerfApplicationTotalInterval   INTEGER,
                 dfrapPerfApplicationTotalRxSnmp     Counter,
                 dfrapPerfApplicationTotalTxSnmp     Counter,
                 dfrapPerfApplicationTotalRxSnmpTrap Counter,
                 dfrapPerfApplicationTotalTxSnmpTrap Counter,
                 dfrapPerfApplicationTotalRxHttp     Counter,
                 dfrapPerfApplicationTotalTxHttp     Counter,
                 dfrapPerfApplicationTotalRxTelnet   Counter,
                 dfrapPerfApplicationTotalTxTelnet   Counter,
                 dfrapPerfApplicationTotalRxSmtp     Counter,
                 dfrapPerfApplicationTotalTxSmtp     Counter,
                 dfrapPerfApplicationTotalRxFtp      Counter,
                 dfrapPerfApplicationTotalTxFtp      Counter,
                 dfrapPerfApplicationTotalRxTftp     Counter,
                 dfrapPerfApplicationTotalTxTftp     Counter,
                 dfrapPerfApplicationTotalRxCustom1  Counter,
                 dfrapPerfApplicationTotalTxCustom1  Counter,
                 dfrapPerfApplicationTotalRxCustom2  Counter,
                 dfrapPerfApplicationTotalTxCustom2  Counter,
                 dfrapPerfApplicationTotalRxCustom3  Counter,
                 dfrapPerfApplicationTotalTxCustom3  Counter,
                 dfrapPerfApplicationTotalRxCustom4  Counter,
                 dfrapPerfApplicationTotalTxCustom4  Counter
             }

      dfrapPerfApplicationTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfApplicationTotalEntry 1 }

      dfrapPerfApplicationTotalRxSnmp    OBJECT-TYPE
             SYNTAX      Counter
             ACCESS      read-only
             STATUS      mandatory
             DESCRIPTION
                "The number of received SNMP bytes
                 that have been counted across all DLCIs."
            ::= { dfrapPerfApplicationTotalEntry 3 }

      dfrapPerfApplicationTotalTxSnmp    OBJECT-TYPE
             SYNTAX      Counter
             ACCESS      read-only
             STATUS      mandatory
             DESCRIPTION
                "The number of transmitted SNMP bytes
                 that have been counted across all DLCIs."
            ::= { dfrapPerfApplicationTotalEntry 4 }

      dfrapPerfApplicationTotalRxSnmpTrap    OBJECT-TYPE
             SYNTAX      Counter
             ACCESS      read-only
             STATUS      mandatory
             DESCRIPTION
                "The number of received SNMP TRAP bytes
                 that have been counted across all DLCIs."
            ::= { dfrapPerfApplicationTotalEntry 5 }

      dfrapPerfApplicationTotalTxSnmpTrap    OBJECT-TYPE
             SYNTAX      Counter
             ACCESS      read-only
             STATUS      mandatory
             DESCRIPTION
                "The number of transmitted SNMP TRAP bytes
                 that have been counted across all DLCIs."
            ::= { dfrapPerfApplicationTotalEntry 6 }

      dfrapPerfApplicationTotalRxHttp    OBJECT-TYPE
             SYNTAX      Counter
             ACCESS      read-only
             STATUS      mandatory
             DESCRIPTION
                "The number of received HTTP bytes
                 that have been counted across all DLCIs."
            ::= { dfrapPerfApplicationTotalEntry 7 }

      dfrapPerfApplicationTotalTxHttp    OBJECT-TYPE
             SYNTAX      Counter
             ACCESS      read-only
             STATUS      mandatory
             DESCRIPTION
                "The number of transmitted HTTP bytes
                 that have been counted across all DLCIs."
            ::= { dfrapPerfApplicationTotalEntry 8 }

      dfrapPerfApplicationTotalRxTelnet    OBJECT-TYPE
             SYNTAX      Counter
             ACCESS      read-only
             STATUS      mandatory
             DESCRIPTION
                "The number of received Telnet bytes
                 that have been counted across all DLCIs."
            ::= { dfrapPerfApplicationTotalEntry 9 }

      dfrapPerfApplicationTotalTxTelnet    OBJECT-TYPE
             SYNTAX      Counter
             ACCESS      read-only
             STATUS      mandatory
             DESCRIPTION
                "The number of transmitted Telnet bytes
                 that have been counted across all DLCIs."
            ::= { dfrapPerfApplicationTotalEntry 10 }

      dfrapPerfApplicationTotalRxSmtp    OBJECT-TYPE
             SYNTAX      Counter
             ACCESS      read-only
             STATUS      mandatory
             DESCRIPTION
                "The number of received SMTP bytes
                 that have been counted across all DLCIs."
            ::= { dfrapPerfApplicationTotalEntry 11 }

      dfrapPerfApplicationTotalTxSmtp    OBJECT-TYPE
             SYNTAX      Counter
             ACCESS      read-only
             STATUS      mandatory
             DESCRIPTION
                "The number of transmitted SMTP bytes
                 that have been counted across all DLCIs."
            ::= { dfrapPerfApplicationTotalEntry 12 }

      dfrapPerfApplicationTotalRxFtp    OBJECT-TYPE
             SYNTAX      Counter
             ACCESS      read-only
             STATUS      mandatory
             DESCRIPTION
                "The number of received FTP bytes
                 that have been counted across all DLCIs."
            ::= { dfrapPerfApplicationTotalEntry 13 }

      dfrapPerfApplicationTotalTxFtp    OBJECT-TYPE
             SYNTAX      Counter
             ACCESS      read-only
             STATUS      mandatory
             DESCRIPTION
                "The number of transmitted FTP bytes
                 that have been counted across all DLCIs."
            ::= { dfrapPerfApplicationTotalEntry 14 }

      dfrapPerfApplicationTotalRxTftp    OBJECT-TYPE
             SYNTAX      Counter
             ACCESS      read-only
             STATUS      mandatory
             DESCRIPTION
                "The number of received TFTP bytes
                 that have been counted across all DLCIs."
            ::= { dfrapPerfApplicationTotalEntry 15 }

      dfrapPerfApplicationTotalTxTftp    OBJECT-TYPE
             SYNTAX      Counter
             ACCESS      read-only
             STATUS      mandatory
             DESCRIPTION
                "The number of transmitted TFTP bytes
                 that have been counted across all DLCIs."
            ::= { dfrapPerfApplicationTotalEntry 16 }

      dfrapPerfApplicationTotalRxCustom1    OBJECT-TYPE
             SYNTAX      Counter
             ACCESS      read-only
             STATUS      mandatory
             DESCRIPTION
                "The number of received bytes of
                 User Defined Protocol #1 that have
                 been counted across all DLCIs."
            ::= { dfrapPerfApplicationTotalEntry 17 }

      dfrapPerfApplicationTotalTxCustom1    OBJECT-TYPE
             SYNTAX      Counter
             ACCESS      read-only
             STATUS      mandatory
             DESCRIPTION
                "The number of transmitted bytes of
                 User Defined Protocol #1 that have
                 been counted across all DLCIs."
            ::= { dfrapPerfApplicationTotalEntry 18 }

      dfrapPerfApplicationTotalRxCustom2    OBJECT-TYPE
             SYNTAX      Counter
             ACCESS      read-only
             STATUS      mandatory
             DESCRIPTION
                "The number of received bytes of
                 User Defined Protocol #2 that have
                 been counted across all DLCIs."
            ::= { dfrapPerfApplicationTotalEntry 19 }

      dfrapPerfApplicationTotalTxCustom2    OBJECT-TYPE
             SYNTAX      Counter
             ACCESS      read-only
             STATUS      mandatory
             DESCRIPTION
                "The number of transmitted bytes of
                 User Defined Protocol #2 that have
                 been counted across all DLCIs."
            ::= { dfrapPerfApplicationTotalEntry 20 }

      dfrapPerfApplicationTotalRxCustom3    OBJECT-TYPE
             SYNTAX      Counter
             ACCESS      read-only
             STATUS      mandatory
             DESCRIPTION
                "The number of received bytes of
                 User Defined Protocol #3 that have
                 been counted across all DLCIs."
            ::= { dfrapPerfApplicationTotalEntry 21 }

      dfrapPerfApplicationTotalTxCustom3    OBJECT-TYPE
             SYNTAX      Counter
             ACCESS      read-only
             STATUS      mandatory
             DESCRIPTION
                "The number of transmitted bytes of
                 User Defined Protocol #3 that have
                 been counted across all DLCIs."
            ::= { dfrapPerfApplicationTotalEntry 22 }

      dfrapPerfApplicationTotalRxCustom4    OBJECT-TYPE
             SYNTAX      Counter
             ACCESS      read-only
             STATUS      mandatory
             DESCRIPTION
                "The number of received bytes of
                 User Defined Protocol #4 that have
                 been counted across all DLCIs."
            ::= { dfrapPerfApplicationTotalEntry 23 }

      dfrapPerfApplicationTotalTxCustom4    OBJECT-TYPE
             SYNTAX      Counter
             ACCESS      read-only
             STATUS      mandatory
             DESCRIPTION
                "The number of transmitted bytes of
                 User Defined Protocol #4 that have
                 been counted across all DLCIs."
            ::= { dfrapPerfApplicationTotalEntry 24 }


   --  Routing Short Term Statistics for each DLCI.

   dfrapPerfRoutingPerDlciTable OBJECT-TYPE
         SYNTAX   SEQUENCE OF DfrapPerfRoutingPerDlciEntry
         ACCESS   not-accessible
         STATUS   mandatory
         DESCRIPTION
            "The Short Term Statistics on the Routing
            protocol for each DLCI."
         ::= { dfrapPerfNetworkShortTerm 9 }

         dfrapPerfRoutingPerDlciEntry OBJECT-TYPE
             SYNTAX   DfrapPerfRoutingPerDlciEntry
             ACCESS   not-accessible
             STATUS   mandatory
             DESCRIPTION
                "The Routing Short Term Statistics for a particular DLCI."
            INDEX { dfrapPerfRoutingPerDlciInterval,
                    dfrapPerfRoutingPerDlciValue }
            ::= { dfrapPerfRoutingPerDlciTable 1 }

         DfrapPerfRoutingPerDlciEntry ::=
             SEQUENCE {
                 dfrapPerfRoutingPerDlciInterval  INTEGER,
                 dfrapPerfRoutingPerDlciValue     INTEGER,
                 dfrapPerfRoutingPerDlciRxOspf    Counter,
                 dfrapPerfRoutingPerDlciTxOspf    Counter,
                 dfrapPerfRoutingPerDlciRxRip     Counter,
                 dfrapPerfRoutingPerDlciTxRip     Counter,
                 dfrapPerfRoutingPerDlciRxNetbios Counter,
                 dfrapPerfRoutingPerDlciTxNetbios Counter
             }

      dfrapPerfRoutingPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfRoutingPerDlciEntry 1 }

      dfrapPerfRoutingPerDlciValue    OBJECT-TYPE
             SYNTAX      INTEGER 
             ACCESS      read-only
             STATUS      mandatory
             DESCRIPTION
                "The DLCI value with which the Statistics are associated."
            ::= { dfrapPerfRoutingPerDlciEntry 2 }


      dfrapPerfRoutingPerDlciRxOspf    OBJECT-TYPE
             SYNTAX      Counter
             ACCESS      read-only
             STATUS      mandatory
             DESCRIPTION
                "The number of received OSPF bytes
                 that have been counted on this DLCI."
            ::= { dfrapPerfRoutingPerDlciEntry 3 }

      dfrapPerfRoutingPerDlciTxOspf    OBJECT-TYPE
             SYNTAX      Counter
             ACCESS      read-only
             STATUS      mandatory
             DESCRIPTION
                "The number of transmitted OSPF bytes
                 that have been counted on this DLCI."
            ::= { dfrapPerfRoutingPerDlciEntry 4 }

      dfrapPerfRoutingPerDlciRxRip    OBJECT-TYPE
             SYNTAX      Counter
             ACCESS      read-only
             STATUS      mandatory
             DESCRIPTION
                "The number of received RIP bytes
                 that have been counted on this DLCI."
            ::= { dfrapPerfRoutingPerDlciEntry 5 }

      dfrapPerfRoutingPerDlciTxRip    OBJECT-TYPE
             SYNTAX      Counter
             ACCESS      read-only
             STATUS      mandatory
             DESCRIPTION
                "The number of transmitted RIP bytes
                 that have been counted on this DLCI."
            ::= { dfrapPerfRoutingPerDlciEntry 6 }

      dfrapPerfRoutingPerDlciRxNetbios    OBJECT-TYPE
             SYNTAX      Counter
             ACCESS      read-only
             STATUS      mandatory
             DESCRIPTION
                "The number of received Netbios bytes
                 that have been counted on this DLCI."
            ::= { dfrapPerfRoutingPerDlciEntry 7 }

      dfrapPerfRoutingPerDlciTxNetbios    OBJECT-TYPE
             SYNTAX      Counter
             ACCESS      read-only
             STATUS      mandatory
             DESCRIPTION
                "The number of transmitted Netbios bytes
                 that have been counted on this DLCI."
            ::= { dfrapPerfRoutingPerDlciEntry 8 }


   --  Routing Short Term Statistics totals.

   dfrapPerfRoutingTotalTable OBJECT-TYPE
         SYNTAX   SEQUENCE OF DfrapPerfRoutingTotalEntry
         ACCESS   not-accessible
         STATUS   mandatory
         DESCRIPTION
            "The Short Term Statistics on the Routing
            protocol across all DLCIs."
         ::= { dfrapPerfNetworkShortTerm 10 }

         dfrapPerfRoutingTotalEntry OBJECT-TYPE
             SYNTAX   DfrapPerfRoutingTotalEntry
             ACCESS   not-accessible
             STATUS   mandatory
             DESCRIPTION
                "The Routing Short Term Statistics across all DLCIs."
             INDEX { dfrapPerfRoutingTotalInterval }
             ::= { dfrapPerfRoutingTotalTable 1 }

         DfrapPerfRoutingTotalEntry ::=
             SEQUENCE {
                 dfrapPerfRoutingTotalInterval  INTEGER,
                 dfrapPerfRoutingTotalRxOspf    Counter,
                 dfrapPerfRoutingTotalTxOspf    Counter,
                 dfrapPerfRoutingTotalRxRip     Counter,
                 dfrapPerfRoutingTotalTxRip     Counter,
                 dfrapPerfRoutingTotalRxNetbios Counter,
                 dfrapPerfRoutingTotalTxNetbios Counter
             }

      dfrapPerfRoutingTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfRoutingTotalEntry 1 }

      dfrapPerfRoutingTotalRxOspf    OBJECT-TYPE
             SYNTAX      Counter 
             ACCESS      read-only
             STATUS      mandatory
             DESCRIPTION
                "The number of received OSPF bytes
                 that have been counted across all DLCIs."
            ::= { dfrapPerfRoutingTotalEntry 3 }

      dfrapPerfRoutingTotalTxOspf    OBJECT-TYPE
             SYNTAX      Counter
             ACCESS      read-only
             STATUS      mandatory
             DESCRIPTION
                "The number of transmitted OSPF bytes
                 that have been counted across all DLCIs."
            ::= { dfrapPerfRoutingTotalEntry 4 }

      dfrapPerfRoutingTotalRxRip    OBJECT-TYPE
             SYNTAX      Counter
             ACCESS      read-only
             STATUS      mandatory
             DESCRIPTION
                "The number of received RIP bytes
                 that have been counted across all DLCIs."
            ::= { dfrapPerfRoutingTotalEntry 5 }

      dfrapPerfRoutingTotalTxRip    OBJECT-TYPE
             SYNTAX      Counter
             ACCESS      read-only
             STATUS      mandatory
             DESCRIPTION
                "The number of transmitted RIP bytes
                 that have been counted across all DLCIs."
            ::= { dfrapPerfRoutingTotalEntry 6 }

      dfrapPerfRoutingTotalRxNetbios    OBJECT-TYPE
             SYNTAX      Counter
             ACCESS      read-only
             STATUS      mandatory
             DESCRIPTION
                "The number of received Netbios bytes
                 that have been counted across all DLCIs."
            ::= { dfrapPerfRoutingTotalEntry 7 }

      dfrapPerfRoutingTotalTxNetbios    OBJECT-TYPE
             SYNTAX      Counter
             ACCESS      read-only
             STATUS      mandatory
             DESCRIPTION
                "The number of transmitted Netbios bytes
                 that have been counted across all DLCIs."
            ::= { dfrapPerfRoutingTotalEntry 8 }



   --  IPX Short Term Statistics for each DLCI.

   dfrapPerfIpxPerDlciTable OBJECT-TYPE
         SYNTAX   SEQUENCE OF DfrapPerfIpxPerDlciEntry
         ACCESS   not-accessible
         STATUS   mandatory
         DESCRIPTION
            "Short Term Statistics on the IPX
             protocol for each DLCI."
         ::= { dfrapPerfNetworkShortTerm 11 }

         dfrapPerfIpxPerDlciEntry OBJECT-TYPE
             SYNTAX   DfrapPerfIpxPerDlciEntry
             ACCESS   not-accessible
             STATUS   mandatory
             DESCRIPTION
                "The IPX Short Term Statistics for a particular DLCI."
            INDEX { dfrapPerfIpxPerDlciInterval, dfrapPerfIpxPerDlciValue }
            ::= { dfrapPerfIpxPerDlciTable 1 }

         DfrapPerfIpxPerDlciEntry ::=
             SEQUENCE {
                 dfrapPerfIpxPerDlciInterval   INTEGER,
                 dfrapPerfIpxPerDlciValue      INTEGER,
                 dfrapPerfIpxPerDlciRxTotal    Counter,
                 dfrapPerfIpxPerDlciTxTotal    Counter,
                 dfrapPerfIpxPerDlciRxSpx      Counter,
                 dfrapPerfIpxPerDlciTxSpx      Counter,
                 dfrapPerfIpxPerDlciRxNcp      Counter,
                 dfrapPerfIpxPerDlciTxNcp      Counter,
                 dfrapPerfIpxPerDlciRxSap      Counter,
                 dfrapPerfIpxPerDlciTxSap      Counter,
                 dfrapPerfIpxPerDlciRxRip      Counter,
                 dfrapPerfIpxPerDlciTxRip      Counter,
                 dfrapPerfIpxPerDlciRxNetbios  Counter,
                 dfrapPerfIpxPerDlciTxNetbios  Counter,
                 dfrapPerfIpxPerDlciRxOther    Counter,
                 dfrapPerfIpxPerDlciTxOther    Counter
             }

      dfrapPerfIpxPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfIpxPerDlciEntry 1 }

      dfrapPerfIpxPerDlciValue    OBJECT-TYPE
             SYNTAX      INTEGER 
            ACCESS      read-only
             STATUS      mandatory
             DESCRIPTION
                "The DLCI value in which the Statistics are associated."
            ::= { dfrapPerfIpxPerDlciEntry 2 }

      dfrapPerfIpxPerDlciRxTotal    OBJECT-TYPE
             SYNTAX      Counter
             ACCESS      read-only
             STATUS      mandatory
             DESCRIPTION
                "The total number of IPX bytes
                 that have been counted on this DLCI."
            ::= { dfrapPerfIpxPerDlciEntry 3 }

      dfrapPerfIpxPerDlciTxTotal    OBJECT-TYPE
             SYNTAX      Counter
             ACCESS      read-only
             STATUS      mandatory
             DESCRIPTION
                "The total number of IPX bytes
                 that have been counted on this DLCI."
            ::= { dfrapPerfIpxPerDlciEntry 4 }

      dfrapPerfIpxPerDlciRxSpx    OBJECT-TYPE
             SYNTAX      Counter
             ACCESS      read-only
             STATUS      mandatory
             DESCRIPTION
                "The number of SPX over IPX bytes
                 that have been counted on this DLCI."
            ::= { dfrapPerfIpxPerDlciEntry 5 }

      dfrapPerfIpxPerDlciTxSpx    OBJECT-TYPE
             SYNTAX      Counter
             ACCESS      read-only
             STATUS      mandatory
             DESCRIPTION
                "The number of SPX over IPX bytes
                 that have been counted on this DLCI."
            ::= { dfrapPerfIpxPerDlciEntry 6 }

      dfrapPerfIpxPerDlciRxNcp    OBJECT-TYPE
             SYNTAX      Counter
             ACCESS      read-only
             STATUS      mandatory
             DESCRIPTION
                "The number of NCP over IPX bytes
                 that have been counted on this DLCI."
            ::= { dfrapPerfIpxPerDlciEntry 7 }

      dfrapPerfIpxPerDlciTxNcp    OBJECT-TYPE
             SYNTAX      Counter
             ACCESS      read-only
             STATUS      mandatory
             DESCRIPTION
                "The number of NCP over IPX bytes
                 that have been counted on this DLCI."
            ::= { dfrapPerfIpxPerDlciEntry 8 }

      dfrapPerfIpxPerDlciRxSap    OBJECT-TYPE
             SYNTAX      Counter
             ACCESS      read-only
             STATUS      mandatory
             DESCRIPTION
                "The number of SAP over IPX bytes
                 that have been counted on this DLCI."
            ::= { dfrapPerfIpxPerDlciEntry 9 }

      dfrapPerfIpxPerDlciTxSap    OBJECT-TYPE
             SYNTAX      Counter
             ACCESS      read-only
             STATUS      mandatory
             DESCRIPTION
                "The number of SAP over IPX bytes
                 that have been counted on this DLCI."
            ::= { dfrapPerfIpxPerDlciEntry 10 }

      dfrapPerfIpxPerDlciRxRip    OBJECT-TYPE
             SYNTAX      Counter
             ACCESS      read-only
             STATUS      mandatory
             DESCRIPTION
                "The number of RIP over IPX bytes
                 that have been counted on this DLCI."
            ::= { dfrapPerfIpxPerDlciEntry 11 }

      dfrapPerfIpxPerDlciTxRip    OBJECT-TYPE
             SYNTAX      Counter
             ACCESS      read-only
             STATUS      mandatory
             DESCRIPTION
                "The number of RIP over IPX bytes
                 that have been counted on this DLCI."
            ::= { dfrapPerfIpxPerDlciEntry 12 }

      dfrapPerfIpxPerDlciRxNetbios    OBJECT-TYPE
             SYNTAX      Counter
             ACCESS      read-only
             STATUS      mandatory
             DESCRIPTION
                "The number of NETBIOS over IPX bytes
                 that have been counted on this DLCI."
            ::= { dfrapPerfIpxPerDlciEntry 13 }

      dfrapPerfIpxPerDlciTxNetbios    OBJECT-TYPE
             SYNTAX      Counter
             ACCESS      read-only
             STATUS      mandatory
             DESCRIPTION
                "The number of NETBIOS over IPX bytes
                 that have been counted on this DLCI."
            ::= { dfrapPerfIpxPerDlciEntry 14 }

      dfrapPerfIpxPerDlciRxOther    OBJECT-TYPE
             SYNTAX      Counter
             ACCESS      read-only
             STATUS      mandatory
             DESCRIPTION
                "The number of received bytes on this DLCI
                 from protocols over IPX that are not counted
                 elsewhere in this table."
            ::= { dfrapPerfIpxPerDlciEntry 15 }

      dfrapPerfIpxPerDlciTxOther    OBJECT-TYPE
             SYNTAX      Counter
             ACCESS      read-only
             STATUS      mandatory
             DESCRIPTION
                "The number of transmitted bytes on this DLCI
                 from protocols over IPX that are not counted
                 elsewhere in this table."
            ::= { dfrapPerfIpxPerDlciEntry 16 }


   --  IPX Short Term Statistics totals.

   dfrapPerfIpxTotalTable OBJECT-TYPE
         SYNTAX   SEQUENCE OF DfrapPerfIpxTotalEntry
         ACCESS   not-accessible
         STATUS   mandatory
         DESCRIPTION
            "Short Term Statistics on the IPX
             protocol across all DLCIs."
         ::= { dfrapPerfNetworkShortTerm 12 }

         dfrapPerfIpxTotalEntry OBJECT-TYPE
             SYNTAX   DfrapPerfIpxTotalEntry
             ACCESS   not-accessible
             STATUS   mandatory
             DESCRIPTION
                "The IPX Short Term Statistics across all DLCIs."
             INDEX { dfrapPerfIpxTotalInterval }
             ::= { dfrapPerfIpxTotalTable 1 }

         DfrapPerfIpxTotalEntry ::=
             SEQUENCE {
                 dfrapPerfIpxTotalInterval   INTEGER,
                 dfrapPerfIpxTotalRxTotal    Counter,
                 dfrapPerfIpxTotalTxTotal    Counter,
                 dfrapPerfIpxTotalRxSpx      Counter,
                 dfrapPerfIpxTotalTxSpx      Counter,
                 dfrapPerfIpxTotalRxNcp      Counter,
                 dfrapPerfIpxTotalTxNcp      Counter,
                 dfrapPerfIpxTotalRxSap      Counter,
                 dfrapPerfIpxTotalTxSap      Counter,
                 dfrapPerfIpxTotalRxRip      Counter,
                 dfrapPerfIpxTotalTxRip      Counter,
                 dfrapPerfIpxTotalRxNetbios  Counter,
                 dfrapPerfIpxTotalTxNetbios  Counter,
                 dfrapPerfIpxTotalRxOther    Counter,
                 dfrapPerfIpxTotalTxOther    Counter
             }

      dfrapPerfIpxTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfIpxTotalEntry 1 }

      dfrapPerfIpxTotalRxTotal    OBJECT-TYPE
             SYNTAX      Counter
             ACCESS      read-only
             STATUS      mandatory
             DESCRIPTION
                "The total number of IPX bytes
                 that have been counted across all DLCIs."
            ::= { dfrapPerfIpxTotalEntry 3 }

      dfrapPerfIpxTotalTxTotal    OBJECT-TYPE
             SYNTAX      Counter
             ACCESS      read-only
             STATUS      mandatory
             DESCRIPTION
                "The total number of IPX bytes
                 that have been counted across all DLCIs."
            ::= { dfrapPerfIpxTotalEntry 4 }

      dfrapPerfIpxTotalRxSpx    OBJECT-TYPE
             SYNTAX      Counter
             ACCESS      read-only
             STATUS      mandatory
             DESCRIPTION
                "The number of SPX over IPX bytes
                 that have been counted across all DLCIs."
            ::= { dfrapPerfIpxTotalEntry 5 }

      dfrapPerfIpxTotalTxSpx    OBJECT-TYPE
             SYNTAX      Counter
             ACCESS      read-only
             STATUS      mandatory
             DESCRIPTION
                "The number of SPX over IPX bytes
                 that have been counted across all DLCIs."
            ::= { dfrapPerfIpxTotalEntry 6 }

      dfrapPerfIpxTotalRxNcp    OBJECT-TYPE
             SYNTAX      Counter
             ACCESS      read-only
             STATUS      mandatory
             DESCRIPTION
                "The number of NCP over IPX bytes
                 that have been counted across all DLCIs."
            ::= { dfrapPerfIpxTotalEntry 7 }

      dfrapPerfIpxTotalTxNcp    OBJECT-TYPE
             SYNTAX      Counter
             ACCESS      read-only
             STATUS      mandatory
             DESCRIPTION
                "The number of NCP over IPX bytes
                 that have been counted across all DLCIs."
            ::= { dfrapPerfIpxTotalEntry 8 }

      dfrapPerfIpxTotalRxSap    OBJECT-TYPE
             SYNTAX      Counter
             ACCESS      read-only
             STATUS      mandatory
             DESCRIPTION
                "The number of SAP over IPX bytes
                 that have been counted across all DLCIs."
            ::= { dfrapPerfIpxTotalEntry 9 }

      dfrapPerfIpxTotalTxSap    OBJECT-TYPE
             SYNTAX      Counter
             ACCESS      read-only
             STATUS      mandatory
             DESCRIPTION
                "The number of SAP over IPX bytes
                 that have been counted across all DLCIs."
            ::= { dfrapPerfIpxTotalEntry 10 }

      dfrapPerfIpxTotalRxRip    OBJECT-TYPE
             SYNTAX      Counter
             ACCESS      read-only
             STATUS      mandatory
             DESCRIPTION
                "The number of RIP over IPX bytes
                 that have been counted across all DLCIs."
            ::= { dfrapPerfIpxTotalEntry 11 }

      dfrapPerfIpxTotalTxRip    OBJECT-TYPE
             SYNTAX      Counter
             ACCESS      read-only
             STATUS      mandatory
             DESCRIPTION
                "The number of RIP over IPX bytes
                 that have been counted across all DLCIs."
            ::= { dfrapPerfIpxTotalEntry 12 }

      dfrapPerfIpxTotalRxNetbios    OBJECT-TYPE
             SYNTAX      Counter
             ACCESS      read-only
             STATUS      mandatory
             DESCRIPTION
                "The number of NETBIOS over IPX bytes
                 that have been counted across all DLCIs."
            ::= { dfrapPerfIpxTotalEntry 13 }

      dfrapPerfIpxTotalTxNetbios    OBJECT-TYPE
             SYNTAX      Counter
             ACCESS      read-only
             STATUS      mandatory
             DESCRIPTION
                "The number of NETBIOS over IPX bytes
                 that have been counted across all DLCIs."
            ::= { dfrapPerfIpxTotalEntry 14 }

      dfrapPerfIpxTotalRxOther    OBJECT-TYPE
             SYNTAX      Counter
             ACCESS      read-only
             STATUS      mandatory
             DESCRIPTION
                "The number of received bytes across all DLCIs
                 from protocols over IPX that are not counted
                 elsewhere in this table."
            ::= { dfrapPerfIpxTotalEntry 15 }

      dfrapPerfIpxTotalTxOther    OBJECT-TYPE
             SYNTAX      Counter
             ACCESS      read-only
             STATUS      mandatory
             DESCRIPTION
                "The number of transmitted bytes across all DLCIs
                 from protocols over IPX that are not counted
                 elsewhere in this table."
            ::= { dfrapPerfIpxTotalEntry 16 }


   --  SNA Short Term Statistics for each DLCI.

   dfrapPerfSnaPerDlciTable OBJECT-TYPE
         SYNTAX   SEQUENCE OF DfrapPerfSnaPerDlciEntry
         ACCESS   not-accessible
         STATUS   mandatory
         DESCRIPTION
            "Short Term Statistics on the SNA
             protocol for each DLCI."
         ::= { dfrapPerfNetworkShortTerm 13 }

         dfrapPerfSnaPerDlciEntry OBJECT-TYPE
             SYNTAX   DfrapPerfSnaPerDlciEntry
             ACCESS   not-accessible
             STATUS   mandatory
             DESCRIPTION
                "The SNA Short Term Statistics for a particular DLCI."
             INDEX { dfrapPerfSnaPerDlciInterval, dfrapPerfSnaPerDlciValue }
             ::= { dfrapPerfSnaPerDlciTable 1 }

         DfrapPerfSnaPerDlciEntry ::=
             SEQUENCE {
                 dfrapPerfSnaPerDlciInterval        INTEGER,
                 dfrapPerfSnaPerDlciValue           INTEGER,
                 dfrapPerfSnaPerDlciRxTotal         Counter,
                 dfrapPerfSnaPerDlciTxTotal         Counter,
                 dfrapPerfSnaPerDlciRxSubarea       Counter,
                 dfrapPerfSnaPerDlciTxSubarea       Counter,
                 dfrapPerfSnaPerDlciRxPeriph        Counter,
                 dfrapPerfSnaPerDlciTxPeriph        Counter,
                 dfrapPerfSnaPerDlciRxAppn          Counter,
                 dfrapPerfSnaPerDlciTxAppn          Counter,
                 dfrapPerfSnaPerDlciRxNetbios       Counter,
                 dfrapPerfSnaPerDlciTxNetbios       Counter,
                 dfrapPerfSnaPerDlciRxOther         Counter,
                 dfrapPerfSnaPerDlciTxOther         Counter
             }

      dfrapPerfSnaPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfSnaPerDlciEntry 1 }

      dfrapPerfSnaPerDlciValue    OBJECT-TYPE
             SYNTAX      INTEGER 
             ACCESS      read-only
             STATUS      mandatory
             DESCRIPTION
                "The DLCI value in which the Statistics are associated."
            ::= { dfrapPerfSnaPerDlciEntry 2 }

      dfrapPerfSnaPerDlciRxTotal    OBJECT-TYPE
             SYNTAX      Counter
             ACCESS      read-only
             STATUS      mandatory
             DESCRIPTION
                "The total number of SNA bytes
                 that have been counted on this DLCI."
            ::= { dfrapPerfSnaPerDlciEntry 3 }

      dfrapPerfSnaPerDlciTxTotal    OBJECT-TYPE
             SYNTAX      Counter
             ACCESS      read-only
             STATUS      mandatory
             DESCRIPTION
                "The total number of SNA bytes
                 that have been counted on this DLCI."
            ::= { dfrapPerfSnaPerDlciEntry 4 }

      dfrapPerfSnaPerDlciRxSubarea    OBJECT-TYPE
             SYNTAX      Counter
             ACCESS      read-only
             STATUS      mandatory
             DESCRIPTION
                "The number of SNA Subarea bytes
                 that have been counted on this DLCI."
            ::= { dfrapPerfSnaPerDlciEntry 5 }

      dfrapPerfSnaPerDlciTxSubarea    OBJECT-TYPE
             SYNTAX      Counter
             ACCESS      read-only
             STATUS      mandatory
             DESCRIPTION
                "The number of SNA Subarea bytes
                 that have been counted on this DLCI."
            ::= { dfrapPerfSnaPerDlciEntry 6 }

      dfrapPerfSnaPerDlciRxPeriph    OBJECT-TYPE
             SYNTAX      Counter
             ACCESS      read-only
             STATUS      mandatory
             DESCRIPTION
                "The number of SNA Periph bytes
                 that have been counted on this DLCI."
            ::= { dfrapPerfSnaPerDlciEntry 7 }

      dfrapPerfSnaPerDlciTxPeriph    OBJECT-TYPE
             SYNTAX      Counter
             ACCESS      read-only
             STATUS      mandatory
             DESCRIPTION
                "The number of SNA Periph bytes
                 that have been counted on this DLCI."
            ::= { dfrapPerfSnaPerDlciEntry 8 }

      dfrapPerfSnaPerDlciRxAppn    OBJECT-TYPE
             SYNTAX      Counter
             ACCESS      read-only
             STATUS      mandatory
             DESCRIPTION
                "The number of SNA Appn bytes
                 that have been counted on this DLCI."
            ::= { dfrapPerfSnaPerDlciEntry 9 }

      dfrapPerfSnaPerDlciTxAppn    OBJECT-TYPE
             SYNTAX      Counter
             ACCESS      read-only
             STATUS      mandatory
             DESCRIPTION
                "The number of SNA Appn bytes
                 that have been counted on this DLCI."
            ::= { dfrapPerfSnaPerDlciEntry 10 }

      dfrapPerfSnaPerDlciRxNetbios    OBJECT-TYPE
             SYNTAX      Counter
             ACCESS      read-only
             STATUS      mandatory
             DESCRIPTION
                "The number of SNA Netbios bytes
                 that have been counted on this DLCI."
            ::= { dfrapPerfSnaPerDlciEntry 11 }

      dfrapPerfSnaPerDlciTxNetbios    OBJECT-TYPE
             SYNTAX      Counter
             ACCESS      read-only
             STATUS      mandatory
             DESCRIPTION
                "The number of SNA Netbios bytes
                 that have been counted on this DLCI."
            ::= { dfrapPerfSnaPerDlciEntry 12 }

      dfrapPerfSnaPerDlciRxOther    OBJECT-TYPE
             SYNTAX      Counter
             ACCESS      read-only
             STATUS      mandatory
             DESCRIPTION
                "The number of received bytes on this DLCI
                 from protocols over SNA that are not counted
                 elsewhere in this table."
            ::= { dfrapPerfSnaPerDlciEntry 13 }

      dfrapPerfSnaPerDlciTxOther    OBJECT-TYPE
             SYNTAX      Counter
             ACCESS      read-only
             STATUS      mandatory
             DESCRIPTION
                "The number of transmitted bytes on this DLCI
                 from protocols over SNA that are not counted
                 elsewhere in this table."
            ::= { dfrapPerfSnaPerDlciEntry 14 }


   --  SNA Short Term Statistics totals.

   dfrapPerfSnaTotalTable OBJECT-TYPE
         SYNTAX   SEQUENCE OF DfrapPerfSnaTotalEntry
         ACCESS   not-accessible
         STATUS   mandatory
         DESCRIPTION
            "Short Term Statistics on the SNA
             protocol across all DLCIs."
         ::= { dfrapPerfNetworkShortTerm 14 }

         dfrapPerfSnaTotalEntry OBJECT-TYPE
             SYNTAX   DfrapPerfSnaTotalEntry
             ACCESS   not-accessible
             STATUS   mandatory
             DESCRIPTION
                "The SNA Short Term Statistics across all DLCIs."
             INDEX { dfrapPerfSnaTotalInterval }
             ::= { dfrapPerfSnaTotalTable 1 }

         DfrapPerfSnaTotalEntry ::=
             SEQUENCE {
                 dfrapPerfSnaTotalInterval        INTEGER,
                 dfrapPerfSnaTotalRxTotal         Counter,
                 dfrapPerfSnaTotalTxTotal         Counter,
                 dfrapPerfSnaTotalRxSubarea       Counter,
                 dfrapPerfSnaTotalTxSubarea       Counter,
                 dfrapPerfSnaTotalRxPeriph        Counter,
                 dfrapPerfSnaTotalTxPeriph        Counter,
                 dfrapPerfSnaTotalRxAppn          Counter,
                 dfrapPerfSnaTotalTxAppn          Counter,
                 dfrapPerfSnaTotalRxNetbios       Counter,
                 dfrapPerfSnaTotalTxNetbios       Counter,
                 dfrapPerfSnaTotalRxOther         Counter,
                 dfrapPerfSnaTotalTxOther         Counter
             }

      dfrapPerfSnaTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfSnaTotalEntry 1 }

      dfrapPerfSnaTotalRxTotal    OBJECT-TYPE
             SYNTAX      Counter
             ACCESS      read-only
             STATUS      mandatory
             DESCRIPTION
                "The total number of SNA bytes
                 that have been counted across all DLCIs."
            ::= { dfrapPerfSnaTotalEntry 3 }

      dfrapPerfSnaTotalTxTotal    OBJECT-TYPE
             SYNTAX      Counter
             ACCESS      read-only
             STATUS      mandatory
             DESCRIPTION
                "The total number of SNA bytes
                 that have been counted across all DLCIs."
            ::= { dfrapPerfSnaTotalEntry 4 }

      dfrapPerfSnaTotalRxSubarea    OBJECT-TYPE
             SYNTAX      Counter
             ACCESS      read-only
             STATUS      mandatory
             DESCRIPTION
                "The number of SNA Subarea bytes
                 that have been counted across all DLCIs."
            ::= { dfrapPerfSnaTotalEntry 5 }

      dfrapPerfSnaTotalTxSubarea    OBJECT-TYPE
             SYNTAX      Counter
             ACCESS      read-only
             STATUS      mandatory
             DESCRIPTION
                "The number of SNA Subarea bytes
                 that have been counted across all DLCIs."
            ::= { dfrapPerfSnaTotalEntry 6 }

      dfrapPerfSnaTotalRxPeriph    OBJECT-TYPE
             SYNTAX      Counter
             ACCESS      read-only
             STATUS      mandatory
             DESCRIPTION
                "The number of SNA Periph bytes
                 that have been counted across all DLCIs."
            ::= { dfrapPerfSnaTotalEntry 7 }

      dfrapPerfSnaTotalTxPeriph    OBJECT-TYPE
             SYNTAX      Counter
             ACCESS      read-only
             STATUS      mandatory
             DESCRIPTION
                "The number of SNA Periph bytes
                 that have been counted across all DLCIs."
            ::= { dfrapPerfSnaTotalEntry 8 }

      dfrapPerfSnaTotalRxAppn    OBJECT-TYPE
             SYNTAX      Counter
             ACCESS      read-only
             STATUS      mandatory
             DESCRIPTION
                "The number of SNA Appn bytes
                 that have been counted across all DLCIs."
            ::= { dfrapPerfSnaTotalEntry 9 }

      dfrapPerfSnaTotalTxAppn    OBJECT-TYPE
             SYNTAX      Counter
             ACCESS      read-only
             STATUS      mandatory
             DESCRIPTION
                "The number of SNA Appn bytes
                 that have been counted across all DLCIs."
            ::= { dfrapPerfSnaTotalEntry 10 }

      dfrapPerfSnaTotalRxNetbios    OBJECT-TYPE
             SYNTAX      Counter
             ACCESS      read-only
             STATUS      mandatory
             DESCRIPTION
                "The number of SNA Netbios bytes
                 that have been counted across all DLCIs."
            ::= { dfrapPerfSnaTotalEntry 11 }

      dfrapPerfSnaTotalTxNetbios    OBJECT-TYPE
             SYNTAX      Counter
             ACCESS      read-only
             STATUS      mandatory
             DESCRIPTION
                "The number of SNA Netbios bytes
                 that have been counted across all DLCIs."
            ::= { dfrapPerfSnaTotalEntry 12 }

      dfrapPerfSnaTotalRxOther    OBJECT-TYPE
             SYNTAX      Counter
             ACCESS      read-only
             STATUS      mandatory
             DESCRIPTION
                "The number of received bytes across all DLCIs
                 from protocols over SNA that are not counted
                 elsewhere in this table."
            ::= { dfrapPerfSnaTotalEntry 13 }

      dfrapPerfSnaTotalTxOther    OBJECT-TYPE
             SYNTAX      Counter
             ACCESS      read-only
             STATUS      mandatory
             DESCRIPTION
                "The number of transmitted bytes across all DLCIs
                 from protocols over SNA that are not counted
                 elsewhere in this table."
            ::= { dfrapPerfSnaTotalEntry 14 }


   --  ARP Short Term Statistics for each DLCI.

   dfrapPerfArpPerDlciTable OBJECT-TYPE
         SYNTAX   SEQUENCE OF DfrapPerfArpPerDlciEntry
         ACCESS   not-accessible
         STATUS   mandatory
         DESCRIPTION
            "Short Term Statistics on the ARP
             protocol for each DLCI."
         ::= { dfrapPerfNetworkShortTerm 15 }

         dfrapPerfArpPerDlciEntry OBJECT-TYPE
             SYNTAX   DfrapPerfArpPerDlciEntry
             ACCESS   not-accessible
             STATUS   mandatory
             DESCRIPTION
                "The ARP Short Term Statistics for a particular DLCI."
             INDEX { dfrapPerfArpPerDlciInterval, dfrapPerfArpPerDlciValue }
             ::= { dfrapPerfArpPerDlciTable 1 }

         DfrapPerfArpPerDlciEntry ::=
             SEQUENCE {
                 dfrapPerfArpPerDlciInterval        INTEGER,
                 dfrapPerfArpPerDlciValue           INTEGER,
                 dfrapPerfArpPerDlciRxTotal         Counter,
                 dfrapPerfArpPerDlciTxTotal         Counter,
                 dfrapPerfArpPerDlciRxArpReq        Counter,
                 dfrapPerfArpPerDlciTxArpReq        Counter,
                 dfrapPerfArpPerDlciRxArpRep        Counter,
                 dfrapPerfArpPerDlciTxArpRep        Counter,
                 dfrapPerfArpPerDlciRxRarpReq       Counter,
                 dfrapPerfArpPerDlciTxRarpReq       Counter,
                 dfrapPerfArpPerDlciRxRarpRep       Counter,
                 dfrapPerfArpPerDlciTxRarpRep       Counter,
                 dfrapPerfArpPerDlciRxInarpReq      Counter,
                 dfrapPerfArpPerDlciTxInarpReq      Counter,
                 dfrapPerfArpPerDlciRxInarpRep      Counter,
                 dfrapPerfArpPerDlciTxInarpRep      Counter,
                 dfrapPerfArpPerDlciRxOther         Counter,
                 dfrapPerfArpPerDlciTxOther         Counter
             }

      dfrapPerfArpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfArpPerDlciEntry 1 }

      dfrapPerfArpPerDlciValue    OBJECT-TYPE
             SYNTAX      INTEGER 
            ACCESS      read-only
             STATUS      mandatory
             DESCRIPTION
                "The DLCI value in which the Statistics are associated."
            ::= { dfrapPerfArpPerDlciEntry 2 }

      dfrapPerfArpPerDlciRxTotal    OBJECT-TYPE
             SYNTAX      Counter
             ACCESS      read-only
             STATUS      mandatory
             DESCRIPTION
                "The total number of ARP bytes
                 that have been counted on this DLCI."
            ::= { dfrapPerfArpPerDlciEntry 3 }

      dfrapPerfArpPerDlciTxTotal    OBJECT-TYPE
             SYNTAX      Counter
             ACCESS      read-only
             STATUS      mandatory
             DESCRIPTION
                "The total number of ARP bytes
                 that have been counted on this DLCI."
            ::= { dfrapPerfArpPerDlciEntry 4 }

      dfrapPerfArpPerDlciRxArpReq    OBJECT-TYPE
             SYNTAX      Counter
             ACCESS      read-only
             STATUS      mandatory
             DESCRIPTION
                "The number of ARP request bytes
                 that have been counted on this DLCI."
            ::= { dfrapPerfArpPerDlciEntry 5 }

      dfrapPerfArpPerDlciTxArpReq    OBJECT-TYPE
             SYNTAX      Counter
             ACCESS      read-only
             STATUS      mandatory
             DESCRIPTION
                "The number of ARP request bytes
                 that have been counted on this DLCI."
            ::= { dfrapPerfArpPerDlciEntry 6 }

      dfrapPerfArpPerDlciRxArpRep    OBJECT-TYPE
             SYNTAX      Counter
             ACCESS      read-only
             STATUS      mandatory
             DESCRIPTION
                "The number of ARP reply bytes
                 that have been counted on this DLCI."
            ::= { dfrapPerfArpPerDlciEntry 7 }

      dfrapPerfArpPerDlciTxArpRep    OBJECT-TYPE
             SYNTAX      Counter
             ACCESS      read-only
             STATUS      mandatory
             DESCRIPTION
                "The number of ARP reply bytes
                 that have been counted on this DLCI."
            ::= { dfrapPerfArpPerDlciEntry 8 }

      dfrapPerfArpPerDlciRxRarpReq    OBJECT-TYPE
             SYNTAX      Counter
             ACCESS      read-only
             STATUS      mandatory
             DESCRIPTION
                "The number of RARP request bytes
                 that have been counted on this DLCI."
            ::= { dfrapPerfArpPerDlciEntry 9 }

      dfrapPerfArpPerDlciTxRarpReq    OBJECT-TYPE
             SYNTAX      Counter
             ACCESS      read-only
             STATUS      mandatory
             DESCRIPTION
                "The number of RARP request bytes
                 that have been counted on this DLCI."
            ::= { dfrapPerfArpPerDlciEntry 10 }

      dfrapPerfArpPerDlciRxRarpRep    OBJECT-TYPE
             SYNTAX      Counter
             ACCESS      read-only
             STATUS      mandatory
             DESCRIPTION
                "The number of RARP reply bytes
                 that have been counted on this DLCI."
            ::= { dfrapPerfArpPerDlciEntry 11 }

      dfrapPerfArpPerDlciTxRarpRep    OBJECT-TYPE
             SYNTAX      Counter
             ACCESS      read-only
             STATUS      mandatory
             DESCRIPTION
                "The number of RARP reply bytes
                 that have been counted on this DLCI."
            ::= { dfrapPerfArpPerDlciEntry 12 }

      dfrapPerfArpPerDlciRxInarpReq    OBJECT-TYPE
             SYNTAX      Counter
             ACCESS      read-only
             STATUS      mandatory
             DESCRIPTION
                "The number of INARP request bytes
                 that have been counted on this DLCI."
            ::= { dfrapPerfArpPerDlciEntry 13 }

      dfrapPerfArpPerDlciTxInarpReq    OBJECT-TYPE
             SYNTAX      Counter
             ACCESS      read-only
             STATUS      mandatory
             DESCRIPTION
                "The number of INARP request bytes
                 that have been counted on this DLCI."
            ::= { dfrapPerfArpPerDlciEntry 14 }

      dfrapPerfArpPerDlciRxInarpRep    OBJECT-TYPE
             SYNTAX      Counter
             ACCESS      read-only
             STATUS      mandatory
             DESCRIPTION
                "The number of INARP reply bytes
                 that have been counted on this DLCI."
            ::= { dfrapPerfArpPerDlciEntry 15 }

      dfrapPerfArpPerDlciTxInarpRep    OBJECT-TYPE
             SYNTAX      Counter
             ACCESS      read-only
             STATUS      mandatory
             DESCRIPTION
                "The number of INARP reply bytes
                 that have been counted on this DLCI."
            ::= { dfrapPerfArpPerDlciEntry 16 }

      dfrapPerfArpPerDlciRxOther    OBJECT-TYPE
             SYNTAX      Counter
             ACCESS      read-only
             STATUS      mandatory
             DESCRIPTION
                "The number of received bytes on this DLCI
                 from ARP message types that are not counted
                 elsewhere in this table."
            ::= { dfrapPerfArpPerDlciEntry 17 }

      dfrapPerfArpPerDlciTxOther    OBJECT-TYPE
             SYNTAX      Counter
             ACCESS      read-only
             STATUS      mandatory
             DESCRIPTION
                "The number of transmitted bytes on this DLCI
                 from ARP message types that are not counted
                 elsewhere in this table."
            ::= { dfrapPerfArpPerDlciEntry 18 }


   --  ARP Short Term Statistics totals.

   dfrapPerfArpTotalTable OBJECT-TYPE
         SYNTAX   SEQUENCE OF DfrapPerfArpTotalEntry
         ACCESS   not-accessible
         STATUS   mandatory
         DESCRIPTION
            "Short Term Statistics on the ARP
             protocol across all DLCIs."
         ::= { dfrapPerfNetworkShortTerm 16 }

         dfrapPerfArpTotalEntry OBJECT-TYPE
             SYNTAX   DfrapPerfArpTotalEntry
             ACCESS   not-accessible
             STATUS   mandatory
             DESCRIPTION
                "The ARP Short Term Statistics across all DLCIs."
             INDEX { dfrapPerfArpTotalInterval }
             ::= { dfrapPerfArpTotalTable 1 }

         DfrapPerfArpTotalEntry ::=
             SEQUENCE {
                 dfrapPerfArpTotalInterval        INTEGER,
                 dfrapPerfArpTotalRxTotal         Counter,
                 dfrapPerfArpTotalTxTotal         Counter,
                 dfrapPerfArpTotalRxArpReq        Counter,
                 dfrapPerfArpTotalTxArpReq        Counter,
                 dfrapPerfArpTotalRxArpRep        Counter,
                 dfrapPerfArpTotalTxArpRep        Counter,
                 dfrapPerfArpTotalRxRarpReq       Counter,
                 dfrapPerfArpTotalTxRarpReq       Counter,
                 dfrapPerfArpTotalRxRarpRep       Counter,
                 dfrapPerfArpTotalTxRarpRep       Counter,
                 dfrapPerfArpTotalRxInarpReq      Counter,
                 dfrapPerfArpTotalTxInarpReq      Counter,
                 dfrapPerfArpTotalRxInarpRep      Counter,
                 dfrapPerfArpTotalTxInarpRep      Counter,
                 dfrapPerfArpTotalRxOther         Counter,
                 dfrapPerfArpTotalTxOther         Counter
             }

      dfrapPerfArpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfArpTotalEntry 1 }

      dfrapPerfArpTotalRxTotal    OBJECT-TYPE
             SYNTAX      Counter
             ACCESS      read-only
             STATUS      mandatory
             DESCRIPTION
                "The total number of ARP bytes
                 that have been counted across all DLCIs."
            ::= { dfrapPerfArpTotalEntry 3 }

      dfrapPerfArpTotalTxTotal    OBJECT-TYPE
             SYNTAX      Counter
             ACCESS      read-only
             STATUS      mandatory
             DESCRIPTION
                "The total number of ARP bytes
                 that have been counted across all DLCIs."
            ::= { dfrapPerfArpTotalEntry 4 }

      dfrapPerfArpTotalRxArpReq    OBJECT-TYPE
             SYNTAX      Counter
             ACCESS      read-only
             STATUS      mandatory
             DESCRIPTION
                "The number of ARP request bytes
                 that have been counted across all DLCIs."
            ::= { dfrapPerfArpTotalEntry 5 }

      dfrapPerfArpTotalTxArpReq    OBJECT-TYPE
             SYNTAX      Counter
             ACCESS      read-only
             STATUS      mandatory
             DESCRIPTION
                "The number of ARP request bytes
                 that have been counted across all DLCIs."
            ::= { dfrapPerfArpTotalEntry 6 }

      dfrapPerfArpTotalRxArpRep    OBJECT-TYPE
             SYNTAX      Counter
             ACCESS      read-only
             STATUS      mandatory
             DESCRIPTION
                "The number of ARP reply bytes
                 that have been counted across all DLCIs."
            ::= { dfrapPerfArpTotalEntry 7 }

      dfrapPerfArpTotalTxArpRep    OBJECT-TYPE
             SYNTAX      Counter
             ACCESS      read-only
             STATUS      mandatory
             DESCRIPTION
                "The number of ARP reply bytes
                 that have been counted across all DLCIs."
            ::= { dfrapPerfArpTotalEntry 8 }

      dfrapPerfArpTotalRxRarpReq    OBJECT-TYPE
             SYNTAX      Counter
             ACCESS      read-only
             STATUS      mandatory
             DESCRIPTION
                "The number of RARP request bytes
                 that have been counted across all DLCIs."
            ::= { dfrapPerfArpTotalEntry 9 }

      dfrapPerfArpTotalTxRarpReq    OBJECT-TYPE
             SYNTAX      Counter
             ACCESS      read-only
             STATUS      mandatory
             DESCRIPTION
                "The number of RARP request bytes
                 that have been counted across all DLCIs."
            ::= { dfrapPerfArpTotalEntry 10 }

      dfrapPerfArpTotalRxRarpRep    OBJECT-TYPE
             SYNTAX      Counter
             ACCESS      read-only
             STATUS      mandatory
             DESCRIPTION
                "The number of RARP reply bytes
                 that have been counted across all DLCIs."
            ::= { dfrapPerfArpTotalEntry 11 }

      dfrapPerfArpTotalTxRarpRep    OBJECT-TYPE
             SYNTAX      Counter
             ACCESS      read-only
             STATUS      mandatory
             DESCRIPTION
                "The number of RARP reply bytes
                 that have been counted across all DLCIs."
            ::= { dfrapPerfArpTotalEntry 12 }

      dfrapPerfArpTotalRxInarpReq    OBJECT-TYPE
             SYNTAX      Counter
             ACCESS      read-only
             STATUS      mandatory
             DESCRIPTION
                "The number of INARP request bytes
                 that have been counted across all DLCIs."
            ::= { dfrapPerfArpTotalEntry 13 }

      dfrapPerfArpTotalTxInarpReq    OBJECT-TYPE
             SYNTAX      Counter
             ACCESS      read-only
             STATUS      mandatory
             DESCRIPTION
                "The number of INARP request bytes
                 that have been counted across all DLCIs."
            ::= { dfrapPerfArpTotalEntry 14 }

      dfrapPerfArpTotalRxInarpRep    OBJECT-TYPE
             SYNTAX      Counter
             ACCESS      read-only
             STATUS      mandatory
             DESCRIPTION
                "The number of INARP reply bytes
                 that have been counted across all DLCIs."
            ::= { dfrapPerfArpTotalEntry 15 }

      dfrapPerfArpTotalTxInarpRep    OBJECT-TYPE
             SYNTAX      Counter
             ACCESS      read-only
             STATUS      mandatory
             DESCRIPTION
                "The number of INARP reply bytes
                 that have been counted across all DLCIs."
            ::= { dfrapPerfArpTotalEntry 16 }

      dfrapPerfArpTotalRxOther    OBJECT-TYPE
             SYNTAX      Counter
             ACCESS      read-only
             STATUS      mandatory
             DESCRIPTION
                "The number of received bytes across all DLCIs
                 from ARP message types that are not counted
                 elsewhere in this table."
            ::= { dfrapPerfArpTotalEntry 17 }

      dfrapPerfArpTotalTxOther    OBJECT-TYPE
             SYNTAX      Counter
             ACCESS      read-only
             STATUS      mandatory
             DESCRIPTION
                "The number of transmitted bytes across all DLCIs
                 from ARP message types that are not counted
                 elsewhere in this table."
            ::= { dfrapPerfArpTotalEntry 18 }


   --  LMI Statistics for each DLCI.

   dfrapPerfLmiPerDlciTable OBJECT-TYPE
         SYNTAX   SEQUENCE OF  DfrapPerfLmiPerDlciEntry
         ACCESS   not-accessible
         STATUS   mandatory
         DESCRIPTION
            "Short Term Statistics on LMI protocol for each DLCI."
         ::= { dfrapPerfNetworkShortTerm  17 }

         dfrapPerfLmiPerDlciEntry OBJECT-TYPE
             SYNTAX   DfrapPerfLmiPerDlciEntry
             ACCESS   not-accessible
             STATUS   mandatory
             DESCRIPTION
                "The LMI Short Term Statistics for a particular DLCI."
             INDEX { dfrapPerfLmiPerDlciInterval, dfrapPerfLmiPerDlciValue }
             ::= { dfrapPerfLmiPerDlciTable 1 }

         DfrapPerfLmiPerDlciEntry ::=
             SEQUENCE {
                 dfrapPerfLmiPerDlciInterval            INTEGER,
                 dfrapPerfLmiPerDlciValue               INTEGER,
                 dfrapPerfLmiPerDlciRxTotalByteCnt      Counter,
                 dfrapPerfLmiPerDlciTxTotalByteCnt      Counter,
                 dfrapPerfLmiPerDlciRxLivoEnqByteCnt    Counter,
                 dfrapPerfLmiPerDlciTxLivoEnqByteCnt    Counter,
                 dfrapPerfLmiPerDlciRxLivoStatByteCnt   Counter,
                 dfrapPerfLmiPerDlciTxLivoStatByteCnt   Counter,
                 dfrapPerfLmiPerDlciRxFullEnqByteCnt    Counter,
                 dfrapPerfLmiPerDlciTxFullEnqByteCnt    Counter,
                 dfrapPerfLmiPerDlciRxFullStatByteCnt   Counter,
                 dfrapPerfLmiPerDlciTxFullStatByteCnt   Counter,
                 dfrapPerfLmiPerDlciRxOtherByteCnt      Counter,
                 dfrapPerfLmiPerDlciTxOtherByteCnt      Counter
             }

      dfrapPerfLmiPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfLmiPerDlciEntry 1 }

      dfrapPerfLmiPerDlciValue    OBJECT-TYPE
             SYNTAX      INTEGER 
             ACCESS      read-only
             STATUS      mandatory
             DESCRIPTION
                "The DLCI value with which the Statistics are associated."
            ::= { dfrapPerfLmiPerDlciEntry 2 }

      dfrapPerfLmiPerDlciRxTotalByteCnt    OBJECT-TYPE
             SYNTAX      Counter 
             ACCESS      read-only
             STATUS      mandatory
             DESCRIPTION
                "The total number of received LMI bytes
                 counted on this DLCI."
            ::= { dfrapPerfLmiPerDlciEntry 3 }

      dfrapPerfLmiPerDlciTxTotalByteCnt    OBJECT-TYPE
             SYNTAX      Counter 
             ACCESS      read-only
             STATUS      mandatory
             DESCRIPTION
                "The total number of transmitted LMI bytes
                 counted on this DLCI."
            ::= { dfrapPerfLmiPerDlciEntry 4 }

      dfrapPerfLmiPerDlciRxLivoEnqByteCnt    OBJECT-TYPE
             SYNTAX      Counter  
             ACCESS      read-only
             STATUS      mandatory
             DESCRIPTION
                "The number of bytes received in Link Integrity
                 Verification Only (LIVO) enquiries on this DLCI."
            ::= { dfrapPerfLmiPerDlciEntry 5 }

      dfrapPerfLmiPerDlciTxLivoEnqByteCnt    OBJECT-TYPE
             SYNTAX      Counter  
             ACCESS      read-only
             STATUS      mandatory
             DESCRIPTION
                "The number of bytes transmitted in Link Integrity
                 Verification Only (LIVO) enquiries on this DLCI."
            ::= { dfrapPerfLmiPerDlciEntry 6 }

      dfrapPerfLmiPerDlciRxLivoStatByteCnt    OBJECT-TYPE
             SYNTAX      Counter  
             ACCESS      read-only
             STATUS      mandatory
             DESCRIPTION
                "The number of bytes received in Link Integrity
                 Verification Only (LIVO) statuses on this DLCI."
            ::= { dfrapPerfLmiPerDlciEntry 7 }

      dfrapPerfLmiPerDlciTxLivoStatByteCnt    OBJECT-TYPE
             SYNTAX      Counter  
             ACCESS      read-only
             STATUS      mandatory
             DESCRIPTION
                "The number of bytes transmitted in Link Integrity
                 Verification Only (LIVO) statuses on this DLCI."
            ::= { dfrapPerfLmiPerDlciEntry 8 }

      dfrapPerfLmiPerDlciRxFullEnqByteCnt    OBJECT-TYPE
             SYNTAX      Counter  
             ACCESS      read-only
             STATUS      mandatory
             DESCRIPTION
                "The number of bytes received in 
                 Full Status enquiries on this DLCI."
            ::= { dfrapPerfLmiPerDlciEntry 9 }

      dfrapPerfLmiPerDlciTxFullEnqByteCnt    OBJECT-TYPE
             SYNTAX      Counter  
             ACCESS      read-only
             STATUS      mandatory
             DESCRIPTION
                "The number of bytes transmitted in 
                 Full Status enquiries on this DLCI."
            ::= { dfrapPerfLmiPerDlciEntry 10 }

      dfrapPerfLmiPerDlciRxFullStatByteCnt    OBJECT-TYPE
             SYNTAX      Counter  
             ACCESS      read-only
             STATUS      mandatory
             DESCRIPTION
                "The number of bytes received in 
                 Full Status messages on this DLCI."
            ::= { dfrapPerfLmiPerDlciEntry 11 }

      dfrapPerfLmiPerDlciTxFullStatByteCnt    OBJECT-TYPE
             SYNTAX      Counter  
             ACCESS      read-only
             STATUS      mandatory
             DESCRIPTION
                "The number of bytes transmitted in 
                 Full Status messages on this DLCI."
            ::= { dfrapPerfLmiPerDlciEntry 12 }

      dfrapPerfLmiPerDlciRxOtherByteCnt    OBJECT-TYPE
             SYNTAX      Counter  
             ACCESS      read-only
             STATUS      mandatory
             DESCRIPTION
                "The number of received bytes on this DLCI
                 from LMI protocols that are not counted
                 elsewhere (other than Total) in this table."
            ::= { dfrapPerfLmiPerDlciEntry 13 }

      dfrapPerfLmiPerDlciTxOtherByteCnt    OBJECT-TYPE
             SYNTAX      Counter  
             ACCESS      read-only
             STATUS      mandatory
             DESCRIPTION
                "The number of transmitted bytes on this DLCI
                 from LMI protocols that are not counted
                 elsewhere (other than Total) in this table."
            ::= { dfrapPerfLmiPerDlciEntry 14 }


   --  LMI Statistics for totals.

   dfrapPerfLmiTotalTable OBJECT-TYPE
         SYNTAX   SEQUENCE OF DfrapPerfLmiTotalEntry
         ACCESS   not-accessible
         STATUS   mandatory
         DESCRIPTION
            "Short Term Statistics on LMI protocol across all DLCIs."
         ::= { dfrapPerfNetworkShortTerm 18 }

         dfrapPerfLmiTotalEntry OBJECT-TYPE
             SYNTAX   DfrapPerfLmiTotalEntry
             ACCESS   not-accessible
             STATUS   mandatory
             DESCRIPTION
                "The LMI Short Term Statistics across all DLCIs."
             INDEX { dfrapPerfLmiTotalInterval }
             ::= { dfrapPerfLmiTotalTable 1 }

         DfrapPerfLmiTotalEntry ::=
             SEQUENCE {
                 dfrapPerfLmiTotalInterval            INTEGER,
                 dfrapPerfLmiTotalDlciValue           INTEGER,
                 dfrapPerfLmiTotalRxTotalByteCnt      Counter,
                 dfrapPerfLmiTotalTxTotalByteCnt      Counter,
                 dfrapPerfLmiTotalRxLivoEnqByteCnt    Counter,
                 dfrapPerfLmiTotalTxLivoEnqByteCnt    Counter,
                 dfrapPerfLmiTotalRxLivoStatByteCnt   Counter,
                 dfrapPerfLmiTotalTxLivoStatByteCnt   Counter,
                 dfrapPerfLmiTotalRxFullEnqByteCnt    Counter,
                 dfrapPerfLmiTotalTxFullEnqByteCnt    Counter,
                 dfrapPerfLmiTotalRxFullStatByteCnt   Counter,
                 dfrapPerfLmiTotalTxFullStatByteCnt   Counter,
                 dfrapPerfLmiTotalRxOtherByteCnt      Counter,
                 dfrapPerfLmiTotalTxOtherByteCnt      Counter
             }

      dfrapPerfLmiTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfLmiTotalEntry 1 }

      dfrapPerfLmiTotalDlciValue    OBJECT-TYPE
             SYNTAX      INTEGER 
             ACCESS      read-only
             STATUS      mandatory
             DESCRIPTION
                "OBSOLETE."
            ::= { dfrapPerfLmiTotalEntry 2 }

      dfrapPerfLmiTotalRxTotalByteCnt    OBJECT-TYPE
             SYNTAX      Counter  
             ACCESS      read-only
             STATUS      mandatory
             DESCRIPTION
                "The total number of received LMI bytes
                 counted on this DLCI."
            ::= { dfrapPerfLmiTotalEntry 3 }

      dfrapPerfLmiTotalTxTotalByteCnt    OBJECT-TYPE
             SYNTAX      Counter  
             ACCESS      read-only
             STATUS      mandatory
             DESCRIPTION
                "The total number of transmitted LMI bytes
                 counted on this DLCI."
            ::= { dfrapPerfLmiTotalEntry 4 }

      dfrapPerfLmiTotalRxLivoEnqByteCnt    OBJECT-TYPE
             SYNTAX      Counter  
             ACCESS      read-only
             STATUS      mandatory
             DESCRIPTION
                "The number of bytes received in Link Integrity
                 Verification Only (LIVO) enquiries on this DLCI."
            ::= { dfrapPerfLmiTotalEntry 5 }

      dfrapPerfLmiTotalTxLivoEnqByteCnt    OBJECT-TYPE
             SYNTAX      Counter  
             ACCESS      read-only
             STATUS      mandatory
             DESCRIPTION
                "The number of bytes transmitted in Link Integrity
                 Verification Only (LIVO) enquiries on this DLCI."
            ::= { dfrapPerfLmiTotalEntry 6 }

      dfrapPerfLmiTotalRxLivoStatByteCnt    OBJECT-TYPE
             SYNTAX      Counter  
             ACCESS      read-only
             STATUS      mandatory
             DESCRIPTION
                "The number of bytes received in Link Integrity
                 Verification Only (LIVO) statuses on this DLCI."
            ::= { dfrapPerfLmiTotalEntry 7 }

      dfrapPerfLmiTotalTxLivoStatByteCnt    OBJECT-TYPE
             SYNTAX      Counter  
             ACCESS      read-only
             STATUS      mandatory
             DESCRIPTION
                "The number of bytes transmitted in Link Integrity
                 Verification Only (LIVO) statuses on this DLCI."
            ::= { dfrapPerfLmiTotalEntry 8 }

      dfrapPerfLmiTotalRxFullEnqByteCnt    OBJECT-TYPE
             SYNTAX      Counter  
             ACCESS      read-only
             STATUS      mandatory
             DESCRIPTION
                "The number of bytes received in 
                 Full Status enquiries on this DLCI."
            ::= { dfrapPerfLmiTotalEntry 9 }

      dfrapPerfLmiTotalTxFullEnqByteCnt    OBJECT-TYPE
             SYNTAX      Counter  
             ACCESS      read-only
             STATUS      mandatory
             DESCRIPTION
                "The number of bytes transmitted in 
                 Full Status enquiries on this DLCI."
            ::= { dfrapPerfLmiTotalEntry 10 }

      dfrapPerfLmiTotalRxFullStatByteCnt    OBJECT-TYPE
             SYNTAX      Counter  
             ACCESS      read-only
             STATUS      mandatory
             DESCRIPTION
                "The number of bytes received in 
                 Full Status messages on this DLCI."
            ::= { dfrapPerfLmiTotalEntry 11 }

      dfrapPerfLmiTotalTxFullStatByteCnt    OBJECT-TYPE
             SYNTAX      Counter  
             ACCESS      read-only
             STATUS      mandatory
             DESCRIPTION
                "The number of bytes transmitted in 
                 Full Status messages on this DLCI."
            ::= { dfrapPerfLmiTotalEntry 12 }

      dfrapPerfLmiTotalRxOtherByteCnt    OBJECT-TYPE
             SYNTAX      Counter  
             ACCESS      read-only
             STATUS      mandatory
             DESCRIPTION
                "The number of received bytes on this DLCI
                 from LMI protocols that are not counted
                 elsewhere (other than Total) in this table."
            ::= { dfrapPerfLmiTotalEntry 13 }

      dfrapPerfLmiTotalTxOtherByteCnt   OBJECT-TYPE
             SYNTAX      Counter  
             ACCESS      read-only
             STATUS      mandatory
             DESCRIPTION
                "The number of transmitted bytes on this DLCI
                 from LMI protocols that are not counted
                 elsewhere (other than Total) in this table."
            ::= { dfrapPerfLmiTotalEntry 14 }



dfrapPerfNetworkLongTerm OBJECT IDENTIFIER ::= { dfrapPerformance 5 }

--
--       Long Term Statistics by DLCI, protocol, and interval.
--

   dfrapPerfNetwLongTermTable OBJECT-TYPE
         SYNTAX   SEQUENCE OF DfrapPerfNetwLongTermEntry
         ACCESS   not-accessible
         STATUS   mandatory
         DESCRIPTION
            "Long Term Statistics by DLCI, protocol, and interval.
             LT statistics are collected on a configurable set
             of DLCIs and protocols. There are 96 intervals maintained
             each with a duration defined by the Long Term Timer. 
             Interval 96 is the current window and Interval 1 is 
             furthest back in time (96xLT Timer seconds ago).
             (CfgFrPerfTimersLTInterval)."
         ::= { dfrapPerfNetworkLongTerm 1 }

         dfrapPerfNetwLongTermEntry OBJECT-TYPE
             SYNTAX   DfrapPerfNetwLongTermEntry
             ACCESS   not-accessible
             STATUS   mandatory
             DESCRIPTION
                "The Long Term Statistic for a particular DLCI,
                 protocol and interval."
             INDEX { dfrapPerfNetwLongTermDlci,
                     dfrapPerfNetwLongTermProtocol,
                     dfrapPerfNetwLongTermInterval }
            ::= { dfrapPerfNetwLongTermTable 1 }

         DfrapPerfNetwLongTermEntry ::=
             SEQUENCE {
                 dfrapPerfNetwLongTermDlci      INTEGER,
                 dfrapPerfNetwLongTermProtocol  INTEGER,
                 dfrapPerfNetwLongTermInterval  INTEGER,
                 dfrapPerfNetwLongTermValue     Counter
             }

         dfrapPerfNetwLongTermDlci    OBJECT-TYPE
             SYNTAX      INTEGER 
             ACCESS      read-only
             STATUS      mandatory
             DESCRIPTION
               "The DLCI monitored for the statistics. The Long
                Term DLCI filter must first be configured 
                (CfgFrPerfLTDlciFilterEntry)."
            ::= { dfrapPerfNetwLongTermEntry 1 }

         dfrapPerfNetwLongTermProtocol    OBJECT-TYPE
            SYNTAX      INTEGER
            {
               ip-tx-bc                    (1),
               ip-rx-bc                    (2),
               tcp-ip-tx-bc                (3),
               tcp-ip-rx-bc                (4),
               ftp-tcp-ip-tx-bc            (5),
               ftp-tcp-ip-rx-bc            (6),
               telnet-tcp-ip-tx-bc         (7),
               telnet-tcp-ip-rx-bc         (8),
               smtp-tcp-ip-tx-bc           (9),
               smtp-tcp-ip-rx-bc           (10),
--             tftp-tcp-ip-tx-bc           (11),
--             tftp-tcp-ip-rx-bc           (12),
               http-tcp-ip-tx-bc           (13),
               http-tcp-ip-rx-bc           (14),
               netbios-ssn-tcp-ip-tx-bc    (15),
               netbios-ssn-tcp-ip-rx-bc    (16),
--             snmp-tcp-ip-tx-bc           (17),
--             snmp-tcp-ip-rx-bc           (18),
--             snmptrap-tcp-ip-tx-bc       (19),
--             snmptrap-tcp-ip-rx-bc       (20),
               udp-ip-tx-bc                (21),
               udp-ip-rx-bc                (22),
--             ftp-udp-ip-tx-bc            (23),
--             ftp-udp-ip-rx-bc            (24),
--             telnet-udp-ip-tx-bc         (25),
--             telnet-udp-ip-rx-bc         (26),
--             smtp-udp-ip-tx-bc           (27),
--             smtp-udp-ip-rx-bc           (28),
               tftp-udp-ip-tx-bc           (29),
               tftp-udp-ip-rx-bc           (30),
--             http-udp-ip-tx-bc           (31),
--             http-udp-ip-rx-bc           (32),
               netbios-dgm-udp-ip-tx-bc    (33),
               netbios-dgm-udp-ip-rx-bc    (34),
               snmp-udp-ip-tx-bc           (35),
               snmp-udp-ip-rx-bc           (36),
               snmptrap-udp-ip-tx-bc       (37),
               snmptrap-udp-ip-rx-bc       (38),
               rip-udp-ip-tx-bc            (39),
               rip-udp-ip-rx-bc            (40),
               icmp-ip-tx-bc               (41),
               icmp-ip-rx-bc               (42),
               echorep-icmp-ip-tx-bc       (43),
               echorep-icmp-ip-rx-bc       (44),
               dest-unr-icmp-ip-tx-bc      (45),
               dest-unr-icmp-ip-rx-bc      (46),
               src-quench-icmp-ip-tx-bc    (47),
               src-quench-icmp-ip-rx-bc    (48),
               redirect-icmp-ip-tx-bc      (49),
               redirect-icmp-ip-rx-bc      (50),
               echoreq-icmp-ip-tx-bc       (51),
               echoreq-icmp-ip-rx-bc       (52),
               time-excd-icmp-ip-tx-bc     (53),
               time-excd-icmp-ip-rx-bc     (54),
               param-prob-icmp-ip-tx-bc    (55),
               param-prob-icmp-ip-rx-bc    (56),
               timestamp-req-icmp-ip-tx-bc (57),
               timestamp-req-icmp-ip-rx-bc (58),
               timestamp-rep-icmp-ip-tx-bc (59),
               timestamp-rep-icmp-ip-rx-bc (60),
               addr-mask-req-icmp-ip-tx-bc (61),
               addr-mask-req-icmp-ip-rx-bc (62),
               addr-mask-rep-icmp-ip-tx-bc (63),
               addr-mask-rep-icmp-ip-rx-bc (64),
               pkt-too-big-icmp-ip-tx-bc   (65),
               pkt-too-big-icmp-ip-rx-bc   (66),
               gp-mem-query-icmp-ip-tx-bc  (67),
               gp-mem-query-icmp-ip-rx-bc  (68),
               gp-mem-report-icmp-ip-tx-bc (69),
               gp-mem-report-icmp-ip-rx-bc (70),
               gp-mem-reduct-icmp-ip-tx-bc (71),
               gp-mem-reduct-icmp-ip-rx-bc (72),
               ospf-ip-tx-bc               (73),
               ospf-ip-rx-bc               (74),
               other-ip-tx-bc              (75),
               other-ip-rx-bc              (76),
               ipx-tx-bc                   (77),
               ipx-rx-bc                   (78),
               spx-ipx-tx-bc               (79),
               spx-ipx-rx-bc               (80),
               ncp-ipx-tx-bc               (81),
               ncp-ipx-rx-bc               (82),
               sap-ipx-tx-bc               (83),
               sap-ipx-rx-bc               (84),
               rip-ipx-tx-bc               (85),
               rip-ipx-rx-bc               (86),
               netbios-ipx-tx-bc           (87),
               netbios-ipx-rx-bc           (88),
               other-ipx-tx-bc             (89),
               other-ipx-rx-bc             (90),
               arp-tx-bc                   (91),
               arp-rx-bc                   (92),
               arp-req-tx-bc               (93),
               arp-req-rx-bc               (94),
               arp-rep-tx-bc               (95),
               arp-rep-rx-bc               (96),
               rarp-req-tx-bc              (97),
               rarp-req-rx-bc              (98),
               rarp-rep-tx-bc              (99),
               rarp-rep-rx-bc              (100),
               inarp-req-tx-bc             (101),
               inarp-req-rx-bc             (102),
               inarp-rep-tx-bc             (103),
               inarp-rep-rx-bc             (104),
               sna-tx-bc                   (105),
               sna-rx-bc                   (106),
               sna-subarea-tx-bc           (107),
               sna-subarea-rx-bc           (108),
               sna-periph-tx-bc            (109),
               sna-periph-rx-bc            (110),
               sna-appn-tx-bc              (111),
               sna-appn-rx-bc              (112),
               sna-netbios-tx-bc           (113),
               sna-netbios-rx-bc           (114),
               cisco-tx-bc                 (115),
               cisco-rx-bc                 (116),
               other-tx-bc                 (117),
               other-rx-bc                 (118),
               user-defined-1-tx-bc        (119),
               user-defined-1-rx-bc        (120),
               user-defined-2-tx-bc        (121),
               user-defined-2-rx-bc        (122),
               user-defined-3-tx-bc        (123),
               user-defined-3-rx-bc        (124),
               user-defined-4-tx-bc        (125),
               user-defined-4-rx-bc        (126),
               thru-byte-tx-bc             (127),
               thru-byte-rx-bc             (128),
               thru-frame-tx-c             (129),
               thru-frame-rx-c             (130),
               thru-fecn-tx-c              (131),
               thru-fecn-rx-c              (132),
               thru-becn-tx-c              (133),
               thru-becn-rx-c              (134),
               thru-de-tx-c                (135),
               thru-de-rx-c                (136),
               cir-percent-range1-tx-bc    (137),
               cir-percent-range1-rx-bc    (138),
               cir-percent-range2-tx-bc    (139),
               cir-percent-range2-rx-bc    (140),
               cir-percent-range3-tx-bc    (141),
               cir-percent-range3-rx-bc    (142),
               cir-percent-range4-tx-bc    (143),
               cir-percent-range4-rx-bc    (144),
               cir-percent-range5-tx-bc    (145),
               cir-percent-range5-rx-bc    (146),
               cir-percent-range6-tx-bc    (147),
               cir-percent-range6-rx-bc    (148),
               cir-percent-range7-tx-bc    (149),
               cir-percent-range7-rx-bc    (150),
               cir-percent-range8-tx-bc    (151),
               cir-percent-range8-rx-bc    (152),
               lmi-tx-bc                   (153),
               lmi-rx-bc                   (154),
               lmi-livo-enq-tx-bc          (155),
               lmi-livo-enq-rx-bc          (156),
               lmi-livo-stat-tx-bc         (157),
               lmi-livo-stat-rx-bc         (158),
               lmi-full-enq-tx-bc          (159),
               lmi-full-enq-rx-bc          (160),
               lmi-full-stat-tx-bc         (161),
               lmi-full-stat-rx-bc         (162),
               lmi-other-tx-bc             (163),
               lmi-other-rx-bc             (164),
               total-uptime                (165),
               total-downtime              (166),
               igrp-tx-bc                  (167),
               igrp-rx-bc                  (168),
               vnip-tx-bc                  (169),
               vnip-rx-bc                  (170),
               annex-g-tx-bc               (171),
               annex-g-rx-bc               (172)
            }
            ACCESS      read-only
            STATUS      mandatory
            DESCRIPTION
             "The type of protocol monitored for the statistics."
            ::= { dfrapPerfNetwLongTermEntry 2 }

         dfrapPerfNetwLongTermInterval    OBJECT-TYPE
             SYNTAX      INTEGER 
             ACCESS      read-only
             STATUS      mandatory
             DESCRIPTION
                "The time interval in which the value was collected.
                 Long Term statistis are maintained for 96 intervals 
                 with the interval duration defined by 
                 (CfgFrPerfTimersLTInterval)."
            ::= { dfrapPerfNetwLongTermEntry 3 }

         dfrapPerfNetwLongTermValue    OBJECT-TYPE
             SYNTAX      Counter
             ACCESS      read-only
             STATUS      mandatory
             DESCRIPTION
                "The statistic collected for the given DLCI and protocol
                 and within the given time interval."
            ::= { dfrapPerfNetwLongTermEntry 4 }


--
--       Long Term Statistics by DLCI: alternative method.
--

   dfrapPerfNetwLongTermAltTable OBJECT-TYPE
         SYNTAX   SEQUENCE OF DfrapPerfNetwLongTermAltEntry
         ACCESS   not-accessible
         STATUS   mandatory
         DESCRIPTION
            "This is an alternative method to access the database of
             long term statistics.  The statistics are indexed by DLCI
             and protocol and are returned in an OCTETSTRING."
         ::= { dfrapPerfNetworkLongTerm 2 }

         dfrapPerfNetwLongTermAltEntry   OBJECT-TYPE
             SYNTAX   DfrapPerfNetwLongTermAltEntry
             ACCESS   not-accessible
             STATUS   mandatory
             DESCRIPTION
                "The Long Term Statistic for a particular
                 DLCI and protocol."
             INDEX { dfrapPerfNetwLongTermAltDlci,
                     dfrapPerfNetwLongTermAltProtocol }
             ::= { dfrapPerfNetwLongTermAltTable 1 }

         DfrapPerfNetwLongTermAltEntry ::=
             SEQUENCE {
                 dfrapPerfNetwLongTermAltDlci      INTEGER,
                 dfrapPerfNetwLongTermAltProtocol  INTEGER,
                 dfrapPerfNetwLongTermAltArray     OCTET STRING
             }

         dfrapPerfNetwLongTermAltDlci    OBJECT-TYPE
             SYNTAX      INTEGER 
             ACCESS      read-only
             STATUS      mandatory
             DESCRIPTION
               "The DLCI monitored for the statistics."
            ::= { dfrapPerfNetwLongTermAltEntry 1 }

         dfrapPerfNetwLongTermAltProtocol   OBJECT-TYPE
             SYNTAX      INTEGER 
             {
                  ip-tx-bc                    (1),
                  ip-rx-bc                    (2),
                  tcp-ip-tx-bc                (3),
                  tcp-ip-rx-bc                (4),
                  ftp-tcp-ip-tx-bc            (5),
                  ftp-tcp-ip-rx-bc            (6),
                  telnet-tcp-ip-tx-bc         (7),
                  telnet-tcp-ip-rx-bc         (8),
                  smtp-tcp-ip-tx-bc           (9),
                  smtp-tcp-ip-rx-bc           (10),
--                tftp-tcp-ip-tx-bc           (11),
--                tftp-tcp-ip-rx-bc           (12),
                  http-tcp-ip-tx-bc           (13),
                  http-tcp-ip-rx-bc           (14),
                  netbios-ssn-tcp-ip-tx-bc    (15),
                  netbios-ssn-tcp-ip-rx-bc    (16),
--                snmp-tcp-ip-tx-bc           (17),
--                snmp-tcp-ip-rx-bc           (18),
--                snmptrap-tcp-ip-tx-bc       (19),
--                snmptrap-tcp-ip-rx-bc       (20),
                  udp-ip-tx-bc                (21),
                  udp-ip-rx-bc                (22),
--                ftp-udp-ip-tx-bc            (23),
--                ftp-udp-ip-rx-bc            (24),
--                telnet-udp-ip-tx-bc         (25),
--                telnet-udp-ip-rx-bc         (26),
--                smtp-udp-ip-tx-bc           (27),
--                smtp-udp-ip-rx-bc           (28),
                  tftp-udp-ip-tx-bc           (29),
                  tftp-udp-ip-rx-bc           (30),
--                http-udp-ip-tx-bc           (31),
--                http-udp-ip-rx-bc           (32),
                  netbios-dgm-udp-ip-tx-bc    (33),
                  netbios-dgm-udp-ip-rx-bc    (34),
                  snmp-udp-ip-tx-bc           (35),
                  snmp-udp-ip-rx-bc           (36),
                  snmptrap-udp-ip-tx-bc       (37),
                  snmptrap-udp-ip-rx-bc       (38),
                  rip-udp-ip-tx-bc            (39),
                  rip-udp-ip-rx-bc            (40),
                  icmp-ip-tx-bc               (41),
                  icmp-ip-rx-bc               (42),
                  echorep-icmp-ip-tx-bc       (43),
                  echorep-icmp-ip-rx-bc       (44),
                  dest-unr-icmp-ip-tx-bc      (45),
                  dest-unr-icmp-ip-rx-bc      (46),
                  src-quench-icmp-ip-tx-bc    (47),
                  src-quench-icmp-ip-rx-bc    (48),
                  redirect-icmp-ip-tx-bc      (49),
                  redirect-icmp-ip-rx-bc      (50),
                  echoreq-icmp-ip-tx-bc       (51),
                  echoreq-icmp-ip-rx-bc       (52),
                  time-excd-icmp-ip-tx-bc     (53),
                  time-excd-icmp-ip-rx-bc     (54),
                  param-prob-icmp-ip-tx-bc    (55),
                  param-prob-icmp-ip-rx-bc    (56),
                  timestamp-req-icmp-ip-tx-bc (57),
                  timestamp-req-icmp-ip-rx-bc (58),
                  timestamp-rep-icmp-ip-tx-bc (59),
                  timestamp-rep-icmp-ip-rx-bc (60),
                  addr-mask-req-icmp-ip-tx-bc (61),
                  addr-mask-req-icmp-ip-rx-bc (62),
                  addr-mask-rep-icmp-ip-tx-bc (63),
                  addr-mask-rep-icmp-ip-rx-bc (64),
                  pkt-too-big-icmp-ip-tx-bc   (65),
                  pkt-too-big-icmp-ip-rx-bc   (66),
                  gp-mem-query-icmp-ip-tx-bc  (67),
                  gp-mem-query-icmp-ip-rx-bc  (68),
                  gp-mem-report-icmp-ip-tx-bc (69),
                  gp-mem-report-icmp-ip-rx-bc (70),
                  gp-mem-reduct-icmp-ip-tx-bc (71),
                  gp-mem-reduct-icmp-ip-rx-bc (72),
                  ospf-ip-tx-bc               (73),
                  ospf-ip-rx-bc               (74),
                  other-ip-tx-bc              (75),
                  other-ip-rx-bc              (76),
                  ipx-tx-bc                   (77),
                  ipx-rx-bc                   (78),
                  spx-ipx-tx-bc               (79),
                  spx-ipx-rx-bc               (80),
                  ncp-ipx-tx-bc               (81),
                  ncp-ipx-rx-bc               (82),
                  sap-ipx-tx-bc               (83),
                  sap-ipx-rx-bc               (84),
                  rip-ipx-tx-bc               (85),
                  rip-ipx-rx-bc               (86),
                  netbios-ipx-tx-bc           (87),
                  netbios-ipx-rx-bc           (88),
                  other-ipx-tx-bc             (89),
                  other-ipx-rx-bc             (90),
                  arp-tx-bc                   (91),
                  arp-rx-bc                   (92),
                  arp-req-tx-bc               (93),
                  arp-req-rx-bc               (94),
                  arp-rep-tx-bc               (95),
                  arp-rep-rx-bc               (96),
                  rarp-req-tx-bc              (97),
                  rarp-req-rx-bc              (98),
                  rarp-rep-tx-bc              (99),
                  rarp-rep-rx-bc              (100),
                  inarp-req-tx-bc             (101),
                  inarp-req-rx-bc             (102),
                  inarp-rep-tx-bc             (103),
                  inarp-rep-rx-bc             (104),
                  sna-tx-bc                   (105),
                  sna-rx-bc                   (106),
                  sna-subarea-tx-bc           (107),
                  sna-subarea-rx-bc           (108),
                  sna-periph-tx-bc            (109),
                  sna-periph-rx-bc            (110),
                  sna-appn-tx-bc              (111),
                  sna-appn-rx-bc              (112),
                  sna-netbios-tx-bc           (113),
                  sna-netbios-rx-bc           (114),
                  cisco-tx-bc                 (115),
                  cisco-rx-bc                 (116),
                  other-tx-bc                 (117),
                  other-rx-bc                 (118),
                  user-defined-1-tx-bc        (119),
                  user-defined-1-rx-bc        (120),
                  user-defined-2-tx-bc        (121),
                  user-defined-2-rx-bc        (122),
                  user-defined-3-tx-bc        (123),
                  user-defined-3-rx-bc        (124),
                  user-defined-4-tx-bc        (125),
                  user-defined-4-rx-bc        (126),
                  thru-byte-tx-bc             (127),
                  thru-byte-rx-bc             (128),
                  thru-frame-tx-c             (129),
                  thru-frame-rx-c             (130),
                  thru-fecn-tx-c              (131),
                  thru-fecn-rx-c              (132),
                  thru-becn-tx-c              (133),
                  thru-becn-rx-c              (134),
                  thru-de-tx-c                (135),
                  thru-de-rx-c                (136),
                  cir-percent-range1-tx-bc    (137),
                  cir-percent-range1-rx-bc    (138),
                  cir-percent-range2-tx-bc    (139),
                  cir-percent-range2-rx-bc    (140),
                  cir-percent-range3-tx-bc    (141),
                  cir-percent-range3-rx-bc    (142),
                  cir-percent-range4-tx-bc    (143),
                  cir-percent-range4-rx-bc    (144),
                  cir-percent-range5-tx-bc    (145),
                  cir-percent-range5-rx-bc    (146),
                  cir-percent-range6-tx-bc    (147),
                  cir-percent-range6-rx-bc    (148),
                  cir-percent-range7-tx-bc    (149),
                  cir-percent-range7-rx-bc    (150),
                  cir-percent-range8-tx-bc    (151),
                  cir-percent-range8-rx-bc    (152),
                  lmi-tx-bc                   (153),
                  lmi-rx-bc                   (154),
                  lmi-livo-enq-tx-bc          (155),
                  lmi-livo-enq-rx-bc          (156),
                  lmi-livo-stat-tx-bc         (157),
                  lmi-livo-stat-rx-bc         (158),
                  lmi-full-enq-tx-bc          (159),
                  lmi-full-enq-rx-bc          (160),
                  lmi-full-stat-tx-bc         (161),
                  lmi-full-stat-rx-bc         (162),
                  lmi-other-tx-bc             (163),
                  lmi-other-rx-bc             (164),
                  total-uptime                (165),
                  total-downtime              (166),
                  igrp-tx-bc                  (167),
                  igrp-rx-bc                  (168),
                  vnip-tx-bc                  (169),
                  vnip-rx-bc                  (170),
                  annex-g-tx-bc               (171),
                  annex-g-rx-bc               (172)
             }
             ACCESS      read-only
             STATUS      mandatory
             DESCRIPTION
               "The protocol monitored for the statistics."
            ::= { dfrapPerfNetwLongTermAltEntry 2 }
      
         dfrapPerfNetwLongTermAltArray    OBJECT-TYPE
             SYNTAX      OCTET STRING
             ACCESS      read-only
             STATUS      mandatory
             DESCRIPTION
                "The statistic collected for the given DLCI and protocol."
            ::= { dfrapPerfNetwLongTermAltEntry 3 }


   dfrapPerfNetworkLongTermCommands OBJECT IDENTIFIER
            ::= { dfrapPerfNetworkLongTerm 3 }

   dfrapPerfNetworkLongTermCmdClear    OBJECT-TYPE
          SYNTAX      INTEGER
          {
              clear-statistics (1)
          }
          ACCESS      write-only
          STATUS      mandatory
          DESCRIPTION
             "Allows the user to zero out all the statistics in
              the long term statistics tables.
              (1) Clear all Long Term statistics"
          ::= { dfrapPerfNetworkLongTermCommands 1 }


dfrapPerfCirPercentUtilization OBJECT IDENTIFIER ::= { dfrapPerformance 6 }

--
--  CIR Percentage Statistics for each DLCI.
--

 dfrapPerfCirPercentUtilizationTable OBJECT-TYPE
         SYNTAX   SEQUENCE OF DfrapPerfCirPercentUtilizationEntry
         ACCESS   not-accessible
         STATUS   mandatory
         DESCRIPTION
            "Short Term Statistics on the percentage of CIR used
             on each DLCI.  Each short term statistics interval,
             the count of bytes transmitted and received is used
             to calculate the percentage of CIR used.  The byte
             count is then added to the appropriate bucket for
             the CIR percentage range."
         ::= { dfrapPerfCirPercentUtilization 1 }

 dfrapPerfCirPercentUtilizationEntry OBJECT-TYPE
             SYNTAX DfrapPerfCirPercentUtilizationEntry
             ACCESS   not-accessible
             STATUS   mandatory
             DESCRIPTION
                "The CIR Percentage Statistics for a particular DLCI.
                 These calculations are done at the completion of each 
                 Short Term interval."
             INDEX { dfrapPerfCirPercentUtilizationInterval,
                     dfrapPerfCirPercentUtilizationDlciValue }
             ::= { dfrapPerfCirPercentUtilizationTable 1 }

         DfrapPerfCirPercentUtilizationEntry ::=
             SEQUENCE {
                 dfrapPerfCirPercentUtilizationInterval    INTEGER,
                 dfrapPerfCirPercentUtilizationDlciValue   INTEGER,
                 dfrapPerfCirRxPercentUtilizationRange1    INTEGER,
                 dfrapPerfCirRxPercentUtilizationRange2    INTEGER,
                 dfrapPerfCirRxPercentUtilizationRange3    INTEGER,
                 dfrapPerfCirRxPercentUtilizationRange4    INTEGER,
                 dfrapPerfCirRxPercentUtilizationRange5    INTEGER,
                 dfrapPerfCirRxPercentUtilizationRange6    INTEGER,
                 dfrapPerfCirRxPercentUtilizationRange7    INTEGER,
                 dfrapPerfCirRxPercentUtilizationRange8    INTEGER,
                 dfrapPerfCirTxPercentUtilizationRange1    INTEGER,
                 dfrapPerfCirTxPercentUtilizationRange2    INTEGER,
                 dfrapPerfCirTxPercentUtilizationRange3    INTEGER,
                 dfrapPerfCirTxPercentUtilizationRange4    INTEGER,
                 dfrapPerfCirTxPercentUtilizationRange5    INTEGER,
                 dfrapPerfCirTxPercentUtilizationRange6    INTEGER,
                 dfrapPerfCirTxPercentUtilizationRange7    INTEGER,
                 dfrapPerfCirTxPercentUtilizationRange8    INTEGER
            }

 dfrapPerfCirPercentUtilizationInterval OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { dfrapPerfCirPercentUtilizationEntry 1 }

 dfrapPerfCirPercentUtilizationDlciValue OBJECT-TYPE
             SYNTAX      INTEGER 
             ACCESS      read-only
             STATUS      mandatory
             DESCRIPTION
                "The DLCI value with which the Statistics are associated."
            ::= { dfrapPerfCirPercentUtilizationEntry 2 }

 dfrapPerfCirRxPercentUtilizationRange1 OBJECT-TYPE
             SYNTAX      INTEGER 
             ACCESS      read-only
             STATUS      mandatory
             DESCRIPTION
                "The number of received bytes counted on this DLCI
                 during intervals where the percentage of
                 CIR was in range 1 (0% of CIR)."
            ::= { dfrapPerfCirPercentUtilizationEntry 21 }

 dfrapPerfCirRxPercentUtilizationRange2 OBJECT-TYPE
             SYNTAX      INTEGER 
             ACCESS      read-only
             STATUS      mandatory
             DESCRIPTION
                "The number of received bytes counted on this DLCI
                 during intervals where the percentage of
                 CIR was in range 2 (1-10% of CIR)."
            ::= { dfrapPerfCirPercentUtilizationEntry 22 }

 dfrapPerfCirRxPercentUtilizationRange3 OBJECT-TYPE
             SYNTAX      INTEGER 
             ACCESS      read-only
             STATUS      mandatory
             DESCRIPTION
                "The number of received bytes counted on this DLCI
                 during intervals where the percentage of
                 CIR was in range 3 (11-20% of CIR)."
            ::= { dfrapPerfCirPercentUtilizationEntry 23 }

 dfrapPerfCirRxPercentUtilizationRange4 OBJECT-TYPE
             SYNTAX      INTEGER 
             ACCESS      read-only
             STATUS      mandatory
             DESCRIPTION
                "The number of received bytes counted on this DLCI
                 during intervals where the percentage of
                 CIR was in range 4 (21-50% of CIR)."
            ::= { dfrapPerfCirPercentUtilizationEntry 24 }

 dfrapPerfCirRxPercentUtilizationRange5 OBJECT-TYPE
             SYNTAX      INTEGER 
             ACCESS      read-only
             STATUS      mandatory
             DESCRIPTION
                "The number of received bytes counted on this DLCI
                 during intervals where the percentage of
                 CIR was in range 5 (51-80% of CIR)."
            ::= { dfrapPerfCirPercentUtilizationEntry 25 }

 dfrapPerfCirRxPercentUtilizationRange6 OBJECT-TYPE
             SYNTAX      INTEGER 
             ACCESS      read-only
             STATUS      mandatory
             DESCRIPTION
                "The number of received bytes counted on this DLCI
                 during intervals where the percentage of
                 CIR was in range 6 (81-100% of CIR)."
            ::= { dfrapPerfCirPercentUtilizationEntry 26 }

 dfrapPerfCirRxPercentUtilizationRange7 OBJECT-TYPE
             SYNTAX      INTEGER 
             ACCESS      read-only
             STATUS      mandatory
             DESCRIPTION
                "The number of received bytes counted on this DLCI
                 during intervals where the percentage of
                 CIR was in range 7 (101-150% of CIR)."
            ::= { dfrapPerfCirPercentUtilizationEntry 27 }

 dfrapPerfCirRxPercentUtilizationRange8 OBJECT-TYPE
             SYNTAX      INTEGER 
             ACCESS      read-only
             STATUS      mandatory
             DESCRIPTION
                "The number of received bytes counted on this DLCI
                 during intervals where the percentage of
                 CIR was in range 8 (> 150% of CIR)."
            ::= { dfrapPerfCirPercentUtilizationEntry 28 }

 dfrapPerfCirTxPercentUtilizationRange1 OBJECT-TYPE
             SYNTAX      INTEGER 
             ACCESS      read-only
             STATUS      mandatory
             DESCRIPTION
                "The number of transmitted bytes counted on this DLCI
                 during intervals where the percentage of
                 CIR was in range 1 (0% of CIR)."
            ::= { dfrapPerfCirPercentUtilizationEntry 41 }

 dfrapPerfCirTxPercentUtilizationRange2 OBJECT-TYPE
             SYNTAX      INTEGER 
             ACCESS      read-only
             STATUS      mandatory
             DESCRIPTION
                "The number of transmitted bytes counted on this DLCI
                 during intervals where the percentage of
                 CIR was in range 2 (1-10% of CIR)."
            ::= { dfrapPerfCirPercentUtilizationEntry 42 }

 dfrapPerfCirTxPercentUtilizationRange3 OBJECT-TYPE
             SYNTAX      INTEGER 
             ACCESS      read-only
             STATUS      mandatory
             DESCRIPTION
                "The number of transmitted bytes counted on this DLCI
                 during intervals where the percentage of
                 CIR was in range 3 (11-20% of CIR)."
            ::= { dfrapPerfCirPercentUtilizationEntry 43 }

 dfrapPerfCirTxPercentUtilizationRange4 OBJECT-TYPE
             SYNTAX      INTEGER 
             ACCESS      read-only
             STATUS      mandatory
             DESCRIPTION
                "The number of transmitted bytes counted on this DLCI
                 during intervals where the percentage of
                 CIR was in range 4 (21-50% of CIR)."
            ::= { dfrapPerfCirPercentUtilizationEntry 44 }

 dfrapPerfCirTxPercentUtilizationRange5 OBJECT-TYPE
             SYNTAX      INTEGER 
             ACCESS      read-only
             STATUS      mandatory
             DESCRIPTION
                "The number of transmitted bytes counted on this DLCI
                 during intervals where the percentage of
                 CIR was in range 5 (51-80% of CIR)."
            ::= { dfrapPerfCirPercentUtilizationEntry 45 }

 dfrapPerfCirTxPercentUtilizationRange6 OBJECT-TYPE
             SYNTAX      INTEGER 
             ACCESS      read-only
             STATUS      mandatory
             DESCRIPTION
                "The number of transmitted bytes counted on this DLCI
                 during intervals where the percentage of
                 CIR was in range 6 (81-100% o0f CIR)."
            ::= { dfrapPerfCirPercentUtilizationEntry 46 }

 dfrapPerfCirTxPercentUtilizationRange7 OBJECT-TYPE
             SYNTAX      INTEGER 
             ACCESS      read-only
             STATUS      mandatory
             DESCRIPTION
                "The number of transmitted bytes counted on this DLCI
                 during intervals where the percentage of
                 CIR was in range 7 (101-150% of CIR)."
            ::= { dfrapPerfCirPercentUtilizationEntry 47 }

 dfrapPerfCirTxPercentUtilizationRange8 OBJECT-TYPE
             SYNTAX      INTEGER 
             ACCESS      read-only
             STATUS      mandatory
             DESCRIPTION
                "The number of transmitted bytes counted on this DLCI
                 during intervals where the percentage of
                 CIR was in range 8 (> 150% of CIR)."
            ::= { dfrapPerfCirPercentUtilizationEntry 48 }


--
--  Current Utilization for each DLCI.
--

 dfrapPerfCurrentPerDlciUtilizationTable OBJECT-TYPE
         SYNTAX   SEQUENCE OF DfrapPerfCurrentPerDlciUtilizationEntry
         ACCESS   not-accessible
         STATUS   mandatory
         DESCRIPTION
            "The current measurement of utilization as a percentage
             of CIR on each DLCI.  Each short term statistics
             interval, the count of bytes transmitted and received
             is used to calculate the percentage of CIR used."
         ::= { dfrapPerfCirPercentUtilization 2 }

 dfrapPerfCurrentPerDlciUtilizationEntry OBJECT-TYPE
             SYNTAX DfrapPerfCurrentPerDlciUtilizationEntry
             ACCESS   not-accessible
             STATUS   mandatory
             DESCRIPTION
                "The utilization statistics for a particular DLCI."
             INDEX { dfrapPerfCurrentPerDlciUtilizationDlciValue }
             ::= { dfrapPerfCurrentPerDlciUtilizationTable 1 }

         DfrapPerfCurrentPerDlciUtilizationEntry ::=
             SEQUENCE {
                 dfrapPerfCurrentPerDlciUtilizationDlciValue  INTEGER,
                 dfrapPerfCurrentPerDlciRxUtilization         INTEGER,
                 dfrapPerfCurrentPerDlciTxUtilization         INTEGER,
                 dfrapPerfCurrentPerDlciAggregateUtilization  INTEGER
             }

 dfrapPerfCurrentPerDlciUtilizationDlciValue OBJECT-TYPE
             SYNTAX      INTEGER 
             ACCESS      read-only
             STATUS      mandatory
             DESCRIPTION
                "The DLCI value with which the Statistics are associated."
            ::= { dfrapPerfCurrentPerDlciUtilizationEntry 1 }

 dfrapPerfCurrentPerDlciRxUtilization OBJECT-TYPE
             SYNTAX      INTEGER 
             ACCESS      read-only
             STATUS      mandatory
             DESCRIPTION
                "The receive direction utilization as a
                 percentage of CIR."
            ::= { dfrapPerfCurrentPerDlciUtilizationEntry 2 }

 dfrapPerfCurrentPerDlciTxUtilization OBJECT-TYPE
             SYNTAX      INTEGER 
             ACCESS      read-only
             STATUS      mandatory
             DESCRIPTION
                "The transmit direction utilization as a
                 percentage of CIR."
            ::= { dfrapPerfCurrentPerDlciUtilizationEntry 3 }

 dfrapPerfCurrentPerDlciAggregateUtilization OBJECT-TYPE
             SYNTAX      INTEGER 
             ACCESS      read-only
             STATUS      mandatory
             DESCRIPTION
                "The aggregate utilization, the average
                 of the receive and transmit utilization
                 as a percentage of CIR."
            ::= { dfrapPerfCurrentPerDlciUtilizationEntry 4 }


--
--  Current Utilization for each interface and the unit as a whole.
--

dfrapPerfCurrentUnitUtilization OBJECT IDENTIFIER
            ::= { dfrapPerfCirPercentUtilization 3 }

 dfrapPerfCurrentDteUtilization OBJECT-TYPE
             SYNTAX      INTEGER 
             ACCESS      read-only
             STATUS      mandatory
             DESCRIPTION
                "The DTE interface utilization as a
                 percentage of line rate."
            ::= { dfrapPerfCurrentUnitUtilization 2 }

 dfrapPerfCurrentWanUtilization OBJECT-TYPE
             SYNTAX      INTEGER 
             ACCESS      read-only
             STATUS      mandatory
             DESCRIPTION
                "The WAN interface utilization as a
                 percentage of line rate."
            ::= { dfrapPerfCurrentUnitUtilization 3 }

 dfrapPerfCurrentAggregateUtilization OBJECT-TYPE
             SYNTAX      INTEGER 
             ACCESS      read-only
             STATUS      mandatory
             DESCRIPTION
                "The aggregate utilization of the unit,
                 the average of the DTE and WAN interface
                 utilizations as a percentage of line rate."
            ::= { dfrapPerfCurrentUnitUtilization 4 }


-- =============================
-- ==  DFRAP EVENT LOG group  ==
-- =============================
dfrapEventTrapLog      OBJECT IDENTIFIER ::= { dfrap 10 }

dfrapEventTrapLogTable              OBJECT-TYPE
        SYNTAX  SEQUENCE OF     DFRAPEventTrapLogEntry
        ACCESS  not-accessible
        STATUS  mandatory
        DESCRIPTION
            "This table contains the Event/Trap log.  The entries are
            indexed by sequence number."
        ::= { dfrapEventTrapLog 1}

    dfrapEventTrapLogEntry              OBJECT-TYPE
        SYNTAX  DFRAPEventTrapLogEntry
        ACCESS  not-accessible
        STATUS  mandatory
        DESCRIPTION
            "The event record for a particular event."
        INDEX {dfrapEventTrapLogSeqNum}
        ::= { dfrapEventTrapLogTable 1}

    DFRAPEventTrapLogEntry ::=
        SEQUENCE
        {
           dfrapEventTrapLogSeqNum        INTEGER,
           dfrapEventTrapLogGenericEvent  INTEGER,
           dfrapEventTrapLogSpecificEvent INTEGER,
           dfrapEventTrapLogTimeStamp     TimeTicks,
           dfrapEventTrapLogVarBind1      INTEGER,
           dfrapEventTrapLogVarBind2      INTEGER,
           dfrapEventTrapLogVarBind3      INTEGER
        }

    dfrapEventTrapLogSeqNum         OBJECT-TYPE
        SYNTAX  INTEGER
        ACCESS  read-only
        STATUS  mandatory
        DESCRIPTION
            "The sequence number associated with an event record."
        ::= {dfrapEventTrapLogEntry 1}

    dfrapEventTrapLogGenericEvent       OBJECT-TYPE
        SYNTAX  INTEGER
        ACCESS  read-only
        STATUS  mandatory
        DESCRIPTION
            "The SNMP generic trap or event number."
        ::= {dfrapEventTrapLogEntry 2}

    dfrapEventTrapLogSpecificEvent      OBJECT-TYPE
        SYNTAX  INTEGER
        ACCESS  read-only
        STATUS  mandatory
        DESCRIPTION
            "The SNMP specific trap or event sub-identifier number."
        ::= {dfrapEventTrapLogEntry 3}

    dfrapEventTrapLogTimeStamp      OBJECT-TYPE
        SYNTAX  TimeTicks
        ACCESS  read-only
        STATUS  mandatory
        DESCRIPTION
            "The SNMP trap timestamp."
        ::= {dfrapEventTrapLogEntry 4}

    dfrapEventTrapLogVarBind1           OBJECT-TYPE
        SYNTAX  INTEGER
        ACCESS  read-only
        STATUS  mandatory
        DESCRIPTION
            "Variable Binding 1 for this SNMP Trap event."
        ::= {dfrapEventTrapLogEntry 5}

    dfrapEventTrapLogVarBind2           OBJECT-TYPE
        SYNTAX  INTEGER
        ACCESS  read-only
        STATUS  mandatory
        DESCRIPTION
            "Variable Binding 2 for this SNMP Trap event."
        ::= {dfrapEventTrapLogEntry 6}

    dfrapEventTrapLogVarBind3           OBJECT-TYPE
        SYNTAX  INTEGER
        ACCESS  read-only
        STATUS  mandatory
        DESCRIPTION
            "Variable Binding 3 for this SNMP Trap event."
        ::= {dfrapEventTrapLogEntry 7}


    dfrapEventLogAltTable OBJECT-TYPE
         SYNTAX   SEQUENCE OF DFRAPEventLogAltEntry
         ACCESS   not-accessible
         STATUS   mandatory
         DESCRIPTION
            "This is an alternative method to access the database of the
             Event/Trap Log.  The database is indexed by Sequence Number
             and Event/Trap log's are returned  in an OCTETSTRING."
         ::= { dfrapEventTrapLog  2 }

        dfrapEventLogAltEntry   OBJECT-TYPE
            SYNTAX   DFRAPEventLogAltEntry
            ACCESS   not-accessible
            STATUS   mandatory
            DESCRIPTION
               "The Event/Trap Log for a particular sequence number."
           INDEX { dfrapEventLogAltSeqNum }
           ::= { dfrapEventLogAltTable 1 }

        DFRAPEventLogAltEntry ::=
            SEQUENCE {
                dfrapEventLogAltSeqNum               INTEGER,
                dfrapEventLogAltArray                OCTET STRING
                }

        dfrapEventLogAltSeqNum    OBJECT-TYPE
            SYNTAX      INTEGER
            ACCESS      read-only
            STATUS      mandatory
            DESCRIPTION
              "The Sequence Number monitored for the Event Log"
           ::= { dfrapEventLogAltEntry 1 }

        dfrapEventLogAltArray    OBJECT-TYPE
            SYNTAX      OCTET STRING
            ACCESS      read-only
            STATUS      mandatory
            DESCRIPTION
               "The Event / Trap log for the given sequence number."
           ::= { dfrapEventLogAltEntry 2 }

   dfrapEventLogCurrentSeqNum                 OBJECT-TYPE
        SYNTAX  INTEGER
        ACCESS  read-only
        STATUS  mandatory
        DESCRIPTION
            "The current index into the Event Log Table."
        ::= {dfrapEventTrapLog 3}


    dfrapEventLogFreeze                 OBJECT-TYPE
        SYNTAX  INTEGER
        {
            freeze      (1),
            un-freeze   (2)
        }
        ACCESS  write-only
        STATUS  mandatory
        DESCRIPTION
            "This freezes the Event/Trap Log. freeze(1) will 
             prevent Events / Traps from being entered into the database,
             un-freeze(2) will allow Events / Traps to be logged into the
             database. An event will be logged indicating a set of this
             entry"
        ::= { dfrapEventTrapLog 4}


    dfrapEventLogClear                  OBJECT-TYPE
        SYNTAX  INTEGER
        {
            clear   (1)
        }
        ACCESS  write-only
        STATUS  mandatory
        DESCRIPTION
            "This clears the Event/Trap Log."
        ::= { dfrapEventTrapLog 5}



-- =========================
-- ==        TRAPS        ==
-- =========================
--
--       Alarm types for the DFRAP.
--       This is here for consistency in alarm/TRAP numbers.
--
--       This is a superset of alarm types and TRAPs.

dfrapAlarmType     OBJECT-TYPE
          SYNTAX      INTEGER
          {
               bad-config-in-set                 (1),
               config-local-update               (2),
               local-unit-loopback-enabled       (14),
               local-unit-loopback-disabled      (15),
               local-unit-loopback-failure       (16),
               local-dte-loopback-enabled        (17),
               local-dte-loopback-disabled       (18),
               local-dte-loopback-failure        (19),
               local-network-loopback-enabled    (26),
               local-network-loopback-disabled   (27),
               local-network-loopback-failure    (28),
               v54-loop-up-initiated             (29),
               v54-loop-down-completed           (30),
               v54-loopback-enabled-by-remote    (31),
               v54-loopback-disabled-by-remote   (32),
               v54-loopback-failure              (33),
               bert-test-pattern-initiated       (44),
               bert-test-pattern-completed       (45),
               bert-test-pattern-failure         (46),
               dlci-active                       (47),
               dlci-inactive                     (48),
               dlci-td-threshold                 (49),
               lmi-sourcing-change-passthru      (50),
               lmi-sourcing-change-user-dte      (51),
               lmi-sourcing-change-net-dte       (52),
               lmi-sourcing-change-user-net      (53),
               lmi-sourcing-change-net-net       (54),
               dte-signal-rts-on                 (55),
               dte-signal-rts-off                (56),
               dte-signal-dtr-on                 (57),
               dte-signal-dtr-off                (58),
               lmi-non-incr-seq-num-dte          (59),
               lmi-non-incr-seq-num-net          (60),
               lmi-seq-num-mismatch-dte          (61),
               lmi-seq-num-mismatch-net          (62),
               line-failure                      (63),
               line-in-service                   (64),
               connected                         (65),
               connect-failure                   (66),
               incoming-call                     (67),
               disconnected                      (68),
               bpv-threshold-exceeded            (69),
               bpv-threshold-acceptable          (70),
               remote-network-simplex-loopback-enabled       (71),
               remote-network-simplex-loopback-disabled      (72),
               remote-network-non-latching-loopback-enabled  (73),
               remote-network-non-latching-loopback-disabled (74),
               trap-muting-active                (75),
               trap-muting-inactive              (76),
               vloop-loop-up                     (90),
               vloop-loop-down                   (91),   
               vloop-up-via-remote               (92),
               vloop-down-via-remote             (93),
               vloop-failed                      (94),
               vbert-started                     (95),
               vbert-stopped                     (96),
               vbert-request-failed              (97),
               pvc-rx-utilization-exceeded       (138),
               pvc-tx-utilization-exceeded       (139),
               pvc-rx-utilization-cleared        (140),
               pvc-tx-utilization-cleared        (141),
               config-install-success            (142),
               tftp-requested                    (257),
               tftp-transferring                 (258),
               tftp-programming                  (259),
               tftp-aborted                      (260),
               tftp-success                      (261),
               tftp-host-unreachable             (262),
               tftp-no-file                      (263),
               tftp-invalid-file                 (264),
               tftp-corrupt-file                 (265)
          }
          ACCESS      read-only
          STATUS      mandatory
          DESCRIPTION
             "The alarm type of the most recent TRAP generated."
          ::= { dfrap 6 }

dfrapDLCINum     OBJECT-TYPE
          SYNTAX      INTEGER
          ACCESS      read-only
          STATUS      mandatory
          DESCRIPTION
             "The DLCI number for the most recent DLCI TRAP generated."
          ::= { dfrap 7 }

dfrapInterface     OBJECT-TYPE
          SYNTAX      INTEGER
          {
             dte   (1),
             dds   (2)
          }
          ACCESS      read-only
          STATUS      mandatory
          DESCRIPTION
             "The interface most recently reported in a TRAP."
          ::= { dfrap 8 }

dfrapIpAddress     OBJECT-TYPE
          SYNTAX      IpAddress
          ACCESS      read-only
          STATUS      mandatory
          DESCRIPTION
             "The IP address most recently reported in a TRAP."
          ::= { dfrap 9 }

dfrapPercentUtilization   OBJECT-TYPE
          SYNTAX      INTEGER
          ACCESS      read-only
          STATUS      mandatory
          DESCRIPTION
            "The percent utilization for a DLCI most recently
           reported in a TRAP."
         ::= { dfrap 11 }

dfrapUtilizationThreshold   OBJECT-TYPE
          SYNTAX      INTEGER
          ACCESS      read-only
          STATUS      mandatory
          DESCRIPTION
            "The percent utilization threshold for a DLCI most 
             recently reported in a TRAP."
         ::= { dfrap 12 }


dfrapCfgLockIpAddress   OBJECT-TYPE
          SYNTAX      INTEGER
          ACCESS      read-only
          STATUS      mandatory
          DESCRIPTION
            "The IP address of the management station locking 
              the configuration most recently reported in a TRAP."
         ::= { dfrap 13 }
          
dfrapTrap          TRAP-TYPE
          ENTERPRISE  dfrap
          VARIABLES   
          { 
               dfrapAlarmType
          }
          DESCRIPTION
             "A dfrapTrap trap signifies that the
             sending node had its `dfrapAlarmType`
             variable modified."
          ::= 0

dfrapBadConfigTrap          TRAP-TYPE
          ENTERPRISE  dfrap
          VARIABLES   
          { 
               dfrapAlarmType
          }
          DESCRIPTION
             "Unit has received a configuration update request 
              through SNMP but the request was rejected due to
              an incorrect or inappropriate parameter."
          ::= 1

dfrapLocalConfigTrap          TRAP-TYPE
          ENTERPRISE  dfrap
          VARIABLES   
          { 
               dfrapAlarmType
          }
          DESCRIPTION
             "Unit configuration has been updated locally 
              (console port or front panel keypad) or remotely 
              (telnet)"
          ::= 2

dfrapLocalUnitLoopbackEnabledTrap          TRAP-TYPE
          ENTERPRISE  dfrap
          VARIABLES   
          { 
               dfrapAlarmType
          }
          DESCRIPTION
             "Unit is in a bi-directional unit loopback. Data 
              is received from either interface, processed, 
              and transmitted back towards the same interface. 
              When configured for Frame Relay operation the unit 
              will preserve the LMI path during this loopback. 
              In Frame Relay mode, only valid frames are looped 
              back (pseudorandom test patterns will be dropped)."
          ::= 14

dfrapLocalUnitLoopbackDisabledTrap          TRAP-TYPE
          ENTERPRISE  dfrap
          VARIABLES   
          { 
               dfrapAlarmType
          }
          DESCRIPTION
             "Bi-directional unit loopback path is removed."
          ::= 15

dfrapLocalUnitLoopbackFailedTrap          TRAP-TYPE
          ENTERPRISE  dfrap
          VARIABLES   
          { 
               dfrapAlarmType
          }
          DESCRIPTION
             "Bi-directional unit loopback request has been 
              rejected by the unit. Typically, this is due 
              to the presence of another loopback condition."
          ::= 16

dfrapLocalDteLoopbackEnabledTrap          TRAP-TYPE
          ENTERPRISE  dfrap
          VARIABLES   
          { 
               dfrapAlarmType
          }
          DESCRIPTION
             "Unit is in a bi-directional DTE loopback. All 
              data received at the DTE interface is looped 
              back regardless of format or content (line 
              loopback). All data received at the WAN interface 
              is looped back regardless of format or content (line 
              loopback) When configured for Frame Relay 
              operation the unit will not preserve the LMI 
              path during this loopback."
          ::= 17

dfrapLocalDteLoopbackDisabledTrap          TRAP-TYPE
          ENTERPRISE  dfrap
          VARIABLES   
          { 
               dfrapAlarmType
          }
          DESCRIPTION
             "Bi-directional DTE loopback path is removed."
          ::= 18

dfrapLocalDteLoopbackFailedTrap          TRAP-TYPE
          ENTERPRISE  dfrap
          VARIABLES   
          { 
               dfrapAlarmType
          }
          DESCRIPTION
             "Bi-directional DTE loopback request has been 
              rejected by the unit. Typically, this is due 
              to the presence of another loopback condition."
          ::= 19

dfrapLocalNetLoopbackEnabledTrap          TRAP-TYPE
          ENTERPRISE  dfrap
          VARIABLES   
          { 
               dfrapAlarmType
          }
          DESCRIPTION
             "Unit is in local network loopback. All data 
              received from the WAN, regardless of format or 
              content, is transmitted back out (line interface 
              loopback) while still being sent to the DTE. When 
              configured for Frame Relay operation the unit 
              will not preserve the LMI path during this loopback."
          ::= 26

dfrapLocalNetLoopbackDisabledTrap          TRAP-TYPE
          ENTERPRISE  dfrap
          VARIABLES   
          { 
               dfrapAlarmType
          }
          DESCRIPTION
             "Local network loopback path is removed."
          ::= 27

dfrapLocalNetLoopbackFailedTrap          TRAP-TYPE
          ENTERPRISE  dfrap
          VARIABLES   
          { 
               dfrapAlarmType
          }
          DESCRIPTION
             "Local network loopback request is rejected. 
              Typically, this is due to the presence of another 
              loopback condition."
          ::= 28

dfrapV54LoopUpInitiatedTrap          TRAP-TYPE
          ENTERPRISE  dfrap
          VARIABLES   
          { 
               dfrapAlarmType
          }
          DESCRIPTION
             "Unit has sent the standard V54 loop up pattern 
              out the WAN at the DTE rate. A compatible piece 
              of equipment can sense this pattern and enter a 
              loopback state - typically putting up a bi-directional 
              DTE loopback path. After sending the V54 loop up 
              pattern, the (local) unit returns to normal operation, 
              expecting a loopback condition at the remote device."
          ::= 29

dfrapV54LoopDownCompletedTrap          TRAP-TYPE
          ENTERPRISE  dfrap
          VARIABLES   
          { 
               dfrapAlarmType
          }
          DESCRIPTION
             "Unit has sent the standard V54 loop down pattern 
              out the WAN at the DTE rate. A compatible piece of 
              equipment can sense this pattern remove the loopback 
              state that is entered after receiving a loop up pattern - 
              typically a bi-directional DTE loopback path. After 
              sending the V54 loop down pattern, the unit returns 
              to normal operation."
          ::= 30

dfrapV54LoopbackEnabledTrap          TRAP-TYPE
          ENTERPRISE  dfrap
          VARIABLES   
          { 
               dfrapAlarmType
          }
          DESCRIPTION
             "Unit has received a V54 loop up pattern from a 
              compatible piece of equipment. A bi-directional DTE 
              loopback is activated. All data received at the 
              DTE interface is looped back regardless of format 
              or content.  All data received at the 
              WAN interface is looped back regardless of format 
              or content. When configured for Frame Relay 
              operation the unit will not preserve the LMI path 
              during this loopback."
          ::= 31

dfrapV54LoopbackDisabledTrap          TRAP-TYPE
          ENTERPRISE  dfrap
          VARIABLES   
          { 
               dfrapAlarmType
          }
          DESCRIPTION
             "Unit has received a V54 loop down pattern from 
              a compatible piece of equipment. The bi-directional 
              local DTE loopback is removed"
          ::= 32

dfrapV54LoopbackFailedTrap          TRAP-TYPE
          ENTERPRISE  dfrap
          VARIABLES   
          { 
              dfrapAlarmType
          }
          DESCRIPTION
             "Unit has rejected the request to send a V54 loop 
              up. Typically, this is due to the presence of 
              another loopback condition."
          ::= 33

dfrapBertInitiatedTrap          TRAP-TYPE
          ENTERPRISE  dfrap
          VARIABLES   
          { 
               dfrapAlarmType
          }
          DESCRIPTION
             "Unit is sending a pseudorandom test pattern 
              (511 or QRSS) out the WAN and monitoring the 
              WAN received data for the same pattern. This 
              test may be ineffective in certain frame relay 
              applications as pseudorandom data lacks appropriate 
              framing."
          ::= 44

dfrapBertCompletedTrap          TRAP-TYPE
          ENTERPRISE  dfrap
          VARIABLES   
          { 
               dfrapAlarmType
          }
          DESCRIPTION
             "Unit has stopped sending a pseudorandom test 
              pattern out the WAN."
          ::= 45


dfrapBertFailedTrap          TRAP-TYPE
          ENTERPRISE  dfrap
          VARIABLES   
          { 
               dfrapAlarmType
          }
          DESCRIPTION
             "Unit has rejected the request to enter a BERT 
              test state. Typically, this is due to the presence 
              of another diagnostic condition."
          ::= 46

dfrapDLCIActiveTrap          TRAP-TYPE
          ENTERPRISE  dfrap
          VARIABLES   
          { 
               dfrapAlarmType,
               dfrapDLCINum
          }
          DESCRIPTION
             "Unit is reporting this DLCI as active and 
              provisioned. An active DLCI is one that is 
              explicitly declared ACTIVE in an LMI Full 
              Status Response (typically coming from a 
              frame relay switch)."
          ::= 47

dfrapDLCIInactiveTrap          TRAP-TYPE
          ENTERPRISE  dfrap
          VARIABLES   
          { 
               dfrapAlarmType,
               dfrapDLCINum
          }
          DESCRIPTION
             "Unit is reporting this DLCI as inactive. An 
              inactive DLCI is determined inactive one of two 
              ways: it is either explicitly declared inactive
              in an LMI Full Status Response (typically coming 
              from a frame relay switch) or a Full Status 
              Response is not seen causing a Full Status Timer 
              expiry. Having the unit's full status timer too 
              low could result in the unit falsely declaring DLCIs 
              inactive (then active again). This does not interfere 
              with any data activity on the DLCI but could result
              in excessive traps."
          ::= 48

dfrapDLCITDThresholdTrap          TRAP-TYPE
          ENTERPRISE  dfrap
          VARIABLES   
          { 
               dfrapAlarmType,
               dfrapDLCINum,
               dfrapIpAddress
          }
          DESCRIPTION
             "VNIP has measured a round-trip transit delay on this
              PVC to this peer which exceeds the user-defined threshold."
          ::= 49

dfrapLmiSourcingChangePassthruTrap          TRAP-TYPE
          ENTERPRISE  dfrap
          VARIABLES   
          { 
               dfrapAlarmType
          }
          DESCRIPTION
             "Unit is not sourcing any LMI messages. If this 
              state persists then LMI is up and the proper 
              handshaking is occurring independent of the unit. 
              This may also be a transient state if the unit 
              is in an LMI hunt mode. If this trap occurs 
              repeatedly, separated by other LMI sourcing states, 
              the unit is not seeing any of the expected LMI 
              messages from either interface. Check LMI type, 
              connectivity, and configuration of associated equipment."
          ::= 50

dfrapLmiSourcingChangeUserDteTrap           TRAP-TYPE
          ENTERPRISE  dfrap
          VARIABLES   
          { 
               dfrapAlarmType
          }
          DESCRIPTION
             "Unit is acting as a source of LMI Status Requests 
              (Link Integrity Verification, Keep Alive). If this 
              state persists then the equipment attached to the 
              DTE interface is configured as a Frame Relay DCE 
              but a companion Frame Relay DTE device is not seen 
              out the WAN. This could also be a transient state 
              if the unit is in an LMI hunt mode. If this trap 
              occurs repeatedly, separated by other LMI sourcing 
              states, the unit is not seeing any of the expected 
              LMI messages from either interface. Check LMI type, 
              connectivity, and configuration of associated equipment."
          ::= 51

dfrapLmiSourcingChangeNetDteTrap            TRAP-TYPE
          ENTERPRISE  dfrap
          VARIABLES   
          { 
               dfrapAlarmType
          }
          DESCRIPTION
             "Unit is acting as a source of LMI Status Responses 
              (Link Integrity Verification, Keep Alive). If this 
              state persists then the equipment attached to the 
              DTE interface is configured as a Frame Relay DTE 
              but a companion Frame Relay DCE device is not seen 
              out the WAN. This could also be a transient state 
              if the unit is in an LMI hunt mode. If this trap 
              occurs repeatedly, separated by other LMI sourcing 
              states, the unit is not seeing any of the expected 
              LMI messages from either interface. Check LMI type, 
              connectivity, and configuration of external equipment."
          ::= 52

dfrapLmiSourcingChangeUserDdsTrap           TRAP-TYPE
          ENTERPRISE  dfrap
          VARIABLES   
          { 
               dfrapAlarmType
          }
          DESCRIPTION
             "Unit is acting as a source of LMI Status Requests 
              (Link Integrity Verification, Keep Alive). If this 
              state persists then the equipment attached to the 
              WAN interface is configured as a Frame Relay DCE 
              but a companion Frame Relay DTE device is not seen 
              out the DTE interface. This could also be a transient 
              state if the unit is in an LMI hunt mode. If this 
              trap occurs repeatedly, separated by other LMI 
              sourcing states, the unit is not seeing any of the 
              expected LMI messages from either interface. Check 
              LMI type, connectivity, and configuration of 
              associated equipment."
          ::= 53

dfrapLmiSourcingChangeNetDdsTrap            TRAP-TYPE
          ENTERPRISE  dfrap
          VARIABLES   
          { 
               dfrapAlarmType
          }
          DESCRIPTION
             "Unit is acting as a source of LMI Status Responses 
              (Link Integrity Verification, Keep Alive). If this 
              state persists then the equipment attached to the 
              WAN interface is configured as a Frame Relay DTE 
              but a companion Frame Relay DCE device is not seen 
              out the DTE interface. This could also be a transient 
              state if the unit is in an LMI hunt mode. If this 
              trap occurs repeatedly, separated by other LMI sourcing 
              states, the unit is not seeing any of the expected 
              LMI messages from either interface. Check LMI type, 
              connectivity, and configuration of associated equipment."
          ::= 54

dfrapDteSignalRtsOnTrap                     TRAP-TYPE
          ENTERPRISE  dfrap
          VARIABLES   
          { 
               dfrapAlarmType
          }
          DESCRIPTION
             "Unit's DTE Request to Send (RTS) interface control 
              signal is now active (on). This signal is presented 
              by the external DTE device."
          ::= 55

dfrapDteSignalRtsOffTrap                    TRAP-TYPE
          ENTERPRISE  dfrap
          VARIABLES   
          { 
               dfrapAlarmType
          }
          DESCRIPTION
             "Unit's DTE Request to Send (RTS) interface control 
              signal is now inactive (off). This signal is presented 
              by the external DTE device."
          ::= 56

dfrapDteSignalDtrOnTrap                     TRAP-TYPE
          ENTERPRISE  dfrap
          VARIABLES   
          { 
               dfrapAlarmType
          }
          DESCRIPTION
             "Unit's DTE Data Terminal Ready (DTR) interface control 
              signal is now active (on). This signal is presented by the 
              external DTE device."
          ::= 57

dfrapDteSignalDtrOffTrap                    TRAP-TYPE
          ENTERPRISE  dfrap
          VARIABLES   
          { 
               dfrapAlarmType
          }
          DESCRIPTION
             "Unit's DTE Data Terminal Ready (DTR) interface control 
              signal is now inactive (off). This signal is presented by 
              the external DTE device."
          ::= 58

dfrapNonIncrLmiSeqNumDteTrap           TRAP-TYPE
          ENTERPRISE  dfrap
          VARIABLES   
          { 
               dfrapAlarmType
          }
          DESCRIPTION
             "Unit has detected a non-incrementing LMI sequence number
              from the DTE. A Status Enquiry or Status Response message 
              has been seen at the DTE interface. The Link Integrity 
              information element's Send Sequence Number was not 
              incremented or was incremented more than once since the 
              last Send Sequence Number seen from the DTE interface."
          ::= 59

dfrapNonIncrLmiSeqNumDdsTrap           TRAP-TYPE
          ENTERPRISE  dfrap
          VARIABLES   
          { 
               dfrapAlarmType
          }
          DESCRIPTION
             "Unit has detected a non-incrementing LMI sequence number
              from the WAN. A Status Enquiry or Status Response message 
              has been seen at the WAN interface. The Link Integrity 
              information element's Send Sequence Number was not 
              incremented or was incremented more than once since the 
              last Send Sequence Number seen from the WAN interface."
          ::= 60

dfrapLmiSeqNumMismatchDteTrap           TRAP-TYPE
          ENTERPRISE  dfrap
          VARIABLES   
          { 
               dfrapAlarmType
          }
          DESCRIPTION
             "Unit has detected an LMI sequence number mismatch from 
              the DTE. A Status Enquiry or Status Response message has 
              been seen at the DTE interface. The Link Inetgrity information 
              element's Receive Sequence Number was not the most recent 
              Send Sequence number sent from the WAN interface"
          ::= 61

dfrapLmiSeqNumMismatchDdsTrap           TRAP-TYPE
          ENTERPRISE  dfrap
          VARIABLES   
          { 
               dfrapAlarmType
          }
          DESCRIPTION
             "Unit has detected an LMI sequence number mismatch from 
              the WAN. A Status Enquiry or Status Response message has 
              been seen at the WAN interface. The Link Integrity information 
              element's Receive Sequence Number was not the most recent 
              Send Sequence number sent from the DTE interface."
          ::= 62

dfrapLineFailureTrap          TRAP-TYPE
          ENTERPRISE  dfrap
          VARIABLES   
          { 
               dfrapAlarmType
          }
          DESCRIPTION
             "The unit is reporting error conditions that inditate that the
              WAN connection is not fully functional."
          ::= 63

dfrapLineInServiceTrap          TRAP-TYPE
          ENTERPRISE  dfrap
          VARIABLES   
          { 
               dfrapAlarmType
          }
          DESCRIPTION
             "The unit is reporting that its WAN link has transitioned from a
              failure state to one which is functioning normally."
          ::= 64

dfrapBPVThresholdExceededTrap          TRAP-TYPE
          ENTERPRISE  dfrap
          VARIABLES   
          { 
               dfrapAlarmType
          }
          DESCRIPTION
             "The unit may be configured to issue this alarm in response to line code 
              violations being received from the service provider. If more than 5 
              violations are detected within a one-second interval, this trap is 
              generated. Network control codes which include bipolar violations
              are not considered errors and will not contribute to this trap. If
              this condition persists then contact your WAN service provider."
          ::= 69

dfrapBPVThresholdAcceptableTrap          TRAP-TYPE
          ENTERPRISE  dfrap
          VARIABLES   
          { 
               dfrapAlarmType
          }
          DESCRIPTION
             "This trap is to announce that the bipolar violation threshold of at least
              5 per second is no longer being exceeded."
          ::= 70

dfrapSimplexCurrentLoopbackEnabledTrap          TRAP-TYPE
          ENTERPRISE  dfrap
          VARIABLES   
          { 
               dfrapAlarmType
          }
          DESCRIPTION
             "The unit has received a DDS-standard simplex current reversal from the 
              WAN. In response, a Network Line Loopback path will be initiated for 
              the duration of the current reversal."
          ::= 71

dfrapSimplexCurrentLoopbackDisabledTrap          TRAP-TYPE
          ENTERPRISE  dfrap
          VARIABLES   
          { 
               dfrapAlarmType
          }
          DESCRIPTION
             "The unit has ceased receiving a simplex current reversal from the WAN. In 
              response, the Network Line Loopback path will be removed."
          ::= 72

dfrapNonLatchingLoopbackEnabledTrap          TRAP-TYPE
          ENTERPRISE  dfrap
          VARIABLES   
          { 
               dfrapAlarmType
          }
          DESCRIPTION
             "The unit has received a DDS-standard in-band loopback command. In response, 
              a Network Line Loopback path will be initiated and maintained as long as the
              appropriate command is recognized."
          ::= 73

dfrapNonLatchingLoopbackDisabledTrap          TRAP-TYPE
          ENTERPRISE  dfrap
          VARIABLES   
          { 
               dfrapAlarmType
          }
          DESCRIPTION
             "The unit has ceased receiving a DDS-standard in-band loopback command. 
              In response, a Network Line Loopback path will be removed."
          ::= 74


dfrapTrapMutingActive           TRAP-TYPE
          ENTERPRISE  dfrap
          VARIABLES   
          { 
               dfrapAlarmType
          }
          DESCRIPTION
             "Trap generation is muted. This trap will be issued at the configured
              trap muting frequency. No other traps will be issued."
          ::= 75

dfrapTrapMutingInactive           TRAP-TYPE
          ENTERPRISE  dfrap
          VARIABLES   
          { 
               dfrapAlarmType
          }
          DESCRIPTION
             "Trap generation is re-enabled (muting disabled)."
          ::= 76


dfrapVloopUp         TRAP-TYPE
          ENTERPRISE  dfrap
          VARIABLES
          { 
               dfrapAlarmType,
               dfrapDLCINum,
               dfrapInterface
          }
          DESCRIPTION
             "A Vnip PVC loopback (VLOOP) request has been sent to
              a remote device on this DLCI out this interface. The
              remote unit should respond by looping all data received
              on this PVC back towards the unit that initiated this
              request. A PVC running VLOOP will not be running any
              user data."
          ::= 90

dfrapVloopDown         TRAP-TYPE
          ENTERPRISE  dfrap
          VARIABLES   
          { 
               dfrapAlarmType,
               dfrapDLCINum,
               dfrapInterface
          }
          DESCRIPTION
             "A Vnip PVC loopback (VLOOP) disable request has been
              sent to a remote device on this DLCI out this interface.
              The remote unit should respond by tearing down the
              logical loop on this DLCI."
          ::= 91 

dfrapVloopUpViaRemote     TRAP-TYPE
          ENTERPRISE  dfrap
          VARIABLES   
          {
               dfrapAlarmType,
               dfrapDLCINum,
               dfrapInterface
          }
          DESCRIPTION
             "A Vnip PVC loopback (VLOOP) request has been received
              from a remote device on this DLCI on this interface.
              The unit will respond by looping all data received on
              this PVC back out the interface towards the unit that
              initiated the request." 
          ::= 92   

dfrapVloopDownViaRemote     TRAP-TYPE
          ENTERPRISE  dfrap
          VARIABLES   
          { 
               dfrapAlarmType,
               dfrapDLCINum,
               dfrapInterface
          }
          DESCRIPTION
           "A request to disable a Vnip PVC loopback (VLOOP) on
           this unit with the indicated DLCI and Interface has
           been received.  Usually this disable request is from
           the remote device that requested the VLOOP, however
           the request may also be due to a local event such as
           expiration of a locally configured loopback timeout.
           The unit will respond by tearing down the logical loop
           on this DLCI."
          ::= 93  

dfrapVloopRequestFailed       TRAP-TYPE
          ENTERPRISE  dfrap
          VARIABLES   
          { 
               dfrapAlarmType,
               dfrapDLCINum,
               dfrapInterface
          }
          DESCRIPTION
             "The request for a PVC loopback (VLOOP) has been rejected
              or did not complete."
          ::= 94

dfrapVbertStarted              TRAP-TYPE
          ENTERPRISE  dfrap
          VARIABLES   
          { 
               dfrapAlarmType,
               dfrapDLCINum,
               dfrapInterface
          }
          DESCRIPTION
             "A Vnip PVC error rate test (VBERT) has been started on
              this DLCI out this interface to a remote device. The
              VBERT test data will be statistically multiplexed in
              with user data, management data, and networking data.
              The destination peer will echo this test data back to
              the source producing a full-duplex volume-based timed
              test."
          ::= 95

dfrapVbertStopped              TRAP-TYPE
          ENTERPRISE  dfrap
          VARIABLES   
          { 
               dfrapAlarmType,
               dfrapDLCINum,
               dfrapInterface
          }   
          DESCRIPTION
             "A Vnip PVC BERT (VBERT) has been stopped on this DLCI 
              on this interface to a remote device."
          ::= 96

dfrapVbertRequestFailed       TRAP-TYPE
          ENTERPRISE  dfrap
          VARIABLES   
          { 
               dfrapAlarmType,
               dfrapDLCINum,
               dfrapInterface
          }   
          DESCRIPTION
             "The request for a PVC BERT (VBERT) on this DLCI 
              on this interface has been rejected."
          ::= 97

dfrapPvcRxUtilizationExceededTrap   TRAP-TYPE
          ENTERPRISE  dfrap
          VARIABLES   
          { 
               dfrapAlarmType,
               dfrapDLCINum,
               dfrapPercentUtilization,
               dfrapUtilizationThreshold
        }
        DESCRIPTION
           "Percent utilization threshold was exceeded for the
           defined number of Short Term Intervals in the
           reception direction on this DLCI. "
        ::= 138

dfrapPvcTxUtilizationExceededTrap   TRAP-TYPE
          ENTERPRISE  dfrap
          VARIABLES   
          { 
               dfrapAlarmType,
               dfrapDLCINum,
               dfrapPercentUtilization,
               dfrapUtilizationThreshold
        }
        DESCRIPTION
           "Percent utilization threshold was exceeded for the
           defined number of Short Term Intervals in the
           transmission direction on this DLCI. "
        ::= 139

dfrapPvcRxUtilizationClearedTrap   TRAP-TYPE
          ENTERPRISE  dfrap
          VARIABLES   
          { 
               dfrapAlarmType,
               dfrapDLCINum,
               dfrapPercentUtilization,
               dfrapUtilizationThreshold
        }
        DESCRIPTION
           "Percent utilization was below the threshold for the
           defined number of Short Term Intervals in the
           reception direction on this DLCI. "
        ::= 140

dfrapPvcTxUtilizationClearedTrap   TRAP-TYPE
          ENTERPRISE  dfrap
          VARIABLES   
          { 
               dfrapAlarmType,
               dfrapDLCINum,
               dfrapPercentUtilization,
               dfrapUtilizationThreshold
        }
        DESCRIPTION
           "Percent utilization was below the threshold for the
           defined number of Short Term Intervals in the
           transmission direction on this DLCI. "
        ::= 141

dfrapConfigInstallSuccess     TRAP-TYPE
          ENTERPRISE  dfrap
          VARIABLES   
          { 
               dfrapAlarmType,
               dfrapCfgLockIpAddress
        }
        DESCRIPTION
             " The configuration install process has successfully 
               completed. "
          ::= 142
          
dfrapTftpRequestedTrap            TRAP-TYPE
          ENTERPRISE  dfrap
          VARIABLES   
          { 
               dfrapAlarmType
          }
          DESCRIPTION
             "Unit has received a TFTP download request. TFTP is 
              the preferred method for upgrading a unit's software 
              image."
          ::= 257

dfrapTftpTransferringTrap            TRAP-TYPE
          ENTERPRISE  dfrap
          VARIABLES   
          { 
               dfrapAlarmType
          }
          DESCRIPTION
             "Unit has established a TFTP session, found the file, 
              and begun the transfer. The file must still be qualified 
              as appropriate for this unit."
          ::= 258

dfrapTftpProgrammingTrap            TRAP-TYPE
          ENTERPRISE  dfrap
          VARIABLES   
          { 
               dfrapAlarmType
          }
          DESCRIPTION
             "Unit has completed the TFTP transfer of a new software 
              image which will next be programmed into non-volatile 
              flash memory"
          ::= 259

dfrapTftpAbortedTrap            TRAP-TYPE
          ENTERPRISE  dfrap
          VARIABLES   
          { 
               dfrapAlarmType
          }
          DESCRIPTION
             "Unit's TFTP session was established but the transfer was 
              aborted by user intervention or an unrecoverable TFTP 
              protocol error"
          ::= 260

dfrapTftpSuccessTrap            TRAP-TYPE
          ENTERPRISE  dfrap
          VARIABLES   
          { 
               dfrapAlarmType
          }
          DESCRIPTION
             "Unit's TFTP download completed successfully. Flash 
              devices will be programmed with a new image. Unit will stop
              passing data during the programming phase (less than a minute)
              and, upon completion, will reset and return to full operation
              using the new image"
          ::= 261

dfrapTftpHostUnreachableTrap    TRAP-TYPE
          ENTERPRISE  dfrap
          VARIABLES   
          { 
               dfrapAlarmType
          }
          DESCRIPTION
             "Unit could not establish a TFTP session with the 
              designated server. Verify that the correct TFTP 
              ip address, TFTP DLCI and TFTP interface are 
              configured on the unit and also verify the TFTP 
              server configuration"
          ::= 262

dfrapTftpNoFileTrap             TRAP-TYPE
          ENTERPRISE  dfrap
          VARIABLES   
          { 
               dfrapAlarmType
          }
          DESCRIPTION
             "Unit could not locate the designated file on the TFTP 
              server. Verify the correct TFTP filename is configured 
              on the unit and verify the location of this file on 
              the server (file name may be case sensitive)"
          ::= 263

dfrapTftpInvalidFileTrap        TRAP-TYPE
          ENTERPRISE  dfrap
          VARIABLES   
          { 
               dfrapAlarmType
          }
          DESCRIPTION
             "Unit had established a TFTP session and began transfer 
              of the designated file. The unit aborted the transfer 
              after determining that the specified file is not 
              appropriate for this product (failed header verification)"
          ::= 264

dfrapTftpCorruptFileTrap        TRAP-TYPE
          ENTERPRISE  dfrap
          VARIABLES   
          { 
               dfrapAlarmType
          }
          DESCRIPTION
             "Unit transferred the designated file but aborted the 
              operation due to a checksum error within the downloaded
              s-record file"
          ::= 265

END
