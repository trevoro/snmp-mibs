FC-MIB DEFINITIONS ::= BEGIN

-- Title:       FastComm Communications Adapter MIB in concise format
-- Version      5.0.4
-- Date:        September 30, 2000

-- Copyright 1993,1994,1995,1996,1997,1998 FastComm Communications, Inc. 
-- All Rights Reserved.  Reproduction of this document is authorized 
-- on condition that the foregoing copyright notice is included.
-- This FastComm SNMP Management Information Base Specification
-- (Specification) embodies FastComm's confidential and proprietary
-- intellectual property.  FastComm retains all title and ownership 
-- in the Specification, including any revisions.  
--
-- It is FastComm's intent to encourage the widespread use of this
-- Specification in connection with the management of FastComm
-- products. FastComm grants vendors, end-users, and other interested 
-- parties a non-exclusive license to use this Specification in 
-- connection with the management of FastComm products.
--
-- This Specification is supplied "AS IS," and FastComm makes no
-- warranty, either express or implied, as to the use, operation, 
-- condition, or performance of the Specification.


IMPORTS
   	enterprises
        	FROM RFC1155-SMI
    	IpAddress
        	FROM RFC1155-SMI
    	OBJECT-TYPE
        	FROM RFC-1212
    	DisplayString
        	FROM RFC1213-MIB
    	TRAP-TYPE
        	FROM RFC-1215;

fastcomm          OBJECT IDENTIFIER ::= { enterprises 635 }

products          OBJECT IDENTIFIER ::= { fastcomm 1 }
registration      OBJECT IDENTIFIER ::= { fastcomm 2 }
temporary         OBJECT IDENTIFIER ::= { fastcomm 3 }

frameRelay        OBJECT IDENTIFIER ::= { products 2 }
snmpAgent         OBJECT IDENTIFIER ::= { products 3 }
fcQuick           OBJECT IDENTIFIER ::= { products 4 }

fsFrad            OBJECT IDENTIFIER ::= { frameRelay 1 }
quick2            OBJECT IDENTIFIER ::= { fcQuick 1 }

-- ***************************************************************************
-- Products
-- These object identifiers are for use as values for sysObjectId.

fcFradReg         OBJECT IDENTIFIER ::= { registration 1 }
cdQuickReg        OBJECT IDENTIFIER ::= { registration 2 }
fcFrad433Reg      OBJECT IDENTIFIER ::= { registration 3 }

fastcomm-F9500-S1    OBJECT IDENTIFIER ::= { cdQuickReg  1 }
fastcomm-F9500-S3    OBJECT IDENTIFIER ::= { cdQuickReg  2 }
fastcomm-F9500-S5    OBJECT IDENTIFIER ::= { cdQuickReg  3 }
fastcomm-F9500-D1    OBJECT IDENTIFIER ::= { cdQuickReg  4 }
fastcomm-F9500-D3    OBJECT IDENTIFIER ::= { cdQuickReg  5 }
fastcomm-F9500-D5    OBJECT IDENTIFIER ::= { cdQuickReg  6 }

-- MonoFRAD
fastcomm-F9100-SN-NI    OBJECT IDENTIFIER ::= { fcFradReg  1 }
fastcomm-F9100-SN-NE    OBJECT IDENTIFIER ::= { fcFradReg  2 }
fastcomm-F9100-DN-NI    OBJECT IDENTIFIER ::= { fcFradReg  3 }
fastcomm-F9100-DN-NE    OBJECT IDENTIFIER ::= { fcFradReg  4 }

fastcomm-F9100-TN-NE    OBJECT IDENTIFIER ::= { fcFradReg  5 }
fastcomm-F9100-EN-NE    OBJECT IDENTIFIER ::= { fcFradReg  6 }

-- QuadFRAD
fastcomm-F9100-SQ-NI    OBJECT IDENTIFIER ::= { fcFradReg 11 }
fastcomm-F9100-SQ-NL    OBJECT IDENTIFIER ::= { fcFradReg 12 }
fastcomm-F9100-DQ-NI    OBJECT IDENTIFIER ::= { fcFradReg 13 }
fastcomm-F9100-DQ-NL    OBJECT IDENTIFIER ::= { fcFradReg 14 }

fastcomm-F9100-SM-NI    OBJECT IDENTIFIER ::= { fcFradReg 15 }
fastcomm-F9100-DM-NI    OBJECT IDENTIFIER ::= { fcFradReg 16 }

-- EtherFRAD-5
fastcomm-F9200-SR-NI    OBJECT IDENTIFIER ::= { fcFradReg 21 }
fastcomm-F9200-SR-NL    OBJECT IDENTIFIER ::= { fcFradReg 22 }
fastcomm-F9200-DR-NI    OBJECT IDENTIFIER ::= { fcFradReg 23 }
fastcomm-F9200-DR-NL    OBJECT IDENTIFIER ::= { fcFradReg 24 }

-- EtherFRAD-2
fastcomm-F9200-SS-NI    OBJECT IDENTIFIER ::= { fcFradReg 25 }
fastcomm-F9200-SS-NE    OBJECT IDENTIFIER ::= { fcFradReg 26 }
fastcomm-F9200-DS-NI    OBJECT IDENTIFIER ::= { fcFradReg 27 }
fastcomm-F9200-DS-NE    OBJECT IDENTIFIER ::= { fcFradReg 28 }

-- EtherFRAD-1
fastcomm-F9200-SN-NI    OBJECT IDENTIFIER ::= { fcFradReg 30 }
fastcomm-F9200-SN-NE    OBJECT IDENTIFIER ::= { fcFradReg 31 }
fastcomm-F9200-DN-NI    OBJECT IDENTIFIER ::= { fcFradReg 32 }
fastcomm-F9200-DN-NE    OBJECT IDENTIFIER ::= { fcFradReg 33 }

-- RingFRAD-4
fastcomm-F9100-SW-NI    OBJECT IDENTIFIER ::= { fcFradReg 41 }
fastcomm-F9100-SW-NL    OBJECT IDENTIFIER ::= { fcFradReg 42 }
fastcomm-F9100-DW-NI    OBJECT IDENTIFIER ::= { fcFradReg 43 }
fastcomm-F9100-DW-NL    OBJECT IDENTIFIER ::= { fcFradReg 44 }

-- RingFRAD-2
fastcomm-F9100-SV-NI    OBJECT IDENTIFIER ::= { fcFradReg 45 }
fastcomm-F9100-SV-NE    OBJECT IDENTIFIER ::= { fcFradReg 46 }
fastcomm-F9100-DV-NI    OBJECT IDENTIFIER ::= { fcFradReg 47 }
fastcomm-F9100-DV-NE    OBJECT IDENTIFIER ::= { fcFradReg 48 }

-- Web Router
fastcomm-F9100-SN-NW    OBJECT IDENTIFIER ::= { fcFradReg 50 }
fastcomm-F9100-DN-NW    OBJECT IDENTIFIER ::= { fcFradReg 51 }
fastcomm-F9200-SN-NW    OBJECT IDENTIFIER ::= { fcFradReg 52 }
fastcomm-F9200-DN-NW    OBJECT IDENTIFIER ::= { fcFradReg 53 }

-- T1 DSU
fastcomm-F9200-TN-NI    OBJECT IDENTIFIER ::= { fcFradReg 60 }
fastcomm-F9200-TN-NE    OBJECT IDENTIFIER ::= { fcFradReg 61 }
fastcomm-F9200-TS-NI    OBJECT IDENTIFIER ::= { fcFradReg 62 }
fastcomm-F9200-TS-NE    OBJECT IDENTIFIER ::= { fcFradReg 63 }
fastcomm-F9200-TR-NI    OBJECT IDENTIFIER ::= { fcFradReg 64 }
fastcomm-F9200-TR-NL    OBJECT IDENTIFIER ::= { fcFradReg 65 }
fastcomm-F9200-TN-NW    OBJECT IDENTIFIER ::= { fcFradReg 66 }
fastcomm-F9200-TM-NI    OBJECT IDENTIFIER ::= { fcFradReg 67 }
fastcomm-F9200-TM-NL    OBJECT IDENTIFIER ::= { fcFradReg 68 }

-- E1 DSU
fastcomm-F9200-EN-NI    OBJECT IDENTIFIER ::= { fcFradReg 70 }
fastcomm-F9200-EN-NE    OBJECT IDENTIFIER ::= { fcFradReg 71 }
fastcomm-F9200-ES-NI    OBJECT IDENTIFIER ::= { fcFradReg 72 }
fastcomm-F9200-ES-NE    OBJECT IDENTIFIER ::= { fcFradReg 73 }
fastcomm-F9200-ER-NI    OBJECT IDENTIFIER ::= { fcFradReg 74 }
fastcomm-F9200-ER-NL    OBJECT IDENTIFIER ::= { fcFradReg 75 }
fastcomm-F9200-EN-NW    OBJECT IDENTIFIER ::= { fcFradReg 76 }
fastcomm-F9200-EM-NI    OBJECT IDENTIFIER ::= { fcFradReg 77 }
fastcomm-F9200-EM-NL    OBJECT IDENTIFIER ::= { fcFradReg 78 }

-- MetroLAN Serial/DSU
fastcomm-F9200-SM-NI    OBJECT IDENTIFIER ::= { fcFradReg 80 }
fastcomm-F9200-SM-NL    OBJECT IDENTIFIER ::= { fcFradReg 81 }
fastcomm-F9200-DM-NI    OBJECT IDENTIFIER ::= { fcFradReg 82 }
fastcomm-F9200-DM-NL    OBJECT IDENTIFIER ::= { fcFradReg 83 }
fastcomm-F9900-GS       OBJECT IDENTIFIER ::= { fcFradReg 84 }

-- For New 433 Modules
fastcomm-F9100-MO-NN    OBJECT IDENTIFIER ::= { fcFrad433Reg 1 }
fastcomm-F9100-MO-NS    OBJECT IDENTIFIER ::= { fcFrad433Reg 2 }
fastcomm-F9100-MO-NX    OBJECT IDENTIFIER ::= { fcFrad433Reg 3 }

fastcomm-F9100-TO-KN    OBJECT IDENTIFIER ::= { fcFrad433Reg 4 }
fastcomm-F9100-TO-KS    OBJECT IDENTIFIER ::= { fcFrad433Reg 5 }
fastcomm-F9100-TO-KX    OBJECT IDENTIFIER ::= { fcFrad433Reg 6 }

fastcomm-F9200-ET-HN    OBJECT IDENTIFIER ::= { fcFrad433Reg 7 }
fastcomm-F9200-ET-HS    OBJECT IDENTIFIER ::= { fcFrad433Reg 8 }
fastcomm-F9200-ET-HX    OBJECT IDENTIFIER ::= { fcFrad433Reg 9 }

fastcomm-F9200-IS-DS    OBJECT IDENTIFIER ::= { fcFrad433Reg 10 }
fastcomm-F9200-IS-DX    OBJECT IDENTIFIER ::= { fcFrad433Reg 11 }

fastcomm-F9200-ALC      OBJECT IDENTIFIER ::= { fcFrad433Reg 12 }
fastcomm-F9200-INET     OBJECT IDENTIFIER ::= { fcFrad433Reg 13 }

fastcomm-SY1-DM-NI      OBJECT IDENTIFIER ::= { fcFrad433Reg 14 }
fastcomm-SY1-DN-NI      OBJECT IDENTIFIER ::= { fcFrad433Reg 15 }
fastcomm-SY1-DQ-NI      OBJECT IDENTIFIER ::= { fcFrad433Reg 16 }
fastcomm-SY1-DV-NI      OBJECT IDENTIFIER ::= { fcFrad433Reg 17 }
fastcomm-SY1-DW-NI      OBJECT IDENTIFIER ::= { fcFrad433Reg 18 }
fastcomm-SY1-SM-NI      OBJECT IDENTIFIER ::= { fcFrad433Reg 19 }
fastcomm-SY1-SV-NI      OBJECT IDENTIFIER ::= { fcFrad433Reg 20 }
fastcomm-SY1-SW-NI      OBJECT IDENTIFIER ::= { fcFrad433Reg 21 }
fastcomm-SY2-DR-NI      OBJECT IDENTIFIER ::= { fcFrad433Reg 22 }

fastcomm-GTEDRNL        OBJECT IDENTIFIER ::= { fcFrad433Reg 23 }
fastcomm-NETLDR         OBJECT IDENTIFIER ::= { fcFrad433Reg 24 }
fastcomm-NNOSNMP        OBJECT IDENTIFIER ::= { fcFrad433Reg 25 }
fastcomm-NOPPPNA        OBJECT IDENTIFIER ::= { fcFrad433Reg 26 }
fastcomm-NOPPPNB        OBJECT IDENTIFIER ::= { fcFrad433Reg 27 }
fastcomm-NOX25NA        OBJECT IDENTIFIER ::= { fcFrad433Reg 28 }
fastcomm-NOX25NB        OBJECT IDENTIFIER ::= { fcFrad433Reg 29 }
fastcomm-NTNONEA        OBJECT IDENTIFIER ::= { fcFrad433Reg 30 }
fastcomm-NTNONEB        OBJECT IDENTIFIER ::= { fcFrad433Reg 31 }

fastcomm-PRODUCTS       OBJECT IDENTIFIER ::= { fcFrad433Reg 40 }

-- ***************************************************************************
-- the SNMP Agent group
-- Implementation of this group is mandatory for all FastComm
-- systems that implement SNMP

snmpMibVersion OBJECT-TYPE
	SYNTAX  DisplayString (SIZE (0..20))
	ACCESS  read-only
	STATUS  mandatory
    	DESCRIPTION  
		"Version of the Fastcomm MIB"
   	::= { snmpAgent 1 }

snmpAgentIpAddr OBJECT-TYPE
   	SYNTAX  IpAddress
    	ACCESS  read-write
 	STATUS  mandatory
    	DESCRIPTION  
		"The frad's IP address."
    	::= { snmpAgent 2 }

snmpAgentName OBJECT-TYPE
	SYNTAX  DisplayString (SIZE (0..15))
	ACCESS  read-write
	STATUS  mandatory
    	DESCRIPTION  
		"The frad's name."
    	::= { snmpAgent 3 }

snmpAgentGetCommunity OBJECT-TYPE
  	SYNTAX  DisplayString (SIZE (0..20))
   	ACCESS  read-write
   	STATUS  mandatory
   	DESCRIPTION  
		"Configurable community string with Read access rights."
    	::= { snmpAgent 4 }

snmpAgentSetCommunity OBJECT-TYPE
   	SYNTAX  DisplayString (SIZE (0..20))
    	ACCESS  read-write
    	STATUS  mandatory
    	DESCRIPTION  
		"Configurable community string with write access rights."
    	::= { snmpAgent 5 }

snmpAgentDefaultTrapIpAddr OBJECT-TYPE
   	SYNTAX  IpAddress
   	ACCESS  read-write
   	STATUS  mandatory
   	DESCRIPTION  
		"The default IP address of where to send TRAPs."
   	::= { snmpAgent 6 }

snmpAgentTrapSendTable OBJECT-TYPE
   	SYNTAX  SEQUENCE OF SnmpAgentTrapTableEntry
    	ACCESS  not-accessible
    	STATUS  mandatory
   	DESCRIPTION  
		"Each row contains the IP address of the SNMP manager for traps."
    	::= { snmpAgent 7 }

  	SnmpAgentTrapTableEntry ::= SEQUENCE {
		trapTableIndex		INTEGER,
		trapSendIPAddress	IpAddress,
		trapTableStatus		INTEGER
		}

  	snmpAgentTrapTableEntry OBJECT-TYPE	
            SYNTAX  SnmpAgentTrapTableEntry
            ACCESS  not-accessible
            STATUS  mandatory
            DESCRIPTION ""
            INDEX { trapTableIndex }
            ::= { snmpAgentTrapSendTable 1 }

	trapTableIndex OBJECT-TYPE
	    	SYNTAX  INTEGER
	    	ACCESS  read-only
	    	STATUS  mandatory
		DESCRIPTION ""
	    	::=  { snmpAgentTrapTableEntry 1 }

  	trapSendIPAddress OBJECT-TYPE
            SYNTAX  IpAddress 
            ACCESS  read-write
            STATUS  mandatory
            DESCRIPTION ""
            ::= { snmpAgentTrapTableEntry 2 }

    	trapTableStatus OBJECT-TYPE
	    SYNTAX  INTEGER {
	        view   (1),
                add    (2),
	        delete (3),
                modify (4)
		}
            ACCESS  read-write
            STATUS  mandatory
	    DESCRIPTION ""
            ::= { snmpAgentTrapTableEntry 3 }

snmpAgentTrapMessageDesc OBJECT-TYPE
   	SYNTAX  DisplayString
   	ACCESS  read-only
   	STATUS  mandatory
   	DESCRIPTION ""
   	::= { snmpAgent 8 }

snmpTrapDefineTable OBJECT-TYPE

   	SYNTAX  SEQUENCE OF SnmpTrapDefineTableEntry

    	ACCESS  not-accessible

    	STATUS  mandatory

   	DESCRIPTION ""

    	::= { snmpAgent 9 }



  	SnmpTrapDefineTableEntry ::= SEQUENCE {

		trapDefIndex			INTEGER,

		trapDefDesc		      	DisplayString,

		trapDefOid				DisplayString,

            trapDefTrapType         	INTEGER,

            trapDefTriggerType         	INTEGER,

            trapDefSimpleTrigValue    	INTEGER,

            trapDefSimpleTrigCond     	INTEGER,

            trapDefRangeValueHigh     	INTEGER,

            trapDefRangeValueLow      	INTEGER,

            trapDefTimeTrigValue      	INTEGER,

            trapDefTimeDuration       	INTEGER,

            trapDefRelativeOccur      	INTEGER,

            trapDefRelativeOID        	DisplayString,

            trapDefRelativeRefOccur   	INTEGER,

            trapDefReTrigger        	INTEGER,

            trapDefTrigPri          	INTEGER,

		trapDefStatus           	INTEGER

		}



  	snmpTrapDefineTableEntry OBJECT-TYPE	

            SYNTAX  SnmpTrapDefineTableEntry

            ACCESS  not-accessible

            STATUS  mandatory

            DESCRIPTION ""

            INDEX { trapDefIndex }

            ::= { snmpTrapDefineTable 1 }



	trapDefIndex OBJECT-TYPE

	    	SYNTAX  INTEGER

	    	ACCESS  read-only

	    	STATUS  mandatory

		DESCRIPTION ""

	    	::=  { snmpTrapDefineTableEntry 1 }



	trapDefDesc OBJECT-TYPE

	    	SYNTAX  DisplayString

	    	ACCESS  read-write

	    	STATUS  mandatory

		DESCRIPTION ""

	    	::=  { snmpTrapDefineTableEntry 2 }



     	trapDefOid OBJECT-TYPE

	    	SYNTAX  DisplayString

	    	ACCESS  read-write

	    	STATUS  mandatory

		DESCRIPTION ""

	    	::=  { snmpTrapDefineTableEntry 3 }



	trapDefTrapType OBJECT-TYPE

	    	SYNTAX  INTEGER (100..200)

	    	ACCESS  read-write

	    	STATUS  mandatory

		DESCRIPTION ""

	    	::=  { snmpTrapDefineTableEntry 4 }



	trapDefTriggerType OBJECT-TYPE

	    	SYNTAX  INTEGER {

			simple	(1),

			range		(2),

			time		(3),

			relative	(4)

			}

	    	ACCESS  read-write

	    	STATUS  mandatory

		DESCRIPTION ""

	    	::=  { snmpTrapDefineTableEntry 5 }



	trapDefSimpleTrigValue OBJECT-TYPE

	    	SYNTAX  INTEGER 

	    	ACCESS  read-write

	    	STATUS  mandatory

		DESCRIPTION ""

	    	::=  { snmpTrapDefineTableEntry 6 }



	trapDefSimpleTrigCond OBJECT-TYPE

	    	SYNTAX  INTEGER {

			lESS-THAN		(1),

 			eQUAL-TO		(2),

			gREATER-THAN	(3)

			}

	    	ACCESS  read-write

	    	STATUS  mandatory

		DESCRIPTION ""

	    	::=  { snmpTrapDefineTableEntry 7 }



	trapDefRangeValueHigh OBJECT-TYPE

	    	SYNTAX  INTEGER 

	    	ACCESS  read-write

	    	STATUS  mandatory

		DESCRIPTION ""

	    	::=  { snmpTrapDefineTableEntry 8 }



	trapDefRangeValueLow OBJECT-TYPE

	    	SYNTAX  INTEGER 

	    	ACCESS  read-write

	    	STATUS  mandatory

		DESCRIPTION ""

	    	::=  { snmpTrapDefineTableEntry 9 }



	trapDefTimeTrigValue OBJECT-TYPE

	    	SYNTAX  INTEGER 

	    	ACCESS  read-write

	    	STATUS  mandatory

		DESCRIPTION ""

	    	::=  { snmpTrapDefineTableEntry 10 }



	trapDefTimeDuration OBJECT-TYPE

	    	SYNTAX  INTEGER 

	    	ACCESS  read-write

	    	STATUS  mandatory

		DESCRIPTION ""

	    	::=  { snmpTrapDefineTableEntry 11 }



	trapDefRelativeOccur OBJECT-TYPE

	    	SYNTAX  INTEGER 

	    	ACCESS  read-write

	    	STATUS  mandatory

		DESCRIPTION ""

	    	::=  { snmpTrapDefineTableEntry 12 }



	trapDefRelativeOID OBJECT-TYPE

	    	SYNTAX  DisplayString

	    	ACCESS  read-write

	    	STATUS  mandatory

		DESCRIPTION ""

	    	::=  { snmpTrapDefineTableEntry 13 }



	trapDefRelativeRefOccur OBJECT-TYPE

	    	SYNTAX  INTEGER 

	    	ACCESS  read-write

	    	STATUS  mandatory

		DESCRIPTION ""

	    	::=  { snmpTrapDefineTableEntry 14 }



	trapDefReTrigger OBJECT-TYPE

	    	SYNTAX  INTEGER {

			manual		(1),

 			automatic		(2)

			}

	    	ACCESS  read-write

	    	STATUS  mandatory

		DESCRIPTION ""

	    	::=  { snmpTrapDefineTableEntry 15 }



	trapDefTrigPri OBJECT-TYPE

	    	SYNTAX  INTEGER {

			normal		(1),

 			critical		(2)

			}

	    	ACCESS  read-write

	    	STATUS  mandatory

		DESCRIPTION ""

	    	::=  { snmpTrapDefineTableEntry 16 }



    	trapDefStatus OBJECT-TYPE

	    	SYNTAX  INTEGER {

	    		view   (1),

                	add    (2),

	        	delete (3),

                	modify (4)

		}

            ACCESS  read-write

            STATUS  mandatory

	    	DESCRIPTION ""

            ::= { snmpTrapDefineTableEntry 17 }

END
