--
-- DVB-MGSIGNALCHARACTERISTICS-MIB.my
-- MIB generated by MG-SOFT Visual MIB Builder Version 2.5 Build 225
-- Friday, November 09, 2001 at 15:02:25
--

	DVB-MGSIGNALCHARACTERISTICS-MIB DEFINITIONS ::= BEGIN

		IMPORTS 
			PIDPlusOne, FloatingPoint, ServiceId, InputNumber, RateStatus, 
			DeliverySystemType, Modulation			
				FROM DVB-MGTR101290-MIB			
			OBJECT-GROUP, MODULE-COMPLIANCE, NOTIFICATION-GROUP			
				FROM SNMPv2-CONF			
			enterprises, Unsigned32, OBJECT-TYPE, MODULE-IDENTITY, NOTIFICATION-TYPE			
				FROM SNMPv2-SMI			
			DateAndTime, TruthValue, TEXTUAL-CONVENTION			
				FROM SNMPv2-TC;
	
	
		mgSignalCharacteristics MODULE-IDENTITY
			LAST-UPDATED "200111071400Z"
			ORGANIZATION
				"DVB"
			CONTACT-INFO
				"DVB project
				European Broadcasting Union
				CH-1218 GRAND SACONNEX (Geneva)
				Switzerland
				Tel: +41 22 717 21 11
				Fax: +41 22 717 24 81"
			DESCRIPTION
				"DVB Measurement Group Signal Characteristics MIB module.
				
				This mgSignalCharacteristics module contains Transport Stream structure information
				and RF characteristics information to assist in interpreting measurements and tests,
				in particular those specified in TR 101 290."
			::= { mg 3 }
		
	
--
-- Textual conventions
--
	
		CASystemID ::= TEXTUAL-CONVENTION
			DISPLAY-HINT
				"x"
			STATUS current
			DESCRIPTION
				"Representation of CA_system_ID as found in a CA_descriptor.
				A value of -1 means that the CA_system_ID is unknown."
			SYNTAX INTEGER (-1..65535)
			
		EncryptionState ::= TEXTUAL-CONVENTION
			STATUS current
			DESCRIPTION
				"Used to indicate whether a service or PID is encrypted or unencrypted.
				The value unknown means that the information is not available, for
				example because the instrument does not gather this information."
			SYNTAX INTEGER
				{
				unencrypted(1),
				encrypted(2),
				unknown(3)
				}
			
		GuardInterval ::= TEXTUAL-CONVENTION
			STATUS current
			DESCRIPTION
				"Guard interval used in the DVB-T modulation scheme."
			SYNTAX INTEGER
				{
				guard1over32(1),
				guard1over16(2),
				guard1over8(3),
				guard1over4(4)
				}
			
		InnerCodeRate ::= TEXTUAL-CONVENTION
			STATUS current
			DESCRIPTION
				"This is used to specify the inner (Viterbi) code rate of
				a transmission."
			SYNTAX INTEGER
				{
				rateNone(1),
				rate1over2(2),
				rate2over3(3),
				rate3over4(4),
				rate5over6(5),
				rate7over8(6)
				}
			
		NetworkID ::= TEXTUAL-CONVENTION
			DISPLAY-HINT
				"x"
			STATUS current
			DESCRIPTION
				"This represents a network_id or original_network_id
				as used in the SI tables. A value of -1 indicates that
				value is unknown."
			SYNTAX INTEGER (-1..65535)
			
		PID ::= TEXTUAL-CONVENTION
			DISPLAY-HINT
				"x"
			STATUS current
			DESCRIPTION
				"An object of type PID directly represents an MPEG-2 PID number"
			REFERENCE
				"ISO 13818-1 2.1.32"
			SYNTAX INTEGER (0..8191)
			
		ReadableString ::= TEXTUAL-CONVENTION
			DISPLAY-HINT
				"255t"
			STATUS current
			DESCRIPTION
				"An octet string containing a human-readable string.  This
				string may have originally been encoded as specified
				in EN 300 468 Annex A, but this is not a requirement.
				
				To maintain generality, the information is represented
				using the ISO/IEC IS 10646-1 character set, encoded as an
				octet string using the UTF-8 transformation format
				described in RFC2279.
				
				Control codes are interpreted as specified in EN 300 468
				Annex A, section A.1.  The interpretation of other control
				codes is undefined.
				
				For information encoded in 7-bit US-ASCII, the UTF-8
				encoding is identical to the US-ASCII encoding.
				
				UTF-8 may require multiple bytes to represent a single
				character/code point; thus the length of this object in
				octets may be different from the number of characters
				encoded.  Similarly, size constraints refer to the number
				of encoded octets, not the number of characters represented
				by an encoding."
			REFERENCE
				"RFC 2279"
			SYNTAX OCTET STRING (SIZE (0..255))
			
		TerrestrialTransmissionMode ::= TEXTUAL-CONVENTION
			STATUS current
			DESCRIPTION
				"Used to inform whether a DVB-T transmission uses 2k or 8k mode."
			SYNTAX INTEGER
				{
				carriers2k(1),
				carriers8k(2)
				}
			
	
--
-- Node definitions
--
	
		dvb OBJECT IDENTIFIER ::= { enterprises 2696 }
		
		mg OBJECT IDENTIFIER ::= { dvb 3 }
		
		mgSignalCharacteristicsObjects OBJECT IDENTIFIER ::= { mgSignalCharacteristics 1 }
		
-- mgTSStructure provides information about the structure of
-- the Transport Stream.  It reports the structure as defined
-- by the PSI and SI tables in the Transport Stream.  For
-- example the mgPIDType object reports the type as defined
-- by the PMT; the measuring instrument is not expected to
-- check the actual contents of the PID.
		mgTSStructure OBJECT IDENTIFIER ::= { mgSignalCharacteristicsObjects 1 }
		
		mgTSStructureTrap OBJECT IDENTIFIER ::= { mgTSStructure 1 }
		
-- This prefix is necessary to satisfy the requirement of RFC 2578
-- section 8.5 that 'the next to last sub-identifier in the name of
-- any newly-defined notification must have the value zero'.
		structureTrapPrefix OBJECT IDENTIFIER ::= { mgTSStructureTrap 0 }
		
		tsStructureChangeTrap NOTIFICATION-TYPE
			OBJECTS { structureTrapInput, structureTrapControlOID, structureTrapControlChangeTime }
			STATUS current
			DESCRIPTION
				"Trap which is sent when any value within the mgTSStructure branch of
				this MIB changes.  Transmission of the trap is subject to rate control
				through the structureTrapControlRateStatus object."
			::= { structureTrapPrefix 1 }
		
		structureTrapControlTable OBJECT-TYPE
			SYNTAX SEQUENCE OF StructureTrapControlEntry
			MAX-ACCESS not-accessible
			STATUS current
			DESCRIPTION
				"Per-input table of values which control the generation of
				tsStructureChangeTrap traps."
			::= { mgTSStructureTrap 1 }
		
		structureTrapControlEntry OBJECT-TYPE
			SYNTAX StructureTrapControlEntry
			MAX-ACCESS not-accessible
			STATUS current
			DESCRIPTION
				"Row specification"
			INDEX { structureTrapControlInputNumber }
			::= { structureTrapControlTable 1 }
		
		StructureTrapControlEntry ::=
			SEQUENCE { 
				structureTrapControlInputNumber
					InputNumber,
				structureTrapControlOID
					OBJECT IDENTIFIER,
				structureTrapControlChangeTime
					DateAndTime,
				structureTrapControlRateStatus
					RateStatus,
				structureTrapControlPeriod 
					Unsigned32
			 }

		structureTrapControlInputNumber OBJECT-TYPE
			SYNTAX InputNumber
			MAX-ACCESS not-accessible
			STATUS current
			DESCRIPTION
				"Transport Stream input to which the trap control objects apply."
			::= { structureTrapControlEntry 1 }
		
		structureTrapControlOID OBJECT-TYPE
			SYNTAX OBJECT IDENTIFIER
			MAX-ACCESS accessible-for-notify
			STATUS current
			DESCRIPTION
				"This object holds the OID of the object within the mgTSStructure
				branch of the MIB whose change triggered the trap. It is present
				for the formal purpose of defining the variable bindings returned
				with the tsStructureChangeTrap.  It is not accessible for normal
				reading."
			::= { structureTrapControlEntry 2 }
		
		structureTrapControlChangeTime OBJECT-TYPE
			SYNTAX DateAndTime
			MAX-ACCESS accessible-for-notify
			STATUS current
			DESCRIPTION
				"This indicates the time when the change which triggered the trap
				occurred. It is present for the formal purpose of defining the
				variable bindings returned with the tsStructureChangeTrap.  It
				is not accessible for normal reading."
			::= { structureTrapControlEntry 3 }
		
		structureTrapControlRateStatus OBJECT-TYPE
			SYNTAX RateStatus
			MAX-ACCESS read-write
			STATUS current
			DESCRIPTION
				"This object is used for rate control of traps, preventing
				overload of the management network by transmission of an
				excessive number of traps. The value 'disabled' means that
				traps are never sent. The value 'enabled' means that a
				trap will be sent when triggered.
				
				When a trap is sent, the agent changes the value of this
				object to 'enabledThrottled'. In this state the agent will
				not send any more traps. The agent automatically changes
				the value back to 'enabled' when the time specified by
				trapControlPeriod expires. A management application may
				set the value to 'enabled' at any time, but must never set
				the value to 'enabledThrottled'."
			::= { structureTrapControlEntry 4 }
		
		structureTrapControlPeriod  OBJECT-TYPE
			SYNTAX Unsigned32 (0..3600000)
			UNITS "millisecond"
			MAX-ACCESS read-write
			STATUS current
			DESCRIPTION
				"The agent will ensure that the interval between sending traps is
				no shorter than this time period (unless overridden by the manager)."
			::= { structureTrapControlEntry 5 }
		
		structureTrapInput OBJECT-TYPE
			SYNTAX InputNumber
			MAX-ACCESS accessible-for-notify
			STATUS current
			DESCRIPTION
				"The Transport Stream input whose change triggered the current
				trap. This information can also be obtained by analysing the
				structureTrapControlOID, but structureTrapInput provides the
				information directly.
				
				This object is present for the formal purpose of defining the
				variable bindings returned with the tsStructureChangeTrap.
				It is not accessible for normal reading."
			::= { mgTSStructureTrap 2 }
		
		mgTSTable OBJECT-TYPE
			SYNTAX SEQUENCE OF MgTSEntry
			MAX-ACCESS not-accessible
			STATUS current
			DESCRIPTION
				"PSI/SI information relating to the whole Transport Stream"
			::= { mgTSStructure 2 }
		
		mgTSEntry OBJECT-TYPE
			SYNTAX MgTSEntry
			MAX-ACCESS not-accessible
			STATUS current
			DESCRIPTION
				"Row specification"
			INDEX { mgTSInputNumber }
			::= { mgTSTable 1 }
		
		MgTSEntry ::=
			SEQUENCE { 
				mgTSInputNumber
					InputNumber,
				mgTSId
					INTEGER,
				mgTSOriginalNetworkID
					NetworkID,
				mgTSNetworkID
					NetworkID,
				mgTSNetworkName
					ReadableString
			 }

		mgTSInputNumber OBJECT-TYPE
			SYNTAX InputNumber
			MAX-ACCESS not-accessible
			STATUS current
			DESCRIPTION
				"The physical input on which this Transport Stream appears"
			::= { mgTSEntry 1 }
		
		mgTSId OBJECT-TYPE
			SYNTAX INTEGER (-1..65535)
			MAX-ACCESS read-only
			STATUS current
			DESCRIPTION
				"The transport_stream_id for this Transport Stream as read
				from the PAT.  If the transport_stream_id is unknown, this
				object has the value -1."
			REFERENCE
				"ISO/IEC 13818-1 2.4.4.3"
			::= { mgTSEntry 2 }
		
		mgTSOriginalNetworkID OBJECT-TYPE
			SYNTAX NetworkID
			MAX-ACCESS read-only
			STATUS current
			DESCRIPTION
				"The original_network_id for this Transport Stream.
				
				This is found by reading the transport_stream_id from the PAT.
				This transport_stream_id is then located in the
				transport_stream_loop of the NIT (actual transport stream).
				The value of mgTSOriginalNetworkID is the original_network_id
				found in this instance of the loop."
			REFERENCE
				"ISO/IEC 13818-1 5.2.1"
			::= { mgTSEntry 3 }
		
		mgTSNetworkID OBJECT-TYPE
			SYNTAX NetworkID
			MAX-ACCESS read-only
			STATUS current
			DESCRIPTION
				"The network_id for this Transport Stream as read from the
				NIT.  This is found by reading the network_id in the NIT
				(actual_network)"
			REFERENCE
				"ISO/IEC 13818-1 5.2.1"
			::= { mgTSEntry 4 }
		
		mgTSNetworkName OBJECT-TYPE
			SYNTAX ReadableString
			MAX-ACCESS read-only
			STATUS current
			DESCRIPTION
				"network_name for this Transport Stream as read from the NIT.
				This is found by reading the network name descriptor in the
				NIT (actual_network).
				
				If the network_name is unknown, the value of this object is
				a zero length string."
			REFERENCE
				"EN 300 468 6.2.24 and 6.2.21"
			::= { mgTSEntry 5 }
		
		mgServiceTable OBJECT-TYPE
			SYNTAX SEQUENCE OF MgServiceEntry
			MAX-ACCESS not-accessible
			STATUS current
			DESCRIPTION
				"PSI/SI information relating to each service within the Transport
				Stream. A service is included in the table if it is found in both
				the PAT and the PMT."
			::= { mgTSStructure 3 }
		
		mgServiceEntry OBJECT-TYPE
			SYNTAX MgServiceEntry
			MAX-ACCESS not-accessible
			STATUS current
			DESCRIPTION
				"Row specification"
			INDEX { mgServiceNumber, mgServiceInputNumber }
			::= { mgServiceTable 1 }
		
		MgServiceEntry ::=
			SEQUENCE { 
				mgServiceInputNumber
					InputNumber,
				mgServiceNumber
					ServiceId,
				mgServiceType
					INTEGER,
				mgServiceName
					ReadableString,
				mgServiceProviderName
					ReadableString,
				mgServicePMTPID
					PID,
				mgServicePCRPID
					PID,
				mgServiceCondAccess
					EncryptionState,
				mgServiceEITComponentDescriptor
					ReadableString
			 }

		mgServiceInputNumber OBJECT-TYPE
			SYNTAX InputNumber
			MAX-ACCESS not-accessible
			STATUS current
			DESCRIPTION
				"The physical input on which this Transport Stream appears"
			::= { mgServiceEntry 1 }
		
		mgServiceNumber OBJECT-TYPE
			SYNTAX ServiceId
			MAX-ACCESS not-accessible
			STATUS current
			DESCRIPTION
				"The program_number/service_id to which the information
				in the rest of the row applies."
			::= { mgServiceEntry 2 }
		
		mgServiceType OBJECT-TYPE
			SYNTAX INTEGER (-1..255)
			MAX-ACCESS read-only
			STATUS current
			DESCRIPTION
				"The service_type from the service_descriptor field in the SDT.
				A value of -1 indicates that the service_type is unknown."
			REFERENCE
				"EN 300 468 6.2.30"
			::= { mgServiceEntry 3 }
		
		mgServiceName OBJECT-TYPE
			SYNTAX ReadableString
			MAX-ACCESS read-only
			STATUS current
			DESCRIPTION
				"The service_name from the service_descriptor in the SDT.
				If this information is not available, the value of this
				object will be a zero length string."
			REFERENCE
				"EN 300 468 6.2.22 and 6.2.30"
			::= { mgServiceEntry 4 }
		
		mgServiceProviderName OBJECT-TYPE
			SYNTAX ReadableString
			MAX-ACCESS read-only
			STATUS current
			DESCRIPTION
				"The service_provider_name from the service_descriptor in the SDT.
				If this information is not available, the value of this object
				will be a zero length string."
			REFERENCE
				"EN 300 468 6.2.22 and 6.2.30"
			::= { mgServiceEntry 5 }
		
		mgServicePMTPID OBJECT-TYPE
			SYNTAX PID
			MAX-ACCESS read-only
			STATUS current
			DESCRIPTION
				"The PMT PID for this service as read from the PAT"
			REFERENCE
				"ISO/IEC 13838-1 2.4.4.3"
			::= { mgServiceEntry 6 }
		
		mgServicePCRPID OBJECT-TYPE
			SYNTAX PID
			MAX-ACCESS read-only
			STATUS current
			DESCRIPTION
				"The PCR PID for this service as read from the PMT"
			REFERENCE
				"ISO/IEC 13838-1 2.4.4.8"
			::= { mgServiceEntry 7 }
		
		mgServiceCondAccess OBJECT-TYPE
			SYNTAX EncryptionState
			MAX-ACCESS read-only
			STATUS current
			DESCRIPTION
				"The encryption state of the service, derived from the
				free_CA_mode bit in the SDT"
			REFERENCE
				"EN 300 468 5.2.3"
			::= { mgServiceEntry 8 }
		
		mgServiceEITComponentDescriptor OBJECT-TYPE
			SYNTAX ReadableString
			MAX-ACCESS read-only
			STATUS current
			DESCRIPTION
				"This is a text description of the main elementary stream
				in the service as read from the component_descriptor
				in the EIT. If this information is not available, the
				value of this object will be a zero length string."
			REFERENCE
				"EN 300 468 6.2.7"
			::= { mgServiceEntry 9 }
		
		mgPIDTable OBJECT-TYPE
			SYNTAX SEQUENCE OF MgPIDEntry
			MAX-ACCESS not-accessible
			STATUS current
			DESCRIPTION
				"PSI/SI information relating to each PID in each service in
				the Transport Stream. A PID is included in the table if it
				listed as an elementary_PID in the PMT for the service."
			::= { mgTSStructure 4 }
		
		mgPIDEntry OBJECT-TYPE
			SYNTAX MgPIDEntry
			MAX-ACCESS not-accessible
			STATUS current
			DESCRIPTION
				"Row specification"
			INDEX { mgPIDServiceNumber, mgPIDNumber, mgPIDInputNumber }
			::= { mgPIDTable 1 }
		
		MgPIDEntry ::=
			SEQUENCE { 
				mgPIDInputNumber
					InputNumber,
				mgPIDServiceNumber
					ServiceId,
				mgPIDNumber
					PIDPlusOne,
				mgPIDType
					INTEGER,
				mgPIDCondAccess
					EncryptionState
			 }

		mgPIDInputNumber OBJECT-TYPE
			SYNTAX InputNumber
			MAX-ACCESS not-accessible
			STATUS current
			DESCRIPTION
				"The physical input on which this Transport Stream appears"
			::= { mgPIDEntry 1 }
		
		mgPIDServiceNumber OBJECT-TYPE
			SYNTAX ServiceId
			MAX-ACCESS not-accessible
			STATUS current
			DESCRIPTION
				"The program_number/service_id to which the row information applies."
			::= { mgPIDEntry 2 }
		
		mgPIDNumber OBJECT-TYPE
			SYNTAX PIDPlusOne
			MAX-ACCESS not-accessible
			STATUS current
			DESCRIPTION
				"The PID, included in the service identified by
				mgPIDServiceNumber, to which the information in the
				row applies."
			::= { mgPIDEntry 3 }
		
		mgPIDType OBJECT-TYPE
			SYNTAX INTEGER (0..255)
			MAX-ACCESS read-only
			STATUS current
			DESCRIPTION
				"The stream_type read from the PMT"
			REFERENCE
				"ISO/IEC 13818-1 Table 2-29"
			::= { mgPIDEntry 4 }
		
		mgPIDCondAccess OBJECT-TYPE
			SYNTAX EncryptionState
			MAX-ACCESS read-only
			STATUS current
			DESCRIPTION
				"The encryption state of the PID. This is deduced from the
				values of the transport_scrambling_control field in the
				Transport Stream packet headers for this PID."
			REFERENCE
				"ISO/IEC 13818-1 2.4.3.2"
			::= { mgPIDEntry 5 }
		
		mgEMMTable OBJECT-TYPE
			SYNTAX SEQUENCE OF MgEMMEntry
			MAX-ACCESS not-accessible
			STATUS current
			DESCRIPTION
				"This table identifies the PIDs occupied by EMMs"
			::= { mgTSStructure 5 }
		
		mgEMMEntry OBJECT-TYPE
			SYNTAX MgEMMEntry
			MAX-ACCESS not-accessible
			STATUS current
			DESCRIPTION
				"Row specification"
			INDEX { mgEMMInputNumber, mgEMMCaPID }
			::= { mgEMMTable 1 }
		
		MgEMMEntry ::=
			SEQUENCE { 
				mgEMMInputNumber
					InputNumber,
				mgEMMCaPID
					PIDPlusOne,
				mgEMMCASystemID
					CASystemID
			 }

		mgEMMInputNumber OBJECT-TYPE
			SYNTAX InputNumber
			MAX-ACCESS not-accessible
			STATUS current
			DESCRIPTION
				"The physical input on which this Transport Stream appears"
			::= { mgEMMEntry 1 }
		
		mgEMMCaPID OBJECT-TYPE
			SYNTAX PIDPlusOne
			MAX-ACCESS not-accessible
			STATUS current
			DESCRIPTION
				"The CA_PID from the CA_descriptor in the CAT plus one.
				This indicates the PID on which the EMM is found."
			REFERENCE
				"ISO/IEC 13818-1 2.6.16"
			::= { mgEMMEntry 2 }
		
		mgEMMCASystemID OBJECT-TYPE
			SYNTAX CASystemID
			MAX-ACCESS read-only
			STATUS current
			DESCRIPTION
				"The CA_system_ID from the CA_descriptor in the CAT"
			REFERENCE
				"ISO/IEC 13818-1 2.6.16"
			::= { mgEMMEntry 3 }
		
		mgServiceECMTable OBJECT-TYPE
			SYNTAX SEQUENCE OF MgServiceECMEntry
			MAX-ACCESS not-accessible
			STATUS current
			DESCRIPTION
				"This table identifies the PIDs occupied by ECMs relating to
				a whole service.  This information is found in the first
				descriptor loop of a TS_program_map_section."
			::= { mgTSStructure 6 }
		
		mgServiceECMEntry OBJECT-TYPE
			SYNTAX MgServiceECMEntry
			MAX-ACCESS not-accessible
			STATUS current
			DESCRIPTION
				"Row specification"
			INDEX { mgServiceECMInputNumber, mgServiceECMServiceNumber }
			::= { mgServiceECMTable 1 }
		
		MgServiceECMEntry ::=
			SEQUENCE { 
				mgServiceECMInputNumber
					InputNumber,
				mgServiceECMServiceNumber
					ServiceId,
				mgServiceECMCaPID
					PIDPlusOne,
				mgServiceECMCASystemID
					CASystemID
			 }

		mgServiceECMInputNumber OBJECT-TYPE
			SYNTAX InputNumber
			MAX-ACCESS not-accessible
			STATUS current
			DESCRIPTION
				"The physical input on which this Transport Stream appears"
			::= { mgServiceECMEntry 1 }
		
		mgServiceECMServiceNumber OBJECT-TYPE
			SYNTAX ServiceId
			MAX-ACCESS not-accessible
			STATUS current
			DESCRIPTION
				"The program_number/service_id to which the information
				in the row applies."
			::= { mgServiceECMEntry 2 }
		
		mgServiceECMCaPID OBJECT-TYPE
			SYNTAX PIDPlusOne
			MAX-ACCESS not-accessible
			STATUS current
			DESCRIPTION
				"The CA_PID from the CA_descriptor in the PMT plus one.
				This indicates the PID on which the ECM is found."
			REFERENCE
				"ISO/IEC 13818-1 2.6.16"
			::= { mgServiceECMEntry 3 }
		
		mgServiceECMCASystemID OBJECT-TYPE
			SYNTAX CASystemID
			MAX-ACCESS read-only
			STATUS current
			DESCRIPTION
				"The CA_system_ID from the CA_descriptor in the PMT"
			REFERENCE
				"ISO/IEC 13818-1 2.6.16"
			::= { mgServiceECMEntry 4 }
		
		mgPIDECMTable OBJECT-TYPE
			SYNTAX SEQUENCE OF MgPIDECMEntry
			MAX-ACCESS not-accessible
			STATUS current
			DESCRIPTION
				"This table identifies the PIDs occupied by ECMs related to
				a single elementary stream.  This information is found in
				the elementary stream specific descriptor loop of a
				TS_program_map_section."
			::= { mgTSStructure 7 }
		
		mgPIDECMEntry OBJECT-TYPE
			SYNTAX MgPIDECMEntry
			MAX-ACCESS not-accessible
			STATUS current
			DESCRIPTION
				"Row specification"
			INDEX { mgPIDECMInputNumber, mgPIDECMServiceNumber, mgPIDECMPID }
			::= { mgPIDECMTable 1 }
		
		MgPIDECMEntry ::=
			SEQUENCE { 
				mgPIDECMInputNumber
					InputNumber,
				mgPIDECMServiceNumber
					ServiceId,
				mgPIDECMPID
					PIDPlusOne,
				mgPIDECMCaPID
					PIDPlusOne,
				mgPIDECMCASystemID
					CASystemID
			 }

		mgPIDECMInputNumber OBJECT-TYPE
			SYNTAX InputNumber
			MAX-ACCESS not-accessible
			STATUS current
			DESCRIPTION
				"The physical input on which this Transport Stream appears"
			::= { mgPIDECMEntry 1 }
		
		mgPIDECMServiceNumber OBJECT-TYPE
			SYNTAX ServiceId
			MAX-ACCESS not-accessible
			STATUS current
			DESCRIPTION
				"The program_number/service_id to which the information
				in the row applies."
			::= { mgPIDECMEntry 2 }
		
		mgPIDECMPID OBJECT-TYPE
			SYNTAX PIDPlusOne
			MAX-ACCESS not-accessible
			STATUS current
			DESCRIPTION
				"The elementary stream PID which is unscrambled by this ECM."
			::= { mgPIDECMEntry 3 }
		
		mgPIDECMCaPID OBJECT-TYPE
			SYNTAX PIDPlusOne
			MAX-ACCESS not-accessible
			STATUS current
			DESCRIPTION
				"The CA_PID from the CA_descriptor in the PMT plus one.
				This indicates the PID on which the ECM is found."
			REFERENCE
				"ISO/IEC 13818-1 2.6.16"
			::= { mgPIDECMEntry 4 }
		
		mgPIDECMCASystemID OBJECT-TYPE
			SYNTAX CASystemID
			MAX-ACCESS read-only
			STATUS current
			DESCRIPTION
				"The CA_system_ID from the CA_descriptor in the PMT"
			REFERENCE
				"ISO/IEC 13818-1 2.6.16"
			::= { mgPIDECMEntry 5 }
		
		mgNITDeliverySystemTable OBJECT-TYPE
			SYNTAX SEQUENCE OF MgNITDeliverySystemEntry
			MAX-ACCESS not-accessible
			STATUS current
			DESCRIPTION
				"Delivery system information for this Transport Stream read from
				the delivery system descriptors in the NIT.
				
				This information is found by reading the transport_stream_id
				from the PAT. This transport_stream_id is then located in the
				transport_stream_loop of the NIT (actual_network). The delivery
				system descriptor found in this instance of the loop is
				analysed to obtain the values in this table."
			REFERENCE
				"EN 300 468 section 6.2.12"
			::= { mgTSStructure 8 }
		
		mgNITDeliverySystemEntry OBJECT-TYPE
			SYNTAX MgNITDeliverySystemEntry
			MAX-ACCESS not-accessible
			STATUS current
			DESCRIPTION
				"Row specification"
			INDEX { mgNITDSInputNumber }
			::= { mgNITDeliverySystemTable 1 }
		
		MgNITDeliverySystemEntry ::=
			SEQUENCE { 
				mgNITDSInputNumber
					InputNumber,
				mgNITDSSystemType
					DeliverySystemType,
				mgNITDSFrequency
					FloatingPoint,
				mgNITDSFecOuter
					INTEGER,
				mgNITDSCableModulation
					INTEGER,
				mgNITDSSymbolRate
					Unsigned32,
				mgNITDSFecInner
					INTEGER,
				mgNITDSOrbitalPosition
					FloatingPoint,
				mgNITDSWestEastFlag
					INTEGER,
				mgNITDSPolarization
					INTEGER,
				mgNITDSSatelliteModulation
					INTEGER,
				mgNITDSBandwidth
					INTEGER,
				mgNITDSConstellation
					INTEGER,
				mgNITDSHierarchyInformation
					INTEGER,
				mgNITDSCodeRateHPStream
					INTEGER,
				mgNITDSCodeRateLPStream
					INTEGER,
				mgNITDSGuardInterval
					INTEGER,
				mgNITDSTransmissionMode
					INTEGER,
				mgNITDSOtherFrequencyFlag
					INTEGER
			 }

		mgNITDSInputNumber OBJECT-TYPE
			SYNTAX InputNumber
			MAX-ACCESS not-accessible
			STATUS current
			DESCRIPTION
				"The physical input on which this Transport Stream appears"
			::= { mgNITDeliverySystemEntry 1 }
		
		mgNITDSSystemType OBJECT-TYPE
			SYNTAX DeliverySystemType
			MAX-ACCESS read-only
			STATUS current
			DESCRIPTION
				"Which delivery system is in use.  The value of this object
				determines which other objects in this table row have
				valid values.  If this object has the value 'unknown' none
				of the other objects in this table row have valid values."
			::= { mgNITDeliverySystemEntry 2 }
		
		mgNITDSFrequency OBJECT-TYPE
			SYNTAX FloatingPoint
			UNITS "MHz"
			MAX-ACCESS read-only
			STATUS current
			DESCRIPTION
				"The frequency or centre_frequency for the transmission
				expressed in MHz
				Valid for: cable, satellite, terrestrial"
			REFERENCE
				"EN 300 468 6.2.12"
			::= { mgNITDeliverySystemEntry 3 }
		
		mgNITDSFecOuter OBJECT-TYPE
			SYNTAX INTEGER (0..15)
			MAX-ACCESS read-only
			STATUS current
			DESCRIPTION
				"The Outer Forward Error Correction Code, values as
				specified for the cable_delivery_system_descriptor.
				Valid for: cable"
			REFERENCE
				"EN 300 468 Table 31"
			::= { mgNITDeliverySystemEntry 4 }
		
		mgNITDSCableModulation OBJECT-TYPE
			SYNTAX INTEGER (0..255)
			MAX-ACCESS read-only
			STATUS current
			DESCRIPTION
				"Modulation scheme, values as specified for the
				cable_delivery_system_descriptor
				Valid for: cable"
			REFERENCE
				"EN 300 468 Table 32"
			::= { mgNITDeliverySystemEntry 5 }
		
		mgNITDSSymbolRate OBJECT-TYPE
			SYNTAX Unsigned32
			UNITS "symbol/s"
			MAX-ACCESS read-only
			STATUS current
			DESCRIPTION
				"The symbol rate in symbols per second
				Valid for: cable, satellite"
			REFERENCE
				"EN 300 468 6.2.12.1 and 6.2.12.2"
			::= { mgNITDeliverySystemEntry 6 }
		
		mgNITDSFecInner OBJECT-TYPE
			SYNTAX INTEGER (0..15)
			MAX-ACCESS read-only
			STATUS current
			DESCRIPTION
				"The inner FEC scheme, values as specified for the
				cable_delivery_system_descriptor
				Valid for: cable, satellite"
			REFERENCE
				"EN 300 468 Table 33"
			::= { mgNITDeliverySystemEntry 7 }
		
		mgNITDSOrbitalPosition OBJECT-TYPE
			SYNTAX FloatingPoint
			UNITS "degree"
			MAX-ACCESS read-only
			STATUS current
			DESCRIPTION
				"The orbital position in degrees
				Valid for: satellite"
			REFERENCE
				"EN 300 468 6.2.12.2"
			::= { mgNITDeliverySystemEntry 8 }
		
		mgNITDSWestEastFlag OBJECT-TYPE
			SYNTAX INTEGER
				{
				west(0),
				east(1)
				}
			MAX-ACCESS read-only
			STATUS current
			DESCRIPTION
				"Orbital position direction: east (1) or west (0).
				Valid for: satellite"
			::= { mgNITDeliverySystemEntry 9 }
		
		mgNITDSPolarization OBJECT-TYPE
			SYNTAX INTEGER (0..3)
			MAX-ACCESS read-only
			STATUS current
			DESCRIPTION
				"Polarization, values as specified for the
				satellite_delivery_system_descriptor
				Valid for: satellite"
			REFERENCE
				"EN 300 468 Table 35"
			::= { mgNITDeliverySystemEntry 10 }
		
		mgNITDSSatelliteModulation OBJECT-TYPE
			SYNTAX INTEGER (0..31)
			MAX-ACCESS read-only
			STATUS current
			DESCRIPTION
				"Modulation scheme, values as specified for the
				satellite_delivery_system_descriptor
				Valid for: satellite"
			REFERENCE
				"EN 300 468 Table 36"
			::= { mgNITDeliverySystemEntry 11 }
		
		mgNITDSBandwidth OBJECT-TYPE
			SYNTAX INTEGER (0..7)
			MAX-ACCESS read-only
			STATUS current
			DESCRIPTION
				"The bandwidth, values as specified for the
				terrestrial_delivery_system_descriptor
				Valid for: terrestrial"
			REFERENCE
				"EN 300 468 Table 38"
			::= { mgNITDeliverySystemEntry 12 }
		
		mgNITDSConstellation OBJECT-TYPE
			SYNTAX INTEGER (0..3)
			MAX-ACCESS read-only
			STATUS current
			DESCRIPTION
				"The modulation constellation: values as specified for
				the terrestrial_delivery_system_descriptor
				Valid for: terrestrial"
			REFERENCE
				"EN 300 468 Table 39"
			::= { mgNITDeliverySystemEntry 13 }
		
		mgNITDSHierarchyInformation OBJECT-TYPE
			SYNTAX INTEGER (0..7)
			MAX-ACCESS read-only
			STATUS current
			DESCRIPTION
				"Hierarchy Information: values as specified for the
				terrestrial_delivery_system_descriptor
				Valid for: terrestrial"
			REFERENCE
				"EN 300 468 Table 40"
			::= { mgNITDeliverySystemEntry 14 }
		
		mgNITDSCodeRateHPStream OBJECT-TYPE
			SYNTAX INTEGER (0..7)
			MAX-ACCESS read-only
			STATUS current
			DESCRIPTION
				"The code rate for the high priority stream: values as specified
				for the terrestrial_delivery_system_descriptor
				Valid for: terrestrial"
			REFERENCE
				"EN 300 468 Table 41"
			::= { mgNITDeliverySystemEntry 15 }
		
		mgNITDSCodeRateLPStream OBJECT-TYPE
			SYNTAX INTEGER (0..7)
			MAX-ACCESS read-only
			STATUS current
			DESCRIPTION
				"The code rate for low priority stream: values as specified
				for the terrestrial_delivery_system_descriptor
				Valid for: terrestrial"
			REFERENCE
				"EN 300 468 Table 41"
			::= { mgNITDeliverySystemEntry 16 }
		
		mgNITDSGuardInterval OBJECT-TYPE
			SYNTAX INTEGER (0..3)
			MAX-ACCESS read-only
			STATUS current
			DESCRIPTION
				"The guard_interval: values as specified for the
				terrestrial_delivery_system_descriptor
				Valid for: terrestrial"
			REFERENCE
				"EN 300 468 Table 42"
			::= { mgNITDeliverySystemEntry 17 }
		
		mgNITDSTransmissionMode OBJECT-TYPE
			SYNTAX INTEGER (0..3)
			MAX-ACCESS read-only
			STATUS current
			DESCRIPTION
				"The transmission_mode: values as specified for the
				terrestrial_delivery_system_descriptor
				Valid for: terrestrial"
			REFERENCE
				"EN 300 468 Table 43"
			::= { mgNITDeliverySystemEntry 18 }
		
		mgNITDSOtherFrequencyFlag OBJECT-TYPE
			SYNTAX INTEGER (0..1)
			MAX-ACCESS read-only
			STATUS current
			DESCRIPTION
				"other_frequency_flag: values as specified for the
				terrestrial_delivery_system_descriptor
				Valid for: terrestrial"
			REFERENCE
				"EN 300 468 6.2.12.3"
			::= { mgNITDeliverySystemEntry 19 }
		
-- mgRFCharacteristics provides information about the
-- RF input to the measuring instrument.  This information
-- may have been derived by measurement or it may report
-- manual or automated settings on the instrument.
		mgRFCharacteristics OBJECT IDENTIFIER ::= { mgSignalCharacteristicsObjects 2 }
		
		mgRFCharacteristicsTrap OBJECT IDENTIFIER ::= { mgRFCharacteristics 1 }
		
-- This prefix is necessary to satisfy the requirement of RFC 2578
-- section 8.5 that 'the next to last sub-identifier in the name of
-- any newly-defined notification must have the value zero'.
		rfTrapPrefix OBJECT IDENTIFIER ::= { mgRFCharacteristicsTrap 0 }
		
		rfCharacteristicsChangeTrap NOTIFICATION-TYPE
			OBJECTS { rfCharacteristicsTrapInput, rfCharacteristicsTrapControlOID, rfCharacteristicsTrapControlChangeTime }
			STATUS current
			DESCRIPTION
				"Trap which is sent when a value in the mgRFCharacteristics
				part of the MIB changes substantially. Transmission of the
				trap is subject to rate control through the
				rfCharacteristicsTrapControlRateStatus object."
			::= { rfTrapPrefix 1 }
		
		rfCharacteristicsTrapControlTable OBJECT-TYPE
			SYNTAX SEQUENCE OF RfCharacteristicsTrapControlEntry
			MAX-ACCESS not-accessible
			STATUS current
			DESCRIPTION
				"Per-input table of values which control the generation of
				rfCharacteristicsChangeTrap traps."
			::= { mgRFCharacteristicsTrap 1 }
		
		rfCharacteristicsTrapControlEntry OBJECT-TYPE
			SYNTAX RfCharacteristicsTrapControlEntry
			MAX-ACCESS not-accessible
			STATUS current
			DESCRIPTION
				"Row specification"
			INDEX { rfCharacteristicsTrapControlInputNumber }
			::= { rfCharacteristicsTrapControlTable 1 }
		
		RfCharacteristicsTrapControlEntry ::=
			SEQUENCE { 
				rfCharacteristicsTrapControlInputNumber
					InputNumber,
				rfCharacteristicsTrapControlOID
					OBJECT IDENTIFIER,
				rfCharacteristicsTrapControlChangeTime
					DateAndTime,
				rfCharacteristicsTrapControlRateStatus
					RateStatus,
				rfCharacteristicsTrapControlPeriod 
					Unsigned32
			 }

		rfCharacteristicsTrapControlInputNumber OBJECT-TYPE
			SYNTAX InputNumber
			MAX-ACCESS not-accessible
			STATUS current
			DESCRIPTION
				"Transport Stream on which an RF value has changed, triggering the
				transmission of the trap."
			::= { rfCharacteristicsTrapControlEntry 1 }
		
		rfCharacteristicsTrapControlOID OBJECT-TYPE
			SYNTAX OBJECT IDENTIFIER
			MAX-ACCESS accessible-for-notify
			STATUS current
			DESCRIPTION
				"This object holds the OID of the object within the rfCharacteristics
				branch of the MIB whose change triggered the trap. It is present for
				the formal purpose of defining the variable bindings returned with
				the rfCharacteristicsChangeTrap. It is not accessible for normal
				reading. Note that this may not be the only value which has changed;
				managers need to poll to obtain all the new values that they need."
			::= { rfCharacteristicsTrapControlEntry 2 }
		
		rfCharacteristicsTrapControlChangeTime OBJECT-TYPE
			SYNTAX DateAndTime
			MAX-ACCESS accessible-for-notify
			STATUS current
			DESCRIPTION
				"This indicates the time when the change which triggered the
				trap occurred. It is present for the formal purpose of defining
				the variable bindings returned with the rfCharacteristicsChangeTrap.
				It is not accessible for normal reading."
			::= { rfCharacteristicsTrapControlEntry 3 }
		
		rfCharacteristicsTrapControlRateStatus OBJECT-TYPE
			SYNTAX RateStatus
			MAX-ACCESS read-write
			STATUS current
			DESCRIPTION
				"This object is used for rate control of traps, preventing
				overload of the management network by transmission of an
				excessive number of traps. The value 'disabled' means that
				traps are never sent. The value 'enabled' means that a
				trap will be sent when triggered.
				
				When a trap is sent, the agent changes the value of this
				object to 'enabledThrottled'. In this state the agent will
				not send any more traps. The agent automatically changes
				the value back to 'enabled' when the time specified by
				trapControlPeriod expires. A management application may
				set the value to 'enabled' at any time, but must never set
				the value to 'enabledThrottled'."
			::= { rfCharacteristicsTrapControlEntry 4 }
		
		rfCharacteristicsTrapControlPeriod  OBJECT-TYPE
			SYNTAX Unsigned32 (0..3600000)
			UNITS "millisecond"
			MAX-ACCESS read-write
			STATUS current
			DESCRIPTION
				"The agent will ensure that the interval between sending traps is
				no shorter than this time period (unless overridden by the manager)."
			::= { rfCharacteristicsTrapControlEntry 5 }
		
		rfCharacteristicsTrapInput OBJECT-TYPE
			SYNTAX InputNumber
			MAX-ACCESS accessible-for-notify
			STATUS current
			DESCRIPTION
				"The Transport Stream input whose change triggered the current
				trap.  This information can also be obtained by analysing the
				rfCharacteristicsTrapOID,  but rfCharacteristicsTrapInput
				provides the information directly.
				
				This object is present for the formal purpose of defining
				the variable bindings returned with the traps. It is not
				accessible for normal reading."
			::= { mgRFCharacteristicsTrap 2 }
		
		mgRFCharacteristicsTable OBJECT-TYPE
			SYNTAX SEQUENCE OF MgRFCharacteristicsEntry
			MAX-ACCESS not-accessible
			STATUS current
			DESCRIPTION
				"The RF characteristics of the input signal. These values represent
				the measuring instrument's 'best effort' to determine them."
			::= { mgRFCharacteristics 2 }
		
		mgRFCharacteristicsEntry OBJECT-TYPE
			SYNTAX MgRFCharacteristicsEntry
			MAX-ACCESS not-accessible
			STATUS current
			DESCRIPTION
				"Row specification"
			INDEX { mgRFInputNumber }
			::= { mgRFCharacteristicsTable 1 }
		
		MgRFCharacteristicsEntry ::=
			SEQUENCE { 
				mgRFInputNumber
					InputNumber,
				mgRFSystemType
					DeliverySystemType,
				mgRFCentreFrequency
					FloatingPoint,
				mgRFModulation
					Modulation,
				mgRFFecInner
					InnerCodeRate,
				mgRFFecInnerLP
					InnerCodeRate,
				mgRFSymbolRate
					FloatingPoint,
				mgRFBandwidth
					FloatingPoint,
				mgRFTransmissionMode
					TerrestrialTransmissionMode,
				mgRFIsHierarchical
					TruthValue,
				mgRFGuardInterval
					GuardInterval
			 }

		mgRFInputNumber OBJECT-TYPE
			SYNTAX InputNumber
			MAX-ACCESS not-accessible
			STATUS current
			DESCRIPTION
				"The physical input on which these RF characteristics are found"
			::= { mgRFCharacteristicsEntry 1 }
		
		mgRFSystemType OBJECT-TYPE
			SYNTAX DeliverySystemType
			MAX-ACCESS read-only
			STATUS current
			DESCRIPTION
				"Which delivery system is in use: cable, satellite or
				terrestrial. The value of this object determines which
				other objects in this table have valid values."
			::= { mgRFCharacteristicsEntry 2 }
		
		mgRFCentreFrequency OBJECT-TYPE
			SYNTAX FloatingPoint
			UNITS "MHz"
			MAX-ACCESS read-only
			STATUS current
			DESCRIPTION
				"This is the centre frequency to which the measuring equipment is 
				tuned. This frequency is the actual input frequency to the
				measuring equipment, which may be at an intermediate frequency
				(IF) rather than the final RF.
				Valid for: cable, satellite, terrestrial"
			::= { mgRFCharacteristicsEntry 3 }
		
		mgRFModulation OBJECT-TYPE
			SYNTAX Modulation
			MAX-ACCESS read-only
			STATUS current
			DESCRIPTION
				"The modulation scheme in use
				Valid for: cable, satellite, terrestrial"
			::= { mgRFCharacteristicsEntry 4 }
		
		mgRFFecInner OBJECT-TYPE
			SYNTAX InnerCodeRate
			MAX-ACCESS read-only
			STATUS current
			DESCRIPTION
				"Inner Forward Error Correction scheme (also referred to as code rate).
				In the case of a hierarchical terrestrial transmission, this is the
				inner code rate for the high priority stream.
				Valid for: satellite, terrestrial"
			::= { mgRFCharacteristicsEntry 5 }
		
		mgRFFecInnerLP OBJECT-TYPE
			SYNTAX InnerCodeRate
			MAX-ACCESS read-only
			STATUS current
			DESCRIPTION
				"Inner Forward Error Correction scheme (also referred to as code rate).
				This is the code rate for the low priority stream in a hierarchical
				terrestrial transmission.
				Valid for: terrestrial"
			::= { mgRFCharacteristicsEntry 6 }
		
		mgRFSymbolRate OBJECT-TYPE
			SYNTAX FloatingPoint
			UNITS "Msymbol/s"
			MAX-ACCESS read-only
			STATUS current
			DESCRIPTION
				"Indicates the symbol rate of the transmission.
				Valid for: cable, satellite"
			::= { mgRFCharacteristicsEntry 7 }
		
		mgRFBandwidth OBJECT-TYPE
			SYNTAX FloatingPoint
			UNITS "MHz"
			MAX-ACCESS read-only
			STATUS current
			DESCRIPTION
				"Bandwidth of the signal. Normally this will be equivalent to
				the channel spacing.
				Valid for: terrestrial"
			::= { mgRFCharacteristicsEntry 8 }
		
		mgRFTransmissionMode OBJECT-TYPE
			SYNTAX TerrestrialTransmissionMode
			MAX-ACCESS read-only
			STATUS current
			DESCRIPTION
				"Whether there are 2k or 8k carriers in the OFDM modulation scheme.
				Valid for: terrestrial"
			::= { mgRFCharacteristicsEntry 9 }
		
		mgRFIsHierarchical OBJECT-TYPE
			SYNTAX TruthValue
			MAX-ACCESS read-only
			STATUS current
			DESCRIPTION
				"Whether the transmission is hierarchical
				Valid for: terrestrial"
			::= { mgRFCharacteristicsEntry 10 }
		
		mgRFGuardInterval OBJECT-TYPE
			SYNTAX GuardInterval
			MAX-ACCESS read-only
			STATUS current
			DESCRIPTION
				"The guard interval in use
				Valid for: terrestrial"
			::= { mgRFCharacteristicsEntry 11 }
		
		mgSignalCharacteristicsConformance OBJECT IDENTIFIER ::= { mgSignalCharacteristics 2 }
		
		mgSignalCharacteristicsCompliances OBJECT IDENTIFIER ::= { mgSignalCharacteristicsConformance 1 }
		
		mgSCTransportStreamCompliance MODULE-COMPLIANCE
			STATUS current
			DESCRIPTION
				"An implementation which provides all the information in
				the mgTSStructure part of the MIB and implements the
				tsStructureChangeTrap can claim this conformance."
			MODULE -- this module
				MANDATORY-GROUPS { mgSCTransportStreamGroup, mgSCTransportStreamTrapGroup }
			::= { mgSignalCharacteristicsCompliances 1 }
		
		mgSCRadioFrequencyCompliance MODULE-COMPLIANCE
			STATUS current
			DESCRIPTION
				"An implementation which provides all the information in
				the mgRFCharacteristics part of the MIB and implements the
				rfCharacteristicsChangeTrap can claim this conformance."
			MODULE -- this module
				MANDATORY-GROUPS { mgSCRadioFrequencyGroup, mgSCRadioFrequencyTrapGroup }
			::= { mgSignalCharacteristicsCompliances 2 }
		
		mgSignalCharacteristicsGroups OBJECT IDENTIFIER ::= { mgSignalCharacteristicsConformance 3 }
		
		mgSCTransportStreamGroup OBJECT-GROUP
			OBJECTS { structureTrapControlOID, structureTrapControlChangeTime, structureTrapControlRateStatus, structureTrapControlPeriod , structureTrapInput, 
				mgTSId, mgTSOriginalNetworkID, mgTSNetworkID, mgTSNetworkName, mgServiceType, 
				mgServiceName, mgServiceProviderName, mgServicePMTPID, mgServicePCRPID, mgServiceCondAccess, 
				mgServiceEITComponentDescriptor, mgPIDType, mgPIDCondAccess, mgEMMCASystemID, mgServiceECMCASystemID, 
				mgPIDECMCASystemID, mgNITDSSystemType, mgNITDSFrequency, mgNITDSFecOuter, mgNITDSCableModulation, 
				mgNITDSSymbolRate, mgNITDSFecInner, mgNITDSOrbitalPosition, mgNITDSWestEastFlag, mgNITDSPolarization, 
				mgNITDSSatelliteModulation, mgNITDSBandwidth, mgNITDSConstellation, mgNITDSHierarchyInformation, mgNITDSCodeRateHPStream, 
				mgNITDSCodeRateLPStream, mgNITDSGuardInterval, mgNITDSTransmissionMode, mgNITDSOtherFrequencyFlag }
			STATUS current
			DESCRIPTION
				"This group contains all the objects in the
				mgTSStructure part of the MIB."
			::= { mgSignalCharacteristicsGroups 1 }
		
		mgSCRadioFrequencyGroup OBJECT-GROUP
			OBJECTS { rfCharacteristicsTrapControlOID, rfCharacteristicsTrapControlChangeTime, rfCharacteristicsTrapControlRateStatus, rfCharacteristicsTrapControlPeriod , rfCharacteristicsTrapInput, 
				mgRFSystemType, mgRFCentreFrequency, mgRFModulation, mgRFFecInner, mgRFFecInnerLP, 
				mgRFSymbolRate, mgRFBandwidth, mgRFTransmissionMode, mgRFIsHierarchical, mgRFGuardInterval
				 }
			STATUS current
			DESCRIPTION
				"This group contains all the objects in the
				mgRFCharacteristics part of the MIB"
			::= { mgSignalCharacteristicsGroups 2 }
		
		mgSCTransportStreamTrapGroup NOTIFICATION-GROUP
			NOTIFICATIONS { tsStructureChangeTrap }
			STATUS current
			DESCRIPTION
				"Contains tsStructureChangeTrap"
			::= { mgSignalCharacteristicsGroups 3 }
		
		mgSCRadioFrequencyTrapGroup NOTIFICATION-GROUP
			NOTIFICATIONS { rfCharacteristicsChangeTrap }
			STATUS current
			DESCRIPTION
				"Contains rfCharacteristicsChangeTrap"
			::= { mgSignalCharacteristicsGroups 4 }
		
	
	END

--
-- DVB-MGSIGNALCHARACTERISTICS-MIB.my
--
