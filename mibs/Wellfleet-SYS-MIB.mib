Wellfleet-SYS-MIB DEFINITIONS ::= BEGIN

-- Created by mdl2asn version 3.1
-- Creation date: Wed Aug 30 16:48:50 EDT 1995


    IMPORTS

      TimeTicks, Gauge
        FROM RFC1155-SMI
      OBJECT-TYPE
        FROM RFC-1212
      DisplayString
        FROM RFC1213-MIB
      wfSystem
        FROM Wellfleet-COMMON-MIB;


    wfSys		OBJECT IDENTIFIER ::= { wfSystem 1 }

    wfSysDescr OBJECT-TYPE
        SYNTAX	DisplayString
        ACCESS	read-only
        STATUS	mandatory
        DESCRIPTION
                "A textual description of the entity including full name and version of
                the system's hardware type, OS, and networking SW "
        ::= { wfSys 1 }

    wfSysObjectID OBJECT-TYPE
        SYNTAX	OBJECT IDENTIFIER
        ACCESS	read-only
        STATUS	mandatory
        DESCRIPTION
                "Provides an unambiguous means for determining the MIB type (old product vs.
                harpoon MIB)."
        ::= { wfSys 2 }

    wfSysUpTime OBJECT-TYPE
        SYNTAX	TimeTicks
        ACCESS	read-only
        STATUS	mandatory
        DESCRIPTION
                "Time in seconds/100 since the last cold start"
        ::= { wfSys 3 }

    wfSysContact OBJECT-TYPE
        SYNTAX	DisplayString
        ACCESS	read-write
        STATUS	mandatory
        DESCRIPTION
                "Contact person for this node and where/how to contact them"
        ::= { wfSys 4 }

    wfSysName OBJECT-TYPE
        SYNTAX	DisplayString
        ACCESS	read-write
        STATUS	mandatory
        DESCRIPTION
                "Node's fully qualified domain name or administratively assigned name"
        ::= { wfSys 5 }

    wfSysLocation OBJECT-TYPE
        SYNTAX	DisplayString
        ACCESS	read-write
        STATUS	mandatory
        DESCRIPTION
                "Physical Location of this Node"
        ::= { wfSys 6 }

    wfSysServices OBJECT-TYPE
        SYNTAX	INTEGER
        ACCESS	read-only
        STATUS	mandatory
        DESCRIPTION
                "A sum of numbers indicating the set of services the entity offers. For each
                layer L, add 2**(L - 1). Example: 78 = Layers 2,3,4, and 7."
        DEFVAL	{ 78 }
        ::= { wfSys 7 }

    wfSysGmtOffset OBJECT-TYPE
        SYNTAX	INTEGER
        ACCESS	read-only
        STATUS	mandatory
        DESCRIPTION
                "The positive or negative offset from Greenwich Mean Time (GMT). This
                effectively describes the time zone."
        ::= { wfSys 8 }

    wfSysMibVersion OBJECT-TYPE
        SYNTAX	DisplayString
        ACCESS	read-only
        STATUS	mandatory
        DESCRIPTION
                "The version of the private management information base currently being
                used by the system software. Format is: xV.RR"
        ::= { wfSys 9 }

    wfSysMibRevision OBJECT-TYPE
        SYNTAX	INTEGER
        ACCESS	read-write
        STATUS	mandatory
        DESCRIPTION
                "The revision level of the private management information base currently
                being used by the system software."
        ::= { wfSys 10 }

    wfSysAgentType OBJECT-TYPE
        SYNTAX	INTEGER {
		    other(1),
    		    anrptragenttype(29),
    		    anhubagenttype(30)
    		}
        ACCESS	read-only
        STATUS	mandatory
        DESCRIPTION
                "The network management agent's module type"
        ::= { wfSys 11 }

    wfSysMibCounterEnable OBJECT-TYPE
        SYNTAX	INTEGER {
    		    enabled(1),
    		    disabled(2)
    		}
        ACCESS	read-write
        STATUS	mandatory
        DESCRIPTION
                "Mib II counter Switch"
        DEFVAL	{ enabled }
        ::= { wfSys 12 }

    wfSysMaxUpTime OBJECT-TYPE
        SYNTAX	TimeTicks
        ACCESS	read-only
        STATUS	mandatory
        DESCRIPTION
                "Time in seconds/100 since the last cold start. 
                Max across slots"
        ::= { wfSys 13 }

    wfSysBccHelpFileName OBJECT-TYPE
        SYNTAX	DisplayString
        ACCESS	read-write
        STATUS	mandatory
        DESCRIPTION
                "Location of the BCC help file."
        DEFVAL	{ "bcc.help" }
        ::= { wfSys 14 }

    wfSysConsoleSlotMask OBJECT-TYPE
        SYNTAX  Gauge
        ACCESS  read-write
        STATUS  mandatory
        DESCRIPTION
                "Slot mask defining which slots Console Interface is 
		eligible to run on.  The MSBit represents slot 1, the
                next most significant bit represents slot 2,
                and so on...  Slots can be 1-14. If set to 0, then
		the Console Interface remains on the first booted slot.
                Default is all slots on a BCN. Affects only multislot
		routers with single physical console port."
        DEFVAL  { 4294705152 }
        ::= { wfSys 15 }

    END  -- Wellfleet-SYS-MIB
