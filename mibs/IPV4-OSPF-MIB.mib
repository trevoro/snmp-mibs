IPV4-OSPF-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, Integer32, IpAddress
			FROM SNMPv2-SMI
		RowStatus
			FROM SNMPv2-TC
		apIpv4Ospf
			FROM APENT-MIB;


    apIpv4OspfMib MODULE-IDENTITY
	   LAST-UPDATED "9805112000Z" -- Mon May 11 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for the Routing Information Protocol"
      ::= { apIpv4Ospf 1}

--arrowpoint
-- apmgmt
--  ipv4Ext
--   apIpv4RoutingProtocols
--     apIpv4Ospf

-- OSPF global configuration information

apIpv4OspfRedistributeLocal OBJECT-TYPE
	SYNTAX      INTEGER {
			    enable (1),
			    disable (2)
			    }
	MAX-ACCESS  read-write
	STATUS      current
	DESCRIPTION
	       "If enabled, local (direct) routes will be advertised by OSPF."
	DEFVAL {2}
	::= {apIpv4Ospf 2}

apIpv4OspfLocalType OBJECT-TYPE
    SYNTAX      INTEGER  {
			    aseType1 (1),
			    aseType2 (2)
			    }
	MAX-ACCESS  read-write
	STATUS      current
	DESCRIPTION
	       "If local routes are advertised by OSPF, this is the ASE type
            to use when advertising the routes."
	DEFVAL {2}
	::= {apIpv4Ospf 3}

apIpv4OspfLocalMetric OBJECT-TYPE
    SYNTAX      INTEGER ( 1..16777215 )
	MAX-ACCESS  read-write
	STATUS      current
	DESCRIPTION
	       "If local routes are advertised by OSPF, this is the metric
            to use when advertising the routes."
	DEFVAL {1}
	::= {apIpv4Ospf 4}

apIpv4OspfLocalTag OBJECT-TYPE
    SYNTAX      Integer32
	MAX-ACCESS  read-write
	STATUS      current
	DESCRIPTION
	       "If local routes are advertised by OSPF, this is the tag value
            to use when advertising the routes."
	DEFVAL {0}
	::= {apIpv4Ospf 5}

apIpv4OspfRedistributeStatic OBJECT-TYPE
	SYNTAX      INTEGER {
			    enable (1),
			    disable (2)
			    }
	MAX-ACCESS  read-write
	STATUS      current
	DESCRIPTION
	       "If enabled, static routes will be advertised by OSPF."
	DEFVAL {2}
	::= {apIpv4Ospf 6}

apIpv4OspfStaticType OBJECT-TYPE
    SYNTAX      INTEGER  {
			    aseType1 (1),
			    aseType2 (2)
			    }
	MAX-ACCESS  read-write
	STATUS      current
	DESCRIPTION
	       "If static routes are advertised by OSPF, this is the ASE type
            to use when advertising the routes."
	DEFVAL {2}
	::= {apIpv4Ospf 7}

apIpv4OspfStaticMetric OBJECT-TYPE
    SYNTAX      INTEGER ( 1..16777215 )
	MAX-ACCESS  read-write
	STATUS      current
	DESCRIPTION
	       "If static routes are advertised by OSPF, this is the metric
            to use when advertising the routes."
	DEFVAL {1}
	::= {apIpv4Ospf 8}

apIpv4OspfStaticTag OBJECT-TYPE
    SYNTAX      Integer32
	MAX-ACCESS  read-write
	STATUS      current
	DESCRIPTION
	       "If static routes are advertised by OSPF, this is the tag value
            to use when advertising the routes."
	DEFVAL {0}
	::= {apIpv4Ospf 9}

apIpv4OspfRedistributeRip OBJECT-TYPE
	SYNTAX      INTEGER {
			    enable (1),
			    disable (2)
			    }
	MAX-ACCESS  read-write
	STATUS      current
	DESCRIPTION
	       "If enabled, RIP routes will be advertised by OSPF."
	DEFVAL {2}
	::= {apIpv4Ospf 10}

apIpv4OspfRipType OBJECT-TYPE
    SYNTAX      INTEGER  {
			    aseType1 (1),
			    aseType2 (2)
			    }
	MAX-ACCESS  read-write
	STATUS      current
	DESCRIPTION
	       "If RIP routes are advertised by OSPF, this is the ASE type
            to use when advertising the routes."
	DEFVAL {2}
	::= {apIpv4Ospf 11}

apIpv4OspfRipMetric OBJECT-TYPE
    SYNTAX      INTEGER ( 0..16777215 )
	MAX-ACCESS  read-write
	STATUS      current
	DESCRIPTION
	       "If RIP routes are advertised by OSPF, this is the metric
            to use when advertising the routes.  If zero is specified,
            the RIP metric will be used."
	DEFVAL {0}
	::= {apIpv4Ospf 12}

apIpv4OspfRipTag OBJECT-TYPE
    SYNTAX      Integer32
	MAX-ACCESS  read-write
	STATUS      current
	DESCRIPTION
	       "If RIP routes are advertised by OSPF, this is the tag value
            to use when advertising the routes."
	DEFVAL {0}
	::= {apIpv4Ospf 13}

apIpv4OspfOriginateDefault OBJECT-TYPE
	SYNTAX      INTEGER {
			    enable (1),
			    disable (2)
			    }
	MAX-ACCESS  read-write
	STATUS      current
	DESCRIPTION
	       "If enabled, an ASE will be generated for the default route."
	DEFVAL {2}
	::= {apIpv4Ospf 14}

apIpv4OspfDefaultType OBJECT-TYPE
    SYNTAX      INTEGER  {
			    aseType1 (1),
			    aseType2 (2)
			    }
	MAX-ACCESS  read-write
	STATUS      current
	DESCRIPTION
	       "If a default ASE is originated by OSPF, this is the ASE type
            to use when advertising the route."
	DEFVAL {2}
	::= {apIpv4Ospf 15}

apIpv4OspfDefaultMetric OBJECT-TYPE
    SYNTAX      INTEGER ( 1..16777215 )
	MAX-ACCESS  read-write
	STATUS      current
	DESCRIPTION
	       "If a default ASE is originated by OSPF, this is the metric
            to use when advertising the route."
	DEFVAL {1}
	::= {apIpv4Ospf 16}

apIpv4OspfDefaultTag OBJECT-TYPE
    SYNTAX      Integer32
	MAX-ACCESS  read-write
	STATUS      current
	DESCRIPTION
	       "If a default ASE is originated by OSPF, this is the tag value
            to use when advertising the route."
	DEFVAL {0}
	::= {apIpv4Ospf 17}

apIpv4OspfRedistributeFirewall OBJECT-TYPE
	SYNTAX      INTEGER {
			    enable (1),
			    disable (2)
			    }
	MAX-ACCESS  read-write
	STATUS      current
	DESCRIPTION
	       "If enabled, firewall routes will be advertised by OSPF."
	DEFVAL {2}
	::= {apIpv4Ospf 18}

apIpv4OspfFirewallType OBJECT-TYPE
    SYNTAX      INTEGER  {
			    aseType1 (1),
			    aseType2 (2)
			    }
	MAX-ACCESS  read-write
	STATUS      current
	DESCRIPTION
	       "If firewall routes are advertised by OSPF, this is the ASE type
            to use when advertising the routes."
	DEFVAL {2}
	::= {apIpv4Ospf 19}

apIpv4OspfFirewallMetric OBJECT-TYPE
    SYNTAX      INTEGER ( 1..16777215 )
	MAX-ACCESS  read-write
	STATUS      current
	DESCRIPTION
	       "If firewall routes are advertised by OSPF, this is the metric
            to use when advertising the routes."
	DEFVAL {1}
	::= {apIpv4Ospf 20}

apIpv4OspfFirewallTag OBJECT-TYPE
    SYNTAX      Integer32
	MAX-ACCESS  read-write
	STATUS      current
	DESCRIPTION
	       "If firewall routes are advertised by OSPF, this is the tag value
            to use when advertising the routes."
	DEFVAL {0}
	::= {apIpv4Ospf 21}

-- OSPF route advertisement table.  This table contains routes that
-- are advertised out all OSPF interfaces, even if the route does not
-- exist in the routing table.

apIpv4OspfAdvRouteTable OBJECT-TYPE
    SYNTAX   SEQUENCE OF ApIpv4OspfAdvRouteEntry
    MAX-ACCESS   not-accessible
    STATUS   current
    DESCRIPTION
       "A list of routes that are advertised via all OSPF interfaces."
    ::= {apIpv4Ospf 22}

apIpv4OspfAdvRouteEntry OBJECT-TYPE
    SYNTAX   	ApIpv4OspfAdvRouteEntry
    MAX-ACCESS  not-accessible
    STATUS   	current	
    DESCRIPTION
        "A single route to advertise via all OSPF interfaces."
    INDEX { apIpv4OspfAdvRoutePrefix, apIpv4OspfAdvRoutePrefixLen }
    ::= { apIpv4OspfAdvRouteTable 1 }

ApIpv4OspfAdvRouteEntry ::=
    SEQUENCE {
        apIpv4OspfAdvRoutePrefix     IpAddress,
        apIpv4OspfAdvRoutePrefixLen  INTEGER,
		apIpv4OspfAdvRouteType	     INTEGER,
        apIpv4OspfAdvRouteMetric     INTEGER,
		apIpv4OspfAdvRouteTag		 Integer32,
        apIpv4OspfAdvRouteStatus     RowStatus
    }

apIpv4OspfAdvRoutePrefix OBJECT-TYPE
    SYNTAX   	IpAddress
    MAX-ACCESS  read-only
    STATUS   	current
    DESCRIPTION
        "The route prefix to be advertised."
    ::= { apIpv4OspfAdvRouteEntry 1 }

apIpv4OspfAdvRoutePrefixLen OBJECT-TYPE
	SYNTAX      INTEGER (1..32)
	MAX-ACCESS  read-only
	STATUS      current
	DESCRIPTION
	       "The network prefix length associated with this route."
	::= { apIpv4OspfAdvRouteEntry 2 }

apIpv4OspfAdvRouteType OBJECT-TYPE
    SYNTAX      INTEGER  {
			    aseType1 (1),
			    aseType2 (2)
			    }
	MAX-ACCESS  read-create
	STATUS      current
	DESCRIPTION
	       "this is the ASE type to use when advertising 
			this route."
	DEFVAL {2}
	::= { apIpv4OspfAdvRouteEntry 3 }

apIpv4OspfAdvRouteMetric OBJECT-TYPE
	SYNTAX      INTEGER (1..16777215)
	MAX-ACCESS  read-create
	STATUS      current
	DESCRIPTION
	       "The metric to use when advertising this route."
	DEFVAL {1}
	::= { apIpv4OspfAdvRouteEntry 4 }

apIpv4OspfAdvRouteTag OBJECT-TYPE
    SYNTAX      Integer32
	MAX-ACCESS  read-create
	STATUS      current
	DESCRIPTION
	       "this is the tag value to use when advertising 
			this route."
	DEFVAL {0}
	::= { apIpv4OspfAdvRouteEntry 5 }

apIpv4OspfAdvRouteStatus OBJECT-TYPE
	SYNTAX      RowStatus
	MAX-ACCESS  read-create
	STATUS      current
	DESCRIPTION
	       "This variable displays the status of  the  en-
           try.  Setting it to 'invalid' has the effect of
           rendering it inoperative.  The internal  effect
           (row removal) is implementation dependent."
	::= { apIpv4OspfAdvRouteEntry 6 }

-- OSPF per-interface route advertisement table.  This table contains routes
-- that are advertised out a specific OSPF interface, even if the route does not
-- exist in the routing table.

apIpv4OspfIfAdvRouteTable OBJECT-TYPE
    SYNTAX   SEQUENCE OF ApIpv4OspfIfAdvRouteEntry
    MAX-ACCESS   not-accessible
    STATUS   current
    DESCRIPTION
       "A list of routes that are advertised via a specific OSPF interface."
    ::= { apIpv4Ospf 23 }

apIpv4OspfIfAdvRouteEntry OBJECT-TYPE
    SYNTAX   ApIpv4OspfIfAdvRouteEntry
    MAX-ACCESS   not-accessible
    STATUS   current
    DESCRIPTION
        "A single route to advertise via a specific OSPF interface."
    INDEX { apIpv4OspfIfAdvRouteAddress, apIpv4OspfIfAdvRoutePrefix,
            apIpv4OspfIfAdvRoutePrefixLen }
    ::= { apIpv4OspfIfAdvRouteTable 1 }

ApIpv4OspfIfAdvRouteEntry ::=
    SEQUENCE {
        apIpv4OspfIfAdvRouteAddress    IpAddress,
        apIpv4OspfIfAdvRoutePrefix     IpAddress,
        apIpv4OspfIfAdvRoutePrefixLen  INTEGER,
		apIpv4OspfIfAdvRouteType	   INTEGER,
        apIpv4OspfIfAdvRouteMetric     INTEGER,
		apIpv4OspfIfAdvRouteTag		   Integer32,
        apIpv4OspfIfAdvRouteStatus     RowStatus
    }

apIpv4OspfIfAdvRouteAddress OBJECT-TYPE
    SYNTAX   IpAddress
    MAX-ACCESS   read-only
    STATUS   current
    DESCRIPTION
        "The address of the OSPF interface.  If this is a valid unicast
         IP address, the interface is numbered.  Otherwise, it indicates
         the ifIndex of an unnumbered interface."
    ::= { apIpv4OspfIfAdvRouteEntry 1 }

apIpv4OspfIfAdvRoutePrefix OBJECT-TYPE
    SYNTAX   IpAddress
    MAX-ACCESS   read-only
    STATUS   current
    DESCRIPTION
        "The route prefix to be advertised."
    ::= { apIpv4OspfIfAdvRouteEntry 2 }

apIpv4OspfIfAdvRoutePrefixLen OBJECT-TYPE
	SYNTAX      INTEGER (1..32)
	MAX-ACCESS  read-only
	STATUS      current
	DESCRIPTION
	       "The network prefix length associated with this route."
	::= { apIpv4OspfIfAdvRouteEntry 3 }

apIpv4OspfIfAdvRouteType OBJECT-TYPE
    SYNTAX      INTEGER  {
			    aseType1 (1),
			    aseType2 (2)
			    }
	MAX-ACCESS  read-create
	STATUS      current
	DESCRIPTION
	       "this is the ASE type to use when advertising 
			this route."
	DEFVAL {2}
	::= { apIpv4OspfIfAdvRouteEntry 4 }

apIpv4OspfIfAdvRouteMetric OBJECT-TYPE
	SYNTAX      INTEGER (1..16777215)
	MAX-ACCESS  read-create
	STATUS      current
	DESCRIPTION
	       "The metric to use when advertising this route."
	DEFVAL {1}
	::= { apIpv4OspfIfAdvRouteEntry 5 }

apIpv4OspfIfAdvRouteTag OBJECT-TYPE
    SYNTAX      Integer32
	MAX-ACCESS  read-create
	STATUS      current
	DESCRIPTION
	       "this is the tag value to use when advertising 
			this route."
	DEFVAL {0}
	::= { apIpv4OspfIfAdvRouteEntry 6 }

apIpv4OspfIfAdvRouteStatus OBJECT-TYPE
	SYNTAX      RowStatus
	MAX-ACCESS  read-create
	STATUS      current
	DESCRIPTION
	       "This variable displays the status of  the  en-
           try.  Setting it to 'invalid' has the effect of
           rendering it inoperative.  The internal  effect
           (row removal) is implementation dependent."
	::= { apIpv4OspfIfAdvRouteEntry 7 }

apIpv4OspfEqualCostRoutes OBJECT-TYPE
    SYNTAX      INTEGER ( 1..15 )
	MAX-ACCESS  read-write
	STATUS      current
	DESCRIPTION
	       "The maximum number of equal-cost routes OSPF can use."
	DEFVAL {1}
	::= {apIpv4Ospf 24}


END
