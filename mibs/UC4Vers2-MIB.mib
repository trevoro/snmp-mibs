--

UC4Vers2-MIB DEFINITIONS ::= BEGIN

--
--  Title:  UC4Vers2 MIB ab UC4 Version 5.00A
--  Author: bakk. Peter Daransky
--  Date:   Sept. 3, 2009
--  Ref.:   Structure of Management Information Version 2 (SMIv2)
--          http://www.rfc-editor.org/rfc/rfc2578.txt
--  =================================================================
--
--  Group Indices
--  -------------
--
--  1 agentData Group
--  2 agentControl Group
--  3 agentWork Group
--  4 system Group
--  5 client Group
--  6 serverInstance Group
--  7 executor Group
--  8 blockingPoints Group
--
--
--  MIB History:
--  ------------
--
--  Date             I From          I Subject
--	Sept.		 3, 2009 I Daransky PeterI MODULE-IDENTITY
--  March.   6, 2008 I Daransky PeterI srvStartTime - SIZE changed from 0..19 to 0..23
--  March.   6, 2008 I Daransky PeterI blkClient - range changed 0..9999
--  March.   6, 2008 I Daransky PeterI cliClient - range changed 0..9999
--  March.   6, 2008 I Daransky PeterI agentStartTime - Format changed, see description
--  March.   6, 2008 I Daransky PeterI agentVersion - SIZE changed from 0..5 to 0..12
--  Sept.    7, 2007 I Wihelm Moser  I Some Placements of Entries have been changed due to conversion
--  Sept.    7, 2007 I Wihelm Moser  I Previous comments added again
--  Sept.    6, 2007 I Wihelm Moser  I converted from SMIv1 to SMIv2
--  Sept.    6, 2007 I Wihelm Moser  I v1tov2 conversion error - DisplayString changed fm RFC-1213 
--  Sept.    6, 2007 I Wihelm Moser  I v1tov2 conversion error - agentConnectCounter changed fm Counter to Integer32
--  Sept.    6, 2007 I Wihelm Moser  I v1tov2 conversion error - cliState INTEGER stop(0) changed to stop(2)
--  Sept.    6, 2007 I Wihelm Moser  I v1tov2 conversion error - cliMonitoring INTEGER no(0) changed to no(2)
--  Sept.    6, 2007 I Wihelm Moser  I v1tov2 conversion error - srvState INTEGER undef(0) to undef(4)
--  Sept.    6, 2007 I Wihelm Moser  I v1tov2 conversion error - srvRunMode INTEGER undef(0) to undef(3) 
--  Sept.    6, 2007 I Wihelm Moser  I v1tov2 conversion error - srvDBState  INTEGER undef(0) to undef(3) 
--  Sept.    6, 2007 I Wihelm Moser  I v1tov2 conversion error - srvSDBState INTEGER noSDB(0) to noSDB(4)
--  Sept.    6, 2007 I Wihelm Moser  I v1tov2 conversion error - exeState INTEGER undef(0) to undef(5) 
--  Sept.    6, 2007 I Wihelm Moser  I v1tov2 conversion error - exeMonitoring no(0) to no(2)
--  Sept.    6, 2007 I Wihelm Moser  I v1tov2 conversion error - blkJPRunNr INTEGER to Integer32 (0..65635)
--  Sept.    6, 2007 I Wihelm Moser  I v1tov2 conversion error - coRunNr INTEGER to Integer32 (0..65635)
--  November 8, 1999 I Roland Stiel  I Add new fields in the table
--                   I               I serverInstance
--                   I               I serverRunMode
--                   I               I serverDBState
--                   I               I serverSDBState
--

IMPORTS
    Integer32, OBJECT-TYPE, MODULE-IDENTITY, snmpModules, enterprises, NOTIFICATION-TYPE
        FROM SNMPv2-SMI
    DisplayString
        FROM SNMPv2-TC; -- 2007-09-06 WM - DisplayString changed fm RFC-1213

		uc4Vers2-module MODULE-IDENTITY
			LAST-UPDATED	"200903091000Z"
			ORGANIZATION	"UC4"
			CONTACT-INFO	"http://www.uc4.com"
			DESCRIPTION		"UC4Vers2-mib module identity"
			REVISION  		"200903091000Z"
			DESCRIPTION   "The initial SMIv2 version."		
			::= { snmpModules 1 }

		sbb 		OBJECT IDENTIFIER	::= { enterprises 2562 }
		uc4 		OBJECT IDENTIFIER	::= { sbb 1 }
		vers1 		OBJECT IDENTIFIER	::= { uc4 1 }
		agentData 	OBJECT IDENTIFIER	::= { vers1 1 }		

--
--  uc4vers2 Mib
--  ============
--          

--  agentData Group
--  ==

agentVersion OBJECT-TYPE
    SYNTAX      DisplayString (SIZE(0..12))
    MAX-ACCESS  read-only
    STATUS      current
    DESCRIPTION 
        "Version of the UC4 SNMP-Subagent in printable format V.RRRMMM-MMM."
    ::= { agentData 1 }

agentStartTime OBJECT-TYPE
    SYNTAX      DisplayString (SIZE(0..30))
    MAX-ACCESS  read-only
    STATUS      current
    DESCRIPTION 
        "Starttime of the UC4 SNMP-Subagent in printable format YYYY-MM-DD HH:MM:SS.MMM."
    ::= { agentData 2 }

agentNumberOfServerTasks OBJECT-TYPE
    SYNTAX      Integer32
    MAX-ACCESS  read-only
    STATUS      current
    DESCRIPTION 
        "Number of UC4 servers currently connected to the UC4 SNMP-Subagent."
    ::= { agentData 3 }

agentConnectCounter OBJECT-TYPE
    SYNTAX      Integer32  -- 2007-09-06 WM - agentConnectCounter changed fm Counter to Integer32
    MAX-ACCESS  read-only
    STATUS      current
    DESCRIPTION 
        "Number of UC4 servers that have ever been connected to the
         UC4 SNMP-subagent (historical value)."
    ::= { agentData 4 }


--  agentControl Group
--  ==================

--  For future use
agentControl OBJECT IDENTIFIER
    ::= { vers1 2 }

--  agentWork Group
--  ===============

agentWork OBJECT IDENTIFIER
    ::= { vers1 3 }

agentWorkSysID OBJECT-TYPE
    SYNTAX      DisplayString (SIZE(0..8))
    MAX-ACCESS  read-write
    STATUS      current
    DESCRIPTION 
        "Work variable for generating a trap (Subagent internal)."
    ::= { agentWork 1 }

agentWorkObject OBJECT-TYPE
    SYNTAX      DisplayString (SIZE(0..255))
    MAX-ACCESS  read-write
    STATUS      current
    DESCRIPTION 
        "Work variable for generating a trap (Subagent internal)."
    ::= { agentWork 2 }

agentWorkString1 OBJECT-TYPE
    SYNTAX      DisplayString (SIZE(0..255))
    MAX-ACCESS  read-write
    STATUS      current
    DESCRIPTION 
        "Work variable for generating a trap (Subagent internal)."
    ::= { agentWork 3 }

agentWorkString2 OBJECT-TYPE
    SYNTAX      DisplayString (SIZE(0..255))
    MAX-ACCESS  read-write
    STATUS      current
    DESCRIPTION 
        "Work variable for generating a trap (Subagent internal)."
    ::= { agentWork 4 }

agentWorkString3 OBJECT-TYPE
    SYNTAX      DisplayString (SIZE(0..255))
    MAX-ACCESS  read-write
    STATUS      current
    DESCRIPTION 
        "Work variable for generating a trap (Subagent internal)."
    ::= { agentWork 5 }

agentWorkString4 OBJECT-TYPE
    SYNTAX      DisplayString (SIZE(0..255))
    MAX-ACCESS  read-write
    STATUS      current
    DESCRIPTION 
        "Work variable for generating a trap (Subagent internal)."
    ::= { agentWork 6 }

agentWorkString5 OBJECT-TYPE
    SYNTAX      DisplayString (SIZE(0..255))
    MAX-ACCESS  read-write
    STATUS      current
    DESCRIPTION 
        "Work variable for generating a trap (Subagent internal)."
    ::= { agentWork 7 }

agentWorkInteger1 OBJECT-TYPE
    SYNTAX      Integer32
    MAX-ACCESS  read-write
    STATUS      current
    DESCRIPTION 
        "Work variable for generating a trap (Subagent internal)."
    ::= { agentWork 8 }

agentWorkInteger2 OBJECT-TYPE
    SYNTAX      Integer32
    MAX-ACCESS  read-write
    STATUS      current
    DESCRIPTION 
        "Work variable for generating a trap (Subagent internal)."
    ::= { agentWork 9 }

agentWorkInteger3 OBJECT-TYPE
    SYNTAX      Integer32
    MAX-ACCESS  read-write
    STATUS      current
    DESCRIPTION 
        "Work variable for generating a trap (Subagent internal)."
    ::= { agentWork 10 }

agentWorkInteger4 OBJECT-TYPE
    SYNTAX      Integer32
    MAX-ACCESS  read-write
    STATUS      current
    DESCRIPTION 
        "Work variable for generating a trap (Subagent internal)."
    ::= { agentWork 11 }

agentWorkInteger5 OBJECT-TYPE
    SYNTAX      Integer32
    MAX-ACCESS  read-write
    STATUS      current
    DESCRIPTION 
        "Work variable for generating a trap (Subagent internal)."
    ::= { agentWork 12 }

--  system Group
--  ============

uc4system OBJECT IDENTIFIER
    ::= { vers1 4 }

systemTable OBJECT-TYPE
    SYNTAX      SEQUENCE OF SystemEntry
    MAX-ACCESS  not-accessible
    STATUS      current
    DESCRIPTION 
        "This table contains a row for each UC4 System
         that connected to the UC4 SNMP-subagent during
         the lifetime of the subagent."
    ::= { uc4system 1 }

systemEntry OBJECT-TYPE
    SYNTAX      SystemEntry
    MAX-ACCESS  not-accessible
    STATUS      current
    DESCRIPTION 
        "systemTable entries indexed by sysSysID."
    INDEX       { sysSysID }
    ::= { systemTable 1 }

SystemEntry ::= SEQUENCE {
    sysSysID        DisplayString,
    sysStartTime    DisplayString,
    sysDbmsName     DisplayString,
    sysDbVersion    DisplayString,
    sysDbName       DisplayString,
    sysEMS          Integer32
}

sysSysID OBJECT-TYPE
    SYNTAX      DisplayString (SIZE(0..8))
    MAX-ACCESS  read-only
    STATUS      current
    DESCRIPTION 
        "The name of the UC4 system. 
         The value of the 'system' keyword in
         the .INI file of the server."
    ::= { systemEntry 1 }

sysStartTime OBJECT-TYPE
    SYNTAX      DisplayString (SIZE(1..19))
    MAX-ACCESS  read-only
    STATUS      current
    DESCRIPTION 
        "The start time of the 1st server of the UC4 system."
    ::= { systemEntry 2 }

sysDbmsName OBJECT-TYPE
    SYNTAX      DisplayString (SIZE(0..30))
    MAX-ACCESS  read-only
    STATUS      current
    DESCRIPTION 
        "The product name of the DB (Oracle 7, Microsoft SQL 7 etc.)."
    ::= { systemEntry 3 }

sysDbVersion OBJECT-TYPE
    SYNTAX      DisplayString (SIZE(0..30))
    MAX-ACCESS  read-only
    STATUS      current
    DESCRIPTION 
        "The version of the database management system."
    ::= { systemEntry 4 }

sysDbName OBJECT-TYPE
    SYNTAX      DisplayString (SIZE(0..30))
    MAX-ACCESS  read-only
    STATUS      current
    DESCRIPTION 
        "The name of the database returned by the DB management system."
    ::= { systemEntry 5 }

sysEMS OBJECT-TYPE
    SYNTAX      Integer32
    MAX-ACCESS  read-only
    STATUS      current
    DESCRIPTION 
        "Licence bitarray for enterprise management software."
    ::= { systemEntry 6 }

--  client Group
--  ============

client OBJECT IDENTIFIER
    ::= { vers1 5 }

clientTable OBJECT-TYPE
    SYNTAX      SEQUENCE OF ClientEntry
    MAX-ACCESS  not-accessible
    STATUS      current
    DESCRIPTION 
        "This table contains a row for each UC4 client
         of all UC4 systems connected to the UC4 SNMP-subagent."
    ::= { client 1 }

clientEntry OBJECT-TYPE
    SYNTAX      ClientEntry
    MAX-ACCESS  not-accessible
    STATUS      current
    DESCRIPTION 
        "clientTable entries indexed by cliSysID+cliClient."
    INDEX       { cliSysID, cliClient }
    ::= { clientTable 1 }

ClientEntry ::= SEQUENCE {
    cliSysID            DisplayString,
    cliClient           Integer32,
    cliLastModifyTime   DisplayString,
    cliState            INTEGER,
    cliMonitoring       INTEGER,
    cliInfo             DisplayString
}

cliSysID OBJECT-TYPE
    SYNTAX      DisplayString (SIZE(0..8))
    MAX-ACCESS  read-only
    STATUS      current
    DESCRIPTION 
        "The symbolic name of the UC4 system the client is a member of."
    ::= { clientEntry 1 }

cliClient OBJECT-TYPE
    SYNTAX      Integer32 (0..9999)
    MAX-ACCESS  read-only
    STATUS      current
    DESCRIPTION 
        "The numeric value representation of the client. This number unambiguously
         identifies the client within a UC4 system."
    ::= { clientEntry 2 }

cliLastModifyTime OBJECT-TYPE
    SYNTAX      DisplayString (SIZE(1..19))
    MAX-ACCESS  read-only
    STATUS      current
    DESCRIPTION 
        "Timestamp of the last update of this record."
    ::= { clientEntry 3 }

cliState OBJECT-TYPE
    SYNTAX      INTEGER { go(1), stop(2) } -- 2007-09-06 WM - cliState INTEGER stop(0) changed to stop(2)
    MAX-ACCESS  read-only
    STATUS      current
    DESCRIPTION 
        "The state of UC4 client.
         Shows whether the execution for this client is permitted (run) or suspended (stop).
         If a client is in stop state every automatic processing is suspended,
         but manual intervention is permitted."
    ::= { clientEntry 4 }

cliMonitoring OBJECT-TYPE
    SYNTAX      INTEGER { yes(1), no(2) } -- 2007-09-06 WM - cliMonitoring INTEGER no(0) changed to no(2)
    MAX-ACCESS  read-only
    STATUS      current
    DESCRIPTION 
        "Shows whether the client is important enough his activity
         to be monitored (productivity client).
         If yes (1) then the monitoring of the actvity of this client is desired.
         Monitoring of activity means watching for call operators and blocked jobs."
    ::= { clientEntry 5 }

cliInfo OBJECT-TYPE
    SYNTAX      DisplayString (SIZE(1..19))
    MAX-ACCESS  read-only
    STATUS      current
    DESCRIPTION 
        "Reserved for usage later."
    ::= { clientEntry 6 }

--  serverInstance Group
--  ====================

serverInstance OBJECT IDENTIFIER
    ::= { vers1 6 }

serverInstanceTable OBJECT-TYPE
    SYNTAX      SEQUENCE OF ServerInstanceEntry
    MAX-ACCESS  not-accessible
    STATUS      current
    DESCRIPTION 
        "This table contains a row for each
         UC4 Server connected to the UC4 SNMP-subagent."
    ::= { serverInstance 1 }

serverInstanceEntry OBJECT-TYPE
    SYNTAX      ServerInstanceEntry
    MAX-ACCESS  not-accessible
    STATUS      current
    DESCRIPTION 
        "serverInstanceTable entries indexed by srvSysID+srvName."
    INDEX       { srvSysID, srvName }
    ::= { serverInstanceTable 1 }

ServerInstanceEntry ::= SEQUENCE {
    srvSysID            DisplayString,
    srvName             DisplayString,
    srvLastModifyTime   DisplayString,
    srvVersion          DisplayString,
    srvStartTime        DisplayString,
    srvState            INTEGER,
    srvSrvConnect       Integer32,
    srvExeConnect       Integer32,
    srvDiaConnect       Integer32,
    srvBusyMin          Integer32,
    srvBusy10Min        Integer32,
    srvBusyHour         Integer32,
    srvRunMode          INTEGER,
    srvDBState          INTEGER,
    srvSDBState         INTEGER
}

srvSysID OBJECT-TYPE
    SYNTAX      DisplayString (SIZE(0..8))
    MAX-ACCESS  read-only
    STATUS      current
    DESCRIPTION 
        "The name of the UC4 system the server belongs to.
         The value of the 'system' keyword in the .INI file of the server."
    ::= { serverInstanceEntry 1 }

srvName OBJECT-TYPE
    SYNTAX      DisplayString (SIZE(0..8))
    MAX-ACCESS  read-only
    STATUS      current
    DESCRIPTION 
        "The name of the UC4 server. The value of the 'name'
         keyword in the .INI file of the server."
    ::= { serverInstanceEntry 2 }

srvLastModifyTime OBJECT-TYPE
    SYNTAX      DisplayString (SIZE(1..19))
    MAX-ACCESS  read-only
    STATUS      current
    DESCRIPTION 
        "Timestamp of the last update of this record."
    ::= { serverInstanceEntry 3 }

srvVersion OBJECT-TYPE
    SYNTAX      DisplayString (SIZE(0..5))
    MAX-ACCESS  read-only
    STATUS      current
    DESCRIPTION 
        "The version of the UC4 server."
    ::= { serverInstanceEntry 4 }

srvStartTime OBJECT-TYPE
    SYNTAX      DisplayString (SIZE(1..23))
    MAX-ACCESS  read-only
    STATUS      current
    DESCRIPTION 
        "Timestamp of the start time of the server."
    ::= { serverInstanceEntry 5 }

srvState OBJECT-TYPE
    SYNTAX      INTEGER { run(1), ended(2), abnormal(3), undef(4) } -- 2007-09-06 WM - srvState INTEGER undef(0) to undef(4)
    MAX-ACCESS  read-only
    STATUS      current
    DESCRIPTION 
        "The state of the UC4 server.
         undef(4)    a should not be case.
         run(1)      means the server is running.
         ended(2)    means the server ended normaly.
         abnormal(3) means the server ended abnormaly,
                     or the connection between the server
                     and the UC4 SNMP-subagent has been lost."
    ::= { serverInstanceEntry 6 }

srvSrvConnect OBJECT-TYPE
    SYNTAX      Integer32
    MAX-ACCESS  read-only
    STATUS      current
    DESCRIPTION 
        "Number of currently connected servers."
    ::= { serverInstanceEntry 7 }

srvExeConnect OBJECT-TYPE
    SYNTAX      Integer32
    MAX-ACCESS  read-only
    STATUS      current
    DESCRIPTION 
        "Number of currently connected executors."
    ::= { serverInstanceEntry 8 }

srvDiaConnect OBJECT-TYPE
    SYNTAX      Integer32
    MAX-ACCESS  read-only
    STATUS      current
    DESCRIPTION 
        "Number of currently connected dialogue clients."
    ::= { serverInstanceEntry 9 }

srvBusyMin OBJECT-TYPE
    SYNTAX      Integer32 (0..100)
    MAX-ACCESS  read-only
    STATUS      current
    DESCRIPTION 
        "Statistical Value. Average load of the server
         in % in the last minute before update."
    ::= { serverInstanceEntry 10 }

srvBusy10Min OBJECT-TYPE
    SYNTAX      Integer32 (0..100)
    MAX-ACCESS  read-only
    STATUS      current
    DESCRIPTION 
        "Statistical Value. Average load of the server
         in % in the last 10 minutes before update."
    ::= { serverInstanceEntry 11 }

srvBusyHour OBJECT-TYPE
    SYNTAX      Integer32 (0..100)
    MAX-ACCESS  read-only
    STATUS      current
    DESCRIPTION 
        "Statistical Value. Average load of the server
         in % in the last hour before update."
    ::= { serverInstanceEntry 12 }

srvRunMode OBJECT-TYPE
    SYNTAX      INTEGER { primary(1), standby(2), undef(3) } -- 2007-09-06 WM - srvRunMode INTEGER undef(0) to undef(3)
    MAX-ACCESS  read-only
    STATUS      current
    DESCRIPTION 
        "The role of the server in the UC4 system.
         undef(3)     yet unset
         primary(1)   the server is a primary in the UC4 system.
         standby(2)   the server is a standby in the UC4 system."
    ::= { serverInstanceEntry 13 }

srvDBState OBJECT-TYPE
    SYNTAX      INTEGER { online(1), offline(2), undef(3) } -- 2007-09-06 WM - srvDBState  INTEGER undef(0) to undef(3) 
    MAX-ACCESS  read-only
    STATUS      current
    DESCRIPTION 
        "The status of the connection between the UC4 server and
         the UC4 database.
         undef(3) 
         online(1)
         offline(2)"
    ::= { serverInstanceEntry 14 }

srvSDBState OBJECT-TYPE
    SYNTAX      INTEGER { online(1), offline(2), dismounted(3), noSDB(4) } -- 2007-09-06 WM - srvSDBState INTEGER noSDB(0) to noSDB(4)
    MAX-ACCESS  read-only
    STATUS      current
    DESCRIPTION 
        "The status of the connection between the UC4 server and
         the UC4 status database.
         4 = noSDB       no SRRC (Status Recording Recovery and Control),
         1 = online      SDB is online, status recording works
         2 = offline     because of failure(s) SDB has been switched off
         3 = dismounted  SDB is unaccessable"
    ::= { serverInstanceEntry 15 }

--  executor Group
--  ==============

executor OBJECT IDENTIFIER
    ::= { vers1 7 }

executorTable OBJECT-TYPE
    SYNTAX      SEQUENCE OF ExecutorEntry
    MAX-ACCESS  not-accessible
    STATUS      current
    DESCRIPTION 
        "This table contains a row for each
         UC4 executor connected to any server that
         is connected to the UC4 SNMP-subagent."
    ::= { executor 1 }

executorEntry OBJECT-TYPE
    SYNTAX      ExecutorEntry
    MAX-ACCESS  not-accessible
    STATUS      current
    DESCRIPTION 
        "executorTable entries indexed by exeSysID+exeSrvName+exeName+exeType."
    INDEX       { exeSysID, exeSrvName, exeName, exeType }
    ::= { executorTable 1 }

ExecutorEntry ::= SEQUENCE {
    exeSysID            DisplayString,
    exeSrvName          DisplayString,
    exeName             DisplayString,
    exeType             DisplayString,
    exeLastModifyTime   DisplayString,
    exeHost             DisplayString,
    exeVersion          DisplayString,
    exeHardware         DisplayString,
    exeSoftware         DisplayString,
    exeSoftwareVers     DisplayString,
    exeJCLTyp           DisplayString,
    exeConnTime         DisplayString,
    exeState            INTEGER,
    exeLastPing         DisplayString,
    exeMonitoring       INTEGER,
    exeInfo             DisplayString
}

exeSysID OBJECT-TYPE
    SYNTAX      DisplayString (SIZE(0..8))
    MAX-ACCESS  read-only
    STATUS      current
    DESCRIPTION 
        "The name of the UC4 system the executor belongs to.
         The value of the 'system' keyword in the .INI file of the server."
    ::= { executorEntry 1 }

exeSrvName OBJECT-TYPE
    SYNTAX      DisplayString (SIZE(0..8))
    MAX-ACCESS  read-only
    STATUS      current
    DESCRIPTION 
        "The name of the server the executor is connected to."
    ::= { executorEntry 2 }

exeName OBJECT-TYPE
    SYNTAX      DisplayString (SIZE(0..8))
    MAX-ACCESS  read-only
    STATUS      current
    DESCRIPTION 
        "The name of the executor. The value of the 'name'
         keyword in the .INI file of the executor."
    ::= { executorEntry 3 }

exeType OBJECT-TYPE
    SYNTAX      DisplayString (SIZE(0..8))
    MAX-ACCESS  read-only
    STATUS      current
    DESCRIPTION 
        "The type of the executor. The value of the 'typ'
         keyword in the .INI file of the executor."
    ::= { executorEntry 4 }

exeLastModifyTime OBJECT-TYPE
    SYNTAX      DisplayString (SIZE(1..19))
    MAX-ACCESS  read-only
    STATUS      current
    DESCRIPTION 
        "Timestamp of the last update of this record."
    ::= { executorEntry 5 }

exeHost OBJECT-TYPE
    SYNTAX      DisplayString (SIZE(0..8))
    MAX-ACCESS  read-only
    STATUS      current
    DESCRIPTION 
        "The name of the executor's host. The value of the 'host'
         keyword in the .INI file of the executor"
    ::= { executorEntry 6 }

exeVersion OBJECT-TYPE
    SYNTAX      DisplayString (SIZE(0..5))
    MAX-ACCESS  read-only
    STATUS      current
    DESCRIPTION 
        "The version of the executor."
    ::= { executorEntry 7 }

exeHardware OBJECT-TYPE
    SYNTAX      DisplayString (SIZE(0..20))
    MAX-ACCESS  read-only
    STATUS      current
    DESCRIPTION 
        "CPU type obtained by the executor from the run-time environment."
    ::= { executorEntry 8 }

exeSoftware OBJECT-TYPE
    SYNTAX      DisplayString (SIZE(0..20))
    MAX-ACCESS  read-only
    STATUS      current
    DESCRIPTION 
        "The executor is running for software."
    ::= { executorEntry 9 }

exeSoftwareVers OBJECT-TYPE
    SYNTAX      DisplayString (SIZE(0..20))
    MAX-ACCESS  read-only
    STATUS      current
    DESCRIPTION 
        "OS type obtained by the executor from the run-time environment."
    ::= { executorEntry 10 }

exeJCLTyp OBJECT-TYPE
    SYNTAX      DisplayString (SIZE(0..8))
    MAX-ACCESS  read-only
    STATUS      current
    DESCRIPTION 
        "Job Control Language for job generation.
         The value of the 'UC_HOST_JCL_VAR' keyword
         in the .INI file of the executor"
    ::= { executorEntry 11 }

exeConnTime OBJECT-TYPE
    SYNTAX      DisplayString (SIZE(1..19))
    MAX-ACCESS  read-only
    STATUS      current
    DESCRIPTION 
        "Timestamp of the last connection setup of the executor."
    ::= { executorEntry 12 }

exeState OBJECT-TYPE
    SYNTAX      INTEGER { run(1), ended(2), lost(3), timeout(4), -- 2007-09-06 WM - exeState INTEGER undef(0) to undef(5) 
                    undef(5) }
    MAX-ACCESS  read-only
    STATUS      current
    DESCRIPTION 
        "The state of the executor.
         undef(5)   not set yet
         run(1)     the executor is working
         ended(2)   the executor is stopped or not started yet
         lost(3)    the connection between the executor and
                    the server has been broken.
         timeout(4) the connection on the transport layer seems to be OK,
                    but the application (executor) does not respond"
    ::= { executorEntry 13 }

exeLastPing OBJECT-TYPE
    SYNTAX      DisplayString (SIZE(1..19))
    MAX-ACCESS  read-only
    STATUS      current
    DESCRIPTION 
        "The timestamp of the last attempt to get life-sign from the executor.."
    ::= { executorEntry 14 }

exeMonitoring OBJECT-TYPE
    SYNTAX      INTEGER { yes(1), no(2) } -- 2007-09-06 WM - exeMonitoring no(0) to no(2)
    MAX-ACCESS  read-only
    STATUS      current
    DESCRIPTION 
        "Shows whether the executor is important enough its availability
         to be monitored (productivity executor).
         If yes (1) then the monitoring of the availability of this executor is desired."
    ::= { executorEntry 15 }

exeInfo OBJECT-TYPE
    SYNTAX      DisplayString (SIZE(1..19))
    MAX-ACCESS  read-only
    STATUS      current
    DESCRIPTION 
        "Reserved for usage later."
    ::= { executorEntry 16 }

--  blockingPoints Group
--  ====================

blockingPoints OBJECT IDENTIFIER
    ::= { vers1 8 }

blockingPointsTable OBJECT-TYPE
    SYNTAX      SEQUENCE OF BlockingPointEntry
    MAX-ACCESS  not-accessible
    STATUS      current
    DESCRIPTION 
        "This table contains a row for each
         blocking object in a job plan."
    ::= { blockingPoints 1 }

blockingPointEntry OBJECT-TYPE
    SYNTAX      BlockingPointEntry
    MAX-ACCESS  not-accessible
    STATUS      current
    DESCRIPTION 
        "blockingPointsTable entries
         indexed by blkSysID+blkClient+blkJPRunNr+blkJPLNR."
    INDEX       { blkSysID, blkClient, blkJPRunNr, blkJPLNR }
    ::= { blockingPointsTable 1 }

BlockingPointEntry ::= SEQUENCE {
    blkSysID            DisplayString,
    blkClient           Integer32,
    blkJPRunNr          Integer32,
    blkJPLNR            Integer32,
    blkLastModifyTime   DisplayString,
    blkJPName           DisplayString,
    blkObjTyp           DisplayString,
    blkObjName          DisplayString,
    blkObjRunNr         Integer32
}

blkSysID OBJECT-TYPE
    SYNTAX      DisplayString (SIZE(0..8))
    MAX-ACCESS  read-only
    STATUS      current
    DESCRIPTION 
        "The name of UC4 system in which the automatic job execution is blocked."
    ::= { blockingPointEntry 1 }

blkClient OBJECT-TYPE
    SYNTAX      Integer32 (0..9999)
    MAX-ACCESS  read-only
    STATUS      current
    DESCRIPTION 
        "The numeric value of the client/mandant the blocking point belongs to."
    ::= { blockingPointEntry 2 }

blkJPRunNr OBJECT-TYPE
    SYNTAX      Integer32 (0..65635) -- 2007-09-06 WM - blkJPRunNr INTEGER to Integer32 (0..65635)
    MAX-ACCESS  read-only
    STATUS      current
    DESCRIPTION 
        "The run number of the job plan where blocking occurred."
    ::= { blockingPointEntry 3 }

blkJPLNR OBJECT-TYPE
    SYNTAX      Integer32 (0..255)
    MAX-ACCESS  read-only
    STATUS      current
    DESCRIPTION 
        "The line identification of the task in which the blocking occurred."
    ::= { blockingPointEntry 4 }

blkLastModifyTime OBJECT-TYPE
    SYNTAX      DisplayString (SIZE(1..19))
    MAX-ACCESS  read-only
    STATUS      current
    DESCRIPTION 
        "Timestamp of the last update of this record."
    ::= { blockingPointEntry 5 }

blkJPName OBJECT-TYPE
    SYNTAX      DisplayString (SIZE(0..200))
    MAX-ACCESS  read-only
    STATUS      current
    DESCRIPTION 
        "The name of the job plan in which the blocking occurred."
    ::= { blockingPointEntry 6 }

blkObjTyp OBJECT-TYPE
    SYNTAX      DisplayString (SIZE(0..8))
    MAX-ACCESS  read-only
    STATUS      current
    DESCRIPTION 
        "The type of the object that caused the blocking."
    ::= { blockingPointEntry 7 }

blkObjName OBJECT-TYPE
    SYNTAX      DisplayString (SIZE(0..200))
    MAX-ACCESS  read-only
    STATUS      current
    DESCRIPTION 
        "The name of the object that caused the blocking."
    ::= { blockingPointEntry 8 }

blkObjRunNr OBJECT-TYPE
    SYNTAX      Integer32
    MAX-ACCESS  read-only
    STATUS      current
    DESCRIPTION 
        "The run number of the object that caused the blocking."
    ::= { blockingPointEntry 9 }

callOperator OBJECT IDENTIFIER
    ::= { vers1 9 }

callOperatorTable OBJECT-TYPE
    SYNTAX      SEQUENCE OF CallOperatorEntry
    MAX-ACCESS  not-accessible
    STATUS      current
    DESCRIPTION 
        "This table contains a row for each
         CallOperator issued by any server that
         is connected to the UC4 SNMP-subagent."
    ::= { callOperator 1 }

callOperatorEntry OBJECT-TYPE
    SYNTAX      CallOperatorEntry
    MAX-ACCESS  not-accessible
    STATUS      current
    DESCRIPTION 
        "callOperatorTable entries indexed by coSysID+coClient+coRunNr."
    INDEX       { coSysID, coClient, coRunNr }
    ::= { callOperatorTable 1 }

CallOperatorEntry ::= SEQUENCE {
    coSysID             DisplayString,
    coClient            Integer32,
    coRunNr             Integer32,
    coLastModifyTime    DisplayString,
    coName              DisplayString,
    coTyp               INTEGER,
    coText              DisplayString,
    coState             Integer32
}

coSysID OBJECT-TYPE
    SYNTAX      DisplayString (SIZE(0..8))
    MAX-ACCESS  read-only
    STATUS      current
    DESCRIPTION 
        "The name of the UC4 system the CallOperator is originated from."
    ::= { callOperatorEntry 1 }

coClient OBJECT-TYPE
    SYNTAX      Integer32 (0..99)
    MAX-ACCESS  read-only
    STATUS      current
    DESCRIPTION 
        "The numeric value of the client the CallOperator belongs to."
    ::= { callOperatorEntry 2 }

coRunNr OBJECT-TYPE
    SYNTAX      Integer32 (0..65635) -- 2007-09-06 WM - coRunNr INTEGER to Integer32 (0..65635)
    MAX-ACCESS  read-only
    STATUS      current
    DESCRIPTION 
        "The RunNr of the CallOperator."
    ::= { callOperatorEntry 3 }

coLastModifyTime OBJECT-TYPE
    SYNTAX      DisplayString (SIZE(1..19))
    MAX-ACCESS  read-only
    STATUS      current
    DESCRIPTION 
        "Timestamp of the last update of this record."
    ::= { callOperatorEntry 4 }

coName OBJECT-TYPE
    SYNTAX      DisplayString (SIZE(0..200))
    MAX-ACCESS  read-only
    STATUS      current
    DESCRIPTION 
        "The symblic name of CallOperator."
    ::= { callOperatorEntry 5 }

coTyp OBJECT-TYPE
    SYNTAX      INTEGER { question(1), message(2), alarm(3) }
    MAX-ACCESS  read-only
    STATUS      current
    DESCRIPTION 
        "Type of CallOperator.
         question(1)
         message(2)
         alarm(3)"
    ::= { callOperatorEntry 6 }

coText OBJECT-TYPE
    SYNTAX      DisplayString (SIZE(0..255))
    MAX-ACCESS  read-only
    STATUS      current
    DESCRIPTION 
        "The explanation text defined in CallOperator."
    ::= { callOperatorEntry 7 }

coState OBJECT-TYPE
    SYNTAX      Integer32
    MAX-ACCESS  read-only
    STATUS      current
    DESCRIPTION 
        "The current state of the CallOperator.
         Calling the operator (1542),
         Escalated (1556),
         Accepted (1553)"
    ::= { callOperatorEntry 8 }

--  Trap definitions 
--  ====================

serverStarted	NOTIFICATION-TYPE
		OBJECTS {	
			agentWorkSysID,
			agentWorkObject,
			agentWorkInteger1,
			agentWorkInteger2
		}
		STATUS			current
		DESCRIPTION	
				"UC4 Server started"
		::= { 3400 }

serverEnd	NOTIFICATION-TYPE
		OBJECTS {	
			agentWorkSysID,
			agentWorkObject,
			agentWorkInteger1,
			agentWorkInteger2
		}
		STATUS			current
		DESCRIPTION	
				"End of a work of dialog process (regardless of the reason) or normal end of the primary work process"
		::= { 3401 }

primaryWorkProcessAborted	NOTIFICATION-TYPE
		OBJECTS {	
			agentWorkSysID,
			agentWorkObject,
			agentWorkInteger1,
			agentWorkInteger2
		}
		STATUS			current
		DESCRIPTION	
				"Primary work process (PWP) ended abnormally"
		::= { 3410 }
		
databaseError	NOTIFICATION-TYPE
		OBJECTS {	
			agentWorkSysID,
			agentWorkObject,
			agentWorkString1
		}
		STATUS			current
		DESCRIPTION	
				"Serious error when accessing the UC4 database. Access no longer possible."
		::= { 3536 }

databaseReconnect	NOTIFICATION-TYPE
		OBJECTS {	
			agentWorkSysID,
			agentWorkObject
		}
		STATUS			current
		DESCRIPTION	
				"Connection to UC4 database re-established."
		::= { 3538 }

agentStop	NOTIFICATION-TYPE
		OBJECTS {	
			agentWorkSysID,
			agentWorkObject,
			agentWorkString1,
			agentWorkInteger1
		}
		STATUS			current
		DESCRIPTION	
				"Shutting down an Agent."
		::= { 11603 }
		
agentStart	NOTIFICATION-TYPE
		OBJECTS {	
			agentWorkSysID,
			agentWorkObject,
			agentWorkString1,
			agentWorkInteger1
		}
		STATUS			current
		DESCRIPTION	
				"Cold start of an Agent."
		::= { 11604 }
	
agentReset	NOTIFICATION-TYPE
		OBJECTS {	
			agentWorkSysID,
			agentWorkObject,
			agentWorkString1
		}
		STATUS			current
		DESCRIPTION	
				"Warm start of an Agent."
		::= { 11622 }
		
agentDisconnected	NOTIFICATION-TYPE
		OBJECTS {	
			agentWorkSysID,
			agentWorkObject,
			agentWorkString1,
			agentWorkInteger1	
		}
		STATUS			current
		DESCRIPTION	
				"Ends connection to an Agent."
		::= { 11650 }

agentSAPDisconnected	NOTIFICATION-TYPE
		OBJECTS {	
			agentWorkSysID,
			agentWorkObject,
			agentWorkString1,
			agentWorkInteger1	
		}
		STATUS			current
		DESCRIPTION	
				"SAP Agent not longer connected to SAP system."
		::= { 11652 }				
		
agentSAPReconnect	NOTIFICATION-TYPE
		OBJECTS {	
			agentWorkSysID,
			agentWorkObject,
			agentWorkString1,
			agentWorkInteger1	
		}
		STATUS			current
		DESCRIPTION	
				"SAP Agent reconnected to SAP system."
		::= { 11662 }	

systemError	NOTIFICATION-TYPE
		OBJECTS {	
			agentWorkSysID,
			agentWorkObject,
			agentWorkString1,
			agentWorkInteger1	
		}
		STATUS			current
		DESCRIPTION	
				"System error of the UC4 Server."
		::= { 11801 }	

serverPWPchanged	NOTIFICATION-TYPE
		OBJECTS {	
			agentWorkSysID,
			agentWorkObject,
			agentWorkInteger1,
			agentWorkInteger2	
		}
		STATUS			current
		DESCRIPTION	
				"Primary Server has changed."
		::= { 11818 }	

notificationMessage	NOTIFICATION-TYPE
		OBJECTS {	
			agentWorkSysID,
			agentWorkObject,
			agentWorkString1,
			agentWorkString2,
			agentWorkInteger1
		}
		STATUS			current
		DESCRIPTION	
				"Message of a Notification."
		::= { 801450 }

-- end of module UC4Vers2-MIB.
END
