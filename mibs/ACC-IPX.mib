ACC-IPX DEFINITIONS ::= BEGIN

    IMPORTS
	 OBJECT-TYPE, IpAddress, TimeTicks, Gauge, Counter FROM RFC1155-SMI
         accTrapLogSeqNum FROM ACC-SYSTEM
	 accBRG, DisplayString, RowStatus, IfIndex, SmdsAddress
             FROM ACC-MIB;

-- IPX Group
   accIpx         OBJECT IDENTIFIER ::= { accBRG 22 }
     accIpxParms	OBJECT IDENTIFIER ::= { accIpx 1 }
       accIpxAdStat  OBJECT-TYPE   
			SYNTAX	INTEGER {
				on(1),
				off(2)
			}
			ACCESS	read-write
			STATUS	mandatory
			DESCRIPTION
                " Administrative status of IPX routing protocol"
			::= { accIpxParms 1 }
	  accIpxCkSum  OBJECT-TYPE   
			SYNTAX	INTEGER {
				off(1),
				packet(2),
				header(3)
			}
			ACCESS	read-write
			STATUS	mandatory
			DESCRIPTION
                " Checksumming of IPX protocol"
			::= { accIpxParms 2 }
	  accIpxSpltHorz  OBJECT-TYPE   
			SYNTAX	INTEGER {
				off(1),
				simple(2),
				poison(3)
			}
			ACCESS	read-write
			STATUS	mandatory
			DESCRIPTION
                " Split horizon mode of IPX protocol"
			::= { accIpxParms 3 }
	  accIpxAllNets  OBJECT-TYPE   
			SYNTAX	INTEGER {
				on(1),
				off(2)
			}
			ACCESS	read-write
			STATUS	mandatory
			DESCRIPTION
                " All nets mode"
			::= { accIpxParms 4 }
	  accIpxMode  OBJECT-TYPE   
			SYNTAX	INTEGER {
				ipx(1),
				ub(2),
				repeat(3)
			}
			ACCESS	read-write
			STATUS	mandatory
			DESCRIPTION
                " RIP protocol type to use"
			::= { accIpxParms 5 }
	  accIpxWdFilter  OBJECT-TYPE   
			SYNTAX	INTEGER {
				disable(1),
				enable(2)
			}
			ACCESS	read-write
			STATUS	mandatory
			DESCRIPTION
                " Switch to enable/disable a dial originate filter
		of the IPX file server watchdog (Keep Alive) packet."
			::= { accIpxParms 6 }
	  accIpxTrigUpdates  OBJECT-TYPE   
			SYNTAX	INTEGER {
				on (1),
				off (2)
			}
			ACCESS	read-write
			STATUS	mandatory
			DESCRIPTION
                " Sets the default for triggered updates to either on or
		off. If on, the default behavior will be to send 
		triggered updates as well as timer generated updates.
		If off, only timer generated updates are sent. 
		Triggered updates are best used with long timer update 
		intervals in order to reduce update traffic."
			DEFVAL { on } 
			::= { accIpxParms 7 }
     accIpxNetTable  OBJECT-TYPE   
			SYNTAX	SEQUENCE OF AccIpxNetEntry
			ACCESS	not-accessible
			STATUS	mandatory
			DESCRIPTION
                " List of IPX Networks.
	          Entries are added/deleted via management action."
			::= { accIpx 2 }
	  accIpxNetEntry  OBJECT-TYPE   
			SYNTAX	AccIpxNetEntry
			ACCESS	not-accessible
			STATUS	mandatory
			DESCRIPTION
                " Information on specific network entry. "
                        INDEX { accIpxNetPort }
			::= { accIpxNetTable 1 }
        AccIpxNetEntry ::= SEQUENCE {
			accIpxNetPort		INTEGER,
			accIpxNetNumber		OCTET STRING,
			accIpxNetType		INTEGER,
			accIpxNetEncap		INTEGER,
			accIpxNetSlot		INTEGER,
			accIpxNetAdStat		INTEGER,
			accIpxNetMtu		INTEGER,
			accIpxNetUpdate		TimeTicks,
			accIpxNetHops		INTEGER,
			accIpxNetCost		INTEGER,
			accIpxNetX25InOutAddr	DisplayString,
			accIpxNetX25InAddr	DisplayString,
			accIpxNetX25Idle	TimeTicks,
			accIpxNetX25PktVal	INTEGER,
			accIpxNetX25PktWin	INTEGER,
			accIpxNetEntryStat	INTEGER,
                        accIpxNetFncAddr	OCTET STRING,
                        accIpxNetSrMode		INTEGER,
			accIpxNetX25FacIndex	INTEGER,
			accIpxNetDlci		INTEGER,
			accIpxNetWdState	INTEGER,
			accIpxNetRtgHldTmr	INTEGER,
			accIpxNetRtgPollCnt	INTEGER,
			accIpxNetRtgProtType	INTEGER,
			accIpxNetRtgSettleTimer	INTEGER,
			accIpxNetRtgQuietTimer	INTEGER,
			accIpxNetRtgDiagLevel	INTEGER,
			accIpxNetDialProt	INTEGER
 			}
	  accIpxNetPort  OBJECT-TYPE   
			SYNTAX	INTEGER
			ACCESS	read-write
			STATUS	mandatory
			DESCRIPTION
                           " IPX logical port number "
			::= { accIpxNetEntry 1 }
	  accIpxNetNumber  OBJECT-TYPE   
			SYNTAX	OCTET STRING
			ACCESS	read-write
			STATUS	mandatory
			DESCRIPTION
                            " IPX network number "
			::= { accIpxNetEntry 2 }
	  accIpxNetType  OBJECT-TYPE   
			SYNTAX	INTEGER {
				enet(1),
				token-ring(2),
				lapb(3),
				x25(4),
				frame-relay(5),
				ppp(6),
				fddi(7),
				dial(8),
				multilink(9)
			}
			ACCESS	read-write
			STATUS	mandatory
			DESCRIPTION
                " Type of network "
			::= { accIpxNetEntry 3 }
	  accIpxNetEncap  OBJECT-TYPE   
			SYNTAX	INTEGER {
				none(0),
				v2(1),
				raw(2),
				llc(3),
				snap(4)
				}
			ACCESS	read-write
			STATUS	mandatory
			DESCRIPTION
                " LAN Encapsulation used for Ethernets.
		"
			::= { accIpxNetEntry 4 }
	  accIpxNetSlot  OBJECT-TYPE   
			SYNTAX	INTEGER {
				j1(1),
				j2(2),
				j3(3),
				b1(4)
			}
			ACCESS	read-write
			STATUS	mandatory
			DESCRIPTION
                " Slot to which the network is attached "
			::= { accIpxNetEntry 5 }
	  accIpxNetAdStat  OBJECT-TYPE   
			SYNTAX	INTEGER {
				on(1),
				off(2)
			}
			ACCESS	read-write
			STATUS	mandatory
			DESCRIPTION
	        " Administrative status of network
	          Object will be defaulted if missing in set PDU which
	          adds entries."
			::= { accIpxNetEntry 6 }
	  accIpxNetMtu  OBJECT-TYPE   
			SYNTAX	INTEGER (576..65535)
			ACCESS	read-write
			STATUS	mandatory
			DESCRIPTION
	        " Maximum packet size
	          Object will be defaulted if missing in set PDU which
	          adds entries."
			::= { accIpxNetEntry 7 }
	  accIpxNetUpdate  OBJECT-TYPE   
			SYNTAX	TimeTicks
			ACCESS	read-write
			STATUS	mandatory
			DESCRIPTION
	                    " Update interval "
                        DEFVAL { 1500 }
			::= { accIpxNetEntry 8 }
	  accIpxNetHops  OBJECT-TYPE   
			SYNTAX	INTEGER
			ACCESS	read-write
			STATUS	mandatory
			DESCRIPTION
	                     " Hop count "
                        DEFVAL { 1 }
			::= { accIpxNetEntry 9 }
	  accIpxNetCost  OBJECT-TYPE   
			SYNTAX	INTEGER
			ACCESS	read-write
			STATUS	mandatory
			DESCRIPTION
	                   " Cost metric "
                        DEFVAL { 1 }
			::= { accIpxNetEntry 10 }
	  accIpxNetX25InOutAddr  OBJECT-TYPE   
			SYNTAX  DisplayString	
			ACCESS	read-write
			STATUS	mandatory
			DESCRIPTION
	        " X25 address to send to and to receive packets from.
	          Object required in set PDU adding X25-type circuit"
			::= { accIpxNetEntry 11 }
	  accIpxNetX25InAddr  OBJECT-TYPE   
			SYNTAX  DisplayString	
			ACCESS	read-write
			STATUS	mandatory
			DESCRIPTION
	        " Receive-only X25 address
	          Object not required in set PDU (defaults to In/Out address)"
			::= { accIpxNetEntry 12 }
	  accIpxNetX25Idle  OBJECT-TYPE   
			SYNTAX	TimeTicks 
			ACCESS	read-write
			STATUS	mandatory
			DESCRIPTION
	                   " Time X25 connection can be idle before it is 
	                     determined to be not busy."
                        DEFVAL { 30000 }
			::= { accIpxNetEntry 13 }
	  accIpxNetX25PktVal  OBJECT-TYPE   
			SYNTAX	INTEGER (0..1024)
			ACCESS	read-write
			STATUS	mandatory
			DESCRIPTION
	                    " X25 packet size "
                        DEFVAL { 0 }
			::= { accIpxNetEntry 14 }
	  accIpxNetX25PktWin  OBJECT-TYPE   
			SYNTAX	INTEGER (0..127)
			ACCESS	read-write
			STATUS	mandatory
			DESCRIPTION
	                   " X25 packet window "
                        DEFVAL { 0 }
			::= { accIpxNetEntry 15 }
	  accIpxNetEntryStat  OBJECT-TYPE   
			SYNTAX	INTEGER {
				other(1),
				invalid(2)
			    }
			ACCESS	read-write
			STATUS	mandatory
			DESCRIPTION
	                     " Status of this table entry
		               Set this object to invalid to delete entry."
                        DEFVAL { other }
			::= { accIpxNetEntry 16 }
	accIpxNetFncAddr OBJECT-TYPE
	    SYNTAX	OCTET STRING  -- (SIZE (6))
	    ACCESS	read-write
	    STATUS	mandatory
	    DESCRIPTION
		 " The MAC-layer functional address for sending and
		   receiving multicasts."
	    ::= { accIpxNetEntry 17 }
	accIpxNetSrMode OBJECT-TYPE
             SYNTAX	INTEGER { 
			off(0), 
			ape(1), 
			spe(2) 
			}
	    ACCESS	read-write
	    STATUS	mandatory
            DESCRIPTION
		 " The source-routing mode for token-ring networks."
            ::= { accIpxNetEntry 18 }
        accIpxNetX25FacIndex OBJECT-TYPE
                   SYNTAX      INTEGER (0..255)
                   ACCESS      read-write
                   STATUS      mandatory
                   DESCRIPTION
                   " Index of optional facility string or 0."
                   DEFVAL { 0 }
                   ::= { accIpxNetEntry 19 }
        accIpxNetDlci       OBJECT-TYPE
                   SYNTAX  INTEGER
                   ACCESS  read-write
                   STATUS  mandatory
                   DESCRIPTION
                   " Frame Relay DLCI for this port"
                   ::= { accIpxNetEntry 20 }
        accIpxNetWdState   OBJECT-TYPE
                   SYNTAX  INTEGER {
			allow(1),
			discard(2),
			proxy(3)
			}
                   ACCESS  read-write
                   STATUS  mandatory
                   DESCRIPTION
                   " Determines the IPX watchdog state on a specific logical
                     port. The default is ALLOW for LAN/DEDICATED WAN type,
                     PROXY for X.21/FFR/Dial type."
                   ::= { accIpxNetEntry 21 }
        accIpxNetRtgHldTmr   OBJECT-TYPE
                   SYNTAX  INTEGER (1..255)
                   ACCESS  read-write
                   STATUS  mandatory
                   DESCRIPTION
                   " Demand RIP/SAP Hold timer"
                   ::= { accIpxNetEntry 22 }
        accIpxNetRtgPollCnt   OBJECT-TYPE
                   SYNTAX  INTEGER (1..255)
                   ACCESS  read-write
                   STATUS  mandatory
                   DESCRIPTION
                   " Demand RIP/SAP Poll Count"
                   ::= { accIpxNetEntry 23 }
        accIpxNetRtgProtType   OBJECT-TYPE
                   SYNTAX  INTEGER {
			off(1),
			normal(2),
			demand(3),
			snapshot(4)
			}
                   ACCESS  read-write
                   STATUS  mandatory
                   DESCRIPTION
                   " Demand RIP/SAP Poll Count"
                   ::= { accIpxNetEntry 24 }
        accIpxNetRtgSettleTimer   OBJECT-TYPE
                   SYNTAX  INTEGER (1..900)
                   ACCESS  read-write
                   STATUS  mandatory
                   DESCRIPTION
                   " Demand RIP/SAP Settle Timer"
                   ::= { accIpxNetEntry 25 }
        accIpxNetRtgQuietTimer   OBJECT-TYPE
                   SYNTAX  INTEGER (0..65535)
                   ACCESS  read-write
                   STATUS  mandatory
                   DESCRIPTION
                   " Demand RIP/SAP Poll Count"
                   ::= { accIpxNetEntry 26 }
        accIpxNetRtgDiagLevel   OBJECT-TYPE
                   SYNTAX  INTEGER (1..7)
                   ACCESS  read-write
                   STATUS  mandatory
                   DESCRIPTION
                   " Demand RIP/SAP Diag level"
                   ::= { accIpxNetEntry 27 }
        accIpxNetDialProt   OBJECT-TYPE
                   SYNTAX  INTEGER {
				none(1),
				ppp(2),
				x25(3)
		   } 
                   ACCESS  read-write
                   STATUS  mandatory
                   DESCRIPTION
                   " Ipx dial protocol forwarder for X25/PPP"
                   ::= { accIpxNetEntry 28 }
     accIpxRtTable  OBJECT-TYPE   
			SYNTAX	SEQUENCE OF AccIpxRtEntry
			ACCESS	not-accessible
			STATUS	mandatory
			DESCRIPTION
                " List of routes to other IPX networks"
			::= { accIpx 3 }
        accIpxRtEntry  OBJECT-TYPE   
			SYNTAX	AccIpxRtEntry
			ACCESS	not-accessible
			STATUS	mandatory
			DESCRIPTION
                " Information on route to destination network"
		        INDEX { accIpxRtDest }
			::= { accIpxRtTable 1 }
        AccIpxRtEntry ::= SEQUENCE {
			accIpxRtDest		OCTET STRING,
			accIpxRtNxtNet		OCTET STRING,
			accIpxRtRouter		OCTET STRING,
			accIpxRtHops		INTEGER,
			accIpxRtCost		INTEGER,
			accIpxRtType		INTEGER,
			accIpxRtOwner		INTEGER,
			accIpxRtAge		TimeTicks,
			accIpxRtPort		INTEGER
 			}
	  accIpxRtDest  OBJECT-TYPE   
			SYNTAX	OCTET STRING  -- (SIZE (4))
			ACCESS	read-only
			STATUS	mandatory
			DESCRIPTION
	        " Destination network."
			::= { accIpxRtEntry 1 }
	  accIpxRtNxtNet  OBJECT-TYPE
			SYNTAX	OCTET STRING
			ACCESS	read-only
			STATUS	mandatory
			DESCRIPTION
		 " The next network along the way 
		   to the destination network."
			::= { accIpxRtEntry 2 }
	  accIpxRtRouter  OBJECT-TYPE   
			SYNTAX	OCTET STRING 
			ACCESS	read-only
			STATUS	mandatory
			DESCRIPTION
	        " Router on next IPX network on route"
			::= { accIpxRtEntry 3 }
	  accIpxRtHops  OBJECT-TYPE   
			SYNTAX	INTEGER
			ACCESS	read-only
			STATUS	mandatory
			DESCRIPTION
	        " Number of hops to remote network"
			::= { accIpxRtEntry 4 }
	  accIpxRtCost  OBJECT-TYPE   
			SYNTAX	INTEGER
			ACCESS	read-only
			STATUS	mandatory
			DESCRIPTION
	        " Cost to remote network"
			::= { accIpxRtEntry 5 }
	  accIpxRtType  OBJECT-TYPE   
			SYNTAX	INTEGER {
				public(1),
				direct(2),
				static(3)
			    }
			ACCESS	read-only
			STATUS	mandatory
			DESCRIPTION
	        " Type of route"
			::= { accIpxRtEntry 6 }
	  accIpxRtOwner  OBJECT-TYPE   
			SYNTAX	INTEGER {
				lli(1),
				nms(2),
				rip(3)
			    }
			ACCESS	read-only
			STATUS	mandatory
			DESCRIPTION
	        " Source of route"
			::= { accIpxRtEntry 7 }
	  accIpxRtAge  OBJECT-TYPE   
			SYNTAX	TimeTicks
			ACCESS	read-only
			STATUS	mandatory
			DESCRIPTION
	        " Age of route"
			::= { accIpxRtEntry 8 }
	  accIpxRtPort  OBJECT-TYPE
			SYNTAX	INTEGER
			ACCESS	read-only
			STATUS	mandatory
			DESCRIPTION
		 " The logical port number through which packets will be
		   forwarded to the destination network."
			::= { accIpxRtEntry 9 }
    accIpxRipStat   OBJECT IDENTIFIER ::= { accIpx 4 }
           accIpxRipReqIns OBJECT-TYPE   
			SYNTAX	Counter
			ACCESS	read-only
			STATUS	mandatory
			DESCRIPTION
	        " IPX RIP requests received"
			::= { accIpxRipStat 1 }
           accIpxRipRespIns OBJECT-TYPE   
			SYNTAX	Counter
			ACCESS	read-only
			STATUS	mandatory
			DESCRIPTION
	        " IPX RIP responses received"
			::= { accIpxRipStat 2 }
           accIpxRipReqOuts OBJECT-TYPE   
			SYNTAX	Counter
			ACCESS	read-only
			STATUS	mandatory
			DESCRIPTION
	        " IPX RIP requests transmitted"
			::= { accIpxRipStat 3 }
           accIpxRipRespOuts OBJECT-TYPE   
			SYNTAX	Counter
			ACCESS	read-only
			STATUS	mandatory
			DESCRIPTION
	        " IPX RIP responses transmitted"
			::= { accIpxRipStat 4 }
           accIpxRipErrIns OBJECT-TYPE   
			SYNTAX	Counter
			ACCESS	read-only
			STATUS	mandatory
			DESCRIPTION
	        " IPX RIP responses recevied with errors."
			::= { accIpxRipStat 5 }
           accIpxRipErrOuts OBJECT-TYPE   
			SYNTAX	Counter
			ACCESS	read-only
			STATUS	mandatory
			DESCRIPTION
	        " IPX RIP responses transmitted with errors."
			::= { accIpxRipStat 6 }
           accIpxRipDemandReqIns OBJECT-TYPE   
			SYNTAX	Counter
			ACCESS	read-only
			STATUS	mandatory
			DESCRIPTION
	        " IPX Demand RIP requests in "
			::= { accIpxRipStat 7 }
           accIpxRipDemandRespIns OBJECT-TYPE   
			SYNTAX	Counter
			ACCESS	read-only
			STATUS	mandatory
			DESCRIPTION
	        " IPX Demand RIP replies in "
			::= { accIpxRipStat 8 }
           accIpxRipDemandAckIns OBJECT-TYPE   
			SYNTAX	Counter
			ACCESS	read-only
			STATUS	mandatory
			DESCRIPTION
	        " IPX Demand RIP acks in "
			::= { accIpxRipStat 9 }
           accIpxRipDemandReqOuts OBJECT-TYPE   
			SYNTAX	Counter
			ACCESS	read-only
			STATUS	mandatory
			DESCRIPTION
	        " IPX Demand RIP requests out "
			::= { accIpxRipStat 10 }
           accIpxRipDemandRespOuts OBJECT-TYPE   
			SYNTAX	Counter
			ACCESS	read-only
			STATUS	mandatory
			DESCRIPTION
	        " IPX Demand RIP replies out "
			::= { accIpxRipStat 11 }
           accIpxRipDemandAckOuts OBJECT-TYPE   
			SYNTAX	Counter
			ACCESS	read-only
			STATUS	mandatory
			DESCRIPTION
	        " IPX Demand RIP acks out "
			::= { accIpxRipStat 12 }
           accIpxRipDemandInErrs OBJECT-TYPE   
			SYNTAX	Counter
			ACCESS	read-only
			STATUS	mandatory
			DESCRIPTION
	        " IPX Demand RIP Errors in "
			::= { accIpxRipStat 13 }
           accIpxRipDemandOutErrs OBJECT-TYPE   
			SYNTAX	Counter
			ACCESS	read-only
			STATUS	mandatory
			DESCRIPTION
	        " IPX Demand RIP Errors out "
			::= { accIpxRipStat 14 }
      accIpxNodeStat  OBJECT IDENTIFIER  ::= { accIpx 5 }
           accIpxLocalIns OBJECT-TYPE   
			SYNTAX	Counter
			ACCESS	read-only
			STATUS	mandatory
			DESCRIPTION
	        " Packets received for local usage"
			::= { accIpxNodeStat 1 }
           accIpxLocalOuts OBJECT-TYPE   
			SYNTAX	Counter
			ACCESS	read-only
			STATUS	mandatory
			DESCRIPTION
	        " Locally generated packets"
			::= { accIpxNodeStat 2 }
           accIpxNoSockets OBJECT-TYPE   
			SYNTAX	Counter
			ACCESS	read-only
			STATUS	mandatory
			DESCRIPTION
	        " Packets received for which there was no socket"
			::= { accIpxNodeStat 3 }
           accIpxNoRoutes OBJECT-TYPE   
			SYNTAX	Counter
			ACCESS	read-only
			STATUS	mandatory
			DESCRIPTION
	        " Packets for which no route was found"
			::= { accIpxNodeStat 4 }
           accIpxNodeInErrs OBJECT-TYPE   
			SYNTAX	Counter
			ACCESS	read-only
			STATUS	mandatory
			DESCRIPTION
	        " The number of input packets discarded by this node because
	          of some unspecified internal error."
			::= { accIpxNodeStat 5 }
           accIpxOutErrs OBJECT-TYPE   
			SYNTAX	Counter
			ACCESS	read-only
			STATUS	mandatory
			DESCRIPTION
	        " Output errors"
			::= { accIpxNodeStat 6 }
           accIpxAllNetsIns OBJECT-TYPE   
			SYNTAX	Counter
			ACCESS	read-only
			STATUS	mandatory
			DESCRIPTION
	        " All-nets packets received"
			::= { accIpxNodeStat 7 }
           accIpxAllNetsOuts OBJECT-TYPE   
			SYNTAX	Counter
			ACCESS	read-only
			STATUS	mandatory
			DESCRIPTION
	        " All-nets packets transmitted"
			::= { accIpxNodeStat 8 }
           accIpxAllNetsErrs OBJECT-TYPE   
			SYNTAX	Counter
			ACCESS	read-only
			STATUS	mandatory
			DESCRIPTION
	        " Erroneous All-Nets packets encountered"
			::= { accIpxNodeStat 9 }
     accIpxPortStatTable  OBJECT-TYPE   
			SYNTAX	SEQUENCE OF AccIpxPortStatEntry
			ACCESS	not-accessible
			STATUS	mandatory
			DESCRIPTION
                " IPX Port statistics table"
			::= { accIpx 6 }
        accIpxPortStatEntry  OBJECT-TYPE   
			SYNTAX	AccIpxPortStatEntry
			ACCESS	not-accessible
			STATUS	mandatory
			DESCRIPTION
                " Per-port statistics "
		        INDEX { accIpxPortNumber }
			::= { accIpxPortStatTable 1 }
        AccIpxPortStatEntry ::= SEQUENCE {
			accIpxPortNumber		INTEGER,
			accIpxPortTotalIns		Counter,
			accIpxPorFwdReqIns		Counter,
			accIpxPortNoFwdRts		Counter,
			accIpxPortTotalOuts		Counter,
			accIpxPortHopCnts		Counter,
			accIpxPortNotForMes		Counter,
			accIpxPortFwdReqOuts		Counter,
			accIpxPortFwdErrs		Counter,
			accIpxPortInErrs		Counter,
			accIpxPortTooShorts		Counter,
			accIpxPortCkSums		Counter,
			accIpxPortTooLongs		Counter,
			accIpxPortOutErrs		Counter,
			accIpxPortOpState		INTEGER
 			}
	  accIpxPortNumber  OBJECT-TYPE   
			SYNTAX	INTEGER
			ACCESS	read-only
			STATUS	mandatory
			DESCRIPTION
	        " Port number"
			::= { accIpxPortStatEntry 1 }
	  accIpxPortTotalIns  OBJECT-TYPE   
			SYNTAX	Counter
			ACCESS	read-only
			STATUS	mandatory
			DESCRIPTION
	        " Total number of IPX  Packets received"
			::= { accIpxPortStatEntry 2 }
	  accIpxPorFwdReqIns  OBJECT-TYPE   
			SYNTAX	Counter
			ACCESS	read-only
			STATUS	mandatory
			DESCRIPTION
		  " The number of input packets not addressed to the receiving
		    port, as a result of which an attempt was made to find a
		    route to forward them to the final destination."
			::= { accIpxPortStatEntry 3 }
	  accIpxPortNoFwdRts  OBJECT-TYPE   
			SYNTAX	Counter
			ACCESS	read-only
			STATUS	mandatory
			DESCRIPTION
	        " The number of packets received on this port for which no
	          route to the destination network could be found."
			::= { accIpxPortStatEntry 4 }
	  accIpxPortTotalOuts  OBJECT-TYPE   
			SYNTAX	Counter
			ACCESS	read-only
			STATUS	mandatory
			DESCRIPTION
	        " Total IPX packets transmitted"
			::= { accIpxPortStatEntry 5 }
	  accIpxPortHopCnts  OBJECT-TYPE   
			SYNTAX	Counter
			ACCESS	read-only
			STATUS	mandatory
			DESCRIPTION
		 " The number of packets received on this port whose hop
		   count had reached the maximum value."
			::= { accIpxPortStatEntry 6 }
	  accIpxPortNotForMes  OBJECT-TYPE   
			SYNTAX	Counter
			ACCESS	read-only
			STATUS	mandatory
			DESCRIPTION
		 " The number of packets received on this port which were
		   addressed to another node on the same network."
			::= { accIpxPortStatEntry 7 }
	  accIpxPortFwdReqOuts  OBJECT-TYPE   
			SYNTAX	Counter
			ACCESS	read-only
			STATUS	mandatory
			DESCRIPTION
		 " The number of packets received on this port which were
		   successfully forwarded to another port."
			::= { accIpxPortStatEntry 8 }
	  accIpxPortFwdErrs  OBJECT-TYPE   
			SYNTAX	Counter
			ACCESS	read-only
			STATUS	mandatory
			DESCRIPTION
		 " The number of packets received on this port which could
		   not be forwarded, either because there were transmitted
		   via a MAC-layer broadcast, or because their source or
		   destination network number were unknown."
			::= { accIpxPortStatEntry 9 }
	  accIpxPortInErrs  OBJECT-TYPE   
			SYNTAX	Counter
			ACCESS	read-only
			STATUS	mandatory
			DESCRIPTION
	        " The number of packets received on this port which were
	          discarded because of some unspecified internal error."
			::= { accIpxPortStatEntry 10 }
	  accIpxPortTooShorts  OBJECT-TYPE   
			SYNTAX	Counter
			ACCESS	read-only
			STATUS	mandatory
			DESCRIPTION
		 " The number of packets received on this port which were
		   discarded because they were too short."
			::= { accIpxPortStatEntry 11 }
	  accIpxPortCkSums  OBJECT-TYPE   
			SYNTAX	Counter
			ACCESS	read-only
			STATUS	mandatory
			DESCRIPTION
	        " IPX packet checksum errors detected"
			::= { accIpxPortStatEntry 12 }
	  accIpxPortTooLongs  OBJECT-TYPE   
			SYNTAX	Counter
			ACCESS	read-only
			STATUS	mandatory
			DESCRIPTION
		 " The number of packets received on this port which were
		   discarded because they were too long."
			::= { accIpxPortStatEntry 13 }
	  accIpxPortOutErrs  OBJECT-TYPE   
			SYNTAX	Counter
			ACCESS	read-only
			STATUS	mandatory
			DESCRIPTION
	        " IPX packet output errors detected"
			::= { accIpxPortStatEntry 14 }
	  accIpxPortOpState  OBJECT-TYPE   
			SYNTAX	INTEGER { 
				off(0),
				down(1),
				start(2),
				stop(3),
				up(4)
			}	
			ACCESS	read-only
			STATUS	mandatory
			DESCRIPTION
	        " Operational status of this port.
		"
			::= { accIpxPortStatEntry 15 }
     accIpxSapStat  OBJECT IDENTIFIER ::= { accIpx 7 }
	  accIpxSapReqIns  OBJECT-TYPE   
			SYNTAX	Counter
			ACCESS	read-only
			STATUS	mandatory
			DESCRIPTION
	        " IPX SAP requests received"
			::= { accIpxSapStat 1 }
	  accIpxSapReqOuts  OBJECT-TYPE   
			SYNTAX	Counter
			ACCESS	read-only
			STATUS	mandatory
			DESCRIPTION
	        " IPX SAP requests transmitted"
			::= { accIpxSapStat 2 }
	  accIpxSapRespIns  OBJECT-TYPE   
			SYNTAX	Counter
			ACCESS	read-only
			STATUS	mandatory
			DESCRIPTION
	        " IPX SAP responses received"
			::= { accIpxSapStat 3 }
	  accIpxSapRespOuts  OBJECT-TYPE   
			SYNTAX	Counter
			ACCESS	read-only
			STATUS	mandatory
			DESCRIPTION
	        " IPX SAP responses transmitted"
			::= { accIpxSapStat 4 }
	  accIpxSapGetNearIns  OBJECT-TYPE   
			SYNTAX	Counter
			ACCESS	read-only
			STATUS	mandatory
			DESCRIPTION
	        " Get nearest requests received"
			::= { accIpxSapStat 5 }
	  accIpxSapGetNearOuts  OBJECT-TYPE   
			SYNTAX	Counter
			ACCESS	read-only
			STATUS	mandatory
			DESCRIPTION
	        " Get nearest requests transmitted"
			::= { accIpxSapStat 6 }
	  accIpxSapNoRoutes  OBJECT-TYPE   
			SYNTAX	Counter
			ACCESS	read-only
			STATUS	mandatory
			DESCRIPTION
	        " IPX SAP packets for unreachable net"
			::= { accIpxSapStat 7 }
	  accIpxSapNotBests  OBJECT-TYPE   
			SYNTAX	Counter
			ACCESS	read-only
			STATUS	mandatory
			DESCRIPTION
	        " IPX SAP packet which we know there is a better route for"
			::= { accIpxSapStat 8 }
	  accIpxSapNoServers  OBJECT-TYPE   
			SYNTAX	Counter
			ACCESS	read-only
			STATUS	mandatory
			DESCRIPTION
	        " No server available"
			::= { accIpxSapStat 9 }
	  accIpxSapInErrs  OBJECT-TYPE   
			SYNTAX	Counter
			ACCESS	read-only
			STATUS	mandatory
			DESCRIPTION
	        " Bad IPX SAP packets received"
			::= { accIpxSapStat 10 }
	  accIpxSapOutErrs  OBJECT-TYPE   
			SYNTAX	Counter
			ACCESS	read-only
			STATUS	mandatory
			DESCRIPTION
	        " Bad IPX SAP packets transmitted"
			::= { accIpxSapStat 11 }
	  accIpxSapDemandReqIns  OBJECT-TYPE   
			SYNTAX	Counter
			ACCESS	read-only
			STATUS	mandatory
			DESCRIPTION
	        " Demand IPX SAP requests in"
			::= { accIpxSapStat 12 }
	  accIpxSapDemandReqOuts  OBJECT-TYPE   
			SYNTAX	Counter
			ACCESS	read-only
			STATUS	mandatory
			DESCRIPTION
	        " Demand IPX SAP requests out"
			::= { accIpxSapStat 13 }
	  accIpxSapDemandRespIns  OBJECT-TYPE   
			SYNTAX	Counter
			ACCESS	read-only
			STATUS	mandatory
			DESCRIPTION
	        " Demand IPX SAP responses in"
			::= { accIpxSapStat 14 }
	  accIpxSapDemandRespOuts  OBJECT-TYPE   
			SYNTAX	Counter
			ACCESS	read-only
			STATUS	mandatory
			DESCRIPTION
	        " Demand IPX SAP responses out"
			::= { accIpxSapStat 15 }
	  accIpxSapDemandAckIns  OBJECT-TYPE   
			SYNTAX	Counter
			ACCESS	read-only
			STATUS	mandatory
			DESCRIPTION
	        " Demand IPX SAP acks in"
			::= { accIpxSapStat 16 }
	  accIpxSapDemandAckOuts  OBJECT-TYPE   
			SYNTAX	Counter
			ACCESS	read-only
			STATUS	mandatory
			DESCRIPTION
	        " Demand IPX SAP acks out"
			::= { accIpxSapStat 17 }
	  accIpxSapDemandInErrs  OBJECT-TYPE   
			SYNTAX	Counter
			ACCESS	read-only
			STATUS	mandatory
			DESCRIPTION
	        " Demand IPX SAP errors in"
			::= { accIpxSapStat 18 }
	  accIpxSapDemandOutErrs  OBJECT-TYPE   
			SYNTAX	Counter
			ACCESS	read-only
			STATUS	mandatory
			DESCRIPTION
	        " Demand IPX SAP errors out"
			::= { accIpxSapStat 19 }
     accIpxSrvTable  OBJECT-TYPE   
			SYNTAX	SEQUENCE OF AccIpxSrvEntry
			ACCESS	not-accessible
			STATUS	mandatory
			DESCRIPTION
                " IPX server table"
			::= { accIpx 8 }
        accIpxSrvEntry  OBJECT-TYPE   
			SYNTAX	AccIpxSrvEntry
			ACCESS	not-accessible
			STATUS	mandatory
			DESCRIPTION
                           " Specific IPX server information"
                        INDEX { accIpxSrvType,
	                        accIpxSrvName }
			::= { accIpxSrvTable 1 }
        AccIpxSrvEntry ::= SEQUENCE {
			accIpxSrvName		DisplayString,
			accIpxSrvType		OCTET STRING,
			accIpxSrvHost		OCTET STRING,
			accIpxSrvHops		INTEGER,
			accIpxSrvOwner		INTEGER,
			accIpxSrvAge		TimeTicks
 			}
	  accIpxSrvName  OBJECT-TYPE   
			SYNTAX  DisplayString	
			ACCESS	read-write
			STATUS	mandatory
			DESCRIPTION
	        " Name of server"
			::= { accIpxSrvEntry 1 }
	  accIpxSrvType  OBJECT-TYPE   
			SYNTAX	OCTET STRING -- (SIZE(2))
			ACCESS	read-write
			STATUS	mandatory
			DESCRIPTION
	        " Type of server"
			::= { accIpxSrvEntry 2 }
	  accIpxSrvHost  OBJECT-TYPE   
			SYNTAX	OCTET STRING
			ACCESS	read-write
			STATUS	mandatory
			DESCRIPTION
	        " Host"
			::= { accIpxSrvEntry 3 }
	  accIpxSrvHops  OBJECT-TYPE   
			SYNTAX	INTEGER
			ACCESS	read-write
			STATUS	mandatory
			DESCRIPTION
	        " Hop counter"
			::= { accIpxSrvEntry 4 }
	  accIpxSrvOwner  OBJECT-TYPE   
			SYNTAX	INTEGER {
				nms(1),
				sap(2)
				}
			ACCESS	read-write
			STATUS	mandatory
			DESCRIPTION
	        " Source of route"
			::= { accIpxSrvEntry 5 }
	  accIpxSrvAge  OBJECT-TYPE   
			SYNTAX	TimeTicks 
			ACCESS	read-write
			STATUS	mandatory
			DESCRIPTION
	        " Age of route"
			::= { accIpxSrvEntry 6 }
--    The following route neighbor and route filter table has been 
--    deprecated.  Route filters are replaced by named route filters
   accIpxRouteFilters OBJECT IDENTIFIER ::= { accIpx 9 }
     accIpxRteFltrDefaultAction OBJECT-TYPE
         SYNTAX   INTEGER { 
		     accept(1), 
		     reject(2) 
		     }
         ACCESS   read-write
         STATUS   deprecated
         DESCRIPTION
          " The action taken on route updates from unconfigured neighbors."
         ::= { accIpxRouteFilters 1 }
      accIpxRteNbrTable OBJECT-TYPE
          SYNTAX   SEQUENCE OF AccIpxRteNbrEntry
          ACCESS   not-accessible
          STATUS   deprecated
          DESCRIPTION
             " A list of Host Identifiers for Routing Neighbors."
          ::= { accIpxRouteFilters 2 }
         accIpxRteNbrEntry OBJECT-TYPE
            SYNTAX   AccIpxRteNbrEntry
            ACCESS   not-accessible
            STATUS   deprecated
            DESCRIPTION
               " The host identifier for an individual routing neighbor."
            INDEX { accIpxRteNbrId }
            ::= { accIpxRteNbrTable 1 }
         AccIpxRteNbrEntry ::=
             SEQUENCE {
                 accIpxRteNbrId
                     OCTET STRING,
                 accIpxRteNbrAction
                     INTEGER,
                 accIpxRteNbrStatus
                     INTEGER
                 }
            accIpxRteNbrId OBJECT-TYPE
                SYNTAX   OCTET STRING -- (SIZE(6))
                ACCESS   read-write
                STATUS   deprecated
                DESCRIPTION
                  " The Host Identifier of a potential routing neighbor."
                ::= { accIpxRteNbrEntry 1 }
            accIpxRteNbrAction OBJECT-TYPE
                SYNTAX   INTEGER { 
			accept(1), 
			reject(2) 
			}
                ACCESS   read-write
                STATUS   deprecated
                DESCRIPTION
         " The action to be taken on advertisements from this routing neighbor,
           unless overridden by a route filter."
                ::= { accIpxRteNbrEntry 2 }
            accIpxRteNbrStatus OBJECT-TYPE
                SYNTAX   INTEGER {
                            invalid(1), 
                            valid(2) 
                            }
                ACCESS   read-write
                STATUS   deprecated
                DESCRIPTION
          " Writing 'invalid' has the effect of deleting this routing neighbor
            and making its associated route filters of no effect."
                ::= { accIpxRteNbrEntry 3 }
--    The following route filter table has been deprecated in
--    deference to the new named route filter table.
     accIpxRteFltrTable OBJECT-TYPE
         SYNTAX   SEQUENCE OF AccIpxRteFltrEntry
         ACCESS   not-accessible
         STATUS   deprecated
         DESCRIPTION
         " A list of special advertisements that a given neighbor might offer.
           Route Advertisements defaults are overridden using this table"
         ::= { accIpxRouteFilters 3 }
        accIpxRteFltrEntry OBJECT-TYPE
            SYNTAX   AccIpxRteFltrEntry
            ACCESS   not-accessible
            STATUS   deprecated
            DESCRIPTION
                  " A single potential advertisement, with information 
                    as to its disposition."
            INDEX { accIpxRteFltrNeighbor, 
                    accIpxRteFltrNetwork }
            ::= { accIpxRteFltrTable 1 }
        AccIpxRteFltrEntry ::=
            SEQUENCE {
                accIpxRteFltrNeighbor
                    OCTET STRING,
                accIpxRteFltrNetwork
                    OCTET STRING,
                accIpxRteFltrAction
                    INTEGER,
                accIpxRteFltrStatus
                    INTEGER
	        }
            accIpxRteFltrNeighbor OBJECT-TYPE
                SYNTAX   OCTET STRING
                ACCESS   read-write
                STATUS   deprecated
                DESCRIPTION
                      " The Host Identifier of the Routing Neighbor that might 
                        offer this advertsiement."
                ::= { accIpxRteFltrEntry 1 }
            accIpxRteFltrNetwork OBJECT-TYPE
                SYNTAX   OCTET STRING  -- (SIZE (4))
                ACCESS   read-write
                STATUS   deprecated
                DESCRIPTION
                     " The Network Number the neighbor might advertise."
                ::= { accIpxRteFltrEntry 2 }
            accIpxRteFltrAction OBJECT-TYPE
                SYNTAX   INTEGER { 
		            accept(1), 
		            reject(2) 
		            }
                ACCESS   read-write
                STATUS   deprecated
                DESCRIPTION
                      " What is to be done with such an advertisement."
                ::= { accIpxRteFltrEntry 3 }
            accIpxRteFltrStatus OBJECT-TYPE
                SYNTAX   INTEGER {
                            invalid(1), 
                            valid(2) 
                            }
                ACCESS   read-write
                STATUS   deprecated
                DESCRIPTION
                     " Writing 'invalid' has the effect of deleting this filter."
                ::= { accIpxRteFltrEntry 4 }
--    The following network filter table has been deprecated in
--    deference to the new table immediately subsequent.
     accIpxNetworkFilters OBJECT IDENTIFIER ::= { accIpx 10 }
         accIpxNetFltrDefaultAction OBJECT-TYPE
             SYNTAX   INTEGER  {
                        discard(0),
                        lowPriority(1),
                        normalPriority(2),
                        highPriority(3)
			}
             ACCESS   read-write
             STATUS   deprecated
             DESCRIPTION
             " The action taken on messages not matched.
		"
             ::= { accIpxNetworkFilters 1 }
        oldIpxNetFltrTable OBJECT-TYPE
            SYNTAX   SEQUENCE OF OldIpxNetFltrEntry
            ACCESS   not-accessible
            STATUS   deprecated
            DESCRIPTION
                    " A list of network pairs to specially act on."
            ::= { accIpxNetworkFilters 2 }
           oldIpxNetFltrEntry OBJECT-TYPE
               SYNTAX   OldIpxNetFltrEntry
               ACCESS   not-accessible
               STATUS   deprecated
               DESCRIPTION
                       " A single Network Number pair to be matched."
               INDEX { oldIpxNetFltrDestination, 
                       oldIpxNetFltrSource }
               ::= { oldIpxNetFltrTable 1 }
           OldIpxNetFltrEntry ::=
               SEQUENCE {
                   oldIpxNetFltrDestination
                       OCTET STRING,
                   oldIpxNetFltrSource
                       OCTET STRING,
                   oldIpxNetFltrAction
                       INTEGER,
                   oldIpxNetFltrStatus
                       INTEGER
	           }
             oldIpxNetFltrDestination OBJECT-TYPE
                 SYNTAX   OCTET STRING  -- (SIZE (4))
                 ACCESS   read-write
                 STATUS   deprecated
                 DESCRIPTION
        " The value to be found in the Destination Network Field, or 0x00000000."
                 ::= { oldIpxNetFltrEntry 1 }
             oldIpxNetFltrSource OBJECT-TYPE
                 SYNTAX   OCTET STRING  -- (SIZE (4))
                 ACCESS   read-write
                 STATUS   deprecated
                 DESCRIPTION
        " The value to be found in the Source Network Field, or 0x00000000."
                 ::= { oldIpxNetFltrEntry 2 }
             oldIpxNetFltrAction OBJECT-TYPE
                 SYNTAX   INTEGER  {
                                     discard(0),
                                     lowPriority(1),
                                     normalPriority(2),
                                     highPriority(3)
		      }
                 ACCESS   read-write
                 STATUS   deprecated
                 DESCRIPTION
                      " The action to be taken on matching messages.
		"
                 ::= { oldIpxNetFltrEntry 3 }
             oldIpxNetFltrStatus OBJECT-TYPE
                 SYNTAX   INTEGER {
                             invalid(1), 
                             valid(2) 
                             }
                 ACCESS   read-write
                 STATUS   deprecated
                 DESCRIPTION
            " Writing 'invalid' has the effect of removing this filter entry."
                 ::= { oldIpxNetFltrEntry 4 }
--    The following network filter table has been deprecated in
--    deference to the new named network filter table.
        accIpxNetFltrTable OBJECT-TYPE
            SYNTAX   SEQUENCE OF AccIpxNetFltrEntry
            ACCESS   not-accessible
            STATUS   deprecated
            DESCRIPTION
                    " A list of network filters to specially act on."
            ::= { accIpxNetworkFilters 3 }
           accIpxNetFltrEntry OBJECT-TYPE
               SYNTAX   AccIpxNetFltrEntry
               ACCESS   not-accessible
               STATUS   deprecated
               DESCRIPTION
                       " A single Network  filter to be matched."
               INDEX { accIpxNetFltrDestination, 
                       accIpxNetFltrSource,
                       accIpxNetFltrDestSkt,
                       accIpxNetFltrSrcSkt,
                       accIpxNetFltrPktType }
               ::= { accIpxNetFltrTable 1 }
           AccIpxNetFltrEntry ::=
               SEQUENCE {
                   accIpxNetFltrDestination
                       OCTET STRING,
                   accIpxNetFltrSource
                       OCTET STRING,
                   accIpxNetFltrAction
                       INTEGER,
                   accIpxNetFltrStatus
                       INTEGER,
                   accIpxNetFltrDestSkt
                       OCTET STRING,
                   accIpxNetFltrSrcSkt
                       OCTET STRING,
                   accIpxNetFltrPktType
                       INTEGER
	           }
             accIpxNetFltrDestination OBJECT-TYPE
                 SYNTAX   OCTET STRING  -- (SIZE (4))
                 ACCESS   read-write
                 STATUS   deprecated
                 DESCRIPTION
        " The value to be found in the Destination Network Field, or 0x00000000."
                 ::= { accIpxNetFltrEntry 1 }
             accIpxNetFltrSource OBJECT-TYPE
                 SYNTAX   OCTET STRING  -- (SIZE (4))
                 ACCESS   read-write
                 STATUS   deprecated
                 DESCRIPTION
        " The value to be found in the Source Network Field, or 0x00000000."
                 ::= { accIpxNetFltrEntry 2 }
             accIpxNetFltrAction OBJECT-TYPE
                 SYNTAX   INTEGER  {
                                     discard(0),
                                     lowPriority(1),
                                     normalPriority(2),
                                     highPriority(3)
			}
                 ACCESS   read-write
                 STATUS   deprecated
                 DESCRIPTION
                      " The action to be taken on matching messages.
		"
                 ::= { accIpxNetFltrEntry 3 }
             accIpxNetFltrStatus OBJECT-TYPE
                 SYNTAX   INTEGER {
                             invalid(1), 
                             valid(2) 
                             }
                 ACCESS   read-write
                 STATUS   deprecated
                 DESCRIPTION
            " Writing 'invalid' has the effect of removing this filter entry."
                 ::= { accIpxNetFltrEntry 4 }
             accIpxNetFltrDestSkt OBJECT-TYPE
                 SYNTAX   OCTET STRING  -- (SIZE (2))
                 ACCESS   read-write
                 STATUS   deprecated
                 DESCRIPTION
        " The value to be found in the Destination Socket field, or 0x0000."
                 ::= { accIpxNetFltrEntry 5 }
             accIpxNetFltrSrcSkt OBJECT-TYPE
                 SYNTAX   OCTET STRING  -- (SIZE (2))
                 ACCESS   read-write
                 STATUS   deprecated
                 DESCRIPTION
        " The value to be found in the Source Socket Field, or 0x0000."
                 ::= { accIpxNetFltrEntry 6 }
             accIpxNetFltrPktType OBJECT-TYPE
                 SYNTAX   INTEGER 
                 ACCESS   read-write
                 STATUS   deprecated
                 DESCRIPTION
            " Packet type or zero"
                 ::= { accIpxNetFltrEntry 7 }
--    The following host filter table has been deprecated in
--    deference to the new named host filter table.
     accIpxHostFilters OBJECT IDENTIFIER ::= { accIpx 11 }
        accIpxHostFltrDefaultAction OBJECT-TYPE
            SYNTAX   INTEGER { 
                        discard(0),
                        lowPriority(1),
                        normalPriority(2),
                        highPriority(3)
		  }
            ACCESS   read-write
            STATUS   deprecated
            DESCRIPTION
                  " The action taken on hosts not listed.
		"
            ::= { accIpxHostFilters 1 }
        accIpxHostFltrTable OBJECT-TYPE
            SYNTAX   SEQUENCE OF AccIpxHostFltrEntry
            ACCESS   not-accessible
            STATUS   deprecated
            DESCRIPTION
                     " A list of IPX Hosts to be handled specially."
            ::= { accIpxHostFilters 2 }
           accIpxHostFltrEntry OBJECT-TYPE
               SYNTAX   AccIpxHostFltrEntry
               ACCESS   not-accessible
               STATUS   deprecated
               DESCRIPTION
                     " A single Host Identifier."
               INDEX { accIpxHostFltrId, 
                       accIpxHostFltrSocket, 
                       accIpxHostFltrPepClient }
               ::= { accIpxHostFltrTable 1 }
           AccIpxHostFltrEntry ::=
               SEQUENCE {
                   accIpxHostFltrId
                       OCTET STRING,
	           accIpxHostFltrSocket
	               OCTET STRING,
	           accIpxHostFltrPepClient
	               OCTET STRING,
                   accIpxHostFltrAction
                       INTEGER,
                   accIpxHostFltrStatus
                       INTEGER
                  }
             accIpxHostFltrId OBJECT-TYPE
                 SYNTAX   OCTET STRING  -- (SIZE(6))
                 ACCESS   read-write
                 STATUS   deprecated
                 DESCRIPTION
                  " Host Identifier "
                 ::= { accIpxHostFltrEntry 1 }
             accIpxHostFltrSocket OBJECT-TYPE
                 SYNTAX   OCTET STRING -- (SIZE (2))
                 ACCESS   read-write
                 STATUS   deprecated
                 DESCRIPTION
                  " The affected socket number, or zero for 'any socket'."
                 ::= { accIpxHostFltrEntry 2 }
             accIpxHostFltrPepClient OBJECT-TYPE
                 SYNTAX   OCTET STRING -- (SIZE(2))
                 ACCESS   read-write
                 STATUS   deprecated
                 DESCRIPTION
                      " On PEP traffic, the affected Client Type, 
                        or zero for all IDP traffic."
                 ::= { accIpxHostFltrEntry 3 }
             accIpxHostFltrAction OBJECT-TYPE
                 SYNTAX   INTEGER {
                                     discard(0),
                                     lowPriority(1),
                                     normalPriority(2),
                                     highPriority(3)
			 }
                 ACCESS   read-write
                 STATUS   deprecated
                 DESCRIPTION
                         " The action to be taken on matching messages.
		"
                 ::= { accIpxHostFltrEntry 4 }
             accIpxHostFltrStatus OBJECT-TYPE
                 SYNTAX   INTEGER {
                             invalid(1), 
                             valid(2) 
                             }
                 ACCESS   read-write
                 STATUS   deprecated
                 DESCRIPTION
           " Writing 'invalid' has the effect of deleting the entry."
                 ::= { accIpxHostFltrEntry 5 }
--    The following Sap filter table has been deprecated in
--    deference to the new named Sap filter table.
--	Service Advertisement Protocol Filter Entries indicate
--	what service names are or not to be advertised through the
--	network.
     accIpxSapFilters OBJECT IDENTIFIER ::= { accIpx 12 }
        accIpxSapFltrDefault OBJECT-TYPE
            SYNTAX   INTEGER {
                        accept(1), 
                        reject(2) 
                        }
            ACCESS   read-write
            STATUS   deprecated
            DESCRIPTION
           " The default behavior taken on locally originated (hop count <= 2)
             Service Advertisements.
             Remote advertisements must be identified individually."
            ::= { accIpxSapFilters 1 }
--  NetWare Service Advertising Protocol Filter Table
        accIpxSapFltrTable OBJECT-TYPE
            SYNTAX   SEQUENCE OF AccIpxSapFltrEntry
            ACCESS   not-accessible
            STATUS   deprecated
            DESCRIPTION
           " A list of Service Names to be handled Specially."
            ::= { accIpxSapFilters 2 }
          accIpxSapFltrEntry OBJECT-TYPE
              SYNTAX   AccIpxSapFltrEntry
              ACCESS   not-accessible
              STATUS   deprecated
              DESCRIPTION
           " A single Service name and its intended disposition."
              INDEX { accIpxSapFltrSrvType, 
                      accIpxSapFltrSrvName }
              ::= { accIpxSapFltrTable 1 }
          AccIpxSapFltrEntry ::=
              SEQUENCE {
                  accIpxSapFltrSrvType
                      OCTET STRING,
                  accIpxSapFltrSrvName
                      OCTET STRING,
                  accIpxSapFltrAction
                      INTEGER,
                  accIpxSapFltrStatus
                      INTEGER
	          }
              accIpxSapFltrSrvType OBJECT-TYPE
                  SYNTAX   OCTET STRING -- (SIZE(2))
	    	  ACCESS   read-write
                  STATUS   deprecated
                  DESCRIPTION
                          " The Service Type of the affected SAP Entry.
                            Zero indicates all services."
                  ::= { accIpxSapFltrEntry 1 }
              accIpxSapFltrSrvName OBJECT-TYPE
                  SYNTAX   OCTET STRING
                  ACCESS   read-write
                  STATUS   deprecated
                  DESCRIPTION
                       " The name of the affected service.  
                         An Octet String of length zero indicates all services.
                         Name may be up to 48 octets"
                  ::= { accIpxSapFltrEntry 2 }
              accIpxSapFltrAction OBJECT-TYPE
                  SYNTAX   INTEGER {
                              accept(1), 
                              reject(2) 
                              }
                  ACCESS   read-write
                  STATUS   deprecated
                  DESCRIPTION
                       " The action to be taken upon a match."
                  ::= { accIpxSapFltrEntry 3 }
              accIpxSapFltrStatus OBJECT-TYPE
                  SYNTAX   INTEGER {
                              valid(1),
                              invalid(2) 
                              }
                  ACCESS   read-write
                  STATUS   deprecated
                  DESCRIPTION
                       " Writing 'invalid' has the effect of removing the entry."
                  ::= { accIpxSapFltrEntry 4 }
--      IPX watchdog parameters
	accIpxNetWdParms OBJECT IDENTIFIER ::= { accIpx 13 }
	accIpxWdProxyDuration OBJECT-TYPE
		SYNTAX INTEGER (0..86400)
		ACCESS read-write
		STATUS mandatory
		DESCRIPTION
			"IPX Watchdog proxy duration 
			Value is 0 to proxy for forever
			& the proxy duration can be set 
			to 0 - 86400"
		DEFVAL { 86400 }
	::= { accIpxNetWdParms 1 }
	accIpxWdHoldPeriod OBJECT-TYPE
		SYNTAX INTEGER (960..60600)
		ACCESS read-write
		STATUS mandatory
		DESCRIPTION
			"ACC IPX Watchdog hold period
	 		Default value is 960 minutes, 
	 		Hold period range is 960 - 60600"
		DEFVAL { 960 }
	::= { accIpxNetWdParms 2 }
	accIpxWdMaxSessions OBJECT-TYPE
		SYNTAX INTEGER (1..4096)
		ACCESS read-write
		STATUS mandatory
		DESCRIPTION
			"ACC IPX Watchdog Max Sessions
	 		Default value is 1024, 
			Valid range is 1- 4096"
		DEFVAL { 1024 }
	::= { accIpxNetWdParms 3 }
	accIpxWdDiagLevel OBJECT-TYPE
		SYNTAX INTEGER (1..7)
		ACCESS read-write
		STATUS mandatory
		DESCRIPTION
			"ACC IPX Watchdog Diagnostics Level 
	 		Default value is 1, 
		Valid range is 1- 7"
		DEFVAL { 1 }
	::= { accIpxNetWdParms 4 }
	accIpxWdCurrentDropDead OBJECT-TYPE
		SYNTAX TimeTicks
		ACCESS read-only
		STATUS mandatory
		DESCRIPTION
			"The SysUpTime value at which the watchdog session will
			 be discarded, if no activity is seen on the session"
	::= { accIpxNetWdParms 5 }
	accIpxWdIpxSessionCnt OBJECT-TYPE
		SYNTAX INTEGER (0..65535)
		ACCESS read-only
		STATUS mandatory
		DESCRIPTION
			"Indicates the number of IPX sessions currently 
			 being proxied"
	::= { accIpxNetWdParms 6 }
	accIpxWdSpxSessionCnt OBJECT-TYPE
		SYNTAX INTEGER (0..65535)
		ACCESS read-only
		STATUS mandatory
		DESCRIPTION
			"Indicates the number of SPX sessions currently 
			 being proxied"
	::= { accIpxNetWdParms 7 }
	accIpxWdSession OBJECT IDENTIFIER ::= { accIpx 14 }
	accIpxWdSessTable	OBJECT-TYPE
		SYNTAX	SEQUENCE OF AccIpxWdSessEntry
		ACCESS	not-accessible
		STATUS	mandatory
              DESCRIPTION ""
	::= { accIpxWdSession  1 }
	AccIpxWdSessEntry	::= SEQUENCE  {
		accIpxWdSessionId	INTEGER,
		accIpxWdState 		INTEGER,
		accIpxWdLastSeen	TimeTicks,
		accIpxWdClientNet	OCTET STRING,
		accIpxWdClientHost	OCTET STRING,
		accIpxWdDropDead	TimeTicks,
		accIpxWdServerNet	OCTET STRING,
		accIpxWdServerHost	OCTET STRING
		}
	accIpxWdSessEntry	OBJECT-TYPE
		SYNTAX	AccIpxWdSessEntry
		ACCESS	not-accessible
		STATUS	mandatory
		DESCRIPTION
			"A descriptor entry for IPX session being proxied"
		INDEX		{ accIpxWdSessionId }
	::= { accIpxWdSessTable 1 }
	accIpxWdSessionId	 OBJECT-TYPE
		SYNTAX INTEGER (0..65535)
		ACCESS read-only
		STATUS mandatory
		DESCRIPTION
			"A unique identifier for the IPX session being proxied"
	::= { accIpxWdSessEntry 1 }
	accIpxWdState 		OBJECT-TYPE
            SYNTAX   INTEGER { 
				operational (0),
				dying (1),
				dead (2)
		  }
            ACCESS   read-only
            STATUS   mandatory
            DESCRIPTION
                  " State of the IPX session being proxied
		"
	::= { accIpxWdSessEntry 2 }
	accIpxWdLastSeen	 OBJECT-TYPE
		SYNTAX TimeTicks
		ACCESS read-only
		STATUS mandatory
		DESCRIPTION
			"The time tick when last watchdog packet for this 
			 session was seen"
	::= { accIpxWdSessEntry 3 }
	accIpxWdClientNet	 OBJECT-TYPE
	    	SYNTAX	OCTET STRING  -- (SIZE (4))
		ACCESS read-only
		STATUS mandatory
		DESCRIPTION
			"The IPX network number on the client side of this IPX 
			 session" 
	::= { accIpxWdSessEntry 4 }
	accIpxWdClientHost	 OBJECT-TYPE
	    	SYNTAX	OCTET STRING  -- (SIZE (6))
		ACCESS read-only
		STATUS mandatory
		DESCRIPTION
			"The IPX node address of the client of this IPX 
			 session" 
	::= { accIpxWdSessEntry 5 }
	accIpxWdDropDead	 OBJECT-TYPE
		SYNTAX TimeTicks
		ACCESS read-only
		STATUS mandatory
		DESCRIPTION
			"The SysUpTime value at which this watchdog session will
			 be discarded"
	::= { accIpxWdSessEntry 6 }
	accIpxWdServerNet	 OBJECT-TYPE
	    	SYNTAX	OCTET STRING  -- (SIZE (4))
		ACCESS read-only
		STATUS mandatory
		DESCRIPTION
			"The IPX network number on the server side of this IPX 
			 session" 
	::= { accIpxWdSessEntry 7 }
	accIpxWdServerHost	 OBJECT-TYPE
	    	SYNTAX	OCTET STRING  -- (SIZE (6))
		ACCESS read-only
		STATUS mandatory
		DESCRIPTION
			"The IPX node address of the server of this IPX 
			 session" 
	::= { accIpxWdSessEntry 8 }
	accIpxSpxWdSession OBJECT IDENTIFIER ::= { accIpx 15 }
	accIpxSpxWdSessTable	OBJECT-TYPE
		SYNTAX	SEQUENCE OF AccIpxSpxWdSessEntry
		ACCESS	not-accessible
		STATUS	mandatory
              DESCRIPTION ""
	::= { accIpxSpxWdSession  1 }
	AccIpxSpxWdSessEntry	::= SEQUENCE  {
		accIpxSpxWdSrcSessionId	INTEGER  ,
		accIpxSpxWdDstSessionId	INTEGER  ,
		accIpxSpxWdState	INTEGER	,
		accIpxSpxWdClientNet	OCTET STRING,
		accIpxSpxWdClientHost	OCTET STRING,
		accIpxSpxWdLastSeen	TimeTicks,
		accIpxSpxWdServerNet	OCTET STRING,
		accIpxSpxWdServerHost	OCTET STRING,
		accIpxSpxWdDropDead	TimeTicks,
		accIpxSpxWdSrcSeqNo	INTEGER,
		accIpxSpxWdDstSeqNo	INTEGER,
		accIpxSpxWdAckDiscards	INTEGER,
		accIpxSpxWdSrcAckNo	INTEGER,
		accIpxSpxWdDstAckNo	INTEGER
		}
	accIpxSpxWdSessEntry	OBJECT-TYPE
		SYNTAX	AccIpxSpxWdSessEntry
		ACCESS	not-accessible
		STATUS	mandatory
		DESCRIPTION
			"A descriptor entry for SPX session being proxied"
		INDEX		{ accIpxSpxWdSrcSessionId,
				  accIpxSpxWdDstSessionId }
	::= { accIpxSpxWdSessTable 1 }
	accIpxSpxWdSrcSessionId	 OBJECT-TYPE
		SYNTAX INTEGER (0..65535)
		ACCESS read-only
		STATUS mandatory
		DESCRIPTION
			"A unique source identifier for the SPX session 
			 being proxied"
	::= { accIpxSpxWdSessEntry 1 }
	accIpxSpxWdDstSessionId	 OBJECT-TYPE
		SYNTAX INTEGER (0..65535)
		ACCESS read-only
		STATUS mandatory
		DESCRIPTION
			"A unique destination identifier for the SPX session 
			 being proxied"
	::= { accIpxSpxWdSessEntry 2 }
	accIpxSpxWdState OBJECT-TYPE
            SYNTAX   INTEGER { 
				proxy (0),
				allow (1),
				dying (2),
				dead (3)
		  }
            ACCESS   read-only
            STATUS   mandatory
            DESCRIPTION
                  " State of the SPX session being proxied
		"
	::= { accIpxSpxWdSessEntry 3 }
	accIpxSpxWdClientNet	 OBJECT-TYPE
	    	SYNTAX	OCTET STRING  -- (SIZE (4))
		ACCESS read-only
		STATUS mandatory
		DESCRIPTION
			"The IPX network number on the client side of this SPX 
			 session" 
	::= { accIpxSpxWdSessEntry 4 }
	accIpxSpxWdClientHost	 OBJECT-TYPE
	    	SYNTAX	OCTET STRING  -- (SIZE (6))
		ACCESS read-only
		STATUS mandatory
		DESCRIPTION
			"The IPX node address of the client of this SPX 
			 session" 
	::= { accIpxSpxWdSessEntry 5 }
	accIpxSpxWdLastSeen	 OBJECT-TYPE
		SYNTAX TimeTicks
		ACCESS read-only
		STATUS mandatory
		DESCRIPTION
			"The time tick when last watchdog packet for this 
			 session was seen"
	::= { accIpxSpxWdSessEntry 6 }
	accIpxSpxWdServerNet	 OBJECT-TYPE
	    	SYNTAX	OCTET STRING  -- (SIZE (4))
		ACCESS read-only
		STATUS mandatory
		DESCRIPTION
			"The IPX network number on the server side of this 
			 session" 
	::= { accIpxSpxWdSessEntry 7 }
	accIpxSpxWdServerHost	 OBJECT-TYPE
	    	SYNTAX	OCTET STRING  -- (SIZE (6))
		ACCESS read-only
		STATUS mandatory
		DESCRIPTION
			"The IPX node address of the server of this session" 
	::= { accIpxSpxWdSessEntry 8 }
	accIpxSpxWdDropDead	 OBJECT-TYPE
		SYNTAX TimeTicks
		ACCESS read-only
		STATUS mandatory
		DESCRIPTION
			"The SysUpTime value at which this watchdog session will
			 be discarded"
	::= { accIpxSpxWdSessEntry 9 }
	accIpxSpxWdSrcSeqNo	 OBJECT-TYPE
		SYNTAX INTEGER (0..65535)
		ACCESS read-only
		STATUS mandatory
		DESCRIPTION
			"The last SPX sequence number used by the server
			 side of this session"
	::= { accIpxSpxWdSessEntry 10 }
	accIpxSpxWdDstSeqNo	 OBJECT-TYPE
		SYNTAX INTEGER (0..65535)
		ACCESS read-only
		STATUS mandatory
		DESCRIPTION
			"The last SPX sequence number used by the client
			 side of this session"
	::= { accIpxSpxWdSessEntry 11 }
	accIpxSpxWdAckDiscards	 OBJECT-TYPE
		SYNTAX INTEGER (0..65535)
		ACCESS read-only
		STATUS mandatory
		DESCRIPTION
			"The number of Acknowledgement packets discarded
			 on the proxied session"
	::= { accIpxSpxWdSessEntry 12 }
	accIpxSpxWdSrcAckNo	 OBJECT-TYPE
		SYNTAX INTEGER (0..65535)
		ACCESS read-only
		STATUS mandatory
		DESCRIPTION
			"The last SPX acknowledgement number used by the 
			 server side of this session"
	::= { accIpxSpxWdSessEntry 13 }
	accIpxSpxWdDstAckNo	 OBJECT-TYPE
		SYNTAX INTEGER (0..65535)
		ACCESS read-only
		STATUS mandatory
		DESCRIPTION
			"The last SPX acknowledgement number used by the 
			 client side of this session"
	::= { accIpxSpxWdSessEntry 14 }
	accIpxNamedRteFilters OBJECT IDENTIFIER ::= { accIpx 16 }
	accIpxNamedRteFltrDefaultAction OBJECT-TYPE
		SYNTAX   INTEGER { 
		     accept(1), 
		     reject(2) 
		     }
		ACCESS   read-write
		STATUS   mandatory
		DESCRIPTION
		" The action taken on route updates from 
	  	unconfigured neighbors."
	::= { accIpxNamedRteFilters 1 }
	accIpxNamedRteFltrTable	OBJECT-TYPE
		SYNTAX	SEQUENCE OF AccIpxNamedRteFltrEntry
		ACCESS	not-accessible
		STATUS	mandatory
              DESCRIPTION ""
	::= { accIpxNamedRteFilters 2 }
	accIpxNamedRteFltrEntry	OBJECT-TYPE
		SYNTAX	AccIpxNamedRteFltrEntry
		ACCESS	not-accessible
		STATUS	mandatory
		DESCRIPTION
		"A single IPX named route filter entry."
		INDEX	{ accIpxNamedRteFltrName }
	::= { accIpxNamedRteFltrTable 1 }
	AccIpxNamedRteFltrEntry	::= SEQUENCE  {
		accIpxNamedRteFltrNeighbor	OCTET STRING,
		accIpxNamedRteFltrNetwork 	OCTET STRING,
		accIpxNamedRteFltrAction	INTEGER,
		accIpxNamedRteFltrStatus	INTEGER,
		accIpxNamedRteFltrName		OCTET STRING,
		accIpxNamedRteFltrPktDir	INTEGER,
		accIpxNamedRteFltrMatches	Counter,
		accIpxNamedRteFltrLastMatch	TimeTicks,
		accIpxNamedRteFltrNetMask       OCTET STRING
		}
	accIpxNamedRteFltrNeighbor  OBJECT-TYPE
		SYNTAX   OCTET STRING
      		ACCESS   read-write
		STATUS   mandatory
		DESCRIPTION	
			"Host identifier of the routing neighbor that might 
			 offer a routing advertisement."
	::=  { accIpxNamedRteFltrEntry 1 }
	accIpxNamedRteFltrNetwork  OBJECT-TYPE
		SYNTAX   OCTET STRING
      		ACCESS   read-write
		STATUS   mandatory
		DESCRIPTION	
			"The network number the routing neighbor might 
			 advertise"  
	::=  { accIpxNamedRteFltrEntry 2 }
	accIpxNamedRteFltrAction  OBJECT-TYPE
		SYNTAX   INTEGER {
				accept (1),
				reject (2)
				}
      		ACCESS   read-write
		STATUS   mandatory
		DESCRIPTION	
			"What is to be done with such an advertisement"  
	::=  { accIpxNamedRteFltrEntry 3 }
	accIpxNamedRteFltrStatus  OBJECT-TYPE
               	SYNTAX   INTEGER {
				invalid (1),
				valid  (2)
				}
      		ACCESS   read-write
		STATUS   mandatory
		DESCRIPTION	
			"Writing 'invalid' has the effect of deleting this 
			 filter"  
	::=  { accIpxNamedRteFltrEntry 4 }
	accIpxNamedRteFltrName  OBJECT-TYPE
		SYNTAX   OCTET STRING
      		ACCESS   read-write
		STATUS   mandatory
		DESCRIPTION	
			"Name of an IPX Route Filter.  A string of up to 15 
			 case sensitive ASCII characters."
	::=  { accIpxNamedRteFltrEntry 5 }
	accIpxNamedRteFltrPktDir  OBJECT-TYPE
		SYNTAX	INTEGER {
				input(1),
				output(2)
				}
		ACCESS	read-write
		STATUS	mandatory	
		DESCRIPTION
			"Traffic direction to which the filter is applied"
	::=  { accIpxNamedRteFltrEntry 6 }
	accIpxNamedRteFltrMatches  OBJECT-TYPE
		SYNTAX   Counter
      		ACCESS   read-only
		STATUS   mandatory
		DESCRIPTION	
			"Number of times an IPX packet matched the filter "
	::=  { accIpxNamedRteFltrEntry 7 }
	accIpxNamedRteFltrLastMatch  OBJECT-TYPE
		SYNTAX   TimeTicks
      		ACCESS   read-only
		STATUS   mandatory
		DESCRIPTION	
			"Time-tick when the last IPX packet matched the filter"
	::=  { accIpxNamedRteFltrEntry 8 }
	accIpxNamedRteFltrNetMask  OBJECT-TYPE
		SYNTAX   OCTET STRING -- ( SIZE (4))
      		ACCESS   read-write
		STATUS   mandatory
		DESCRIPTION	
			"Network Mask to describe a range of network numbers 
			 that a neighbor might advertise.  Network mask is a 
			 hexadecimal number in the range of 0x0 to
			 0xffffffff containing a contiguous stream of 1 bits"
	::=  { accIpxNamedRteFltrEntry 9 }
	accIpxRteFltrApplTable OBJECT-TYPE
		SYNTAX  SEQUENCE OF AccIpxRteFltrApplEntry 
		ACCESS  	not-accessible
		STATUS  	mandatory
		DESCRIPTION
			"This table describes application of IPX Route filters 
			 to IPX ports"
	::= { accIpxNamedRteFilters 3 }
	AccIpxRteFltrApplEntry  ::= SEQUENCE {
		accIpxRteFltrApplIfIndex	INTEGER,
		accIpxRteFltrApplPktDir	        INTEGER,
		accIpxRteFltrApplSeqNum		INTEGER,
		accIpxRteFltrApplName		DisplayString,
		accIpxRteFltrApplMatches	Counter,
		accIpxRteFltrApplLastMatch	TimeTicks
	}
	accIpxRteFltrApplEntry	OBJECT-TYPE
		SYNTAX	AccIpxRteFltrApplEntry
		ACCESS	not-accessible
		STATUS	mandatory
		DESCRIPTION
			"IPX named route filter application entry."
		INDEX		{ accIpxRteFltrApplIfIndex,
				  accIpxRteFltrApplPktDir,
   				  accIpxRteFltrApplSeqNum  }
	::= { accIpxRteFltrApplTable 1 }
	accIpxRteFltrApplIfIndex	OBJECT-TYPE
		SYNTAX	INTEGER
		ACCESS	read-only
		STATUS	mandatory
		DESCRIPTION
			"Interface Index to which the IPX Route  filter is 
			 applied"
	::= { accIpxRteFltrApplEntry 1 }
	accIpxRteFltrApplPktDir	OBJECT-TYPE
		SYNTAX	INTEGER  {
				input(1),
				output(2),
				global(3)
				}
		ACCESS	read-only
		STATUS	mandatory
		DESCRIPTION
			"Traffic direction to which the IPX Route  filter is 
			 applied"
	::= { accIpxRteFltrApplEntry 2 }
	accIpxRteFltrApplSeqNum	OBJECT-TYPE
		SYNTAX	INTEGER
		ACCESS	read-only
		STATUS	mandatory
		DESCRIPTION
			"Internally generated number indicating the sequence 
			 in which the IPX Route filter is applied. Filters are 
			 applied in the order of most specific to least 
			 specific filter "
	::= { accIpxRteFltrApplEntry 3 }
	accIpxRteFltrApplName	OBJECT-TYPE
		SYNTAX	DisplayString
		ACCESS	read-only
		STATUS	mandatory
		DESCRIPTION
			"Name of the IPX Route  filter being applied"
	::= { accIpxRteFltrApplEntry 4 }
	accIpxRteFltrApplMatches	OBJECT-TYPE
		SYNTAX	Counter
		ACCESS	read-only
		STATUS	mandatory
		DESCRIPTION
			"Number of times the filter matched an IPX traffic 
			 packet - on the given interface"
	::= { accIpxRteFltrApplEntry 5 }
	accIpxRteFltrApplLastMatch	OBJECT-TYPE
		SYNTAX	TimeTicks
		ACCESS	read-only
		STATUS	mandatory
		DESCRIPTION
			"Time tick value when the filter last matched an IPX 
			 traffic packet - on the given interface"
	::= { accIpxRteFltrApplEntry 6 }
	accIpxNamedNetFilters OBJECT IDENTIFIER ::= { accIpx 17 }
        accIpxNamedNetFltrDefault OBJECT-TYPE
             SYNTAX   INTEGER  {
                        discard(0),
                        lowPriority(1),
                        normalPriority(2),
                        highPriority(3)
			}
             ACCESS   read-write
             STATUS   mandatory
             DESCRIPTION
             " The action taken on messages not matched.
		"
             ::= { accIpxNamedNetFilters 1 }
	accIpxNamedNetFltrTable	OBJECT-TYPE
		SYNTAX	SEQUENCE OF AccIpxNamedNetFltrEntry
		ACCESS	not-accessible
		STATUS	mandatory
              DESCRIPTION ""
	::= { accIpxNamedNetFilters 2 }
	AccIpxNamedNetFltrEntry	::= SEQUENCE  {
		accIpxNamedNetFltrDestination	OCTET STRING,
		accIpxNamedNetFltrSource	OCTET STRING,
		accIpxNamedNetFltrAction	INTEGER,
		accIpxNamedNetFltrStatus	INTEGER,
		accIpxNamedNetFltrDestSkt	OCTET STRING,
		accIpxNamedNetFltrSrcSkt	OCTET STRING,
		accIpxNamedNetFltrType	        INTEGER,
		accIpxNamedNetFltrName		OCTET STRING,
		accIpxNamedNetFltrPktDir	INTEGER,
		accIpxNamedNetFltrMatches	Counter,
		accIpxNamedNetFltrLastMatch	TimeTicks,
 		accIpxNamedNetFltrDestMask      OCTET STRING,
		accIpxNamedNetFltrSrcMask	OCTET STRING
		}
	accIpxNamedNetFltrEntry	OBJECT-TYPE
		SYNTAX	AccIpxNamedNetFltrEntry
		ACCESS	not-accessible
		STATUS	mandatory
		DESCRIPTION
                       	"A single IPX named network filter entry."
		INDEX		{ accIpxNamedNetFltrName }
	::= { accIpxNamedNetFltrTable 1 }
 	accIpxNamedNetFltrDestination  OBJECT-TYPE
		SYNTAX   OCTET STRING   -- ( Size (4) )
      		ACCESS   read-write
		STATUS   mandatory
		DESCRIPTION	
			"The value to be found in the Destination Network Field,
			 or 0x00000000."			
	::=  { accIpxNamedNetFltrEntry 1 }
	accIpxNamedNetFltrSource  OBJECT-TYPE
		SYNTAX   OCTET STRING   -- ( Size (4) )
      		ACCESS   read-write
		STATUS   mandatory
		DESCRIPTION	
			"The value to be found in the Source Network Field, or 
			 0x00000000."			
	::=  { accIpxNamedNetFltrEntry 2 }
	accIpxNamedNetFltrAction  OBJECT-TYPE
                 SYNTAX   INTEGER  {
                                     discard(0),
                                     lowPriority(1),
                                     normalPriority(2),
                                     highPriority(3)
			}
                 ACCESS   read-write
                 STATUS   deprecated
                 DESCRIPTION
                      " The action to be taken on matching messages.
		"
	::=  { accIpxNamedNetFltrEntry 3 }
	accIpxNamedNetFltrStatus  OBJECT-TYPE
		SYNTAX   INTEGER  {
				invalid (1),
				valid (2)
				}
      		ACCESS   read-write
		STATUS   mandatory
		DESCRIPTION	
			"Writing 'invalid' has the effect of removing this 
			 filter entry" 		
	::=  { accIpxNamedNetFltrEntry 4 }
	accIpxNamedNetFltrDestSkt  OBJECT-TYPE
		SYNTAX   OCTET STRING   -- ( Size (2) )
      		ACCESS   read-write
		STATUS   mandatory
		DESCRIPTION	
			"The value to be found in the Destination Socket Field,
			 or 0x0000" 
	::=  { accIpxNamedNetFltrEntry 5 }
	accIpxNamedNetFltrSrcSkt  OBJECT-TYPE
		SYNTAX   OCTET STRING   -- ( Size (2) )
      		ACCESS   read-write
		STATUS   mandatory
		DESCRIPTION	
			"The value to be found in the Source Socket Field, or 
			 0x0000" 
	::=  { accIpxNamedNetFltrEntry 6 }
	accIpxNamedNetFltrType  OBJECT-TYPE
		SYNTAX   INTEGER
      		ACCESS   read-write
		STATUS   mandatory
		DESCRIPTION	
			"Packet type or zero" 
	::=  { accIpxNamedNetFltrEntry 7 }
	accIpxNamedNetFltrName  OBJECT-TYPE
		SYNTAX   OCTET STRING
      		ACCESS   read-write
		STATUS   mandatory
		DESCRIPTION	
			"Name of an IPX Network Filter.  A string of up to 15 
			 case sensitive ASCII characters."			
	::=  { accIpxNamedNetFltrEntry 8 }
	accIpxNamedNetFltrPktDir  OBJECT-TYPE
		SYNTAX	INTEGER {
				input(1),
				output(2)
				}
		ACCESS	read-write
		STATUS	mandatory	
		DESCRIPTION
			"Traffic direction to which the filter is applied"
	::=  { accIpxNamedNetFltrEntry 9 }
	accIpxNamedNetFltrMatches  OBJECT-TYPE
		SYNTAX   Counter
      		ACCESS   read-only
		STATUS   mandatory
		DESCRIPTION	
			"Number of times an IPX packet matched the filter "
	::=  { accIpxNamedNetFltrEntry 10 }
	accIpxNamedNetFltrLastMatch  OBJECT-TYPE
		SYNTAX   TimeTicks
      		ACCESS   read-only
		STATUS   mandatory
		DESCRIPTION	
			"Time-tick when the last IPX packet matched the filter"
	::=  { accIpxNamedNetFltrEntry 11 }
	accIpxNamedNetFltrDestMask  OBJECT-TYPE
		SYNTAX   OCTET STRING -- ( SIZE (4))
      		ACCESS   read-write
		STATUS   mandatory
		DESCRIPTION	
			"Network Mask to describe a range of destination 
			 network numbers.  Network mask is a hexadecimal number
			 in the range of 0x0 to 0xffffffff containing a 
			 contiguous stream of 1 bits "
 	::=  { accIpxNamedNetFltrEntry 12 }
	accIpxNamedNetFltrSrcMask  OBJECT-TYPE
		SYNTAX   OCTET STRING -- ( SIZE (4))
      		ACCESS   read-write
		STATUS   mandatory
		DESCRIPTION	
			"Network Mask to describe a range of source network 
			 numbers. Network mask is a hexadecimal number in the 
			 range of 0x0 to 0xffffffff containing a contiguous 
			 stream of 1 bits "
 	::=  { accIpxNamedNetFltrEntry 13 }
	accIpxNetFltrApplTable OBJECT-TYPE
		SYNTAX  SEQUENCE OF AccIpxNetFltrApplEntry 
		ACCESS  	not-accessible
		STATUS  	mandatory
		DESCRIPTION
			"This table describes application of IPX Net filters 
			 to IPX ports"
	::=  { accIpxNamedNetFilters 3  }
	AccIpxNetFltrApplEntry  ::= SEQUENCE {
		accIpxNetFltrApplIfIndex        INTEGER,
		accIpxNetFltrApplPktDir	        INTEGER,
		accIpxNetFltrApplSeqNum		INTEGER,
		accIpxNetFltrApplName		DisplayString,
		accIpxNetFltrApplMatches        Counter,
		accIpxNetFltrApplLastMatch	TimeTicks
	}
	accIpxNetFltrApplEntry	OBJECT-TYPE
		SYNTAX	AccIpxNetFltrApplEntry
		ACCESS	not-accessible
		STATUS	mandatory
		DESCRIPTION
			"IPX named network filter application entry."
		INDEX		{ accIpxNetFltrApplIfIndex,
				  accIpxNetFltrApplPktDir,
				  accIpxNetFltrApplSeqNum  }
	::= { accIpxNetFltrApplTable 1 }
	accIpxNetFltrApplIfIndex	OBJECT-TYPE
		SYNTAX	INTEGER
		ACCESS	read-only
		STATUS	mandatory
		DESCRIPTION
			"Interface Index to which the IPX Net filter is applied"
	::= { accIpxNetFltrApplEntry 1 }
	accIpxNetFltrApplPktDir	OBJECT-TYPE
		SYNTAX	INTEGER  {
				input(1),
				output(2),
				global(3)
				}
		ACCESS	read-only
		STATUS	mandatory
		DESCRIPTION
			"Traffic direction to which the IPX Net filter is 
			 applied"
	::= { accIpxNetFltrApplEntry 2 }
	accIpxNetFltrApplSeqNum	OBJECT-TYPE
		SYNTAX	INTEGER
		ACCESS	read-only
		STATUS	mandatory
		DESCRIPTION
			"Internally generated number indicating the sequence in
			 which the IPX Net filter is applied. Filters are 
			 applied in the order of most specific to least 
			 specific filter "
	::= { accIpxNetFltrApplEntry 3 }
	accIpxNetFltrApplName	OBJECT-TYPE
		SYNTAX	DisplayString
		ACCESS	read-only
		STATUS	mandatory
		DESCRIPTION
			"Name of the IPX Net filter being applied"
	::= { accIpxNetFltrApplEntry 4 }
	accIpxNetFltrApplMatches	OBJECT-TYPE
		SYNTAX	Counter
		ACCESS	read-only
		STATUS	mandatory
		DESCRIPTION
			"Number of times the filter matched an IPX traffic 
			 packet - on the given interface"
	::= { accIpxNetFltrApplEntry 5 }
	accIpxNetFltrApplLastMatch	OBJECT-TYPE
		SYNTAX	TimeTicks
		ACCESS	read-only
		STATUS	mandatory
		DESCRIPTION
			"Time tick value when the filter last matched an IPX 
			 traffic packet - on the given interface"
	::= { accIpxNetFltrApplEntry 6 }
	accIpxNamedHostFilters OBJECT IDENTIFIER ::= { accIpx 18 }
        accIpxNamedHostFltrDefaultAction OBJECT-TYPE
            SYNTAX   INTEGER { 
                        discard(0),
                        lowPriority(1),
                        normalPriority(2),
                        highPriority(3)
		  }
            ACCESS   read-write
            STATUS   mandatory
            DESCRIPTION
                  " The action taken on hosts not listed.
		"
            ::= { accIpxNamedHostFilters 1 }
	accIpxNamedHostFltrTable	OBJECT-TYPE
		SYNTAX	SEQUENCE OF AccIpxNamedHostFltrEntry
		ACCESS	not-accessible
		STATUS	mandatory
              DESCRIPTION ""
	::= { accIpxNamedHostFilters 2 }
	AccIpxNamedHostFltrEntry	::= SEQUENCE  {
		accIpxNamedHostFltrId		OCTET STRING,
		accIpxNamedHostFltrSocket	OCTET STRING,
		accIpxNamedHostFltrPepClient	OCTET STRING,
		accIpxNamedHostFltrAction	INTEGER,
		accIpxNamedHostFltrStatus	INTEGER,
		accIpxNamedHostFltrName		OCTET STRING,
		accIpxNamedHostFltrPktDir	INTEGER,
		accIpxNamedHostFltrMatches	Counter,
		accIpxNamedHostFltrLastMatch	TimeTicks
		}
	accIpxNamedHostFltrEntry	OBJECT-TYPE
		SYNTAX	AccIpxNamedHostFltrEntry
		ACCESS	not-accessible
		STATUS	mandatory
		DESCRIPTION
			"A single IPX named host filter entry."
		INDEX		{ accIpxNamedHostFltrName }
	::= { accIpxNamedHostFltrTable 1 }
	accIpxNamedHostFltrId  OBJECT-TYPE
		SYNTAX   OCTET STRING   -- ( Size (6) )
      		ACCESS   read-write
		STATUS   mandatory
		DESCRIPTION	
			"Host Identifier of the destination host in IPX message"
	::=  { accIpxNamedHostFltrEntry 1 }
	accIpxNamedHostFltrSocket  OBJECT-TYPE
		SYNTAX   OCTET STRING   -- ( Size (2) )
      		ACCESS   read-write
		STATUS   mandatory
		DESCRIPTION	
			"Destination socket in IPX message or zero" 
	::=  { accIpxNamedHostFltrEntry 2 }
	accIpxNamedHostFltrPepClient  OBJECT-TYPE
		SYNTAX   OCTET STRING   -- ( Size (2) )
      		ACCESS   read-write
		STATUS   mandatory
		DESCRIPTION	
			"On PEP traffic, client type in message or zero for
      			 all IPX and IDP traffic" 
	::=  { accIpxNamedHostFltrEntry 3 }
	accIpxNamedHostFltrAction  OBJECT-TYPE
		SYNTAX   INTEGER {
                               discard(0),
                               lowPriority(1),
                               normalPriority(2),
                               highPriority(3)
			 	}
		ACCESS   read-write
		STATUS   mandatory
		DESCRIPTION
                         " The action to be taken on matching messages.
		"
	::=  { accIpxNamedHostFltrEntry 4 }
	accIpxNamedHostFltrStatus  OBJECT-TYPE
		SYNTAX   INTEGER  {
				invalid (1),
				valid (2)
			}
      		ACCESS   read-write
		STATUS   mandatory
		DESCRIPTION	
			"Writing 'invalid' has the effect of deleting the entry" 
	::=  { accIpxNamedHostFltrEntry 5 }
	accIpxNamedHostFltrName  OBJECT-TYPE
		SYNTAX   OCTET STRING
      		ACCESS   read-write
		STATUS   mandatory
		DESCRIPTION	
			"Name of an IPX Host Filter.  A string of up to 15 case
			 sensitive ASCII characters." 
	::=  { accIpxNamedHostFltrEntry 6 }
	accIpxNamedHostFltrPktDir  OBJECT-TYPE
		SYNTAX	INTEGER {
				input(1),
				output(2)
				}
		ACCESS	read-write
		STATUS	mandatory	
		DESCRIPTION
			"Traffic direction to which the filter is applied"
	::=  { accIpxNamedHostFltrEntry 7 }
	accIpxNamedHostFltrMatches  OBJECT-TYPE
		SYNTAX   Counter
      		ACCESS   read-only
		STATUS   mandatory
		DESCRIPTION	
			"Number of times an IPX packet matched the filter "
	::=  { accIpxNamedHostFltrEntry 8 }
	accIpxNamedHostFltrLastMatch  OBJECT-TYPE
		SYNTAX   TimeTicks
		ACCESS   read-only
		STATUS   mandatory
		DESCRIPTION	
			"Time-tick when the last IPX packet matched the filter"
	::=  { accIpxNamedHostFltrEntry 9 }
--
--		The IPX Host Filter Application Table
--
	accIpxHostFltrApplTable OBJECT-TYPE
		SYNTAX  SEQUENCE OF AccIpxHostFltrApplEntry 
		ACCESS  	not-accessible
		STATUS  	mandatory
		DESCRIPTION
			"This table describes application of IPX Host filters 
			 to IPX ports"
	::= { accIpxNamedHostFilters 3 }
	AccIpxHostFltrApplEntry  ::= SEQUENCE {
		accIpxHostFltrApplIfIndex	INTEGER,
		accIpxHostFltrApplPktDir	INTEGER,
		accIpxHostFltrApplSeqNum	INTEGER,
		accIpxHostFltrApplName		DisplayString,
		accIpxHostFltrApplMatches	Counter,
		accIpxHostFltrApplLastMatch	TimeTicks
	}
	accIpxHostFltrApplEntry	OBJECT-TYPE
		SYNTAX	AccIpxHostFltrApplEntry
		ACCESS	not-accessible
		STATUS	mandatory
		DESCRIPTION
			"IPX named host filter application entry."
		INDEX		{ accIpxHostFltrApplIfIndex,
				  accIpxHostFltrApplPktDir,
				  accIpxHostFltrApplSeqNum  }
	::= { accIpxHostFltrApplTable 1 }
	accIpxHostFltrApplIfIndex	OBJECT-TYPE
		SYNTAX	INTEGER
		ACCESS	read-only
		STATUS	mandatory
		DESCRIPTION
			"Interface Index to which the IPX Host filter is 
			 applied"
	::= { accIpxHostFltrApplEntry 1 }
	accIpxHostFltrApplPktDir	OBJECT-TYPE
		SYNTAX	INTEGER  {
				input(1),
				output(2),
				global(3)
				}
		ACCESS	read-only
		STATUS	mandatory
		DESCRIPTION
			"Traffic direction to which the IPX Host filter is 
			 applied"
	::= { accIpxHostFltrApplEntry 2 }
	accIpxHostFltrApplSeqNum	OBJECT-TYPE
		SYNTAX	INTEGER
		ACCESS	read-only
		STATUS	mandatory
		DESCRIPTION
			"Internally generated number indicating the sequence in 
			 which the IPX Host filter is applied.  Filters are 
			 applied in the order of most specific to least 
			 specific filter"
	::= { accIpxHostFltrApplEntry 3 }
	accIpxHostFltrApplName	OBJECT-TYPE
		SYNTAX	DisplayString
		ACCESS	read-only
		STATUS	mandatory
		DESCRIPTION
			"Name of the IPX Host filter being applied"
	::= { accIpxHostFltrApplEntry 4 }
	accIpxHostFltrApplMatches	OBJECT-TYPE
		SYNTAX	Counter
		ACCESS	read-only
		STATUS	mandatory
		DESCRIPTION
			"Number of times the filter matched an IPX traffic 
			 packet - on the given interface"
	::= { accIpxHostFltrApplEntry 5 }
	accIpxHostFltrApplLastMatch	OBJECT-TYPE
		SYNTAX	TimeTicks
		ACCESS	read-only
		STATUS	mandatory
		DESCRIPTION
			"Time tick value when the filter last matched an IPX 
			 traffic packet - on the given interface"
	::= { accIpxHostFltrApplEntry 6 }
	accIpxNamedSapFilters	OBJECT IDENTIFIER	::= { accIpx 19 }
        accIpxNamedSapFltrDefault OBJECT-TYPE
            SYNTAX   INTEGER {
                        accept(1), 
                        reject(2) 
                        }
            ACCESS   read-write
            STATUS   mandatory
            DESCRIPTION
		" The default behavior taken on locally originated (hop count 
		  <= 2) Service Advertisements.  Remote advertisements must be
		  identified individually."
	::= { accIpxNamedSapFilters 1 }
	accIpxNamedSapFltrTable	OBJECT-TYPE
		SYNTAX	SEQUENCE OF AccIpxNamedSapFltrEntry
		ACCESS	not-accessible
		STATUS	mandatory
              DESCRIPTION ""
	::= { accIpxNamedSapFilters 2 }
	AccIpxNamedSapFltrEntry	::= SEQUENCE  {
		accIpxNamedSapFltrSrvType	OCTET STRING,
		accIpxNamedSapFltrSrvName	OCTET STRING,
		accIpxNamedSapFltrAction	INTEGER,
		accIpxNamedSapFltrStatus	INTEGER,
		accIpxNamedSapFltrName		OCTET STRING,
		accIpxNamedSapFltrPktDir	INTEGER,
		accIpxNamedSapFltrMatches	Counter,
		accIpxNamedSapFltrLastMatch	TimeTicks
		}
	accIpxNamedSapFltrEntry	OBJECT-TYPE
		SYNTAX	AccIpxNamedSapFltrEntry
		ACCESS	not-accessible
		STATUS	mandatory
		DESCRIPTION
			"A single IPX named SAP filter entry."
		INDEX		{ accIpxNamedSapFltrName }
	::= { accIpxNamedSapFltrTable 1 }
	accIpxNamedSapFltrSrvType  OBJECT-TYPE
		SYNTAX   OCTET STRING   -- ( Size (2) )
     		ACCESS   read-write
		STATUS   mandatory
		DESCRIPTION	
			"The service type of the affected SAP entry.  Zero  
			 indicates all service types."
	::=  { accIpxNamedSapFltrEntry 1 }
	accIpxNamedSapFltrSrvName  OBJECT-TYPE
		SYNTAX   OCTET STRING
     		ACCESS   read-write
		STATUS   mandatory
		DESCRIPTION	
			"The name of the affected service.  A '*' character in 
			 the name indicates wild-carding.  A name of '*' 
			 matches all services.  Name may be up to 48 
			 characters long"
	::=  { accIpxNamedSapFltrEntry 2 }
	accIpxNamedSapFltrAction  OBJECT-TYPE
		SYNTAX   INTEGER {
				accept (1),
				reject (2)
				}
      		ACCESS   read-write
		STATUS   mandatory
		DESCRIPTION	
			"The action to be taken upon a match"  
	::=  { accIpxNamedSapFltrEntry 3 }
	accIpxNamedSapFltrStatus  OBJECT-TYPE
               	SYNTAX   INTEGER {
				invalid (1),
				valid  (2)
				}
      		ACCESS   read-write
		STATUS   mandatory
		DESCRIPTION	
			"Writing 'invalid' has the effect of deleting this 
			 filter"  
	::=  { accIpxNamedSapFltrEntry 4 }
	accIpxNamedSapFltrName  OBJECT-TYPE
		SYNTAX   OCTET STRING
     		ACCESS   read-write
		STATUS   mandatory
		DESCRIPTION	
			"Name of an IPX SAP Filter.  A string of up to 15 case 
			 sensitive ASCII characters."
	::=  { accIpxNamedSapFltrEntry 5 }
	accIpxNamedSapFltrPktDir  OBJECT-TYPE
		SYNTAX	INTEGER {
				input(1),
				output(2)
				}
		ACCESS	read-write
		STATUS	mandatory	
		DESCRIPTION
			"Traffic direction to which the filter is applied"
	::=  { accIpxNamedSapFltrEntry 6 }
	accIpxNamedSapFltrMatches  OBJECT-TYPE
		SYNTAX   Counter
		ACCESS   read-only
		STATUS   mandatory
		DESCRIPTION	
			"Number of times an IPX packet matched the filter "
	::=  { accIpxNamedSapFltrEntry 7 }
	accIpxNamedSapFltrLastMatch  OBJECT-TYPE
		SYNTAX   TimeTicks
      		ACCESS   read-only
		STATUS   mandatory
		DESCRIPTION	
			"Time-tick when the last IPX packet matched the filter"	
	::=  { accIpxNamedSapFltrEntry 8  }
	accIpxSapFltrApplTable OBJECT-TYPE
		SYNTAX  SEQUENCE OF AccIpxSapFltrApplEntry 
		ACCESS  	not-accessible
		STATUS  	mandatory
		DESCRIPTION
			"This table describes application of IPX Sap filters 
			 to IPX ports"
	::= {  accIpxNamedSapFilters 3  }
	AccIpxSapFltrApplEntry  ::= SEQUENCE {
		accIpxSapFltrApplIfIndex        INTEGER,
		accIpxSapFltrApplPktDir	        INTEGER,
		accIpxSapFltrApplSeqNum		INTEGER,
		accIpxSapFltrApplName		DisplayString,
		accIpxSapFltrApplMatches        Counter,
		accIpxSapFltrApplLastMatch	TimeTicks
	}
	accIpxSapFltrApplEntry	OBJECT-TYPE
		SYNTAX	AccIpxSapFltrApplEntry
		ACCESS	not-accessible
		STATUS	mandatory
		DESCRIPTION
			"IPX named sap filter application entry."
		INDEX		{ accIpxSapFltrApplIfIndex,
				  accIpxSapFltrApplPktDir,
				  accIpxSapFltrApplSeqNum  }
	::= { accIpxSapFltrApplTable 1 }
	accIpxSapFltrApplIfIndex	OBJECT-TYPE
		SYNTAX	INTEGER
		ACCESS	read-only
		STATUS	mandatory
		DESCRIPTION
			"Interface Index to which the IPX Sap filter is applied"
	::= { accIpxSapFltrApplEntry 1 }
	accIpxSapFltrApplPktDir	OBJECT-TYPE
		SYNTAX	INTEGER  {
				input(1),
				output(2),
				global(3)
				}
		ACCESS	read-only
		STATUS	mandatory
		DESCRIPTION
			"Traffic direction to which the IPX Sap filter is 
			 applied"
	::= { accIpxSapFltrApplEntry 2 }
	accIpxSapFltrApplSeqNum	OBJECT-TYPE
		SYNTAX	INTEGER
		ACCESS	read-only
		STATUS	mandatory
		DESCRIPTION
			"Internally generated number indicating the sequence in 
			 which the IPX Sap filter is applied. Filters are 
			 applied in the order of most specific to least 
			 specific filter"
	::= { accIpxSapFltrApplEntry 3 }
	accIpxSapFltrApplName	OBJECT-TYPE
		SYNTAX	DisplayString
		ACCESS	read-only
		STATUS	mandatory
		DESCRIPTION
			"Name of the IPX Sap filter being applied"
	::= { accIpxSapFltrApplEntry 4 }
	accIpxSapFltrApplMatches	OBJECT-TYPE
		SYNTAX	Counter
		ACCESS	read-only
		STATUS	mandatory
		DESCRIPTION
			"Number of times the filter matched an IPX traffic 
			 packet - on the given interface"
	::= { accIpxSapFltrApplEntry 5 }
	accIpxSapFltrApplLastMatch	OBJECT-TYPE
		SYNTAX	TimeTicks
		ACCESS	read-only
		STATUS	mandatory
		DESCRIPTION
			"Time tick value when the filter last matched an IPX 
			 traffic packet - on the given interface"
	::= { accIpxSapFltrApplEntry 6 }

END
