ENTERASYS-IEEE8021-BRIDGE-MIB-EXT-MIB DEFINITIONS ::= BEGIN

--  enterasys-ieee8021-bridge-mib-ext-mib.txt 
--
--  Part Number:
--
--

--  This module provides authoritative definitions for Enterasys
--  Networks' IEEE8021-BRIDGE-MIB extension mib

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February, 2012 Enterasys Networks, Inc.

IMPORTS
    MODULE-IDENTITY, OBJECT-TYPE
        FROM SNMPv2-SMI
    MODULE-COMPLIANCE, OBJECT-GROUP
        FROM SNMPv2-CONF
    EnabledStatus
        FROM P-BRIDGE-MIB
    IEEE8021PbbComponentIdentifier
        FROM IEEE8021-TC-MIB
    ieee8021BridgeBasePort, ieee8021BridgeBasePortEntry
        FROM IEEE8021-BRIDGE-MIB
    etsysModules
        FROM ENTERASYS-MIB-NAMES;

etsysIeee8021BridgeMibExtMIB MODULE-IDENTITY
    LAST-UPDATED "201202071435Z"  -- Tue Feb  7 14:35 UTC 2012
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"

    DESCRIPTION
        "This MIB module defines a portion of the SNMP MIB under
         the Enterasys Networks enterprise OID pertaining to
         proprietary extensions to the IEEE8021-BRIDGE-MIB."

    REVISION     "201202071435Z"  -- Tue Feb  7 14:35 UTC 2012
    DESCRIPTION  "Initial version of this MIB module."

    ::= { etsysModules 90 }

-- -------------------------------------------------------------
-- Ieee8021BridgeMib Extension MIB Groups
-- -------------------------------------------------------------

etsysIeee8021BridgeMibExtObjects
    OBJECT IDENTIFIER ::= { etsysIeee8021BridgeMibExtMIB 1 }

etsysIeee8021BridgeMibExtConformance
    OBJECT IDENTIFIER ::= { etsysIeee8021BridgeMibExtMIB 2 }

etsysIeee8021BridgeBase
     OBJECT IDENTIFIER ::= { etsysIeee8021BridgeMibExtObjects 1 }

-- -------------------------------------------------------------
-- Extensions to the ieee8021BridgeBase Object 
-- -------------------------------------------------------------

etsysIeee8021BridgeBaseMode OBJECT-TYPE
    SYNTAX      INTEGER {
                  customerBridge(1),
                  providerBridge(2),
                  providerBackboneBridge(3)
                }
    MAX-ACCESS  read-write
    STATUS      current
    DESCRIPTION
        "Indicates the mode of operation of this bridge. The
         following operation modes are possible:

         customerBridge(1) - Indicates the bridge is a MAC
         Bridge as specified by IEEE Std 802.1D or a VLAN
         Bridge as specified by IEEE Std 802.1Q.

         providerBridge(2) - Indicates the bridge is an
         S-VLAN bridge or Provider Edge Bridge.

         providerBackboneBridge(3) - Indicates the bridge is a
         Backbone Core Bridge or a Backbone Edge Bridge."
    ::= { etsysIeee8021BridgeBase 1 }

etsysIeee8021BridgeBasePortTable OBJECT-TYPE
    SYNTAX      SEQUENCE OF EtsysIeee8021BridgeBasePortEntry
    MAX-ACCESS  not-accessible
    STATUS      current
    DESCRIPTION
        "This table contains generic information about every 
         bridge port that is associated with this bridge. It
         extends the information provided by the 
         ieee8021BridgeBasePortTable."
    ::= { etsysIeee8021BridgeBase 2 }

etsysIeee8021BridgeBasePortEntry OBJECT-TYPE
    SYNTAX      EtsysIeee8021BridgeBasePortEntry
    MAX-ACCESS  not-accessible
    STATUS      current
    DESCRIPTION
        "A list of objects containing information for each port
         of the bridge."
    INDEX { ieee8021BridgeBasePort }
    ::= { etsysIeee8021BridgeBasePortTable 1 }

EtsysIeee8021BridgeBasePortEntry ::=
    SEQUENCE { 
        etsys8021BridgePortComponentId
             IEEE8021PbbComponentIdentifier
    }

etsys8021BridgePortComponentId    OBJECT-TYPE
    SYNTAX      IEEE8021PbbComponentIdentifier
    MAX-ACCESS  read-only
    STATUS      current
    DESCRIPTION
        "The componentId a bridge port belongs to or is assigned to."
    ::= { etsysIeee8021BridgeBasePortEntry 1 }

-- -------------------------------------------------------------
-- Ieee8021BridgeMib Extension MIB Branches
-- -------------------------------------------------------------

etsysIeee8021BridgeMibExtMrpBranch
    OBJECT IDENTIFIER ::= { etsysIeee8021BridgeMibExtObjects 2 }

-- -------------------------------------------------------------
-- Extension MIB MRP Branch 
-- -------------------------------------------------------------

etsysIeee8021BridgeMibExtMrpTable OBJECT-TYPE
    SYNTAX      SEQUENCE OF EtsysIeee8021BridgeMibExtMrpEntry
    MAX-ACCESS  not-accessible
    STATUS      current
    DESCRIPTION
        "A table of bridge port MRP timer control information."
    ::= { etsysIeee8021BridgeMibExtMrpBranch 1 }

etsysIeee8021BridgeMibExtMrpEntry OBJECT-TYPE
    SYNTAX      EtsysIeee8021BridgeMibExtMrpEntry
    MAX-ACCESS  not-accessible
    STATUS      current
    DESCRIPTION
        "MRP timer control information for a bridge port."
    AUGMENTS { ieee8021BridgeBasePortEntry }
    ::= { etsysIeee8021BridgeMibExtMrpTable 1 }

EtsysIeee8021BridgeMibExtMrpEntry ::=
    SEQUENCE {
        etsysIeee8021BridgeMibExtMrpPeriodicEnabled
            EnabledStatus
    }

etsysIeee8021BridgeMibExtMrpPeriodicEnabled OBJECT-TYPE
    SYNTAX      EnabledStatus
    MAX-ACCESS  read-write
    STATUS      current
    DESCRIPTION
        "The MRP periodic transmission enabled status.
         The value of this object MUST be retained across
         re-initializations of the management system."
    DEFVAL      { disabled }
    ::= { etsysIeee8021BridgeMibExtMrpEntry 1 }

-- -------------------------------------------------------------
-- Conformance Information
-- -------------------------------------------------------------

etsysIeee8021BridgeMibExtGroups      OBJECT IDENTIFIER
    ::= { etsysIeee8021BridgeMibExtConformance 1 }

etsysIeee8021BridgeMibExtCompliances OBJECT IDENTIFIER
    ::= { etsysIeee8021BridgeMibExtConformance 2 }

-- -------------------------------------------------------------
-- Units of conformance
-- -------------------------------------------------------------

etsysIeee8021BridgeMibExtBaseModeGroup OBJECT-GROUP
    OBJECTS {
        etsysIeee8021BridgeBaseMode
    }
    STATUS      current
    DESCRIPTION
        "A collection of objects providing information about
         the mode of operation of the bridge."
    ::= { etsysIeee8021BridgeMibExtGroups 1 }

etsysIeee8021BridgeMibExtBasePortGroup OBJECT-GROUP
    OBJECTS {
        etsys8021BridgePortComponentId
    }
    STATUS      current
    DESCRIPTION
        "A collection of objects providing information about
         the relation between bridge port and componentId."
    ::= { etsysIeee8021BridgeMibExtGroups 2 }

etsysIeee8021BridgeMibExtMrpGroup OBJECT-GROUP
    OBJECTS {
        etsysIeee8021BridgeMibExtMrpPeriodicEnabled
    }
    STATUS      current
    DESCRIPTION
        "A collection of objects providing port level control 
         and status information for MRP operation"
    ::= { etsysIeee8021BridgeMibExtGroups 3 }

-- -------------------------------------------------------------
-- Compliance statements
-- -------------------------------------------------------------

etsysIeee8021BridgeMibExtCompliance MODULE-COMPLIANCE
    STATUS      current
    DESCRIPTION
        "The compliance statement for devices that support
         etsysIeee8021BridgeMibExtMIB."

    MODULE
        GROUP       etsysIeee8021BridgeMibExtBaseModeGroup
        DESCRIPTION
            "This group is REQUIRED for devices supporting
             IEEE8021-BRIDGE-MIB."

        GROUP       etsysIeee8021BridgeMibExtBasePortGroup 
        DESCRIPTION
            "This group is REQUIRED for devices supporting 
             IEEE8021-BRIDGE-MIB."

    ::= { etsysIeee8021BridgeMibExtCompliances 1 }

etsysIeee8021BridgeMibExtMrpCompliance MODULE-COMPLIANCE
    STATUS      current
    DESCRIPTION
        "The compliance statement for devices that support
         the MRP periodic transmission status."

    MODULE
        GROUP       etsysIeee8021BridgeMibExtMrpGroup
        DESCRIPTION
            "This group is REQUIRED for devices supporting 
             IEEE8021-BRIDGE-MIB."

    ::= { etsysIeee8021BridgeMibExtCompliances 2 }

END
