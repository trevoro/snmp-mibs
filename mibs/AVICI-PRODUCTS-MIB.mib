AVICI-PRODUCTS-MIB DEFINITIONS ::= BEGIN

IMPORTS
   MODULE-IDENTITY
      FROM SNMPv2-SMI
   aviciMibs, aviciProducts
      FROM AVICI-SMI;

aviciProductsMIB MODULE-IDENTITY
   LAST-UPDATED   "000524190000Z"
   ORGANIZATION   "Avici Systems, Inc."
   CONTACT-INFO   "
                  Avici Systems, Inc.
                  101 Billerica Avenue
                  North Billerica, MA 01862-1256

                  (978) 964-2000
                  (978) 964-2100 (fax)

                  snmp@avici.com"
   DESCRIPTION
      "This MIB module contains the definitions for all Avici products."
   ::= { aviciMibs 1 }


aviciTSR OBJECT IDENTIFIER ::= { aviciProducts 1 }


END
