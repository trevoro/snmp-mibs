Nortel-Magellan-Passport-X25DteMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      InterfaceIndex,
      Gauge32,
      Integer32,
      Unsigned32
   FROM Nortel-Magellan-Passport-StandardTextualConventionsMIB

      AsciiString,
      NonReplicated,
      DigitString,
      HexString,
      Link
   FROM Nortel-Magellan-Passport-TextualConventionsMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     X25Dte Enterprise MIB."

x25DteMIB OBJECT IDENTIFIER ::= { passportMIBs 48 }










-- 
-- X25Dte/n
-- The X25Dte component defines the general parameters for 
-- implementing the X.25 DTE interface. 

x25Dte OBJECT IDENTIFIER ::= { components 90 }



x25DteRowStatusTable OBJECT-TYPE
   SYNTAX     SEQUENCE OF X25DteRowStatusEntry
   ACCESS     not-accessible
   STATUS     mandatory
   DESCRIPTION
     "This entry controls the addition and deletion of 
      x25Dte components."
::= { x25Dte 1 }

x25DteRowStatusEntry OBJECT-TYPE
   SYNTAX     X25DteRowStatusEntry
   ACCESS     not-accessible
   STATUS     mandatory
   DESCRIPTION
     "A single entry in the table represents a single 
      x25Dte component."
   INDEX {
      x25DteIndex }
::= { x25DteRowStatusTable 1 }

X25DteRowStatusEntry ::= SEQUENCE {
   x25DteRowStatus
      RowStatus,
   x25DteComponentName
      DisplayString,
   x25DteStorageType
      StorageType,
   x25DteIndex
      Integer32 }

x25DteRowStatus OBJECT-TYPE
   SYNTAX     RowStatus 
   ACCESS     read-write
   STATUS     mandatory
   DESCRIPTION
     "This variable is used as the basis for SNMP naming of
      x25Dte components.
      These components can be added and deleted."
::= { x25DteRowStatusEntry 1 }

x25DteComponentName OBJECT-TYPE
   SYNTAX     DisplayString 
   ACCESS     read-only
   STATUS     mandatory
   DESCRIPTION
     "This variable provides the component's string name for
      use with the ASCII Console Interface"
::= { x25DteRowStatusEntry 2 }

x25DteStorageType OBJECT-TYPE
   SYNTAX     StorageType 
   ACCESS     read-only
   STATUS     mandatory
   DESCRIPTION
     "This variable represents the storage type value for the
      x25Dte tables."
::= { x25DteRowStatusEntry 4 }

x25DteIndex OBJECT-TYPE
   SYNTAX     Integer32 (1..65535)
   ACCESS     not-accessible
   STATUS     mandatory
   DESCRIPTION
     "This variable represents the index for the x25Dte tables."
::= { x25DteRowStatusEntry 10 }

x25DteCidDataTable OBJECT-TYPE
   SYNTAX     SEQUENCE OF X25DteCidDataEntry
   ACCESS     not-accessible
   STATUS     mandatory
   DESCRIPTION
     "This group contains the attribute for a component's Customer 
      Identifier (CID). Refer to the attribute description for a detailed 
      explanation of CIDs."
::= { x25Dte 20 }

x25DteCidDataEntry OBJECT-TYPE
   SYNTAX     X25DteCidDataEntry
   ACCESS     not-accessible
   STATUS     mandatory
   DESCRIPTION
     "An entry in the x25DteCidDataTable."
   INDEX {
      x25DteIndex }
::= { x25DteCidDataTable 1 }

X25DteCidDataEntry ::= SEQUENCE {
   x25DteCustomerIdentifier
      Unsigned32 }

x25DteCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { x25DteCidDataEntry 1 }

x25DteIfTable OBJECT-TYPE
   SYNTAX     SEQUENCE OF X25DteIfEntry
   ACCESS     not-accessible
   STATUS     mandatory
   DESCRIPTION
     "This group provides the administrative set of parameters for the 
      X.25 interface."
::= { x25Dte 21 }

x25DteIfEntry OBJECT-TYPE
   SYNTAX     X25DteIfEntry
   ACCESS     not-accessible
   STATUS     mandatory
   DESCRIPTION
     "An entry in the x25DteIfTable."
   INDEX {
      x25DteIndex }
::= { x25DteIfTable 1 }

X25DteIfEntry ::= SEQUENCE {
   x25DteInterfaceMode
      INTEGER,
   x25DteMaxActiveChannels
      Unsigned32,
   x25DteNumberOfPLcn
      Unsigned32,
   x25DtePacketSequencing
      INTEGER,
   x25DteT20RestartTimer
      Unsigned32,
   x25DteT21CallTimer
      Unsigned32,
   x25DteT22ResetTimer
      Unsigned32,
   x25DteT23ClearTimer
      Unsigned32 }

x25DteInterfaceMode OBJECT-TYPE
   SYNTAX     INTEGER  {
                 dte(1),
                 dce(2) }
   ACCESS     read-only
   STATUS     mandatory
   DESCRIPTION
     "This attribute specifies the packet mode in which the X.25 interface 
      operates. When this attribute is set to dte, interface on the other side 
      of the physical link must be configured as a dce."
   DEFVAL     { dte }
::= { x25DteIfEntry 1 }

x25DteMaxActiveChannels OBJECT-TYPE
   SYNTAX     Unsigned32 (0..4095)
   ACCESS     read-write
   STATUS     mandatory
   DESCRIPTION
     "This attribute specifies the maximum number of channels that can 
      be active on this interface including the Permanent Lcns and the 
      Switched Lcns. In total maxActiveChannel will determine the 
      maximum number of Lcn components which may exist at a given 
      time. This should be set to a value greater or equal to the 
      numberOfPLcn provisioned."
   DEFVAL     { 10 }
::= { x25DteIfEntry 2 }

x25DteNumberOfPLcn OBJECT-TYPE
   SYNTAX     Unsigned32 (0..4095)
   ACCESS     read-write
   STATUS     mandatory
   DESCRIPTION
     "This attribute specifies the number of Permanent Logical Channels 
      that are supported on this X.25 interface (that is, the number of 
      PermLcn components that may be provisioned at this interface). 
      The PermLcn components use channel numbers starting from 1 and 
      up to lowestILChannelNumber. 
      A value of 0 for this attribute indicates that no Permanent Logical 
      channels are supported on this X.25 interface."
   DEFVAL     { 0 }
::= { x25DteIfEntry 3 }

x25DtePacketSequencing OBJECT-TYPE
   SYNTAX     INTEGER  {
                 modulo8(1),
                 modulo128(2) }
   ACCESS     read-write
   STATUS     mandatory
   DESCRIPTION
     "This attribute specifies the sequence numbering of packets for the 
      X.25 interface. The value of this attribute must be the same as the 
      packet sequencing configured at the X.25 interface on the other side 
      of the physical link."
   DEFVAL     { modulo8 }
::= { x25DteIfEntry 4 }

x25DteT20RestartTimer OBJECT-TYPE
   SYNTAX     Unsigned32 (1000..65536000)
   ACCESS     read-write
   STATUS     mandatory
   DESCRIPTION
     "This attribute provides the period in milliseconds within which a 
      restart request packet should be confirmed."
   DEFVAL     { 60000 }
::= { x25DteIfEntry 5 }

x25DteT21CallTimer OBJECT-TYPE
   SYNTAX     Unsigned32 (1000..65536000)
   ACCESS     read-write
   STATUS     mandatory
   DESCRIPTION
     "This attribute provides the period in milliseconds within which a 
      call request packet should be confirmed."
   DEFVAL     { 180000 }
::= { x25DteIfEntry 6 }

x25DteT22ResetTimer OBJECT-TYPE
   SYNTAX     Unsigned32 (1000..65536000)
   ACCESS     read-write
   STATUS     mandatory
   DESCRIPTION
     "This attribute provides the period in milliseconds within which a 
      reset request packet should be confirmed."
   DEFVAL     { 60000 }
::= { x25DteIfEntry 7 }

x25DteT23ClearTimer OBJECT-TYPE
   SYNTAX     Unsigned32 (1000..65536000)
   ACCESS     read-write
   STATUS     mandatory
   DESCRIPTION
     "This attribute provides the period in milliseconds within which a 
      clear request packet should be confirmed."
   DEFVAL     { 60000 }
::= { x25DteIfEntry 8 }

x25DteLcnCTable OBJECT-TYPE
   SYNTAX     SEQUENCE OF X25DteLcnCEntry
   ACCESS     not-accessible
   STATUS     mandatory
   DESCRIPTION
     "This group contains the provisionable attributes for the Logical 
      Channel configuration of the X.25 Interface. The logical channel 
      range table is ordered as follows: 
      
      Permanent Logical Channels(PLC),
      One-way Incoming Channels (IC), 
      Two-way Channels(TC) and 
      One-way Outgoing Channels (OC),
      
      in a consecutive manner."
::= { x25Dte 22 }

x25DteLcnCEntry OBJECT-TYPE
   SYNTAX     X25DteLcnCEntry
   ACCESS     not-accessible
   STATUS     mandatory
   DESCRIPTION
     "An entry in the x25DteLcnCTable."
   INDEX {
      x25DteIndex }
::= { x25DteLcnCTable 1 }

X25DteLcnCEntry ::= SEQUENCE {
   x25DteLowestILChannelNumber
      Unsigned32,
   x25DteHighestILChannelNumber
      Unsigned32,
   x25DteLowestTLChannelNumber
      Unsigned32,
   x25DteHighestTLChannelNumber
      Unsigned32,
   x25DteLowestOLChannelNumber
      Unsigned32,
   x25DteHighestOLChannelNumber
      Unsigned32 }

x25DteLowestILChannelNumber OBJECT-TYPE
   SYNTAX     Unsigned32 (0..4095)
   ACCESS     read-write
   STATUS     mandatory
   DESCRIPTION
     "This attribute specifies the lowest Lcn number of the One-way 
      Incoming Channel range for this X.25 interface. The value for this 
      attribute must be greater than the numberOfPLcn attribute."
   DEFVAL     { 0 }
::= { x25DteLcnCEntry 1 }

x25DteHighestILChannelNumber OBJECT-TYPE
   SYNTAX     Unsigned32 (0..4095)
   ACCESS     read-write
   STATUS     mandatory
   DESCRIPTION
     "This attribute specifies the highest Lcn number of the One-way 
      Incoming Channel range for this X.25 interface. A value of 0 
      indicates that there are no channels in this range."
   DEFVAL     { 0 }
::= { x25DteLcnCEntry 2 }

x25DteLowestTLChannelNumber OBJECT-TYPE
   SYNTAX     Unsigned32 (0..4095)
   ACCESS     read-write
   STATUS     mandatory
   DESCRIPTION
     "This attribute specifies the lowest Lcn number of the Two-way 
      Channel range for this X.25 interface. The value for this attribute 
      must be greater than the highestILChannelNumber attribute."
   DEFVAL     { 1 }
::= { x25DteLcnCEntry 3 }

x25DteHighestTLChannelNumber OBJECT-TYPE
   SYNTAX     Unsigned32 (0..4095)
   ACCESS     read-write
   STATUS     mandatory
   DESCRIPTION
     "This attribute specifies the highest Lcn number of the Two-way 
      Channel range for this X.25 interface. A value of 0 indicates that 
      there are no channels in this range."
   DEFVAL     { 20 }
::= { x25DteLcnCEntry 4 }

x25DteLowestOLChannelNumber OBJECT-TYPE
   SYNTAX     Unsigned32 (0..4095)
   ACCESS     read-write
   STATUS     mandatory
   DESCRIPTION
     "This attribute specifies the lowest Lcn number of the One-way 
      Outgoing Channel range for this X.25 interface. The value for this 
      attribute must be greater than the highestTLChannelNumber 
      attribute."
   DEFVAL     { 0 }
::= { x25DteLcnCEntry 5 }

x25DteHighestOLChannelNumber OBJECT-TYPE
   SYNTAX     Unsigned32 (0..4095)
   ACCESS     read-write
   STATUS     mandatory
   DESCRIPTION
     "This attribute specifies the highest Lcn number of the One-way 
      Outgoing Channel range for this X.25 interface. A value of 0 
      indicates that there are no channels in this range."
   DEFVAL     { 0 }
::= { x25DteLcnCEntry 6 }

x25DteDcpTable OBJECT-TYPE
   SYNTAX     SEQUENCE OF X25DteDcpEntry
   ACCESS     not-accessible
   STATUS     mandatory
   DESCRIPTION
     "This group contains the provisionable attributes giving the default 
      call parameters used by all the logical channels during call setup. It 
      is possible that different default call parameters will be used for a 
      particular call, based on the Peer component for the given call. The 
      actual call parameters operational for a given call are found in the 
      Lcn component."
::= { x25Dte 23 }

x25DteDcpEntry OBJECT-TYPE
   SYNTAX     X25DteDcpEntry
   ACCESS     not-accessible
   STATUS     mandatory
   DESCRIPTION
     "An entry in the x25DteDcpTable."
   INDEX {
      x25DteIndex }
::= { x25DteDcpTable 1 }

X25DteDcpEntry ::= SEQUENCE {
   x25DteInPacketSize
      Unsigned32,
   x25DteOutPacketSize
      Unsigned32,
   x25DteInWindowSize
      Unsigned32,
   x25DteOutWindowSize
      Unsigned32,
   x25DteAcceptReverseCharging
      INTEGER,
   x25DteProposeReverseCharging
      INTEGER,
   x25DteOutThroughputClassSize
      INTEGER,
   x25DteInThroughputClassSize
      INTEGER,
   x25DteCugIndex
      AsciiString,
   x25DteCugoaIndex
      AsciiString,
   x25DteChargingInformation
      INTEGER,
   x25DteRpoa
      AsciiString,
   x25DteTrnstDlySlctnAInd
      Unsigned32,
   x25DteCallingNetworkFax
      HexString,
   x25DteCalledNetworkFax
      HexString,
   x25DteCallUserData
      HexString }

x25DteInPacketSize OBJECT-TYPE
   SYNTAX     Unsigned32 (16 | 32 | 64 | 128 | 256 | 512 | 1024 | 2048 | 4096)
   ACCESS     read-write
   STATUS     mandatory
   DESCRIPTION
     "This attribute specifies the maximum receive packet size in octets 
      for the X.25 interface."
   DEFVAL     { 128 }
::= { x25DteDcpEntry 1 }

x25DteOutPacketSize OBJECT-TYPE
   SYNTAX     Unsigned32 (16 | 32 | 64 | 128 | 256 | 512 | 1024 | 2048 | 4096)
   ACCESS     read-write
   STATUS     mandatory
   DESCRIPTION
     "This attribute specifies the maximum transmit packet size in octets 
      for the X.25 interface."
   DEFVAL     { 128 }
::= { x25DteDcpEntry 2 }

x25DteInWindowSize OBJECT-TYPE
   SYNTAX     Unsigned32 (1..127)
   ACCESS     read-write
   STATUS     mandatory
   DESCRIPTION
     "This attribute specifies the maximum receive window size for the 
      X.25 interface. A window size greater than 7 is only valid when the 
      packetSequencing attribute is set to modulo128."
   DEFVAL     { 2 }
::= { x25DteDcpEntry 3 }

x25DteOutWindowSize OBJECT-TYPE
   SYNTAX     Unsigned32 (1..127)
   ACCESS     read-write
   STATUS     mandatory
   DESCRIPTION
     "This attribute specifies the maximum transmit window size for the 
      X.25 interface. A window size greater than 7 is only valid when the 
      packetSequencing is set to modulo128."
   DEFVAL     { 2 }
::= { x25DteDcpEntry 4 }

x25DteAcceptReverseCharging OBJECT-TYPE
   SYNTAX     INTEGER  {
                 accept(2),
                 refuse(3),
                 neverAccept(4) }
   ACCESS     read-write
   STATUS     mandatory
   DESCRIPTION
     "This attribute specifies whether local end will accept or refuse 
      charges for a call. A value of neverAccept is only used at the X.25 
      interface level and indicates that this interface will never accept 
      reverse charging (that is no Peer component can override this 
      parameter, allowing reverse charged calls to be accepted)."
   DEFVAL     { refuse }
::= { x25DteDcpEntry 5 }

x25DteProposeReverseCharging OBJECT-TYPE
   SYNTAX     INTEGER  {
                 reverse(2),
                 local(3) }
   ACCESS     read-write
   STATUS     mandatory
   DESCRIPTION
     "This attribute specifies whether local/reverse charging is signalled 
      in the call request packet."
   DEFVAL     { local }
::= { x25DteDcpEntry 6 }

x25DteOutThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-write
   STATUS     mandatory
   DESCRIPTION
     "This attribute specifies the value of the transmit throughput class to 
      be negotiated. A value of notSpecified means the facility is not 
      signalled."
   DEFVAL     { notSpecified }
::= { x25DteDcpEntry 8 }

x25DteInThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-write
   STATUS     mandatory
   DESCRIPTION
     "This attribute specifies the value of the receive throughput class to 
      be negotiated. A value of notSpecified means the facility is not 
      signalled."
   DEFVAL     { notSpecified }
::= { x25DteDcpEntry 9 }

x25DteCugIndex OBJECT-TYPE
   SYNTAX     AsciiString (SIZE (0..4))
   ACCESS     read-write
   STATUS     mandatory
   DESCRIPTION
     "This attribute specifies the index of the Closed User Group facility 
      to signal. The index consists of two or four octets each representing 
      a digit in the range of 0 to 9. A value of null (empty string) at the 
      X.25 interface means no CUG facility is signalled. If a cugIndex is 
      provisioned to be signalled, the cugoaIndex attribute must be null."
   DEFVAL     { ''H }  -- ""
::= { x25DteDcpEntry 10 }

x25DteCugoaIndex OBJECT-TYPE
   SYNTAX     AsciiString (SIZE (0..4))
   ACCESS     read-write
   STATUS     mandatory
   DESCRIPTION
     "This attribute specifies the index of the Close User Group with 
      Outgoing Access facility to signal. The index consists of two or four 
      octets each representing a digit in the range of 0 to 9. A value of 
      null (empty string) at the X.25 interface means no CUGOA facility 
      is signalled. If a cugoaIndex is provisioned to be signalled, the 
      cugIndex attribute must be null."
   DEFVAL     { ''H }  -- ""
::= { x25DteDcpEntry 11 }

x25DteChargingInformation OBJECT-TYPE
   SYNTAX     INTEGER  {
                 notSpecified(2),
                 notRequested(3),
                 requested(4) }
   ACCESS     read-write
   STATUS     mandatory
   DESCRIPTION
     "This attribute specifies whether the charging information facility is 
      to be signalled in a call request packet. A value of notSpecified 
      means the facility is not signalled. A value of notRequested means 
      the facility is signalled but charging information is not requested 
      (that is, the charging info field of the facility is set Off). A value of 
      requested means the facility is signalled to explicitly request 
      charging information."
   DEFVAL     { notSpecified }
::= { x25DteDcpEntry 13 }

x25DteRpoa OBJECT-TYPE
   SYNTAX     AsciiString (SIZE (0..108))
   ACCESS     read-write
   STATUS     mandatory
   DESCRIPTION
     "This attribute specifies the value of the RPOA facility to signal in a 
      call request packet. The value of null (empty string) at the X.25 
      interface means no RPOA facility is signalled."
   DEFVAL     { ''H }  -- ""
::= { x25DteDcpEntry 14 }

x25DteTrnstDlySlctnAInd OBJECT-TYPE
   SYNTAX     Unsigned32 (0..65536)
   ACCESS     read-write
   STATUS     mandatory
   DESCRIPTION
     "This attribute specifies the value of the Transit Delay Selection and 
      Indication facility to signal in a call request packet. A value of 
      65536 at the X.25 interface level means no TDSAI facility is 
      signalled."
   DEFVAL     { 65536 }
::= { x25DteDcpEntry 15 }

x25DteCallingNetworkFax OBJECT-TYPE
   SYNTAX     HexString (SIZE (0..108))
   ACCESS     read-write
   STATUS     mandatory
   DESCRIPTION
     "This attribute specifies the Calling Network facilities to be signalled 
      in a call request packet. A value of null (empty string) at the X.25 
      interface means no facilities are signalled."
   DEFVAL     { ''H }  -- ""
::= { x25DteDcpEntry 24 }

x25DteCalledNetworkFax OBJECT-TYPE
   SYNTAX     HexString (SIZE (0..108))
   ACCESS     read-write
   STATUS     mandatory
   DESCRIPTION
     "This attribute specifies the called network facilities to be signalled 
      in a call request packet. A value of null (empty string) at the X.25 
      interface means no facilities are signalled."
   DEFVAL     { ''H }  -- ""
::= { x25DteDcpEntry 25 }

x25DteCallUserData OBJECT-TYPE
   SYNTAX     HexString (SIZE (0..128))
   ACCESS     read-only
   STATUS     mandatory
   DESCRIPTION
     "This attribute specifies the user data to be signalled in the call 
      request packet. A value of null (empty string) means no user data is 
      signalled."
   DEFVAL     { ''H }  -- ""
::= { x25DteDcpEntry 26 }

x25DteIfEntryTable OBJECT-TYPE
   SYNTAX     SEQUENCE OF X25DteIfEntryEntry
   ACCESS     not-accessible
   STATUS     mandatory
   DESCRIPTION
     "This group contains the provisionable attributes for the ifEntry."
::= { x25Dte 24 }

x25DteIfEntryEntry OBJECT-TYPE
   SYNTAX     X25DteIfEntryEntry
   ACCESS     not-accessible
   STATUS     mandatory
   DESCRIPTION
     "An entry in the x25DteIfEntryTable."
   INDEX {
      x25DteIndex }
::= { x25DteIfEntryTable 1 }

X25DteIfEntryEntry ::= SEQUENCE {
   x25DteIfAdminStatus
      INTEGER,
   x25DteIfIndex
      InterfaceIndex }

x25DteIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { x25DteIfEntryEntry 1 }

x25DteIfIndex OBJECT-TYPE
   SYNTAX     InterfaceIndex (1..65535)
   ACCESS     read-only
   STATUS     mandatory
   DESCRIPTION
     "This is the index for the IfEntry. Its value is automatically initialized 
      during the provisioning process."
::= { x25DteIfEntryEntry 2 }

x25DteStateTable OBJECT-TYPE
   SYNTAX     SEQUENCE OF X25DteStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { x25Dte 25 }

x25DteStateEntry OBJECT-TYPE
   SYNTAX     X25DteStateEntry
   ACCESS     not-accessible
   STATUS     mandatory
   DESCRIPTION
     "An entry in the x25DteStateTable."
   INDEX {
      x25DteIndex }
::= { x25DteStateTable 1 }

X25DteStateEntry ::= SEQUENCE {
   x25DteAdminState
      INTEGER,
   x25DteOperationalState
      INTEGER,
   x25DteUsageState
      INTEGER }

x25DteAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { x25DteStateEntry 1 }

x25DteOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { x25DteStateEntry 2 }

x25DteUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { x25DteStateEntry 3 }

x25DteOperStatusTable OBJECT-TYPE
   SYNTAX     SEQUENCE OF X25DteOperStatusEntry
   ACCESS     not-accessible
   STATUS     mandatory
   DESCRIPTION
     "This group includes the Operational Status attribute. This attribute 
      defines the current operational state of this component."
::= { x25Dte 26 }

x25DteOperStatusEntry OBJECT-TYPE
   SYNTAX     X25DteOperStatusEntry
   ACCESS     not-accessible
   STATUS     mandatory
   DESCRIPTION
     "An entry in the x25DteOperStatusTable."
   INDEX {
      x25DteIndex }
::= { x25DteOperStatusTable 1 }

X25DteOperStatusEntry ::= SEQUENCE {
   x25DteSnmpOperStatus
      INTEGER }

x25DteSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { x25DteOperStatusEntry 1 }

x25DteOpTable OBJECT-TYPE
   SYNTAX     SEQUENCE OF X25DteOpEntry
   ACCESS     not-accessible
   STATUS     mandatory
   DESCRIPTION
     "This group contains the operational status of the X.25 interface."
::= { x25Dte 27 }

x25DteOpEntry OBJECT-TYPE
   SYNTAX     X25DteOpEntry
   ACCESS     not-accessible
   STATUS     mandatory
   DESCRIPTION
     "An entry in the x25DteOpTable."
   INDEX {
      x25DteIndex }
::= { x25DteOpTable 1 }

X25DteOpEntry ::= SEQUENCE {
   x25DteInterfaceState
      INTEGER }

x25DteInterfaceState OBJECT-TYPE
   SYNTAX     INTEGER  {
                 notReady(0),
                 localRestarting(1),
                 remoteRestarting(2),
                 ready(3) }
   ACCESS     read-only
   STATUS     mandatory
   DESCRIPTION
     "This attribute specifies the state of the interface. The notReady 
      state, is the initial state of the service, when it is being initialized. 
      The localRestarting state is entered when a Restart packet is sent to 
      the link and the interface is waiting for a response. The 
      remoteRestarting state is entered when a Restart packet is received 
      from the link, and is being processed. In ready state, the service is 
      operational and ready to provide service."
::= { x25DteOpEntry 1 }

x25DteStatsTable OBJECT-TYPE
   SYNTAX     SEQUENCE OF X25DteStatsEntry
   ACCESS     not-accessible
   STATUS     mandatory
   DESCRIPTION
     "This component contains the statistics for the X.25 interface."
::= { x25Dte 28 }

x25DteStatsEntry OBJECT-TYPE
   SYNTAX     X25DteStatsEntry
   ACCESS     not-accessible
   STATUS     mandatory
   DESCRIPTION
     "An entry in the x25DteStatsTable."
   INDEX {
      x25DteIndex }
::= { x25DteStatsTable 1 }

X25DteStatsEntry ::= SEQUENCE {
   x25DteInCalls
      Counter32,
   x25DteInCallRefusals
      Counter32,
   x25DteInPrvdrInitiatedClrs
      Counter32,
   x25DteInRmtInitiatedRsts
      Counter32,
   x25DteInPrvdrInitiatedRsts
      Counter32,
   x25DteInRestarts
      Counter32,
   x25DteInDataPackets
      Counter32,
   x25DteInPktsAcusdOfPrtclErr
      Counter32,
   x25DteInInterruptPackets
      Counter32,
   x25DteOutCallAttempts
      Counter32,
   x25DteOutCallFailures
      Counter32,
   x25DteOutInterruptPackets
      Counter32,
   x25DteOutDataPackets
      Counter32,
   x25DteOutActiveChannels
      Counter32,
   x25DteInActiveChannels
      Counter32,
   x25DteTwowayActiveChannels
      Counter32,
   x25DteT20RestartTimeouts
      Counter32,
   x25DteT21CallTimeouts
      Counter32,
   x25DteT22ResetTimeouts
      Counter32,
   x25DteT23ClearTimeouts
      Counter32 }

x25DteInCalls OBJECT-TYPE
   SYNTAX     Counter32 
   ACCESS     read-only
   STATUS     mandatory
   DESCRIPTION
     "This attribute counts the number of call packets received from link."
::= { x25DteStatsEntry 1 }

x25DteInCallRefusals OBJECT-TYPE
   SYNTAX     Counter32 
   ACCESS     read-only
   STATUS     mandatory
   DESCRIPTION
     "This attribute counts the number of calls received from the link 
      which have been cleared. This includes calls cleared by the X.25 
      interface and calls cleared by the higher level."
::= { x25DteStatsEntry 2 }

x25DteInPrvdrInitiatedClrs OBJECT-TYPE
   SYNTAX     Counter32 
   ACCESS     read-only
   STATUS     mandatory
   DESCRIPTION
     "This attribute counts the number of clear packets received from the 
      link with a cause code other than DTE initiated."
::= { x25DteStatsEntry 3 }

x25DteInRmtInitiatedRsts OBJECT-TYPE
   SYNTAX     Counter32 
   ACCESS     read-only
   STATUS     mandatory
   DESCRIPTION
     "This attribute counts the number of reset packets received from the 
      link with the cause code DTE initiated."
::= { x25DteStatsEntry 4 }

x25DteInPrvdrInitiatedRsts OBJECT-TYPE
   SYNTAX     Counter32 
   ACCESS     read-only
   STATUS     mandatory
   DESCRIPTION
     "This attribute counts the number of reset packets received from the 
      link with the cause code other than DTE initiated."
::= { x25DteStatsEntry 5 }

x25DteInRestarts OBJECT-TYPE
   SYNTAX     Counter32 
   ACCESS     read-only
   STATUS     mandatory
   DESCRIPTION
     "This attribute counts the number of restart packets received from the 
      link while the service is in ready state."
::= { x25DteStatsEntry 6 }

x25DteInDataPackets OBJECT-TYPE
   SYNTAX     Counter32 
   ACCESS     read-only
   STATUS     mandatory
   DESCRIPTION
     "This attribute counts the number of data packets received from link."
::= { x25DteStatsEntry 7 }

x25DteInPktsAcusdOfPrtclErr OBJECT-TYPE
   SYNTAX     Counter32 
   ACCESS     read-only
   STATUS     mandatory
   DESCRIPTION
     "This attribute counts the number of clear, reset, restart and 
      diagnostic packets received from link containing a procedure error 
      cause code."
::= { x25DteStatsEntry 8 }

x25DteInInterruptPackets OBJECT-TYPE
   SYNTAX     Counter32 
   ACCESS     read-only
   STATUS     mandatory
   DESCRIPTION
     "This attributes counts the number of interrupt packets received from 
      link."
::= { x25DteStatsEntry 9 }

x25DteOutCallAttempts OBJECT-TYPE
   SYNTAX     Counter32 
   ACCESS     read-only
   STATUS     mandatory
   DESCRIPTION
     "This attribute counts the number of call packets sent from this 
      interface."
::= { x25DteStatsEntry 10 }

x25DteOutCallFailures OBJECT-TYPE
   SYNTAX     Counter32 
   ACCESS     read-only
   STATUS     mandatory
   DESCRIPTION
     "This attribute counts the number of call attempts from this interface 
      that failed. This includes calls that were cleared because of 
      restrictive fast select."
::= { x25DteStatsEntry 11 }

x25DteOutInterruptPackets OBJECT-TYPE
   SYNTAX     Counter32 
   ACCESS     read-only
   STATUS     mandatory
   DESCRIPTION
     "This attribute counts the number of interrupt packets sent to the 
      link."
::= { x25DteStatsEntry 12 }

x25DteOutDataPackets OBJECT-TYPE
   SYNTAX     Counter32 
   ACCESS     read-only
   STATUS     mandatory
   DESCRIPTION
     "This attribute counts the number of data packets sent to the link."
::= { x25DteStatsEntry 13 }

x25DteOutActiveChannels OBJECT-TYPE
   SYNTAX     Counter32 
   ACCESS     read-only
   STATUS     mandatory
   DESCRIPTION
     "This attribute indicates the number of One-way Outgoing Channels 
      that are currently in use. This counter includes the call requests that 
      have not been accepted."
::= { x25DteStatsEntry 14 }

x25DteInActiveChannels OBJECT-TYPE
   SYNTAX     Counter32 
   ACCESS     read-only
   STATUS     mandatory
   DESCRIPTION
     "This attribute indicates number of One-way Incoming Channels that 
      are currently active."
::= { x25DteStatsEntry 15 }

x25DteTwowayActiveChannels OBJECT-TYPE
   SYNTAX     Counter32 
   ACCESS     read-only
   STATUS     mandatory
   DESCRIPTION
     "This attribute indicates the number of Two-way Channels that are in 
      use. This includes call requests sent but not yet accepted."
::= { x25DteStatsEntry 16 }

x25DteT20RestartTimeouts OBJECT-TYPE
   SYNTAX     Counter32 
   ACCESS     read-only
   STATUS     mandatory
   DESCRIPTION
     "This attribute counts the number of times the T20 restart timer has 
      expired."
::= { x25DteStatsEntry 17 }

x25DteT21CallTimeouts OBJECT-TYPE
   SYNTAX     Counter32 
   ACCESS     read-only
   STATUS     mandatory
   DESCRIPTION
     "This attribute counts the number of times the T21 call timer has 
      expired."
::= { x25DteStatsEntry 18 }

x25DteT22ResetTimeouts OBJECT-TYPE
   SYNTAX     Counter32 
   ACCESS     read-only
   STATUS     mandatory
   DESCRIPTION
     "This attribute counts the number of times the T22 reset timer has 
      expired."
::= { x25DteStatsEntry 19 }

x25DteT23ClearTimeouts OBJECT-TYPE
   SYNTAX     Counter32 
   ACCESS     read-only
   STATUS     mandatory
   DESCRIPTION
     "This attribute counts the number of times the T23 clear timer has 
      expired."
::= { x25DteStatsEntry 20 }


-- 
-- X25Dte/n Peer/n
-- 
-- This optional component defines the parameters to be used in 
-- setting up a switched circuit call to a particular remote destination. 
-- Multiple instances of this component can co-exist under the same 
-- X25Dte component. 
-- An instance of this component is needed for each remote host with 
-- which the X.25 Dte is to communicate (that is, each peer to which it 
-- may establish calls or from which it is to accept calls). 

x25DtePeer OBJECT IDENTIFIER ::= { x25Dte 2 }



x25DtePeerRowStatusTable OBJECT-TYPE
   SYNTAX     SEQUENCE OF X25DtePeerRowStatusEntry
   ACCESS     not-accessible
   STATUS     mandatory
   DESCRIPTION
     "This entry controls the addition and deletion of 
      x25DtePeer components."
::= { x25DtePeer 1 }

x25DtePeerRowStatusEntry OBJECT-TYPE
   SYNTAX     X25DtePeerRowStatusEntry
   ACCESS     not-accessible
   STATUS     mandatory
   DESCRIPTION
     "A single entry in the table represents a single 
      x25DtePeer component."
   INDEX {
      x25DteIndex,
      x25DtePeerIndex }
::= { x25DtePeerRowStatusTable 1 }

X25DtePeerRowStatusEntry ::= SEQUENCE {
   x25DtePeerRowStatus
      RowStatus,
   x25DtePeerComponentName
      DisplayString,
   x25DtePeerStorageType
      StorageType,
   x25DtePeerIndex
      Integer32 }

x25DtePeerRowStatus OBJECT-TYPE
   SYNTAX     RowStatus 
   ACCESS     read-write
   STATUS     mandatory
   DESCRIPTION
     "This variable is used as the basis for SNMP naming of
      x25DtePeer components.
      These components can be added and deleted."
::= { x25DtePeerRowStatusEntry 1 }

x25DtePeerComponentName OBJECT-TYPE
   SYNTAX     DisplayString 
   ACCESS     read-only
   STATUS     mandatory
   DESCRIPTION
     "This variable provides the component's string name for
      use with the ASCII Console Interface"
::= { x25DtePeerRowStatusEntry 2 }

x25DtePeerStorageType OBJECT-TYPE
   SYNTAX     StorageType 
   ACCESS     read-only
   STATUS     mandatory
   DESCRIPTION
     "This variable represents the storage type value for the
      x25DtePeer tables."
::= { x25DtePeerRowStatusEntry 4 }

x25DtePeerIndex OBJECT-TYPE
   SYNTAX     Integer32 (1..4095)
   ACCESS     not-accessible
   STATUS     mandatory
   DESCRIPTION
     "This variable represents the index for the x25DtePeer tables."
::= { x25DtePeerRowStatusEntry 10 }

x25DtePeerIfTable OBJECT-TYPE
   SYNTAX     SEQUENCE OF X25DtePeerIfEntry
   ACCESS     not-accessible
   STATUS     mandatory
   DESCRIPTION
     "This group provides the administrative set of parameters for the 
      Peer interface."
::= { x25DtePeer 10 }

x25DtePeerIfEntry OBJECT-TYPE
   SYNTAX     X25DtePeerIfEntry
   ACCESS     not-accessible
   STATUS     mandatory
   DESCRIPTION
     "An entry in the x25DtePeerIfTable."
   INDEX {
      x25DteIndex,
      x25DtePeerIndex }
::= { x25DtePeerIfTable 1 }

X25DtePeerIfEntry ::= SEQUENCE {
   x25DtePeerEncAddressType
      INTEGER,
   x25DtePeerEncAddress
      AsciiString,
   x25DtePeerX25Address
      DigitString,
   x25DtePeerLinkToRemoteGroup
      Link }

x25DtePeerEncAddressType OBJECT-TYPE
   SYNTAX     INTEGER  {
                 ip(204) }
   ACCESS     read-write
   STATUS     mandatory
   DESCRIPTION
     "This attribute specifies the encapsulation type for the address of the 
      remote host with which this Peer component allows 
      communication."
   DEFVAL     { ip }
::= { x25DtePeerIfEntry 1 }

x25DtePeerEncAddress OBJECT-TYPE
   SYNTAX     AsciiString (SIZE (0..128))
   ACCESS     read-write
   STATUS     mandatory
   DESCRIPTION
     "This attribute specifies the encapsulation address of the remote host 
      with which this Peer component allows communication. This 
      address must correspond with the encapsulation address type. Thus 
      in the case of IP, it will contain a IP address."
::= { x25DtePeerIfEntry 2 }

x25DtePeerX25Address OBJECT-TYPE
   SYNTAX     DigitString (SIZE (1..15))
   ACCESS     read-write
   STATUS     mandatory
   DESCRIPTION
     "This attribute specifies the X.25 address that identifies the remote 
      host with which this Peer component allows communication. The 
      remote X.25 interface could be subdivided through the use of 
      RemoteGroup components; in which case this x25Address is the 
      X.25 address of the destination's RemoteGroup (not to be confused 
      with the RemoteGroup indicated by the linkToRemoteGroup 
      attribute of THIS Peer component)."
::= { x25DtePeerIfEntry 3 }

x25DtePeerLinkToRemoteGroup OBJECT-TYPE
   SYNTAX     Link 
   ACCESS     read-write
   STATUS     mandatory
   DESCRIPTION
     "This is a link to a RemoteGroup component. The RemoteGroup 
      components logically divide up the X.25 Interface such that a 
      number of Protocol Ports (and consequently a number of Virtual 
      Routers) may share the same X.25 Interface into a Wide Area 
      Network. In particular, the remote host identified by this Peer 
      component is designated as belonging to the RemoteGroup linked 
      by this attribute. The set of all Peer components and PermLcn 
      components which link to a given RemoteGroup determine the 
      subset of remote hosts which are accessible to a particular Protocol 
      Port (and ultimately a Virtual Router)."
::= { x25DtePeerIfEntry 4 }

x25DtePeerCpTable OBJECT-TYPE
   SYNTAX     SEQUENCE OF X25DtePeerCpEntry
   ACCESS     not-accessible
   STATUS     mandatory
   DESCRIPTION
     "This group contains the call parameters used to establish a call to/
      from the remote host identified by this Peer component"
::= { x25DtePeer 12 }

x25DtePeerCpEntry OBJECT-TYPE
   SYNTAX     X25DtePeerCpEntry
   ACCESS     not-accessible
   STATUS     mandatory
   DESCRIPTION
     "An entry in the x25DtePeerCpTable."
   INDEX {
      x25DteIndex,
      x25DtePeerIndex }
::= { x25DtePeerCpTable 1 }

X25DtePeerCpEntry ::= SEQUENCE {
   x25DtePeerInPacketSize
      Unsigned32,
   x25DtePeerOutPacketSize
      Unsigned32,
   x25DtePeerInWindowSize
      Unsigned32,
   x25DtePeerOutWindowSize
      Unsigned32,
   x25DtePeerAcceptReverseCharging
      INTEGER,
   x25DtePeerProposeReverseCharging
      INTEGER,
   x25DtePeerOutThroughputClassSize
      INTEGER,
   x25DtePeerInThroughputClassSize
      INTEGER,
   x25DtePeerCugIndex
      AsciiString,
   x25DtePeerCugoaIndex
      AsciiString,
   x25DtePeerNetworkUserIdentifier
      HexString,
   x25DtePeerChargingInformation
      INTEGER,
   x25DtePeerRpoa
      AsciiString,
   x25DtePeerTrnstDlySlctnAInd
      Unsigned32,
   x25DtePeerCallingNetworkFax
      HexString,
   x25DtePeerCalledNetworkFax
      HexString,
   x25DtePeerCallUserData
      HexString }

x25DtePeerInPacketSize OBJECT-TYPE
   SYNTAX     Unsigned32 (0 | 16 | 32 | 64 | 128 | 256 | 512 | 1024 | 2048 | 4096)
   ACCESS     read-write
   STATUS     mandatory
   DESCRIPTION
     "This attribute specifies the default maximum receive packet size in 
      octets. A setting of 0 indicates the inPacketSize setting for the X.25 
      interface (in X25Dte component) is used during call setup to the 
      remote host identified by this Peer component."
   DEFVAL     { 128 }
::= { x25DtePeerCpEntry 1 }

x25DtePeerOutPacketSize OBJECT-TYPE
   SYNTAX     Unsigned32 (0 | 16 | 32 | 64 | 128 | 256 | 512 | 1024 | 2048 | 4096)
   ACCESS     read-write
   STATUS     mandatory
   DESCRIPTION
     "This attribute specifies the default maximum transmit packet size in 
      octets. A setting of 0 indicates the outPacketSize setting for the 
      X.25 interface (in the X25Dte component) is used during call setup 
      to the remote host identified by this Peer component."
   DEFVAL     { 128 }
::= { x25DtePeerCpEntry 2 }

x25DtePeerInWindowSize OBJECT-TYPE
   SYNTAX     Unsigned32 (0..127)
   ACCESS     read-write
   STATUS     mandatory
   DESCRIPTION
     "This attribute specifies the default receive window size. A window 
      size of 0 indicates the inWindowSize setting for the X.25 interface 
      (in the X25Dte component) is used during call setup to the remote 
      host identified by this Peer component. A window size greater than 
      7 is only valid when the packetSequencing attribute of the X25Dte 
      component is set to modulo128."
   DEFVAL     { 2 }
::= { x25DtePeerCpEntry 3 }

x25DtePeerOutWindowSize OBJECT-TYPE
   SYNTAX     Unsigned32 (0..127)
   ACCESS     read-write
   STATUS     mandatory
   DESCRIPTION
     "This attribute specifies the default transmit window size. A window 
      size of 0 indicates the outWindowSize setting for the X.25 interface 
      is used during call setup to the Peer identified by this component. A 
      window size greater than 7 is only valid when the packetSequencing 
      attribute of the X25Dte component is set to modulo128."
   DEFVAL     { 2 }
::= { x25DtePeerCpEntry 4 }

x25DtePeerAcceptReverseCharging OBJECT-TYPE
   SYNTAX     INTEGER  {
                 default(1),
                 accept(2),
                 refuse(3) }
   ACCESS     read-write
   STATUS     mandatory
   DESCRIPTION
     "This attribute specifies whether the local end will accept or refuse 
      charges for a call from the remote host identified by this Peer 
      component. A value of default indicates the use of the 
      acceptReverseCharging value from the X25Dte component. If the 
      value at the X25Dte level is neverAccept, a value of accept in this 
      Peer component will be ignored because no reverse charge calls are 
      to be accepted by this X.25 Dte."
   DEFVAL     { refuse }
::= { x25DtePeerCpEntry 5 }

x25DtePeerProposeReverseCharging OBJECT-TYPE
   SYNTAX     INTEGER  {
                 default(1),
                 reverse(2),
                 local(3) }
   ACCESS     read-write
   STATUS     mandatory
   DESCRIPTION
     "This attribute specifies whether local/reverse charging is signalled 
      in a call request packet. A value of default indicates the use of the 
      value from the proposeReverseCharging attribute of the X25Dte 
      component."
   DEFVAL     { local }
::= { x25DtePeerCpEntry 6 }

x25DtePeerOutThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17),
                 default(18) }
   ACCESS     read-write
   STATUS     mandatory
   DESCRIPTION
     "This attribute specifies the value of the transmit throughput class to 
      be negotiated. A value of default indicates the use of the value from 
      the outThroughputClassSize attribute of the X25Dte component. A 
      value of notSpecified means the facility is not signalled."
   DEFVAL     { notSpecified }
::= { x25DtePeerCpEntry 8 }

x25DtePeerInThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17),
                 default(18) }
   ACCESS     read-write
   STATUS     mandatory
   DESCRIPTION
     "This attribute specifies the value of the receive throughput class to 
      be negotiated. A value of default indicates the use of the value from 
      the inThroughputClassSize attribute of the X25Dte component. A 
      value of notSpecified means the facility is not signalled."
   DEFVAL     { notSpecified }
::= { x25DtePeerCpEntry 9 }

x25DtePeerCugIndex OBJECT-TYPE
   SYNTAX     AsciiString (SIZE (0..4))
   ACCESS     read-write
   STATUS     mandatory
   DESCRIPTION
     "This attribute specifies the index of the Closed User Group facility 
      to signal. A value of 'DEF' indicates the use of the value from the 
      cugIndex attribute of the X25Dte component. A value of null 
      (empty string) indicates no CUG facility is to be signalled. If a 
      cugIndex is provisioned to be signalled, the cugoaIndex attribute 
      must be null."
   DEFVAL     { ''H }  -- ""
::= { x25DtePeerCpEntry 10 }

x25DtePeerCugoaIndex OBJECT-TYPE
   SYNTAX     AsciiString (SIZE (0..4))
   ACCESS     read-write
   STATUS     mandatory
   DESCRIPTION
     "This attribute specifies the index of the Closed User Group with 
      Outgoing Access facility to signal. A value of 'DEF' indicates the 
      use of the value from the cugoaIndex attribute of the X25Dte 
      component. A value of null (empty string) indicates no CUGOA 
      facility is to be signalled. If a cugoaIndex is provisioned to be 
      signalled, the cugIndex attribute must be null."
   DEFVAL     { ''H }  -- ""
::= { x25DtePeerCpEntry 11 }

x25DtePeerNetworkUserIdentifier OBJECT-TYPE
   SYNTAX     HexString (SIZE (0..108))
   ACCESS     read-write
   STATUS     mandatory
   DESCRIPTION
     "This attribute specifies the Network User Identifier facility to signal. 
      A value of null (empty string) indicates no NUI facility is to be 
      signalled."
   DEFVAL     { ''H }  -- ""
::= { x25DtePeerCpEntry 12 }

x25DtePeerChargingInformation OBJECT-TYPE
   SYNTAX     INTEGER  {
                 default(1),
                 notSpecified(2),
                 notRequested(3),
                 requested(4) }
   ACCESS     read-write
   STATUS     mandatory
   DESCRIPTION
     "This attribute specifies whether the charging information facility is 
      signalled in the call request packet. A value of default indicates the 
      use of the value from the chargingInformation attribute of the 
      X25Dte component. A value of notSpecified means the facility is 
      not signalled. A value of notRequested means the facility is 
      signalled but charging information is not requested (that is, the 
      charging info field of the facility is set Off). A value of requested 
      means the facility is signalled to explicitly request charging 
      information."
   DEFVAL     { notSpecified }
::= { x25DtePeerCpEntry 13 }

x25DtePeerRpoa OBJECT-TYPE
   SYNTAX     AsciiString (SIZE (0..108))
   ACCESS     read-write
   STATUS     mandatory
   DESCRIPTION
     "This attribute specifies the RPOA facility to signal in a call request 
      packet. A value of 'DEF' indicates the use of the value from the 
      rpoa attribute of the X25Dte component. A value of null (empty 
      string) indicates no RPOA facility is to be signalled."
   DEFVAL     { ''H }  -- ""
::= { x25DtePeerCpEntry 14 }

x25DtePeerTrnstDlySlctnAInd OBJECT-TYPE
   SYNTAX     Unsigned32 (0..65537)
   ACCESS     read-write
   STATUS     mandatory
   DESCRIPTION
     "This attribute specifies the value of the Transit Delay Selection and 
      Indication facility to signal in a call request packet. A value of 
      65536 indicates no facility is signalled. A value of 65537 indicates 
      the use of the value from the trnstDlySlctnAInd attribute of the 
      X25Dte component."
   DEFVAL     { 65536 }
::= { x25DtePeerCpEntry 15 }

x25DtePeerCallingNetworkFax OBJECT-TYPE
   SYNTAX     HexString (SIZE (0..108))
   ACCESS     read-write
   STATUS     mandatory
   DESCRIPTION
     "This attribute specifies the Calling Network facilities to signal in a 
      call request packet. The facilities are encoded here exactly as they 
      are encoded in the call packet. These facilities do not include the 
      marker facility code. A value of null (empty string) indicates the 
      callingNetworkFax from the X25Dte are to be signalled. If that 
      value is also null, no Calling Network Facilities are signalled."
   DEFVAL     { ''H }  -- ""
::= { x25DtePeerCpEntry 24 }

x25DtePeerCalledNetworkFax OBJECT-TYPE
   SYNTAX     HexString (SIZE (0..108))
   ACCESS     read-write
   STATUS     mandatory
   DESCRIPTION
     "This attribute specifies the Called Network facilities to signal in a 
      call request packet. The facilities are encoded here exactly as they 
      are encoded in the call packet. These facilities do not include the 
      marker facility code. A value of null (empty string) indicates the 
      calledNetworkFax from the X25Dte are to be signalled. If that value 
      is also null, no Called Network Facilities are signalled."
   DEFVAL     { ''H }  -- ""
::= { x25DtePeerCpEntry 25 }

x25DtePeerCallUserData OBJECT-TYPE
   SYNTAX     HexString (SIZE (0..128))
   ACCESS     read-only
   STATUS     mandatory
   DESCRIPTION
     "This attribute specifies the user data to signal in a call request 
      packet. A value of null (empty string) indicates that the 
      callUserData from the X25Dte is to be signalled. If callUserData of 
      the X25Dte component is also null and protocolEncType of this 
      Peer has the value IP, H.CC will be signalled as the call user data of 
      a call request packet. Thus for IP encapsulation according to 
      RFC1356, both the callUserData from the Peer and X25Dte 
      components must be null and the protocolEncType set to IP."
   DEFVAL     { ''H }  -- ""
::= { x25DtePeerCpEntry 26 }

x25DtePeerPEncTable OBJECT-TYPE
   SYNTAX     SEQUENCE OF X25DtePeerPEncEntry
   ACCESS     not-accessible
   STATUS     mandatory
   DESCRIPTION
     "Each instance of this replicated attribute describes an encapsulation 
      method permitted for encapsulating the protocol data units (PDUs) 
      of an upper layer protocol when communicating with the remote 
      host identified by this Peer component. The index of a given 
      replicated instance of this attribute represents the relative priority of 
      the encapsulation method specified by the given attribute instance. 
      An attribute with index '1' has the highest priority, so the 
      encapsulation method described by it will be the first one attempted 
      when signalling a call to the link. If the protocolEncType is set to 
      IP to encapsulate IP traffic according to RFC1356, the 
      callUserData for this Peer component and the X25Dte component 
      must both be null, so that H.CC will be signalled as the call user 
      data of the call request. This indicates that the protocol 
      encapsulation type of IP is to be used for the channel.
      A call received from the link will be accepted as long as the 
      encapsulation method indicated in the call user data of the incoming 
      call packet is included in one of these replicated attributes. (This 
      presupposes that the incoming call has been directed to the 
      RemoteGroup to which this Peer is linked through the 
      linkToRemoteGroup attribute.)"
::= { x25DtePeer 208 }

x25DtePeerPEncEntry OBJECT-TYPE
   SYNTAX     X25DtePeerPEncEntry
   ACCESS     not-accessible
   STATUS     mandatory
   DESCRIPTION
     "An entry in the x25DtePeerPEncTable."
   INDEX {
      x25DteIndex,
      x25DtePeerIndex,
      x25DtePeerPEncIndex }
::= { x25DtePeerPEncTable 1 }

X25DtePeerPEncEntry ::= SEQUENCE {
   x25DtePeerPEncIndex
      Integer32,
   x25DtePeerPEncValue
      INTEGER,
   x25DtePeerPEncRowStatus
      RowStatus }

x25DtePeerPEncIndex OBJECT-TYPE
   SYNTAX     Integer32 (1..1)
   ACCESS     not-accessible
   STATUS     mandatory
   DESCRIPTION
     "This variable represents the index for the x25DtePeerPEncTable."
::= { x25DtePeerPEncEntry 1 }

x25DtePeerPEncValue OBJECT-TYPE
   SYNTAX     INTEGER  {
                 ip(204) }
   ACCESS     read-write
   STATUS     mandatory
   DESCRIPTION
     "This variable represents an individual value for the
      x25DtePeerPEncTable."
::= { x25DtePeerPEncEntry 2 }

x25DtePeerPEncRowStatus OBJECT-TYPE
   SYNTAX     RowStatus 
   ACCESS     write-only
   STATUS     mandatory
   DESCRIPTION
     "This variable is used to control the addition and deletion 
      of individual values of the x25DtePeerPEncTable."
::= { x25DtePeerPEncEntry 3 }

x25DtePeerLcnTable OBJECT-TYPE
   SYNTAX     SEQUENCE OF X25DtePeerLcnEntry
   ACCESS     not-accessible
   STATUS     mandatory
   DESCRIPTION
     "This attribute specifies the local logical channel numbers (Lcn) in 
      use for the X.25 calls to the remote host identified by this Peer 
      component."
::= { x25DtePeer 209 }

x25DtePeerLcnEntry OBJECT-TYPE
   SYNTAX     X25DtePeerLcnEntry
   ACCESS     not-accessible
   STATUS     mandatory
   DESCRIPTION
     "An entry in the x25DtePeerLcnTable."
   INDEX {
      x25DteIndex,
      x25DtePeerIndex,
      x25DtePeerLcnValue }
::= { x25DtePeerLcnTable 1 }

X25DtePeerLcnEntry ::= SEQUENCE {
   x25DtePeerLcnValue
      Integer32 }

x25DtePeerLcnValue OBJECT-TYPE
   SYNTAX     Integer32 (1..4095)
   ACCESS     read-only
   STATUS     mandatory
   DESCRIPTION
     "This variable represents both the value and the index for the
      x25DtePeerLcnTable."
::= { x25DtePeerLcnEntry 1 }


-- 
-- X25Dte/n PermLcn/n
-- 
-- This component defines the parameters required for the Permanent 
-- logical channels of an X.25 interface.

x25DtePLcn OBJECT IDENTIFIER ::= { x25Dte 3 }



x25DtePLcnRowStatusTable OBJECT-TYPE
   SYNTAX     SEQUENCE OF X25DtePLcnRowStatusEntry
   ACCESS     not-accessible
   STATUS     mandatory
   DESCRIPTION
     "This entry controls the addition and deletion of 
      x25DtePLcn components."
::= { x25DtePLcn 1 }

x25DtePLcnRowStatusEntry OBJECT-TYPE
   SYNTAX     X25DtePLcnRowStatusEntry
   ACCESS     not-accessible
   STATUS     mandatory
   DESCRIPTION
     "A single entry in the table represents a single 
      x25DtePLcn component."
   INDEX {
      x25DteIndex,
      x25DtePLcnIndex }
::= { x25DtePLcnRowStatusTable 1 }

X25DtePLcnRowStatusEntry ::= SEQUENCE {
   x25DtePLcnRowStatus
      RowStatus,
   x25DtePLcnComponentName
      DisplayString,
   x25DtePLcnStorageType
      StorageType,
   x25DtePLcnIndex
      Integer32 }

x25DtePLcnRowStatus OBJECT-TYPE
   SYNTAX     RowStatus 
   ACCESS     read-write
   STATUS     mandatory
   DESCRIPTION
     "This variable is used as the basis for SNMP naming of
      x25DtePLcn components.
      These components can be added and deleted."
::= { x25DtePLcnRowStatusEntry 1 }

x25DtePLcnComponentName OBJECT-TYPE
   SYNTAX     DisplayString 
   ACCESS     read-only
   STATUS     mandatory
   DESCRIPTION
     "This variable provides the component's string name for
      use with the ASCII Console Interface"
::= { x25DtePLcnRowStatusEntry 2 }

x25DtePLcnStorageType OBJECT-TYPE
   SYNTAX     StorageType 
   ACCESS     read-only
   STATUS     mandatory
   DESCRIPTION
     "This variable represents the storage type value for the
      x25DtePLcn tables."
::= { x25DtePLcnRowStatusEntry 4 }

x25DtePLcnIndex OBJECT-TYPE
   SYNTAX     Integer32 (1..4095)
   ACCESS     not-accessible
   STATUS     mandatory
   DESCRIPTION
     "This variable represents the index for the x25DtePLcn tables."
::= { x25DtePLcnRowStatusEntry 10 }

x25DtePLcnProvTable OBJECT-TYPE
   SYNTAX     SEQUENCE OF X25DtePLcnProvEntry
   ACCESS     not-accessible
   STATUS     mandatory
   DESCRIPTION
     "This group contains the provisionable parameters for the permanent 
      logical channels (PLcns) on the X.25 interface (corresponding to 
      Permanent Virtual Circuits (PVCs) provisioned on the Wide Area 
      Network)."
::= { x25DtePLcn 10 }

x25DtePLcnProvEntry OBJECT-TYPE
   SYNTAX     X25DtePLcnProvEntry
   ACCESS     not-accessible
   STATUS     mandatory
   DESCRIPTION
     "An entry in the x25DtePLcnProvTable."
   INDEX {
      x25DteIndex,
      x25DtePLcnIndex }
::= { x25DtePLcnProvTable 1 }

X25DtePLcnProvEntry ::= SEQUENCE {
   x25DtePLcnEncAddressType
      INTEGER,
   x25DtePLcnEncAddress
      AsciiString,
   x25DtePLcnProtocolEncType
      INTEGER,
   x25DtePLcnLinkToRemoteGroup
      Link,
   x25DtePLcnInPacketSize
      Unsigned32,
   x25DtePLcnOutPacketSize
      Unsigned32,
   x25DtePLcnInWindowSize
      Unsigned32,
   x25DtePLcnOutWindowSize
      Unsigned32 }

x25DtePLcnEncAddressType OBJECT-TYPE
   SYNTAX     INTEGER  {
                 none(0),
                 ip(204) }
   ACCESS     read-write
   STATUS     mandatory
   DESCRIPTION
     "This attribute specifies the encapsulation type for the address of the 
      remote host with which this Peer component allows 
      communication."
   DEFVAL     { ip }
::= { x25DtePLcnProvEntry 1 }

x25DtePLcnEncAddress OBJECT-TYPE
   SYNTAX     AsciiString (SIZE (0..128))
   ACCESS     read-write
   STATUS     mandatory
   DESCRIPTION
     "This attribute specifies the encapsulation address of the remote host 
      with which this PermLcn component defines a connection"
::= { x25DtePLcnProvEntry 2 }

x25DtePLcnProtocolEncType OBJECT-TYPE
   SYNTAX     INTEGER  {
                 null(0),
                 ip(204),
                 nscNull(257) }
   ACCESS     read-write
   STATUS     mandatory
   DESCRIPTION
     "This attribute specifies the encapsulation method to use when 
      exchanging protocol data units (PDUs) over this channel. IP and 
      Null protocolEncTypes are as defined in RFC1356. 
      NscNull is an encapsulation method for carrying IP datagrams 
      which requires removing 3 padding octets of zeroes and the 
      protocol identifier H.CC from the front of each data packet received 
      from the link in order to obtain the PDU. PDUs sent to the link are 
      propounded by a the protocol identifier H.CC. NscNull should only 
      be set when the remote host is following this same encapsulation 
      method."
   DEFVAL     { ip }
::= { x25DtePLcnProvEntry 3 }

x25DtePLcnLinkToRemoteGroup OBJECT-TYPE
   SYNTAX     Link 
   ACCESS     read-write
   STATUS     mandatory
   DESCRIPTION
     "This attribute specifies the link to the RemoteGroup, indicating the 
      RemoteGroup component with which this PermLcn component is 
      associated. The RemoteGroup components logically divide up the 
      X.25 Interface such that a number of Protocol Ports (and 
      consequently a number of Virtual Routers) may share the same 
      X.25 Interface into a Wide Area Network. In particular, the remote 
      host identified by this PermLcn component is designated as 
      belonging to the RemoteGroup linked by this attribute. The set of all 
      PermLcn and Peer components which link to a given RemoteGroup 
      determine the subset of remote hosts which are accessible to a 
      particular Protocol Port (and ultimately a Virtual Router)."
::= { x25DtePLcnProvEntry 4 }

x25DtePLcnInPacketSize OBJECT-TYPE
   SYNTAX     Unsigned32 (16 | 32 | 64 | 128 | 256 | 512 | 1024 | 2048 | 4096)
   ACCESS     read-write
   STATUS     mandatory
   DESCRIPTION
     "This attribute specifies the maximum receive packet size in octets."
   DEFVAL     { 128 }
::= { x25DtePLcnProvEntry 5 }

x25DtePLcnOutPacketSize OBJECT-TYPE
   SYNTAX     Unsigned32 (16 | 32 | 64 | 128 | 256 | 512 | 1024 | 2048 | 4096)
   ACCESS     read-write
   STATUS     mandatory
   DESCRIPTION
     "This attribute specifies the maximum transmit packet size in octets."
   DEFVAL     { 128 }
::= { x25DtePLcnProvEntry 6 }

x25DtePLcnInWindowSize OBJECT-TYPE
   SYNTAX     Unsigned32 (1..127)
   ACCESS     read-write
   STATUS     mandatory
   DESCRIPTION
     "This attribute specifies the maximum receive window size. A 
      inWindowSize greater than 7 is only valid when the 
      packetSequencing attribute of the X25Dte component is set to 
      modulo128."
   DEFVAL     { 2 }
::= { x25DtePLcnProvEntry 7 }

x25DtePLcnOutWindowSize OBJECT-TYPE
   SYNTAX     Unsigned32 (1..127)
   ACCESS     read-write
   STATUS     mandatory
   DESCRIPTION
     "This attribute specifies the maximum transmit window size. A 
      outWindowSize greater than 7 is only valid when the 
      packetSequencing attribute of the X25Dte component is set to 
      modulo128."
   DEFVAL     { 2 }
::= { x25DtePLcnProvEntry 8 }

-- 
-- *** THIS SUBTREE CURRENTLY NOT IMPLEMENTED ***
-- 

-- 
-- X25Dte/x Lcn/x
-- 
-- This component contains information about a specific logical 
-- channel of an X.25 interface.

x25DteLcn OBJECT IDENTIFIER ::= { x25Dte 4 }



x25DteLcnRowStatusTable OBJECT-TYPE
   SYNTAX     SEQUENCE OF X25DteLcnRowStatusEntry
   ACCESS     not-accessible
   STATUS     mandatory
   DESCRIPTION
     "*** THIS TABLE CURRENTLY NOT IMPLEMENTED ***

      This entry controls the addition and deletion of 
      x25DteLcn components."
::= { x25DteLcn 1 }

x25DteLcnRowStatusEntry OBJECT-TYPE
   SYNTAX     X25DteLcnRowStatusEntry
   ACCESS     not-accessible
   STATUS     mandatory
   DESCRIPTION
     "A single entry in the table represents a single 
      x25DteLcn component."
   INDEX {
      x25DteIndex,
      x25DteLcnIndex }
::= { x25DteLcnRowStatusTable 1 }

X25DteLcnRowStatusEntry ::= SEQUENCE {
   x25DteLcnRowStatus
      RowStatus,
   x25DteLcnComponentName
      DisplayString,
   x25DteLcnStorageType
      StorageType,
   x25DteLcnIndex
      Integer32 }

x25DteLcnRowStatus OBJECT-TYPE
   SYNTAX     RowStatus 
   ACCESS     read-only
   STATUS     mandatory
   DESCRIPTION
     "This variable is used as the basis for SNMP naming of
      x25DteLcn components.
      These components cannot be added nor deleted."
::= { x25DteLcnRowStatusEntry 1 }

x25DteLcnComponentName OBJECT-TYPE
   SYNTAX     DisplayString 
   ACCESS     read-only
   STATUS     mandatory
   DESCRIPTION
     "This variable provides the component's string name for
      use with the ASCII Console Interface"
::= { x25DteLcnRowStatusEntry 2 }

x25DteLcnStorageType OBJECT-TYPE
   SYNTAX     StorageType 
   ACCESS     read-only
   STATUS     mandatory
   DESCRIPTION
     "This variable represents the storage type value for the
      x25DteLcn tables."
::= { x25DteLcnRowStatusEntry 4 }

x25DteLcnIndex OBJECT-TYPE
   SYNTAX     Integer32 (1..4095)
   ACCESS     not-accessible
   STATUS     mandatory
   DESCRIPTION
     "This variable represents the index for the x25DteLcn tables."
::= { x25DteLcnRowStatusEntry 10 }

x25DteLcnStateTable OBJECT-TYPE
   SYNTAX     SEQUENCE OF X25DteLcnStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { x25DteLcn 10 }

x25DteLcnStateEntry OBJECT-TYPE
   SYNTAX     X25DteLcnStateEntry
   ACCESS     not-accessible
   STATUS     mandatory
   DESCRIPTION
     "An entry in the x25DteLcnStateTable."
   INDEX {
      x25DteIndex,
      x25DteLcnIndex }
::= { x25DteLcnStateTable 1 }

X25DteLcnStateEntry ::= SEQUENCE {
   x25DteLcnAdminState
      INTEGER,
   x25DteLcnOperationalState
      INTEGER,
   x25DteLcnUsageState
      INTEGER }

x25DteLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { x25DteLcnStateEntry 1 }

x25DteLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { x25DteLcnStateEntry 2 }

x25DteLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { x25DteLcnStateEntry 3 }

x25DteLcnCpTable OBJECT-TYPE
   SYNTAX     SEQUENCE OF X25DteLcnCpEntry
   ACCESS     not-accessible
   STATUS     mandatory
   DESCRIPTION
     "*** THIS TABLE CURRENTLY NOT IMPLEMENTED ***

      This group contains the call parameters that are in use for this 
      logical channel. For a PVC only the packet size and the window 
      size attributes are meaningful."
::= { x25DteLcn 11 }

x25DteLcnCpEntry OBJECT-TYPE
   SYNTAX     X25DteLcnCpEntry
   ACCESS     not-accessible
   STATUS     mandatory
   DESCRIPTION
     "An entry in the x25DteLcnCpTable."
   INDEX {
      x25DteIndex,
      x25DteLcnIndex }
::= { x25DteLcnCpTable 1 }

X25DteLcnCpEntry ::= SEQUENCE {
   x25DteLcnInPacketSize
      Unsigned32,
   x25DteLcnOutPacketSize
      Unsigned32,
   x25DteLcnInWindowSize
      Unsigned32,
   x25DteLcnOutWindowSize
      Unsigned32,
   x25DteLcnProposeReverseCharging
      INTEGER,
   x25DteLcnFastSelect
      INTEGER,
   x25DteLcnOutThroughputClassSize
      INTEGER,
   x25DteLcnInThroughputClassSize
      INTEGER,
   x25DteLcnCugIndex
      AsciiString,
   x25DteLcnCugoaIndex
      AsciiString,
   x25DteLcnNetworkUserIdentifier
      HexString,
   x25DteLcnChargingInformation
      INTEGER,
   x25DteLcnRpoa
      AsciiString,
   x25DteLcnTrnstDlySlctnAInd
      Unsigned32,
   x25DteLcnCallingNetworkFax
      HexString,
   x25DteLcnCalledNetworkFax
      HexString,
   x25DteLcnCallUserData
      HexString }

x25DteLcnInPacketSize OBJECT-TYPE
   SYNTAX     Unsigned32 (16 | 32 | 64 | 128 | 256 | 512 | 1024 | 2048 | 4096)
   ACCESS     read-only
   STATUS     mandatory
   DESCRIPTION
     "This attribute indicates the maximum receive packet size in octets."
::= { x25DteLcnCpEntry 1 }

x25DteLcnOutPacketSize OBJECT-TYPE
   SYNTAX     Unsigned32 (16 | 32 | 64 | 128 | 256 | 512 | 1024 | 2048 | 4096)
   ACCESS     read-only
   STATUS     mandatory
   DESCRIPTION
     "This attribute indicates the maximum transmit packet size in octets."
::= { x25DteLcnCpEntry 2 }

x25DteLcnInWindowSize OBJECT-TYPE
   SYNTAX     Unsigned32 (1..127)
   ACCESS     read-only
   STATUS     mandatory
   DESCRIPTION
     "This attribute indicates the receive window size."
::= { x25DteLcnCpEntry 3 }

x25DteLcnOutWindowSize OBJECT-TYPE
   SYNTAX     Unsigned32 (1..127)
   ACCESS     read-only
   STATUS     mandatory
   DESCRIPTION
     "This attribute indicates the transmit window size."
::= { x25DteLcnCpEntry 4 }

x25DteLcnProposeReverseCharging OBJECT-TYPE
   SYNTAX     INTEGER  {
                 reverse(2),
                 local(3) }
   ACCESS     read-only
   STATUS     mandatory
   DESCRIPTION
     "Specifies whether local/reverse charging was negotiated for this 
      logical channel. To determine which end of the channel is paying 
      for the call, this attribute must be examined in combination with the 
      callDirection attribute. For example, if this attribute is set to reverse 
      and the callDirection attribute indicates incoming, it means the 
      incoming call signalled reverse charging, so the local end of the 
      channel is being charged. On the other, if the value of this attribute 
      is reverse and the callDirection is outgoing, it means that the call 
      request sent to the link signalled reverse charging; so the remote end 
      is charged. Similarly, a value of local must also be interpreted in 
      combination with the callDirection to determine which end is being 
      charged. If the value of the callDirection attribute is plcn, the 
      proposeReverseCharging attribute is meaningless."
   DEFVAL     { local }
::= { x25DteLcnCpEntry 5 }

x25DteLcnFastSelect OBJECT-TYPE
   SYNTAX     INTEGER  {
                 unrestricted(3),
                 restricted(4),
                 no(5) }
   ACCESS     read-only
   STATUS     mandatory
   DESCRIPTION
     "This attribute indicates whether the fast select was used in 
      establishing this logical channel."
   DEFVAL     { no }
::= { x25DteLcnCpEntry 6 }

x25DteLcnOutThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-only
   STATUS     mandatory
   DESCRIPTION
     "This attribute specifies the transmit throughput class."
   DEFVAL     { notSpecified }
::= { x25DteLcnCpEntry 7 }

x25DteLcnInThroughputClassSize OBJECT-TYPE
   SYNTAX     INTEGER  {
                 n75(3),
                 n150(4),
                 n300(5),
                 n600(6),
                 n1200(7),
                 n2400(8),
                 n4800(9),
                 n9600(10),
                 n19200(11),
                 n48000(12),
                 n64000(13),
                 notSpecified(17) }
   ACCESS     read-only
   STATUS     mandatory
   DESCRIPTION
     "This attribute specifies the receive throughput class."
   DEFVAL     { notSpecified }
::= { x25DteLcnCpEntry 8 }

x25DteLcnCugIndex OBJECT-TYPE
   SYNTAX     AsciiString (SIZE (0..4))
   ACCESS     read-only
   STATUS     mandatory
   DESCRIPTION
     "This attribute indicates the index of the Closed User Group facility 
      used in establishing this logical channel."
   DEFVAL     { ''H }  -- ""
::= { x25DteLcnCpEntry 9 }

x25DteLcnCugoaIndex OBJECT-TYPE
   SYNTAX     AsciiString (SIZE (0..4))
   ACCESS     read-only
   STATUS     mandatory
   DESCRIPTION
     "This attribute indicates the index of the Closed User Group with 
      Outgoing Access facility used in establishing this logical channel."
   DEFVAL     { ''H }  -- ""
::= { x25DteLcnCpEntry 10 }

x25DteLcnNetworkUserIdentifier OBJECT-TYPE
   SYNTAX     HexString (SIZE (0..108))
   ACCESS     read-only
   STATUS     mandatory
   DESCRIPTION
     "Specifies the Network User Identifier used for this logical channel."
   DEFVAL     { ''H }  -- ""
::= { x25DteLcnCpEntry 11 }

x25DteLcnChargingInformation OBJECT-TYPE
   SYNTAX     INTEGER  {
                 notSpecified(2),
                 notRequested(3),
                 requested(4) }
   ACCESS     read-only
   STATUS     mandatory
   DESCRIPTION
     "This attribute indicates whether or not the charging information 
      facility was used in establishing this logical channel. A value of 
      notSpecified means the facility was not signalled. A value of 
      notRequested means the facility was signalled but charging 
      information was not requested (that is, the charging info field of the 
      facility was set Off). A value of requested means the facility was 
      signalled to explicitly request charging information. 
      DESCRIPTION"
   DEFVAL     { notSpecified }
::= { x25DteLcnCpEntry 12 }

x25DteLcnRpoa OBJECT-TYPE
   SYNTAX     AsciiString (SIZE (0..108))
   ACCESS     read-only
   STATUS     mandatory
   DESCRIPTION
     "This attribute indicates the RPOA facility which was signalled in 
      establishing this logical channel."
   DEFVAL     { ''H }  -- ""
::= { x25DteLcnCpEntry 13 }

x25DteLcnTrnstDlySlctnAInd OBJECT-TYPE
   SYNTAX     Unsigned32 (0..65536)
   ACCESS     read-only
   STATUS     mandatory
   DESCRIPTION
     "This attribute indicates the Transit Delay Selection and Indication 
      value used for this logical channel. A value of 65536 means no 
      facility was signalled."
   DEFVAL     { 65536 }
::= { x25DteLcnCpEntry 14 }

x25DteLcnCallingNetworkFax OBJECT-TYPE
   SYNTAX     HexString (SIZE (0..108))
   ACCESS     read-only
   STATUS     mandatory
   DESCRIPTION
     "This attribute indicates the Calling Network facilities which were 
      signalled in the call packet. A value of null (empty string) means no 
      calling network facilities were signalled."
   DEFVAL     { ''H }  -- ""
::= { x25DteLcnCpEntry 23 }

x25DteLcnCalledNetworkFax OBJECT-TYPE
   SYNTAX     HexString (SIZE (0..108))
   ACCESS     read-only
   STATUS     mandatory
   DESCRIPTION
     "This attribute indicates the called network facilities which were 
      signalled in the call packet. A value of null (empty string) means no 
      called network facilities were signalled."
   DEFVAL     { ''H }  -- ""
::= { x25DteLcnCpEntry 24 }

x25DteLcnCallUserData OBJECT-TYPE
   SYNTAX     HexString (SIZE (0..128))
   ACCESS     read-only
   STATUS     mandatory
   DESCRIPTION
     "This attribute indicates the user data which was signalled in the call 
      packet. A value of null (empty string) means no user data was 
      signalled."
   DEFVAL     { ''H }  -- ""
::= { x25DteLcnCpEntry 25 }

x25DteLcnLcnStatusTable OBJECT-TYPE
   SYNTAX     SEQUENCE OF X25DteLcnLcnStatusEntry
   ACCESS     not-accessible
   STATUS     mandatory
   DESCRIPTION
     "*** THIS TABLE CURRENTLY NOT IMPLEMENTED ***

      This group contains the status for an X.25 Logical Channel."
::= { x25DteLcn 12 }

x25DteLcnLcnStatusEntry OBJECT-TYPE
   SYNTAX     X25DteLcnLcnStatusEntry
   ACCESS     not-accessible
   STATUS     mandatory
   DESCRIPTION
     "An entry in the x25DteLcnLcnStatusTable."
   INDEX {
      x25DteIndex,
      x25DteLcnIndex }
::= { x25DteLcnLcnStatusTable 1 }

X25DteLcnLcnStatusEntry ::= SEQUENCE {
   x25DteLcnStatus
      INTEGER,
   x25DteLcnCallDirection
      INTEGER,
   x25DteLcnCalledAddress
      DigitString,
   x25DteLcnCallingAddress
      DigitString,
   x25DteLcnOriginalCalledAddress
      DigitString }

x25DteLcnStatus OBJECT-TYPE
   SYNTAX     INTEGER  {
                 closed(2),
                 calling(3),
                 dataTransfer(4),
                 clearing(5),
                 resetting(7) }
   ACCESS     read-only
   STATUS     mandatory
   DESCRIPTION
     "This attribute indicates the current state of the logical channel."
::= { x25DteLcnLcnStatusEntry 1 }

x25DteLcnCallDirection OBJECT-TYPE
   SYNTAX     INTEGER  {
                 incoming(1),
                 outgoing(2),
                 permanentLcn(3) }
   ACCESS     read-only
   STATUS     mandatory
   DESCRIPTION
     "This attribute indicates the direction of the call that caused the 
      establishment of this channel."
::= { x25DteLcnLcnStatusEntry 3 }

x25DteLcnCalledAddress OBJECT-TYPE
   SYNTAX     DigitString (SIZE (0..15))
   ACCESS     read-only
   STATUS     mandatory
   DESCRIPTION
     "This attribute indicates the called X.25 address to which the call is 
      established."
::= { x25DteLcnLcnStatusEntry 4 }

x25DteLcnCallingAddress OBJECT-TYPE
   SYNTAX     DigitString (SIZE (0..15))
   ACCESS     read-only
   STATUS     mandatory
   DESCRIPTION
     "This attribute indicates the calling X.25 address from which the call 
      originated"
::= { x25DteLcnLcnStatusEntry 5 }

x25DteLcnOriginalCalledAddress OBJECT-TYPE
   SYNTAX     DigitString (SIZE (0..15))
   ACCESS     read-only
   STATUS     mandatory
   DESCRIPTION
     "This attribute indicates the X.25 address of the originally called 
      DTE to which the call was attempted. This could be different from 
      the value of the calledAddress attribute in the case where the 
      original call was redirected."
::= { x25DteLcnLcnStatusEntry 6 }

x25DteLcnStatsTable OBJECT-TYPE
   SYNTAX     SEQUENCE OF X25DteLcnStatsEntry
   ACCESS     not-accessible
   STATUS     mandatory
   DESCRIPTION
     "*** THIS TABLE CURRENTLY NOT IMPLEMENTED ***

      This group contains the operational statistics for an X.25 Logical 
      Channel."
::= { x25DteLcn 13 }

x25DteLcnStatsEntry OBJECT-TYPE
   SYNTAX     X25DteLcnStatsEntry
   ACCESS     not-accessible
   STATUS     mandatory
   DESCRIPTION
     "An entry in the x25DteLcnStatsTable."
   INDEX {
      x25DteIndex,
      x25DteLcnIndex }
::= { x25DteLcnStatsTable 1 }

X25DteLcnStatsEntry ::= SEQUENCE {
   x25DteLcnInUknownProtocols
      Counter32,
   x25DteLcnInDataOctets
      Counter32,
   x25DteLcnInDataPackets
      Counter32,
   x25DteLcnInRmtInitiatedRsts
      Counter32,
   x25DteLcnInPrvdrInitiatedRsts
      Counter32,
   x25DteLcnInInterruptPackets
      Counter32,
   x25DteLcnOutDataOctets
      Counter32,
   x25DteLcnOutDataPackets
      Counter32,
   x25DteLcnOutInterruptPackets
      Counter32,
   x25DteLcnT22ResetTimeouts
      Counter32 }

x25DteLcnInUknownProtocols OBJECT-TYPE
   SYNTAX     Counter32 
   ACCESS     read-only
   STATUS     mandatory
   DESCRIPTION
     "This attribute counts the number packets received from link which 
      were discareded because of an unkown or unsupported protocols."
::= { x25DteLcnStatsEntry 1 }

x25DteLcnInDataOctets OBJECT-TYPE
   SYNTAX     Counter32 
   ACCESS     read-only
   STATUS     mandatory
   DESCRIPTION
     "This attribute counts the number of octets of user data received from 
      the link."
::= { x25DteLcnStatsEntry 2 }

x25DteLcnInDataPackets OBJECT-TYPE
   SYNTAX     Counter32 
   ACCESS     read-only
   STATUS     mandatory
   DESCRIPTION
     "This attribute counts the number of data packets received from the 
      link."
::= { x25DteLcnStatsEntry 3 }

x25DteLcnInRmtInitiatedRsts OBJECT-TYPE
   SYNTAX     Counter32 
   ACCESS     read-only
   STATUS     mandatory
   DESCRIPTION
     "This attribute counts the number of reset packets, with a cause code 
      of 'DTE initiated', which were received from the link"
::= { x25DteLcnStatsEntry 4 }

x25DteLcnInPrvdrInitiatedRsts OBJECT-TYPE
   SYNTAX     Counter32 
   ACCESS     read-only
   STATUS     mandatory
   DESCRIPTION
     "This attribute counts the number of reset packets, with a cause code 
      other than 'DTE initiated', which were received from the link."
::= { x25DteLcnStatsEntry 5 }

x25DteLcnInInterruptPackets OBJECT-TYPE
   SYNTAX     Counter32 
   ACCESS     read-only
   STATUS     mandatory
   DESCRIPTION
     "This attribute counts the number of interrupt packets received from 
      the link."
::= { x25DteLcnStatsEntry 6 }

x25DteLcnOutDataOctets OBJECT-TYPE
   SYNTAX     Counter32 
   ACCESS     read-only
   STATUS     mandatory
   DESCRIPTION
     "This attribute counts the number of octets of user data sent to the 
      link."
::= { x25DteLcnStatsEntry 7 }

x25DteLcnOutDataPackets OBJECT-TYPE
   SYNTAX     Counter32 
   ACCESS     read-only
   STATUS     mandatory
   DESCRIPTION
     "This attribute counts the number of data packets sent to link."
::= { x25DteLcnStatsEntry 8 }

x25DteLcnOutInterruptPackets OBJECT-TYPE
   SYNTAX     Counter32 
   ACCESS     read-only
   STATUS     mandatory
   DESCRIPTION
     "This attribute counts the number of interrupt packets sent to link."
::= { x25DteLcnStatsEntry 9 }

x25DteLcnT22ResetTimeouts OBJECT-TYPE
   SYNTAX     Counter32 
   ACCESS     read-only
   STATUS     mandatory
   DESCRIPTION
     "This attribute counts the number of times the t22 reset timer has 
      expired."
::= { x25DteLcnStatsEntry 10 }


-- 
-- This component defines the LAPB protocol and its related service 
-- options.

x25DteLapb OBJECT IDENTIFIER ::= { x25Dte 5 }



x25DteLapbRowStatusTable OBJECT-TYPE
   SYNTAX     SEQUENCE OF X25DteLapbRowStatusEntry
   ACCESS     not-accessible
   STATUS     mandatory
   DESCRIPTION
     "This entry controls the addition and deletion of 
      x25DteLapb components."
::= { x25DteLapb 1 }

x25DteLapbRowStatusEntry OBJECT-TYPE
   SYNTAX     X25DteLapbRowStatusEntry
   ACCESS     not-accessible
   STATUS     mandatory
   DESCRIPTION
     "A single entry in the table represents a single 
      x25DteLapb component."
   INDEX {
      x25DteIndex,
      x25DteLapbIndex }
::= { x25DteLapbRowStatusTable 1 }

X25DteLapbRowStatusEntry ::= SEQUENCE {
   x25DteLapbRowStatus
      RowStatus,
   x25DteLapbComponentName
      DisplayString,
   x25DteLapbStorageType
      StorageType,
   x25DteLapbIndex
      NonReplicated }

x25DteLapbRowStatus OBJECT-TYPE
   SYNTAX     RowStatus 
   ACCESS     read-only
   STATUS     mandatory
   DESCRIPTION
     "This variable is used as the basis for SNMP naming of
      x25DteLapb components.
      These components cannot be added nor deleted."
::= { x25DteLapbRowStatusEntry 1 }

x25DteLapbComponentName OBJECT-TYPE
   SYNTAX     DisplayString 
   ACCESS     read-only
   STATUS     mandatory
   DESCRIPTION
     "This variable provides the component's string name for
      use with the ASCII Console Interface"
::= { x25DteLapbRowStatusEntry 2 }

x25DteLapbStorageType OBJECT-TYPE
   SYNTAX     StorageType 
   ACCESS     read-only
   STATUS     mandatory
   DESCRIPTION
     "This variable represents the storage type value for the
      x25DteLapb tables."
::= { x25DteLapbRowStatusEntry 4 }

x25DteLapbIndex OBJECT-TYPE
   SYNTAX     NonReplicated 
   ACCESS     not-accessible
   STATUS     mandatory
   DESCRIPTION
     "This variable represents the index for the x25DteLapb tables."
::= { x25DteLapbRowStatusEntry 10 }

x25DteLapbCpTable OBJECT-TYPE
   SYNTAX     SEQUENCE OF X25DteLapbCpEntry
   ACCESS     not-accessible
   STATUS     mandatory
   DESCRIPTION
     "X25Dte/n Lapb 
      This group contains the set of configuration parameters for the 
      LAPB interface."
::= { x25DteLapb 10 }

x25DteLapbCpEntry OBJECT-TYPE
   SYNTAX     X25DteLapbCpEntry
   ACCESS     not-accessible
   STATUS     mandatory
   DESCRIPTION
     "An entry in the x25DteLapbCpTable."
   INDEX {
      x25DteIndex,
      x25DteLapbIndex }
::= { x25DteLapbCpTable 1 }

X25DteLapbCpEntry ::= SEQUENCE {
   x25DteLapbStationType
      INTEGER,
   x25DteLapbFrameSequencing
      INTEGER,
   x25DteLapbN1FrameSize
      Unsigned32,
   x25DteLapbKWindowSize
      Unsigned32,
   x25DteLapbN2TransmitLimit
      Unsigned32,
   x25DteLapbT1AckTimer
      Unsigned32,
   x25DteLapbT2AckDelayTimer
      Unsigned32,
   x25DteLapbT4IdleProbeTimer
      Unsigned32,
   x25DteLapbActionInitiate
      INTEGER,
   x25DteLapbActionRecvDM
      INTEGER,
   x25DteLapbTxQDegradeThreshold
      Unsigned32,
   x25DteLapbTxQResetThreshold
      Unsigned32 }

x25DteLapbStationType OBJECT-TYPE
   SYNTAX     INTEGER  {
                 dte(1),
                 dce(2) }
   ACCESS     read-write
   STATUS     mandatory
   DESCRIPTION
     "This attribute specifies the DCE or the DTE role of operation for the 
      LAPB interface. Changing this attribute will cause the lapb link to 
      Reset."
   DEFVAL     { dte }
::= { x25DteLapbCpEntry 1 }

x25DteLapbFrameSequencing OBJECT-TYPE
   SYNTAX     INTEGER  {
                 modulo8(1),
                 modulo128(2) }
   ACCESS     read-write
   STATUS     mandatory
   DESCRIPTION
     "This attribute specifies the modulo of the frame sequence 
      numbering of the LAPB interface. Changing this attribute will cause 
      the lapb link to Reset."
   DEFVAL     { modulo8 }
::= { x25DteLapbCpEntry 2 }

x25DteLapbN1FrameSize OBJECT-TYPE
   SYNTAX     Unsigned32 (40..32856)
   ACCESS     read-write
   STATUS     mandatory
   DESCRIPTION
     "This attribute specifies the maximum frame size in bits that can be 
      transmitted or received. This value must be greater than or equal to 
      the maximum packet size across the interface(in bits)+ max level 3 
      header size(in bits)+ max level 2 header size(in bits)+ crc in bits.
      
      (max Pkt size + -------------> 4096*8
      max level 3 header size + ---> 4*8
      level 2 header size + --------> 5*8
      crc -------------------> 2*8)"
   DEFVAL     { 32856 }
::= { x25DteLapbCpEntry 3 }

x25DteLapbKWindowSize OBJECT-TYPE
   SYNTAX     Unsigned32 (1..127)
   ACCESS     read-write
   STATUS     mandatory
   DESCRIPTION
     "This attribute specifies the window size. This is the maximum 
      number of unacknowledged sequenced frames that may be 
      outstanding from or to this interface at any one time. A window size 
      of greater than 7 is only valid when the sequence numbering of 
      frames is modulo 128."
   DEFVAL     { 7 }
::= { x25DteLapbCpEntry 4 }

x25DteLapbN2TransmitLimit OBJECT-TYPE
   SYNTAX     Unsigned32 (1..20)
   ACCESS     read-write
   STATUS     mandatory
   DESCRIPTION
     "This attribute specifies the maximum number of times a frame can 
      be transmitted before appropriate recovery action is taken."
   DEFVAL     { 10 }
::= { x25DteLapbCpEntry 5 }

x25DteLapbT1AckTimer OBJECT-TYPE
   SYNTAX     Unsigned32 (1000..10000)
   ACCESS     read-write
   STATUS     mandatory
   DESCRIPTION
     "This attribute specifies the period in milliseconds within which an 
      acknowledgment of a sent frame must be received. The value set for 
      t1 ack timer must be less than the value set for the t4 idle probe 
      timer."
   DEFVAL     { 3000 }
::= { x25DteLapbCpEntry 6 }

x25DteLapbT2AckDelayTimer OBJECT-TYPE
   SYNTAX     Unsigned32 (0..10000)
   ACCESS     read-write
   STATUS     mandatory
   DESCRIPTION
     "This attribute specifies the maximum period in milliseconds 
      permissible to wait before sending an acknowledgment for a 
      received in sequenced I-frame. A value of 0 means there will be no 
      delay in acknowledgment."
   DEFVAL     { 0 }
::= { x25DteLapbCpEntry 7 }

x25DteLapbT4IdleProbeTimer OBJECT-TYPE
   SYNTAX     Unsigned32 (1000..65535000)
   ACCESS     read-write
   STATUS     mandatory
   DESCRIPTION
     "This attribute specifies the time period in milliseconds the link will 
      be permitted to remain idle (that is, no frames are exchanged on the 
      data link). Upon expiry of this timer, LAPB will poll its peer for 
      status. The value set for t4 idle probe timer must be greater than the 
      value set for the t1 ack timer."
   DEFVAL     { 60000 }
::= { x25DteLapbCpEntry 8 }

x25DteLapbActionInitiate OBJECT-TYPE
   SYNTAX     INTEGER  {
                 sendSABM(1),
                 sendDM(3),
                 none(4) }
   ACCESS     read-write
   STATUS     mandatory
   DESCRIPTION
     "This attribute specifies the action to be taken by the LAPB interface 
      to initiate link setup."
   DEFVAL     { sendSABM }
::= { x25DteLapbCpEntry 9 }

x25DteLapbActionRecvDM OBJECT-TYPE
   SYNTAX     INTEGER  {
                 sendSABM(1) }
   ACCESS     read-write
   STATUS     mandatory
   DESCRIPTION
     "This attribute specifies the action to be taken by the LAPB interface 
      when it receives a DM response."
   DEFVAL     { sendSABM }
::= { x25DteLapbCpEntry 10 }

x25DteLapbTxQDegradeThreshold OBJECT-TYPE
   SYNTAX     Unsigned32 (1..65536)
   ACCESS     read-write
   STATUS     mandatory
   DESCRIPTION
     "This attribute specifies the threshold of the number of higher layer 
      packets queued, beyond which LAPB should initiate a service 
      degrade alarm. A value of 65536 means no threshold."
   DEFVAL     { 65536 }
::= { x25DteLapbCpEntry 11 }

x25DteLapbTxQResetThreshold OBJECT-TYPE
   SYNTAX     Unsigned32 (1..65536)
   ACCESS     read-write
   STATUS     mandatory
   DESCRIPTION
     "This attribute specifies the threshold of the number of higher layer 
      packets queued, beyond which LAPB should initiate an overload 
      alarm and reset the link. A value of 65536 means no threshold."
   DEFVAL     { 65536 }
::= { x25DteLapbCpEntry 12 }

x25DteLapbStateTable OBJECT-TYPE
   SYNTAX     SEQUENCE OF X25DteLapbStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { x25DteLapb 11 }

x25DteLapbStateEntry OBJECT-TYPE
   SYNTAX     X25DteLapbStateEntry
   ACCESS     not-accessible
   STATUS     mandatory
   DESCRIPTION
     "An entry in the x25DteLapbStateTable."
   INDEX {
      x25DteIndex,
      x25DteLapbIndex }
::= { x25DteLapbStateTable 1 }

X25DteLapbStateEntry ::= SEQUENCE {
   x25DteLapbAdminState
      INTEGER,
   x25DteLapbOperationalState
      INTEGER,
   x25DteLapbUsageState
      INTEGER }

x25DteLapbAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { x25DteLapbStateEntry 1 }

x25DteLapbOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { x25DteLapbStateEntry 2 }

x25DteLapbUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { x25DteLapbStateEntry 3 }

x25DteLapbStatusTable OBJECT-TYPE
   SYNTAX     SEQUENCE OF X25DteLapbStatusEntry
   ACCESS     not-accessible
   STATUS     mandatory
   DESCRIPTION
     "This group contains the status for the LAPB interface."
::= { x25DteLapb 12 }

x25DteLapbStatusEntry OBJECT-TYPE
   SYNTAX     X25DteLapbStatusEntry
   ACCESS     not-accessible
   STATUS     mandatory
   DESCRIPTION
     "An entry in the x25DteLapbStatusTable."
   INDEX {
      x25DteIndex,
      x25DteLapbIndex }
::= { x25DteLapbStatusTable 1 }

X25DteLapbStatusEntry ::= SEQUENCE {
   x25DteLapbCurrentState
      INTEGER,
   x25DteLapbLastStateChangeReason
      INTEGER,
   x25DteLapbFrmrTransmit
      HexString,
   x25DteLapbFrmrReceive
      HexString,
   x25DteLapbCurrentQueueSize
      Unsigned32 }

x25DteLapbCurrentState OBJECT-TYPE
   SYNTAX     INTEGER  {
                 disconnected(1),
                 linkSetup(2),
                 frameReject(3),
                 disconnectRequest(4),
                 informationTransfer(5),
                 waitingAck(7) }
   ACCESS     read-only
   STATUS     mandatory
   DESCRIPTION
     "This attribute specifies the current state of the LAPB interface."
::= { x25DteLapbStatusEntry 1 }

x25DteLapbLastStateChangeReason OBJECT-TYPE
   SYNTAX     INTEGER  {
                 notStarted(1),
                 abmEntered(2),
                 abmeEntered(3),
                 abmReset(4),
                 abmeReset(5),
                 dmReceived(6),
                 dmSent(7),
                 discReceived(8),
                 discSent(9),
                 frmrReceived(10),
                 frmrSent(11),
                 n2TimeOut(12),
                 other(13) }
   ACCESS     read-only
   STATUS     mandatory
   DESCRIPTION
     "This attribute specifies the reason for the most recent state change."
::= { x25DteLapbStatusEntry 2 }

x25DteLapbFrmrTransmit OBJECT-TYPE
   SYNTAX     HexString (SIZE (0..7))
   ACCESS     read-only
   STATUS     mandatory
   DESCRIPTION
     "This attribute specifies the Information field of the FRMR most 
      recently sent."
   DEFVAL     { ''H }  -- ""
::= { x25DteLapbStatusEntry 3 }

x25DteLapbFrmrReceive OBJECT-TYPE
   SYNTAX     HexString (SIZE (0..7))
   ACCESS     read-only
   STATUS     mandatory
   DESCRIPTION
     "This attribute specifies the Information field of the FRMR most 
      recently received."
   DEFVAL     { ''H }  -- ""
::= { x25DteLapbStatusEntry 4 }

x25DteLapbCurrentQueueSize OBJECT-TYPE
   SYNTAX     Unsigned32 (0..4294967295)
   ACCESS     read-only
   STATUS     mandatory
   DESCRIPTION
     "This attribute specifies the number of packets on the lapb transmit 
      queue."
::= { x25DteLapbStatusEntry 5 }

x25DteLapbStatsTable OBJECT-TYPE
   SYNTAX     SEQUENCE OF X25DteLapbStatsEntry
   ACCESS     not-accessible
   STATUS     mandatory
   DESCRIPTION
     "This group contains the statistics for the LAPB interface."
::= { x25DteLapb 13 }

x25DteLapbStatsEntry OBJECT-TYPE
   SYNTAX     X25DteLapbStatsEntry
   ACCESS     not-accessible
   STATUS     mandatory
   DESCRIPTION
     "An entry in the x25DteLapbStatsTable."
   INDEX {
      x25DteIndex,
      x25DteLapbIndex }
::= { x25DteLapbStatsTable 1 }

X25DteLapbStatsEntry ::= SEQUENCE {
   x25DteLapbStateChanges
      Counter32,
   x25DteLapbRemoteBusy
      Counter32,
   x25DteLapbTransmitRejectFrames
      Counter32,
   x25DteLapbReceiveRejectFrames
      Counter32,
   x25DteLapbT1AckTimeout
      Counter32 }

x25DteLapbStateChanges OBJECT-TYPE
   SYNTAX     Counter32 
   ACCESS     read-only
   STATUS     mandatory
   DESCRIPTION
     "This attribute counts the number of times LAPB state has changed. 
      Refer to the attribute 'linkState' for the set of possible states."
::= { x25DteLapbStatsEntry 1 }

x25DteLapbRemoteBusy OBJECT-TYPE
   SYNTAX     Counter32 
   ACCESS     read-only
   STATUS     mandatory
   DESCRIPTION
     "This attribute counts the number of times transmission of an I-frame 
      was un-successful due to a perceived remote busy condition 
      (window closed or remote busy)."
::= { x25DteLapbStatsEntry 2 }

x25DteLapbTransmitRejectFrames OBJECT-TYPE
   SYNTAX     Counter32 
   ACCESS     read-only
   STATUS     mandatory
   DESCRIPTION
     "This attribute counts the number of REJ frames sent by the 
      interface."
::= { x25DteLapbStatsEntry 3 }

x25DteLapbReceiveRejectFrames OBJECT-TYPE
   SYNTAX     Counter32 
   ACCESS     read-only
   STATUS     mandatory
   DESCRIPTION
     "This attribute counts the number of REJ frames received by the 
      interface."
::= { x25DteLapbStatsEntry 4 }

x25DteLapbT1AckTimeout OBJECT-TYPE
   SYNTAX     Counter32 
   ACCESS     read-only
   STATUS     mandatory
   DESCRIPTION
     "This attribute counts the number of times the T1 timer has expired."
::= { x25DteLapbStatsEntry 5 }


-- 
-- X25Dte/n Lapb Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

x25DteLapbFramer OBJECT IDENTIFIER ::= { x25DteLapb 2 }



x25DteLapbFramerRowStatusTable OBJECT-TYPE
   SYNTAX     SEQUENCE OF X25DteLapbFramerRowStatusEntry
   ACCESS     not-accessible
   STATUS     mandatory
   DESCRIPTION
     "This entry controls the addition and deletion of 
      x25DteLapbFramer components."
::= { x25DteLapbFramer 1 }

x25DteLapbFramerRowStatusEntry OBJECT-TYPE
   SYNTAX     X25DteLapbFramerRowStatusEntry
   ACCESS     not-accessible
   STATUS     mandatory
   DESCRIPTION
     "A single entry in the table represents a single 
      x25DteLapbFramer component."
   INDEX {
      x25DteIndex,
      x25DteLapbIndex,
      x25DteLapbFramerIndex }
::= { x25DteLapbFramerRowStatusTable 1 }

X25DteLapbFramerRowStatusEntry ::= SEQUENCE {
   x25DteLapbFramerRowStatus
      RowStatus,
   x25DteLapbFramerComponentName
      DisplayString,
   x25DteLapbFramerStorageType
      StorageType,
   x25DteLapbFramerIndex
      NonReplicated }

x25DteLapbFramerRowStatus OBJECT-TYPE
   SYNTAX     RowStatus 
   ACCESS     read-only
   STATUS     mandatory
   DESCRIPTION
     "This variable is used as the basis for SNMP naming of
      x25DteLapbFramer components.
      These components cannot be added nor deleted."
::= { x25DteLapbFramerRowStatusEntry 1 }

x25DteLapbFramerComponentName OBJECT-TYPE
   SYNTAX     DisplayString 
   ACCESS     read-only
   STATUS     mandatory
   DESCRIPTION
     "This variable provides the component's string name for
      use with the ASCII Console Interface"
::= { x25DteLapbFramerRowStatusEntry 2 }

x25DteLapbFramerStorageType OBJECT-TYPE
   SYNTAX     StorageType 
   ACCESS     read-only
   STATUS     mandatory
   DESCRIPTION
     "This variable represents the storage type value for the
      x25DteLapbFramer tables."
::= { x25DteLapbFramerRowStatusEntry 4 }

x25DteLapbFramerIndex OBJECT-TYPE
   SYNTAX     NonReplicated 
   ACCESS     not-accessible
   STATUS     mandatory
   DESCRIPTION
     "This variable represents the index for the x25DteLapbFramer tables."
::= { x25DteLapbFramerRowStatusEntry 10 }

x25DteLapbFramerProvTable OBJECT-TYPE
   SYNTAX     SEQUENCE OF X25DteLapbFramerProvEntry
   ACCESS     not-accessible
   STATUS     mandatory
   DESCRIPTION
     "This group contains the base provisioning data for the Framer 
      component. Application or hardware interface specific provisioning 
      data is contained in other provisionable Framer groups."
::= { x25DteLapbFramer 10 }

x25DteLapbFramerProvEntry OBJECT-TYPE
   SYNTAX     X25DteLapbFramerProvEntry
   ACCESS     not-accessible
   STATUS     mandatory
   DESCRIPTION
     "An entry in the x25DteLapbFramerProvTable."
   INDEX {
      x25DteIndex,
      x25DteLapbIndex,
      x25DteLapbFramerIndex }
::= { x25DteLapbFramerProvTable 1 }

X25DteLapbFramerProvEntry ::= SEQUENCE {
   x25DteLapbFramerInterfaceName
      Link }

x25DteLapbFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { x25DteLapbFramerProvEntry 1 }

x25DteLapbFramerLinkTable OBJECT-TYPE
   SYNTAX     SEQUENCE OF X25DteLapbFramerLinkEntry
   ACCESS     not-accessible
   STATUS     mandatory
   DESCRIPTION
     "This group contains attributes defining the framing of data on the 
      link interface."
::= { x25DteLapbFramer 11 }

x25DteLapbFramerLinkEntry OBJECT-TYPE
   SYNTAX     X25DteLapbFramerLinkEntry
   ACCESS     not-accessible
   STATUS     mandatory
   DESCRIPTION
     "An entry in the x25DteLapbFramerLinkTable."
   INDEX {
      x25DteIndex,
      x25DteLapbIndex,
      x25DteLapbFramerIndex }
::= { x25DteLapbFramerLinkTable 1 }

X25DteLapbFramerLinkEntry ::= SEQUENCE {
   x25DteLapbFramerFlagsBetweenFrames
      Unsigned32 }

x25DteLapbFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { x25DteLapbFramerLinkEntry 4 }

x25DteLapbFramerStateTable OBJECT-TYPE
   SYNTAX     SEQUENCE OF X25DteLapbFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { x25DteLapbFramer 12 }

x25DteLapbFramerStateEntry OBJECT-TYPE
   SYNTAX     X25DteLapbFramerStateEntry
   ACCESS     not-accessible
   STATUS     mandatory
   DESCRIPTION
     "An entry in the x25DteLapbFramerStateTable."
   INDEX {
      x25DteIndex,
      x25DteLapbIndex,
      x25DteLapbFramerIndex }
::= { x25DteLapbFramerStateTable 1 }

X25DteLapbFramerStateEntry ::= SEQUENCE {
   x25DteLapbFramerAdminState
      INTEGER,
   x25DteLapbFramerOperationalState
      INTEGER,
   x25DteLapbFramerUsageState
      INTEGER }

x25DteLapbFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { x25DteLapbFramerStateEntry 1 }

x25DteLapbFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { x25DteLapbFramerStateEntry 2 }

x25DteLapbFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { x25DteLapbFramerStateEntry 3 }

x25DteLapbFramerStatsTable OBJECT-TYPE
   SYNTAX     SEQUENCE OF X25DteLapbFramerStatsEntry
   ACCESS     not-accessible
   STATUS     mandatory
   DESCRIPTION
     "This group contains the operational statistics data for a Framer 
      component."
::= { x25DteLapbFramer 13 }

x25DteLapbFramerStatsEntry OBJECT-TYPE
   SYNTAX     X25DteLapbFramerStatsEntry
   ACCESS     not-accessible
   STATUS     mandatory
   DESCRIPTION
     "An entry in the x25DteLapbFramerStatsTable."
   INDEX {
      x25DteIndex,
      x25DteLapbIndex,
      x25DteLapbFramerIndex }
::= { x25DteLapbFramerStatsTable 1 }

X25DteLapbFramerStatsEntry ::= SEQUENCE {
   x25DteLapbFramerFrmToIf
      Counter32,
   x25DteLapbFramerFrmFromIf
      Counter32,
   x25DteLapbFramerOctetFromIf
      Counter32,
   x25DteLapbFramerAborts
      Counter32,
   x25DteLapbFramerCrcErrors
      Counter32,
   x25DteLapbFramerLrcErrors
      Counter32,
   x25DteLapbFramerNonOctetErrors
      Counter32,
   x25DteLapbFramerOverruns
      Counter32,
   x25DteLapbFramerUnderruns
      Counter32 }

x25DteLapbFramerFrmToIf OBJECT-TYPE
   SYNTAX     Counter32 
   ACCESS     read-only
   STATUS     mandatory
   DESCRIPTION
     "The number of frames transmitted to the link interface by Framer.
      
      Note: This does not include the number of frames transmitted 
      directly to the hardware queue, thus bypassing the Framer 
      component."
::= { x25DteLapbFramerStatsEntry 1 }

x25DteLapbFramerFrmFromIf OBJECT-TYPE
   SYNTAX     Counter32 
   ACCESS     read-only
   STATUS     mandatory
   DESCRIPTION
     "The number of frames received from the link interface by Framer."
::= { x25DteLapbFramerStatsEntry 2 }

x25DteLapbFramerOctetFromIf OBJECT-TYPE
   SYNTAX     Counter32 
   ACCESS     read-only
   STATUS     mandatory
   DESCRIPTION
     "The number of bytes received from the link interface by Framer."
::= { x25DteLapbFramerStatsEntry 3 }

x25DteLapbFramerAborts OBJECT-TYPE
   SYNTAX     Counter32 
   ACCESS     read-only
   STATUS     mandatory
   DESCRIPTION
     "This attribute is the total number of aborts received."
::= { x25DteLapbFramerStatsEntry 4 }

x25DteLapbFramerCrcErrors OBJECT-TYPE
   SYNTAX     Counter32 
   ACCESS     read-only
   STATUS     mandatory
   DESCRIPTION
     "This attribute is the total number of frames with CRC errors, 
      occurring in the receive direction from the link."
::= { x25DteLapbFramerStatsEntry 5 }

x25DteLapbFramerLrcErrors OBJECT-TYPE
   SYNTAX     Counter32 
   ACCESS     read-only
   STATUS     mandatory
   DESCRIPTION
     "This attribute is the total number of frames with LRC errors, 
      occurring in the Tx link prior to transmission onto the link."
::= { x25DteLapbFramerStatsEntry 6 }

x25DteLapbFramerNonOctetErrors OBJECT-TYPE
   SYNTAX     Counter32 
   ACCESS     read-only
   STATUS     mandatory
   DESCRIPTION
     "This attribute is the total number of frames that were non octet 
      aligned."
::= { x25DteLapbFramerStatsEntry 7 }

x25DteLapbFramerOverruns OBJECT-TYPE
   SYNTAX     Counter32 
   ACCESS     read-only
   STATUS     mandatory
   DESCRIPTION
     "This attribute is the total number of frames received from the link 
      for which overruns occurred."
::= { x25DteLapbFramerStatsEntry 8 }

x25DteLapbFramerUnderruns OBJECT-TYPE
   SYNTAX     Counter32 
   ACCESS     read-only
   STATUS     mandatory
   DESCRIPTION
     "This attribute is the total number of frames transmitted to the link 
      for which underruns occurred."
::= { x25DteLapbFramerStatsEntry 9 }

x25DteLapbFramerUtilTable OBJECT-TYPE
   SYNTAX     SEQUENCE OF X25DteLapbFramerUtilEntry
   ACCESS     not-accessible
   STATUS     mandatory
   DESCRIPTION
     "This group contains the link utilizaiton operational data for a 
      Framer component."
::= { x25DteLapbFramer 14 }

x25DteLapbFramerUtilEntry OBJECT-TYPE
   SYNTAX     X25DteLapbFramerUtilEntry
   ACCESS     not-accessible
   STATUS     mandatory
   DESCRIPTION
     "An entry in the x25DteLapbFramerUtilTable."
   INDEX {
      x25DteIndex,
      x25DteLapbIndex,
      x25DteLapbFramerIndex }
::= { x25DteLapbFramerUtilTable 1 }

X25DteLapbFramerUtilEntry ::= SEQUENCE {
   x25DteLapbFramerNormPrioLinkUtilToIf
      Gauge32,
   x25DteLapbFramerNormPrioLinkUtilFromIf
      Gauge32 }

x25DteLapbFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities of 0, 6 and 9 and/or Emission Priority of 2 and 3. 
      The utilization is the average for the last minute."
   DEFVAL     { 0 }
::= { x25DteLapbFramerUtilEntry 1 }

x25DteLapbFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 or 9 and/or Emission Priority of 
      2 and 3. The utilization is the average for the last minute."
   DEFVAL     { 0 }
::= { x25DteLapbFramerUtilEntry 3 }


-- 
-- X25Dte/n PacketLayerEntity
-- 
-- This component provides information that applies to multiprotocol 
-- interconnect over an X.25 service. 

x25DtePle OBJECT IDENTIFIER ::= { x25Dte 6 }



x25DtePleRowStatusTable OBJECT-TYPE
   SYNTAX     SEQUENCE OF X25DtePleRowStatusEntry
   ACCESS     not-accessible
   STATUS     mandatory
   DESCRIPTION
     "This entry controls the addition and deletion of 
      x25DtePle components."
::= { x25DtePle 1 }

x25DtePleRowStatusEntry OBJECT-TYPE
   SYNTAX     X25DtePleRowStatusEntry
   ACCESS     not-accessible
   STATUS     mandatory
   DESCRIPTION
     "A single entry in the table represents a single 
      x25DtePle component."
   INDEX {
      x25DteIndex,
      x25DtePleIndex }
::= { x25DtePleRowStatusTable 1 }

X25DtePleRowStatusEntry ::= SEQUENCE {
   x25DtePleRowStatus
      RowStatus,
   x25DtePleComponentName
      DisplayString,
   x25DtePleStorageType
      StorageType,
   x25DtePleIndex
      NonReplicated }

x25DtePleRowStatus OBJECT-TYPE
   SYNTAX     RowStatus 
   ACCESS     read-only
   STATUS     mandatory
   DESCRIPTION
     "This variable is used as the basis for SNMP naming of
      x25DtePle components.
      These components cannot be added nor deleted."
::= { x25DtePleRowStatusEntry 1 }

x25DtePleComponentName OBJECT-TYPE
   SYNTAX     DisplayString 
   ACCESS     read-only
   STATUS     mandatory
   DESCRIPTION
     "This variable provides the component's string name for
      use with the ASCII Console Interface"
::= { x25DtePleRowStatusEntry 2 }

x25DtePleStorageType OBJECT-TYPE
   SYNTAX     StorageType 
   ACCESS     read-only
   STATUS     mandatory
   DESCRIPTION
     "This variable represents the storage type value for the
      x25DtePle tables."
::= { x25DtePleRowStatusEntry 4 }

x25DtePleIndex OBJECT-TYPE
   SYNTAX     NonReplicated 
   ACCESS     not-accessible
   STATUS     mandatory
   DESCRIPTION
     "This variable represents the index for the x25DtePle tables."
::= { x25DtePleRowStatusEntry 10 }

x25DtePleProvTable OBJECT-TYPE
   SYNTAX     SEQUENCE OF X25DtePleProvEntry
   ACCESS     not-accessible
   STATUS     mandatory
   DESCRIPTION
     "This group contains the provisionable attributes relevant to an 
      interface used to carry Multiprotocol Interconnect traffic over X.25."
::= { x25DtePle 10 }

x25DtePleProvEntry OBJECT-TYPE
   SYNTAX     X25DtePleProvEntry
   ACCESS     not-accessible
   STATUS     mandatory
   DESCRIPTION
     "An entry in the x25DtePleProvTable."
   INDEX {
      x25DteIndex,
      x25DtePleIndex }
::= { x25DtePleProvTable 1 }

X25DtePleProvEntry ::= SEQUENCE {
   x25DtePleInactivityTimer
      Unsigned32 }

x25DtePleInactivityTimer OBJECT-TYPE
   SYNTAX     Unsigned32 (0..65536000)
   ACCESS     read-write
   STATUS     mandatory
   DESCRIPTION
     "This attribute specifies the period in milliseconds this interface will 
      keep an idle connection open before closing it."
   DEFVAL     { 180000 }
::= { x25DtePleProvEntry 1 }

x25DtePleOpTable OBJECT-TYPE
   SYNTAX     SEQUENCE OF X25DtePleOpEntry
   ACCESS     not-accessible
   STATUS     mandatory
   DESCRIPTION
     "This group contains the Operational attributes relevant to an 
      interface used to carry Multiprotocol Interconnect traffic over X.25."
::= { x25DtePle 11 }

x25DtePleOpEntry OBJECT-TYPE
   SYNTAX     X25DtePleOpEntry
   ACCESS     not-accessible
   STATUS     mandatory
   DESCRIPTION
     "An entry in the x25DtePleOpTable."
   INDEX {
      x25DteIndex,
      x25DtePleIndex }
::= { x25DtePleOpTable 1 }

X25DtePleOpEntry ::= SEQUENCE {
   x25DtePleEncAddrToX25LkupFlrs
      Unsigned32,
   x25DtePleLastFailedEncAddr
      HexString,
   x25DtePleX25AddrToEncLkupFlrs
      Unsigned32,
   x25DtePleLastFailedX25Addr
      DigitString }

x25DtePleEncAddrToX25LkupFlrs OBJECT-TYPE
   SYNTAX     Unsigned32 (0..4294967295)
   ACCESS     read-only
   STATUS     mandatory
   DESCRIPTION
     "This attribute indicates the number of times a translation attempt 
      from an Encapsulation address to an X.25 address failed to find a 
      corresponding X.25 address. Such a failure could occur when a 
      Protocol Port, linked to a RemoteGroup via the linkToProtocolPort 
      attribute of the RemoteGroup, requests through the software that a 
      X.25 call be established to a particular Encapsulation address. If the 
      RemoteGroup does not have a Peer component linked in its 
      linkToPeer attribute list, with the encAddress attribute equal to the 
      Encapsulation address specified, this counter will be incremented, 
      because the corresponding Peer component needed to establish an 
      X.25 connection was not found."
   DEFVAL     { 0 }
::= { x25DtePleOpEntry 1 }

x25DtePleLastFailedEncAddr OBJECT-TYPE
   SYNTAX     HexString (SIZE (2..128))
   ACCESS     read-only
   STATUS     mandatory
   DESCRIPTION
     "This attribute indicates the last Encapsulation address for which no 
      corresponding X.25 address was found and thus caused 
      encAddressToX25LkupFlrs to be incremented."
::= { x25DtePleOpEntry 2 }

x25DtePleX25AddrToEncLkupFlrs OBJECT-TYPE
   SYNTAX     Unsigned32 (0..4294967295)
   ACCESS     read-only
   STATUS     mandatory
   DESCRIPTION
     "This attribute indicates the number of times a translation attempt 
      from an X.25 address to an Encapsulation address failed to find a 
      corresponding Encapsulation address. Such a failure could occur 
      when a incoming call received from the link by the X.25 DTE is 
      directed to a specific RemoteGroup because the called address 
      matches the localAddress attribute of the RemoteGroup component. 
      If the RemoteGroup component does not have a Peer component 
      linked in its linkToPeer attribute list, with the x25Address attribute 
      equal to the calling address from the incoming call packet, there is 
      no appropriate Peer component, so the call is cleared and this 
      counter is incremented."
   DEFVAL     { 0 }
::= { x25DtePleOpEntry 4 }

x25DtePleLastFailedX25Addr OBJECT-TYPE
   SYNTAX     DigitString (SIZE (0..15))
   ACCESS     read-only
   STATUS     mandatory
   DESCRIPTION
     "This field specifies the last X.25 address that caused 
      x25AddressToEncLkupFlrs to be incremented."
::= { x25DtePleOpEntry 5 }


-- 
-- X25Dte/n RemoteGroup/n
-- 
-- At least one RemoteGroup is required for each X25Dte component. 
-- The RemoteGroup allows the X.25 DTE interface to be shared 
-- amongst a number of Protocol Ports. This allows separate Virtual 
-- Routers to share the same physical X.25 connection into a Wide 
-- Area Network.

x25DteRg OBJECT IDENTIFIER ::= { x25Dte 7 }



x25DteRgRowStatusTable OBJECT-TYPE
   SYNTAX     SEQUENCE OF X25DteRgRowStatusEntry
   ACCESS     not-accessible
   STATUS     mandatory
   DESCRIPTION
     "This entry controls the addition and deletion of 
      x25DteRg components."
::= { x25DteRg 1 }

x25DteRgRowStatusEntry OBJECT-TYPE
   SYNTAX     X25DteRgRowStatusEntry
   ACCESS     not-accessible
   STATUS     mandatory
   DESCRIPTION
     "A single entry in the table represents a single 
      x25DteRg component."
   INDEX {
      x25DteIndex,
      x25DteRgIndex }
::= { x25DteRgRowStatusTable 1 }

X25DteRgRowStatusEntry ::= SEQUENCE {
   x25DteRgRowStatus
      RowStatus,
   x25DteRgComponentName
      DisplayString,
   x25DteRgStorageType
      StorageType,
   x25DteRgIndex
      Integer32 }

x25DteRgRowStatus OBJECT-TYPE
   SYNTAX     RowStatus 
   ACCESS     read-write
   STATUS     mandatory
   DESCRIPTION
     "This variable is used as the basis for SNMP naming of
      x25DteRg components.
      These components can be added and deleted."
::= { x25DteRgRowStatusEntry 1 }

x25DteRgComponentName OBJECT-TYPE
   SYNTAX     DisplayString 
   ACCESS     read-only
   STATUS     mandatory
   DESCRIPTION
     "This variable provides the component's string name for
      use with the ASCII Console Interface"
::= { x25DteRgRowStatusEntry 2 }

x25DteRgStorageType OBJECT-TYPE
   SYNTAX     StorageType 
   ACCESS     read-only
   STATUS     mandatory
   DESCRIPTION
     "This variable represents the storage type value for the
      x25DteRg tables."
::= { x25DteRgRowStatusEntry 4 }

x25DteRgIndex OBJECT-TYPE
   SYNTAX     Integer32 (1..1023)
   ACCESS     not-accessible
   STATUS     mandatory
   DESCRIPTION
     "This variable represents the index for the x25DteRg tables."
::= { x25DteRgRowStatusEntry 10 }

x25DteRgIfEntryTable OBJECT-TYPE
   SYNTAX     SEQUENCE OF X25DteRgIfEntryEntry
   ACCESS     not-accessible
   STATUS     mandatory
   DESCRIPTION
     "This group contains the provisionable attributes for the ifEntry."
::= { x25DteRg 10 }

x25DteRgIfEntryEntry OBJECT-TYPE
   SYNTAX     X25DteRgIfEntryEntry
   ACCESS     not-accessible
   STATUS     mandatory
   DESCRIPTION
     "An entry in the x25DteRgIfEntryTable."
   INDEX {
      x25DteIndex,
      x25DteRgIndex }
::= { x25DteRgIfEntryTable 1 }

X25DteRgIfEntryEntry ::= SEQUENCE {
   x25DteRgIfAdminStatus
      INTEGER,
   x25DteRgIfIndex
      InterfaceIndex }

x25DteRgIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { x25DteRgIfEntryEntry 1 }

x25DteRgIfIndex OBJECT-TYPE
   SYNTAX     InterfaceIndex (1..65535)
   ACCESS     read-only
   STATUS     mandatory
   DESCRIPTION
     "This is the index for the IfEntry. Its value is automatically initialized 
      during the provisioning process."
::= { x25DteRgIfEntryEntry 2 }

x25DteRgProvTable OBJECT-TYPE
   SYNTAX     SEQUENCE OF X25DteRgProvEntry
   ACCESS     not-accessible
   STATUS     mandatory
   DESCRIPTION
     "This group contains the provisionable attributes of the 
      RemoteGroup component."
::= { x25DteRg 11 }

x25DteRgProvEntry OBJECT-TYPE
   SYNTAX     X25DteRgProvEntry
   ACCESS     not-accessible
   STATUS     mandatory
   DESCRIPTION
     "An entry in the x25DteRgProvTable."
   INDEX {
      x25DteIndex,
      x25DteRgIndex }
::= { x25DteRgProvTable 1 }

X25DteRgProvEntry ::= SEQUENCE {
   x25DteRgLinkToProtocolPort
      Link,
   x25DteRgLocalAddress
      DigitString,
   x25DteRgMtuSize
      Unsigned32 }

x25DteRgLinkToProtocolPort OBJECT-TYPE
   SYNTAX     Link 
   ACCESS     read-write
   STATUS     mandatory
   DESCRIPTION
     "This attribute contains a protocol port component name. The 
      attribute associates the application with a protocol port."
::= { x25DteRgProvEntry 1 }

x25DteRgLocalAddress OBJECT-TYPE
   SYNTAX     DigitString (SIZE (1..15))
   ACCESS     read-write
   STATUS     mandatory
   DESCRIPTION
     "This attribute contains the unique X.25 address which identifies this 
      RemoteGroup. It should correspond to the called address in X.25 
      incoming call packets which are to be directed to this 
      RemoteGroup. This allows calls received from the link to be 
      directed to the appropriate RemoteGroup based on the called 
      address in the X.25 call packet. The RemoteGroup components 
      allow the X.25 interface to be shared amongst a number of Protocol 
      Ports (and ultimately Virtual Routers) because each RemoteGroup 
      is coupled with a specific ProtocolPort through its 
      linkToProtocolPort attribute."
::= { x25DteRgProvEntry 2 }

x25DteRgMtuSize OBJECT-TYPE
   SYNTAX     Unsigned32 (576..9188)
   ACCESS     read-write
   STATUS     mandatory
   DESCRIPTION
     "This attribute specifies the Maximum Transmit Unit (MTU); that is, 
      the size of the largest datagram (in octets) which can be sent/
      received on the interface."
   DEFVAL     { 1600 }
::= { x25DteRgProvEntry 3 }

x25DteRgStateTable OBJECT-TYPE
   SYNTAX     SEQUENCE OF X25DteRgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { x25DteRg 12 }

x25DteRgStateEntry OBJECT-TYPE
   SYNTAX     X25DteRgStateEntry
   ACCESS     not-accessible
   STATUS     mandatory
   DESCRIPTION
     "An entry in the x25DteRgStateTable."
   INDEX {
      x25DteIndex,
      x25DteRgIndex }
::= { x25DteRgStateTable 1 }

X25DteRgStateEntry ::= SEQUENCE {
   x25DteRgAdminState
      INTEGER,
   x25DteRgOperationalState
      INTEGER,
   x25DteRgUsageState
      INTEGER }

x25DteRgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { x25DteRgStateEntry 1 }

x25DteRgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { x25DteRgStateEntry 2 }

x25DteRgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { x25DteRgStateEntry 3 }

x25DteRgOperStatusTable OBJECT-TYPE
   SYNTAX     SEQUENCE OF X25DteRgOperStatusEntry
   ACCESS     not-accessible
   STATUS     mandatory
   DESCRIPTION
     "This group includes the Operational Status attribute. This attribute 
      defines the current operational state of this component."
::= { x25DteRg 13 }

x25DteRgOperStatusEntry OBJECT-TYPE
   SYNTAX     X25DteRgOperStatusEntry
   ACCESS     not-accessible
   STATUS     mandatory
   DESCRIPTION
     "An entry in the x25DteRgOperStatusTable."
   INDEX {
      x25DteIndex,
      x25DteRgIndex }
::= { x25DteRgOperStatusTable 1 }

X25DteRgOperStatusEntry ::= SEQUENCE {
   x25DteRgSnmpOperStatus
      INTEGER }

x25DteRgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { x25DteRgOperStatusEntry 1 }

x25DteRgLTPlcnTable OBJECT-TYPE
   SYNTAX     SEQUENCE OF X25DteRgLTPlcnEntry
   ACCESS     not-accessible
   STATUS     mandatory
   DESCRIPTION
     "This attribute is a list of links to PermLcn components. The set of 
      all Peer and PermLcn components which link to a given 
      RemoteGroup determine the subset of remote hosts which are 
      accessible to a particular Protocol Port (and ultimately a Virtual 
      Router)."
::= { x25DteRg 210 }

x25DteRgLTPlcnEntry OBJECT-TYPE
   SYNTAX     X25DteRgLTPlcnEntry
   ACCESS     not-accessible
   STATUS     mandatory
   DESCRIPTION
     "An entry in the x25DteRgLTPlcnTable."
   INDEX {
      x25DteIndex,
      x25DteRgIndex,
      x25DteRgLTPlcnValue }
::= { x25DteRgLTPlcnTable 1 }

X25DteRgLTPlcnEntry ::= SEQUENCE {
   x25DteRgLTPlcnValue
      Link,
   x25DteRgLTPlcnRowStatus
      RowStatus }

x25DteRgLTPlcnValue OBJECT-TYPE
   SYNTAX     Link 
   ACCESS     read-write
   STATUS     mandatory
   DESCRIPTION
     "This variable represents both the value and the index for the
      x25DteRgLTPlcnTable."
::= { x25DteRgLTPlcnEntry 1 }

x25DteRgLTPlcnRowStatus OBJECT-TYPE
   SYNTAX     RowStatus 
   ACCESS     write-only
   STATUS     mandatory
   DESCRIPTION
     "This variable is used to control the addition and deletion 
      of individual values of the x25DteRgLTPlcnTable."
::= { x25DteRgLTPlcnEntry 2 }

x25DteRgLtPeerTable OBJECT-TYPE
   SYNTAX     SEQUENCE OF X25DteRgLtPeerEntry
   ACCESS     not-accessible
   STATUS     mandatory
   DESCRIPTION
     "This attribute gives a list of links to Peer components. The set of all 
      Peer and PermLcn components which link to a given RemoteGroup 
      determine the subset of remote hosts which are accessible to a 
      particular Protocol Port (and ultimately a Virtual Router)."
::= { x25DteRg 211 }

x25DteRgLtPeerEntry OBJECT-TYPE
   SYNTAX     X25DteRgLtPeerEntry
   ACCESS     not-accessible
   STATUS     mandatory
   DESCRIPTION
     "An entry in the x25DteRgLtPeerTable."
   INDEX {
      x25DteIndex,
      x25DteRgIndex,
      x25DteRgLtPeerValue }
::= { x25DteRgLtPeerTable 1 }

X25DteRgLtPeerEntry ::= SEQUENCE {
   x25DteRgLtPeerValue
      Link,
   x25DteRgLtPeerRowStatus
      RowStatus }

x25DteRgLtPeerValue OBJECT-TYPE
   SYNTAX     Link 
   ACCESS     read-write
   STATUS     mandatory
   DESCRIPTION
     "This variable represents both the value and the index for the
      x25DteRgLtPeerTable."
::= { x25DteRgLtPeerEntry 1 }

x25DteRgLtPeerRowStatus OBJECT-TYPE
   SYNTAX     RowStatus 
   ACCESS     write-only
   STATUS     mandatory
   DESCRIPTION
     "This variable is used to control the addition and deletion 
      of individual values of the x25DteRgLtPeerTable."
::= { x25DteRgLtPeerEntry 2 }

x25DteRgLcnTable OBJECT-TYPE
   SYNTAX     SEQUENCE OF X25DteRgLcnEntry
   ACCESS     not-accessible
   STATUS     mandatory
   DESCRIPTION
     "This attribute lists the Lcn components for the X25Dte, which 
      belong to this RemoteGroup. There is an Lcn component listed here 
      for every lcn connection belonging to this RemoteGroup. The lcns 
      were established using either a Peer component linked to this 
      RemoteGroup (in response to a switched call) or using a PermLcn 
      component linked to this RemoteGroup (a permanent connection)."
::= { x25DteRg 212 }

x25DteRgLcnEntry OBJECT-TYPE
   SYNTAX     X25DteRgLcnEntry
   ACCESS     not-accessible
   STATUS     mandatory
   DESCRIPTION
     "An entry in the x25DteRgLcnTable."
   INDEX {
      x25DteIndex,
      x25DteRgIndex,
      x25DteRgLcnValue }
::= { x25DteRgLcnTable 1 }

X25DteRgLcnEntry ::= SEQUENCE {
   x25DteRgLcnValue
      Integer32 }

x25DteRgLcnValue OBJECT-TYPE
   SYNTAX     Integer32 (1..4095)
   ACCESS     read-only
   STATUS     mandatory
   DESCRIPTION
     "This variable represents both the value and the index for the
      x25DteRgLcnTable."
::= { x25DteRgLcnEntry 1 }




-- 
-- Version and Compliance statements
-- 



-- Object-Group Statement:
-- A list of all current accessible leaf objects.

-- OBJECTS { x25DteHighestTLChannelNumber,
--           x25DtePleStorageType,
--           x25DteOutDataPackets,
--           x25DteLapbCurrentQueueSize,
--           x25DtePeerX25Address,
--           x25DteLapbFramerOverruns,
--           x25DteInRestarts,
--           x25DtePleEncAddrToX25LkupFlrs,
--           x25DteLcnCalledAddress,
--           x25DteRgComponentName,
--           x25DteLcnCallUserData,
--           x25DteT20RestartTimer,
--           x25DteLcnTrnstDlySlctnAInd,
--           x25DteLcnFastSelect,
--           x25DteLapbT2AckDelayTimer,
--           x25DteLcnNetworkUserIdentifier,
--           x25DteLapbFramerFrmToIf,
--           x25DteLcnInWindowSize,
--           x25DteLcnInUknownProtocols,
--           x25DtePLcnInWindowSize,
--           x25DtePeerCallUserData,
--           x25DteOutCallAttempts,
--           x25DtePeerTrnstDlySlctnAInd,
--           x25DteLowestILChannelNumber,
--           x25DteOutThroughputClassSize,
--           x25DtePeerNetworkUserIdentifier,
--           x25DteLapbLastStateChangeReason,
--           x25DteLapbTransmitRejectFrames,
--           x25DteRgSnmpOperStatus,
--           x25DtePeerInWindowSize,
--           x25DteRgIfIndex,
--           x25DteLcnStorageType,
--           x25DteRgLTPlcnValue,
--           x25DteT22ResetTimer,
--           x25DteRgLtPeerRowStatus,
--           x25DteLapbFramerNormPrioLinkUtilToIf,
--           x25DteInActiveChannels,
--           x25DtePLcnStorageType,
--           x25DteHighestOLChannelNumber,
--           x25DteLcnInRmtInitiatedRsts,
--           x25DteLapbFramerStorageType,
--           x25DteInCallRefusals,
--           x25DteRgLtPeerValue,
--           x25DteLcnAdminState,
--           x25DteLapbFramerCrcErrors,
--           x25DteCallUserData,
--           x25DteLcnRpoa,
--           x25DteLapbActionRecvDM,
--           x25DteLapbStationType,
--           x25DtePLcnEncAddress,
--           x25DteLapbFramerAdminState,
--           x25DtePleLastFailedEncAddr,
--           x25DteRgRowStatus,
--           x25DteLcnInThroughputClassSize,
--           x25DteTrnstDlySlctnAInd,
--           x25DteMaxActiveChannels,
--           x25DteLapbReceiveRejectFrames,
--           x25DtePleX25AddrToEncLkupFlrs,
--           x25DteLcnInInterruptPackets,
--           x25DteLapbRowStatus,
--           x25DteLcnCallingNetworkFax,
--           x25DteInWindowSize,
--           x25DteRgUsageState,
--           x25DteLapbFramerNonOctetErrors,
--           x25DtePLcnInPacketSize,
--           x25DteLcnChargingInformation,
--           x25DteLapbUsageState,
--           x25DteLapbComponentName,
--           x25DteLcnCugoaIndex,
--           x25DtePeerInThroughputClassSize,
--           x25DteRgOperationalState,
--           x25DtePeerInPacketSize,
--           x25DtePeerCallingNetworkFax,
--           x25DteLapbOperationalState,
--           x25DteLcnInDataPackets,
--           x25DtePleComponentName,
--           x25DteStorageType,
--           x25DteLapbTxQDegradeThreshold,
--           x25DteLcnCallDirection,
--           x25DteLcnStatus,
--           x25DteLapbRemoteBusy,
--           x25DtePeerCugoaIndex,
--           x25DtePeerEncAddress,
--           x25DteInRmtInitiatedRsts,
--           x25DtePeerChargingInformation,
--           x25DtePeerAcceptReverseCharging,
--           x25DteAdminState,
--           x25DteLapbStateChanges,
--           x25DteHighestILChannelNumber,
--           x25DteInterfaceState,
--           x25DteIfAdminStatus,
--           x25DteNumberOfPLcn,
--           x25DteLapbN2TransmitLimit,
--           x25DteCustomerIdentifier,
--           x25DteLcnInPrvdrInitiatedRsts,
--           x25DteLapbKWindowSize,
--           x25DteInThroughputClassSize,
--           x25DteLapbFramerFlagsBetweenFrames,
--           x25DtePeerStorageType,
--           x25DteInPacketSize,
--           x25DteInInterruptPackets,
--           x25DtePleLastFailedX25Addr,
--           x25DteCallingNetworkFax,
--           x25DteLcnOutWindowSize,
--           x25DteRgLcnValue,
--           x25DtePeerCalledNetworkFax,
--           x25DteChargingInformation,
--           x25DtePLcnOutWindowSize,
--           x25DteRgLTPlcnRowStatus,
--           x25DteCugoaIndex,
--           x25DteLcnComponentName,
--           x25DteLcnInDataOctets,
--           x25DteAcceptReverseCharging,
--           x25DteInPrvdrInitiatedClrs,
--           x25DteLcnT22ResetTimeouts,
--           x25DtePeerOutWindowSize,
--           x25DtePLcnComponentName,
--           x25DteInPktsAcusdOfPrtclErr,
--           x25DteLapbFramerComponentName,
--           x25DteLapbT1AckTimeout,
--           x25DteTwowayActiveChannels,
--           x25DtePleRowStatus,
--           x25DteLapbFramerUnderruns,
--           x25DteOutActiveChannels,
--           x25DteRgMtuSize,
--           x25DtePeerRpoa,
--           x25DteT21CallTimeouts,
--           x25DteInDataPackets,
--           x25DtePeerLcnValue,
--           x25DtePLcnLinkToRemoteGroup,
--           x25DteCalledNetworkFax,
--           x25DteInPrvdrInitiatedRsts,
--           x25DteLcnOutThroughputClassSize,
--           x25DteLcnCugIndex,
--           x25DteLapbFrmrTransmit,
--           x25DteLcnOutInterruptPackets,
--           x25DteOutWindowSize,
--           x25DteRgStorageType,
--           x25DteLapbFramerFrmFromIf,
--           x25DteLapbTxQResetThreshold,
--           x25DtePLcnOutPacketSize,
--           x25DtePLcnRowStatus,
--           x25DteLapbStorageType,
--           x25DteLowestTLChannelNumber,
--           x25DteRgLocalAddress,
--           x25DtePeerOutThroughputClassSize,
--           x25DteLapbT1AckTimer,
--           x25DteLcnRowStatus,
--           x25DteLapbT4IdleProbeTimer,
--           x25DtePeerCugIndex,
--           x25DteT22ResetTimeouts,
--           x25DteRpoa,
--           x25DtePeerOutPacketSize,
--           x25DteRgIfAdminStatus,
--           x25DteT23ClearTimeouts,
--           x25DteLapbN1FrameSize,
--           x25DteLapbAdminState,
--           x25DteLcnUsageState,
--           x25DteLapbFramerRowStatus,
--           x25DtePacketSequencing,
--           x25DteLapbActionInitiate,
--           x25DteLapbFrmrReceive,
--           x25DtePeerLinkToRemoteGroup,
--           x25DtePeerRowStatus,
--           x25DteLapbFramerUsageState,
--           x25DtePLcnProtocolEncType,
--           x25DteLcnOperationalState,
--           x25DteLapbFramerNormPrioLinkUtilFromIf,
--           x25DtePleInactivityTimer,
--           x25DtePLcnEncAddressType,
--           x25DteT20RestartTimeouts,
--           x25DteLcnOutDataPackets,
--           x25DteComponentName,
--           x25DteLapbFramerInterfaceName,
--           x25DteSnmpOperStatus,
--           x25DtePeerComponentName,
--           x25DteIfIndex,
--           x25DteInterfaceMode,
--           x25DteLapbFramerOperationalState,
--           x25DtePeerEncAddressType,
--           x25DteT21CallTimer,
--           x25DteProposeReverseCharging,
--           x25DteLapbCurrentState,
--           x25DteLcnCallingAddress,
--           x25DteCugIndex,
--           x25DteRgLinkToProtocolPort,
--           x25DteInCalls,
--           x25DteOutPacketSize,
--           x25DteOutInterruptPackets,
--           x25DteLapbFramerLrcErrors,
--           x25DteLcnProposeReverseCharging,
--           x25DtePeerPEncRowStatus,
--           x25DteLcnOriginalCalledAddress,
--           x25DteLapbFramerAborts,
--           x25DteLcnOutPacketSize,
--           x25DteLowestOLChannelNumber,
--           x25DtePeerPEncValue,
--           x25DteRowStatus,
--           x25DteLcnOutDataOctets,
--           x25DteLcnCalledNetworkFax,
--           x25DteRgAdminState,
--           x25DtePeerProposeReverseCharging,
--           x25DteUsageState,
--           x25DteOutCallFailures,
--           x25DteLapbFramerOctetFromIf,
--           x25DteLapbFrameSequencing,
--           x25DteT23ClearTimer,
--           x25DteLcnInPacketSize,
--           x25DteOperationalState }
-- STATUS  mandatory
-- DESCRIPTION
--   "A list of all current accessible leaf objects."

x25DteGroup OBJECT IDENTIFIER ::= { x25DteMIB 1 }
x25DteGroupBE OBJECT IDENTIFIER ::= { x25DteGroup 5 }
x25DteGroupBE00 OBJECT IDENTIFIER ::= { x25DteGroupBE 1 }
x25DteGroupBE00A OBJECT IDENTIFIER ::= { x25DteGroupBE00 2 }



-- Agent-Capabilities Statement:

-- PRODUCT-RELEASE "Passport Release 7.0 X25Dte."
-- STATUS          mandatory
-- DESCRIPTION     "X25Dte MIB: MIB Version BE00A,
--                  Software Version BG00S4C."
-- SUPPORTS        Nortel-Magellan-Passport-X25DteMIB
--    INCLUDES     { x25DteGroupBE00A }

x25DteCapabilities OBJECT IDENTIFIER ::= { x25DteMIB 3 }
x25DteCapabilitiesBE OBJECT IDENTIFIER ::= { x25DteCapabilities 5 }
x25DteCapabilitiesBE00 OBJECT IDENTIFIER ::= { x25DteCapabilitiesBE 1 }
x25DteCapabilitiesBE00A OBJECT IDENTIFIER ::= { x25DteCapabilitiesBE00 2 }





END
