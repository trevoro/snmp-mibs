-- *****************************************************************
-- Unisphere-Data-BRIDGE-ETHERNET-MIB
--
-- Unisphere Networks Inc. Enterprise MIB
-- BRIDGE ETHERNET MIB
--
-- Copyright (c) 1998, 1999 Redstone Communications, Incorporated.
-- Copyright (c) 1999, 2002 Unisphere Networks, Incorporated.
-- All Rights Reserved.
-- *****************************************************************

Unisphere-Data-BRIDGE-ETHERNET-MIB DEFINITIONS ::= BEGIN

IMPORTS
    MODULE-IDENTITY, OBJECT-TYPE
        FROM SNMPv2-SMI

    RowStatus
        FROM SNMPv2-TC

    MODULE-COMPLIANCE, OBJECT-GROUP
        FROM SNMPv2-CONF

    InterfaceIndex, InterfaceIndexOrZero
        FROM IF-MIB

    usDataMibs
        FROM Unisphere-Data-MIBs

    UsdNextIfIndex
        FROM Unisphere-Data-TC;


usdBridgeEthernetMIB  MODULE-IDENTITY
    LAST-UPDATED "200009261443Z" -- 26-Sep-00 10:43 AM EDT
    ORGANIZATION "Unisphere Networks, Inc."
    CONTACT-INFO
        "       Unisphere Networks, Inc.
        Postal: 10 Technology Park Drive
                Westford MA  01886
                USA
        Tel:    +1 978 589 5800
        Email:  mib@UnisphereNetworks.com" 
    DESCRIPTION
        "The Bridge Ethernet MIB for the Unisphere Networks Inc.
        enterprise."
    -- Revision History
    REVISION      "200009261443Z" -- 26-Sep-00 10:43 AM EDT  kwc
    DESCRIPTION
        "Make it SMIv2 conformant."
    REVISION      "200003272345Z" -- 27-Mar-00 6:45 PM EST
    DESCRIPTION
        "Obsolete usdBridgedEthProxyArp."
    REVISION      "9912101830Z" -- 10-Dec-99 1:30 PM EST
    DESCRIPTION
        "Initial version of this MIB module."
    ::= { usDataMibs 31 }

-- ++++++++++++++++++++++++++++++++++++++++++++++++++++++++++++++++++++++
-- Textual conventions
-- ++++++++++++++++++++++++++++++++++++++++++++++++++++++++++++++++++++++

-- No textual conventions are defined in this MIB.


-- ++++++++++++++++++++++++++++++++++++++++++++++++++++++++++++++++++++++
-- Managed objects
-- ++++++++++++++++++++++++++++++++++++++++++++++++++++++++++++++++++++++

usdBridgedEthernetObjects     OBJECT IDENTIFIER ::= { usdBridgeEthernetMIB 1 }

-- 
-- This MIB contains managed objects for the bridged Ethernet
-- sublayer interface.
--
-- Management objects are provided to query for an available
-- interface index, and to create/delete interfaces of that type.
-- Creating/deleting these interface types using this MIB has the
-- side effect of creating/deleting corresponding entries in the
-- Interface MIB ifTable/ifXTable, and in the Unisphere Enterprise
-- Interface MIB usdIfTable.
--

usdBridgedEthernetIfLayer    OBJECT IDENTIFIER ::= { usdBridgedEthernetObjects 1 }

-- //////////////////////////////////////////////////////////////////////
--
-- Bridged Ethernet Interface Layer
--
-- This layer is managed with the following elements:
--
--  o NextIfIndex (generator for Bridged Ethernet IfIndex selection)
--  o Interface Table (creation/configuration/deletion of Bridged Ethernet
--    interfaces)
--
-- //////////////////////////////////////////////////////////////////////

--
-- IfIndex selection for creating new Brdiged Ethernet interfaces
--

usdBridgedEthernetNextIfIndex OBJECT-TYPE
    SYNTAX      UsdNextIfIndex
    MAX-ACCESS  read-only
    STATUS      current
    DESCRIPTION
        "Coordinate ifIndex value allocation for entries
        in usdBridgedEthernetIfTable.

        A GET of this object returns the next available ifIndex 
        value to be used to create an entry in the associated
        interface table; or zero, if no valid ifIndex value is
        available. This object also returns a value of zero when 
        it is the lexicographic successor of a varbind presented 
        in an SNMP GETNEXT or GETBULK request, for which circumstance
        it is assumed that ifIndex allocation is unintended.

        Successive GETs will typically return different
        values, thus avoiding collisions among cooperating
        management clients seeking to create table entries
        simultaneously.
        "
    ::= { usdBridgedEthernetIfLayer 1 }

--
-- The Bridged Ethernet Interface Table
--

usdBridgedEthernetIfTable OBJECT-TYPE
    SYNTAX      SEQUENCE OF UsdBridgedEthernetIfEntry
    MAX-ACCESS  not-accessible
    STATUS      current
    DESCRIPTION
        "The parameters for the BridgedEthernet service on this interface."

    ::= { usdBridgedEthernetIfLayer 2 }

usdBridgedEthernetIfEntry OBJECT-TYPE
    SYNTAX      UsdBridgedEthernetIfEntry
    MAX-ACCESS  not-accessible
    STATUS      current
    DESCRIPTION
        "The Parameters for a particular Bridged Ethernet interface. 

        Creating/deleting entries in this table causes corresponding 
        entries for be created/deleted in ifTable/ifXTable/usdIfTable"

    INDEX   { usdBridgedEthernetIfIfIndex }
    ::= { usdBridgedEthernetIfTable 1 }

UsdBridgedEthernetIfEntry ::= SEQUENCE {
    usdBridgedEthernetIfIfIndex                InterfaceIndex,
    usdBridgedEthernetProxyArp                 INTEGER, 
    usdBridgedEthernetIfLowerIfIndex           InterfaceIndexOrZero,
    usdBridgedEthernetIfRowStatus              RowStatus
}

usdBridgedEthernetIfIfIndex OBJECT-TYPE
    SYNTAX      InterfaceIndex
    MAX-ACCESS  read-only
    STATUS      current
    DESCRIPTION
        "The ifIndex value of the corresponding ifEntry."
    ::= { usdBridgedEthernetIfEntry 1 }

usdBridgedEthernetProxyArp OBJECT-TYPE
    SYNTAX     INTEGER {enableRestricted(1),
                        enableUnrestricted(2),
                        disable(3) }
    MAX-ACCESS  read-create
    STATUS      obsolete
    DESCRIPTION
        "The proxyArp configuration setting for this entry.
        
        *** NOTE: This MIB object has been obsoleted. ***"
    DEFVAL { enableRestricted }
    ::= { usdBridgedEthernetIfEntry 2 }

usdBridgedEthernetIfLowerIfIndex OBJECT-TYPE
    SYNTAX      InterfaceIndexOrZero
    MAX-ACCESS  read-create
    STATUS      current
    DESCRIPTION
        "The ifIndex of an interface over which this Bridged Ethernet
        interface is to be layered. A value of zero indicates no layering.
        An implementation may choose to require that a nonzero value
        be configured at entry creation."
    ::= { usdBridgedEthernetIfEntry 3 }

usdBridgedEthernetIfRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            usdBridgedEthernetIfRowStatus
            usdBridgedEthernetIfLowerIfIndex

        In addition, when creating an entry the following
        conditions must hold:

            A value for usdBridgedEthernetIfIndex must have been determined
            previously, by reading usdBridgedEthernetNextIfIndex. 

            The interface identified by usdBridgedEthernetIfLowerIfIndex
            must exist, and must be an interface type that
            permits layering of Bridged Ethernet above it.

        A corresponding entry in ifTable/ifXTable/usdIfTable is 
        created/destroyed as a result of creating/destroying an entry 
        in this table. "

    ::= { usdBridgedEthernetIfEntry 4 }


-- ++++++++++++++++++++++++++++++++++++++++++++++++++++++++++++++++++++++
-- Notification control objects
-- ++++++++++++++++++++++++++++++++++++++++++++++++++++++++++++++++++++++

-- No notifications are defined in this MIB. Placeholder follows.

-- usdBridgeEthernetTrapControl OBJECT IDENTIFIER ::= { usdBridgeEthernetMIB 2 }


-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdBridgedEthernetTraps  OBJECT IDENTIFIER ::= { usdBridgeEthernetMIB 3 }
-- usdBridgeEthernetPrefix  OBJECT IDENTIFIER ::= { usdBridgeEthernetTraps 0 }


-- ++++++++++++++++++++++++++++++++++++++++++++++++++++++++++++++++++++++
-- Conformance information
-- ++++++++++++++++++++++++++++++++++++++++++++++++++++++++++++++++++++++

usdBridgeEthernetConformance
    OBJECT IDENTIFIER ::= { usdBridgeEthernetMIB 4 }
usdBridgeEthernetCompliances
    OBJECT IDENTIFIER ::= { usdBridgeEthernetConformance 1 }
usdBridgeEthernetGroups
    OBJECT IDENTIFIER ::= { usdBridgeEthernetConformance 2 }

-- compliance statements

usdBridgedEthernetCompliance MODULE-COMPLIANCE
    STATUS      current
    DESCRIPTION
        "The compliance statement for entities which implement the Unisphere
        bridged Ethernet MIB."
    MODULE  -- this module
        MANDATORY-GROUPS { usdBridgedEthernetGroup2 }
    ::= { usdBridgeEthernetCompliances 1 }

-- units of conformance

usdBridgedEthernetGroup OBJECT-GROUP
    OBJECTS {
        usdBridgedEthernetNextIfIndex,
        usdBridgedEthernetIfIfIndex,
        usdBridgedEthernetProxyArp,
        usdBridgedEthernetIfLowerIfIndex,
        usdBridgedEthernetIfRowStatus }
    STATUS      obsolete
    DESCRIPTION
        "A collection of objects providing management of Bridged Ethernet
        interfaces in a Unisphere product.  This group became obsolete when
        usdBridgedEthernetProxyArp was made obsolete."
    ::= { usdBridgeEthernetGroups 1 }

usdBridgedEthernetGroup2 OBJECT-GROUP
    OBJECTS {
        usdBridgedEthernetNextIfIndex,
        usdBridgedEthernetIfIfIndex,
        usdBridgedEthernetIfLowerIfIndex,
        usdBridgedEthernetIfRowStatus }
    STATUS      current
    DESCRIPTION
        "A collection of objects providing management of Bridged Ethernet
        interfaces in a Unisphere product."
    ::= { usdBridgeEthernetGroups 2 }

END
