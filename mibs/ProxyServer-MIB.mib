ProxyServer-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        proxyServer     OBJECT IDENTIFIER ::= { internetServer 11 }
        proxyStatistics OBJECT IDENTIFIER ::= { proxyServer 1 }

-- Proxy Server Statistics
	totalInetBytesSent OBJECT-TYPE
		SYNTAX	Counter
		ACCESS	read-only
		STATUS	mandatory
		DESCRIPTION 
			"The rate at which data bytes are sent by the Web Proxy service to remote servers on the Internet, or to a chained upstream proxy."
		::= { proxyStatistics 1 }

	totalInetBytesRecvd OBJECT-TYPE
		SYNTAX	Counter
		ACCESS	read-only
		STATUS	mandatory
		DESCRIPTION 
			"The rate at which data bytes are received by the Web Proxy service from remote servers on the Internet, or from a chained upstream proxy, in response to requests from the Web Proxy service."
		::= { proxyStatistics 2 }

	totalInetBytes OBJECT-TYPE
		SYNTAX	Counter
		ACCESS	read-only
		STATUS	mandatory
		DESCRIPTION 
			"The total rate for all bytes transferred between ISA Server and remote servers on the Internet, or a chained upstream proxy."
		::= { proxyStatistics 3 }

	totalClntBytesSent OBJECT-TYPE
		SYNTAX	Counter
		ACCESS	read-only
		STATUS	mandatory
		DESCRIPTION 
			"The rate at which data bytes are sent by the Web Proxy service to Web Proxy clients."
		::= { proxyStatistics 4 }

	totalClntBytesRecvd OBJECT-TYPE
		SYNTAX	Counter
		ACCESS	read-only
		STATUS	mandatory
		DESCRIPTION 
			"The rate at which data bytes are received by the Web Proxy service from Web Proxy clients."
		::= { proxyStatistics 5 }

	totalClntBytes OBJECT-TYPE
		SYNTAX	Counter
		ACCESS	read-only
		STATUS	mandatory
		DESCRIPTION 
			"The sum of Client Bytes Sent/sec and Client Bytes Received/sec. This is the total rate for all bytes transferred between the Web Proxy service and Web Proxy clients."
		::= { proxyStatistics 6 }

	totalSSLClntBytesSent OBJECT-TYPE
		SYNTAX	Counter
		ACCESS	read-only
		STATUS	mandatory
		DESCRIPTION 
			"The rate at which Secure Sockets Layer (SSL) data bytes are sent by the Web Proxy service to secured Web Proxy clients."
		::= { proxyStatistics 7 }

	totalSSLClntBytesRecvd OBJECT-TYPE
		SYNTAX	Counter
		ACCESS	read-only
		STATUS	mandatory
		DESCRIPTION 
			"The rate at which Secure Sockets Layer (SSL) data bytes are received by the Web Proxy service from secured Web Proxy clients."
		::= { proxyStatistics 8 }

	totalSSLClntBytes OBJECT-TYPE
		SYNTAX	Counter
		ACCESS	read-only
		STATUS	mandatory
		DESCRIPTION 
			"The sum of SSL Client Bytes Sent/sec and Bytes Received/sec. This is the total rate for all bytes transferred between the Web Proxy service and secured Web Proxy clients."
		::= { proxyStatistics 9 }

	currentUsers OBJECT-TYPE
		SYNTAX	INTEGER
		ACCESS	read-only
		STATUS	mandatory
		DESCRIPTION 
			"The number of users currently connected to the Web Proxy service."
		::= { proxyStatistics 10 }

	totalUsers OBJECT-TYPE
		SYNTAX	Counter
		ACCESS	read-only
		STATUS	mandatory
		DESCRIPTION 
			"The total number of users that have ever connected to the Web Proxy service."
		::= { proxyStatistics 11 }

	maxUsers OBJECT-TYPE
		SYNTAX	Counter
		ACCESS	read-only
		STATUS	mandatory
		DESCRIPTION 
			"The maximum number of users that have connected to the Web Proxy service simultaneously."
		::= { proxyStatistics 12 }

	ftpRequests OBJECT-TYPE
		SYNTAX	Counter
		ACCESS	read-only
		STATUS	mandatory
		DESCRIPTION 
			"The number of Ftp requests that have been made to the Web Proxy service."
		::= { proxyStatistics 13 }

	gopherRequests OBJECT-TYPE
		SYNTAX	Counter
		ACCESS	read-only
		STATUS	mandatory
		DESCRIPTION 
			"The number of Gopher requests that have been made to the Web Proxy service."
		::= { proxyStatistics 14 }

	httpRequests OBJECT-TYPE
		SYNTAX	Counter
		ACCESS	read-only
		STATUS	mandatory
		DESCRIPTION 
			"The number of Http requests that have been made to the Web Proxy service."
		::= { proxyStatistics 15 }

	totalRequests OBJECT-TYPE
		SYNTAX	Counter
		ACCESS	read-only
		STATUS	mandatory
		DESCRIPTION 
			"The total number of requests that have ever been made to the Web Proxy service."
		::= { proxyStatistics 16 }

	totalSuccRequests OBJECT-TYPE
		SYNTAX	Counter
		ACCESS	read-only
		STATUS	mandatory
		DESCRIPTION 
			"The total number of requests that have been successfully processed by the Web Proxy service."
		::= { proxyStatistics 17 }

	totalFailRequests OBJECT-TYPE
		SYNTAX	Counter
		ACCESS	read-only
		STATUS	mandatory
		DESCRIPTION 
			"The total number of requests that have failed to be processed due to errors.  Errors can be the result of the Web Proxy service failing to locate a requested server URL on the Internet or because of the Web Proxy client being denied access to the requested URL."
		::= { proxyStatistics 18 }

	totalCacheFetches OBJECT-TYPE
		SYNTAX	Counter
		ACCESS	read-only
		STATUS	mandatory
		DESCRIPTION 
			"The total number of Web Proxy client requests that have been served by using data from the ISA Server cache."
		::= { proxyStatistics 19 }

	totalInetFetches OBJECT-TYPE
		SYNTAX	Counter
		ACCESS	read-only
		STATUS	mandatory
		DESCRIPTION 
			"The total number of requests that have been served by using data retrieved from remote servers on the Internet or from a chained upstream ISA Server computer."
		::= { proxyStatistics 20 }

	cacheHitRatio OBJECT-TYPE
		SYNTAX	Counter
		ACCESS	read-only
		STATUS	mandatory
		DESCRIPTION 
			"The percentage of Web Proxy client requests that have been served using cached data, out of the total number of Web Proxy client requests to the ISA Server."
		::= { proxyStatistics 21 }

	cacheRunningHitRatio OBJECT-TYPE
		SYNTAX	Counter
		ACCESS	read-only
		STATUS	mandatory
		DESCRIPTION 
			"The percentage of Web Proxy client requests that have been served using cached data out of the total number of Web Proxy client requests to the ISA Server, for the last 10,000 requests serviced."
		::= { proxyStatistics 22 }

	totalSitesDenied OBJECT-TYPE
		SYNTAX	Counter
		ACCESS	read-only
		STATUS	mandatory
		DESCRIPTION 
			"The total number of Internet sites to which the Web Proxy service has denied access."
		::= { proxyStatistics 23 }

	totalSitesGranted OBJECT-TYPE
		SYNTAX	Counter
		ACCESS	read-only
		STATUS	mandatory
		DESCRIPTION 
			"The total number of Internet sites to which the Web Proxy service has granted access."
		::= { proxyStatistics 24 }

	dnsCacheEntries OBJECT-TYPE
		SYNTAX	Counter
		ACCESS	read-only
		STATUS	mandatory
		DESCRIPTION 
			"The current number of DNS domain name entries cached as a result of Web Proxy service activity."
		::= { proxyStatistics 25 }

	dnsCacheRetrievals OBJECT-TYPE
		SYNTAX	Counter
		ACCESS	read-only
		STATUS	mandatory
		DESCRIPTION 
			"The total number of DNS domain names that have been retrieved by the Web Proxy service."
		::= { proxyStatistics 26 }

	dnsCacheFlushes OBJECT-TYPE
		SYNTAX	Counter
		ACCESS	read-only
		STATUS	mandatory
		DESCRIPTION 
			"The total number of times that the DNS domain name cache has been flushed or cleared by the Web Proxy service."
		::= { proxyStatistics 27 }

	dnsCacheHits OBJECT-TYPE
		SYNTAX	Counter
		ACCESS	read-only
		STATUS	mandatory
		DESCRIPTION 
			"The total number of times a DNS domain name was found within the DNS Cache by the Web Proxy service."
		::= { proxyStatistics 28 }

	dnsCacheRatio OBJECT-TYPE
		SYNTAX	Counter
		ACCESS	read-only
		STATUS	mandatory
		DESCRIPTION 
			"The percentage of DNS domain names served by the DNS cache, out of a total of all DNS entries that have been retrieved by the Web Proxy service."
		::= { proxyStatistics 29 }

	httpsSessions OBJECT-TYPE
		SYNTAX	Counter
		ACCESS	read-only
		STATUS	mandatory
		DESCRIPTION 
			"The total number of HTTP-secured sessions serviced by the Secure Sockets Layer (SSL) tunnel."
		::= { proxyStatistics 30 }

	snewsSessions OBJECT-TYPE
		SYNTAX	Counter
		ACCESS	read-only
		STATUS	mandatory
		DESCRIPTION 
			"The total number of SNEWS sessions serviced by the Secure Sockets Layer (SSL) tunnel."
		::= { proxyStatistics 31 }

	sslSessions OBJECT-TYPE
		SYNTAX	Counter
		ACCESS	read-only
		STATUS	mandatory
		DESCRIPTION 
			"The total number of unknown Secure Sockets Layer (SSL) sessions serviced by the SSL tunnel."
		::= { proxyStatistics 32 }

	sslTotalSessions OBJECT-TYPE
		SYNTAX	Counter
		ACCESS	read-only
		STATUS	mandatory
		DESCRIPTION 
			"The total number of Secure Sockets Layer (SSL) sessions serviced by the SSL tunnel."
		::= { proxyStatistics 33 }

	threadPoolSize OBJECT-TYPE
		SYNTAX	Counter
		ACCESS	read-only
		STATUS	mandatory
		DESCRIPTION 
			"The number of threads in the thread pool."
		::= { proxyStatistics 34 }

	threadPoolFailures OBJECT-TYPE
		SYNTAX	Counter
		ACCESS	read-only
		STATUS	mandatory
		DESCRIPTION 
			"The number of requests rejected because the thread pool was overcommitted."
		::= { proxyStatistics 35 }

	poolSessions OBJECT-TYPE
		SYNTAX	INTEGER
		ACCESS	read-only
		STATUS	mandatory
		DESCRIPTION 
			"The number of sessions being actively serviced by thread pool threads."
		::= { proxyStatistics 36 }

	totalArrayBytesSent OBJECT-TYPE
		SYNTAX	Counter
		ACCESS	read-only
		STATUS	mandatory
		DESCRIPTION 
			"The rate at which data bytes are sent by the ISA Server to other servers within the same array."
		::= { proxyStatistics 37 }

	totalArrayBytesRecvd OBJECT-TYPE
		SYNTAX	Counter
		ACCESS	read-only
		STATUS	mandatory
		DESCRIPTION 
			"The rate at which data bytes are received by the ISA Server from other servers within the same array in response to requests from the Web Proxy service."
		::= { proxyStatistics 38 }

	totalArrayBytes OBJECT-TYPE
		SYNTAX	Counter
		ACCESS	read-only
		STATUS	mandatory
		DESCRIPTION 
			"The sum of Array Bytes Sent/sec and Bytes Received/sec. This is the total rate for all bytes transferred between the ISA Server and other members of the same array."
		::= { proxyStatistics 39 }

	totalProcessingTime OBJECT-TYPE
		SYNTAX	Counter
		ACCESS	read-only
		STATUS	mandatory
		DESCRIPTION 
			"The mean number of milliseconds required to service a Web Proxy client request (not including requests serviced by the Secure Sockets Layer tunnel)."
		::= { proxyStatistics 40 }

	totalArrayFetches OBJECT-TYPE
		SYNTAX	Counter
		ACCESS	read-only
		STATUS	mandatory
		DESCRIPTION 
			"The total number of Web Proxy client requests that have been serviced by requesting the data from another ISA Server within the array."
		::= { proxyStatistics 41 }

	totalReverseBytesSent OBJECT-TYPE
		SYNTAX	Counter
		ACCESS	read-only
		STATUS	mandatory
		DESCRIPTION 
			"The rate at which data bytes are sent by the Web Proxy service to Web publishing servers in response to incoming Web requests."
		::= { proxyStatistics 42 }

	totalReverseBytesRecvd OBJECT-TYPE
		SYNTAX	Counter
		ACCESS	read-only
		STATUS	mandatory
		DESCRIPTION 
			"The rate at which data bytes are received by the Web Proxy service from Web publishing servers in response to incoming Web requests."
		::= { proxyStatistics 43 }

	totalReverseBytes OBJECT-TYPE
		SYNTAX	Counter
		ACCESS	read-only
		STATUS	mandatory
		DESCRIPTION 
			"The sum of Reverse Bytes Sent/sec and Bytes Received/sec. This is the total rate for all bytes transferred between the ISA Server and Web publishing servers in response to incoming Web requests."
		::= { proxyStatistics 44 }

	totalReverseFetches OBJECT-TYPE
		SYNTAX	Counter
		ACCESS	read-only
		STATUS	mandatory
		DESCRIPTION 
			"The total number of incoming Web requests that have been serviced by using data retrieved from Web publishing servers."
		::= { proxyStatistics 45 }

	totalPendingConnects OBJECT-TYPE
		SYNTAX	Counter
		ACCESS	read-only
		STATUS	mandatory
		DESCRIPTION 
			"The total number of pending connects."
		::= { proxyStatistics 46 }

	totalMemberProcessingTime OBJECT-TYPE
		SYNTAX	Counter
		ACCESS	read-only
		STATUS	mandatory
		DESCRIPTION 
			"The mean number of milliseconds required to service a Web Proxy client request that is fetched through another array member (not including requests serviced by the Secure Sockets Layer tunnel)."
		::= { proxyStatistics 47 }

	totalDirectProcessingTime OBJECT-TYPE
		SYNTAX	Counter
		ACCESS	read-only
		STATUS	mandatory
		DESCRIPTION 
			"The mean number of milliseconds required to service a Web Proxy client request directly to the Web server or Upstream proxy (not including requests serviced by the Secure Sockets Layer tunnel)."
		::= { proxyStatistics 48 }

	totalCacheProcessingTime OBJECT-TYPE
		SYNTAX	Counter
		ACCESS	read-only
		STATUS	mandatory
		DESCRIPTION 
			"The mean number of milliseconds required to service a Web Proxy client request from cache (not including requests serviced by the Secure Sockets Layer tunnel)."
		::= { proxyStatistics 49 }


END
