-- Documents: 285-532-1.

EICON-MIB-TRACE DEFINITIONS  ::=  BEGIN


IMPORTS
	TimeTicks, enterprises
		FROM RFC1155-SMI
	OBJECT-TYPE
		FROM RFC-1212
	DisplayString
		FROM RFC1213-MIB;

eicon           OBJECT IDENTIFIER  ::= { enterprises 434 }
management      OBJECT IDENTIFIER  ::= { eicon 2 }
mibv2           OBJECT IDENTIFIER  ::= { management 2 }
module          OBJECT IDENTIFIER  ::= { mibv2 4 }


 ActionState ::= INTEGER {
	done (1),
	failed (2),
	in-progress (3)
	}

-- Used to indicate that corresponding control parameters are invalid
ControlOnOff ::= INTEGER {
	stop (1),
	start (2),
	invalid (3)
	}

CardRef ::= INTEGER (1..6)      -- EiconCard reference on the server.

PortRef ::= INTEGER (1..48)     -- Port reference on the server.

PositiveInteger ::= INTEGER (0..2147483647)


trace   OBJECT IDENTIFIER ::= { module 15 }

--      The trace MIB contains configuration information about the traces.
--      It is composed of one table with rows for each configured trace. Each row corresponds to one 
--      protocol and one set of trace parameters.  If the parameters of a given row are activated, the 
--      trace is started and written to the file. 

--      Definitions

traceFreeEntryIndex     OBJECT-TYPE
	SYNTAX  PositiveInteger
	ACCESS  read-only
	STATUS  mandatory
	DESCRIPTION
		"The number indicating to the Manager the first available index for the new Entry in the 
		traceTable.  The Manager will first get this value from the Agent and then use it to 
		attempt to create an entry with that index value."
	::= { trace 1 }

traceControlTable       OBJECT-TYPE
	SYNTAX  SEQUENCE OF TraceControlEntry 
	ACCESS  not-accessible
	STATUS  mandatory
	DESCRIPTION     
		"Trace control paramters table, one row per port.
		All parameters in this table have read-write access and have to be set before the trace         
		can be started."
	::= { trace 2 }

traceControlEntry       OBJECT-TYPE
	SYNTAX  TraceControlEntry
	ACCESS  not-accessible
	STATUS  mandatory
	DESCRIPTION
		"The set of attributes for each port."
	INDEX           { traceCntrlIndex }
	::= { traceControlTable 1 }

TraceControlEntry ::= SEQUENCE {
	traceCntrlIndex
		PositiveInteger,
	traceCntrlEntryStatus
		INTEGER,
	traceCntrlEntryOwner
		DisplayString,
	traceCntrlProtocol
		INTEGER,
	traceCntrlEntryReclaimTime
		TimeTicks,
	traceCntrlOnOff
		INTEGER,
	traceCntrlActionState
		ActionState,
	traceCntrlActionError
		INTEGER,
	traceCntrlFileName
		DisplayString,
	traceCntrlCardRef
		CardRef,
	traceCntrlPortRef
		PortRef,
	traceCntrlConnectionRef
		INTEGER,
	traceCntrlPURef
		DisplayString,
	traceCntrlModeRef
		DisplayString,
	traceCntrlLURef
		INTEGER,
	traceCntrlStationRef
		INTEGER,
	traceCntrlLLURef
		DisplayString,
	traceCntrlRLURef
		DisplayString,
	traceCntrlOption
		INTEGER,
	traceCntrlPeriod
		INTEGER,
	traceCntrlMask
		INTEGER,
	traceCntrlBufSize
		INTEGER,
	traceCntrlEntrySize
		INTEGER,
	traceCntrlBufFullAction
		INTEGER,
	traceCntrlReadFromEntryIndex
		INTEGER,
	traceCntrlFileType
		INTEGER
	}

traceCntrlIndex OBJECT-TYPE
	SYNTAX  PositiveInteger
	ACCESS  read-only
	STATUS  mandatory
	DESCRIPTION     
		"Index of the table"
	::= { traceControlEntry 1 }

traceCntrlEntryStatus   OBJECT-TYPE
	SYNTAX  INTEGER {
		invalid (1),
		create (2),
		valid (3)
		}
	ACCESS  read-write
	STATUS  mandatory
	DESCRIPTION     
		"Status of this entry in the table"
	::= { traceControlEntry 2 }

traceCntrlEntryOwner    OBJECT-TYPE
	SYNTAX  DisplayString (SIZE(0..16))
	ACCESS  read-write
	STATUS  mandatory
	DESCRIPTION     
		"Owner of entry"
	::= { traceControlEntry 3 }

traceCntrlProtocol      OBJECT-TYPE
	SYNTAX  INTEGER {
		x25 (1),
		sdlc (2),
		frelay (3),
		hdlc (4),
		xportiso (5),
		xporttgx (6),
		llc (7),
		sna (8),
		ppp (9),
		snafr (10)
		}
	ACCESS  read-write
	STATUS  mandatory
	DESCRIPTION     
		"The Protocol to trace"
	::= { traceControlEntry 4 }

traceCntrlEntryReclaimTime      OBJECT-TYPE
	SYNTAX  TimeTicks
	ACCESS  read-write
	STATUS  mandatory
	DESCRIPTION     
		"This is the amount of time the the entry is valid. a value
		of 0 means valid forever. default is 1 day ticks"
	::= { traceControlEntry 5 }

traceCntrlOnOff OBJECT-TYPE
	SYNTAX  INTEGER {
		start (1),
		read (2),
		stop (3),
		invalid (4)
		}
	ACCESS  read-write
	STATUS  mandatory
	DESCRIPTION     
		"The start/stop parameter"
	::= { traceControlEntry 6 }

traceCntrlActionState OBJECT-TYPE
	SYNTAX  ActionState
	ACCESS  read-only
	STATUS  mandatory
	DESCRIPTION     
		"Result of the Trace start operation. Management Station
		should read this value after starting the trace to find
		it's status."
	::= { traceControlEntry 7 }

traceCntrlActionError   OBJECT-TYPE
	SYNTAX  INTEGER {
		no-error (1),
		bad-param (2)
		}
	ACCESS  read-only
	STATUS  mandatory
	DESCRIPTION     
		"The error codes if traceStartResult has start-failed"
	::= { traceControlEntry 8 }

traceCntrlFileName      OBJECT-TYPE
	SYNTAX  DisplayString (SIZE (1..128))
	ACCESS  read-write
	STATUS  mandatory
	DESCRIPTION     
		"The trace file name (full).  Has to be provided by the Operator.  
		The Agent will create the file traceFileName."
	::= { traceControlEntry 9 }

traceCntrlCardRef       OBJECT-TYPE
	SYNTAX  CardRef
	ACCESS  read-write
	STATUS  mandatory
	DESCRIPTION     
		"The EiconCard Reference if the traced protocol requires 
		 a card reference."
	::= { traceControlEntry 10 }

traceCntrlPortRef       OBJECT-TYPE
	SYNTAX  PortRef
	ACCESS  read-write
	STATUS  mandatory
	DESCRIPTION     
		"The pointer to the port, the same as hdlcParmPortRef from the 
		hdlcParmTable."
	::= { traceControlEntry 11 }

traceCntrlConnectionRef OBJECT-TYPE
	SYNTAX  INTEGER
	ACCESS  read-write
	STATUS  mandatory
	DESCRIPTION     
		"Connection Id reference, for Transport and Frame Relay."
	::= { traceControlEntry 12 }

traceCntrlPURef OBJECT-TYPE
	SYNTAX  DisplayString (SIZE (1..32))
	ACCESS  read-write
	STATUS  mandatory
	DESCRIPTION     
		"PU name for SNA PC."
	::= { traceControlEntry 13 }

traceCntrlModeRef       OBJECT-TYPE
	SYNTAX  DisplayString (SIZE (1..32))
	ACCESS  read-write
	STATUS  mandatory
	DESCRIPTION     
		"Mode reference name for SNA APPC."
	::= { traceControlEntry 14 }

traceCntrlLURef OBJECT-TYPE
	SYNTAX  INTEGER
	ACCESS  read-write
	STATUS  mandatory
	DESCRIPTION     
		"LU reference for SNA PC"
	::= { traceControlEntry 15 }

traceCntrlStationRef    OBJECT-TYPE
	SYNTAX  INTEGER
	ACCESS  read-write
	STATUS  mandatory
	DESCRIPTION     
		"Station reference for SDLC"
	::= { traceControlEntry 16 }

traceCntrlLLURef        OBJECT-TYPE
	SYNTAX  DisplayString (SIZE (1..32))
	ACCESS  read-write
	STATUS  mandatory
	DESCRIPTION     
		"LLU reference."
	::= { traceControlEntry 17 }

traceCntrlRLURef        OBJECT-TYPE
	SYNTAX  DisplayString (SIZE (1..32))
	ACCESS  read-write
	STATUS  mandatory
	DESCRIPTION     
		"RLU reference."
	::= { traceControlEntry 18 }

traceCntrlOption        OBJECT-TYPE
	SYNTAX  INTEGER {
		append (1),
		clear (2)
		}
	ACCESS  read-write
	STATUS  mandatory
	DESCRIPTION     
		"The option to reset the trace buffer"
	::= { traceControlEntry 19 }

traceCntrlPeriod        OBJECT-TYPE
	SYNTAX  INTEGER
	ACCESS  read-write
	STATUS  mandatory
	DESCRIPTION     
		"The time period for the trace, in seconds"
	::= { traceControlEntry 20 }

traceCntrlMask  OBJECT-TYPE
	SYNTAX  INTEGER
	ACCESS  read-write
	STATUS  mandatory
	DESCRIPTION     
		"The filter for the EiconCard trace function.
		The value has to be OR-ed using the following components,
		specific for each protocol.

		hdlc,sdlc:
			nothing (0),
			framesI (1),
			framesRR (2),
			framesRNR&REJ (4),
			framesFRMR&SAMB&DISC&UA(8),             for hdlc only,
			framesFRMR&SNRM&DISC&UA&DM(8),  for sdlc only,
			framesOther (16),       for hdlc only: 
						all frames other than indicated by values 1,2,4 ,8,
			framesXID&Other (16)    for sdlc only: 
						all frames other than indicated by values 1,2,4 ,8

		x.25:
			nothing (0),
			packets-data (1),
			packets-RR&RNR (2),
			packets-Reset&Interrupt (4),
			packets-Call&Clear (8),
			other (16),     all packets other than indicated by values 1,2,4 ,8,

		appc, SNA-FM, SNA-PC:
			nothing (0),
			frames-LU-LU-FMD (1),
			frames-LU-LU-DFC (2),
			frames-LU-LU-SC (4),
			frames-SSCP-LU-FMD (8),
			frames-SSCP-LU-SC (16),
			frames-SSCP-PU-FMD (32),
			frames-SSCP-PU-SC (64).
		"
	::= { traceControlEntry 21 }

traceCntrlBufSize       OBJECT-TYPE
	SYNTAX  INTEGER
	ACCESS  read-write
	STATUS  mandatory
	DESCRIPTION     
		"The size of the trace buffer on the EiconCard"
	::= { traceControlEntry 22 }

traceCntrlEntrySize     OBJECT-TYPE
	SYNTAX  INTEGER
	ACCESS  read-write
	STATUS  mandatory
	DESCRIPTION     
		"The buffer entry truncation length."
	::= { traceControlEntry 23 }

traceCntrlBufFullAction OBJECT-TYPE
	SYNTAX  INTEGER {
		wrap (1),
		stop (2),
		stopAndAlarm (3)
		}
	ACCESS  read-write
	STATUS  mandatory
	DESCRIPTION     
		"The buffer-full action of the EiconCard, wrap or stop and alarm. 
		Only wrap is implemented in this first version."
	::= { traceControlEntry 24 }

traceCntrlReadFromEntryIndex    OBJECT-TYPE
	SYNTAX  INTEGER
	ACCESS  read-write
	STATUS  mandatory
	DESCRIPTION     
		"This parameter is used to indicate to the EiconCard trace function the position in the 	
	buffer when reading the trace buffer.  Used with the GET for traceTable."
	::= { traceControlEntry 25 }

traceCntrlFileType      OBJECT-TYPE
	SYNTAX  INTEGER {
		ascii (1),
		ebcdic (2)
	}
	ACCESS  read-write
	STATUS  mandatory
	DESCRIPTION     
		"  "
	::= { traceControlEntry 26 }


END
