-- MIB generated by miftomib version 1.0a

INTELLANDESKSERVERMANAGER-LOCALRESPONSEAMAPPER-MIB DEFINITIONS ::= BEGIN

IMPORTS
    OBJECT-TYPE
    FROM RFC-1212
    enterprises
    FROM RFC1155-SMI
    DisplayString
    FROM RFC1213-MIB;

DmiInteger			::= INTEGER
DmiDisplaystring	::= DisplayString
DmiDateX			::= OCTET STRING (SIZE (28))
DmiComponentIndex	::= INTEGER

intel                  	OBJECT IDENTIFIER ::= {enterprises 343}
products                OBJECT IDENTIFIER ::= {intel 2}
server-products         OBJECT IDENTIFIER ::= {products 6}
dmtfGroups          	OBJECT IDENTIFIER ::= {server-products 7}


-- SComponentid ::= SEQUENCE {
--	a1Manufacturer                          	DmiDisplaystring,
--	a1Product                               	DmiDisplaystring,
--	a1Version                               	DmiDisplaystring,
--	a1SerialNumber                          	DmiDisplaystring,
--	a1Installation                          	DmiDateX,
--	a1Verify                                	DmiInteger
--}
--
-- tComponentid OBJECT-TYPE
--	SYNTAX		SEQUENCE OF SComponentid
--	ACCESS		not-accessible
--	STATUS		mandatory
--	DESCRIPTION	"This group defines attributes common to all components. This
--group is required."
--	::= {dmtfGroups 1}
--
--eComponentid OBJECT-TYPE
--	SYNTAX		SComponentid
--	ACCESS		not-accessible
--	STATUS		mandatory
--	DESCRIPTION	""
--	INDEX		{DmiComponentIndex}
--	::= {tComponentid 1}
--
--a1Manufacturer OBJECT-TYPE
--	SYNTAX		DmiDisplaystring
--	ACCESS		read-only
--	STATUS		mandatory
--	DESCRIPTION	"The organization that produced this component"
--	::= {eComponentid 1}
--
--a1Product OBJECT-TYPE
--	SYNTAX		DmiDisplaystring
--	ACCESS		read-only
--	STATUS		mandatory
--	DESCRIPTION	"The name of this component or product"
--	::= {eComponentid 2}
--
--a1Version OBJECT-TYPE
--	SYNTAX		DmiDisplaystring
--	ACCESS		read-only
--	STATUS		mandatory
--	DESCRIPTION	"MIF Version"
--	::= {eComponentid 3}
--
--a1SerialNumber OBJECT-TYPE
--	SYNTAX		DmiDisplaystring
--	ACCESS		read-only
--	STATUS		mandatory
--	DESCRIPTION	"The serial number for this component"
--	::= {eComponentid 4}
--
--a1Installation OBJECT-TYPE
--	SYNTAX		DmiDateX
--	ACCESS		read-only
--	STATUS		mandatory
--	DESCRIPTION	"The time and date of the last install of the component on
--this system"
--	::= {eComponentid 5}
--
--a1Verify OBJECT-TYPE
--	SYNTAX		INTEGER {
--		vAnErrorOccurredCheckStatusCode         	(0),
--		vThisComponentDoesNotExist              	(1),
--		vVerificationIsNotSupported             	(2),
--		vReserved                               	(3),
--		vThisComponentExistsButTheFunctionalityI	(4),
--		vThisComponentExistsButTheFunctionality1	(5),
--		vThisComponentExistsAndIsNotFunctioningC	(6),
--		vThisComponentExistsAndIsFunctioningCorr	(7)
--	}
--	ACCESS		read-only
--	STATUS		mandatory
--	DESCRIPTION	"The verification level for this component"
--	::= {eComponentid 6}
--
SNameTable ::= SEQUENCE {
	a2MifId                                 	DmiInteger,
	a2ComponentName                         	DmiDisplaystring
}

tNameTable OBJECT-TYPE
	SYNTAX		SEQUENCE OF SNameTable
	ACCESS		not-accessible
	STATUS		mandatory
	DESCRIPTION	"Maps a component Name to a MIF ID"
	::= {dmtfGroups 5}

eNameTable OBJECT-TYPE
	SYNTAX		SNameTable
	ACCESS		not-accessible
	STATUS		mandatory
	DESCRIPTION	""
	INDEX		{DmiComponentIndex, a2MifId}
	::= {tNameTable 1}

a2MifId OBJECT-TYPE
	SYNTAX		INTEGER {
		vUnknown                                	(0),
		vBaseboard                              	(1),
		vAdaptecScsi                            	(2),
		vMylexRaid                              	(3),
		vNic                                    	(4),
		vUps                                    	(5),
		vSymbiosSdms                            	(6),
		vAmiRaid                                	(7),
		vMylexGamRaid                           	(8),
		vAdaptecCioScsi                         	(9),
		vSymbiosScsi                            	(10),
		vIntelNic                               	(11),
		vTestmif                                	(99)
	}
	ACCESS		read-only
	STATUS		mandatory
	DESCRIPTION	"The MIF Id that corresponds to the component Name. This is
used further in Action Table"
	::= {eNameTable 1}

a2ComponentName OBJECT-TYPE
	SYNTAX		DmiDisplaystring
	ACCESS		read-only
	STATUS		mandatory
	DESCRIPTION	"The component Name that will be matched to a MIF Id"
	::= {eNameTable 2}

SActionsTable ::= SEQUENCE {
	a4RelatedMif                            	DmiInteger,
	a4Group                                 	DmiInteger,
	a4Instance                              	DmiInteger,
	a4Attribute                             	DmiInteger,
	a4Value                                 	DmiInteger,
	a4Severity                              	DmiInteger,
	a4BeepSpeaker                           	DmiInteger,
	a4DisplayAlertMessageOnConsole          	DmiInteger,
	a4LogToDisk                             	DmiInteger,
	a4WriteToLcd                            	DmiInteger,
	a4ShutdownTheOs                         	DmiInteger,
	a4ShutdownAndPowerOffTheSystem          	DmiInteger,
	a4ShutdownAndResetTheSystem             	DmiInteger,
	a4ImmediatePowerOff                     	DmiInteger,
	a4ImmediateReset                        	DmiInteger,
	a4BroadcastMessageOnNetwork             	DmiInteger,
	a4AmsAlertName                          	DmiDisplaystring,
	a4Enabled                               	DmiInteger
}

tActionsTable OBJECT-TYPE
	SYNTAX		SEQUENCE OF SActionsTable
	ACCESS		not-accessible
	STATUS		mandatory
	DESCRIPTION	"LRA Event Response Configuration"
	::= {dmtfGroups 6}

eActionsTable OBJECT-TYPE
	SYNTAX		SActionsTable
	ACCESS		not-accessible
	STATUS		mandatory
	DESCRIPTION	""
	INDEX		{DmiComponentIndex, a4RelatedMif, a4Group, a4Instance, a4Attribute, a4Value, a4Severity}
	::= {tActionsTable 1}

a4RelatedMif OBJECT-TYPE
	SYNTAX		INTEGER {
		vUnknown                                	(0),
		vBaseboard                              	(1),
		vAdaptecScsi                            	(2),
		vMylexRaid                              	(3),
		vNic                                    	(4),
		vUps                                    	(5),
		vSymbiosSdms                            	(6),
		vAmiRaid                                	(7),
		vMylexGamRaid                           	(8),
		vAdaptecCioScsi                         	(9),
		vSymbiosScsi                            	(10),
		vIntelNic                               	(11),
		vTestmif                                	(99)
	}
	ACCESS		read-only
	STATUS		mandatory
	DESCRIPTION	"This field identifies that the row in this group 
corresponds
to BASEBOARD MIF or something else.
This is for a future expansion."
	::= {eActionsTable 1}

a4Group OBJECT-TYPE
	SYNTAX		DmiInteger
	ACCESS		read-only
	STATUS		mandatory
	DESCRIPTION	"This is the Group ID that caused the error."
	::= {eActionsTable 2}

a4Instance OBJECT-TYPE
	SYNTAX		DmiInteger
	ACCESS		read-only
	STATUS		mandatory
	DESCRIPTION	"The Row in the Group that caused the error."
	::= {eActionsTable 3}

a4Attribute OBJECT-TYPE
	SYNTAX		DmiInteger
	ACCESS		read-only
	STATUS		mandatory
	DESCRIPTION	"The Attribute ID (within the Group) that caused the error"
	::= {eActionsTable 4}

a4Value OBJECT-TYPE
	SYNTAX		DmiInteger
	ACCESS		read-only
	STATUS		mandatory
	DESCRIPTION	"The value of the attribute causing the error"
	::= {eActionsTable 5}

a4Severity OBJECT-TYPE
	SYNTAX		DmiInteger
	ACCESS		read-only
	STATUS		mandatory
	DESCRIPTION	"The value of the Error Status attribute from the Error Control
Group"
	::= {eActionsTable 6}

a4BeepSpeaker OBJECT-TYPE
	SYNTAX		DmiInteger
	ACCESS		read-write
	STATUS		mandatory
	DESCRIPTION	"Beep the Speaker on the local Server"
	::= {eActionsTable 7}

a4DisplayAlertMessageOnConsole OBJECT-TYPE
	SYNTAX		DmiInteger
	ACCESS		read-write
	STATUS		mandatory
	DESCRIPTION	"Write a Text message on the local server console"
	::= {eActionsTable 8}

a4LogToDisk OBJECT-TYPE
	SYNTAX		DmiInteger
	ACCESS		read-write
	STATUS		mandatory
	DESCRIPTION	"Log a message into standard system log"
	::= {eActionsTable 9}

a4WriteToLcd OBJECT-TYPE
	SYNTAX		DmiInteger
	ACCESS		read-write
	STATUS		mandatory
	DESCRIPTION	"Write a text message to LCD display on local server"
	::= {eActionsTable 10}

a4ShutdownTheOs OBJECT-TYPE
	SYNTAX		DmiInteger
	ACCESS		read-write
	STATUS		mandatory
	DESCRIPTION	"Shutdown the Operating System"
	::= {eActionsTable 11}

a4ShutdownAndPowerOffTheSystem OBJECT-TYPE
	SYNTAX		DmiInteger
	ACCESS		read-write
	STATUS		mandatory
	DESCRIPTION	"Shutdown the Operating System and then Power Off the machine"
	::= {eActionsTable 12}

a4ShutdownAndResetTheSystem OBJECT-TYPE
	SYNTAX		DmiInteger
	ACCESS		read-write
	STATUS		mandatory
	DESCRIPTION	"Shutdown the Operating System and then do a Hardware Reset"
	::= {eActionsTable 13}

a4ImmediatePowerOff OBJECT-TYPE
	SYNTAX		DmiInteger
	ACCESS		read-write
	STATUS		mandatory
	DESCRIPTION	"Do an immediate Power Off. No attempt is made to shutdown
the OS. Data may be lost"
	::= {eActionsTable 14}

a4ImmediateReset OBJECT-TYPE
	SYNTAX		DmiInteger
	ACCESS		read-write
	STATUS		mandatory
	DESCRIPTION	"Do a hardware reset. No attempt is made to shutdown the OS.
Data may be lost"
	::= {eActionsTable 15}

a4BroadcastMessageOnNetwork OBJECT-TYPE
	SYNTAX		DmiInteger
	ACCESS		read-write
	STATUS		mandatory
	DESCRIPTION	"Broadcast a message on Network. On NetWare, this will be
to Supervisor/Admin. On Windows NT, this will be to everyone in domain. "
	::= {eActionsTable 16}

a4AmsAlertName OBJECT-TYPE
	SYNTAX		DmiDisplaystring
	ACCESS		read-only
	STATUS		mandatory
	DESCRIPTION	"Name of the AMS Alert that will be generated"
	::= {eActionsTable 17}

a4Enabled OBJECT-TYPE
	SYNTAX		DmiInteger
	ACCESS		read-write
	STATUS		mandatory
	DESCRIPTION	"The Flag indicating if the actions are enabled"
	::= {eActionsTable 30}

SActionsTableForStandardIndications ::= SEQUENCE {
	a10RelatedMif                           	DmiInteger,
	a10EventGenerationGroup                 	DmiInteger,
	a10EventType                            	DmiInteger,
	a10Instance                             	DmiInteger,
	a10Reserved1                            	DmiInteger,
	a10Severity                             	DmiInteger,
	a10BeepSpeaker                          	DmiInteger,
	a10DisplayAlertMessageOnConsole         	DmiInteger,
	a10LogToDisk                            	DmiInteger,
	a10WriteToLcd                           	DmiInteger,
	a10ShutdownTheOs                        	DmiInteger,
	a10ShutdownAndPowerOffTheSystem         	DmiInteger,
	a10ShutdownAndResetTheSystem            	DmiInteger,
	a10ImmediatePowerOff                    	DmiInteger,
	a10ImmediateReset                       	DmiInteger,
	a10BroadcastMessageOnNetwork            	DmiInteger,
	a10AmsAlertName                         	DmiDisplaystring,
	a10ImmediateNmi                         	DmiInteger,
	a10Page                                 	DmiInteger,
	a10Email									DmiInteger,
	a10Enabled                              	DmiInteger,
	a10EventSystem                          	DmiInteger,
	a10EventSub-system                      	DmiInteger
}

tActionsTableForStandardIndications OBJECT-TYPE
	SYNTAX		SEQUENCE OF SActionsTableForStandardIndications
	ACCESS		not-accessible
	STATUS		mandatory
	DESCRIPTION	"LRA Event Response Configuration"
	::= {dmtfGroups 7}

eActionsTableForStandardIndications OBJECT-TYPE
	SYNTAX		SActionsTableForStandardIndications
	ACCESS		not-accessible
	STATUS		mandatory
	DESCRIPTION	""
	INDEX		{DmiComponentIndex, a10RelatedMif, a10EventGenerationGroup, a10EventType, a10Instance, a10Reserved, a10Severity, a10EventSystem, a10EventSub-system}
	::= {tActionsTableForStandardIndications 1}

a10RelatedMif OBJECT-TYPE
	SYNTAX		INTEGER {
		vUnknown                                	(0),
		vBaseboard                              	(1),
		vAdaptecScsi                            	(2),
		vMylexRaid                              	(3),
		vNic                                    	(4),
		vUps                                    	(5),
		vSymbiosSdms                            	(6),
		vAmiRaid                                	(7),
		vMylexGamRaid                           	(8),
		vAdaptecCioScsi                         	(9),
		vSymbiosScsi                            	(10),
		vIntelNic                               	(11),
		vTestmif                                	(99)
	}
	ACCESS		read-only
	STATUS		mandatory
	DESCRIPTION	"This field identifies that the row in this group 
corresponds
to BASEBOARD MIF or something else.
"
	::= {eActionsTableForStandardIndications 1}

a10EventGenerationGroup OBJECT-TYPE
	SYNTAX		DmiInteger
	ACCESS		read-only
	STATUS		mandatory
	DESCRIPTION	"This is the Group ID of the Event generation Group sending
the indication."
	::= {eActionsTableForStandardIndications 2}

a10EventType OBJECT-TYPE
	SYNTAX		DmiInteger
	ACCESS		read-only
	STATUS		mandatory
	DESCRIPTION	"This is the ID number for the reported event in the enumeration
list of possible events."
	::= {eActionsTableForStandardIndications 3}

a10Instance OBJECT-TYPE
	SYNTAX		DmiInteger
	ACCESS		read-only
	STATUS		mandatory
	DESCRIPTION	"The Row in the Group that caused the error."
	::= {eActionsTableForStandardIndications 4}

a10Reserved OBJECT-TYPE
	SYNTAX		DmiInteger
	ACCESS		read-only
	STATUS		mandatory
	DESCRIPTION	"This attribute is reserved for future use. "
	::= {eActionsTableForStandardIndications 5}

a10Severity OBJECT-TYPE
	SYNTAX		DmiInteger
	ACCESS		read-only
	STATUS		mandatory
	DESCRIPTION	"The severity of the  Error "
	::= {eActionsTableForStandardIndications 6}

a10BeepSpeaker OBJECT-TYPE
	SYNTAX		DmiInteger
	ACCESS		read-write
	STATUS		mandatory
	DESCRIPTION	"Beep the Speaker on the local Server"
	::= {eActionsTableForStandardIndications 7}

a10DisplayAlertMessageOnConsole OBJECT-TYPE
	SYNTAX		DmiInteger
	ACCESS		read-write
	STATUS		mandatory
	DESCRIPTION	"Write a Text message on the local server console"
	::= {eActionsTableForStandardIndications 8}

a10LogToDisk OBJECT-TYPE
	SYNTAX		DmiInteger
	ACCESS		read-write
	STATUS		mandatory
	DESCRIPTION	"Log a message into standard system log"
	::= {eActionsTableForStandardIndications 9}

a10WriteToLcd OBJECT-TYPE
	SYNTAX		DmiInteger
	ACCESS		read-write
	STATUS		mandatory
	DESCRIPTION	"Write a text message to LCD display on local server"
	::= {eActionsTableForStandardIndications 10}

a10ShutdownTheOs OBJECT-TYPE
	SYNTAX		DmiInteger
	ACCESS		read-write
	STATUS		mandatory
	DESCRIPTION	"Shutdown the Operating System"
	::= {eActionsTableForStandardIndications 11}

a10ShutdownAndPowerOffTheSystem OBJECT-TYPE
	SYNTAX		DmiInteger
	ACCESS		read-write
	STATUS		mandatory
	DESCRIPTION	"Shutdown the Operating System and then Power Off the machine"
	::= {eActionsTableForStandardIndications 12}

a10ShutdownAndResetTheSystem OBJECT-TYPE
	SYNTAX		DmiInteger
	ACCESS		read-write
	STATUS		mandatory
	DESCRIPTION	"Shutdown the Operating System and then do a Hardware Reset"
	::= {eActionsTableForStandardIndications 13}

a10ImmediatePowerOff OBJECT-TYPE
	SYNTAX		DmiInteger
	ACCESS		read-write
	STATUS		mandatory
	DESCRIPTION	"Do an immediate Power Off. No attempt is made to shutdown
the OS. Data may be lost"
	::= {eActionsTableForStandardIndications 14}

a10ImmediateReset OBJECT-TYPE
	SYNTAX		DmiInteger
	ACCESS		read-write
	STATUS		mandatory
	DESCRIPTION	"Do a hardware reset. No attempt is made to shutdown the OS.
Data may be lost"
	::= {eActionsTableForStandardIndications 15}

a10BroadcastMessageOnNetwork OBJECT-TYPE
	SYNTAX		DmiInteger
	ACCESS		read-write
	STATUS		mandatory
	DESCRIPTION	"Broadcast a message on Network. On NetWare, this will be
to Supervisor/Admin. On Windows NT, this will be to everyone in domain. "
	::= {eActionsTableForStandardIndications 16}

a10AmsAlertName OBJECT-TYPE
	SYNTAX		DmiDisplaystring
	ACCESS		read-only
	STATUS		mandatory
	DESCRIPTION	"Name of the AMS Alert that will be generated"
	::= {eActionsTableForStandardIndications 17}

a10ImmediateNmi OBJECT-TYPE
	SYNTAX		DmiInteger
	ACCESS		read-write
	STATUS		mandatory
	DESCRIPTION	"Issue a hardware NMI  (Non-Maskable Interrupt) to the system.On
certain Operating Systems, this will cause a system crash dump. "
	::= {eActionsTableForStandardIndications 18}

a10Page OBJECT-TYPE
	SYNTAX		DmiInteger
	ACCESS		read-write
	STATUS		mandatory
	DESCRIPTION	"Issue a page request"
	::= {eActionsTableForStandardIndications 19}

a10Email OBJECT-TYPE
	SYNTAX		DmiInteger
	ACCESS		read-write
	STATUS		mandatory
	DESCRIPTION	"Send an e-mail Alert"
	::= {eActionsTableForStandardIndications 20}

a10Enabled OBJECT-TYPE
	SYNTAX		DmiInteger
	ACCESS		read-write
	STATUS		mandatory
	DESCRIPTION	"The Flag indicating if the actions are enabled"
	::= {eActionsTableForStandardIndications 30}

a10EventSystem OBJECT-TYPE
	SYNTAX		DmiInteger
	ACCESS		read-only
	STATUS		mandatory
	DESCRIPTION	"The value of Event System attribute in the indication "
	::= {eActionsTableForStandardIndications 31}

a10EventSub-system OBJECT-TYPE
	SYNTAX		DmiInteger
	ACCESS		read-only
	STATUS		mandatory
	DESCRIPTION	"The value of Event Sub-System attribute in the indication
"
	::= {eActionsTableForStandardIndications 32}

--SMiftomib ::= SEQUENCE {
--	a99MibName                              	DmiDisplaystring,
--	a99MibOid                               	DmiDisplaystring,
--	a99DisableTrap                          	DmiInteger
--}
--
--tMiftomib OBJECT-TYPE
--	SYNTAX		SEQUENCE OF SMiftomib
--	ACCESS		not-accessible
--	STATUS		mandatory
--	DESCRIPTION	"This group defines attributes required for DMI to SNMP translati
--n."
--	::= {dmtfGroups 99}
--
--eMiftomib OBJECT-TYPE
--	SYNTAX		SMiftomib
--	ACCESS		not-accessible
--	STATUS		mandatory
--	DESCRIPTION	""
--	INDEX		{DmiComponentIndex}
--	::= {tMiftomib 1}
--
--a99MibName OBJECT-TYPE
--	SYNTAX		DmiDisplaystring
--	ACCESS		read-only
--	STATUS		mandatory
--	DESCRIPTION	"The MIB name that defines this MIF"
--	::= {eMiftomib 1}
--
--a99MibOid OBJECT-TYPE
--	SYNTAX		DmiDisplaystring
--	ACCESS		read-only
--	STATUS		mandatory
--	DESCRIPTION	"The MIB OID that corresponds to this MIF"
--	::= {eMiftomib 2}
--
--a99DisableTrap OBJECT-TYPE
--	SYNTAX		DmiInteger
--	ACCESS		read-write
--	STATUS		mandatory
--	DESCRIPTION	"This attribute can be changed to disable sending oftraps
--from this component"
--	::= {eMiftomib 3}
--
END
