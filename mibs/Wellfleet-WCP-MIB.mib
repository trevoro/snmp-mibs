Wellfleet-WCP-MIB DEFINITIONS ::= BEGIN

-- Created by mdl2asn version 3.1
-- Creation date: Wed Aug 30 16:49:56 EDT 1995


    IMPORTS

      Counter
        FROM RFC1155-SMI
      OBJECT-TYPE
        FROM RFC-1212
      wfCompressionGroup
        FROM Wellfleet-COMMON-MIB;


    wfWcpLineTable OBJECT-TYPE
        SYNTAX	SEQUENCE OF WfWcpLineEntry
        ACCESS	not-accessible
        STATUS	mandatory
        DESCRIPTION
                "The line table contains line entries."
        ::= { wfCompressionGroup 1 }

    wfWcpLineEntry OBJECT-TYPE
        SYNTAX	WfWcpLineEntry
        ACCESS	not-accessible
        STATUS	mandatory
        DESCRIPTION
                "The components of the instance ID of a line entry."
        INDEX	{ wfWcpLineLineNumber,
    		  wfWcpLineLLIndex }
        ::= { wfWcpLineTable 1 }

    WfWcpLineEntry ::= SEQUENCE {
    	    wfWcpLineDelete
    		INTEGER,
    	    wfWcpLineDisable
    		INTEGER,
    	    wfWcpLineLineNumber
    		INTEGER,
    	    wfWcpLineLLIndex
    		INTEGER,
    	    wfWcpLineCompressionMode
    		INTEGER,
    	    wfWcpLineHistorySize
    		INTEGER,
    	    wfWcpLineBufferSize
    		INTEGER,
    	    wfWcpLineEngineType
    		INTEGER,
            wfWcpLineSearchDepth
                INTEGER,
            wfWcpLineFallbackCompressionMode
                INTEGER,
            wfWcpLineClientCompressorRingSize
                INTEGER,
            wfWcpLineClientDecompressorRingSize
                INTEGER
        }

    wfWcpLineDelete OBJECT-TYPE
        SYNTAX	INTEGER {
    		    created(1),
    		    deleted(2)
    		}
        ACCESS	read-write
        STATUS	mandatory
        DESCRIPTION
                "Indicates whether the instance have been created or deleted."
        DEFVAL	{ created }
        ::= { wfWcpLineEntry 1 }

    wfWcpLineDisable OBJECT-TYPE
        SYNTAX	INTEGER {
    		    enabled(1),
    		    disabled(2)
    		}
        ACCESS	read-write
        STATUS	mandatory
        DESCRIPTION
                "Indicates whether the instance have been enabled or disabled."
        DEFVAL	{ enabled }
        ::= { wfWcpLineEntry 2 }

    wfWcpLineLineNumber OBJECT-TYPE
        SYNTAX	INTEGER
        ACCESS	read-only
        STATUS	mandatory
        DESCRIPTION
                "instance ID."
        ::= { wfWcpLineEntry 3 }

    wfWcpLineLLIndex OBJECT-TYPE
        SYNTAX	INTEGER
        ACCESS	read-only
        STATUS	mandatory
        DESCRIPTION
                "instance ID."
        ::= { wfWcpLineEntry 4 }

    wfWcpLineCompressionMode OBJECT-TYPE
        SYNTAX	INTEGER {
    		    cpc(1),
    		    ppc(2)
    		}
        ACCESS	read-write
        STATUS	mandatory
        DESCRIPTION
                "line is relatively noisy."
        DEFVAL	{ cpc }
        ::= { wfWcpLineEntry 5 }

    wfWcpLineHistorySize OBJECT-TYPE
        SYNTAX	INTEGER {
    		    k32(1),
    		    k8(2)
    		}
        ACCESS	read-write
        STATUS	mandatory
        DESCRIPTION
                "line."
        DEFVAL	{ k32 }
        ::= { wfWcpLineEntry 6 }

    wfWcpLineBufferSize OBJECT-TYPE
        SYNTAX	INTEGER {
    		    verylarge(1),
    		    large(2),
    		    normal(3),
    		    none(4)
    		}
        ACCESS	read-write
        STATUS	mandatory
        DESCRIPTION
                "used."
        DEFVAL	{ normal }
        ::= { wfWcpLineEntry 7 }

    wfWcpLineEngineType OBJECT-TYPE
        SYNTAX	INTEGER {
    		    software(1),
    		    hardware(2)
    		}
        ACCESS	read-write
        STATUS	mandatory
        DESCRIPTION
                "Indicates whether to use hardware or software compression"
        DEFVAL	{ software }
        ::= { wfWcpLineEntry 8 }

    wfWcpLineSearchDepth OBJECT-TYPE
        SYNTAX	INTEGER(1..255)
        ACCESS	read-write
        STATUS	mandatory
        DESCRIPTION
                "This attribute is only relevant for HW Compression VCs 
                 configured for CPC, 8K history. It indicates the Search 
                 Depth configured for this line. Increasing this attribute 
                 may allow the user to achieve better Compression ratios. 
                 This however could occur at the expense of throughput 
                 (i.e. you may get better compression ratios, but lower 
                 throughput). Note that this value may be set to 0, if the 
                 user wishes to run their Line in High Speed mode."
        DEFVAL	{ 8 }
        ::= { wfWcpLineEntry 9 }

    wfWcpLineFallbackCompressionMode OBJECT-TYPE
        SYNTAX	INTEGER {
    		    softwarecpc(1),
    		    hardwareppc(2),
                    none(3)
    		}
        ACCESS	read-write
        STATUS	mandatory
        DESCRIPTION
                "This attribute is only relevant for HW Compression VCs 
                 configured for CPC. It indicates what Compression Mode 
                 the user wants All VCs on a line to use, when any VC on 
                 that line is unable to register for HW Compression due 
                 to a lack of physical HW Context memory (Note that only 
                 HW CPC contexts can fail registration in this way)."
        DEFVAL	{ softwarecpc }
        ::= { wfWcpLineEntry 10 }

    wfWcpLineClientCompressorRingSize OBJECT-TYPE
        SYNTAX  INTEGER
        ACCESS  read-write
        STATUS  mandatory
        DESCRIPTION
                "Specifies the client compressor ring size for clients
                 of this line.  The default value is ZERO which will cause
                 the hardware compression to assign the hard coded default
                 value."
        DEFVAL  { 0 }
        ::= { wfWcpLineEntry 11 }

    wfWcpLineClientDecompressorRingSize OBJECT-TYPE
        SYNTAX  INTEGER
        ACCESS  read-write
        STATUS  mandatory
        DESCRIPTION
                "Specifies the client decompressor ring size for clients
                 of this line.  The default value is ZERO which will cause
                 the hardware compression to assign the hard coded default
                 value."
        DEFVAL  { 0 }
        ::= { wfWcpLineEntry 12 }

    wfWcpCircuitTable OBJECT-TYPE
        SYNTAX	SEQUENCE OF WfWcpCircuitEntry
        ACCESS	not-accessible
        STATUS	mandatory
        DESCRIPTION
                "The circuit table contains circuit entries."
        ::= { wfCompressionGroup 2 }

    wfWcpCircuitEntry OBJECT-TYPE
        SYNTAX	WfWcpCircuitEntry
        ACCESS	not-accessible
        STATUS	mandatory
        DESCRIPTION
                "The components of the instance ID of a circuit entry."
        INDEX	{ wfWcpCircuitId }
        ::= { wfWcpCircuitTable 1 }

    WfWcpCircuitEntry ::= SEQUENCE {
    	    wfWcpCircuitDelete
    		INTEGER,
    	    wfWcpCircuitDisable
    		INTEGER,
    	    wfWcpCircuitId
    		INTEGER,
    	    wfWcpCircuitCompressionMode
    		INTEGER,
    	    wfWcpCircuitHistorySize
    		INTEGER,
    	    wfWcpCircuitEngineType
    		INTEGER,
            wfWcpCircuitSearchDepth
                INTEGER, 
	    wfWcpCircuitCompressorOutBytes
    		Counter,
    	    wfWcpCircuitDecompressorOutBytes
    		Counter
        }

    wfWcpCircuitDelete OBJECT-TYPE
        SYNTAX	INTEGER {
    		    created(1),
    		    deleted(2)
    		}
        ACCESS	read-write
        STATUS	mandatory
        DESCRIPTION
                "Indicates whether the instance have been created or deleted."
        DEFVAL	{ created }
        ::= { wfWcpCircuitEntry 1 }

    wfWcpCircuitDisable OBJECT-TYPE
        SYNTAX	INTEGER {
    		    enabled(1),
    		    disabled(2)
    		}
        ACCESS	read-write
        STATUS	mandatory
        DESCRIPTION
                "Indicates whether the instance have been enabled or disabled."
        DEFVAL	{ enabled }
        ::= { wfWcpCircuitEntry 2 }

    wfWcpCircuitId OBJECT-TYPE
        SYNTAX	INTEGER
        ACCESS	read-only
        STATUS	mandatory
        DESCRIPTION
                "Indicates the circuit ID of this entry."
        ::= { wfWcpCircuitEntry 3 }

    wfWcpCircuitCompressionMode OBJECT-TYPE
        SYNTAX	INTEGER {
    		    cpc(1),
    		    ppc(2),
    		    inherit(3)
    		}
        ACCESS	read-write
        STATUS	mandatory
        DESCRIPTION
                "suitable when the line is relatively noisy."
        DEFVAL	{ inherit }
        ::= { wfWcpCircuitEntry 4 }

    wfWcpCircuitHistorySize OBJECT-TYPE
        SYNTAX	INTEGER {
    		    k32(1),
    		    k8(2),
    		    inherit(3)
    		}
        ACCESS	read-write
        STATUS	mandatory
        DESCRIPTION
                "circuit."
        DEFVAL	{ inherit }
        ::= { wfWcpCircuitEntry 5 }

    wfWcpCircuitEngineType OBJECT-TYPE
        SYNTAX	INTEGER {
    		    software(1),
    		    hardware(2),
    		    inherit(3)
    		}
        ACCESS	read-write
        STATUS	mandatory
        DESCRIPTION
                "Indicates whether to use hardware or software compression"
        DEFVAL	{ inherit }
        ::= { wfWcpCircuitEntry 6 }

    wfWcpCircuitSearchDepth OBJECT-TYPE
        SYNTAX	INTEGER(1..256)
        ACCESS	read-write
        STATUS	mandatory
        DESCRIPTION
                "This attribute is only relevant for HW Compression VCs 
                 configured for CPC, 8K history. It indicates the Search 
                 Depth configured for this circuit. Increasing this attribute 
                 may allow the user to achieve better Compression ratios. 
                 This however could occur at the expense of throughput 
                 (i.e. you may get better compression ratios, but lower 
                 throughput). Note that this value may be set to 0, if the 
                 user wishes to run this circuit in High Speed mode.
                 Note that the default value of 256 is actually used to 
                 indicate that that this attribute should be inherited from
                 wfWcpLineEntry MIB & is not a valid search depth value.
                 Valid Search Depth values lie within the 1..255 range."
        DEFVAL	{ 256 }
        ::= { wfWcpCircuitEntry 7 }

    wfWcpCircuitCompressorOutBytes OBJECT-TYPE
        SYNTAX	Counter
        ACCESS	read-only
        STATUS	mandatory
        DESCRIPTION
                "Indicates the number of bytes produced by the compressor."
        ::= { wfWcpCircuitEntry 8 }

    wfWcpCircuitDecompressorOutBytes OBJECT-TYPE
        SYNTAX	Counter
        ACCESS	read-only
        STATUS	mandatory
        DESCRIPTION
                "Indicates the number of bytes produced by the decompressor."
        ::= { wfWcpCircuitEntry 9 }

    wfWcpVcTable OBJECT-TYPE
        SYNTAX	SEQUENCE OF WfWcpVcEntry
        ACCESS	not-accessible
        STATUS	mandatory
        DESCRIPTION
                "The VC table contains VC entries"
        ::= { wfCompressionGroup 3 }

    wfWcpVcEntry OBJECT-TYPE
        SYNTAX	WfWcpVcEntry
        ACCESS	not-accessible
        STATUS	mandatory
        DESCRIPTION
                "The components of the instance ID of a VC entry."
        INDEX	{ wfWcpVcLineNumber,
    		  wfWcpVcLLIndex,
    		  wfWcpVcCircuitId,
    		  wfWcpVcId }
        ::= { wfWcpVcTable 1 }

    WfWcpVcEntry ::= SEQUENCE {
    	    wfWcpVcCompressorState
    		INTEGER,
    	    wfWcpVcDecompressorState
    		INTEGER,
    	    wfWcpVcLineNumber
    		INTEGER,
    	    wfWcpVcLLIndex
    		INTEGER,
    	    wfWcpVcCircuitId
    		INTEGER,
    	    wfWcpVcId
    		INTEGER,
    	    wfWcpVcCompressionMode
    		INTEGER,
    	    wfWcpVcHistorySize
    		INTEGER,
    	    wfWcpVcCompressorInBytes
    		Counter,
    	    wfWcpVcCompressorOutBytes
    		Counter,
    	    wfWcpVcDecompressorInBytes
    		Counter,
    	    wfWcpVcDecompressorOutBytes
    		Counter,
    	    wfWcpVcTxCPCPackets
    		Counter,
    	    wfWcpVcRxCPCPackets
    		Counter,
    	    wfWcpVcTxPPCPackets
    		Counter,
    	    wfWcpVcRxPPCPackets
    		Counter,
    	    wfWcpVcTxAntiExpPackets
    		Counter,
    	    wfWcpVcRxAntiExpPackets
    		Counter,
    	    wfWcpVcTxResetReqs
    		Counter,
    	    wfWcpVcRxResetReqs
    		Counter,
    	    wfWcpVcTxRexmitReqs
    		Counter,
    	    wfWcpVcRxRexmitReqs
    		Counter,
    	    wfWcpVcTxRexmitNaks
    		Counter,
    	    wfWcpVcRxRexmitNaks
    		Counter,
    	    wfWcpVcDataOutOfSeqs
    		Counter,
    	    wfWcpVcRexmitOutOfSeqs
    		Counter,
    	    wfWcpVcRexmitTimeouts
    		Counter,
    	    wfWcpVcExceededKs
    		Counter,
    	    wfWcpVcInvalidOpCodes
    		Counter,
    	    wfWcpVcEngineType
    		INTEGER,
            wfWcpVcSearchDepth
                INTEGER
        }

    wfWcpVcCompressorState OBJECT-TYPE
        SYNTAX	INTEGER {
    		    data(1),
    		    disabled(2),
    		    disconnected(3),
    		    init(4),
    		    nak(5)
    		}
        ACCESS	read-only
        STATUS	mandatory
        DESCRIPTION
                "Indicates the VC compressor state of the WCP logical connection."
        DEFVAL	{ disconnected }
        ::= { wfWcpVcEntry 1 }

    wfWcpVcDecompressorState OBJECT-TYPE
        SYNTAX	INTEGER {
    		    data(1),
    		    disabled(2),
    		    disconnected(3),
    		    init(4),
    		    rexmit(5),
    		    reset(6),
    		    connecting(7),
    		    disconnecting(8)
    		}
        ACCESS	read-only
        STATUS	mandatory
        DESCRIPTION
                "Indicates the VC decompressor state of the WCP logical connection."
        DEFVAL	{ disconnected }
        ::= { wfWcpVcEntry 2 }

    wfWcpVcLineNumber OBJECT-TYPE
        SYNTAX	INTEGER
        ACCESS	read-only
        STATUS	mandatory
        DESCRIPTION
                "instance ID."
        ::= { wfWcpVcEntry 3 }

    wfWcpVcLLIndex OBJECT-TYPE
        SYNTAX	INTEGER
        ACCESS	read-only
        STATUS	mandatory
        DESCRIPTION
                "instance ID."
        ::= { wfWcpVcEntry 4 }

    wfWcpVcCircuitId OBJECT-TYPE
        SYNTAX	INTEGER
        ACCESS	read-only
        STATUS	mandatory
        DESCRIPTION
                "ID."
        ::= { wfWcpVcEntry 5 }

    wfWcpVcId OBJECT-TYPE
        SYNTAX	INTEGER
        ACCESS	read-only
        STATUS	mandatory
        DESCRIPTION
                "Indicates the ID of this VC entry. This is part of the instance ID."
        ::= { wfWcpVcEntry 6 }

    wfWcpVcCompressionMode OBJECT-TYPE
        SYNTAX	INTEGER {
    		    cpc(1),
    		    ppc(2)
    		}
        ACCESS	read-only
        STATUS	mandatory
        DESCRIPTION
                "line is relatively noisy."
        ::= { wfWcpVcEntry 7 }

    wfWcpVcHistorySize OBJECT-TYPE
        SYNTAX	INTEGER {
    		    k32(1),
    		    k8(2)
    		}
        ACCESS	read-only
        STATUS	mandatory
        DESCRIPTION
                "VC. HIGH will allow the highest compression ratio to be realized."
        ::= { wfWcpVcEntry 8 }

    wfWcpVcCompressorInBytes OBJECT-TYPE
        SYNTAX	Counter
        ACCESS	read-only
        STATUS	mandatory
        DESCRIPTION
                "Indicates the number of bytes submitted to the compressor."
        ::= { wfWcpVcEntry 9 }

    wfWcpVcCompressorOutBytes OBJECT-TYPE
        SYNTAX	Counter
        ACCESS	read-only
        STATUS	mandatory
        DESCRIPTION
                "Indicates the number of bytes produced by the compressor."
        ::= { wfWcpVcEntry 10 }

    wfWcpVcDecompressorInBytes OBJECT-TYPE
        SYNTAX	Counter
        ACCESS	read-only
        STATUS	mandatory
        DESCRIPTION
                "Indicates the number of bytes submitted to the decompressor."
        ::= { wfWcpVcEntry 11 }

    wfWcpVcDecompressorOutBytes OBJECT-TYPE
        SYNTAX	Counter
        ACCESS	read-only
        STATUS	mandatory
        DESCRIPTION
                "Indicates the number of bytes produced by the decompressor."
        ::= { wfWcpVcEntry 12 }

    wfWcpVcTxCPCPackets OBJECT-TYPE
        SYNTAX	Counter
        ACCESS	read-only
        STATUS	mandatory
        DESCRIPTION
                "Indicates the number of continuous mode packets sent."
        ::= { wfWcpVcEntry 13 }

    wfWcpVcRxCPCPackets OBJECT-TYPE
        SYNTAX	Counter
        ACCESS	read-only
        STATUS	mandatory
        DESCRIPTION
                "Indicates the number of continuous mode packets received."
        ::= { wfWcpVcEntry 14 }

    wfWcpVcTxPPCPackets OBJECT-TYPE
        SYNTAX	Counter
        ACCESS	read-only
        STATUS	mandatory
        DESCRIPTION
                "Indicates the number of PPC mode packets sent."
        ::= { wfWcpVcEntry 15 }

    wfWcpVcRxPPCPackets OBJECT-TYPE
        SYNTAX	Counter
        ACCESS	read-only
        STATUS	mandatory
        DESCRIPTION
                "Indicates the number of PPC mode packets Received."
        ::= { wfWcpVcEntry 16 }

    wfWcpVcTxAntiExpPackets OBJECT-TYPE
        SYNTAX	Counter
        ACCESS	read-only
        STATUS	mandatory
        DESCRIPTION
                "Indicates the number of anti-expanded packets sent."
        ::= { wfWcpVcEntry 17 }

    wfWcpVcRxAntiExpPackets OBJECT-TYPE
        SYNTAX	Counter
        ACCESS	read-only
        STATUS	mandatory
        DESCRIPTION
                "Indicates the number of anti-expanded packets received."
        ::= { wfWcpVcEntry 18 }

    wfWcpVcTxResetReqs OBJECT-TYPE
        SYNTAX	Counter
        ACCESS	read-only
        STATUS	mandatory
        DESCRIPTION
                "Indicates the number of reset request sent."
        ::= { wfWcpVcEntry 19 }

    wfWcpVcRxResetReqs OBJECT-TYPE
        SYNTAX	Counter
        ACCESS	read-only
        STATUS	mandatory
        DESCRIPTION
                "Indicates the number of reset request received."
        ::= { wfWcpVcEntry 20 }

    wfWcpVcTxRexmitReqs OBJECT-TYPE
        SYNTAX	Counter
        ACCESS	read-only
        STATUS	mandatory
        DESCRIPTION
                "Indicates the number of re-transmit request sent."
        ::= { wfWcpVcEntry 21 }

    wfWcpVcRxRexmitReqs OBJECT-TYPE
        SYNTAX	Counter
        ACCESS	read-only
        STATUS	mandatory
        DESCRIPTION
                "Indicates the number of re-transmit request received."
        ::= { wfWcpVcEntry 22 }

    wfWcpVcTxRexmitNaks OBJECT-TYPE
        SYNTAX	Counter
        ACCESS	read-only
        STATUS	mandatory
        DESCRIPTION
                "Indicates the number of re-transmit Nak sent."
        ::= { wfWcpVcEntry 23 }

    wfWcpVcRxRexmitNaks OBJECT-TYPE
        SYNTAX	Counter
        ACCESS	read-only
        STATUS	mandatory
        DESCRIPTION
                "Indicates the number of re-transmit Nak received."
        ::= { wfWcpVcEntry 24 }

    wfWcpVcDataOutOfSeqs OBJECT-TYPE
        SYNTAX	Counter
        ACCESS	read-only
        STATUS	mandatory
        DESCRIPTION
                "Indicates the number of times that a data indication is out of sequence."
        ::= { wfWcpVcEntry 25 }

    wfWcpVcRexmitOutOfSeqs OBJECT-TYPE
        SYNTAX	Counter
        ACCESS	read-only
        STATUS	mandatory
        DESCRIPTION
                "Indicates the number of times that a re-transmit Ack is out of sequence."
        ::= { wfWcpVcEntry 26 }

    wfWcpVcRexmitTimeouts OBJECT-TYPE
        SYNTAX	Counter
        ACCESS	read-only
        STATUS	mandatory
        DESCRIPTION
                "Indicates the number of re-transmit timeout."
        ::= { wfWcpVcEntry 27 }

    wfWcpVcExceededKs OBJECT-TYPE
        SYNTAX	Counter
        ACCESS	read-only
        STATUS	mandatory
        DESCRIPTION
                "Indicates the number of times that K is exceeded."
        ::= { wfWcpVcEntry 28 }

    wfWcpVcInvalidOpCodes OBJECT-TYPE
        SYNTAX	Counter
        ACCESS	read-only
        STATUS	mandatory
        DESCRIPTION
                "Indicates the number of packets received with invalid op code."
        ::= { wfWcpVcEntry 29 }

    wfWcpVcEngineType OBJECT-TYPE
        SYNTAX	INTEGER {
    		    software(1),
    		    hardware(2),
                    none(3)
    		}
        ACCESS	read-only
        STATUS	mandatory
        DESCRIPTION
                "Indicates whether hardware or software compression is used"
        ::= { wfWcpVcEntry 30 }

    wfWcpVcSearchDepth OBJECT-TYPE
        SYNTAX	INTEGER 
        ACCESS	read-only
        STATUS	mandatory
        DESCRIPTION
                "This attribute is only relevant for HW Compression VCs 
                 configured for CPC, 8K history. It indicates the Search 
                 Depth configured for this VC. Increasing this attribute 
                 may allow the user to achieve better Compression ratios. 
                 This however could occur at the expense of throughput 
                 (i.e. you may get better compression ratios, but lower 
                 throughput). Note that this value may be  0, if the user 
                 wishes to run  their VC in High Speed Mode."
        ::= { wfWcpVcEntry 31 }

    wfHwCompTable OBJECT-TYPE
        SYNTAX	SEQUENCE OF WfHwCompEntry
        ACCESS	not-accessible
        STATUS	mandatory
        DESCRIPTION
                "The HW Compression Table contains compression entries."
        ::= { wfCompressionGroup 4 }

    wfHwCompEntry OBJECT-TYPE
        SYNTAX	WfHwCompEntry
        ACCESS	not-accessible
        STATUS	mandatory
        DESCRIPTION
                "Slot number used as instance identifier."
        INDEX	{ wfHwCompSlot,
    		  wfHwCompModule,
    		  wfHwCompEngineNumber}
        ::= { wfHwCompTable 1 }

    WfHwCompEntry ::= SEQUENCE {
    	    wfHwCompState
    		INTEGER,
    	    wfHwCompSlot
    		INTEGER,
    	    wfHwCompModule
    		INTEGER,
    	    wfHwCompEngineNumber
    		INTEGER,
    	    wfHwCompCompressionHistoryTotal
    		INTEGER,
    	    wfHwCompCompressionHashTblSize
    		INTEGER,
    	    wfHwCompDecompressionHistoryTotal
    		INTEGER,
    	    wfHwComp8kContextsTotal
    		INTEGER,
    	    wfHwComp32kContextsTotal
    		INTEGER,
     	    wfHwComp8kCpcContextsInUse
     		INTEGER,
     	    wfHwComp8kPpcContextsInUse
    		INTEGER,
    	    wfHwComp32kContextsInUse
    		INTEGER,
    	    wfHwComp8kContextsAvailable
    		INTEGER,
    	    wfHwComp32kContextsAvailable
    		INTEGER,
            wfHwCompCpcContextsRegistered
                INTEGER,
            wfHwCompPpcContextsRegistered
                INTEGER,
            wfHwCompCompressionTotalRingSize
                INTEGER,
            wfHwCompDecompressionTotalRingSize
                INTEGER,
            wfHwCompCompressionCurrentQueued
                INTEGER,
            wfHwCompDecompressionCurrentQueued
                INTEGER,
            wfHwCompCompressionQHiWatermark
                INTEGER,
            wfHwCompDecompressionQHiWatermark
                INTEGER,
    	    wfHwCompCompressionPkts
    		Counter,
    	    wfHwCompDecompressionPkts
    		Counter,
    	    wfHwCompTxExpandedPkts
    		Counter,
            wfHwCompTxNonCompressedPkts
                Counter,
            wfHwCompRxNonCompressedPkts
                Counter,
            wfHwCompRxDroppedPkts
                Counter,
            wfHwCompRxLcbMismatches
                Counter,
            wfHwCompCompressionRingOverflows
                Counter,
            wfHwCompDecompressionRingOverflows
                Counter,
     	    wfHwCompCompressionErrors
    		Counter,
    	    wfHwCompDecompressionErrors
    		Counter,
    	    wfHwCompCompressionSrcPktLenErrors
    		Counter,
    	    wfHwCompCompressionCcbFormatErrors
    		Counter,
    	    wfHwCompCompressionDescFormatErrors
    		Counter,
    	    wfHwCompCompressionInternalErrors
    		Counter,
    	    wfHwCompDecompressionSrcPktLenErrors
    		Counter,
    	    wfHwCompDecompressionCcbFormatErrors
    		Counter,
    	    wfHwCompDecompressionDescFormatErrors
    		Counter,
    	    wfHwCompDecompressionInternalErrors
    		Counter,
            wfHwCompChipType
		INTEGER,
            wfHwCompMsaCpcContextsRegistered
                INTEGER,
            wfHwCompMsaPpcContextsRegistered
                INTEGER,
	    wfHwCompMsa8KContextsGuaranteed
                INTEGER,
            wfHwCompStacContextsTotal
		INTEGER,
            wfHwCompStacCpcContextsRegistered
                INTEGER,
            wfHwCompStacPpcContextsRegistered
                INTEGER,
	    wfHwCompStacPpcContextsInUse
                INTEGER,
	    wfHwCompStacContextsAvailable
                INTEGER,
	    wfHwCompStacContextsGuaranteed
		INTEGER,
    	    wfHwCompMsaCompressedPkts
    		Counter,
    	    wfHwCompStacCompressedPkts
    		Counter,
    	    wfHwCompMsaDecompressedPkts
    		Counter,
    	    wfHwCompStacDecompressedPkts
    		Counter,
    	    wfHwCompMsaTxExpandedPkts
    		Counter,
    	    wfHwCompStacTxExpandedPkts
    		Counter,
            wfHwCompMsaTxNonCompressedPkts
                Counter,
            wfHwCompStacTxNonCompressedPkts
                Counter,
            wfHwCompMsaRxNonCompressedPkts
                Counter,
            wfHwCompStacRxNonCompressedPkts
                Counter
        }

    wfHwCompState OBJECT-TYPE
        SYNTAX	INTEGER {
    		    up(1),
    		    down(2),
    		    init(3)
    		}
        ACCESS	read-only
        STATUS	mandatory
        DESCRIPTION
                "Driver state variable."
        ::= { wfHwCompEntry 1 }

    wfHwCompSlot OBJECT-TYPE
        SYNTAX	INTEGER
        ACCESS	read-only
        STATUS	mandatory
        DESCRIPTION
                "Slot number -- gotten from the instance ID."
        ::= { wfHwCompEntry 2 }

    wfHwCompModule OBJECT-TYPE
        SYNTAX	INTEGER
        ACCESS	read-only
        STATUS	mandatory
        DESCRIPTION
                "Module # -- gotten from the instance ID."
        ::= { wfHwCompEntry 3 }

    wfHwCompEngineNumber OBJECT-TYPE
        SYNTAX	INTEGER
        ACCESS	read-only
        STATUS	mandatory
        DESCRIPTION
                "Compression Engine #. Gotten from the instance ID."
        ::= { wfHwCompEntry 4 }

    wfHwCompCompressionHistoryTotal OBJECT-TYPE
        SYNTAX	INTEGER
        ACCESS	read-only
        STATUS	mandatory
        DESCRIPTION
                "The amount of memory allocated for Compression History."
        ::= { wfHwCompEntry 5 }

    wfHwCompCompressionHashTblSize OBJECT-TYPE
        SYNTAX	INTEGER
        ACCESS	read-only
        STATUS	mandatory
        DESCRIPTION
                "The amount of memory allocated for Compression Hash Tables.
                 These Hash Tables are used to do lookups in Compression
                 History memory."
        ::= { wfHwCompEntry 6 }

    wfHwCompDecompressionHistoryTotal OBJECT-TYPE
        SYNTAX	INTEGER
        ACCESS	read-only
        STATUS	mandatory
        DESCRIPTION
                "The amount of memory allocated for Decompression History."
        ::= { wfHwCompEntry 7 }

    wfHwComp8kContextsTotal OBJECT-TYPE
        SYNTAX	INTEGER
        ACCESS	read-only
        STATUS	mandatory
        DESCRIPTION
                "This indicates the maximum number of 8KB Context Control Blocks (CCBs)
                (i.e. VC's) we can support with this memory configuration. This is
                assuming ALL VC's using Variable Search Depth Mode, 8KB 
                history size. This equals wfHwCompCompressionHistoryTotal 
                divided by 8KB."
        ::= { wfHwCompEntry 8 }

    wfHwComp32kContextsTotal OBJECT-TYPE
        SYNTAX	INTEGER
        ACCESS	read-only
        STATUS	mandatory
        DESCRIPTION
                "This indicates the maximum number of 32KB Context Control Blocks (CCBs)
                (i.e. VC's) we can support with this memory configuration. This is
                assuming ALL VC's using High Speed, Single Search Mode, 32KB 
                history size. This equals wfHwCompCompressionHistoryTotal 
                divided by 32KB."
        ::= { wfHwCompEntry 9 }

    wfHwComp8kCpcContextsInUse OBJECT-TYPE
        SYNTAX	INTEGER
        ACCESS	read-only
        STATUS	mandatory
        DESCRIPTION
                "This indicates the current number of 8KB CPC (Continuous
                 Packet Compression) Mode VC's using Hardware Compression 
                services."
        ::= { wfHwCompEntry 10 }

    wfHwComp8kPpcContextsInUse OBJECT-TYPE
        SYNTAX	INTEGER
        ACCESS	read-only
        STATUS	mandatory
        DESCRIPTION
                "This indicates the number of PPC (Per Packet Compression) 
                 Mode VC's allocated for HW Compression. This value ALWAYS
                 equates to 1, as 1 PPC Context is ALWAYS reserved as a 
                 resource for any VC doing HW Compression to use.

                 All VC's configured to run in PPC Mode share this context.
                 This context is also used when a VC enters Transient PPC
                 Compression Mode, which occurs when frames are dropped
                 or errors occur on the physical link."
        ::= { wfHwCompEntry 11 }

    wfHwComp32kContextsInUse OBJECT-TYPE
        SYNTAX	INTEGER
        ACCESS	read-only
        STATUS	mandatory
        DESCRIPTION
                "This indicates the current number of 32KB Context Control Blocks (CCBs)
                (i.e. VC's) using Hardware Compression services."
        ::= { wfHwCompEntry 12 }

    wfHwComp8kContextsAvailable OBJECT-TYPE
        SYNTAX	INTEGER
        ACCESS	read-only
        STATUS	mandatory
        DESCRIPTION
                "This indicates the number of 'usable' 8k Context Control Blocks available.
                Note that this will get reduced (by 4) when a user configures a VC for
                32KB History Size (i.e. High Speed, Single Search Mode)."
        ::= { wfHwCompEntry 13 }

    wfHwComp32kContextsAvailable OBJECT-TYPE
        SYNTAX	INTEGER
        ACCESS	read-only
        STATUS	mandatory
        DESCRIPTION
                "This indicates the number of 'usable' 32k Context Control Blocks
                available. This means that this/these number of pages of Compression
                Memory currently have NO Context Control Block (i.e.VC) associated
                with them."
        ::= { wfHwCompEntry 14 }

    wfHwCompCpcContextsRegistered OBJECT-TYPE
        SYNTAX	INTEGER
        ACCESS	read-only
        STATUS	mandatory
        DESCRIPTION
                "This indicates the number of VC's which have registered for 
                 HW Compression and are using Continuous Packet Compression 
                 (CPC) mode. Anytime a VC/Context successfully registers with 
                 HW Compression using this mode, a HW context has been 
                 dedicated to that VC."
        ::= { wfHwCompEntry 15 }

    wfHwCompPpcContextsRegistered OBJECT-TYPE
        SYNTAX	INTEGER
        ACCESS	read-only
        STATUS	mandatory
        DESCRIPTION
                "This indicates the number of VC's which have registered 
                 for HW Compression and are using Packet by Packet Compression
                 (PPC) mode. All VCs/Contexts which register using PPC mode, 
                 share 1 HW Context which has been dedicated for use by PPC 
                 Vcs."
        ::= { wfHwCompEntry 16 }

    wfHwCompCompressionTotalRingSize OBJECT-TYPE
        SYNTAX	INTEGER
        ACCESS	read-only
        STATUS	mandatory
        DESCRIPTION
                "This indicates the total number of Descriptor ring entries 
                 available for HW Compression."
        ::= { wfHwCompEntry 17 }

    wfHwCompDecompressionTotalRingSize OBJECT-TYPE
        SYNTAX	INTEGER
        ACCESS	read-only
        STATUS	mandatory
        DESCRIPTION
                "This indicates the total number of Descriptor ring entries 
                 available for HW Decompression."
        ::= { wfHwCompEntry 18 }

    wfHwCompCompressionCurrentQueued OBJECT-TYPE
        SYNTAX	INTEGER
        ACCESS	read-only
        STATUS	mandatory
        DESCRIPTION
                "This is a snapshot of the current number of entries 
                 outstanding on the HW Compression Ring."
        ::= { wfHwCompEntry 19 }

    wfHwCompDecompressionCurrentQueued OBJECT-TYPE
        SYNTAX	INTEGER
        ACCESS	read-only
        STATUS	mandatory
        DESCRIPTION
                "This is a snapshot of the current number of entries 
                 outstanding on the HW Decompression Ring."
        ::= { wfHwCompEntry 20 }

    wfHwCompCompressionQHiWatermark OBJECT-TYPE
        SYNTAX	INTEGER
        ACCESS	read-only
        STATUS	mandatory
        DESCRIPTION
                "This indicates the largest number of frames ever
                 outstanding on the HW Compression Ring since this
                 Compression Engine started providing HW Compression
                 services."
        ::= { wfHwCompEntry 21 }

    wfHwCompDecompressionQHiWatermark OBJECT-TYPE
        SYNTAX	INTEGER
        ACCESS	read-only
        STATUS	mandatory
        DESCRIPTION
                "This indicates the largest number of frames ever
                 outstanding on the HW Decompression Ring since this
                 Compression Engine started providing HW Compression
                 services."
        ::= { wfHwCompEntry 22 }

    wfHwCompCompressionPkts OBJECT-TYPE
        SYNTAX	Counter
        ACCESS	read-only
        STATUS	mandatory
        DESCRIPTION
                "The # of pkts successfully compressed."
        ::= { wfHwCompEntry 23 }

    wfHwCompDecompressionPkts OBJECT-TYPE
        SYNTAX	Counter
        ACCESS	read-only
        STATUS	mandatory
        DESCRIPTION
                "The # of pkts successfully decompressed."
        ::= { wfHwCompEntry 24 }

    wfHwCompTxExpandedPkts OBJECT-TYPE
        SYNTAX	Counter
        ACCESS	read-only
        STATUS	mandatory
        DESCRIPTION
                "The # of pkts given to the Compressor which actually expanded
                 instead of compressing."
        ::= { wfHwCompEntry 25 }

    wfHwCompTxNonCompressedPkts OBJECT-TYPE
        SYNTAX	Counter
        ACCESS	read-only
        STATUS	mandatory
        DESCRIPTION
                "This indicates a temporary Buffer Starvation condition.
                 When we cannot get a buffer to Compress into, this stat
                 gets incremented & the original UnCompressed frame is sent."
        ::= { wfHwCompEntry 26 }

    wfHwCompRxNonCompressedPkts OBJECT-TYPE
        SYNTAX	Counter
        ACCESS	read-only
        STATUS	mandatory
        DESCRIPTION
                "The # of pkts received across the link which happened to
                 come across the link uncompressed. This can be either
                 because the pkt was an Expanded pkt at the remote end or
                 for some reason the sending device could not compress this
                 particular pkt due to resource issues."
        ::= { wfHwCompEntry 27 }

    wfHwCompRxDroppedPkts OBJECT-TYPE
        SYNTAX	Counter
        ACCESS	read-only
        STATUS	mandatory
        DESCRIPTION
                "This indicates a temporary Buffer Starvation condition.
                 When we cannot get a buffer to Decompress into, this stat
                 gets incremented & the received Compressed data frame is
                 run through the Decompressor in order to update the
                 Decompressors histories and then dropped."
        ::= { wfHwCompEntry 28 }

    wfHwCompRxLcbMismatches OBJECT-TYPE
        SYNTAX	Counter
        ACCESS	read-only
        STATUS	mandatory
        DESCRIPTION
                "This indicates a frame was dropped between the remote
                 end and this end. Line errors such as CRC Errors cause
                 this. Buffer starvation in this router can also cause this."
        ::= { wfHwCompEntry 29 }

    wfHwCompCompressionRingOverflows OBJECT-TYPE
        SYNTAX	Counter
        ACCESS	read-only
        STATUS	mandatory
        DESCRIPTION
                "Number of frames dropped due to Compression Descriptor
                 Ring full condition."
        ::= { wfHwCompEntry 30 }

    wfHwCompDecompressionRingOverflows OBJECT-TYPE
        SYNTAX	Counter
        ACCESS	read-only
        STATUS	mandatory
        DESCRIPTION
                "Number of frames dropped due to Decompression Descriptor
                 Ring full condition."
        ::= { wfHwCompEntry 31 }

    wfHwCompCompressionErrors OBJECT-TYPE
        SYNTAX	Counter
        ACCESS	read-only
        STATUS	mandatory
        DESCRIPTION
                "Indicates the total # of Compression Errors detected on this module."
        ::= { wfHwCompEntry 32 }

    wfHwCompDecompressionErrors OBJECT-TYPE
        SYNTAX	Counter
        ACCESS	read-only
        STATUS	mandatory
        DESCRIPTION
                "Indicates the total # of Decompression Errors detected on this module."
        ::= { wfHwCompEntry 33 }

    wfHwCompCompressionSrcPktLenErrors OBJECT-TYPE
        SYNTAX	Counter
        ACCESS	read-only
        STATUS	mandatory
        DESCRIPTION
                "A zero length source packet was received by the Compressor or
                Decompressor."
        ::= { wfHwCompEntry 34 }

    wfHwCompCompressionCcbFormatErrors OBJECT-TYPE
        SYNTAX	Counter
        ACCESS	read-only
        STATUS	mandatory
        DESCRIPTION
                "The format of the specified Context Control Block (CCB) was detected to be
                in error."
        ::= { wfHwCompEntry 35 }

    wfHwCompCompressionDescFormatErrors OBJECT-TYPE
        SYNTAX	Counter
        ACCESS	read-only
        STATUS	mandatory
        DESCRIPTION
                "The format of the current descriptor is in error."
        ::= { wfHwCompEntry 36 }

    wfHwCompCompressionInternalErrors OBJECT-TYPE
        SYNTAX	Counter
        ACCESS	read-only
        STATUS	mandatory
        DESCRIPTION
                "The Compressor or Decompressor took an internal error when processing
                this descriptor."
        ::= { wfHwCompEntry 37 }

    wfHwCompDecompressionSrcPktLenErrors OBJECT-TYPE
        SYNTAX	Counter
        ACCESS	read-only
        STATUS	mandatory
        DESCRIPTION
                "A zero length source packet was received by the Compressor or
                Decompressor."
        ::= { wfHwCompEntry 38 }

    wfHwCompDecompressionCcbFormatErrors OBJECT-TYPE
        SYNTAX	Counter
        ACCESS	read-only
        STATUS	mandatory
        DESCRIPTION
                "The format of the specified Context Control Block (CCB) was detected to be
                in error."
        ::= { wfHwCompEntry 39 }

    wfHwCompDecompressionDescFormatErrors OBJECT-TYPE
        SYNTAX	Counter
        ACCESS	read-only
        STATUS	mandatory
        DESCRIPTION
                "The format of the current descriptor is in error."
        ::= { wfHwCompEntry 40 }

    wfHwCompDecompressionInternalErrors OBJECT-TYPE
        SYNTAX	Counter
        ACCESS	read-only
        STATUS	mandatory
        DESCRIPTION
                "The Compressor or Decompressor took an internal error when processing
                this descriptor."
        ::= { wfHwCompEntry 41 }

   wfHwCompChipType OBJECT-TYPE
        SYNTAX  INTEGER {
		   magna(1),
		   itcs(2)
		}	
        ACCESS  read-only
        STATUS  mandatory
        DESCRIPTION
                "Compression Chip Type: MAGNALINK or ITCS"
        ::= { wfHwCompEntry 42 }

   wfHwCompMsaCpcContextsRegistered OBJECT-TYPE
        SYNTAX  INTEGER
        ACCESS  read-only
        STATUS  mandatory
        DESCRIPTION
                "The number of MSA VC's which have registered for
                 HW Compression and are using Continuous Packet Compression
                 (CPC) mode. Anytime an MSA VC/Context successfully registers with
                 HW Compression using this mode, a HW context has been
                 dedicated to that VC."
        ::= { wfHwCompEntry 43 }

    wfHwCompMsaPpcContextsRegistered OBJECT-TYPE
        SYNTAX  INTEGER
        ACCESS  read-only
        STATUS  mandatory
        DESCRIPTION
                "The number of MSA VC's which have registered
                 for HW Compression and are using Packet by Packet Compression
                 (PPC) mode. All MSA VCs/Contexts which register using PPC mode,
                 share 1 HW Context which has been dedicated for use by PPC
                 Vcs."
        ::= { wfHwCompEntry 44 }

     wfHwCompMsa8KContextsGuaranteed OBJECT-TYPE
        SYNTAX  INTEGER
        ACCESS  read-only
        STATUS  mandatory
        DESCRIPTION
		"The number of 8K MSA contexts reserved with
	 	 a particular memory carving. Calculated as number of pages
		 guaranteed for MSA times 4, where 4 is the maximum number
		 of 8K MSA contexts per page."
        ::= { wfHwCompEntry 45 }

     wfHwCompStacContextsTotal OBJECT-TYPE
        SYNTAX  INTEGER
        ACCESS  read-only
        STATUS  mandatory
        DESCRIPTION
		"The maximum number of STAC CCBs that can be
		 supported for a particular memory carving."
        ::= { wfHwCompEntry 46 }

     wfHwCompStacCpcContextsRegistered OBJECT-TYPE
        SYNTAX  INTEGER
        ACCESS  read-only
        STATUS  mandatory
        DESCRIPTION
                "This indicates the number of STAC VC's which have registered for
                 HW Compression and are using Continuous Packet Compression
                 (CPC) mode. Anytime a STAC VC/Context successfully registers with
                 HW Compression using this mode, a HW context has been
                 dedicated to that VC."
        ::= { wfHwCompEntry 47 }

     wfHwCompStacPpcContextsRegistered OBJECT-TYPE
        SYNTAX  INTEGER
        ACCESS  read-only
        STATUS  mandatory
        DESCRIPTION
                "The number of STAC VC's which have registered
                 for HW Compression and are using Packet by Packet Compression
                 (PPC) mode. All STAC VCs/Contexts which register using PPC mode,
                 share 1 HW Context which has been dedicated for use by PPC
                 Vcs."
        ::= { wfHwCompEntry 48 }

     wfHwCompStacPpcContextsInUse OBJECT-TYPE
        SYNTAX  INTEGER
        ACCESS  read-only
        STATUS  mandatory
        DESCRIPTION
                "The number of STAC contexts allocated for PPC.
		 Equals 1 if STAC is enabled, 0 if it is disabled."
        ::= { wfHwCompEntry 49 }

     wfHwCompStacContextsAvailable  OBJECT-TYPE
        SYNTAX  INTEGER
        ACCESS  read-only
        STATUS  mandatory
        DESCRIPTION
                "The number of 'usable' STAC context control blocks
		 available."
        ::= { wfHwCompEntry 50 }

     wfHwCompStacContextsGuaranteed OBJECT-TYPE
        SYNTAX  INTEGER
        ACCESS  read-only
        STATUS  mandatory
        DESCRIPTION
                "The number of STAC contexts reserved with
                 a particular memory carving. Calculated as number of pages
                 guaranteed for STAC times 8, where 8 is the maximum number
                 of STAC contexts per page."
        ::= { wfHwCompEntry 51 }

    wfHwCompMsaCompressedPkts OBJECT-TYPE
        SYNTAX	Counter
        ACCESS	read-only
        STATUS	mandatory
        DESCRIPTION
                "The # of pkts successfully compressed using MSA compression algorithm."
        ::= { wfHwCompEntry 52 }

    wfHwCompStacCompressedPkts OBJECT-TYPE
        SYNTAX	Counter
        ACCESS	read-only
        STATUS	mandatory
        DESCRIPTION
                "The # of pkts successfully compressed using STAC compression algorithm."
        ::= { wfHwCompEntry 53 }

    wfHwCompMsaDecompressedPkts OBJECT-TYPE
        SYNTAX	Counter
        ACCESS	read-only
        STATUS	mandatory
        DESCRIPTION
                "The # of pkts successfully decompressed using MSA compression algorithm."
        ::= { wfHwCompEntry 54 }

    wfHwCompStacDecompressedPkts OBJECT-TYPE
        SYNTAX	Counter
        ACCESS	read-only
        STATUS	mandatory
        DESCRIPTION
                "The # of pkts successfully decompressed using STAC compression algorithm."
        ::= { wfHwCompEntry 55 }

    wfHwCompMsaTxExpandedPkts OBJECT-TYPE
        SYNTAX	Counter
        ACCESS	read-only
        STATUS	mandatory
        DESCRIPTION
                "The # of pkts given to the Compressor which actually expanded
                 instead of compressing using MSA compression algorithm."
        ::= { wfHwCompEntry 56 }

    wfHwCompStacTxExpandedPkts OBJECT-TYPE
        SYNTAX	Counter
        ACCESS	read-only
        STATUS	mandatory
        DESCRIPTION
                "The # of pkts given to the Compressor which actually expanded
                 instead of compressing using STAC compression algorithm."
        ::= { wfHwCompEntry 57 }

    wfHwCompMsaTxNonCompressedPkts OBJECT-TYPE
        SYNTAX	Counter
        ACCESS	read-only
        STATUS	mandatory
        DESCRIPTION
                "This indicates a temporary Buffer Starvation condition.
                 When we cannot get a buffer to Compress into, this stat
                 gets incremented & the original UnCompressed frame is sent."
        ::= { wfHwCompEntry 58 }

    wfHwCompStacTxNonCompressedPkts OBJECT-TYPE
        SYNTAX	Counter
        ACCESS	read-only
        STATUS	mandatory
        DESCRIPTION
                "This indicates a temporary Buffer Starvation condition.
                 When we cannot get a buffer to Compress into, this stat
                 gets incremented & the original UnCompressed frame is sent."
        ::= { wfHwCompEntry 59 }

    wfHwCompMsaRxNonCompressedPkts OBJECT-TYPE
        SYNTAX	Counter
        ACCESS	read-only
        STATUS	mandatory
        DESCRIPTION
                "The # of pkts received across the link which happened to
                 come across the link uncompressed. This can be either
                 because the pkt was an Expanded pkt at the remote end or
                 for some reason the sending device could not compress this
                 particular pkt due to resource issues."
        ::= { wfHwCompEntry 60 }

    wfHwCompStacRxNonCompressedPkts OBJECT-TYPE
        SYNTAX	Counter
        ACCESS	read-only
        STATUS	mandatory
        DESCRIPTION
                "The # of pkts received across the link which happened to
                 come across the link uncompressed. This can be either
                 because the pkt was an Expanded pkt at the remote end or
                 for some reason the sending device could not compress this
                 particular pkt due to resource issues."
        ::= { wfHwCompEntry 61 }


    wfStacCircuitTable OBJECT-TYPE
        SYNTAX	SEQUENCE OF WfStacCircuitEntry
        ACCESS	not-accessible
        STATUS	mandatory
        DESCRIPTION
                "The circuit table contains circuit entries."
        ::= { wfCompressionGroup 6 }

    wfStacCircuitEntry OBJECT-TYPE
        SYNTAX	WfStacCircuitEntry
        ACCESS	not-accessible
        STATUS	mandatory
        DESCRIPTION
                "The components of the instance ID of a circuit entry."
        INDEX	{ wfStacCircuitId }
        ::= { wfStacCircuitTable 1 }

    WfStacCircuitEntry ::= SEQUENCE {
    	    wfStacCircuitDelete
    		INTEGER,
    	    wfStacCircuitDisable
    		INTEGER,
    	    wfStacCircuitId
    		INTEGER,
    	    wfStacCircuitEngineType
    		INTEGER,
    	    wfStacCircuitCompressionMode
    		INTEGER,
    	    wfStacCircuitCompressorState
    		INTEGER,
    	    wfStacCircuitDecompressorState
    		INTEGER,
            wfStacCircuitFallBackCompressionMode
                INTEGER,
    	    wfStacCircuitCompressorInBytes
    		Counter,
    	    wfStacCircuitCompressorOutBytes
    		Counter,
    	    wfStacCircuitDecompressorInBytes
    		Counter,
    	    wfStacCircuitDecompressorOutBytes
    		Counter,
            wfStacCircuitTxMode0Packets
                Counter,
            wfStacCircuitRxMode0Packets
                Counter,
            wfStacCircuitTxMode3Packets
                Counter,
            wfStacCircuitRxMode3Packets
                Counter,
            wfStacCircuitTxExpPackets
                Counter,
            wfStacCircuitRxExpPackets
                Counter,
            wfStacCircuitTxResetReqs
                Counter,
            wfStacCircuitRxResetReqs
                Counter
    }

    wfStacCircuitDelete OBJECT-TYPE
        SYNTAX	 INTEGER {
    		    created(1),
    		    deleted(2)
    		}
        ACCESS	 read-write
        STATUS 	mandatory
        DESCRIPTION
		 "Indication to delete this Stac LZS/PPP interface"
	 DEFVAL	{ created }
        ::= { wfStacCircuitEntry 1 }

    wfStacCircuitDisable OBJECT-TYPE
        SYNTAX 	INTEGER {
    		    enabled(1),
    		    disabled(2)
    		}
        ACCESS	 read-write
        STATUS	 mandatory
        DESCRIPTION
                "Used to enable and disable compression."
        DEFVAL	{ enabled }
        ::= { wfStacCircuitEntry 2 }

    wfStacCircuitId OBJECT-TYPE
        SYNTAX	 INTEGER
        ACCESS	 read-write
        STATUS	 mandatory
        DESCRIPTION
                "Indicates the circuit ID of this entry."
        ::= { wfStacCircuitEntry 3 }

    wfStacCircuitEngineType OBJECT-TYPE
        SYNTAX	 INTEGER {
    		    software(1),
    		    hardware(2),
    		    inherit(3),
                    none(4)
    		}
        ACCESS	 read-write
        STATUS	 mandatory
        DESCRIPTION
                "Indicates whether to use hardware or software compression"
        DEFVAL	{ software }
        ::= { wfStacCircuitEntry 4 }

    wfStacCircuitCompressionMode OBJECT-TYPE
        SYNTAX	INTEGER {
    		    mode0(1),
    		    mode3(4)
    		}
        ACCESS	read-write
        STATUS	mandatory
        DESCRIPTION
                "Indicates the check mode. See RFC 1974."
        DEFVAL	{ mode3 }
        ::= { wfStacCircuitEntry 5 }

    wfStacCircuitCompressorState OBJECT-TYPE
        SYNTAX	 INTEGER {
                     data(1),
                     disabled(2)
                 }
        ACCESS	 read-only
        STATUS	 mandatory
        DESCRIPTION
                "Indicates the compressor state of this circuit entry."
        DEFVAL	{ disabled }
        ::= { wfStacCircuitEntry 6 }

    wfStacCircuitDecompressorState OBJECT-TYPE
        SYNTAX	 INTEGER {
                     data(1),
                     disabled(2),
                     reset(3)
                 }
        ACCESS	 read-only
        STATUS	 mandatory
        DESCRIPTION
                "Indicates the decompressor state of this circuit entry."
        DEFVAL	{ disabled }
        ::= { wfStacCircuitEntry 7 }

    wfStacCircuitFallBackCompressionMode OBJECT-TYPE
        SYNTAX	INTEGER {
    		    softwarecpc(1),
                    none(2)
    		}
        ACCESS	read-write
        STATUS	mandatory
        DESCRIPTION
                "This attribute is only relevant when any the circuit on 
                 that line is unable to register for HW Compression due 
                 to a lack of physical HW Context memory (Note that only 
                 HW CPC contexts can fail registration in this way)."
        DEFVAL	{ softwarecpc }
        ::= { wfStacCircuitEntry 8 }

    wfStacCircuitCompressorInBytes OBJECT-TYPE
        SYNTAX 	Counter
        ACCESS	 read-only
        STATUS	 mandatory
        DESCRIPTION
                "Indicates the number of bytes submitted to the compressor."
        ::= { wfStacCircuitEntry 9 }

    wfStacCircuitCompressorOutBytes OBJECT-TYPE
        SYNTAX	 Counter
        ACCESS	 read-only
        STATUS	 mandatory
        DESCRIPTION
                "Indicates the number of bytes produced by the compressor."
        ::= { wfStacCircuitEntry 10 }

    wfStacCircuitDecompressorInBytes OBJECT-TYPE
        SYNTAX	 Counter
        ACCESS	 read-only
        STATUS	 mandatory
        DESCRIPTION
                "Indicates the number of bytes submitted to the decompressor."
        ::= { wfStacCircuitEntry 11 }

    wfStacCircuitDecompressorOutBytes OBJECT-TYPE
        SYNTAX	 Counter
        ACCESS	 read-only
        STATUS	 mandatory
        DESCRIPTION
                "Indicates the number of bytes produced by the decompressor."
        ::= { wfStacCircuitEntry 12 }

    wfStacCircuitTxMode0Packets OBJECT-TYPE
        SYNTAX	 Counter
        ACCESS	 read-only
        STATUS	 mandatory
        DESCRIPTION
                "Indicates the number of mode 0 packets sent."
        ::= { wfStacCircuitEntry 13 }

    wfStacCircuitRxMode0Packets OBJECT-TYPE
        SYNTAX	 Counter
        ACCESS	 read-only
        STATUS	 mandatory
        DESCRIPTION
                "Indicates the number of mode 0 packets received."
        ::= { wfStacCircuitEntry 14 }

    wfStacCircuitTxMode3Packets OBJECT-TYPE
        SYNTAX	 Counter
        ACCESS	 read-only
        STATUS	 mandatory
        DESCRIPTION
                "Indicates the number of mode 3 packets sent."
        ::= { wfStacCircuitEntry 15 }

    wfStacCircuitRxMode3Packets OBJECT-TYPE
        SYNTAX	 Counter
        ACCESS	 read-only
        STATUS	 mandatory
        DESCRIPTION
                "Indicates the number of mode 3 packets received."
        ::= { wfStacCircuitEntry 16 }

    wfStacCircuitTxExpPackets OBJECT-TYPE
        SYNTAX	 Counter
        ACCESS	 read-only
        STATUS	 mandatory
        DESCRIPTION
                "Indicates the number of expanded packets sent."
        ::= { wfStacCircuitEntry 17 }

    wfStacCircuitRxExpPackets OBJECT-TYPE
        SYNTAX	 Counter
        ACCESS	 read-only
        STATUS	 mandatory
        DESCRIPTION
                "Indicates the number of expanded packets received."
        ::= { wfStacCircuitEntry 18 }

    wfStacCircuitTxResetReqs OBJECT-TYPE
        SYNTAX	 Counter
        ACCESS	 read-only
        STATUS	 mandatory
        DESCRIPTION
                "Indicates the number of reset requests sent."
        ::= { wfStacCircuitEntry 19 }

    wfStacCircuitRxResetReqs OBJECT-TYPE
        SYNTAX	 Counter
        ACCESS	 read-only
        STATUS	 mandatory
        DESCRIPTION
                "Indicates the number of reset requests received."
        ::= { wfStacCircuitEntry 20 }

    END  -- Wellfleet-WCP-MIB
