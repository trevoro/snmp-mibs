--			Ascend mibwatchdog MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBWATCHDOG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibwatchdogConfigProfile  OBJECT IDENTIFIER ::= { configuration 162}

	-- The mibwatchdogConfigProfile table
	--
	-- This table contains parameters for the mibwatchdogConfigProfile profile
	--

    mibwatchdogConfigProfileTable	OBJECT-TYPE
	SYNTAX		SEQUENCE OF MibwatchdogConfigProfileEntry
	ACCESS		not-accessible
	STATUS		mandatory
	DESCRIPTION	"A list of mibwatchdogConfigProfile profile entries."
	::= { mibwatchdogConfigProfile 1 }

    mibwatchdogConfigProfileEntry	OBJECT-TYPE
	SYNTAX		MibwatchdogConfigProfileEntry
	ACCESS		not-accessible
	STATUS		mandatory
	DESCRIPTION	"A mibwatchdogConfigProfile entry containing objects that
			 maps to the parameters of mibwatchdogConfigProfile profile."
	INDEX		{ watchdogConfigProfile-WatchdogIndex-WatchdogType, watchdogConfigProfile-WatchdogIndex-LocationId, watchdogConfigProfile-WatchdogIndex-Unit }
	::= { mibwatchdogConfigProfileTable 1 }

    MibwatchdogConfigProfileEntry ::=
	SEQUENCE {
	    watchdogConfigProfile-WatchdogIndex-WatchdogType
		INTEGER,
	    watchdogConfigProfile-WatchdogIndex-LocationId
		INTEGER,
	    watchdogConfigProfile-WatchdogIndex-Unit
		INTEGER,
	    watchdogConfigProfile-WatchdogTrapEnable
		INTEGER,
	    watchdogConfigProfile-WatchdogName
		DisplayString,
	    watchdogConfigProfile-Action-o
		INTEGER
	}

    watchdogConfigProfile-WatchdogIndex-WatchdogType	OBJECT-TYPE
	SYNTAX	INTEGER
	ACCESS	read-only
	STATUS	mandatory
	DESCRIPTION	"A number that specifies the type of watchdog."
	::= { mibwatchdogConfigProfileEntry 1 }

    watchdogConfigProfile-WatchdogIndex-LocationId	OBJECT-TYPE
	SYNTAX	INTEGER
	ACCESS	read-only
	STATUS	mandatory
	DESCRIPTION	"location id uniquely identifies the location of a watchdog"
	::= { mibwatchdogConfigProfileEntry 2 }

    watchdogConfigProfile-WatchdogIndex-Unit	OBJECT-TYPE
	SYNTAX	INTEGER
	ACCESS	read-only
	STATUS	mandatory
	DESCRIPTION	"unit no specifies the instance no of a particular type of watchdog It is 1 based."
	::= { mibwatchdogConfigProfileEntry 3 }

    watchdogConfigProfile-WatchdogTrapEnable	OBJECT-TYPE
	SYNTAX	INTEGER {
		    no (1),
		    yes (2)
		}
	ACCESS	read-write
	STATUS	mandatory
	DESCRIPTION	"Enables or disables trap for the specific watchdog. default is yes "
	::= { mibwatchdogConfigProfileEntry 4 }

    watchdogConfigProfile-WatchdogName	OBJECT-TYPE
	SYNTAX	DisplayString
	ACCESS	read-write
	STATUS	mandatory
	DESCRIPTION	"Contains a descriptive name for the watchdog. The watchdog-name is sent to the SNMP manager when the watchdog causes a trap."
	::= { mibwatchdogConfigProfileEntry 5 }

    watchdogConfigProfile-Action-o	OBJECT-TYPE
	SYNTAX	INTEGER {
		    noAction (1),
		    createProfile (2),
		    deleteProfile (3)
		}
	ACCESS	read-write
	STATUS	mandatory
	DESCRIPTION	""
	::= { mibwatchdogConfigProfileEntry 6 }

END
