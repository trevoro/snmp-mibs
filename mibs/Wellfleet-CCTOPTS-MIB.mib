Wellfleet-CCTOPTS-MIB DEFINITIONS ::= BEGIN

-- Created by mdl2asn version 3.1
-- Creation date: Wed Aug 30 16:38:49 EDT 1995


    IMPORTS

      IpAddress, Counter, Gauge
        FROM RFC1155-SMI
      OBJECT-TYPE
        FROM RFC-1212
      DisplayString
        FROM RFC1213-MIB
      wfCircuitOptsGroup
        FROM Wellfleet-COMMON-MIB;


    wfCctOptsTable OBJECT-TYPE
        SYNTAX	SEQUENCE OF WfCctOptsEntry
        ACCESS	not-accessible
        STATUS	mandatory
        DESCRIPTION
                "The table of circuit names"
        ::= { wfCircuitOptsGroup 1 }

    wfCctOptsEntry OBJECT-TYPE
        SYNTAX	WfCctOptsEntry
        ACCESS	not-accessible
        STATUS	mandatory
        DESCRIPTION
                "Entry format for the table of circuit options"
        INDEX	{ wfCctOptsCct }
        ::= { wfCctOptsTable 1 }

    WfCctOptsEntry ::= SEQUENCE {
    	    wfCctOptsDelete
    		INTEGER,
    	    wfCctOptsPriorityQueueingDisable
    		INTEGER,
    	    wfCctOptsCct
    		INTEGER,
    	    wfCctOptsHighPriorityQueueLimit
    		INTEGER,
    	    wfCctOptsNormalPriorityQueueLimit
    		INTEGER,
    	    wfCctOptsLowPriorityQueueLimit
    		INTEGER,
    	    wfCctOptsMaxInterruptQueueLatency
    		INTEGER,
    	    wfCctOptsMaxHighPriorityQueueLatency
    		INTEGER,
    	    wfCctOptsHiXmits
    		Counter,
    	    wfCctOptsNormalXmits
    		Counter,
    	    wfCctOptsLoXmits
    		Counter,
    	    wfCctOptsHiClippedPkts
    		Counter,
    	    wfCctOptsNormalClippedPkts
    		Counter,
    	    wfCctOptsLoClippedPkts
    		Counter,
    	    wfCctOptsIntrQHighWaterPkts
    		Gauge,
    	    wfCctOptsHiQHighWaterPkts
    		Gauge,
    	    wfCctOptsNormalQHighWaterPkts
    		Gauge,
    	    wfCctOptsLoQHighWaterPkts
    		Gauge,
    	    wfCctOptsHighWaterPktsClear
    		INTEGER,
    	    wfCctOptsDroppedPkts
    		Counter,
    	    wfCctOptsLargePkts
    		Counter,
    	    wfCctOptsRxPkts
    		Counter,
    	    wfCctOptsChooserType
    		INTEGER,
    	    wfCctOptsPqDequeueAlgType
    		INTEGER,
    	    wfCctOptsHiPercent
    		INTEGER,
    	    wfCctOptsNormalPercent
    		INTEGER,
    	    wfCctOptsLoPercent
    		INTEGER,
    	    wfCctOptsHiTotalOctets
    		Counter,
    	    wfCctOptsNormalTotalOctets
    		Counter,
    	    wfCctOptsLoTotalOctets
    		Counter,
    	    wfCctOptsCircuitType
    		INTEGER,
    	    wfCctOptsBackupCct
    		INTEGER,
    	    wfCctOptsPrimaryCctWanProtocolType
    		INTEGER,
    	    wfCctOptsMacFilterFormat
                INTEGER,
            wfCctOptsPktsNotQueued
                Counter,
            wfCctOptsBitsShiftCount
                INTEGER,
            wfCctOptsFrSetDeLowQ
                INTEGER,
            wfCctOptsFrSetDeNormQ
                INTEGER,
            wfCctOptsShapedPriorityQueueLimit
                INTEGER,
            wfCctOptsMaxShapedPriorityQueueLatency
                INTEGER,
            wfCctOptsShapedXmits
                Counter,
            wfCctOptsShapedClippedPkts
                Counter,
            wfCctOptsShapedQHighWaterPkts
                Gauge,
            wfCctOptsShapedTotalOctets
                Counter,
            wfCctOptsPpqDebugLevel
                INTEGER,
	    wfDequeueAtLineRate
		INTEGER
        }

    wfCctOptsDelete OBJECT-TYPE
        SYNTAX	INTEGER {
    		    created(1),
    		    deleted(2)
    		}
        ACCESS	read-write
        STATUS	mandatory
        DESCRIPTION
                "Creation and deletion flag for this record"
        DEFVAL	{ created }
        ::= { wfCctOptsEntry 1 }

    wfCctOptsPriorityQueueingDisable OBJECT-TYPE
        SYNTAX	INTEGER {
    		    enabled(1),
    		    disabled(2)
    		}
        ACCESS	read-write
        STATUS	mandatory
        DESCRIPTION
                "Priority Queuing option"
        DEFVAL	{ enabled }
        ::= { wfCctOptsEntry 2 }

    wfCctOptsCct OBJECT-TYPE
        SYNTAX	INTEGER
        ACCESS	read-only
        STATUS	mandatory
        DESCRIPTION
                "circuit number"
        ::= { wfCctOptsEntry 3 }

    wfCctOptsHighPriorityQueueLimit OBJECT-TYPE
        SYNTAX	INTEGER {
    		    default(20)
    		}
        ACCESS	read-write
        STATUS	mandatory
        DESCRIPTION
                "High Priority Queue limit
                The minimum valid value is zero.
                no maximum valid value (limited by bufs for the slot)"
        DEFVAL	{ default }
        ::= { wfCctOptsEntry 4 }

    wfCctOptsNormalPriorityQueueLimit OBJECT-TYPE
        SYNTAX	INTEGER {
    		    default(20)
    		}
        ACCESS	read-write
        STATUS	mandatory
        DESCRIPTION
                "Normal Priority Queue limit
                The minimum valid value is zero.
                no maximum valid value (limited by bufs for the slot)"
        DEFVAL	{ default }
        ::= { wfCctOptsEntry 5 }

    wfCctOptsLowPriorityQueueLimit OBJECT-TYPE
        SYNTAX	INTEGER {
    		    default(20)
    		}
        ACCESS	read-write
        STATUS	mandatory
        DESCRIPTION
                "Low Priority Queue limit
                The minimum valid value is zero.
                no maximum valid value (limited by bufs for the slot)"
        DEFVAL	{ default }
        ::= { wfCctOptsEntry 6 }

    wfCctOptsMaxInterruptQueueLatency OBJECT-TYPE
        SYNTAX	INTEGER(100..5000)
        ACCESS	read-write
        STATUS	mandatory
        DESCRIPTION
                "Interrupt Queue Latency"
        DEFVAL	{ 2500 }
        ::= { wfCctOptsEntry 7 }

    wfCctOptsMaxHighPriorityQueueLatency OBJECT-TYPE
        SYNTAX	INTEGER(100..5000)
        ACCESS	read-write
        STATUS	mandatory
        DESCRIPTION
                "High Priority Queue Latency"
        DEFVAL	{ 250 }
        ::= { wfCctOptsEntry 8 }

    wfCctOptsHiXmits OBJECT-TYPE
        SYNTAX	Counter
        ACCESS	read-only
        STATUS	mandatory
        DESCRIPTION
                "High Priority Transmit count"
        ::= { wfCctOptsEntry 9 }

    wfCctOptsNormalXmits OBJECT-TYPE
        SYNTAX	Counter
        ACCESS	read-only
        STATUS	mandatory
        DESCRIPTION
                "Normal Priority Transmit count"
        ::= { wfCctOptsEntry 10 }

    wfCctOptsLoXmits OBJECT-TYPE
        SYNTAX	Counter
        ACCESS	read-only
        STATUS	mandatory
        DESCRIPTION
                "Low Priority Transmit count"
        ::= { wfCctOptsEntry 11 }

    wfCctOptsHiClippedPkts OBJECT-TYPE
        SYNTAX	Counter
        ACCESS	read-only
        STATUS	mandatory
        DESCRIPTION
                "High Prio Transmit Clip Count"
        ::= { wfCctOptsEntry 12 }

    wfCctOptsNormalClippedPkts OBJECT-TYPE
        SYNTAX	Counter
        ACCESS	read-only
        STATUS	mandatory
        DESCRIPTION
                "Normal Prio Transmit Clip Count"
        ::= { wfCctOptsEntry 13 }

    wfCctOptsLoClippedPkts OBJECT-TYPE
        SYNTAX	Counter
        ACCESS	read-only
        STATUS	mandatory
        DESCRIPTION
                "Low Prio Transmit Clip Count"
        ::= { wfCctOptsEntry 14 }

    wfCctOptsIntrQHighWaterPkts OBJECT-TYPE
        SYNTAX	Gauge
        ACCESS	read-only
        STATUS	mandatory
        DESCRIPTION
                "Interrupt Queue high-water mark"
        ::= { wfCctOptsEntry 15 }

    wfCctOptsHiQHighWaterPkts OBJECT-TYPE
        SYNTAX	Gauge
        ACCESS	read-only
        STATUS	mandatory
        DESCRIPTION
                "High-priority Queue high-water mark"
        ::= { wfCctOptsEntry 16 }

    wfCctOptsNormalQHighWaterPkts OBJECT-TYPE
        SYNTAX	Gauge
        ACCESS	read-only
        STATUS	mandatory
        DESCRIPTION
                "Normal Queue high-water mark"
        ::= { wfCctOptsEntry 17 }

    wfCctOptsLoQHighWaterPkts OBJECT-TYPE
        SYNTAX	Gauge
        ACCESS	read-only
        STATUS	mandatory
        DESCRIPTION
                "Low-priority Queue high-water mark"
        ::= { wfCctOptsEntry 18 }

    wfCctOptsHighWaterPktsClear OBJECT-TYPE
        SYNTAX	INTEGER
        ACCESS	read-write
        STATUS	mandatory
        DESCRIPTION
                "Attribute to clear the high-water marks. When the MIB
                changes, Priority Queueing (if ENABLED) checks to see
                if HighWaterPktsClear is different than the last time the MIB
                was modified in any way.  If it is different,
                all the high water marks (see above) are set to zero."
        ::= { wfCctOptsEntry 19 }

    wfCctOptsDroppedPkts OBJECT-TYPE
        SYNTAX	Counter
        ACCESS	read-only
        STATUS	mandatory
        DESCRIPTION
                "Packets which were filtered in Priority Queueing"
        ::= { wfCctOptsEntry 20 }

    wfCctOptsLargePkts OBJECT-TYPE
        SYNTAX	Counter
        ACCESS	read-only
        STATUS	mandatory
        DESCRIPTION
                "Large Packets which became an exception to latency rules"
        ::= { wfCctOptsEntry 21 }

    wfCctOptsRxPkts OBJECT-TYPE
        SYNTAX	Counter
        ACCESS	read-only
        STATUS	mandatory
        DESCRIPTION
                "Packets received"
        ::= { wfCctOptsEntry 22 }

    wfCctOptsChooserType OBJECT-TYPE
        SYNTAX	INTEGER {
    		    random(1),
    		    addrbased(2),
                    multilinkfr(3)
    		}
        ACCESS	read-write
        STATUS	mandatory
        DESCRIPTION
                "Algorithm to choose line within a multiline circuit"
        DEFVAL	{ addrbased }
        ::= { wfCctOptsEntry 23 }

    wfCctOptsPqDequeueAlgType OBJECT-TYPE
        SYNTAX	INTEGER {
    		    prioritization(1),
    		    allocation(2)
    		}
        ACCESS	read-write
        STATUS	mandatory
        DESCRIPTION
                "Selection of Priority Queueing dequeueing algorithm
                PQ_STRICT_PRIORITIZATION is 'classical' 7.50 dequeueing.
                PQ_BANDWIDTH_ALLOCATION makes exceptions to strict
                prioritization in order to prevent starvation of the
                Normal and/or Low priority traffic."
        DEFVAL	{ allocation }
        ::= { wfCctOptsEntry 24 }

    wfCctOptsHiPercent OBJECT-TYPE
        SYNTAX	INTEGER {
    		    default(70)
    		}
        ACCESS	read-write
        STATUS	mandatory
        DESCRIPTION
                "This is the percent of the SYNC line bandwidth that
                the network manager wishes to allocate to traffic
                which has been configured to be High Priority.
                This parameter only has meaning when the bandwidth allocation
                dequeueing algorithm is enabled by setting the dequeueing
                algorithm type appropriately.
                With this parameter
                set other than 100, each time the configured percent
                utilization is reached, Normal and Low traffic is
                sent out (if any is queued up), up to their
                configured percentages."
        DEFVAL	{ default }
        ::= { wfCctOptsEntry 25 }

    wfCctOptsNormalPercent OBJECT-TYPE
        SYNTAX	INTEGER {
    		    default(20)
    		}
        ACCESS	read-write
        STATUS	mandatory
        DESCRIPTION
                "The minimum percent of the SYNC line that Normal-priority
                traffic will get (if there is any) when the Bandwidth
                Allocation feature is enabled.
                See text for wfCctOptsHiPercent for more information."
        DEFVAL	{ default }
        ::= { wfCctOptsEntry 26 }

    wfCctOptsLoPercent OBJECT-TYPE
        SYNTAX	INTEGER {
    		    default(10)
    		}
        ACCESS	read-write
        STATUS	mandatory
        DESCRIPTION
                "The minimum percent of the SYNC line that Low-priority traffic
                will get (if there is any) when the Bandwidth Allocation
                feature is enabled.
                See text for wfCctOptsHiPercent for more information."
        DEFVAL	{ default }
        ::= { wfCctOptsEntry 27 }

    wfCctOptsHiTotalOctets OBJECT-TYPE
        SYNTAX	Counter
        ACCESS	read-only
        STATUS	mandatory
        DESCRIPTION
                "Running total of High Octets transmitted when
                using Bandwidth Allocation dequeueing algorithm"
        ::= { wfCctOptsEntry 28 }

    wfCctOptsNormalTotalOctets OBJECT-TYPE
        SYNTAX	Counter
        ACCESS	read-only
        STATUS	mandatory
        DESCRIPTION
                "Running total of Normal Octets transmitted when
                using Bandwidth Allocation dequeueing algorithm"
        ::= { wfCctOptsEntry 29 }

    wfCctOptsLoTotalOctets OBJECT-TYPE
        SYNTAX	Counter
        ACCESS	read-only
        STATUS	mandatory
        DESCRIPTION
                "Running total of Low Octets transmitted when
                using Bandwidth Allocation dequeueing algorithm"
        ::= { wfCctOptsEntry 30 }

    wfCctOptsCircuitType OBJECT-TYPE
        SYNTAX	INTEGER {
    		    normal(1),
    		    primary(2),
    		    dialondemand(3),
    		    bandwidthondemand(4),
                    standbyprimary(5),
    		    unused(99)
    		}
        ACCESS	read-write
        STATUS	mandatory
        DESCRIPTION
                "Circuit Type Attribute"
        DEFVAL	{ normal }
        ::= { wfCctOptsEntry 31 }

    wfCctOptsBackupCct OBJECT-TYPE
        SYNTAX	INTEGER
        ACCESS	read-write
        STATUS	mandatory
        DESCRIPTION
                "backup circuit number"
        ::= { wfCctOptsEntry 32 }

    wfCctOptsPrimaryCctWanProtocolType OBJECT-TYPE
        SYNTAX	INTEGER {
    		    unknown(1),
    		    ppp(2),
    		    relay(3),
    		    sync(4)
    		}
        ACCESS	read-write
        STATUS	mandatory
        DESCRIPTION
                "The type of WAN protocol type which is running
                on the primary line. This attribute is only
                read when a dial backup circuit is using this
                mib record."
        DEFVAL	{ unknown }
        ::= { wfCctOptsEntry 33 }

    wfCctOptsMacFilterFormat OBJECT-TYPE
        SYNTAX	INTEGER {
    		    default(1),
    		    tokenring(2)
    		}
        ACCESS	read-write
        STATUS	mandatory
        DESCRIPTION
                "Used to force the Mac src/dst address to be matched
                in Token Ring format."
        DEFVAL	{ default }
        ::= { wfCctOptsEntry 34 }

    wfCctOptsPktsNotQueued OBJECT-TYPE
        SYNTAX Counter
        ACCESS read-only
        STATUS mandatory
        DESCRIPTION
                "Packets that were not Queued or Dropped by  
                 Priority Queuing "
        ::= { wfCctOptsEntry 35 }

    wfCctOptsBitsShiftCount OBJECT-TYPE
        SYNTAX  INTEGER (0..30)
        ACCESS  read-write
        STATUS  mandatory
        DESCRIPTION
                "Used to shift src/dst address to the right
                when addressed based chooser is set."
        ::= { wfCctOptsEntry 36 }

    wfCctOptsFrSetDeLowQ OBJECT-TYPE
        SYNTAX INTEGER {
                   default(1),
                   dontsetdebit(2)
               }
        ACCESS read-write
        STATUS mandatory
        DESCRIPTION
                "Used on Frame Relay interfaces, allows Set of 
                 DE ( Discard Eligible ) bit of packets that end up 
                 in PQ's Low Queue, the Default is Do Set DE bit"
        DEFVAL { default }
        ::= { wfCctOptsEntry 37 }

    wfCctOptsFrSetDeNormQ OBJECT-TYPE
        SYNTAX INTEGER {
                   default(1),
                   setdebit(2)
               }
        ACCESS read-write
        STATUS mandatory
        DESCRIPTION
                "Used on Frame Relay interfaces, allows Set of 
                 DE ( Discard Eligible ) bit of packets that end up 
                 in PQ's Normal Queue, the Default is Don't Set DE bit"
        DEFVAL { default }
        ::= { wfCctOptsEntry 38 }

    wfCctOptsShapedPriorityQueueLimit OBJECT-TYPE
        SYNTAX  INTEGER {
                    default(200)
                }
        ACCESS  read-write
        STATUS  mandatory
        DESCRIPTION
                "Frame Relay Traffic Shaping Priority Queue Limit.
                 the minimum valid value is zerom no maximum valid
                 value (limited by bufs for the slot)."
        DEFVAL  { default }
        ::= { wfCctOptsEntry 39 }

    wfCctOptsMaxShapedPriorityQueueLatency OBJECT-TYPE
        SYNTAX  INTEGER(100..5000)
        ACCESS  read-write
        STATUS  mandatory
        DESCRIPTION
                "Frame Relay Traffic Shaping Priority Queue Latency."
        DEFVAL  { 250 }
        ::= { wfCctOptsEntry 40 }

    wfCctOptsShapedXmits OBJECT-TYPE
        SYNTAX  Counter
        ACCESS  read-only
        STATUS  mandatory
        DESCRIPTION
                "Frame Relay Traffic Shaping Priority Transmit count."
        ::= { wfCctOptsEntry 41 }

    wfCctOptsShapedClippedPkts OBJECT-TYPE
        SYNTAX  Counter
        ACCESS  read-only
        STATUS  mandatory
        DESCRIPTION
                "Frame Relay Traffic Shaping Transmit Clip count."
        ::= { wfCctOptsEntry 42 }

    wfCctOptsShapedQHighWaterPkts OBJECT-TYPE
        SYNTAX  Gauge
        ACCESS  read-only
        STATUS  mandatory
        DESCRIPTION
                "Frame Relay Traffic Shaping Queue high-water mark."
        ::= { wfCctOptsEntry 43 }

    wfCctOptsShapedTotalOctets OBJECT-TYPE
        SYNTAX  Counter
        ACCESS  read-only
        STATUS  mandatory
        DESCRIPTION
                "Running total of Frame Relay Traffic Shaping octets
                 transmitted."
        ::= { wfCctOptsEntry 44 }

    wfCctOptsPpqDebugLevel OBJECT-TYPE
        SYNTAX  INTEGER(1..4)
        ACCESS  read-write
        STATUS  mandatory
        DESCRIPTION
                "Protocol Priority Queueing Debug Level."
        DEFVAL  { 1 }
        ::= { wfCctOptsEntry 45 }

    wfDequeueAtLineRate OBJECT-TYPE
	SYNTAX INTEGER {
	    enabled(1),
	    disabled(2)
	}
	ACCESS read-write
	STATUS mandatory
	DESCRIPTION
                "Determines whether the dequeuing from the
                 queues is to be done at the line rate
                 instead of the conventional technique or
                 not."
	DEFVAL  { disabled }
	::= { wfCctOptsEntry 46 }

    wfCctOptsBrFilterTable OBJECT-TYPE
        SYNTAX	SEQUENCE OF WfCctOptsBrFilterEntry
        ACCESS	not-accessible
        STATUS	mandatory
        DESCRIPTION
                "Bridge  Filters"
        ::= { wfCircuitOptsGroup 2 }

    wfCctOptsBrFilterEntry OBJECT-TYPE
        SYNTAX	WfCctOptsBrFilterEntry
        ACCESS	not-accessible
        STATUS	mandatory
        DESCRIPTION
                "An entry in WfCctOptsBrFilterTable."
        INDEX	{ wfCctOptsBrFilterCct,
    		  wfCctOptsBrFilterRuleNumber,
    		  wfCctOptsBrFilterFragment }
        ::= { wfCctOptsBrFilterTable 1 }

    WfCctOptsBrFilterEntry ::= SEQUENCE {
    	    wfCctOptsBrFilterCreate
    		INTEGER,
    	    wfCctOptsBrFilterEnable
    		INTEGER,
    	    wfCctOptsBrFilterState
    		INTEGER,
    	    wfCctOptsBrFilterCounter
    		Counter,
    	    wfCctOptsBrFilterDefinition
    		OCTET STRING,
    	    wfCctOptsBrFilterReserved
    		INTEGER,
    	    wfCctOptsBrFilterCct
    		INTEGER,
    	    wfCctOptsBrFilterRuleNumber
    		INTEGER,
    	    wfCctOptsBrFilterFragment
    		INTEGER,
    	    wfCctOptsBrFilterName
    		DisplayString
        }

    wfCctOptsBrFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfCctOptsBrFilterEntry 1 }

    wfCctOptsBrFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfCctOptsBrFilterEntry 2 }

    wfCctOptsBrFilterState OBJECT-TYPE
        SYNTAX	INTEGER {
    		    active(1),
    		    error(2),
    		    inactive(3)
    		}
        ACCESS	read-only
        STATUS	mandatory
        DESCRIPTION
                "Defines the current State of the traffic filter:
                inactive - the rule is not in use.
                active - the rule is being used.
                error - the application detected an error in the rule."
        DEFVAL	{ inactive }
        ::= { wfCctOptsBrFilterEntry 3 }

    wfCctOptsBrFilterCounter OBJECT-TYPE
        SYNTAX	Counter
        ACCESS	read-only
        STATUS	mandatory
        DESCRIPTION
                "The number of received packets that have
                matched this rule."
        ::= { wfCctOptsBrFilterEntry 4 }

    wfCctOptsBrFilterDefinition OBJECT-TYPE
        SYNTAX	OCTET STRING
        ACCESS	read-write
        STATUS	mandatory
        DESCRIPTION
                "The filter rule definition."
        ::= { wfCctOptsBrFilterEntry 5 }

    wfCctOptsBrFilterReserved OBJECT-TYPE
        SYNTAX	INTEGER
        ACCESS	read-only
        STATUS	mandatory
        DESCRIPTION
                "Reserved field."
        ::= { wfCctOptsBrFilterEntry 6 }

    wfCctOptsBrFilterCct OBJECT-TYPE
        SYNTAX	INTEGER
        ACCESS	read-only
        STATUS	mandatory
        DESCRIPTION
                "The ID of the CctBridge Cct to which the
                filter is applied."
        ::= { wfCctOptsBrFilterEntry 7 }

    wfCctOptsBrFilterRuleNumber OBJECT-TYPE
        SYNTAX	INTEGER
        ACCESS	read-only
        STATUS	mandatory
        DESCRIPTION
                "ID for the rule."
        ::= { wfCctOptsBrFilterEntry 8 }

    wfCctOptsBrFilterFragment OBJECT-TYPE
        SYNTAX	INTEGER
        ACCESS	read-only
        STATUS	mandatory
        DESCRIPTION
                "Fragment number - for large rules."
        ::= { wfCctOptsBrFilterEntry 9 }

    wfCctOptsBrFilterName OBJECT-TYPE
        SYNTAX	DisplayString
        ACCESS	read-write
        STATUS	mandatory
        DESCRIPTION
                "name of the rule number"
        ::= { wfCctOptsBrFilterEntry 10 }

    wfCctOptsIpFilterTable OBJECT-TYPE
        SYNTAX	SEQUENCE OF WfCctOptsIpFilterEntry
        ACCESS	not-accessible
        STATUS	mandatory
        DESCRIPTION
                "Ip  Filters"
        ::= { wfCircuitOptsGroup 3 }

    wfCctOptsIpFilterEntry OBJECT-TYPE
        SYNTAX	WfCctOptsIpFilterEntry
        ACCESS	not-accessible
        STATUS	mandatory
        DESCRIPTION
                "An entry in WfCctOptsIpFilterTable."
        INDEX	{ wfCctOptsIpFilterCct,
    		  wfCctOptsIpFilterRuleNumber,
    		  wfCctOptsIpFilterFragment }
        ::= { wfCctOptsIpFilterTable 1 }

    WfCctOptsIpFilterEntry ::= SEQUENCE {
    	    wfCctOptsIpFilterCreate
    		INTEGER,
    	    wfCctOptsIpFilterEnable
    		INTEGER,
    	    wfCctOptsIpFilterState
    		INTEGER,
    	    wfCctOptsIpFilterCounter
    		Counter,
    	    wfCctOptsIpFilterDefinition
    		OCTET STRING,
    	    wfCctOptsIpFilterReserved
    		INTEGER,
    	    wfCctOptsIpFilterCct
    		INTEGER,
    	    wfCctOptsIpFilterRuleNumber
    		INTEGER,
    	    wfCctOptsIpFilterFragment
    		INTEGER,
    	    wfCctOptsIpFilterName
    		DisplayString
        }

    wfCctOptsIpFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfCctOptsIpFilterEntry 1 }

    wfCctOptsIpFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfCctOptsIpFilterEntry 2 }

    wfCctOptsIpFilterState OBJECT-TYPE
        SYNTAX	INTEGER {
    		    active(1),
    		    error(2),
    		    inactive(3)
    		}
        ACCESS	read-only
        STATUS	mandatory
        DESCRIPTION
                "Defines the current State of the traffic filter:
                inactive - the rule is not in use.
                active - the rule is being used.
                error - the application detected an error in the rule."
        DEFVAL	{ inactive }
        ::= { wfCctOptsIpFilterEntry 3 }

    wfCctOptsIpFilterCounter OBJECT-TYPE
        SYNTAX	Counter
        ACCESS	read-only
        STATUS	mandatory
        DESCRIPTION
                "The number of received packets that have
                matched this rule."
        ::= { wfCctOptsIpFilterEntry 4 }

    wfCctOptsIpFilterDefinition OBJECT-TYPE
        SYNTAX	OCTET STRING
        ACCESS	read-write
        STATUS	mandatory
        DESCRIPTION
                "The filter rule definition."
        ::= { wfCctOptsIpFilterEntry 5 }

    wfCctOptsIpFilterReserved OBJECT-TYPE
        SYNTAX	INTEGER
        ACCESS	read-only
        STATUS	mandatory
        DESCRIPTION
                "Reserved field."
        ::= { wfCctOptsIpFilterEntry 6 }

    wfCctOptsIpFilterCct OBJECT-TYPE
        SYNTAX	INTEGER
        ACCESS	read-only
        STATUS	mandatory
        DESCRIPTION
                "The ID of the CctIp Cct to which the
                filter is applied."
        ::= { wfCctOptsIpFilterEntry 7 }

    wfCctOptsIpFilterRuleNumber OBJECT-TYPE
        SYNTAX	INTEGER
        ACCESS	read-only
        STATUS	mandatory
        DESCRIPTION
                "ID for the rule."
        ::= { wfCctOptsIpFilterEntry 8 }

    wfCctOptsIpFilterFragment OBJECT-TYPE
        SYNTAX	INTEGER
        ACCESS	read-only
        STATUS	mandatory
        DESCRIPTION
                "Fragment number - for large rules."
        ::= { wfCctOptsIpFilterEntry 9 }

    wfCctOptsIpFilterName OBJECT-TYPE
        SYNTAX	DisplayString
        ACCESS	read-write
        STATUS	mandatory
        DESCRIPTION
                "name of the rule number"
        ::= { wfCctOptsIpFilterEntry 10 }

    wfCctOptsLengthBasedTable OBJECT-TYPE
        SYNTAX	SEQUENCE OF WfCctOptsLengthBasedEntry
        ACCESS	not-accessible
        STATUS	mandatory
        DESCRIPTION
                "Length Based Priority Table"
        ::= { wfCircuitOptsGroup 4 }

    wfCctOptsLengthBasedEntry OBJECT-TYPE
        SYNTAX	WfCctOptsLengthBasedEntry
        ACCESS	not-accessible
        STATUS	mandatory
        DESCRIPTION
                "An entry in WfCctOptsLengthBasedTable."
        INDEX	{ wfCctOptsLengthBasedCct,
    		  wfCctOptsLengthBasedMux,
    		  wfCctOptsLengthBasedData }
        ::= { wfCctOptsLengthBasedTable 1 }

    WfCctOptsLengthBasedEntry ::= SEQUENCE {
    	    wfCctOptsLengthBasedDelete
    		INTEGER,
    	    wfCctOptsLengthBasedDisable
    		INTEGER,
    	    wfCctOptsLengthBasedState
    		INTEGER,
    	    wfCctOptsLengthBasedCct
    		INTEGER,
    	    wfCctOptsLengthBasedMux
    		INTEGER,
    	    wfCctOptsLengthBasedData
    		OCTET STRING,
    	    wfCctOptsLengthBasedLength
    		INTEGER,
    	    wfCctOptsLengthBasedLessThanQ
    		INTEGER,
    	    wfCctOptsLengthBasedGreaterThanQ
    		INTEGER
        }

    wfCctOptsLengthBasedDelete OBJECT-TYPE
        SYNTAX	INTEGER {
    		    created(1),
    		    deleted(2)
    		}
        ACCESS	read-write
        STATUS	mandatory
        DESCRIPTION
                "Defines the existence of the length based priority filter rule:
                created - traffic filter exists
                delete - traffic filter does not exist and can be deleted."
        DEFVAL	{ created }
        ::= { wfCctOptsLengthBasedEntry 1 }

    wfCctOptsLengthBasedDisable OBJECT-TYPE
        SYNTAX	INTEGER {
    		    enabled(1),
    		    disabled(2)
    		}
        ACCESS	read-write
        STATUS	mandatory
        DESCRIPTION
                "Defines whether or not the length based priority filter rule should be used:
                enabled - activate the rule.
                disabled - inactivate the rule."
        DEFVAL	{ enabled }
        ::= { wfCctOptsLengthBasedEntry 2 }

    wfCctOptsLengthBasedState OBJECT-TYPE
        SYNTAX	INTEGER {
    		    active(1),
    		    error(2),
    		    inactive(3)
    		}
        ACCESS	read-only
        STATUS	mandatory
        DESCRIPTION
                "Defines the current State of the length based priority filter:
                inactive - the rule is not in use.
                active - the rule is being used.
                error - the application detected an error in the rule."
        DEFVAL	{ inactive }
        ::= { wfCctOptsLengthBasedEntry 3 }

    wfCctOptsLengthBasedCct OBJECT-TYPE
        SYNTAX	INTEGER
        ACCESS	read-only
        STATUS	mandatory
        DESCRIPTION
                "The ID of the Cct to which the filter is applied"
        ::= { wfCctOptsLengthBasedEntry 4 }

    wfCctOptsLengthBasedMux OBJECT-TYPE
        SYNTAX	INTEGER {
    		    etype(1),
    		    lsap(2),
    		    snap(3)
    		}
        ACCESS	read-only
        STATUS	mandatory
        DESCRIPTION
                "packet mux type"
        ::= { wfCctOptsLengthBasedEntry 5 }

    wfCctOptsLengthBasedData OBJECT-TYPE
        SYNTAX	OCTET STRING (SIZE (5))
        ACCESS	read-only
        STATUS	mandatory
        DESCRIPTION
                "a five byte quantity of the form
                ethernet  - 0x6003000000 (e.g. DECnet)
                lsap      - 0xfefe030000 (e.g. OSI)
                snap      - 0x0000000800 (e.g. IP)
                   - 0x0800070800 (e.g. Appletalk DDP)"
        ::= { wfCctOptsLengthBasedEntry 6 }

    wfCctOptsLengthBasedLength OBJECT-TYPE
        SYNTAX	INTEGER
        ACCESS	read-write
        STATUS	mandatory
        DESCRIPTION
                "Maximum length of a packet to be considered high priority"
        ::= { wfCctOptsLengthBasedEntry 7 }

    wfCctOptsLengthBasedLessThanQ OBJECT-TYPE
        SYNTAX	INTEGER {
    		    hi(3),
    		    normal(2),
    		    lo(1)
    		}
        ACCESS	read-write
        STATUS	mandatory
        DESCRIPTION
                "queue into which packets of length less than or equal
                wfCctOptsLengthBasedLength are placed"
        DEFVAL	{ normal }
        ::= { wfCctOptsLengthBasedEntry 8 }

    wfCctOptsLengthBasedGreaterThanQ OBJECT-TYPE
        SYNTAX	INTEGER {
    		    hi(3),
    		    normal(2),
    		    lo(1)
    		}
        ACCESS	read-write
        STATUS	mandatory
        DESCRIPTION
                "queue into which packets of length greater than
                wfCctOptsLengthBasedLength are placed"
        DEFVAL	{ lo }
        ::= { wfCctOptsLengthBasedEntry 9 }

    wfSwservOptsTable OBJECT-TYPE
        SYNTAX	SEQUENCE OF WfSwservOptsEntry
        ACCESS	not-accessible
        STATUS	mandatory
        DESCRIPTION
                "The table of circuits defined  over  switched services"
        ::= { wfCircuitOptsGroup 5 }

    wfSwservOptsEntry OBJECT-TYPE
        SYNTAX	WfSwservOptsEntry
        ACCESS	not-accessible
        STATUS	mandatory
        DESCRIPTION
                "Entry  format for the table  of sw_serv circuit options"
        INDEX	{ wfSwservOptsCct }
        ::= { wfSwservOptsTable 1 }

    WfSwservOptsEntry ::= SEQUENCE {
    	    wfSwservOptsDelete
    		INTEGER,
    	    wfSwservOptsCct
    		INTEGER,
    	    wfSwservOptsCircuitType
    		INTEGER,
    	    wfSwservOptsBackupCct
    		INTEGER,
    	    wfSwservOptsBackupPool
    		INTEGER,
    	    wfSwservOptsDemandPool
    		INTEGER,
    	    wfSwservOptsBackupMode
    		INTEGER,
    	    wfSwservOptsActiveBackupCct
    		INTEGER,
    	    wfSwservOptsForcedDial
    		INTEGER,
    	    wfSwservOptsMaxUpTime
    		INTEGER,
    	    wfSwservOptsBringUpHour
    		INTEGER,
    	    wfSwservOptsBringUpMinute
    		INTEGER,
    	    wfSwservOptsTakeDownHour
    		INTEGER,
    	    wfSwservOptsTakeDownMinute
    		INTEGER,
    	    wfSwservOptsInactivityTime
    		INTEGER,
    	    wfSwservOptsCircuitState
    		INTEGER,
    	    wfSwservOptsPrimaryDownTime
    		INTEGER,
    	    wfSwservOptsNumOutgoingConn
    		Counter,
    	    wfSwservOptsNumIncomingConn
    		Counter,
    	    wfSwservOptsActiveSlot
    		INTEGER,
    	    wfSwservOptsActiveLine
    		INTEGER,
    	    wfSwservOptsPacketsDropped
    		Counter,
    	    wfSwservOptsTimeLastPktDropped
    		INTEGER,
    	    wfSwservOptsForcedTakedown
    		INTEGER,
    	    wfSwservOptsRetryMax
    		INTEGER,
    	    wfSwservOptsRetryCount
    		Counter,
    	    wfSwservOptsRetryDelay
    		INTEGER,
    	    wfSwservOptsDemandConnectionMode
    		INTEGER,
    	    wfSwservOptsAutoDemandTermination
    		INTEGER,
    	    wfSwservOptsAutoDemandTermReset
    		INTEGER,
    	    wfSwservOptsChapLocalName
    		DisplayString,
    	    wfSwservOptsChapSecret
    		DisplayString,
    	    wfSwservOptsMaxUpTermination
    		INTEGER,
    	    wfSwservOptsMaxUpTermReset
    		INTEGER,
    	    wfSwservOptsBandwidthPool
    		INTEGER,
    	    wfSwservOptsBandwidthMode
    		INTEGER,
    	    wfSwservOptsPapId
    		DisplayString,
    	    wfSwservOptsPapPassword
    		DisplayString,
    	    wfSwservOptsDebugMsgLevel
    		INTEGER,
    	    wfSwservOptsDmdCctGroupNum
    		INTEGER,
    	    wfSwservOptsWanProtocol
    		INTEGER,
    	    wfSwservOptsSecondaryCct
    		INTEGER,
    	    wfSwservOptsPoolLineNumber
    		INTEGER,
    	    wfSwservOptsPoolLineIndex
    		INTEGER,
    	    wfSwservOptsMinDuration
    		INTEGER,
    	    wfSwservOptsInactivityMode
    		INTEGER,
    	    wfSwservOptsOpportunityRouting
    		INTEGER,
    	    wfSwservOptsOutboundAuth
    		INTEGER,
    	    wfSwservOptsOverSubRetryTimer
    		INTEGER,
    	    wfSwservOptsStandbyMode
    		INTEGER,
    	    wfSwservOptsStandbyFailBackMode
    		INTEGER,
    	    wfSwservOptsManualStandbyAction
    		INTEGER,
            wfSwservOptsCallbackMode
                INTEGER,
            wfSwservOptsCallbackServerDelay
                INTEGER,
            wfSwservOptsCallbackClientDelay
                INTEGER,
    	    wfSwservOptsQueueSize
    		INTEGER,
            wfSwservOptsDequeueWaitTimer
		INTEGER,
            wfSwservOptsMru
                INTEGER,
            wfSwservOptsRfc1661Compliance
                INTEGER,
	    wfSwservOptsBootupDelay
                INTEGER,
            wfSwservOptsCallbackOptRfc1570
                INTEGER,
            wfSwservOptsCallbackDataRfc1570
    		DisplayString
        }

    wfSwservOptsDelete OBJECT-TYPE
        SYNTAX	INTEGER {
    		    created(1),
    		    deleted(2)
    		}
        ACCESS	read-write
        STATUS	mandatory
        DESCRIPTION
                "Creation and deletion flag"
        DEFVAL	{ created }
        ::= { wfSwservOptsEntry 1 }

    wfSwservOptsCct OBJECT-TYPE
        SYNTAX	INTEGER
        ACCESS	read-only
        STATUS	mandatory
        DESCRIPTION
                "Circuit Number"
        ::= { wfSwservOptsEntry 2 }

    wfSwservOptsCircuitType OBJECT-TYPE
        SYNTAX	INTEGER {
    		    normal(1),
    		    primary(2),
    		    dialondemand(3),
    		    bandwidthondemand(4)
    		}
        ACCESS	read-write
        STATUS	mandatory
        DESCRIPTION
                "Circuit Type Attribute"
        DEFVAL	{ normal }
        ::= { wfSwservOptsEntry 3 }

    wfSwservOptsBackupCct OBJECT-TYPE
        SYNTAX	INTEGER
        ACCESS	read-write
        STATUS	mandatory
        DESCRIPTION
                "Backup Circuit Number assigned by site manager"
        ::= { wfSwservOptsEntry 4 }

    wfSwservOptsBackupPool OBJECT-TYPE
        SYNTAX	INTEGER(1..255)
        ACCESS	read-write
        STATUS	mandatory
        DESCRIPTION
                "Backup Pool Id"
        ::= { wfSwservOptsEntry 5 }

    wfSwservOptsDemandPool OBJECT-TYPE
        SYNTAX	INTEGER(1..255)
        ACCESS	read-write
        STATUS	mandatory
        DESCRIPTION
                "Dial on Demand Pool Id"
        ::= { wfSwservOptsEntry 6 }

    wfSwservOptsBackupMode OBJECT-TYPE
        SYNTAX	INTEGER {
    		    master(1),
    		    slave(2)
    		}
        ACCESS	read-write
        STATUS	mandatory
        DESCRIPTION
                "Mode  Master ( initiate  dialing ) or Slave"
        DEFVAL	{ master }
        ::= { wfSwservOptsEntry 7 }

    wfSwservOptsActiveBackupCct OBJECT-TYPE
        SYNTAX	INTEGER
        ACCESS	read-write
        STATUS	mandatory
        DESCRIPTION
                "Active Backup Indicator"
        ::= { wfSwservOptsEntry 8 }

    wfSwservOptsForcedDial OBJECT-TYPE
        SYNTAX	INTEGER {
    		    enabled(1),
    		    disabled(2)
    		}
        ACCESS	read-write
        STATUS	mandatory
        DESCRIPTION
                "Forced Dial Indicator"
        DEFVAL	{ disabled }
        ::= { wfSwservOptsEntry 9 }

    wfSwservOptsMaxUpTime OBJECT-TYPE
        SYNTAX	INTEGER(1..999999)
        ACCESS	read-write
        STATUS	mandatory
        DESCRIPTION
                "Max amount fo time dial call can exist"
        DEFVAL	{ 60 }
        ::= { wfSwservOptsEntry 10 }

    wfSwservOptsBringUpHour OBJECT-TYPE
        SYNTAX	INTEGER
        ACCESS	read-write
        STATUS	mandatory
        DESCRIPTION
                "Time of day hour to allow a line to dial"
        ::= { wfSwservOptsEntry 11 }

    wfSwservOptsBringUpMinute OBJECT-TYPE
        SYNTAX	INTEGER
        ACCESS	read-write
        STATUS	mandatory
        DESCRIPTION
                "Time of day minute to allow a line to dial"
        ::= { wfSwservOptsEntry 12 }

    wfSwservOptsTakeDownHour OBJECT-TYPE
        SYNTAX	INTEGER
        ACCESS	read-write
        STATUS	mandatory
        DESCRIPTION
                "Time of day hour to take down a dial line"
        ::= { wfSwservOptsEntry 13 }

    wfSwservOptsTakeDownMinute OBJECT-TYPE
        SYNTAX	INTEGER
        ACCESS	read-write
        STATUS	mandatory
        DESCRIPTION
                "Time of day minute to take down a dial line"
        ::= { wfSwservOptsEntry 14 }

    wfSwservOptsInactivityTime OBJECT-TYPE
        SYNTAX	INTEGER(1..2147483647)
        ACCESS	read-write
        STATUS	mandatory
        DESCRIPTION
                "Maximum for inactivity timer is equal to
                infinity = 99999999"
        DEFVAL	{ 60 }
        ::= { wfSwservOptsEntry 15 }

    wfSwservOptsCircuitState OBJECT-TYPE
        SYNTAX	INTEGER {
    		    active(1),
    		    inactive(2),
    		    notpresent(3)
    		}
        ACCESS	read-only
        STATUS	mandatory
        DESCRIPTION
                "Circuit State"
        DEFVAL	{ notpresent }
        ::= { wfSwservOptsEntry 16 }

    wfSwservOptsPrimaryDownTime OBJECT-TYPE
        SYNTAX	INTEGER {
    		    default(5)
    		}
        ACCESS	read-write
        STATUS	mandatory
        DESCRIPTION
                "Amount of time allowed for establishment of primary before
                the backup is invoked"
        DEFVAL	{ default }
        ::= { wfSwservOptsEntry 17 }

    wfSwservOptsNumOutgoingConn OBJECT-TYPE
        SYNTAX	Counter
        ACCESS	read-only
        STATUS	mandatory
        DESCRIPTION
                "Number of Outgoing call attempts for this circuit"
        ::= { wfSwservOptsEntry 18 }

    wfSwservOptsNumIncomingConn OBJECT-TYPE
        SYNTAX	Counter
        ACCESS	read-only
        STATUS	mandatory
        DESCRIPTION
                "Number of Incoming call attempts for this circuit"
        ::= { wfSwservOptsEntry 19 }

    wfSwservOptsActiveSlot OBJECT-TYPE
        SYNTAX	INTEGER
        ACCESS	read-only
        STATUS	mandatory
        DESCRIPTION
                "Slot actively in use by this call"
        ::= { wfSwservOptsEntry 20 }

    wfSwservOptsActiveLine OBJECT-TYPE
        SYNTAX	INTEGER
        ACCESS	read-only
        STATUS	mandatory
        DESCRIPTION
                "Line actively in use by this call"
        ::= { wfSwservOptsEntry 21 }

    wfSwservOptsPacketsDropped OBJECT-TYPE
        SYNTAX	Counter
        ACCESS	read-only
        STATUS	mandatory
        DESCRIPTION
                "Number of Incoming call attempts for this circuit"
        ::= { wfSwservOptsEntry 22 }

    wfSwservOptsTimeLastPktDropped OBJECT-TYPE
        SYNTAX	INTEGER
        ACCESS	read-only
        STATUS	mandatory
        DESCRIPTION
                "Number of Incoming call attempts for this circuit"
        ::= { wfSwservOptsEntry 23 }

    wfSwservOptsForcedTakedown OBJECT-TYPE
        SYNTAX	INTEGER {
    		    enabled(1),
    		    disabled(2)
    		}
        ACCESS	read-write
        STATUS	mandatory
        DESCRIPTION
                "Forced Dial Indicator"
        DEFVAL	{ disabled }
        ::= { wfSwservOptsEntry 24 }

    wfSwservOptsRetryMax OBJECT-TYPE
        SYNTAX	INTEGER(1..10)
        ACCESS	read-write
        STATUS	mandatory
        DESCRIPTION
                "Redial count"
        DEFVAL	{ 2 }
        ::= { wfSwservOptsEntry 25 }

    wfSwservOptsRetryCount OBJECT-TYPE
        SYNTAX	Counter
        ACCESS	read-only
        STATUS	mandatory
        DESCRIPTION
                "Redial count"
        ::= { wfSwservOptsEntry 26 }

    wfSwservOptsRetryDelay OBJECT-TYPE
        SYNTAX	INTEGER(1..60)
        ACCESS	read-write
        STATUS	mandatory
        DESCRIPTION
                "delay to wait after retrys fails. value is in seconds"
        DEFVAL	{ 3 }
        ::= { wfSwservOptsEntry 27 }

    wfSwservOptsDemandConnectionMode OBJECT-TYPE
        SYNTAX	INTEGER {
    		    nodial(1),
    		    collmaster(2),
    		    collslave(3)
    		}
        ACCESS	read-write
        STATUS	mandatory
        DESCRIPTION
                "Mode Master - outgoing call has precedence terminate
                incoming call
                Slave - incoming call has precedence terminate
                outgoing call
                 NO_Dial - if data is present do MOT establish connection
                just drop the data"
        DEFVAL	{ collmaster }
        ::= { wfSwservOptsEntry 28 }

    wfSwservOptsAutoDemandTermination OBJECT-TYPE
        SYNTAX	INTEGER {
    		    enabled(1),
    		    disabled(2)
    		}
        ACCESS	read-write
        STATUS	mandatory
        DESCRIPTION
                "Automatically terminates demand circuit if
                maximum connect attempts reached"
        DEFVAL	{ disabled }
        ::= { wfSwservOptsEntry 29 }

    wfSwservOptsAutoDemandTermReset OBJECT-TYPE
        SYNTAX	INTEGER(1..999999)
        ACCESS	read-write
        STATUS	mandatory
        DESCRIPTION
                "Amount of time ( in Minutes )before atttempting to recreate
                the demand circuit after an auto termination"
        DEFVAL	{ 60 }
        ::= { wfSwservOptsEntry 30 }

    wfSwservOptsChapLocalName OBJECT-TYPE
        SYNTAX	DisplayString
        ACCESS	read-write
        STATUS	mandatory
        DESCRIPTION
                "This attribute is used to assign a local CHAP Name to
                outbound calls to to inform our peer of our identity,
                during WHOAMI processing"
        ::= { wfSwservOptsEntry 31 }

    wfSwservOptsChapSecret OBJECT-TYPE
        SYNTAX	DisplayString
        ACCESS	read-write
        STATUS	mandatory
        DESCRIPTION
                "Secret used for running CHAP when this cct is active.
                The peer must use the same secret when responding to our
                Challenges, which will be found in the Whoami Table"
        ::= { wfSwservOptsEntry 32 }

    wfSwservOptsMaxUpTermination OBJECT-TYPE
        SYNTAX	INTEGER {
    		    enabled(1),
    		    disabled(2)
    		}
        ACCESS	read-write
        STATUS	mandatory
        DESCRIPTION
                "Automatically terminates demand circuit if
                maximum connect attempts reached"
        DEFVAL	{ disabled }
        ::= { wfSwservOptsEntry 33 }

    wfSwservOptsMaxUpTermReset OBJECT-TYPE
        SYNTAX	INTEGER(1..999999)
        ACCESS	read-write
        STATUS	mandatory
        DESCRIPTION
                "Amount of time ( in Minutes )before atttempting to recreate
                the demand circuit after an auto termination"
        DEFVAL	{ 60 }
        ::= { wfSwservOptsEntry 34 }

    wfSwservOptsBandwidthPool OBJECT-TYPE
        SYNTAX	INTEGER(1..255)
        ACCESS	read-write
        STATUS	mandatory
        DESCRIPTION
                "Bandwidth on Demand Pool Id"
        ::= { wfSwservOptsEntry 35 }

    wfSwservOptsBandwidthMode OBJECT-TYPE
        SYNTAX	INTEGER {
    		    monitor(1),
    		    normal(2)
    		}
        ACCESS	read-write
        STATUS	mandatory
        DESCRIPTION
                "Bandwidth Mode Monitor (Congestion Monitor) or NORMAL"
        DEFVAL	{ normal }
        ::= { wfSwservOptsEntry 36 }

    wfSwservOptsPapId OBJECT-TYPE
        SYNTAX	DisplayString
        ACCESS	read-write
        STATUS	mandatory
        DESCRIPTION
                "This attribute is used to assign a local PAP Id to
                outbound calls to to inform our peer of our identity,
                during WHOAMI processing"
        ::= { wfSwservOptsEntry 37 }

    wfSwservOptsPapPassword OBJECT-TYPE
        SYNTAX	DisplayString
        ACCESS	read-write
        STATUS	mandatory
        DESCRIPTION
                "This attribute is used to assign a local PAP Password
                to outbound calls to to inform our peer of our identity,
                during WHOAMI processing"
        ::= { wfSwservOptsEntry 38 }

    wfSwservOptsDebugMsgLevel OBJECT-TYPE
        SYNTAX	INTEGER {
    		    one(1),
    		    two(2),
    		    three(3),
    		    debug(4)
    		}
        ACCESS	read-write
        STATUS	mandatory
        DESCRIPTION
                "This attribute is used to assign the level of Swserv Debug
                message to be logged for the circuit"
        DEFVAL	{ debug }
        ::= { wfSwservOptsEntry 39 }

    wfSwservOptsDmdCctGroupNum OBJECT-TYPE
        SYNTAX	INTEGER
        ACCESS	read-write
        STATUS	mandatory
        DESCRIPTION
                "Backup Circuit Number assigned by site manager"
        ::= { wfSwservOptsEntry 40 }

    wfSwservOptsWanProtocol OBJECT-TYPE
        SYNTAX	INTEGER {
                    unknown(1),
                    ppp(2),
                    fr(3),
                    frswitch(4)
                }
        ACCESS	read-write
        STATUS	mandatory
        DESCRIPTION
                "Wan Protocol for this circuit assigned by site manager.
                 Used by BNX Software to Support ISDN Switched access
                 to Frame Relay Switch Network."
        DEFVAL	{ ppp }
        ::= { wfSwservOptsEntry 41 }

    wfSwservOptsSecondaryCct OBJECT-TYPE
        SYNTAX	INTEGER
        ACCESS	read-write
        STATUS	mandatory
        DESCRIPTION
                "Secondary circuit to be used by Line Manager when 
		 creating a backup for this primary circuit."
        ::= { wfSwservOptsEntry 42 }

    wfSwservOptsPoolLineNumber OBJECT-TYPE
        SYNTAX	INTEGER
        ACCESS	read-write
        STATUS	mandatory
        DESCRIPTION
                "Pooling line number used for identifying Frame Relay backup
		 interface objects associated with a pool."
        ::= { wfSwservOptsEntry 43 }
 
    wfSwservOptsPoolLineIndex OBJECT-TYPE
        SYNTAX	INTEGER
        ACCESS	read-write
        STATUS	mandatory
        DESCRIPTION
                "Lower layer index used for identifying Frame Relay backup
		 interface objects associated with a pool."
        ::= { wfSwservOptsEntry 44 }
        
    wfSwservOptsMinDuration OBJECT-TYPE
        SYNTAX	INTEGER(10..2147483647)
        ACCESS	read-write
        STATUS	mandatory
        DESCRIPTION
                "Maximum for min duration  timer in seconds  is equal to
                infinity = 99999999, min is 10"
        DEFVAL	{ 60 }
        ::= { wfSwservOptsEntry 45 }

    wfSwservOptsInactivityMode OBJECT-TYPE
        SYNTAX	INTEGER {
    		    bothdirection(1),
    		    transmitonly(2),
    		    receiveonly(3),
    		    eitherdirection(4)
    		}
        ACCESS	read-write
        STATUS	mandatory
        DESCRIPTION
                "Inactivity check mode"
        DEFVAL	{ bothdirection }
        ::= { wfSwservOptsEntry 46 }

    wfSwservOptsOpportunityRouting OBJECT-TYPE
        SYNTAX	INTEGER {
    		    enabled(1),
    		    disabled(2)
    		}
        ACCESS	read-write
        STATUS	mandatory
        DESCRIPTION
                "OpportunityRouting Indicator"
        DEFVAL	{ disabled }
        ::= { wfSwservOptsEntry 47 }

    wfSwservOptsOutboundAuth OBJECT-TYPE
        SYNTAX	INTEGER {
    		    enabled(1),
    		    disabled(2)
    		}
        ACCESS	read-write
        STATUS	mandatory
        DESCRIPTION
                "Allows the disabling of Authentication when the router is 
                 placing an outbound call."
        DEFVAL	{ enabled }
        ::= { wfSwservOptsEntry 48 }

    wfSwservOptsOverSubRetryTimer OBJECT-TYPE
        SYNTAX  INTEGER(0..1440)
        ACCESS  read-write
        STATUS  mandatory
        DESCRIPTION
                "This parameter allows the user to cofigure the time
                 period at which a connection  will be retried, if
	         a previous connection attempt for routing updates failed 
		 due to lack of line resources. This time should be less than 
	         the stabilization timer for IP/IPX protocols. This time is 
	         expressed in minutes and is meaningful only if Dial Optimized
	         Routing is enabled."
        DEFVAL   { 2 }
        ::= { wfSwservOptsEntry 49 }

    wfSwservOptsStandbyMode OBJECT-TYPE
        SYNTAX  INTEGER{
                    demandnormal(1),
                    standbynormal(2),
                    standbyhot(3)
                 }
        ACCESS  read-write
        STATUS  mandatory
        DESCRIPTION
                "This parameter allows a demand circuit to be identified as standby
		 or demand. The hot standby circuit is down until an event invokes 
		 it. Normal standby is invoked manually or by an incoming call."
        DEFVAL   { demandnormal }
        ::= { wfSwservOptsEntry 50 }

    wfSwservOptsStandbyFailBackMode OBJECT-TYPE
        SYNTAX  INTEGER{
                    none(1),
                    automatic(2),
                    manual(3)
                 }
        ACCESS  read-write
        STATUS  mandatory
        DESCRIPTION
                "This parameter is used to indicate if standby failback should be
                 automatic or manual."
        DEFVAL   { none }
        ::= { wfSwservOptsEntry 51 }

    wfSwservOptsManualStandbyAction OBJECT-TYPE
        SYNTAX  INTEGER{
                    noaction(1),
                    activate(2),
                    deactivate(3)
                 }
        ACCESS  read-write
        STATUS  mandatory
        DESCRIPTION
                "This parameter is used to manually activate and deactivate
		 a standby circuit."
        DEFVAL   { noaction }
        ::= { wfSwservOptsEntry 52 }

    wfSwservOptsCallbackMode OBJECT-TYPE
        SYNTAX  INTEGER {
                    inactive(1),
                    server(2),
                    client(3),
                    server-callid(4),
                    client-one-charge(5),
                    server-one-charge(6),
                    server-one-charge-callid(7),
                    client-rfc1570(8),
                    server-rfc1570(9)
                }
        ACCESS  read-write
        STATUS  mandatory
        DESCRIPTION
                "Defines the role this circuit will play in Callback.
                 INACTIVE disables Callback on this circuit.
                 SERVER performs Callback via Outgoing Phone Number.
                 CLIENT circuit expects peer to perform Callback.
                 SERVER_CALLID performs Callback via ANI"
        DEFVAL  { inactive }
        ::= { wfSwservOptsEntry 53 }

    wfSwservOptsCallbackServerDelay OBJECT-TYPE
        SYNTAX  INTEGER(0..1800)
        ACCESS  read-write
        STATUS  mandatory
        DESCRIPTION
                "The amount of time the CALLBACK_SERVER will wait,
                 (in seconds) before performing Callback,dialing back
                 the initial caller. The default time is 0, however modem
                 connections may need some delay configured to prevent busy
                 situations."

        ::= { wfSwservOptsEntry 54 }

    wfSwservOptsCallbackClientDelay OBJECT-TYPE
        SYNTAX  INTEGER(0..1800)
        ACCESS  read-write
        STATUS  mandatory
        DESCRIPTION
                "The amount of time the CALLBACK_CLIENT will wait,
                 (in seconds) for its peer to perform Callback. Data ariving
                 during opperation of the timer, will not cause a connection
                 to be established."

        DEFVAL  { 5 }
        ::= { wfSwservOptsEntry 55 }

    wfSwservOptsQueueSize OBJECT-TYPE
        SYNTAX  INTEGER(1..20)
        ACCESS  read-write
        STATUS  mandatory
        DESCRIPTION
                "This parameter controls the length of the queue used for
                 dial services."
        DEFVAL   { 6 }
        ::= { wfSwservOptsEntry 56 }

	wfSwservOptsDequeueWaitTimer OBJECT-TYPE
		SYNTAX  INTEGER(0..600)
		ACCESS  read-write
		STATUS  mandatory
		DESCRIPTION
                "This parameter controls the time FR waits before dequeuing 
				 data for FRDOD."
        DEFVAL   { 0 }
        ::= { wfSwservOptsEntry 57 }

    wfSwservOptsMru OBJECT-TYPE
        SYNTAX  INTEGER(1..4600)
        ACCESS  read-write
        STATUS  mandatory
        DESCRIPTION
                "This is the MRU being used for this demand circuit."
        DEFVAL   { 1500 }
        ::= { wfSwservOptsEntry 58 }

    wfSwservOptsRfc1661Compliance OBJECT-TYPE
        SYNTAX  INTEGER {
                    enabled(1),
                    disabled(2)
                }
        ACCESS  read-write
        STATUS  mandatory
        DESCRIPTION
                "Enable/disable RFC 1661 compliance"
        DEFVAL  { disabled }
        ::= { wfSwservOptsEntry 59 }

    wfSwservOptsBootupDelay OBJECT-TYPE
        SYNTAX  INTEGER
        ACCESS  read-write
        STATUS  mandatory
        DESCRIPTION
                "Delay in initiation of the DoD circuit at bootup time"
        DEFVAL  { 0 }
        ::= { wfSwservOptsEntry 60 }

    wfSwservOptsCallbackOptRfc1570 OBJECT-TYPE
        SYNTAX  INTEGER {
                    location(1),
                    dialstring(2),
                    locationid(3),
                    e164number(4),
                    name(5)
                }
        ACCESS  read-write
        STATUS  mandatory
        DESCRIPTION
                "The PPP/LCP Callback Option; indicates the type of
		data content the callback client places in 
                wfSwservOptsCallbackDataRfc1570 for the callback server"
        DEFVAL  { dialstring }
        ::= { wfSwservOptsEntry 61 }

    wfSwservOptsCallbackDataRfc1570 OBJECT-TYPE
        SYNTAX	DisplayString
        ACCESS	read-write
        STATUS	mandatory
        DESCRIPTION
                "The PPP/LCP Callback Data; the actual callback client 
		data which is sent to the callback server for processing"
        ::= { wfSwservOptsEntry 62 }


    wfSwservOutPhoneNumTable OBJECT-TYPE
        SYNTAX	SEQUENCE OF WfSwservOutPhoneNumEntry
        ACCESS	not-accessible
        STATUS	mandatory
        DESCRIPTION
                "***************************************
                SWSERV outgoing phone number list "
        ::= { wfCircuitOptsGroup 6 }

    wfSwservOutPhoneNumEntry OBJECT-TYPE
        SYNTAX	WfSwservOutPhoneNumEntry
        ACCESS	not-accessible
        STATUS	mandatory
        DESCRIPTION
                "An entry in the SWSERV_SYNC table"
        INDEX	{ wfSwservOutPhoneNumCct,
    		  wfSwservOutPhoneNumIndex }
        ::= { wfSwservOutPhoneNumTable 1 }

    WfSwservOutPhoneNumEntry ::= SEQUENCE {
    	    wfSwservOutPhoneNumDelete
    		INTEGER,
    	    wfSwservOutPhoneNumCct
    		INTEGER,
    	    wfSwservOutPhoneNumIndex
    		INTEGER,
    	    wfSwservOutPhoneNumRmtStationNum
    		DisplayString,
    	    wfSwservOutPhoneNumSubAddr
    		DisplayString,
    	    wfSwservOutPhoneNumDelimiter
    		DisplayString,
    	    wfSwservOutPhoneNumType
    		INTEGER,
    	    wfSwservOutPhoneNumTypeofNum
    		INTEGER,
    	    wfSwservOutPhoneNumPlan
    		INTEGER,
    	    wfSwservOutPhoneNumRateAdaption
    		INTEGER,
	    wfSwservOutPhoneNumRemotePoolType
    		INTEGER,
	    wfSwservOutPhoneNumConnectionType
                INTEGER,
            wfSwservOutPhoneNumChannelType
                INTEGER,
            wfSwservOutPhoneNumAggrChanCnt
		INTEGER,
    	    wfSwservOutPhoneNumPrefix
    		DisplayString,
	    wfSwservOutPhoneNumBearerService
		INTEGER
        }

    wfSwservOutPhoneNumDelete OBJECT-TYPE
        SYNTAX	INTEGER {
    		    create(1),
    		    delete(2)
    		}
        ACCESS	read-write
        STATUS	mandatory
        DESCRIPTION
                "Delete this phone number from the list"
        DEFVAL	{ create }
        ::= { wfSwservOutPhoneNumEntry 1 }

    wfSwservOutPhoneNumCct OBJECT-TYPE
        SYNTAX	INTEGER(1..1023)
        ACCESS	read-only
        STATUS	mandatory
        DESCRIPTION
                "CCT number for this phone list instance"
        ::= { wfSwservOutPhoneNumEntry 2 }

    wfSwservOutPhoneNumIndex OBJECT-TYPE
        SYNTAX	INTEGER(1..255)
        ACCESS	read-only
        STATUS	mandatory
        DESCRIPTION
                "a unique one up type number to create a list"
        ::= { wfSwservOutPhoneNumEntry 3 }

    wfSwservOutPhoneNumRmtStationNum OBJECT-TYPE
        SYNTAX	DisplayString
        ACCESS	read-write
        STATUS	mandatory
        DESCRIPTION
                "the station address (phone number) of the remote system"
        ::= { wfSwservOutPhoneNumEntry 4 }

    wfSwservOutPhoneNumSubAddr OBJECT-TYPE
        SYNTAX	DisplayString
        ACCESS	read-write
        STATUS	mandatory
        DESCRIPTION
                "for Swserv phone numbers, the sub address portion"
        ::= { wfSwservOutPhoneNumEntry 5 }

    wfSwservOutPhoneNumDelimiter OBJECT-TYPE
        SYNTAX	DisplayString
        ACCESS	read-write
        STATUS	mandatory
        DESCRIPTION
                "for Swserv phone numbers, the delimiter portion"
        ::= { wfSwservOutPhoneNumEntry 6 }

    wfSwservOutPhoneNumType OBJECT-TYPE
        SYNTAX	INTEGER {
    		    dial(1),
    		    isdn(2),
		    dialasync(3)
    		}
        ACCESS	read-write
        STATUS	mandatory
        DESCRIPTION
                "phone number types; ISDN types, Modem Sync Dial or Async
		 Dial types"
        DEFVAL	{ dial }
        ::= { wfSwservOutPhoneNumEntry 7 }

    wfSwservOutPhoneNumTypeofNum OBJECT-TYPE
        SYNTAX	INTEGER {
    		    unknown(1),
    		    international(16),
    		    national(32),
    		    specific(48),
    		    subscriber(64),
    		    abbreviated(96)
    		}
        ACCESS	read-write
        STATUS	mandatory
        DESCRIPTION
                "IF ISDN type number, it needs type of number
                UNKNOWN Type is 0, use 1 to satisfy MDL requirement
                This attribute value will be ANDED with  0xFFF0 before using it."
        DEFVAL	{ unknown }
        ::= { wfSwservOutPhoneNumEntry 8 }

    wfSwservOutPhoneNumPlan OBJECT-TYPE
        SYNTAX	INTEGER {
    		    unknown(16),
    		    telephony(1),
    		    x121(3),
    		    telex(4),
    		    standard(8),
    		    private(9)
    		}
        ACCESS	read-write
        STATUS	mandatory
        DESCRIPTION
                "If Isdn and if type of number is UNKNOWN or INERNATIONAL or NATIONAL
                or SUBSCRIBER  then a plan number is needed. UNKNOWN is 0 ,
                using 16 (0x10)to satisfy MDL requirement. We will AND  this field with
                0x0F before using it."
        DEFVAL	{ unknown }
        ::= { wfSwservOutPhoneNumEntry 9 }

    wfSwservOutPhoneNumRateAdaption OBJECT-TYPE
        SYNTAX	INTEGER {
    		    rate64(1),
    		    rate56(2)
    		}
        ACCESS	read-write
        STATUS	mandatory
        DESCRIPTION
                "If Isdn and if a specifis Transfer rate is to be requested when
                establishing a call to this distination address specify the desired
                rate."
        DEFVAL	{ rate64 }
        ::= { wfSwservOutPhoneNumEntry 10 }

    wfSwservOutPhoneNumRemotePoolType OBJECT-TYPE
        SYNTAX	INTEGER {
		    dialondemand(1),
    		    bandwidthondemand(2),
    		    dialandbandwidth(3)
    		}
        ACCESS	read-write
        STATUS	mandatory
        DESCRIPTION
                "Specify the types of calls accepted by the remote router on this port.	
		 For example, if the port on the remote router resides in only a demand 
		pool specify the port type for this phone number to be dialondemand."
        DEFVAL	{ dialandbandwidth }
        ::= { wfSwservOutPhoneNumEntry 11 }
    wfSwservOutPhoneNumConnectionType OBJECT-TYPE
        SYNTAX	INTEGER {
		    single(1),
    		    multiple(2)
    		}
        ACCESS	read-write
        STATUS	mandatory
        DESCRIPTION
                "Specify if this phone number can be used to receive a single call or multiple calls."

        DEFVAL	{ multiple }
        ::= { wfSwservOutPhoneNumEntry 12 }

    wfSwservOutPhoneNumChannelType OBJECT-TYPE
        SYNTAX  INTEGER {
                    bchannel(1),
                    multirate(2)
                  }
        ACCESS  read-write
        STATUS  mandatory
        DESCRIPTION
                "Type of Channels used for the outgoing call."
        DEFVAL  { bchannel }
        ::= { wfSwservOutPhoneNumEntry 13 }

    wfSwservOutPhoneNumAggrChanCnt OBJECT-TYPE
        SYNTAX  INTEGER(2..23)
        ACCESS  read-write
        STATUS  mandatory
        DESCRIPTION
                "Multiplier for the Multirate call."
        ::= { wfSwservOutPhoneNumEntry 14 }

    wfSwservOutPhoneNumPrefix OBJECT-TYPE
        SYNTAX	DisplayString
        ACCESS	read-write
        STATUS	mandatory
        DESCRIPTION
                "Phone number prefix such as hayes dial command."
        ::= { wfSwservOutPhoneNumEntry 15 }
	
    wfSwservOutPhoneNumBearerService OBJECT-TYPE
	SYNTAX	INTEGER {
			voice (1),
			data  (2)
			}
	ACCESS  read-write
	STATUS  mandatory
	DESCRIPTION
		"The Bearer service - data or voice, for ISDN call setup using this number"
	DEFVAL  { data }
	::= { wfSwservOutPhoneNumEntry 16 }

    wfSwservInPhoneNumTable OBJECT-TYPE
        SYNTAX	SEQUENCE OF WfSwservInPhoneNumEntry
        ACCESS	not-accessible
        STATUS	mandatory
        DESCRIPTION
                "SWSERV Ingoing phone number list "
        ::= { wfCircuitOptsGroup 7 }

    wfSwservInPhoneNumEntry OBJECT-TYPE
        SYNTAX	WfSwservInPhoneNumEntry
        ACCESS	not-accessible
        STATUS	mandatory
        DESCRIPTION
                "An entry in the Swserv_SYNC table"
        INDEX	{ wfSwservInPhoneNumIndex }
        ::= { wfSwservInPhoneNumTable 1 }

    WfSwservInPhoneNumEntry ::= SEQUENCE {
    	    wfSwservInPhoneNumDelete
    		INTEGER,
    	    wfSwservInPhoneNumIndex
    		INTEGER,
    	    wfSwservInPhoneNumRmtStationNum
    		DisplayString,
    	    wfSwservInPhoneNumSubAddr
    		DisplayString,
    	    wfSwservInPhoneNumDelimiter
    		DisplayString,
    	    wfSwservInPhoneNumType
    		INTEGER,
    	    wfSwservInPhoneNumTypeofNum
    		INTEGER,
    	    wfSwservInPhoneNumPlan
    		INTEGER,
            wfSwservInPhoneNumCct
                INTEGER
        }

    wfSwservInPhoneNumDelete OBJECT-TYPE
        SYNTAX	INTEGER {
    		    create(1),
    		    delete(2)
    		}
        ACCESS	read-write
        STATUS	mandatory
        DESCRIPTION
                "Delete this phone number from the list"
        DEFVAL	{ create }
        ::= { wfSwservInPhoneNumEntry 1 }

    wfSwservInPhoneNumIndex OBJECT-TYPE
        SYNTAX	INTEGER(1..255)
        ACCESS	read-only
        STATUS	mandatory
        DESCRIPTION
                "a unique one up type number to create a list"
        ::= { wfSwservInPhoneNumEntry 2 }

    wfSwservInPhoneNumRmtStationNum OBJECT-TYPE
        SYNTAX	DisplayString
        ACCESS	read-write
        STATUS	mandatory
        DESCRIPTION
                "the station address (phone number) of the remote system"
        ::= { wfSwservInPhoneNumEntry 3 }

    wfSwservInPhoneNumSubAddr OBJECT-TYPE
        SYNTAX	DisplayString
        ACCESS	read-write
        STATUS	mandatory
        DESCRIPTION
                "for Swserv phone numbers, the sub address portion"
        ::= { wfSwservInPhoneNumEntry 4 }

    wfSwservInPhoneNumDelimiter OBJECT-TYPE
        SYNTAX	DisplayString
        ACCESS	read-write
        STATUS	mandatory
        DESCRIPTION
                "for Swserv phone numbers, the delimiter portion"
        ::= { wfSwservInPhoneNumEntry 5 }

    wfSwservInPhoneNumType OBJECT-TYPE
        SYNTAX	INTEGER {
    		    dial(1),
    		    isdn(2)
    		}
        ACCESS	read-write
        STATUS	mandatory
        DESCRIPTION
                "phone number types; ISDN types or Modem Dial types"
        DEFVAL	{ dial }
        ::= { wfSwservInPhoneNumEntry 6 }

    wfSwservInPhoneNumTypeofNum OBJECT-TYPE
        SYNTAX	INTEGER {
    		    unknown(1),
    		    international(16),
    		    national(32),
    		    specific(48),
    		    subscriber(64),
    		    abbreviated(96)
    		}
        ACCESS	read-write
        STATUS	mandatory
        DESCRIPTION
                "We will AND  this field with  0x0xFFF0 before using it."
        DEFVAL	{ unknown }
        ::= { wfSwservInPhoneNumEntry 7 }

    wfSwservInPhoneNumPlan OBJECT-TYPE
        SYNTAX	INTEGER {
    		    unknown(16),
    		    telephony(1),
    		    x121(3),
    		    telex(4),
    		    standard(8),
    		    private(9)
    		}
        ACCESS	read-write
        STATUS	mandatory
        DESCRIPTION
                "0x0F before using it."
        DEFVAL	{ unknown }
        ::= { wfSwservInPhoneNumEntry 8 }

    wfSwservInPhoneNumCct OBJECT-TYPE
        SYNTAX	INTEGER
        ACCESS  read-write
        STATUS  mandatory
        DESCRIPTION
                "Identifies which circuit should be used when performing
                 Callback.  If Null, Authentication must complete before
                 Callback can occur."
        ::= { wfSwservInPhoneNumEntry 9 }


    wfCctOptsBrBuPppFilterTable OBJECT-TYPE
        SYNTAX	SEQUENCE OF WfCctOptsBrBuPppFilterEntry
        ACCESS	not-accessible
        STATUS	mandatory
        DESCRIPTION
                "Dial Backup PPP Datalink filter table"
        ::= { wfCircuitOptsGroup 8 }

    wfCctOptsBrBuPppFilterEntry OBJECT-TYPE
        SYNTAX	WfCctOptsBrBuPppFilterEntry
        ACCESS	not-accessible
        STATUS	mandatory
        DESCRIPTION
                "An entry in WfCctOptsBrBuPppFilterTable."
        INDEX	{ wfCctOptsBrBuPppFilterCct,
    		  wfCctOptsBrBuPppFilterRuleNumber,
    		  wfCctOptsBrBuPppFilterFragment }
        ::= { wfCctOptsBrBuPppFilterTable 1 }

    WfCctOptsBrBuPppFilterEntry ::= SEQUENCE {
    	    wfCctOptsBrBuPppFilterCreate
    		INTEGER,
    	    wfCctOptsBrBuPppFilterEnable
    		INTEGER,
    	    wfCctOptsBrBuPppFilterState
    		INTEGER,
    	    wfCctOptsBrBuPppFilterCounter
    		Counter,
    	    wfCctOptsBrBuPppFilterDefinition
    		OCTET STRING,
    	    wfCctOptsBrBuPppFilterReserved
    		INTEGER,
    	    wfCctOptsBrBuPppFilterCct
    		INTEGER,
    	    wfCctOptsBrBuPppFilterRuleNumber
    		INTEGER,
    	    wfCctOptsBrBuPppFilterFragment
    		INTEGER,
    	    wfCctOptsBrBuPppFilterName
    		DisplayString
        }

    wfCctOptsBrBuPppFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfCctOptsBrBuPppFilterEntry 1 }

    wfCctOptsBrBuPppFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfCctOptsBrBuPppFilterEntry 2 }

    wfCctOptsBrBuPppFilterState OBJECT-TYPE
        SYNTAX	INTEGER {
    		    active(1),
    		    error(2),
    		    inactive(3)
    		}
        ACCESS	read-only
        STATUS	mandatory
        DESCRIPTION
                "Defines the current State of the traffic filter:
                inactive - the rule is not in use.
                active - the rule is being used.
                error - the application detected an error in the rule."
        DEFVAL	{ inactive }
        ::= { wfCctOptsBrBuPppFilterEntry 3 }

    wfCctOptsBrBuPppFilterCounter OBJECT-TYPE
        SYNTAX	Counter
        ACCESS	read-only
        STATUS	mandatory
        DESCRIPTION
                "The number of received packets that have
                matched this rule."
        ::= { wfCctOptsBrBuPppFilterEntry 4 }

    wfCctOptsBrBuPppFilterDefinition OBJECT-TYPE
        SYNTAX	OCTET STRING
        ACCESS	read-write
        STATUS	mandatory
        DESCRIPTION
                "The filter rule definition."
        ::= { wfCctOptsBrBuPppFilterEntry 5 }

    wfCctOptsBrBuPppFilterReserved OBJECT-TYPE
        SYNTAX	INTEGER
        ACCESS	read-only
        STATUS	mandatory
        DESCRIPTION
                "Reserved field."
        ::= { wfCctOptsBrBuPppFilterEntry 6 }

    wfCctOptsBrBuPppFilterCct OBJECT-TYPE
        SYNTAX	INTEGER
        ACCESS	read-only
        STATUS	mandatory
        DESCRIPTION
                "The ID of the CctBridge Cct to which the
                filter is applied."
        ::= { wfCctOptsBrBuPppFilterEntry 7 }

    wfCctOptsBrBuPppFilterRuleNumber OBJECT-TYPE
        SYNTAX	INTEGER
        ACCESS	read-only
        STATUS	mandatory
        DESCRIPTION
                "ID for the rule."
        ::= { wfCctOptsBrBuPppFilterEntry 8 }

    wfCctOptsBrBuPppFilterFragment OBJECT-TYPE
        SYNTAX	INTEGER
        ACCESS	read-only
        STATUS	mandatory
        DESCRIPTION
                "Fragment number - for large rules."
        ::= { wfCctOptsBrBuPppFilterEntry 9 }

    wfCctOptsBrBuPppFilterName OBJECT-TYPE
        SYNTAX	DisplayString
        ACCESS	read-write
        STATUS	mandatory
        DESCRIPTION
                "name of the rule number"
        ::= { wfCctOptsBrBuPppFilterEntry 10 }

    wfCctOptsIpBuPppFilterTable OBJECT-TYPE
        SYNTAX	SEQUENCE OF WfCctOptsIpBuPppFilterEntry
        ACCESS	not-accessible
        STATUS	mandatory
        DESCRIPTION
                "IP Filter Table for Backup Lines"
        ::= { wfCircuitOptsGroup 9 }

    wfCctOptsIpBuPppFilterEntry OBJECT-TYPE
        SYNTAX	WfCctOptsIpBuPppFilterEntry
        ACCESS	not-accessible
        STATUS	mandatory
        DESCRIPTION
                "An entry in WfCctOptsIpBuPppFilterTable."
        INDEX	{ wfCctOptsIpBuPppFilterCct,
    		  wfCctOptsIpBuPppFilterRuleNumber,
    		  wfCctOptsIpBuPppFilterFragment }
        ::= { wfCctOptsIpBuPppFilterTable 1 }

    WfCctOptsIpBuPppFilterEntry ::= SEQUENCE {
    	    wfCctOptsIpBuPppFilterCreate
    		INTEGER,
    	    wfCctOptsIpBuPppFilterEnable
    		INTEGER,
    	    wfCctOptsIpBuPppFilterState
    		INTEGER,
    	    wfCctOptsIpBuPppFilterCounter
    		Counter,
    	    wfCctOptsIpBuPppFilterDefinition
    		OCTET STRING,
    	    wfCctOptsIpBuPppFilterReserved
    		INTEGER,
    	    wfCctOptsIpBuPppFilterCct
    		INTEGER,
    	    wfCctOptsIpBuPppFilterRuleNumber
    		INTEGER,
    	    wfCctOptsIpBuPppFilterFragment
    		INTEGER,
    	    wfCctOptsIpBuPppFilterName
    		DisplayString
        }

    wfCctOptsIpBuPppFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfCctOptsIpBuPppFilterEntry 1 }

    wfCctOptsIpBuPppFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfCctOptsIpBuPppFilterEntry 2 }

    wfCctOptsIpBuPppFilterState OBJECT-TYPE
        SYNTAX	INTEGER {
    		    active(1),
    		    error(2),
    		    inactive(3)
    		}
        ACCESS	read-only
        STATUS	mandatory
        DESCRIPTION
                "Defines the current State of the traffic filter:
                inactive - the rule is not in use.
                active - the rule is being used.
                error - the application detected an error in the rule."
        DEFVAL	{ inactive }
        ::= { wfCctOptsIpBuPppFilterEntry 3 }

    wfCctOptsIpBuPppFilterCounter OBJECT-TYPE
        SYNTAX	Counter
        ACCESS	read-only
        STATUS	mandatory
        DESCRIPTION
                "The number of received packets that have
                matched this rule."
        ::= { wfCctOptsIpBuPppFilterEntry 4 }

    wfCctOptsIpBuPppFilterDefinition OBJECT-TYPE
        SYNTAX	OCTET STRING
        ACCESS	read-write
        STATUS	mandatory
        DESCRIPTION
                "The filter rule definition."
        ::= { wfCctOptsIpBuPppFilterEntry 5 }

    wfCctOptsIpBuPppFilterReserved OBJECT-TYPE
        SYNTAX	INTEGER
        ACCESS	read-only
        STATUS	mandatory
        DESCRIPTION
                "Reserved field."
        ::= { wfCctOptsIpBuPppFilterEntry 6 }

    wfCctOptsIpBuPppFilterCct OBJECT-TYPE
        SYNTAX	INTEGER
        ACCESS	read-only
        STATUS	mandatory
        DESCRIPTION
                "The ID of the CctBridge Cct to which the
                filter is applied."
        ::= { wfCctOptsIpBuPppFilterEntry 7 }

    wfCctOptsIpBuPppFilterRuleNumber OBJECT-TYPE
        SYNTAX	INTEGER
        ACCESS	read-only
        STATUS	mandatory
        DESCRIPTION
                "ID for the rule."
        ::= { wfCctOptsIpBuPppFilterEntry 8 }

    wfCctOptsIpBuPppFilterFragment OBJECT-TYPE
        SYNTAX	INTEGER
        ACCESS	read-only
        STATUS	mandatory
        DESCRIPTION
                "Fragment number - for large rules."
        ::= { wfCctOptsIpBuPppFilterEntry 9 }

    wfCctOptsIpBuPppFilterName OBJECT-TYPE
        SYNTAX	DisplayString
        ACCESS	read-write
        STATUS	mandatory
        DESCRIPTION
                "name of the rule number"
        ::= { wfCctOptsIpBuPppFilterEntry 10 }

    wfCctOptsCngcTable OBJECT-TYPE
        SYNTAX	SEQUENCE OF WfCctOptsCngcEntry
        ACCESS	not-accessible
        STATUS	mandatory
        DESCRIPTION
                "BNX Switch congestion control Table"
        ::= { wfCircuitOptsGroup 10 }

    wfCctOptsCngcEntry OBJECT-TYPE
        SYNTAX	WfCctOptsCngcEntry
        ACCESS	not-accessible
        STATUS	mandatory
        DESCRIPTION
                "An entry in WfCctOptsCngcTable."
        INDEX	{ wfCctOptsCngcCct }
        ::= { wfCctOptsCngcTable 1 }

    WfCctOptsCngcEntry ::= SEQUENCE {
    	    wfCctOptsCngcDelete
    		INTEGER,
    	    wfCctOptsCngcDisable
    		INTEGER,
    	    wfCctOptsCngcCct
    		INTEGER,
    	    wfCctOptsCngcSmdsDiscardability
    		INTEGER,
    	    wfCctOptsCngcCfgSwtxqThreshold
    		INTEGER,
    	    wfCctOptsCngcSwtxqThreshold
    		INTEGER,
    	    wfCctOptsCngcCngLevel0Threshold
    		INTEGER,
    	    wfCctOptsCngcCngLevel1Threshold
    		INTEGER,
    	    wfCctOptsCngcCngLevel2Threshold
    		INTEGER,
    	    wfCctOptsCngcLinkType
    		INTEGER,
    	    wfCctOptsCngcTrfPriorityEnable
    		INTEGER,
    	    wfCctOptsCngcPortIPTrfPriority
    		INTEGER,
    	    wfCctOptsCngcPortTrfDiscardLvl
    		INTEGER,
    	    wfCctOptsCngcPortTrfPriority
    		INTEGER,
    	    wfCctOptsCngcCfgHwtxQThreshold
    		INTEGER,
    	    wfCctOptsCngcHwtxQThreshold
    		INTEGER,
    	    wfCctOptsCngcSndTrapForPktsDropped
    		INTEGER,
    	    wfCctOptsCngcCfgQp0Threshold
    		INTEGER,
    	    wfCctOptsCngcQp0Threshold
    		INTEGER,
    	    wfCctOptsCngcQp0CngLvl0Threshold
    		INTEGER,
    	    wfCctOptsCngcQp0CngLvl1Threshold
    		INTEGER,
    	    wfCctOptsCngcQp0CngLvl2Threshold
    		INTEGER,
    	    wfCctOptsCngcQp0PktsServPriNxtQ
    		INTEGER,
    	    wfCctOptsCngcCfgQp1Threshold
    		INTEGER,
    	    wfCctOptsCngcQp1Threshold
    		INTEGER,
    	    wfCctOptsCngcQp1CngLvl0Threshold
    		INTEGER,
    	    wfCctOptsCngcQp1CngLvl1Threshold
    		INTEGER,
    	    wfCctOptsCngcQp1CngLvl2Threshold
    		INTEGER,
    	    wfCctOptsCngcQp1PktsServPriNxtQ
    		INTEGER,
    	    wfCctOptsCngcCfgQp2Threshold
    		INTEGER,
    	    wfCctOptsCngcQp2Threshold
    		INTEGER,
    	    wfCctOptsCngcQp2CngLvl0Threshold
    		INTEGER,
    	    wfCctOptsCngcQp2CngLvl1Threshold
    		INTEGER,
    	    wfCctOptsCngcQp2CngLvl2Threshold
    		INTEGER,
    	    wfCctOptsCngcQp2PktsServPriNxtQ
    		INTEGER,
    	    wfCctOptsCngcCfgQp3Threshold
    		INTEGER,
    	    wfCctOptsCngcQp3Threshold
    		INTEGER,
    	    wfCctOptsCngcQp3CngLvl0Threshold
    		INTEGER,
    	    wfCctOptsCngcQp3CngLvl1Threshold
    		INTEGER,
    	    wfCctOptsCngcQp3CngLvl2Threshold
    		INTEGER,
    	    wfCctOptsCngcPriority0TxPkts
    		Counter,
    	    wfCctOptsCngcPriority0TxOctets
    		Counter,
    	    wfCctOptsCngcPriority0DropPkts
    		Counter,
    	    wfCctOptsCngcPriority0DropOctets
    		Counter,
    	    wfCctOptsCngcPriority1TxPkts
    		Counter,
    	    wfCctOptsCngcPriority1TxOctets
    		Counter,
    	    wfCctOptsCngcPriority1DropPkts
    		Counter,
    	    wfCctOptsCngcPriority1DropOctets
    		Counter,
    	    wfCctOptsCngcPriority2TxPkts
    		Counter,
    	    wfCctOptsCngcPriority2TxOctets
    		Counter,
    	    wfCctOptsCngcPriority2DropPkts
    		Counter,
    	    wfCctOptsCngcPriority2DropOctets
    		Counter,
    	    wfCctOptsCngcPriority3TxPkts
    		Counter,
    	    wfCctOptsCngcPriority3TxOctets
    		Counter,
    	    wfCctOptsCngcPriority3DropPkts
    		Counter,
    	    wfCctOptsCngcPriority3DropOctets
    		Counter,
    	    wfCctOptsCngcTxFRNonDePkts
    		Counter,
    	    wfCctOptsCngcTxFRNonDeOctets
    		Counter,
    	    wfCctOptsCngcTxFRDePkts
    		Counter,
    	    wfCctOptsCngcTxFRDeOctets
    		Counter,
    	    wfCctOptsCngcDropFRNonDePkts
    		Counter,
    	    wfCctOptsCngcDropFRNonDeOctets
    		Counter,
    	    wfCctOptsCngcDropFRDePkts
    		Counter,
    	    wfCctOptsCngcDropFRDeOctets
    		Counter,
    	    wfCctOptsCngcFRSetFecnPkts
    		Counter,
    	    wfCctOptsCngcFRSetFecnOctets
    		Counter,
    	    wfCctOptsCngcFRSetBecnPkts
    		Counter,
    	    wfCctOptsCngcFRSetBecnOctets
    		Counter,
    	    wfCctOptsCngcDropNonFRPkts
    		Counter,
            wfCctOptsCngcDropNonFROctets
    		Counter,
            wfCctOptsCngcLogPower
    		INTEGER    		
        }

    wfCctOptsCngcDelete OBJECT-TYPE
        SYNTAX	INTEGER {
    		    created(1),
    		    deleted(2)
    		}
        ACCESS	read-write
        STATUS	mandatory
        DESCRIPTION
                "Defines the existence of the congestion control entry
                CNGC_CREATED - congestion control entry exists
                CNGC_DELETED - congestion control entry does not exist and can
                          be deleted. "
        DEFVAL	{ created }
        ::= { wfCctOptsCngcEntry 1 }

    wfCctOptsCngcDisable OBJECT-TYPE
        SYNTAX	INTEGER {
    		    enabled(1),
    		    disabled(2)
    		}
        ACCESS	read-write
        STATUS	mandatory
        DESCRIPTION
                "Defines whether congestion control is enabled or disabled on the
                circuit"
        DEFVAL	{ enabled }
        ::= { wfCctOptsCngcEntry 2 }

    wfCctOptsCngcCct OBJECT-TYPE
        SYNTAX	INTEGER
        ACCESS	read-only
        STATUS	mandatory
        DESCRIPTION
                "The circuit number of the circuit to which the entry is applied"
        ::= { wfCctOptsCngcEntry 3 }

    wfCctOptsCngcSmdsDiscardability OBJECT-TYPE
        SYNTAX	INTEGER {
    		    datagram(1),
    		    frde(2),
    		    frnde(3)
    		}
        ACCESS	read-write
        STATUS	mandatory
        DESCRIPTION
                "This is obsolete in V5.0 and upwards.
                Defines how SMDS packets entering BNX network through
                SMDS SSI and SMDS SNI interfaces should be treated at this
                circuit during congestion for dropping. This is applicable
                only on the internodal links.
                     CNGC_FRDE - treat this like Frame relay DE frame.
                     CNGC_FRNDE - treat this like Frame Relay non DE frame
                     CNGC_DATAGRAM - treat this like a datagram packet. "
        DEFVAL	{ datagram }
        ::= { wfCctOptsCngcEntry 4 }

    wfCctOptsCngcCfgSwtxqThreshold OBJECT-TYPE
        SYNTAX	INTEGER(1..256)
        ACCESS	read-write
        STATUS	mandatory
        DESCRIPTION
                "This is obsolete in V5.0 and upwards.
                Defines the user configured software transmit queue threshold.
                If this is set to NULL_VAL then the switch calculates
                the default value depending on the media and uses the default value.
                The default value is recommended."
        ::= { wfCctOptsCngcEntry 5 }

    wfCctOptsCngcSwtxqThreshold OBJECT-TYPE
        SYNTAX	INTEGER
        ACCESS	read-only
        STATUS	mandatory
        DESCRIPTION
                "This is obsolete in V5.0 and upwards.
                Defines the software transmit queue threshold in use.
                Switch updates this attribute to inform user what the
                current software transmit queue threshold is."
        ::= { wfCctOptsCngcEntry 6 }

    wfCctOptsCngcCngLevel0Threshold OBJECT-TYPE
        SYNTAX	INTEGER(1..100)
        ACCESS	read-write
        STATUS	mandatory
        DESCRIPTION
                "This is obsolete in V5.0 and upwards.
                Defines the Software Transmit Queue congestion level 0 threshold
                as a percentage of the Software Transmit Queue Threshold.
                The default value is recommended."
        DEFVAL	{ 25 }
        ::= { wfCctOptsCngcEntry 7 }

    wfCctOptsCngcCngLevel1Threshold OBJECT-TYPE
        SYNTAX	INTEGER(1..100)
        ACCESS	read-write
        STATUS	mandatory
        DESCRIPTION
                "This is obsolete in V5.0 and upwards.
                Defines the Software Transmit Queue congestion level 1 threshold
                as a percentage of the Software Transmit Queue Threshold.
                The default value is recommended.
                wfCctOptsCngcCngLevel1Threshold should be more than
                wfCctOptsCngcCngLevel0Threshold, otherwise there will be no
                congestion level 1."
        DEFVAL	{ 50 }
        ::= { wfCctOptsCngcEntry 8 }

    wfCctOptsCngcCngLevel2Threshold OBJECT-TYPE
        SYNTAX	INTEGER(1..100)
        ACCESS	read-write
        STATUS	mandatory
        DESCRIPTION
                "This is obsolete in V5.0 and upwards.
                Defines the Software Transmit Queue congestion level 2 threshold
                as a percentage of the Software Transmit Queue Threshold.
                The default value is recommended.
                wfCctOptsCngcCngLevel2Threshold should be more than
                wfCctOptsCngcCngLevel1Threshold, otherwise there will be no
                congestion level 2."
        DEFVAL	{ 75 }
        ::= { wfCctOptsCngcEntry 9 }

    wfCctOptsCngcLinkType OBJECT-TYPE
        SYNTAX	INTEGER {
    		    access(1),
    		    nodal(2)
    		}
        ACCESS	read-write
        STATUS	mandatory
        DESCRIPTION
                "Defines whether the circuit is an access link or inter-nodal
                link (trunk).
                Traffic monitoring, traffic priority determination, traffic
                discardability level determination are done at access link and each
                incoming packet on an access link is tagged with the information.
                Inter-nodal link (trunk) uses the above tagged information in packets
                for priority queueing and discarding packets during congestion.
                WARNING - It is important to set the appropriate link type for this
                attribute otherwise congestion control will not work. The default
                value for this attribute is access link. This attribute value
                must be changed to CNGC_LINK_INTER_NODAL for inter-nodal link(trunk)."
        DEFVAL	{ access }
        ::= { wfCctOptsCngcEntry 10 }

    wfCctOptsCngcTrfPriorityEnable OBJECT-TYPE
        SYNTAX	INTEGER {
    		    enabled(1),
    		    disabled(2)
    		}
        ACCESS	read-write
        STATUS	mandatory
        DESCRIPTION
                "Defines whether traffic prioritization is enabled or disabled
                on the circuit."
        DEFVAL	{ disabled }
        ::= { wfCctOptsCngcEntry 11 }

    wfCctOptsCngcPortIPTrfPriority OBJECT-TYPE
        SYNTAX	INTEGER {
    		    one(1),
    		    two(2),
    		    three(3)
    		}
        ACCESS	read-write
        STATUS	mandatory
        DESCRIPTION
                "Defines the traffic priority for transmitting Non Frame Relay
                or SMDS traffic on this port.
                       CNGC_IPPRIORITY_TWO - Default Value
                          Set all non FR or SMDS user traffic packets to priority 2.
                       CNGC_IPPRIORITY_ONE - Set all non FR or SMDS packets to priority 1.
                       CNGC_IPPRIORITY_TWO - Set all non FR or SMDS packets to priority 2.
                       CNGC_IPPRIORITY_THREE - Set all non FR or SMDS packets to priority 3."
        DEFVAL	{ two }
        ::= { wfCctOptsCngcEntry 12 }

    wfCctOptsCngcPortTrfDiscardLvl OBJECT-TYPE
        SYNTAX	INTEGER {
    		    one(1),
    		    two(2),
    		    three(3),
    		    four(4)
    		}
        ACCESS	read-write
        STATUS	mandatory
        DESCRIPTION
                "Defines at what congestion level the incoming packets on this
                port should be discarded in the network.
                CNGC_DISCARD_AT_LVL_TWO - Discard FR DE packets at level 2,
                                              discard FR non DE packets at level 4,
                                              discard SMDS packets at level 3,
                                              discard IP packets at level 3.
                                              Default value
                CNGC_DISCARD_AT_LVL_ONE - discard all at level 1
                CNGC_DISCARD_AT_LVL_TWO - discard all at level 2
                CNGC_DISCARD_AT_LVL_THREE - discard all at level 3
                CNGC_DISCARD_AT_LVL_FOUR - discard all at level 4"
        DEFVAL	{ two }
        ::= { wfCctOptsCngcEntry 13 }

    wfCctOptsCngcPortTrfPriority OBJECT-TYPE
        SYNTAX	INTEGER {
    		    one(1),
    		    two(2),
    		    three(3)
    		}
        ACCESS	read-write
        STATUS	mandatory
        DESCRIPTION
                "Defines the traffic priority level of all the incoming packets
                on this port.
                CNGC_PRIORITY_TWO - Default value
                   Set all incoming user traffic packets to priority 2.
                CNGC_PRIORITY_ONE - Set all incoming packets to priority 1.
                CNGC_PRIORITY_TWO - Set all incoming packets to priority 2.
                CNGC_PRIORITY_THREE - Set all incoming packets to priority 3.
                Priority 0 is reserved for network critical packets like
                OSPF, FR LMI and SMDS heartbeat, Cross Net polling and is
                    not available for user traffic."
        DEFVAL	{ two }
        ::= { wfCctOptsCngcEntry 14 }

    wfCctOptsCngcCfgHwtxQThreshold OBJECT-TYPE
        SYNTAX	INTEGER(1..64)
        ACCESS	read-write
        STATUS	mandatory
        DESCRIPTION
                "Defines the user configured hardware transmit queue threshold.
                NULL_VAL - Switch calculates the appropriate value based on
                           system resources and uses the value. This is recommended.
                CNGC_HWTXQ_MINIMUM - minimum value to be used.
                CNGC_HWTXQ_MAXIMUM - maximum value to be used."
        ::= { wfCctOptsCngcEntry 15 }

    wfCctOptsCngcHwtxQThreshold OBJECT-TYPE
        SYNTAX	INTEGER
        ACCESS	read-only
        STATUS	mandatory
        DESCRIPTION
                "The current hardware queue threshold"
        ::= { wfCctOptsCngcEntry 16 }

    wfCctOptsCngcSndTrapForPktsDropped OBJECT-TYPE
        SYNTAX	INTEGER(100..1000000)
        ACCESS	read-write
        STATUS	mandatory
        DESCRIPTION
                "Switch sends a congestion notification trap for every
                wfCctOptsCngcSndTrapForPktsDropped number of packets dropped."
        DEFVAL	{ 100000 }
        ::= { wfCctOptsCngcEntry 17 }

    wfCctOptsCngcCfgQp0Threshold OBJECT-TYPE
        SYNTAX	INTEGER(1..2048)
        ACCESS	read-write
        STATUS	mandatory
        DESCRIPTION
                "Defines the Priority 0 queue threshold
                NULL_VAL - Switch calculates the appropriate value based on
                           system resources and uses the value. This is recommended."
        ::= { wfCctOptsCngcEntry 18 }

    wfCctOptsCngcQp0Threshold OBJECT-TYPE
        SYNTAX	INTEGER
        ACCESS	read-only
        STATUS	mandatory
        DESCRIPTION
                "current Priority 0 queue threshold"
        ::= { wfCctOptsCngcEntry 19 }

    wfCctOptsCngcQp0CngLvl0Threshold OBJECT-TYPE
        SYNTAX	INTEGER(1..100)
        ACCESS	read-write
        STATUS	mandatory
        DESCRIPTION
                "Defines priority 0 queue congestion level 0 threshold as a
                percentage of priority 0 queue threshold."
        DEFVAL	{ 25 }
        ::= { wfCctOptsCngcEntry 20 }

    wfCctOptsCngcQp0CngLvl1Threshold OBJECT-TYPE
        SYNTAX	INTEGER(1..100)
        ACCESS	read-write
        STATUS	mandatory
        DESCRIPTION
                "Defines priority 0 queue congestion level 1 threshold as a
                percentage of priority 0 queue threshold.
                The value of this attribute should be greater than
                wfCctOptsCngcQp0CngLvl0Threshold, otherwise there will be no
                priority 0 queue congestion level 1."
        DEFVAL	{ 50 }
        ::= { wfCctOptsCngcEntry 21 }

    wfCctOptsCngcQp0CngLvl2Threshold OBJECT-TYPE
        SYNTAX	INTEGER(1..100)
        ACCESS	read-write
        STATUS	mandatory
        DESCRIPTION
                "Defines priority 0 queue congestion level 2 threshold as a
                percentage of priority 0 queue threshold.
                The value of this attribute should be greater than
                wfCctOptsCngcQp0CngLvl1Threshold, otherwise there will be no
                priority 0 queue congestion level 2."
        DEFVAL	{ 75 }
        ::= { wfCctOptsCngcEntry 22 }

    wfCctOptsCngcQp0PktsServPriNxtQ OBJECT-TYPE
        SYNTAX	INTEGER(1..20)
        ACCESS	read-write
        STATUS	mandatory
        DESCRIPTION
                "Defines the number of priority 0 queue packets to be served
                prior to serving each priority 1 queue packet. If priority 0 queue
                is empty then priority 1 queue packets are served."
        DEFVAL	{ 2 }
        ::= { wfCctOptsCngcEntry 23 }

    wfCctOptsCngcCfgQp1Threshold OBJECT-TYPE
        SYNTAX	INTEGER(1..2048)
        ACCESS	read-write
        STATUS	mandatory
        DESCRIPTION
                "Defines the Priority 1 queue threshold
                NULL_VAL - Switch calculates the appropriate value based on
                           system resources and uses the value. This is recommended."
        ::= { wfCctOptsCngcEntry 24 }

    wfCctOptsCngcQp1Threshold OBJECT-TYPE
        SYNTAX	INTEGER
        ACCESS	read-only
        STATUS	mandatory
        DESCRIPTION
                "current Priority 0 queue threshold"
        ::= { wfCctOptsCngcEntry 25 }

    wfCctOptsCngcQp1CngLvl0Threshold OBJECT-TYPE
        SYNTAX	INTEGER(1..100)
        ACCESS	read-write
        STATUS	mandatory
        DESCRIPTION
                "Defines priority 1 queue congestion level 0 threshold as a
                percentage of priority 1 queue threshold."
        DEFVAL	{ 25 }
        ::= { wfCctOptsCngcEntry 26 }

    wfCctOptsCngcQp1CngLvl1Threshold OBJECT-TYPE
        SYNTAX	INTEGER(1..100)
        ACCESS	read-write
        STATUS	mandatory
        DESCRIPTION
                "Defines priority 1 queue congestion level 1 threshold as a
                percentage of priority 1 queue threshold.
                The value of this attribute should be greater than
                wfCctOptsCngcQp1CngLvl0Threshold, otherwise there will be no
                priority 1 queue congestion level 1."
        DEFVAL	{ 50 }
        ::= { wfCctOptsCngcEntry 27 }

    wfCctOptsCngcQp1CngLvl2Threshold OBJECT-TYPE
        SYNTAX	INTEGER(1..100)
        ACCESS	read-write
        STATUS	mandatory
        DESCRIPTION
                "Defines priority 1 queue congestion level 2 threshold as a
                percentage of priority 1 queue threshold.
                The value of this attribute should be greater than
                wfCctOptsCngcQp1CngLvl1Threshold, otherwise there will be no
                priority 1 queue congestion level 2."
        DEFVAL	{ 75 }
        ::= { wfCctOptsCngcEntry 28 }

    wfCctOptsCngcQp1PktsServPriNxtQ OBJECT-TYPE
        SYNTAX	INTEGER(1..20)
        ACCESS	read-write
        STATUS	mandatory
        DESCRIPTION
                "Defines the number of priority 1 queue packets to be served
                prior to serving each priority 2 queue packet. If priority 1 queue
                is empty then priority 2 queue packets are served."
        DEFVAL	{ 2 }
        ::= { wfCctOptsCngcEntry 29 }

    wfCctOptsCngcCfgQp2Threshold OBJECT-TYPE
        SYNTAX	INTEGER(1..2048)
        ACCESS	read-write
        STATUS	mandatory
        DESCRIPTION
                "Defines the Priority 2 queue threshold
                NULL_VAL - Switch calculates the appropriate value based on
                           system resources and uses the value. This is recommended."
        ::= { wfCctOptsCngcEntry 30 }

    wfCctOptsCngcQp2Threshold OBJECT-TYPE
        SYNTAX	INTEGER
        ACCESS	read-only
        STATUS	mandatory
        DESCRIPTION
                "current Priority 0 queue threshold"
        ::= { wfCctOptsCngcEntry 31 }

    wfCctOptsCngcQp2CngLvl0Threshold OBJECT-TYPE
        SYNTAX	INTEGER(1..100)
        ACCESS	read-write
        STATUS	mandatory
        DESCRIPTION
                "Defines priority 2 queue congestion level 0 threshold as a
                percentage of priority 2 queue threshold."
        DEFVAL	{ 25 }
        ::= { wfCctOptsCngcEntry 32 }

    wfCctOptsCngcQp2CngLvl1Threshold OBJECT-TYPE
        SYNTAX	INTEGER(1..100)
        ACCESS	read-write
        STATUS	mandatory
        DESCRIPTION
                "Defines priority 2 queue congestion level 1 threshold as a
                percentage of priority 2 queue threshold.
                The value of this attribute should be greater than
                wfCctOptsCngcQp2CngLvl0Threshold, otherwise there will be no
                priority 2 queue congestion level 1."
        DEFVAL	{ 50 }
        ::= { wfCctOptsCngcEntry 33 }

    wfCctOptsCngcQp2CngLvl2Threshold OBJECT-TYPE
        SYNTAX	INTEGER(1..100)
        ACCESS	read-write
        STATUS	mandatory
        DESCRIPTION
                "Defines priority 2 queue congestion level 2 threshold as a
                percentage of priority 2 queue threshold.
                The value of this attribute should be greater than
                wfCctOptsCngcQp2CngLvl1Threshold, otherwise there wil be no
                priority 2 queue congestion level 2."
        DEFVAL	{ 75 }
        ::= { wfCctOptsCngcEntry 34 }

    wfCctOptsCngcQp2PktsServPriNxtQ OBJECT-TYPE
        SYNTAX	INTEGER(1..20)
        ACCESS	read-write
        STATUS	mandatory
        DESCRIPTION
                "Defines the number of priority 2 queue packets to be served
                prior to serving each priority 3 queue packet. If priority 2 queue
                is empty then priority 3 queue packets are served."
        DEFVAL	{ 2 }
        ::= { wfCctOptsCngcEntry 35 }

    wfCctOptsCngcCfgQp3Threshold OBJECT-TYPE
        SYNTAX	INTEGER(1..2048)
        ACCESS	read-write
        STATUS	mandatory
        DESCRIPTION
                "Defines the Priority 3 queue threshold
                NULL_VAL - Switch calculates the appropriate value based on
                           system resources and uses the value. This is recommended."
        ::= { wfCctOptsCngcEntry 36 }

    wfCctOptsCngcQp3Threshold OBJECT-TYPE
        SYNTAX	INTEGER
        ACCESS	read-only
        STATUS	mandatory
        DESCRIPTION
                "current Priority 3 queue threshold"
        ::= { wfCctOptsCngcEntry 37 }

    wfCctOptsCngcQp3CngLvl0Threshold OBJECT-TYPE
        SYNTAX	INTEGER(1..100)
        ACCESS	read-write
        STATUS	mandatory
        DESCRIPTION
                "Defines priority 3 queue congestion level 0 threshold as a
                percentage of priority 3 queue threshold."
        DEFVAL	{ 25 }
        ::= { wfCctOptsCngcEntry 38 }

    wfCctOptsCngcQp3CngLvl1Threshold OBJECT-TYPE
        SYNTAX	INTEGER(1..100)
        ACCESS	read-write
        STATUS	mandatory
        DESCRIPTION
                "Defines priority 3 queue congestion level 1 threshold as a
                percentage of priority 3 queue threshold.
                The value of this attribute should be greater than
                wfCctOptsCngcQp3CngLvl0Threshold, otherwise there will be no
                priority 3 queue congestion level 1."
        DEFVAL	{ 50 }
        ::= { wfCctOptsCngcEntry 39 }

    wfCctOptsCngcQp3CngLvl2Threshold OBJECT-TYPE
        SYNTAX	INTEGER(1..100)
        ACCESS	read-write
        STATUS	mandatory
        DESCRIPTION
                "Defines priority 3 queue congestion level 2 threshold as a
                percentage of priority 3 queue threshold.
                The value of this attribute should be greater than
                wfCctOptsCngcQp3CngLvl1Threshold, otherwise there will be no
                priority 3 queue congestion level 2."
        DEFVAL	{ 75 }
        ::= { wfCctOptsCngcEntry 40 }

    wfCctOptsCngcPriority0TxPkts OBJECT-TYPE
        SYNTAX	Counter
        ACCESS	read-only
        STATUS	mandatory
        DESCRIPTION
                "Number of priority 0 packets transmitted"
        ::= { wfCctOptsCngcEntry 41 }

    wfCctOptsCngcPriority0TxOctets OBJECT-TYPE
        SYNTAX	Counter
        ACCESS	read-only
        STATUS	mandatory
        DESCRIPTION
                "Number of priority 0 Octets transmitted"
        ::= { wfCctOptsCngcEntry 42 }

    wfCctOptsCngcPriority0DropPkts OBJECT-TYPE
        SYNTAX	Counter
        ACCESS	read-only
        STATUS	mandatory
        DESCRIPTION
                "Number of priority 0 packets dropped */"
        ::= { wfCctOptsCngcEntry 43 }

    wfCctOptsCngcPriority0DropOctets OBJECT-TYPE
        SYNTAX	Counter
        ACCESS	read-only
        STATUS	mandatory
        DESCRIPTION
                "Number of priority 0 octets dropped"
        ::= { wfCctOptsCngcEntry 44 }

    wfCctOptsCngcPriority1TxPkts OBJECT-TYPE
        SYNTAX	Counter
        ACCESS	read-only
        STATUS	mandatory
        DESCRIPTION
                "Number of priority 1 packets transmitted"
        ::= { wfCctOptsCngcEntry 45 }

    wfCctOptsCngcPriority1TxOctets OBJECT-TYPE
        SYNTAX	Counter
        ACCESS	read-only
        STATUS	mandatory
        DESCRIPTION
                "Number of priority 1 Octets transmitted"
        ::= { wfCctOptsCngcEntry 46 }

    wfCctOptsCngcPriority1DropPkts OBJECT-TYPE
        SYNTAX	Counter
        ACCESS	read-only
        STATUS	mandatory
        DESCRIPTION
                "Number of priority 1 packets dropped */"
        ::= { wfCctOptsCngcEntry 47 }

    wfCctOptsCngcPriority1DropOctets OBJECT-TYPE
        SYNTAX	Counter
        ACCESS	read-only
        STATUS	mandatory
        DESCRIPTION
                "Number of priority 1 octets dropped"
        ::= { wfCctOptsCngcEntry 48 }

    wfCctOptsCngcPriority2TxPkts OBJECT-TYPE
        SYNTAX	Counter
        ACCESS	read-only
        STATUS	mandatory
        DESCRIPTION
                "Number of priority 2 packets transmitted"
        ::= { wfCctOptsCngcEntry 49 }

    wfCctOptsCngcPriority2TxOctets OBJECT-TYPE
        SYNTAX	Counter
        ACCESS	read-only
        STATUS	mandatory
        DESCRIPTION
                "Number of priority 2 Octets transmitted"
        ::= { wfCctOptsCngcEntry 50 }

    wfCctOptsCngcPriority2DropPkts OBJECT-TYPE
        SYNTAX	Counter
        ACCESS	read-only
        STATUS	mandatory
        DESCRIPTION
                "Number of priority 2 packets dropped */"
        ::= { wfCctOptsCngcEntry 51 }

    wfCctOptsCngcPriority2DropOctets OBJECT-TYPE
        SYNTAX	Counter
        ACCESS	read-only
        STATUS	mandatory
        DESCRIPTION
                "Number of priority 2 octets dropped"
        ::= { wfCctOptsCngcEntry 52 }

    wfCctOptsCngcPriority3TxPkts OBJECT-TYPE
        SYNTAX	Counter
        ACCESS	read-only
        STATUS	mandatory
        DESCRIPTION
                "Number of priority 3 packets transmitted"
        ::= { wfCctOptsCngcEntry 53 }

    wfCctOptsCngcPriority3TxOctets OBJECT-TYPE
        SYNTAX	Counter
        ACCESS	read-only
        STATUS	mandatory
        DESCRIPTION
                "Number of priority 3 Octets transmitted"
        ::= { wfCctOptsCngcEntry 54 }

    wfCctOptsCngcPriority3DropPkts OBJECT-TYPE
        SYNTAX	Counter
        ACCESS	read-only
        STATUS	mandatory
        DESCRIPTION
                "Number of priority 3 packets dropped */"
        ::= { wfCctOptsCngcEntry 55 }

    wfCctOptsCngcPriority3DropOctets OBJECT-TYPE
        SYNTAX	Counter
        ACCESS	read-only
        STATUS	mandatory
        DESCRIPTION
                "Number of priority 3 octets dropped"
        ::= { wfCctOptsCngcEntry 56 }

    wfCctOptsCngcTxFRNonDePkts OBJECT-TYPE
        SYNTAX	Counter
        ACCESS	read-only
        STATUS	mandatory
        DESCRIPTION
                "Number of Frame Relay non DE packets transmitted"
        ::= { wfCctOptsCngcEntry 57 }

    wfCctOptsCngcTxFRNonDeOctets OBJECT-TYPE
        SYNTAX	Counter
        ACCESS	read-only
        STATUS	mandatory
        DESCRIPTION
                "Number of Frame Relay non DE octets transmitted"
        ::= { wfCctOptsCngcEntry 58 }

    wfCctOptsCngcTxFRDePkts OBJECT-TYPE
        SYNTAX	Counter
        ACCESS	read-only
        STATUS	mandatory
        DESCRIPTION
                "Number of Frame Relay DE packets transmitted"
        ::= { wfCctOptsCngcEntry 59 }

    wfCctOptsCngcTxFRDeOctets OBJECT-TYPE
        SYNTAX	Counter
        ACCESS	read-only
        STATUS	mandatory
        DESCRIPTION
                "Number of Frame Relay DE octets transmitted"
        ::= { wfCctOptsCngcEntry 60 }

    wfCctOptsCngcDropFRNonDePkts OBJECT-TYPE
        SYNTAX	Counter
        ACCESS	read-only
        STATUS	mandatory
        DESCRIPTION
                "Number of Frame Relay non DE packets dropped"
        ::= { wfCctOptsCngcEntry 61 }

    wfCctOptsCngcDropFRNonDeOctets OBJECT-TYPE
        SYNTAX	Counter
        ACCESS	read-only
        STATUS	mandatory
        DESCRIPTION
                "number of Frame Relay non DE octets dropped"
        ::= { wfCctOptsCngcEntry 62 }

    wfCctOptsCngcDropFRDePkts OBJECT-TYPE
        SYNTAX	Counter
        ACCESS	read-only
        STATUS	mandatory
        DESCRIPTION
                "number of Frame Relay DE packets dropped"
        ::= { wfCctOptsCngcEntry 63 }

    wfCctOptsCngcDropFRDeOctets OBJECT-TYPE
        SYNTAX	Counter
        ACCESS	read-only
        STATUS	mandatory
        DESCRIPTION
                "number of Frame Relay DE octets dropped"
        ::= { wfCctOptsCngcEntry 64 }

    wfCctOptsCngcFRSetFecnPkts OBJECT-TYPE
        SYNTAX	Counter
        ACCESS	read-only
        STATUS	mandatory
        DESCRIPTION
                "number of Frame Relay packets in which this link set FECN"
        ::= { wfCctOptsCngcEntry 65 }

    wfCctOptsCngcFRSetFecnOctets OBJECT-TYPE
        SYNTAX	Counter
        ACCESS	read-only
        STATUS	mandatory
        DESCRIPTION
                "number of Frame Relay octets in which this link set FECN"
        ::= { wfCctOptsCngcEntry 66 }

    wfCctOptsCngcFRSetBecnPkts OBJECT-TYPE
        SYNTAX	Counter
        ACCESS	read-only
        STATUS	mandatory
        DESCRIPTION
                "number of Frame Relay frames in which this link set BECN"
        ::= { wfCctOptsCngcEntry 67 }

    wfCctOptsCngcFRSetBecnOctets OBJECT-TYPE
        SYNTAX	Counter
        ACCESS	read-only
        STATUS	mandatory
        DESCRIPTION
                "number of Frame Relay octets in which this link set BECN"
        ::= { wfCctOptsCngcEntry 68 }

    wfCctOptsCngcDropNonFRPkts OBJECT-TYPE
        SYNTAX	Counter
        ACCESS	read-only
        STATUS	mandatory
        DESCRIPTION
                "Number of Non Frame Relay packets dropped"
        ::= { wfCctOptsCngcEntry 69 }

    wfCctOptsCngcDropNonFROctets OBJECT-TYPE
        SYNTAX	Counter
        ACCESS	read-only
        STATUS	mandatory
        DESCRIPTION
                "number of Non Frame Relay octets dropped"
        ::= { wfCctOptsCngcEntry 70 }

    wfCctOptsCngcLogPower OBJECT-TYPE
        SYNTAX	INTEGER(10..31)
        ACCESS	read-write
        STATUS	mandatory
        DESCRIPTION
                "This number specifies that the following log events:
                      1. Dropped DE Frame.
                      2. Dropped Non DE Frames.
                      3. Set DE Frames.
                      4. Set FECN/BECN.
                 be logged once every (X) occurances.  Where (X) = Base 2
                 raised to the power.  The user specifies the power by setting
                 this wfCctOptsCngcLogPower mib attribute.

                 For example, setting wfCctOptsCngcLogPower to a value of 10 means
                 that a log message will be logged once every 1024 occurances.
                      1024 = (2 ^ wfCctOptsCngcLogPower) or (2 raised to 10th power).

                 Legal values for this attribute ranges from 10 to 31.  This translates
                 to 2^10 (1024) through 2^31 (2147483648).  Default: 2^31."
        DEFVAL	{ 31 }
        ::= { wfCctOptsCngcEntry 71 }

    wfSwservTODTable OBJECT-TYPE
        SYNTAX	SEQUENCE OF WfSwservTODEntry
        ACCESS	not-accessible
        STATUS	mandatory
        DESCRIPTION
                "SWSERV circuit time of day MIB"
        ::= { wfCircuitOptsGroup 11 }

    wfSwservTODEntry OBJECT-TYPE
        SYNTAX	WfSwservTODEntry
        ACCESS	not-accessible
        STATUS	mandatory
        DESCRIPTION
                "An entry in the wfSwservTODTable"
        INDEX	{ wfSwservTODCct,
    		  wfSwservTODIndex }
        ::= { wfSwservTODTable 1 }

    WfSwservTODEntry ::= SEQUENCE {
    	    wfSwservTODDelete
    		INTEGER,
    	    wfSwservTODCct
    		INTEGER,
    	    wfSwservTODIndex
    		INTEGER,
    	    wfSwservTODType
    		INTEGER,
    	    wfSwservTODStartTime
    		INTEGER,
    	    wfSwservTODEndTime
    		INTEGER,
    	    wfSwservTODInactivityEnable
    		INTEGER,
    	    wfSwservTODAvailabilityMode
    		INTEGER,
    	    wfSwservTODStandbyFailBackMode
    		INTEGER,
    	    wfSwservTODStandbyFailBackTime
    		INTEGER
        }

    wfSwservTODDelete OBJECT-TYPE
        SYNTAX	INTEGER {
    		    create(1),
    		    delete(2)
    		}
        ACCESS	read-write
        STATUS	mandatory
        DESCRIPTION
                "Delete time of day instance from the list for this circuit"
        DEFVAL	{ create }
        ::= { wfSwservTODEntry 1 }

    wfSwservTODCct OBJECT-TYPE
        SYNTAX	INTEGER(1..1023)
        ACCESS	read-only
        STATUS	mandatory
        DESCRIPTION
                "CCT number for time of day instance"
        ::= { wfSwservTODEntry 2 }

    wfSwservTODIndex OBJECT-TYPE
        SYNTAX	INTEGER(1..24)
        ACCESS	read-only
        STATUS	mandatory
        DESCRIPTION
                "a unique number to specify instance"
        ::= { wfSwservTODEntry 3 }

    wfSwservTODType OBJECT-TYPE
        SYNTAX	INTEGER {
    		    sun(1),
    		    mon(2),
    		    tues(3),
    		    wed(4),
    		    thurs(5),
    		    fri(6),
    		    sat(7),
    		    weekday(8),
    		    weekend(9)
    		}
        ACCESS	read-write
        STATUS	mandatory
        DESCRIPTION
                "Type of TOD Configuration"
        DEFVAL	{ weekday }
        ::= { wfSwservTODEntry 4 }

    wfSwservTODStartTime OBJECT-TYPE
        SYNTAX	INTEGER(0..2400)
        ACCESS	read-write
        STATUS	mandatory
        DESCRIPTION
                "Start Time of day allow a line to dial ( HHMM format )"
        DEFVAL	{ 0000 }
        ::= { wfSwservTODEntry 5 }

    wfSwservTODEndTime OBJECT-TYPE
        SYNTAX	INTEGER(0..2400)
        ACCESS	read-write
        STATUS	mandatory
        DESCRIPTION
                "End Time of day connection can be active for
                specified circuit ( HHMM format )"
        DEFVAL	{ 2400 }
        ::= { wfSwservTODEntry 6 }

    wfSwservTODInactivityEnable OBJECT-TYPE
        SYNTAX	INTEGER {
    		    enabled(1),
    		    disabled(2)
    		}
        ACCESS	read-write
        STATUS	mandatory
        DESCRIPTION
                "Inactivity Timer if disabled the inactivity timer is ignored during this
                time period, if enabled the connection is brought down due to
                inactivity.  If this parameter is DISABLED, the circuit will be
                established automatically during the configured times, 
                regardless of the Availability Mode."
        DEFVAL	{ disabled }
        ::= { wfSwservTODEntry 7 }

    wfSwservTODAvailabilityMode OBJECT-TYPE
        SYNTAX	INTEGER {
    		    available(1),
    		    notavailable(2)
    		}
        ACCESS	read-write
        STATUS	mandatory
        DESCRIPTION
                 "Set this field to AVAILABLE to allow the circuit to be 
                 established between the configured start and end times.  
                 Set it to NOT AVAILABLE to prevent the circuit from 
                 being established during those times.
                 Inactivity Timeout must be ENABLED for Availability Mode 
                 to have any effect.  If Inactivity Timeout is DISABLED, the 
                 circuit will be established automatically during the 
                 configured times, regardless of the Availability Mode. "
        DEFVAL	{ available }
        ::= { wfSwservTODEntry 8 }

    wfSwservTODStandbyFailBackMode OBJECT-TYPE
        SYNTAX	INTEGER {
    		    automatic(1),
    		    manual(2)
    		}
        ACCESS	read-write
        STATUS	mandatory
        DESCRIPTION
                "Indicates if failback mode for this time of day range. When set to
		 automatic circuit will failback subject to the failback timer. When
		 set to manual circuit will not failback."
        DEFVAL	{ automatic }
        ::= { wfSwservTODEntry 9 }

    wfSwservTODStandbyFailBackTime OBJECT-TYPE
        SYNTAX	INTEGER (0..1439)
        ACCESS	read-write
        STATUS	mandatory
        DESCRIPTION
                "Indicates number of minutes to wait after the primary is observed
		 as active before deactivating the standby. Default value of 0
		 disables failback timer."
        DEFVAL	{ 0 }
        ::= { wfSwservTODEntry 10 }

    wfDemandCctGrpTable OBJECT-TYPE
        SYNTAX	SEQUENCE OF WfDemandCctGrpEntry
        ACCESS	not-accessible
        STATUS	mandatory
        DESCRIPTION
                "The table of demand circuits groups defined  over  switched services"
        ::= { wfCircuitOptsGroup 12 }

    wfDemandCctGrpEntry OBJECT-TYPE
        SYNTAX	WfDemandCctGrpEntry
        ACCESS	not-accessible
        STATUS	mandatory
        DESCRIPTION
                "Entry  format for the table  of demand circuit group options"
        INDEX	{ wfDmdCctGroupNum,
    		  wfDmdCctGroupPoolId }
        ::= { wfDemandCctGrpTable 1 }

    WfDemandCctGrpEntry ::= SEQUENCE {
    	    wfDmdCctGroupDelete
    		INTEGER,
    	    wfDmdCctGroupNum
    		INTEGER,
    	    wfDmdCctGroupPoolId
    		INTEGER,
    	    wfDmdCctGroupNumofCcts
    		INTEGER,
    	    wfDmdCctGroupIPEnable
    		INTEGER,
    	    wfDmdCctGroupIPUnnumAssoc
    		IpAddress,
    	    wfDmdCctGroupRIPEnable
    		INTEGER,
    	    wfDmdCctGroupOSPFEnable
    		INTEGER,
    	    wfDmdCctGroupIPXEnable
    		INTEGER,
    	    wfDmdCctGroupBridgeEnable
    		INTEGER,
    	    wfDmdCctGroupCctList
    		OCTET STRING,
	        wfDmdCctGroupIPXRouting
		    INTEGER,
	        wfDmdCctGroupIPXWANEnable
		    INTEGER,
            wfDmdCctGroupRadiusEnable
            INTEGER
        }

    wfDmdCctGroupDelete OBJECT-TYPE
        SYNTAX	INTEGER {
    		    created(1),
    		    deleted(2)
    		}
        ACCESS	read-write
        STATUS	mandatory
        DESCRIPTION
                "Creation and deletion flag"
        DEFVAL	{ created }
        ::= { wfDemandCctGrpEntry 1 }

    wfDmdCctGroupNum OBJECT-TYPE
        SYNTAX	INTEGER
        ACCESS	read-only
        STATUS	mandatory
        DESCRIPTION
                "Circuit Number"
        ::= { wfDemandCctGrpEntry 2 }

    wfDmdCctGroupPoolId OBJECT-TYPE
        SYNTAX	INTEGER(1..255)
        ACCESS	read-only
        STATUS	mandatory
        DESCRIPTION
                "Demand pool id used by this demand circuit group"
        ::= { wfDemandCctGrpEntry 3 }

    wfDmdCctGroupNumofCcts OBJECT-TYPE
        SYNTAX	INTEGER(1..124)
        ACCESS	read-write
        STATUS	mandatory
        DESCRIPTION
                "Demand pool id used by this demand circuit group"
        DEFVAL	{ 1 }
        ::= { wfDemandCctGrpEntry 4 }

    wfDmdCctGroupIPEnable OBJECT-TYPE
        SYNTAX	INTEGER {
    		    enabled(1),
    		    disabled(2)
    		}
        ACCESS	read-write
        STATUS	mandatory
        DESCRIPTION
                "IP unnumbered enabled or disabled for specified demand circuit group"
        DEFVAL	{ disabled }
        ::= { wfDemandCctGrpEntry 5 }

    wfDmdCctGroupIPUnnumAssoc OBJECT-TYPE
        SYNTAX	IpAddress
        ACCESS	read-write
        STATUS	mandatory
        DESCRIPTION
                "The associated IP address used by unnumbered demand circuit group
                every demand circuit in this demand circuit group uses the same
                associated IP address."
        ::= { wfDemandCctGrpEntry 6 }

    wfDmdCctGroupRIPEnable OBJECT-TYPE
        SYNTAX	INTEGER {
    		    enabled(1),
    		    disabled(2)
    		}
        ACCESS	read-write
        STATUS	mandatory
        DESCRIPTION
                "RIP enabled or disabled for specified demand circuit group"
        DEFVAL	{ disabled }
        ::= { wfDemandCctGrpEntry 7 }

    wfDmdCctGroupOSPFEnable OBJECT-TYPE
        SYNTAX	INTEGER {
    		    enabled(1),
    		    disabled(2)
    		}
        ACCESS	read-write
        STATUS	mandatory
        DESCRIPTION
                "OSPF enabled or disabled for specified demand circuit group"
        DEFVAL	{ disabled }
        ::= { wfDemandCctGrpEntry 8 }

    wfDmdCctGroupIPXEnable OBJECT-TYPE
        SYNTAX	INTEGER {
    		    enabled(1),
    		    disabled(2)
    		}
        ACCESS	read-write
        STATUS	mandatory
        DESCRIPTION
                "IPX unnumbered enabled or disabled for specified demand circuit group"
        DEFVAL	{ disabled }
        ::= { wfDemandCctGrpEntry 9 }

    wfDmdCctGroupBridgeEnable OBJECT-TYPE
        SYNTAX	INTEGER {
    		    enabled(1),
    		    disabled(2)
    		}
        ACCESS	read-write
        STATUS	mandatory
        DESCRIPTION
                "Bridge enabled or disabled for specified demand circuit group"
        DEFVAL	{ disabled }
        ::= { wfDemandCctGrpEntry 10 }

    wfDmdCctGroupCctList OBJECT-TYPE
        SYNTAX	OCTET STRING
        ACCESS	read-write
        STATUS	mandatory
        DESCRIPTION
                "List of demand circuits that are members of this group"
        ::= { wfDemandCctGrpEntry 11 }

    wfDmdCctGroupIPXRouting OBJECT-TYPE
        SYNTAX	INTEGER {
        	    rip(1),
        	    nlsp(2),
    		    ripnlsp(3)
    		}
        ACCESS	read-write
        STATUS	mandatory
        DESCRIPTION
                "IPX routing protocol used for specified demand circuit group"
        DEFVAL	{ rip }
        ::= { wfDemandCctGrpEntry 12 }

    wfDmdCctGroupIPXWANEnable OBJECT-TYPE
        SYNTAX	INTEGER {
    		    enabled(1),
    		    disabled(2)
    		}
        ACCESS	read-write
        STATUS	mandatory
        DESCRIPTION
                "IPXWAN enabled or disabled for specified demand circuit group"
        DEFVAL	{ disabled }
        ::= { wfDemandCctGrpEntry 13 }

	wfDmdCctGroupRadiusEnable OBJECT-TYPE
        SYNTAX  INTEGER {
                enabled(1),
                disabled(2)
            }
        ACCESS  read-write
        STATUS  mandatory
        DESCRIPTION
                "Radius enabled or disabled for specified demand circuit group"
        DEFVAL  { disabled }
        ::= { wfDemandCctGrpEntry 14 }

    END  -- Wellfleet-CCTOPTS-MIB
