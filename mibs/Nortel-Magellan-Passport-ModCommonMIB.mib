Nortel-Magellan-Passport-ModCommonMIB
DEFINITIONS ::= BEGIN



IMPORTS

      OBJECT-TYPE
   FROM RFC-1212

      passportMIBs
   FROM Nortel-Magellan-Passport-UsefulDefinitionsMIB

      DisplayString,
      StorageType,
      RowStatus
   FROM Nortel-Magellan-Passport-StandardTextualConventionsMIB

      NonReplicated
   FROM Nortel-Magellan-Passport-TextualConventionsMIB

      mod,
      modIndex
   FROM Nortel-Magellan-Passport-ShelfMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     ModCommon Enterprise MIB."

modCommonMIB OBJECT IDENTIFIER ::= { passportMIBs 74 }










-- Mod FrameRelaySystem
-- The Frs component defines the overall module wide data that is 
-- applicable to the Frame Relay system.

modFrs OBJECT IDENTIFIER ::= { mod 3 }



modFrsRowStatusTable OBJECT-TYPE
   SYNTAX     SEQUENCE OF ModFrsRowStatusEntry
   ACCESS     not-accessible
   STATUS     mandatory
   DESCRIPTION
     "This entry controls the addition and deletion of 
      modFrs components."
::= { modFrs 1 }

modFrsRowStatusEntry OBJECT-TYPE
   SYNTAX     ModFrsRowStatusEntry
   ACCESS     not-accessible
   STATUS     mandatory
   DESCRIPTION
     "A single entry in the table represents a single 
      modFrs component."
   INDEX {
      modIndex,
      modFrsIndex }
::= { modFrsRowStatusTable 1 }

ModFrsRowStatusEntry ::= SEQUENCE {
   modFrsRowStatus
      RowStatus,
   modFrsComponentName
      DisplayString,
   modFrsStorageType
      StorageType,
   modFrsIndex
      NonReplicated }

modFrsRowStatus OBJECT-TYPE
   SYNTAX     RowStatus 
   ACCESS     read-only
   STATUS     mandatory
   DESCRIPTION
     "This variable is used as the basis for SNMP naming of
      modFrs components.
      These components cannot be added nor deleted."
::= { modFrsRowStatusEntry 1 }

modFrsComponentName OBJECT-TYPE
   SYNTAX     DisplayString 
   ACCESS     read-only
   STATUS     mandatory
   DESCRIPTION
     "This variable provides the component's string name for
      use with the ASCII Console Interface"
::= { modFrsRowStatusEntry 2 }

modFrsStorageType OBJECT-TYPE
   SYNTAX     StorageType 
   ACCESS     read-only
   STATUS     mandatory
   DESCRIPTION
     "This variable represents the storage type value for the
      modFrs tables."
::= { modFrsRowStatusEntry 4 }

modFrsIndex OBJECT-TYPE
   SYNTAX     NonReplicated 
   ACCESS     not-accessible
   STATUS     mandatory
   DESCRIPTION
     "This variable represents the index for the modFrs tables."
::= { modFrsRowStatusEntry 10 }




-- 
-- Version and Compliance statements
-- 



-- Object-Group Statement:
-- A list of all current accessible leaf objects.

-- OBJECTS { modFrsComponentName,
--           modFrsStorageType,
--           modFrsRowStatus }
-- STATUS  mandatory
-- DESCRIPTION
--   "A list of all current accessible leaf objects."

modCommonGroup OBJECT IDENTIFIER ::= { modCommonMIB 1 }
modCommonGroupBE OBJECT IDENTIFIER ::= { modCommonGroup 5 }
modCommonGroupBE01 OBJECT IDENTIFIER ::= { modCommonGroupBE 2 }
modCommonGroupBE01A OBJECT IDENTIFIER ::= { modCommonGroupBE01 2 }



-- Agent-Capabilities Statement:

-- PRODUCT-RELEASE "Passport Release 7.0 ModCommon."
-- STATUS          mandatory
-- DESCRIPTION     "ModCommon MIB: MIB Version BE01A,
--                  Software Version BG00S4C."
-- SUPPORTS        Nortel-Magellan-Passport-ModCommonMIB
--    INCLUDES     { modCommonGroupBE01A }

modCommonCapabilities OBJECT IDENTIFIER ::= { modCommonMIB 3 }
modCommonCapabilitiesBE OBJECT IDENTIFIER ::= { modCommonCapabilities 5 }
modCommonCapabilitiesBE01 OBJECT IDENTIFIER ::= { modCommonCapabilitiesBE 2 }
modCommonCapabilitiesBE01A OBJECT IDENTIFIER ::= { modCommonCapabilitiesBE01 2 }





END
