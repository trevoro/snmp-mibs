CRESCENDO-MIB DEFINITIONS ::= BEGIN

-- Title:       Crescendo Communications Concentrator MIB in concise format
-- Date:        February 20, 1992
-- By:          Cal Palmore <palmore@crescendo.com>

IMPORTS
        enterprises,  IpAddress, Counter, Gauge, TimeTicks
                FROM RFC1155-SMI
        OBJECT-TYPE
                FROM RFC-1212
        DisplayString
                FROM RFC1213-MIB;

crescendo               OBJECT IDENTIFIER ::= { enterprises 203 }
crescendoProducts       OBJECT IDENTIFIER ::= { crescendo 1 }

concentrator            OBJECT IDENTIFIER ::= { crescendoProducts 1 }
conc                    OBJECT IDENTIFIER ::= { concentrator 1 }
chassis                 OBJECT IDENTIFIER ::= { concentrator 2 }
module                  OBJECT IDENTIFIER ::= { concentrator 3 }
port                    OBJECT IDENTIFIER ::= { concentrator 4 }


-- the concentrator group

concMgmtType OBJECT-TYPE
        SYNTAX        INTEGER {
                                other(1),  -- none of the following
                                snmp(2)    -- Simple Network Management Protocol
                                }
        ACCESS        read-only
        STATUS        mandatory
        DESCRIPTION   "The type of network management running on the 
                      concentrator."
        ::= { conc 1 }

concIpAddr OBJECT-TYPE
        SYNTAX        IpAddress
        ACCESS        read-write
        STATUS        mandatory
        DESCRIPTION   "The concentrator's IP address."
        ::= { conc 2 }

concNetMask OBJECT-TYPE
        SYNTAX        IpAddress
        ACCESS        read-write
        STATUS        mandatory
        DESCRIPTION   "The concentrator's subnet mask."
        ::= { conc 3 }

concBroadcast OBJECT-TYPE
        SYNTAX        IpAddress
        ACCESS        read-write
STATUS        mandatory
        DESCRIPTION   "The concentrator's broadcast address."
        ::= { conc 4 }

-- the trap receiver table

concTrapReceiverTable OBJECT-TYPE
        SYNTAX        SEQUENCE OF ConcTrapReceiverEntry
        ACCESS        not-accessible
        STATUS        mandatory
        DESCRIPTION   "The concentrator trap receiver table (0 to 10 entries).
                      This table lists the addresses of Network Management 
                      Stations that should receive trap messages from this 
                      concentrator when an exception condition occurs."
        ::= { conc 5 }

concTrapReceiverEntry OBJECT-TYPE
        SYNTAX        ConcTrapReceiverEntry
        ACCESS        not-accessible
        STATUS        mandatory
        DESCRIPTION   "A trap receiver table entry."
        INDEX         { concTrapReceiverAddr }
        ::= { concTrapReceiverTable 1 }

ConcTrapReceiverEntry ::=
        SEQUENCE {
                concTrapReceiverType
                        INTEGER,
                concTrapReceiverAddr
                        IpAddress,
                concTrapReceiverComm
                        DisplayString
        }

concTrapReceiverType OBJECT-TYPE
        SYNTAX        INTEGER {
                                other(1),        -- none of the following
                                invalid(2)        -- an invalid address
                                }
        ACCESS        read-write
        STATUS        mandatory
        DESCRIPTION   "Setting this object to invalid(2) removes the 
                      corresponding entry from the concTrapReceiverTable.  
                      To add a new entry to the concTrapReceiverTable, 
                      set the concTrapReceiverAddr to an IpAddress which is 
                      not already in the table.  The concTrapReceiverType for 
                      that entry is automatically set to other(1)."
        ::= { concTrapReceiverEntry 1 }

concTrapReceiverAddr OBJECT-TYPE
        SYNTAX        IpAddress
        ACCESS        read-write
        STATUS        mandatory
        DESCRIPTION   "IP address for trap receiver."
        ::= { concTrapReceiverEntry 2 }

concTrapReceiverComm OBJECT-TYPE
        SYNTAX        DisplayString (SIZE (0..20))
        ACCESS        read-write
        STATUS        mandatory
        DESCRIPTION   "Community string used for trap messages to this trap 
                      receiver."
        ::= { concTrapReceiverEntry 3 }

-- the community table

concCommunityTable OBJECT-TYPE
        SYNTAX        SEQUENCE OF ConcCommunityEntry
        ACCESS        not-accessible
        STATUS        mandatory
        DESCRIPTION   "The concentrator community table (4 entries).  This 
                      table lists community strings and their access levels.  
                      When an SNMP message is received by this concentrator, 
                      the community string in the message is compared with 
                      this table to determine access rights of the sender."
        ::= { conc 6 }

concCommunityEntry OBJECT-TYPE
        SYNTAX        ConcCommunityEntry
        ACCESS        not-accessible
        STATUS        mandatory
        DESCRIPTION   "A community table entry."
        INDEX         { concCommunityAccess }
        ::= { concCommunityTable 1 }

ConcCommunityEntry ::=
        SEQUENCE {
                concCommunityAccess
                      INTEGER,
                concCommunityString
                      DisplayString
        }

concCommunityAccess OBJECT-TYPE
        SYNTAX        INTEGER {
				other(1),        -- none of the following
                                readOnly(2),     -- read but not write all but
                                                 -- concCommunityTable
                                readWrite(3),    -- read and write all but
                                                 -- concCommunityTable
                                readWriteAll(4)  -- read and write all
                                }
        ACCESS        read-only
        STATUS        mandatory
        DESCRIPTION   "A value of readWriteAll(4) allows the community to read 
                      and write all objects in the MIB.  A value of readWrite(3)
                      allows the community to read and write all objects except 
                      the concCommunityTable, which it cannot access at all.  
                      A value of readOnly(2) allows the community to read all 
                      objects except the concCommunityTable.  A value of 
                      other(1) allows no access."
        ::= { concCommunityEntry 1 }

concCommunityString OBJECT-TYPE
        SYNTAX        DisplayString (SIZE (0..20))
        ACCESS        read-write
        STATUS        mandatory
        DESCRIPTION   "Configurable community string with access rights 
                      defined by the value of concCommunityAccess."
        ::= { concCommunityEntry 2 }

-- additional concentrator objects

concAttachType OBJECT-TYPE
        SYNTAX        INTEGER {
                                other(1),        -- none of the following
                                dualAttach(2),   -- port 1 is A and port 2 is B
                                singleAttach(3), -- port 1 is S and port 2 is M
                                nullAttach(4)    -- port 1 is M and port 2 is M
                                }
        ACCESS        read-write
        STATUS        mandatory
        DESCRIPTION   "The requested concentrator attachment type.  For a dual 
                      attachment concentrator connected to the trunk ring, 
                      port 1 on the supervisor module (or single board 
                      concentrator) is configured as A and port 2 is 
                      configured as B.  For a single attachment concentrator 
                      connected beneath another concentrator, port 1 is 
                      configured as S and port 2 is configured as M.  For a 
                      null attachment concentrator at the root of the tree, 
                      ports 1 and 2 are configured as M.  This object does 
                      not take effect until the concentrator is reset.  The 
                      current attachment type can be determined from 
                      snmpFddiPORTPCType for ports 1 and 2.  Note that a 
                      concentrator with no MAC is always null attachment type."
        ::= { conc 7 }

concTraffic OBJECT-TYPE
        SYNTAX        INTEGER (0..100)
        ACCESS        read-only
        STATUS        mandatory
        DESCRIPTION   "The percentage of bandwidth utilization on the network 
                      for the previous polling interval."
        ::= { conc 8 }

concReset OBJECT-TYPE
        SYNTAX        INTEGER {
                                other(1),        -- none of the following
                                reset(2)         -- resetting
                                }
        ACCESS        read-write
        STATUS        mandatory
        DESCRIPTION   "Writing a 2 to this object resets the control logic of
                      all modules in the concentrator."
        ::= { conc 9 }

concBaudRate OBJECT-TYPE
        SYNTAX        INTEGER
        ACCESS        read-write
        STATUS        mandatory
        DESCRIPTION   "The baud rate in bits per second of the concentrator
                      RS-232 port."
        ::= { conc 10 }


-- the chassis group

chassisType OBJECT-TYPE
        SYNTAX        INTEGER {
                                other(1),        -- none of the following
                                cxxxx(2),        -- reserved
                                c1000(3),        -- CDDI Workgroup Concentrator
                                c1001(4)         -- FDDI Workgroup Concentrator
                                }
        ACCESS        read-only
        STATUS        mandatory
        DESCRIPTION   "The chassis type."
        ::= { chassis 1 }

chassisBkplType OBJECT-TYPE
        SYNTAX        INTEGER {
                                other(1),        -- none of the following
                                fddi(2),         -- fddi
                                fddiEthernet(3)  -- fddi and ethernet
                                }
        ACCESS        read-only
        STATUS        mandatory
        DESCRIPTION   "The chassis backplane type."
        ::= { chassis 2 }

chassisPs1Type OBJECT-TYPE
        SYNTAX        INTEGER {
                                other(1),        -- none of the following
                                none(2),         -- no power supply installed
                                w50(3),          -- 50 watt supply
                                w200(4),         -- 200 watt supply
                                w600(5)          -- 600 watt supply
                                }
        ACCESS        read-only
        STATUS        mandatory
        DESCRIPTION   "Type of power supply number 1."
        ::= { chassis 3 }

chassisPs1Status OBJECT-TYPE
        SYNTAX        INTEGER {
                                other(1),        -- none of the following
                                ok(2),           -- status ok
                                minorFault(3),   -- minor problem
                                majorFault(4)    -- major problem
                                }
        ACCESS        read-only
        STATUS        mandatory
        DESCRIPTION   "Status of power supply number 1.  If the status is not 
                      ok, the value of chassisPs1TestResult gives more 
                      detailed information about the power supply's failure 
                      condition(s)."
        ::= { chassis 4 }

chassisPs1TestResult OBJECT-TYPE
        SYNTAX        INTEGER
        ACCESS        read-only
        STATUS        mandatory
        DESCRIPTION   "Test result for power supply number 1.  A zero 
                      indicates that the supply passed all tests.  Bits set 
                      in the result indicate error conditions."
        ::= { chassis 5 }

chassisPs2Type OBJECT-TYPE
        SYNTAX        INTEGER {
                                other(1),        -- none of the following
                                none(2),         -- no power supply installed
                                w50(3),          -- 50 watt supply
                                w200(4),         -- 200 watt supply
                                w600(5)          -- 600 watt supply
                                }
        ACCESS        read-only
        STATUS        mandatory
        DESCRIPTION   "Type of power supply number 2."
        ::= { chassis 6 }

chassisPs2Status OBJECT-TYPE
        SYNTAX        INTEGER {
                                other(1),        -- none of the following
                                ok(2),           -- status ok
                                minorFault(3),   -- minor problem
                                majorFault(4)    -- major problem
                                }
        ACCESS        read-only
        STATUS        mandatory
        DESCRIPTION   "Status of power supply number 2.  If the status is not
                      ok, the value of chassisPs2TestResult gives more 
                      detailed information about the power supply's failure 
                      condition(s)."
        ::= { chassis 7 }

chassisPs2TestResult OBJECT-TYPE
        SYNTAX        INTEGER
        ACCESS        read-only
        STATUS        mandatory
        DESCRIPTION   "Test result for power supply number 2.  A zero 
                      indicates that the supply passed all tests.  Bits set 
                      in the result indicate error conditions."
        ::= { chassis 8 }

chassisFanStatus OBJECT-TYPE
        SYNTAX        INTEGER {
                                other(1),        -- none of the following
                                ok(2),           -- status ok
                                minorFault(3),   -- minor problem
                                majorFault(4)    -- major problem
                                }
        ACCESS        read-only
        STATUS        mandatory
        DESCRIPTION   "Status of the chassis fan.  If the status is not ok, 
                      the value of chassisFanTestResult gives more detailed 
                      information about the fan's failure condition(s)."
        ::= { chassis 9 }

chassisFanTestResult OBJECT-TYPE
        SYNTAX        INTEGER
        ACCESS        read-only
        STATUS        mandatory
        DESCRIPTION   "Test result for the chassis fan.  A zero indicates 
                      that the fan passed all tests.  Bits set in the result 
                      indicate error conditions."
        ::= { chassis 10 }

chassisMinorAlarm OBJECT-TYPE
        SYNTAX        INTEGER {
                                off(1),
                                on(2)
                                }
        ACCESS        read-only
        STATUS        mandatory
        DESCRIPTION   "The chassis minor alarm status."
        ::= { chassis 11 }

chassisMajorAlarm OBJECT-TYPE
        SYNTAX        INTEGER {
                                off(1),
                                on(2)
                                }
        ACCESS        read-only
        STATUS        mandatory
        DESCRIPTION   "The chassis major alarm status."
        ::= { chassis 12 }

chassisTempAlarm OBJECT-TYPE
        SYNTAX        INTEGER {
                                off(1),
                                on(2)
                                }
        ACCESS        read-only
        STATUS        mandatory
        DESCRIPTION   "The chassis temperature alarm status."
        ::= { chassis 13 }
                                

chassisNumSlots OBJECT-TYPE
        SYNTAX        INTEGER
        ACCESS        read-only
        STATUS        mandatory
        DESCRIPTION   "The number of slots in the chassis for plug-in modules."
        ::= { chassis 14 }

chassisSlotConfig OBJECT-TYPE
        SYNTAX        INTEGER
        ACCESS        read-only
        STATUS        mandatory
        DESCRIPTION   "An indication of which slots in the chassis have 
                      modules inserted.  This is an integer value with bits 
                      set to indicate configured modules.  It can be 
                      interpreted as a sum of f(x) as x goes from 1 to the 
                      number of slots, where f(x) = 0 module and f(x) = 
                      exp(2, x-1) for a module inserted."
        ::= { chassis 15 }


-- the module group

moduleTable OBJECT-TYPE
        SYNTAX        SEQUENCE OF ModuleEntry
        ACCESS        not-accessible
        STATUS        mandatory
        DESCRIPTION   "A list of module entries.  The number of entries is 
                      given by the value of chassisNumSlots."
        ::= { module 1 }

moduleEntry OBJECT-TYPE
        SYNTAX        ModuleEntry
        ACCESS        not-accessible
        STATUS        mandatory
        DESCRIPTION   "Entry containing information about one module in a 
                      slot of the concentrator."
        INDEX         { moduleIndex }
        ::= { moduleTable 1 }

ModuleEntry ::=
        SEQUENCE {
                moduleIndex
                        INTEGER,
                moduleType
                        INTEGER,
                moduleSerialNumber
                        INTEGER,
                moduleHwHiVersion
                        INTEGER,
                moduleHwLoVersion
                        INTEGER,
                moduleFwHiVersion
                        INTEGER,
                moduleFwLoVersion
                        INTEGER,
                moduleSwHiVersion
                        INTEGER,
                moduleSwLoVersion
                        INTEGER,
                moduleStatus
                        INTEGER,
                moduleTestResult
                        INTEGER,
                moduleReset
                        INTEGER,
                moduleName
                        DisplayString,
                moduleNumPorts
                        INTEGER,
                modulePortStatus
                        OCTET STRING
                }

moduleIndex OBJECT-TYPE
        SYNTAX        INTEGER
        ACCESS        read-only
        STATUS        mandatory
        DESCRIPTION   "A unique value for each module within the concentrator.
                      This value is determined by the chassis slot number 
                      where the module is inserted.  Valid entries are 1 to 
                      the value of chassisNumSlots"
        ::= { moduleEntry 1 }

moduleType OBJECT-TYPE
        SYNTAX        INTEGER {
                                other(1),       -- none of the following
                                empty(2),       -- nothing installed
                                c1000(3),       -- CDDI Workgroup Concentrator
                                c1001(4)        -- FDDI Workgroup Concentrator
                                }
        ACCESS        read-only
        STATUS        mandatory
        DESCRIPTION   "The type of module."
        ::= { moduleEntry 2 }

moduleSerialNumber OBJECT-TYPE
        SYNTAX        INTEGER
        ACCESS        read-only
        STATUS        mandatory
        DESCRIPTION   "The serial number of the module."
        ::= { moduleEntry 3 }

moduleHwHiVersion OBJECT-TYPE
        SYNTAX        INTEGER
        ACCESS        read-only
        STATUS        mandatory
        DESCRIPTION   "The high part of the hardware version of the module.  
                      For example, if the hardware version is 3.1, the value 
                      of moduleHwHiVersion is 3."
        ::= { moduleEntry 4 }

moduleHwLoVersion OBJECT-TYPE
        SYNTAX        INTEGER
        ACCESS        read-only
        STATUS        mandatory
        DESCRIPTION   "The low part of the hardware version of the module.  
                      For example, if the hardware version is 3.1, the value 
                      of moduleHwLoVersion is 1."
        ::= { moduleEntry 5 }

moduleFwHiVersion OBJECT-TYPE
        SYNTAX        INTEGER
        ACCESS        read-only
        STATUS        mandatory
        DESCRIPTION   "The high part of the firmware version number.  For 
                      example, if the firmware version is 3.1, the value of 
                      moduleFwHiVersion is 3."
        ::= { moduleEntry 6 }

moduleFwLoVersion OBJECT-TYPE
        SYNTAX        INTEGER
        ACCESS        read-only
        STATUS        mandatory
        DESCRIPTION   "The low part of the firmware version number.  For 
                      example, if the firmware version is 3.1, the value of 
                      moduleFwLoVersion is 1."
        ::= { moduleEntry 7 }

moduleSwHiVersion OBJECT-TYPE
        SYNTAX        INTEGER
        ACCESS        read-only
        STATUS        mandatory
        DESCRIPTION   "The high part of the software version number.  For 
                      example, if the software version is 3.1, the value of 
                      moduleSwHiVersion is 3."
        ::= { moduleEntry 8 }

moduleSwLoVersion OBJECT-TYPE
        SYNTAX        INTEGER
        ACCESS        read-only
        STATUS        mandatory
        DESCRIPTION   "The low part of the software version number.  For 
                      example, if the software version is 3.1, the value of 
                      moduleSwLoVersion is 1."
        ::= { moduleEntry 9 }

moduleStatus OBJECT-TYPE
        SYNTAX        INTEGER {
                                other(1),       -- none of the following
                                ok(2),          -- status ok
                                minorFault(3),  -- minor problem
                                majorFault(4)   -- major problem
                                }
        ACCESS        read-only
        STATUS        mandatory
        DESCRIPTION   "The operational status of the module.  If the status 
                      is not ok, the value of moduleTestResult gives more 
                      detailed information about the module's failure
                      condition(s)."
        ::= { moduleEntry 10 }

moduleTestResult OBJECT-TYPE
        SYNTAX        INTEGER
        ACCESS        read-only
        STATUS        mandatory
        DESCRIPTION   "The result of the module's self test.  A zero 
                      indicates that the module passed all tests.  Bits set 
                      in the result indicate error conditions."
        ::= { moduleEntry 11 }

moduleReset OBJECT-TYPE
        SYNTAX        INTEGER {
                                other(1),       -- none of the following
                                reset(2)        -- resetting
                                }
        ACCESS        read-write
        STATUS        mandatory
        DESCRIPTION   "Writing a 2 to this object resets the module's 
                      control logic.  This has the same affect as pressing 
                      the reset button on the module."
        ::= { moduleEntry 12 }

moduleName OBJECT-TYPE
        SYNTAX        DisplayString (SIZE (0..20))
        ACCESS        read-write
        STATUS        mandatory
        DESCRIPTION   "A descriptive string used by the network administrator 
                      to name the module."
        ::= { moduleEntry 13 }

moduleNumPorts OBJECT-TYPE
        SYNTAX        INTEGER
        ACCESS        read-only
        STATUS        mandatory
        DESCRIPTION   "The number of ports supported by the module."
        ::= { moduleEntry 14 }

modulePortStatus OBJECT-TYPE
        SYNTAX        OCTET STRING (SIZE (0..20))
        ACCESS        read-only
        STATUS        mandatory
        DESCRIPTION   "A series of bytes containing status information about 
                      the module and each of the ports on the module.  The 
                      first byte contains the status for the module (same 
                      value as moduleStatus), and subsequent bytes contain 
                      status for the first through the last ports on the 
                      module (same value as portStatus)."
        ::= { moduleEntry 15 }


-- the port group

portTable OBJECT-TYPE
        SYNTAX        SEQUENCE OF PortEntry
        ACCESS        not-accessible
        STATUS        mandatory
        DESCRIPTION   "A list of port entries.  The number of entries is 
                      determined by the number of modules in the concentrator 
                      and the number of ports on each module."
        ::= { port 1 }

portEntry OBJECT-TYPE
        SYNTAX        PortEntry
        ACCESS        not-accessible
        STATUS        mandatory
        DESCRIPTION   "Entry containing information for a particular port on 
                      a module."
        INDEX         { portModuleIndex, portIndex }
        ::= { portTable 1 }

PortEntry ::= SEQUENCE {
                portModuleIndex
                        INTEGER,
                portIndex
                        INTEGER,
                portFddiIndex
                        INTEGER,
                portName
                        DisplayString,
                portType
                        INTEGER,
                portStatus
                        INTEGER
                }

portModuleIndex OBJECT-TYPE
        SYNTAX        INTEGER
        ACCESS        read-only
        STATUS        mandatory
        DESCRIPTION   "A unique value for each module within the concentrator.
                      This value is determined by the chassis slot number 
                      which the module is plugged into.  Valid entries are 1 
                      to the value of chassisNumSlots."
        ::= { portEntry 1 }

portIndex OBJECT-TYPE
        SYNTAX        INTEGER
        ACCESS        read-only
        STATUS        mandatory
        DESCRIPTION   "A unique value for each port within a module.  This 
                      value is determined by the location of the port on the 
                      module.  Valid entries are 1 to the value of 
                      moduleNumPorts for this module."
        ::= { portEntry 2 }

portFddiIndex OBJECT-TYPE
        SYNTAX        INTEGER
        ACCESS        read-only
        STATUS        mandatory
        DESCRIPTION   "The snmpFddiPORTIndex for this module/port."
        ::= { portEntry 3 }

portName OBJECT-TYPE
        SYNTAX        DisplayString (SIZE (0..20))
        ACCESS        read-write
        STATUS        mandatory
        DESCRIPTION   "A descriptive string used by the network administrator 
                      to name the port."
        ::= { portEntry 4 }

portType OBJECT-TYPE
        SYNTAX        INTEGER {
                                other(1),       -- none of the following
                                cddi(2),        -- CDDI (twisted pair)
                                fiber(3),       -- fiber optic cable
                                multiMedia(4)   -- multi-media connector
                                }
        ACCESS        read-only
        STATUS        mandatory
        DESCRIPTION   "The type of physical layer medium dependent interface
                      on the port."
        ::= { portEntry 5 }

portStatus OBJECT-TYPE
        SYNTAX        INTEGER {
                                other(1),       -- none of the following
                                ok(2),          -- status ok
                                minorFault(3),  -- minor problem
                                majorFault(4)   -- major problem
                                }
        ACCESS        read-only
        STATUS        mandatory
        DESCRIPTION   "The operational status of the port.  If the status is 
                      not ok, the values of snmpFddiPORTCEState and 
                      snmpFddiPORTConnectState give more detailed information 
                      about the port's failure condition(s)."
        ::= { portEntry 6 }
END

------------------ End of crescendo-concentrator-mib file -----------------
