--******************************************************************
--*
--*         Copyright (c) 1993, 1999 by 3Com Corporation
--*                    All Rights Reserved
--*
--*    $Revision:   1.19  $
--*    $Date:   Jun 29 2000 11:38:56  $
--*
--*    3COM DS3 MIB
--*
--******************************************************************


DS3-3COM-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

ds3 OBJECT IDENTIFIER ::= { nas 44 }

ds3Cfg OBJECT IDENTIFIER ::= { ds3 1 }

ds3CfgTable OBJECT-TYPE
SYNTAX SEQUENCE OF DS3CfgEntry
ACCESS not-accessible
STATUS mandatory
DESCRIPTION
"The DS3 Configuration Table."
::= { ds3Cfg 1 }

ds3CfgEntry OBJECT-TYPE
SYNTAX DS3CfgEntry
ACCESS not-accessible
STATUS mandatory
DESCRIPTION
"An entry in the DS3 Configuration Table."
INDEX { ds3CfgIndex }
::= { ds3CfgTable 1 }

DS3CfgEntry ::=
SEQUENCE {
ds3CfgIndex
    INTEGER,
ds3CfgXmitLineBuildOut
    INTEGER,
ds3CfgMonitorPortSource
    INTEGER
}

ds3CfgIndex OBJECT-TYPE
SYNTAX INTEGER
ACCESS read-write
STATUS mandatory
DESCRIPTION
"A unique value at the DS3 level in the chassis."
::= { ds3CfgEntry 1 }

ds3CfgXmitLineBuildOut OBJECT-TYPE
SYNTAX INTEGER{
  twoHundredTwentyFive(1),
  fourHundredFifty(2)
}
ACCESS read-write
STATUS mandatory
DESCRIPTION
"This object is used to configure the amount of attenuation 
that is to be applied to the DS3 transmit signal in order 
to control cross-talk, etc. The settings are for distances 
of 0-225 feet or 226 to 450 feet. Default=225(1)"
::= { ds3CfgEntry 2 }

ds3CfgMonitorPortSource OBJECT-TYPE
SYNTAX INTEGER{
  spanBITS(29),
  spanLine1(1),
  spanLine2(2),
  spanLine3(3),
  spanLine4(4),
  spanLine5(5),
  spanLine6(6),
  spanLine7(7),
  spanLine8(8),
  spanLine9(9),
  spanLine10(10),
  spanLine11(11),
  spanLine12(12),
  spanLine13(13),
  spanLine14(14),
  spanLine15(15),
  spanLine16(16),
  spanLine17(17),
  spanLine18(18),
  spanLine19(19),
  spanLine20(20),
  spanLine21(21),
  spanLine22(22),
  spanLine23(23),
  spanLine24(24),
  spanLine25(25),
  spanLine26(26),
  spanLine27(27),
  spanLine28(28)
}
ACCESS read-write
STATUS mandatory
DESCRIPTION
"This object is for designation of monitor port DS1 source. 
Default=spanLine1(1)."
::= { ds3CfgEntry 3 }

ds3Current OBJECT IDENTIFIER ::= { ds3 2 }

ds3CurrentTable OBJECT-TYPE
SYNTAX SEQUENCE OF DS3CurrentEntry
ACCESS not-accessible
STATUS mandatory
DESCRIPTION
"This table contains various statistics being collected for 
the current 15 minute interval."
::= { ds3Current 1 }

ds3CurrentEntry OBJECT-TYPE
SYNTAX DS3CurrentEntry
ACCESS not-accessible
STATUS mandatory
DESCRIPTION
"An entry in the DS3 current table."
INDEX { ds3CurrentIndex }
::= { ds3CurrentTable 1 }

DS3CurrentEntry ::=
SEQUENCE {
ds3CurrentIndex
    INTEGER,
ds3CurrentFCPs
    Gauge,
ds3CurrentFCCPs
    Gauge,
ds3CurrentSESLs
    Gauge,
ds3CurrentUASCPs
    Gauge
}

ds3CurrentIndex OBJECT-TYPE
SYNTAX INTEGER
ACCESS read-only
STATUS mandatory
DESCRIPTION
"The index value which uniquely identifies the DS3 interface 
to which this entry is applicable."
::= { ds3CurrentEntry 1 }

ds3CurrentFCPs OBJECT-TYPE
SYNTAX Gauge
ACCESS read-only
STATUS mandatory
DESCRIPTION
"This object indicates near end path failure count. The 
count of LOF or AIS events."
::= { ds3CurrentEntry 2 }

ds3CurrentFCCPs OBJECT-TYPE
SYNTAX Gauge
ACCESS read-only
STATUS mandatory
DESCRIPTION
"This object indicates far end path failure count. The count 
of Remote Alarm Indication (RAI) events."
::= { ds3CurrentEntry 3 }

ds3CurrentSESLs OBJECT-TYPE
SYNTAX Gauge
ACCESS read-only
STATUS mandatory
DESCRIPTION
"The object is the counter associated with the number of 
Severely Errored Seconds on the line."
::= { ds3CurrentEntry 4 }

ds3CurrentUASCPs OBJECT-TYPE
SYNTAX Gauge
ACCESS read-only
STATUS mandatory
DESCRIPTION
"This object is the counter associated with the number of 
Unavailable Seconds for the C-bit parity application."
::= { ds3CurrentEntry 5 }

ds3Interval OBJECT IDENTIFIER ::= { ds3 3 }

ds3IntervalTable OBJECT-TYPE
SYNTAX SEQUENCE OF DS3IntervalEntry
ACCESS not-accessible
STATUS mandatory
DESCRIPTION
"The DS3 Interval Table contains various statistics 
collected by each DS3 Interface over the previous 24 hours 
of operation. The past 24 hours are broken into 96 
completed 15 minute intervals. Each row in this table 
represents one such interval (identified by 
ds3IntervalNumber) and for one specific interface 
(identified by ds3IntervalIndex)."
::= { ds3Interval 1 }

ds3IntervalEntry OBJECT-TYPE
SYNTAX DS3IntervalEntry
ACCESS not-accessible
STATUS mandatory
DESCRIPTION
"An entry in the DS3 Interval Table."
INDEX { ds3IntervalIndex, ds3IntervalNumber }
::= { ds3IntervalTable 1 }

DS3IntervalEntry ::=
SEQUENCE {
ds3IntervalIndex
    INTEGER,
ds3IntervalNumber
    INTEGER,
ds3IntervalSESLs
    Gauge,
ds3IntervalCVCPs
    Gauge,
ds3IntervalUASCPs
    Gauge
}

ds3IntervalIndex OBJECT-TYPE
SYNTAX INTEGER
ACCESS read-only
STATUS mandatory
DESCRIPTION
"The index value which uniquely identifies the DS3 interface 
to which this entry is applicable."
::= { ds3IntervalEntry 1 }

ds3IntervalNumber OBJECT-TYPE
SYNTAX INTEGER (1..96)
ACCESS read-only
STATUS mandatory
DESCRIPTION
"A number between 1 and 96, where 1 is the most recently 
completed 15 minute interval and 96 is the 15 minutes 
interval completes 23 hours and 45 minutes prior to 
interval 1."
::= { ds3IntervalEntry 2 }

ds3IntervalSESLs OBJECT-TYPE
SYNTAX Gauge
ACCESS read-only
STATUS mandatory
DESCRIPTION
"This object is the counter associated with the number of 
Severely Errored Seconds on the line in the previous 15 
minute interval."
::= { ds3IntervalEntry 3 }

ds3IntervalCVCPs OBJECT-TYPE
SYNTAX Gauge
ACCESS read-only
STATUS mandatory
DESCRIPTION
"This object is the counter associated with the number of 
near-end path code violations for the C-bit parity 
application in the previous 15 minute interval."
::= { ds3IntervalEntry 4 }

ds3IntervalUASCPs OBJECT-TYPE
SYNTAX Gauge
ACCESS read-only
STATUS mandatory
DESCRIPTION
"This object is the counter associated with the number of 
Unavailable Seconds for the C-bit parity application in the 
previous 15 minute interval."
::= { ds3IntervalEntry 5 }

ds3Total OBJECT IDENTIFIER ::= { ds3 4 }

ds3TotalTable OBJECT-TYPE
SYNTAX SEQUENCE OF DS3TotalEntry
ACCESS not-accessible
STATUS mandatory
DESCRIPTION
"The DS3 Total Table contains the cumulative sum of the 
various statics for the 24 hour period preceding the 
current interval."
::= { ds3Total 1 }

ds3TotalEntry OBJECT-TYPE
SYNTAX DS3TotalEntry
ACCESS not-accessible
STATUS mandatory
DESCRIPTION
"An entry in the DS3 Total Table."
INDEX { ds3TotalIndex }
::= { ds3TotalTable 1 }

DS3TotalEntry ::=
SEQUENCE {
ds3TotalIndex
    INTEGER,
ds3TotalSESLs
    Gauge,
ds3TotalCVCPs
    Gauge,
ds3TotalUASCPs
    Gauge
}

ds3TotalIndex OBJECT-TYPE
SYNTAX INTEGER
ACCESS read-only
STATUS mandatory
DESCRIPTION
"The index value which uniquely identifies the DS3 interface 
to which this entry is applicable."
::= { ds3TotalEntry 1 }

ds3TotalSESLs OBJECT-TYPE
SYNTAX Gauge
ACCESS read-only
STATUS mandatory
DESCRIPTION
"This object is the counter associated with the number of 
Severely Errored Seconds on the line in the previous 24 
hour interval. Invalid 15 intervals count as 0."
::= { ds3TotalEntry 2 }

ds3TotalCVCPs OBJECT-TYPE
SYNTAX Gauge
ACCESS read-only
STATUS mandatory
DESCRIPTION
"This object is the counter associated with the number of 
near-end path code violations for the C-bit parity 
application in the previous 24 hour interval. Invalid 15 
minute intervals count as 0."
::= { ds3TotalEntry 3 }

ds3TotalUASCPs OBJECT-TYPE
SYNTAX Gauge
ACCESS read-only
STATUS mandatory
DESCRIPTION
"This object is the counter associated with the number of 
Unavailable Seconds for the C-bit parity application in the 
previous 24 hour interval. Invalid 15 minute intervals 
count as 0."
::= { ds3TotalEntry 4 }

ds3TrapEnable OBJECT IDENTIFIER ::= { ds3 5 }

ds3TrapEnableTable OBJECT-TYPE
SYNTAX SEQUENCE OF DS3TrapEnableEntry
ACCESS not-accessible
STATUS mandatory
DESCRIPTION
"The DS3 Trap eanble table contains the line status change 
trap enable"


::= { ds3TrapEnable 1 }

ds3TrapEnableEntry OBJECT-TYPE
SYNTAX DS3TrapEnableEntry
ACCESS not-accessible
STATUS mandatory
DESCRIPTION
"An entry in Ds3 Trap Enable Table"
INDEX { ds3TrapEnableIndex }
::= { ds3TrapEnableTable 1 }

DS3TrapEnableEntry ::=
SEQUENCE {
ds3TrapEnableIndex
    INTEGER,
ds3LineStatusChangeTE
    INTEGER
}

ds3TrapEnableIndex OBJECT-TYPE
SYNTAX INTEGER
ACCESS read-only
STATUS mandatory
DESCRIPTION
"An unique value which identifies the DS3. "
::= { ds3TrapEnableEntry 1 }

ds3LineStatusChangeTE OBJECT-TYPE
SYNTAX INTEGER{
  enableTrap(1),
  disableAll(2),
  enableLog(3),
  enableAll(4)
}
ACCESS read-write
STATUS mandatory
DESCRIPTION
"DS3 Line status change trap enable flag"
::= { ds3TrapEnableEntry 2 }

ds3TrapObj OBJECT IDENTIFIER ::= { ds3 6 }

ds3TrapObjTable OBJECT-TYPE
SYNTAX SEQUENCE OF Ds3TrapObjEntry
ACCESS not-accessible
STATUS mandatory
DESCRIPTION
"DS3 Trap obj table is a pace holder for status string"
::= { ds3TrapObj 1 }

ds3TrapObjEntry OBJECT-TYPE
SYNTAX Ds3TrapObjEntry
ACCESS not-accessible
STATUS mandatory
DESCRIPTION
"An entry in DS3 Trap Obj table"
INDEX { ds3TrapObjIndex }
::= { ds3TrapObjTable 1 }

Ds3TrapObjEntry ::=
SEQUENCE {
ds3TrapObjIndex
    INTEGER,
ds3StatusObjString
    DisplayString
}

ds3TrapObjIndex OBJECT-TYPE
SYNTAX INTEGER
ACCESS read-only
STATUS mandatory
DESCRIPTION
"An unique value for the index"
::= { ds3TrapObjEntry 1 }

ds3StatusObjString OBJECT-TYPE
SYNTAX DisplayString (SIZE(0..50))
ACCESS not-accessible
STATUS mandatory
DESCRIPTION
"For line status string it is a place holder"
::= { ds3TrapObjEntry 2 }

END
