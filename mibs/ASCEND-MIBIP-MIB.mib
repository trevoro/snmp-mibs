--			Ascend mibip MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibipInterfaceProfile  OBJECT IDENTIFIER ::= { configuration 82}
    mibipGlobalProfile  OBJECT IDENTIFIER ::= { configuration 83}

	-- The mibipInterfaceProfile table
	--
	-- This table contains parameters for the mibipInterfaceProfile profile
	--

    mibipInterfaceProfileTable	OBJECT-TYPE
	SYNTAX		SEQUENCE OF MibipInterfaceProfileEntry
	ACCESS		not-accessible
	STATUS		mandatory
	DESCRIPTION	"A list of mibipInterfaceProfile profile entries."
	::= { mibipInterfaceProfile 1 }

    mibipInterfaceProfileEntry	OBJECT-TYPE
	SYNTAX		MibipInterfaceProfileEntry
	ACCESS		not-accessible
	STATUS		mandatory
	DESCRIPTION	"A mibipInterfaceProfile entry containing objects that
			 maps to the parameters of mibipInterfaceProfile profile."
	INDEX		{ ipInterfaceProfile-Shelf-o, ipInterfaceProfile-Slot-o, ipInterfaceProfile-Item-o, ipInterfaceProfile-LogicalItem-o }
	::= { mibipInterfaceProfileTable 1 }

    MibipInterfaceProfileEntry ::=
	SEQUENCE {
	    ipInterfaceProfile-Shelf-o
		INTEGER,
	    ipInterfaceProfile-Slot-o
		INTEGER,
	    ipInterfaceProfile-Item-o
		INTEGER,
	    ipInterfaceProfile-LogicalItem-o
		INTEGER,
	    ipInterfaceProfile-InterfaceAddress-PhysicalAddress-Shelf
		INTEGER,
	    ipInterfaceProfile-InterfaceAddress-PhysicalAddress-Slot
		INTEGER,
	    ipInterfaceProfile-InterfaceAddress-PhysicalAddress-ItemNumber
		INTEGER,
	    ipInterfaceProfile-InterfaceAddress-LogicalItem
		INTEGER,
	    ipInterfaceProfile-IpAddress
		IpAddress,
	    ipInterfaceProfile-Netmask
		IpAddress,
	    ipInterfaceProfile-o2ndIpAddress
		IpAddress,
	    ipInterfaceProfile-Netmask2
		IpAddress,
	    ipInterfaceProfile-ProxyMode
		INTEGER,
	    ipInterfaceProfile-RipMode
		INTEGER,
	    ipInterfaceProfile-o2ndRipMode
		INTEGER,
	    ipInterfaceProfile-RouteFilter
		DisplayString,
	    ipInterfaceProfile-Rip2UseMulticast
		INTEGER,
	    ipInterfaceProfile-Ospf-Active
		INTEGER,
	    ipInterfaceProfile-Ospf-Area
		IpAddress,
	    ipInterfaceProfile-Ospf-AreaType
		INTEGER,
	    ipInterfaceProfile-Ospf-HelloInterval
		INTEGER,
	    ipInterfaceProfile-Ospf-DeadInterval
		INTEGER,
	    ipInterfaceProfile-Ospf-Priority
		INTEGER,
	    ipInterfaceProfile-Ospf-AuthenType
		INTEGER,
	    ipInterfaceProfile-Ospf-AuthKey
		DisplayString,
	    ipInterfaceProfile-Ospf-KeyId
		INTEGER,
	    ipInterfaceProfile-Ospf-Cost
		INTEGER,
	    ipInterfaceProfile-Ospf-DownCost
		INTEGER,
	    ipInterfaceProfile-Ospf-AseType
		INTEGER,
	    ipInterfaceProfile-Ospf-AseTag
		DisplayString,
	    ipInterfaceProfile-Ospf-TransitDelay
		INTEGER,
	    ipInterfaceProfile-Ospf-RetransmitInterval
		INTEGER,
	    ipInterfaceProfile-Ospf-NonMulticast
		INTEGER,
	    ipInterfaceProfile-Ospf-NetworkType
		INTEGER,
	    ipInterfaceProfile-Ospf-PollInterval
		INTEGER,
	    ipInterfaceProfile-Ospf-Md5AuthKey
		DisplayString,
	    ipInterfaceProfile-MulticastAllowed
		INTEGER,
	    ipInterfaceProfile-MulticastRateLimit
		INTEGER,
	    ipInterfaceProfile-MulticastGroupLeaveDelay
		INTEGER,
	    ipInterfaceProfile-DirectedBroadcastAllowed
		INTEGER,
	    ipInterfaceProfile-Vrouter
		DisplayString,
	    ipInterfaceProfile-ManagementOnlyInterface
		INTEGER,
	    ipInterfaceProfile-DhcpClientEnabled
		INTEGER,
	    ipInterfaceProfile-NatProfileName
		DisplayString,
	    ipInterfaceProfile-AddressRealm
		INTEGER,
	    ipInterfaceProfile-VlanEnabled
		INTEGER,
	    ipInterfaceProfile-Action-o
		INTEGER
	}

    ipInterfaceProfile-Shelf-o	OBJECT-TYPE
	SYNTAX	INTEGER
	ACCESS	read-only
	STATUS	mandatory
	DESCRIPTION	""
	::= { mibipInterfaceProfileEntry 1 }

    ipInterfaceProfile-Slot-o	OBJECT-TYPE
	SYNTAX	INTEGER
	ACCESS	read-only
	STATUS	mandatory
	DESCRIPTION	""
	::= { mibipInterfaceProfileEntry 2 }

    ipInterfaceProfile-Item-o	OBJECT-TYPE
	SYNTAX	INTEGER
	ACCESS	read-only
	STATUS	mandatory
	DESCRIPTION	""
	::= { mibipInterfaceProfileEntry 3 }

    ipInterfaceProfile-LogicalItem-o	OBJECT-TYPE
	SYNTAX	INTEGER
	ACCESS	read-only
	STATUS	mandatory
	DESCRIPTION	""
	::= { mibipInterfaceProfileEntry 4 }

    ipInterfaceProfile-InterfaceAddress-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibipInterfaceProfileEntry 5 }

    ipInterfaceProfile-InterfaceAddress-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibipInterfaceProfileEntry 6 }

    ipInterfaceProfile-InterfaceAddress-PhysicalAddress-ItemNumber	OBJECT-TYPE
	SYNTAX	INTEGER
	ACCESS	read-write
	STATUS	mandatory
	DESCRIPTION	"A number that specifies an addressable entity within the context of shelf and slot."
	::= { mibipInterfaceProfileEntry 7 }

    ipInterfaceProfile-InterfaceAddress-LogicalItem	OBJECT-TYPE
	SYNTAX	INTEGER
	ACCESS	read-write
	STATUS	mandatory
	DESCRIPTION	"A number that specifies an addressable logical entity within the context of a physical address."
	::= { mibipInterfaceProfileEntry 8 }

    ipInterfaceProfile-IpAddress	OBJECT-TYPE
	SYNTAX	IpAddress
	ACCESS	read-write
	STATUS	mandatory
	DESCRIPTION	"The IP Address of this interface."
	::= { mibipInterfaceProfileEntry 9 }

    ipInterfaceProfile-Netmask	OBJECT-TYPE
	SYNTAX	IpAddress
	ACCESS	read-write
	STATUS	mandatory
	DESCRIPTION	"The Network Mask of this interface."
	::= { mibipInterfaceProfileEntry 43 }

    ipInterfaceProfile-o2ndIpAddress	OBJECT-TYPE
	SYNTAX	IpAddress
	ACCESS	read-write
	STATUS	mandatory
	DESCRIPTION	"Alternate IP address of this interface."
	::= { mibipInterfaceProfileEntry 10 }

    ipInterfaceProfile-Netmask2	OBJECT-TYPE
	SYNTAX	IpAddress
	ACCESS	read-write
	STATUS	mandatory
	DESCRIPTION	"Netmask for the alternate IP address."
	::= { mibipInterfaceProfileEntry 44 }

    ipInterfaceProfile-ProxyMode	OBJECT-TYPE
	SYNTAX	INTEGER {
		    off (1),
		    active (2),
		    inactive (3),
		    always (4)
		}
	ACCESS	read-write
	STATUS	mandatory
	DESCRIPTION	"Specify how proxy arp is to be used on an interface."
	::= { mibipInterfaceProfileEntry 11 }

    ipInterfaceProfile-RipMode	OBJECT-TYPE
	SYNTAX	INTEGER {
		    routingOff (1),
		    routingSendOnly (2),
		    routingRecvOnly (3),
		    routingSendAndRecv (4),
		    routingSendOnlyV2 (5),
		    routingRecvOnlyV2 (6),
		    routingSendAndRecvV2 (7)
		}
	ACCESS	read-write
	STATUS	mandatory
	DESCRIPTION	"Specify how RIP is to be used on this interface. Options are off, on, ignore received routing updates, don't send routing updates."
	::= { mibipInterfaceProfileEntry 12 }

    ipInterfaceProfile-o2ndRipMode	OBJECT-TYPE
	SYNTAX	INTEGER {
		    routingOff (1),
		    routingSendOnly (2),
		    routingRecvOnly (3),
		    routingSendAndRecv (4),
		    routingSendOnlyV2 (5),
		    routingRecvOnlyV2 (6),
		    routingSendAndRecvV2 (7)
		}
	ACCESS	read-write
	STATUS	mandatory
	DESCRIPTION	"Specify how RIP is to be used on this interface. Options are off, on, ignore received routing updates, don't send routing updates."
	::= { mibipInterfaceProfileEntry 13 }

    ipInterfaceProfile-RouteFilter	OBJECT-TYPE
	SYNTAX	DisplayString
	ACCESS	read-write
	STATUS	mandatory
	DESCRIPTION	"The name of this filter. All filters are referenced by name so a name must be assigned to active filters."
	::= { mibipInterfaceProfileEntry 14 }

    ipInterfaceProfile-Rip2UseMulticast	OBJECT-TYPE
	SYNTAX	INTEGER {
		    no (1),
		    yes (2)
		}
	ACCESS	read-write
	STATUS	mandatory
	DESCRIPTION	"Use multicast address for sending RIP V2 packets on this interface ."
	::= { mibipInterfaceProfileEntry 15 }

    ipInterfaceProfile-Ospf-Active	OBJECT-TYPE
	SYNTAX	INTEGER {
		    no (1),
		    yes (2)
		}
	ACCESS	read-write
	STATUS	mandatory
	DESCRIPTION	"Is OSPF active on this interface."
	::= { mibipInterfaceProfileEntry 16 }

    ipInterfaceProfile-Ospf-Area	OBJECT-TYPE
	SYNTAX	IpAddress
	ACCESS	read-write
	STATUS	mandatory
	DESCRIPTION	"The area that this interface belongs to."
	::= { mibipInterfaceProfileEntry 17 }

    ipInterfaceProfile-Ospf-AreaType	OBJECT-TYPE
	SYNTAX	INTEGER {
		    normal (1),
		    stub (2),
		    nSSA (3)
		}
	ACCESS	read-write
	STATUS	mandatory
	DESCRIPTION	"The type of Area. Normal, Stub, NSSA"
	::= { mibipInterfaceProfileEntry 18 }

    ipInterfaceProfile-Ospf-HelloInterval	OBJECT-TYPE
	SYNTAX	INTEGER
	ACCESS	read-write
	STATUS	mandatory
	DESCRIPTION	"The hello interval (seconds)."
	::= { mibipInterfaceProfileEntry 19 }

    ipInterfaceProfile-Ospf-DeadInterval	OBJECT-TYPE
	SYNTAX	INTEGER
	ACCESS	read-write
	STATUS	mandatory
	DESCRIPTION	"The dead interval (seconds)."
	::= { mibipInterfaceProfileEntry 20 }

    ipInterfaceProfile-Ospf-Priority	OBJECT-TYPE
	SYNTAX	INTEGER
	ACCESS	read-write
	STATUS	mandatory
	DESCRIPTION	"The priority of this router in DR elections."
	::= { mibipInterfaceProfileEntry 21 }

    ipInterfaceProfile-Ospf-AuthenType	OBJECT-TYPE
	SYNTAX	INTEGER {
		    none (1),
		    simple (2),
		    md5 (3)
		}
	ACCESS	read-write
	STATUS	mandatory
	DESCRIPTION	"The type of OSPF authentication in effect."
	::= { mibipInterfaceProfileEntry 22 }

    ipInterfaceProfile-Ospf-AuthKey	OBJECT-TYPE
	SYNTAX	DisplayString
	ACCESS	read-write
	STATUS	mandatory
	DESCRIPTION	"The authentication key."
	::= { mibipInterfaceProfileEntry 23 }

    ipInterfaceProfile-Ospf-KeyId	OBJECT-TYPE
	SYNTAX	INTEGER
	ACCESS	read-write
	STATUS	mandatory
	DESCRIPTION	"The key identifier for MD5 authentication."
	::= { mibipInterfaceProfileEntry 24 }

    ipInterfaceProfile-Ospf-Cost	OBJECT-TYPE
	SYNTAX	INTEGER
	ACCESS	read-write
	STATUS	mandatory
	DESCRIPTION	"The output cost."
	::= { mibipInterfaceProfileEntry 25 }

    ipInterfaceProfile-Ospf-DownCost	OBJECT-TYPE
	SYNTAX	INTEGER
	ACCESS	read-write
	STATUS	mandatory
	DESCRIPTION	"The output cost when the link is physically down but virtually up."
	::= { mibipInterfaceProfileEntry 26 }

    ipInterfaceProfile-Ospf-AseType	OBJECT-TYPE
	SYNTAX	INTEGER {
		    type1 (1),
		    type2 (2)
		}
	ACCESS	read-write
	STATUS	mandatory
	DESCRIPTION	"The OSPF ASE type of this LSA."
	::= { mibipInterfaceProfileEntry 27 }

    ipInterfaceProfile-Ospf-AseTag	OBJECT-TYPE
	SYNTAX	DisplayString
	ACCESS	read-write
	STATUS	mandatory
	DESCRIPTION	"The OSPF ASE tag of this link."
	::= { mibipInterfaceProfileEntry 28 }

    ipInterfaceProfile-Ospf-TransitDelay	OBJECT-TYPE
	SYNTAX	INTEGER
	ACCESS	read-write
	STATUS	mandatory
	DESCRIPTION	"The estimated transit delay (seconds)."
	::= { mibipInterfaceProfileEntry 29 }

    ipInterfaceProfile-Ospf-RetransmitInterval	OBJECT-TYPE
	SYNTAX	INTEGER
	ACCESS	read-write
	STATUS	mandatory
	DESCRIPTION	"The retransmit time (seconds)."
	::= { mibipInterfaceProfileEntry 30 }

    ipInterfaceProfile-Ospf-NonMulticast	OBJECT-TYPE
	SYNTAX	INTEGER {
		    no (1),
		    yes (2)
		}
	ACCESS	read-write
	STATUS	mandatory
	DESCRIPTION	"Use direct addresses instead of multicast addresses."
	::= { mibipInterfaceProfileEntry 31 }

    ipInterfaceProfile-Ospf-NetworkType	OBJECT-TYPE
	SYNTAX	INTEGER {
		    broadcast (2),
		    nonBroadcast (3),
		    pointToPoint (4)
		}
	ACCESS	read-write
	STATUS	mandatory
	DESCRIPTION	"The type of network attachment."
	::= { mibipInterfaceProfileEntry 32 }

    ipInterfaceProfile-Ospf-PollInterval	OBJECT-TYPE
	SYNTAX	INTEGER
	ACCESS	read-write
	STATUS	mandatory
	DESCRIPTION	"The poll interval for non-broadcast multi-access network (seconds)."
	::= { mibipInterfaceProfileEntry 33 }

    ipInterfaceProfile-Ospf-Md5AuthKey	OBJECT-TYPE
	SYNTAX	DisplayString
	ACCESS	read-write
	STATUS	mandatory
	DESCRIPTION	"The MD5 authentication key."
	::= { mibipInterfaceProfileEntry 34 }

    ipInterfaceProfile-MulticastAllowed	OBJECT-TYPE
	SYNTAX	INTEGER {
		    no (1),
		    yes (2)
		}
	ACCESS	read-write
	STATUS	mandatory
	DESCRIPTION	"Multicast traffic allowed."
	::= { mibipInterfaceProfileEntry 35 }

    ipInterfaceProfile-MulticastRateLimit	OBJECT-TYPE
	SYNTAX	INTEGER
	ACCESS	read-write
	STATUS	mandatory
	DESCRIPTION	"Multicast traffic rate limit in seconds "
	::= { mibipInterfaceProfileEntry 36 }

    ipInterfaceProfile-MulticastGroupLeaveDelay	OBJECT-TYPE
	SYNTAX	INTEGER
	ACCESS	read-write
	STATUS	mandatory
	DESCRIPTION	"Multicast group leave dealy in seconds "
	::= { mibipInterfaceProfileEntry 37 }

    ipInterfaceProfile-DirectedBroadcastAllowed	OBJECT-TYPE
	SYNTAX	INTEGER {
		    no (1),
		    yes (2)
		}
	ACCESS	read-write
	STATUS	mandatory
	DESCRIPTION	"allow forwarding directed broadcast traffic "
	::= { mibipInterfaceProfileEntry 38 }

    ipInterfaceProfile-Vrouter	OBJECT-TYPE
	SYNTAX	DisplayString
	ACCESS	read-write
	STATUS	mandatory
	DESCRIPTION	"Specifies the VRouter in which this IP interface profile belongs."
	::= { mibipInterfaceProfileEntry 39 }

    ipInterfaceProfile-ManagementOnlyInterface	OBJECT-TYPE
	SYNTAX	INTEGER {
		    no (1),
		    yes (2)
		}
	ACCESS	read-write
	STATUS	mandatory
	DESCRIPTION	"set the interface for management use only"
	::= { mibipInterfaceProfileEntry 40 }

    ipInterfaceProfile-DhcpClientEnabled	OBJECT-TYPE
	SYNTAX	INTEGER {
		    no (1),
		    yes (2)
		}
	ACCESS	read-write
	STATUS	mandatory
	DESCRIPTION	""
	::= { mibipInterfaceProfileEntry 41 }

    ipInterfaceProfile-NatProfileName	OBJECT-TYPE
	SYNTAX	DisplayString
	ACCESS	read-write
	STATUS	mandatory
	DESCRIPTION	"The profile to use for NAT translations on this interface."
	::= { mibipInterfaceProfileEntry 45 }

    ipInterfaceProfile-AddressRealm	OBJECT-TYPE
	SYNTAX	INTEGER
	ACCESS	read-write
	STATUS	mandatory
	DESCRIPTION	"Used to determine which interfaces and WANs are connected to the same address space--they will have the identical values in this field."
	::= { mibipInterfaceProfileEntry 46 }

    ipInterfaceProfile-VlanEnabled	OBJECT-TYPE
	SYNTAX	INTEGER {
		    no (1),
		    yes (2)
		}
	ACCESS	read-write
	STATUS	mandatory
	DESCRIPTION	"Enable vlan for this ip interface."
	::= { mibipInterfaceProfileEntry 47 }

    ipInterfaceProfile-Action-o	OBJECT-TYPE
	SYNTAX	INTEGER {
		    noAction (1),
		    createProfile (2),
		    deleteProfile (3)
		}
	ACCESS	read-write
	STATUS	mandatory
	DESCRIPTION	""
	::= { mibipInterfaceProfileEntry 42 }


	-- The mibipGlobalProfile table
	--
	-- This table contains parameters for the mibipGlobalProfile profile
	--

    mibipGlobalProfileTable	OBJECT-TYPE
	SYNTAX		SEQUENCE OF MibipGlobalProfileEntry
	ACCESS		not-accessible
	STATUS		mandatory
	DESCRIPTION	"A list of mibipGlobalProfile profile entries."
	::= { mibipGlobalProfile 1 }

    mibipGlobalProfileEntry	OBJECT-TYPE
	SYNTAX		MibipGlobalProfileEntry
	ACCESS		not-accessible
	STATUS		mandatory
	DESCRIPTION	"A mibipGlobalProfile entry containing objects that
			 maps to the parameters of mibipGlobalProfile profile."
	INDEX		{ ipGlobalProfile-Index-o }
	::= { mibipGlobalProfileTable 1 }

    MibipGlobalProfileEntry ::=
	SEQUENCE {
	    ipGlobalProfile-Index-o
		INTEGER,
	    ipGlobalProfile-DomainName
		DisplayString,
	    ipGlobalProfile-DnsPrimaryServer
		IpAddress,
	    ipGlobalProfile-DhcpServer-Active
		INTEGER,
	    ipGlobalProfile-DhcpServer-LeaseDuration
		INTEGER,
	    ipGlobalProfile-DhcpServer-DefaultPool
		INTEGER,
	    ipGlobalProfile-DhcpServer-DefaultMaxLease
		INTEGER,
	    ipGlobalProfile-DhcpServer-DefaultLeaseDuration
		INTEGER,
	    ipGlobalProfile-DhcpServer-TftpHostName
		DisplayString,
	    ipGlobalProfile-DhcpServer-BootFilePath
		DisplayString,
	    ipGlobalProfile-DhcpServer-ServerAddress
		IpAddress,
	    ipGlobalProfile-DnsSecondaryServer
		IpAddress,
	    ipGlobalProfile-DnsServerQueryType
		INTEGER,
	    ipGlobalProfile-SystemIpAddr
		IpAddress,
	    ipGlobalProfile-NetbiosPrimaryNs
		IpAddress,
	    ipGlobalProfile-NetbiosSecondaryNs
		IpAddress,
	    ipGlobalProfile-MustAcceptAddressAssign
		INTEGER,
	    ipGlobalProfile-PoolSummary
		INTEGER,
	    ipGlobalProfile-PoolChaining
		INTEGER,
	    ipGlobalProfile-PoolOspfAdvType
		INTEGER,
	    ipGlobalProfile-RipPolicy
		INTEGER,
	    ipGlobalProfile-RipOptions-MaxMultipathOrBackupRoutes
		INTEGER,
	    ipGlobalProfile-SummarizeRipRoutes
		INTEGER,
	    ipGlobalProfile-RipTrigger
		INTEGER,
	    ipGlobalProfile-MinRipTriggerDelay
		INTEGER,
	    ipGlobalProfile-MaxRipTriggerDelay
		INTEGER,
	    ipGlobalProfile-BootpEnabled
		INTEGER,
	    ipGlobalProfile-BootpRelay-Active
		INTEGER,
	    ipGlobalProfile-DropSourceRoutedIpPackets
		INTEGER,
	    ipGlobalProfile-IgnoreDefRoute
		INTEGER,
	    ipGlobalProfile-RarpEnabled
		INTEGER,
	    ipGlobalProfile-UdpCksum
		INTEGER,
	    ipGlobalProfile-TcpTimeout
		INTEGER,
	    ipGlobalProfile-DialoutPoison
		INTEGER,
	    ipGlobalProfile-TelnetPassword
		DisplayString,
	    ipGlobalProfile-UserProfile
		DisplayString,
	    ipGlobalProfile-SharedProf
		INTEGER,
	    ipGlobalProfile-DnsListAttempt
		INTEGER,
	    ipGlobalProfile-StaticPref
		INTEGER,
	    ipGlobalProfile-RipPref
		INTEGER,
	    ipGlobalProfile-RipQueueDepth
		INTEGER,
	    ipGlobalProfile-OspfPref
		INTEGER,
	    ipGlobalProfile-OspfAsePref
		INTEGER,
	    ipGlobalProfile-OspfGlobal-Enable
		INTEGER,
	    ipGlobalProfile-OspfGlobal-AsBoundaryRouter
		INTEGER,
	    ipGlobalProfile-OspfGlobal-OspfMaxLsa
		INTEGER,
	    ipGlobalProfile-RipTag
		DisplayString,
	    ipGlobalProfile-RipAseType
		INTEGER,
	    ipGlobalProfile-IprouteCacheEnable
		INTEGER,
	    ipGlobalProfile-IprouteCacheSize
		INTEGER,
	    ipGlobalProfile-IpportCacheEnable
		INTEGER,
	    ipGlobalProfile-SuppressHostRoutes
		INTEGER,
	    ipGlobalProfile-SntpInfo-Enabled
		INTEGER,
	    ipGlobalProfile-SntpInfo-oGMTOffset
		INTEGER,
	    ipGlobalProfile-SntpInfo-UpdateThreshold
		INTEGER,
	    ipGlobalProfile-SntpInfo-UpdateInterval
		INTEGER,
	    ipGlobalProfile-DnsListSize
		INTEGER,
	    ipGlobalProfile-ClientPrimaryDnsServer
		IpAddress,
	    ipGlobalProfile-ClientSecondaryDnsServer
		IpAddress,
	    ipGlobalProfile-AllowAsClientDnsInfo
		INTEGER,
	    ipGlobalProfile-DnsLocalTable-Enabled
		INTEGER,
	    ipGlobalProfile-DnsLocalTable-AutoUpdate
		INTEGER,
	    ipGlobalProfile-MulticastForwarding
		INTEGER,
	    ipGlobalProfile-MboneProfile
		DisplayString,
	    ipGlobalProfile-MboneLanInterface-PhysicalAddress-Shelf
		INTEGER,
	    ipGlobalProfile-MboneLanInterface-PhysicalAddress-Slot
		INTEGER,
	    ipGlobalProfile-MboneLanInterface-PhysicalAddress-ItemNumber
		INTEGER,
	    ipGlobalProfile-MboneLanInterface-LogicalItem
		INTEGER,
	    ipGlobalProfile-MulticastHbeatAddr
		IpAddress,
	    ipGlobalProfile-MulticastHbeatPort
		INTEGER,
	    ipGlobalProfile-MulticastHbeatSlotTime
		INTEGER,
	    ipGlobalProfile-MulticastHbeatNumberSlot
		INTEGER,
	    ipGlobalProfile-MulticastHbeatAlarmThreshold
		INTEGER,
	    ipGlobalProfile-MulticastHbeatSrcAddr
		IpAddress,
	    ipGlobalProfile-MulticastHbeatSrcAddrMask
		IpAddress,
	    ipGlobalProfile-SecDomainName
		DisplayString,
	    ipGlobalProfile-MulticastMemberTimeout
		INTEGER,
	    ipGlobalProfile-Finger
		INTEGER,
	    ipGlobalProfile-IgnoreIcmpRedirects
		INTEGER,
	    ipGlobalProfile-IcmpReplyDirectedBcast
		INTEGER,
	    ipGlobalProfile-SendIcmpDestUnreachable
		INTEGER,
	    ipGlobalProfile-GlobalVrouter
		DisplayString,
	    ipGlobalProfile-RouterId
		IpAddress,
	    ipGlobalProfile-DefaultFilterCacheTime
		INTEGER,
	    ipGlobalProfile-DefaultPrtCacheTime
		INTEGER,
	    ipGlobalProfile-TcpSynFloodProtect
		INTEGER,
	    ipGlobalProfile-ThrottleNoPortMatchUdpTrafficOnSlot
		INTEGER,
	    ipGlobalProfile-IpsecOptions-Enabled
		INTEGER,
	    ipGlobalProfile-IpsecOptions-SecurityPolicyDatabase
		DisplayString,
	    ipGlobalProfile-DnsCacheEnable
		INTEGER,
	    ipGlobalProfile-DnsAutoUpdateInterval
		INTEGER,
	    ipGlobalProfile-MboneTimeout
		INTEGER,
	    ipGlobalProfile-Action-o
		INTEGER
	}

    ipGlobalProfile-Index-o	OBJECT-TYPE
	SYNTAX	INTEGER
	ACCESS	read-only
	STATUS	mandatory
	DESCRIPTION	""
	::= { mibipGlobalProfileEntry 1 }

    ipGlobalProfile-DomainName	OBJECT-TYPE
	SYNTAX	DisplayString
	ACCESS	read-write
	STATUS	mandatory
	DESCRIPTION	"The DNS domain name assigned to this unit."
	::= { mibipGlobalProfileEntry 2 }

    ipGlobalProfile-DnsPrimaryServer	OBJECT-TYPE
	SYNTAX	IpAddress
	ACCESS	read-write
	STATUS	mandatory
	DESCRIPTION	"The IP address of the primary DNS server."
	::= { mibipGlobalProfileEntry 3 }

    ipGlobalProfile-DhcpServer-Active	OBJECT-TYPE
	SYNTAX	INTEGER {
		    no (1),
		    yes (2)
		}
	ACCESS	read-write
	STATUS	mandatory
	DESCRIPTION	"Enable DHCP address pool."
	::= { mibipGlobalProfileEntry 4 }

    ipGlobalProfile-DhcpServer-LeaseDuration	OBJECT-TYPE
	SYNTAX	INTEGER
	ACCESS	read-write
	STATUS	mandatory
	DESCRIPTION	"Lease will expire after renewal-time seconds."
	::= { mibipGlobalProfileEntry 5 }

    ipGlobalProfile-DhcpServer-DefaultPool	OBJECT-TYPE
	SYNTAX	INTEGER
	ACCESS	read-write
	STATUS	mandatory
	DESCRIPTION	"Pool number to use for all DHCP requests from local LAN."
	::= { mibipGlobalProfileEntry 6 }

    ipGlobalProfile-DhcpServer-DefaultMaxLease	OBJECT-TYPE
	SYNTAX	INTEGER
	ACCESS	read-write
	STATUS	mandatory
	DESCRIPTION	"Maximum number of leases allowed on this connection."
	::= { mibipGlobalProfileEntry 7 }

    ipGlobalProfile-DhcpServer-DefaultLeaseDuration	OBJECT-TYPE
	SYNTAX	INTEGER
	ACCESS	read-write
	STATUS	mandatory
	DESCRIPTION	"Lease will expire after default-lease-duration seconds."
	::= { mibipGlobalProfileEntry 8 }

    ipGlobalProfile-DhcpServer-TftpHostName	OBJECT-TYPE
	SYNTAX	DisplayString
	ACCESS	read-write
	STATUS	mandatory
	DESCRIPTION	"Name of TFTP host."
	::= { mibipGlobalProfileEntry 9 }

    ipGlobalProfile-DhcpServer-BootFilePath	OBJECT-TYPE
	SYNTAX	DisplayString
	ACCESS	read-write
	STATUS	mandatory
	DESCRIPTION	"Complete path to where boot file resides."
	::= { mibipGlobalProfileEntry 10 }

    ipGlobalProfile-DhcpServer-ServerAddress	OBJECT-TYPE
	SYNTAX	IpAddress
	ACCESS	read-write
	STATUS	mandatory
	DESCRIPTION	"Address of the server to be reported to client."
	::= { mibipGlobalProfileEntry 11 }

    ipGlobalProfile-DnsSecondaryServer	OBJECT-TYPE
	SYNTAX	IpAddress
	ACCESS	read-write
	STATUS	mandatory
	DESCRIPTION	"The IP address of the secondary DNS server. This server is used when the primary is not available."
	::= { mibipGlobalProfileEntry 12 }

    ipGlobalProfile-DnsServerQueryType	OBJECT-TYPE
	SYNTAX	INTEGER {
		    udp (1),
		    udpIgnoreTcBit (2),
		    tcp (3),
		    tcpKeepOpen (4)
		}
	ACCESS	read-write
	STATUS	mandatory
	DESCRIPTION	"Specify how to query a DNS server."
	::= { mibipGlobalProfileEntry 13 }

    ipGlobalProfile-SystemIpAddr	OBJECT-TYPE
	SYNTAX	IpAddress
	ACCESS	read-write
	STATUS	mandatory
	DESCRIPTION	"System ip address for the box."
	::= { mibipGlobalProfileEntry 14 }

    ipGlobalProfile-NetbiosPrimaryNs	OBJECT-TYPE
	SYNTAX	IpAddress
	ACCESS	read-write
	STATUS	mandatory
	DESCRIPTION	"The IP address of the primary NetBios name server."
	::= { mibipGlobalProfileEntry 15 }

    ipGlobalProfile-NetbiosSecondaryNs	OBJECT-TYPE
	SYNTAX	IpAddress
	ACCESS	read-write
	STATUS	mandatory
	DESCRIPTION	"The IP address of the secondary NetBios name server."
	::= { mibipGlobalProfileEntry 16 }

    ipGlobalProfile-MustAcceptAddressAssign	OBJECT-TYPE
	SYNTAX	INTEGER {
		    no (1),
		    yes (2)
		}
	ACCESS	read-write
	STATUS	mandatory
	DESCRIPTION	"Flag, when set indicates that addresses assigned from the address pool may NOT be overridden by addresses received from the far end."
	::= { mibipGlobalProfileEntry 17 }

    ipGlobalProfile-PoolSummary	OBJECT-TYPE
	SYNTAX	INTEGER {
		    no (1),
		    yes (2)
		}
	ACCESS	read-write
	STATUS	mandatory
	DESCRIPTION	"Flag, when set indicates that host addresses assigned from the pool should be marked as PRIVATE in the routing table and summarized to the world at large via a (constant) network advertisement for the whole pool."
	::= { mibipGlobalProfileEntry 18 }

    ipGlobalProfile-PoolChaining	OBJECT-TYPE
	SYNTAX	INTEGER {
		    no (1),
		    yes (2)
		}
	ACCESS	read-write
	STATUS	mandatory
	DESCRIPTION	"Enable ip address pool chaining."
	::= { mibipGlobalProfileEntry 19 }

    ipGlobalProfile-PoolOspfAdvType	OBJECT-TYPE
	SYNTAX	INTEGER {
		    type1 (1),
		    type2 (2),
		    internal (3)
		}
	ACCESS	read-write
	STATUS	mandatory
	DESCRIPTION	"The OSPF advertisement type to be used with pool summaries."
	::= { mibipGlobalProfileEntry 20 }

    ipGlobalProfile-RipPolicy	OBJECT-TYPE
	SYNTAX	INTEGER {
		    splitHorzn (1),
		    poisonRvrs (2)
		}
	ACCESS	read-write
	STATUS	mandatory
	DESCRIPTION	"An Enum describing whether to use Poison reverse or Split Horizon policy. Global for the box."
	::= { mibipGlobalProfileEntry 21 }

    ipGlobalProfile-RipOptions-MaxMultipathOrBackupRoutes	OBJECT-TYPE
	SYNTAX	INTEGER
	ACCESS	read-write
	STATUS	mandatory
	DESCRIPTION	"Max number of redundant routes learnt by RIP. Checked for new learnt RIP routes."
	::= { mibipGlobalProfileEntry 93 }

    ipGlobalProfile-SummarizeRipRoutes	OBJECT-TYPE
	SYNTAX	INTEGER {
		    no (1),
		    yes (2)
		}
	ACCESS	read-write
	STATUS	mandatory
	DESCRIPTION	"Summarize subnets in RIP broadcasts per RFC 1058/RFC 1009."
	::= { mibipGlobalProfileEntry 22 }

    ipGlobalProfile-RipTrigger	OBJECT-TYPE
	SYNTAX	INTEGER {
		    no (1),
		    yes (2)
		}
	ACCESS	read-write
	STATUS	mandatory
	DESCRIPTION	"When set to TRUE (its default value) it causes RIP to send triggered (incremental) updates. Otherwise full table updates are sent when a change in the routing table is noticed."
	::= { mibipGlobalProfileEntry 23 }

    ipGlobalProfile-MinRipTriggerDelay	OBJECT-TYPE
	SYNTAX	INTEGER
	ACCESS	read-write
	STATUS	mandatory
	DESCRIPTION	"Minimum delay in seconds to send triggered updates."
	::= { mibipGlobalProfileEntry 85 }

    ipGlobalProfile-MaxRipTriggerDelay	OBJECT-TYPE
	SYNTAX	INTEGER
	ACCESS	read-write
	STATUS	mandatory
	DESCRIPTION	"Maximum delay in seconds to send triggered updates."
	::= { mibipGlobalProfileEntry 86 }

    ipGlobalProfile-BootpEnabled	OBJECT-TYPE
	SYNTAX	INTEGER {
		    no (1),
		    yes (2)
		}
	ACCESS	read-write
	STATUS	mandatory
	DESCRIPTION	"TRUE if this box is to use bootp to get params and check for a new load."
	::= { mibipGlobalProfileEntry 24 }

    ipGlobalProfile-BootpRelay-Active	OBJECT-TYPE
	SYNTAX	INTEGER {
		    no (1),
		    yes (2)
		}
	ACCESS	read-write
	STATUS	mandatory
	DESCRIPTION	"Is BOOTP RELAY agent active."
	::= { mibipGlobalProfileEntry 25 }

    ipGlobalProfile-DropSourceRoutedIpPackets	OBJECT-TYPE
	SYNTAX	INTEGER {
		    no (1),
		    yes (2)
		}
	ACCESS	read-write
	STATUS	mandatory
	DESCRIPTION	"If TRUE, do not forward IP packets with the source route option set."
	::= { mibipGlobalProfileEntry 26 }

    ipGlobalProfile-IgnoreDefRoute	OBJECT-TYPE
	SYNTAX	INTEGER {
		    no (1),
		    yes (2)
		}
	ACCESS	read-write
	STATUS	mandatory
	DESCRIPTION	"A boolean. When set to TRUE (its default value) we will ignore default addresses advertized by routing protocols."
	::= { mibipGlobalProfileEntry 27 }

    ipGlobalProfile-RarpEnabled	OBJECT-TYPE
	SYNTAX	INTEGER {
		    no (1),
		    yes (2)
		}
	ACCESS	read-write
	STATUS	mandatory
	DESCRIPTION	"TRUE if interfaces are to RARP for their IP address."
	::= { mibipGlobalProfileEntry 28 }

    ipGlobalProfile-UdpCksum	OBJECT-TYPE
	SYNTAX	INTEGER {
		    no (1),
		    yes (2)
		}
	ACCESS	read-write
	STATUS	mandatory
	DESCRIPTION	"TRUE means that locally originated UDP packets will include a UDP checksum."
	::= { mibipGlobalProfileEntry 29 }

    ipGlobalProfile-TcpTimeout	OBJECT-TYPE
	SYNTAX	INTEGER
	ACCESS	read-write
	STATUS	mandatory
	DESCRIPTION	"The maximum time (in seconds) to spend in TCP retransmissions before deciding that there is no connection."
	::= { mibipGlobalProfileEntry 30 }

    ipGlobalProfile-DialoutPoison	OBJECT-TYPE
	SYNTAX	INTEGER {
		    no (1),
		    yes (2)
		}
	ACCESS	read-write
	STATUS	mandatory
	DESCRIPTION	"Should dialout routes be poisoned if no trunks."
	::= { mibipGlobalProfileEntry 31 }

    ipGlobalProfile-TelnetPassword	OBJECT-TYPE
	SYNTAX	DisplayString
	ACCESS	read-write
	STATUS	mandatory
	DESCRIPTION	"The password that must be used to be able to Telnet into the box."
	::= { mibipGlobalProfileEntry 32 }

    ipGlobalProfile-UserProfile	OBJECT-TYPE
	SYNTAX	DisplayString
	ACCESS	read-write
	STATUS	mandatory
	DESCRIPTION	"The name of the default user profile associated with telnet sessions. If none is specified, the user must log in."
	::= { mibipGlobalProfileEntry 33 }

    ipGlobalProfile-SharedProf	OBJECT-TYPE
	SYNTAX	INTEGER {
		    no (1),
		    yes (2)
		}
	ACCESS	read-write
	STATUS	mandatory
	DESCRIPTION	"When TRUE multiple users may share a connection profile, as long as IP addresses are not duplicated."
	::= { mibipGlobalProfileEntry 34 }

    ipGlobalProfile-DnsListAttempt	OBJECT-TYPE
	SYNTAX	INTEGER {
		    no (1),
		    yes (2)
		}
	ACCESS	read-write
	STATUS	mandatory
	DESCRIPTION	"Should DNS List feature be used."
	::= { mibipGlobalProfileEntry 35 }

    ipGlobalProfile-StaticPref	OBJECT-TYPE
	SYNTAX	INTEGER
	ACCESS	read-write
	STATUS	mandatory
	DESCRIPTION	"The default preference given to static routes."
	::= { mibipGlobalProfileEntry 36 }

    ipGlobalProfile-RipPref	OBJECT-TYPE
	SYNTAX	INTEGER
	ACCESS	read-write
	STATUS	mandatory
	DESCRIPTION	"The default preference given to rip routes."
	::= { mibipGlobalProfileEntry 37 }

    ipGlobalProfile-RipQueueDepth	OBJECT-TYPE
	SYNTAX	INTEGER
	ACCESS	read-write
	STATUS	mandatory
	DESCRIPTION	"The maximum number of RIP packets waiting to be serviced. Additional packets will be dropped. When setting this value, you're trading memory resources versus losing RIP updates (only when the box is busy and gets behind on servicing the RIP packets). Zero indicates there is no limit. "
	::= { mibipGlobalProfileEntry 38 }

    ipGlobalProfile-OspfPref	OBJECT-TYPE
	SYNTAX	INTEGER
	ACCESS	read-write
	STATUS	mandatory
	DESCRIPTION	"The default preference given to ospf routes."
	::= { mibipGlobalProfileEntry 39 }

    ipGlobalProfile-OspfAsePref	OBJECT-TYPE
	SYNTAX	INTEGER
	ACCESS	read-write
	STATUS	mandatory
	DESCRIPTION	"The default preference given to ospf ASE routes."
	::= { mibipGlobalProfileEntry 40 }

    ipGlobalProfile-OspfGlobal-Enable	OBJECT-TYPE
	SYNTAX	INTEGER {
		    no (1),
		    yes (2)
		}
	ACCESS	read-write
	STATUS	mandatory
	DESCRIPTION	"Enable/Disable OSPF routing protocol."
	::= { mibipGlobalProfileEntry 41 }

    ipGlobalProfile-OspfGlobal-AsBoundaryRouter	OBJECT-TYPE
	SYNTAX	INTEGER {
		    no (1),
		    yes (2)
		}
	ACCESS	read-write
	STATUS	mandatory
	DESCRIPTION	"Is this router allowed to advertise ASE's."
	::= { mibipGlobalProfileEntry 42 }

    ipGlobalProfile-OspfGlobal-OspfMaxLsa	OBJECT-TYPE
	SYNTAX	INTEGER
	ACCESS	read-write
	STATUS	mandatory
	DESCRIPTION	"Max number of LSAs allowed in link state database."
	::= { mibipGlobalProfileEntry 43 }

    ipGlobalProfile-RipTag	OBJECT-TYPE
	SYNTAX	DisplayString
	ACCESS	read-write
	STATUS	mandatory
	DESCRIPTION	"The tag to associate with RIP routes."
	::= { mibipGlobalProfileEntry 44 }

    ipGlobalProfile-RipAseType	OBJECT-TYPE
	SYNTAX	INTEGER
	ACCESS	read-write
	STATUS	mandatory
	DESCRIPTION	"The ASE type to associate with RIP routes."
	::= { mibipGlobalProfileEntry 45 }

    ipGlobalProfile-IprouteCacheEnable	OBJECT-TYPE
	SYNTAX	INTEGER {
		    no (1),
		    yes (2)
		}
	ACCESS	read-write
	STATUS	mandatory
	DESCRIPTION	"IP cache Enabled or Disabled."
	::= { mibipGlobalProfileEntry 46 }

    ipGlobalProfile-IprouteCacheSize	OBJECT-TYPE
	SYNTAX	INTEGER
	ACCESS	read-write
	STATUS	mandatory
	DESCRIPTION	"Ip Routing cache size."
	::= { mibipGlobalProfileEntry 47 }

    ipGlobalProfile-IpportCacheEnable	OBJECT-TYPE
	SYNTAX	INTEGER {
		    no (1),
		    yes (2)
		}
	ACCESS	read-write
	STATUS	mandatory
	DESCRIPTION	"IP-Port route cache Enabled or Disabled."
	::= { mibipGlobalProfileEntry 48 }

    ipGlobalProfile-SuppressHostRoutes	OBJECT-TYPE
	SYNTAX	INTEGER {
		    no (1),
		    yes (2)
		}
	ACCESS	read-write
	STATUS	mandatory
	DESCRIPTION	"Suppress host route in the routing advertisement."
	::= { mibipGlobalProfileEntry 49 }

    ipGlobalProfile-SntpInfo-Enabled	OBJECT-TYPE
	SYNTAX	INTEGER {
		    sntpDisabled (1),
		    sntpEnabled (2),
		    sntpPassive (3)
		}
	ACCESS	read-write
	STATUS	mandatory
	DESCRIPTION	"Use SNTP to get time."
	::= { mibipGlobalProfileEntry 50 }

    ipGlobalProfile-SntpInfo-oGMTOffset	OBJECT-TYPE
	SYNTAX	INTEGER {
		    utc1130 (-41399),
		    utc1100 (-39599),
		    utc1030 (-37799),
		    utc1000 (-35999),
		    utc0930 (-34199),
		    utc0900 (-32399),
		    utc0830 (-30599),
		    utc0800 (-28799),
		    utc0730 (-26999),
		    utc0700 (-25199),
		    utc0630 (-23399),
		    utc0600 (-21599),
		    utc0530 (-19799),
		    utc0500 (-17999),
		    utc0430 (-16199),
		    utc0400 (-14399),
		    utc0330 (-12599),
		    utc0300 (-10799),
		    utc0230 (-8999),
		    utc0200 (-7199),
		    utc0130 (-5399),
		    utc0100 (-3599),
		    utc0030 (-1799),
		    utc-plus-0000 (1),
		    utc-plus-0030 (1801),
		    utc-plus-0100 (3601),
		    utc-plus-0130 (5401),
		    utc-plus-0200 (7201),
		    utc-plus-0230 (9001),
		    utc-plus-0300 (10801),
		    utc-plus-0330 (12601),
		    utc-plus-0400 (14401),
		    utc-plus-0430 (16201),
		    utc-plus-0500 (18001),
		    utc-plus-0530 (19801),
		    utc-plus-0600 (21601),
		    utc-plus-0630 (23401),
		    utc-plus-0700 (25201),
		    utc-plus-0730 (27001),
		    utc-plus-0800 (28801),
		    utc-plus-0830 (30601),
		    utc-plus-0900 (32401),
		    utc-plus-0930 (34201),
		    utc-plus-1000 (36001),
		    utc-plus-1030 (37801),
		    utc-plus-1100 (39601),
		    utc-plus-1130 (41401),
		    utc-plus-1200 (43201),
		    utc-plus-1230 (45001),
		    utc-plus-1300 (46801)
		}
	ACCESS	read-write
	STATUS	mandatory
	DESCRIPTION	"Offset from UTC for the timezone of this unit. Set to UTC-0000 if you desire time to be kept in UTC."
	::= { mibipGlobalProfileEntry 51 }

    ipGlobalProfile-SntpInfo-UpdateThreshold	OBJECT-TYPE
	SYNTAX	INTEGER
	ACCESS	read-write
	STATUS	mandatory
	DESCRIPTION	"SNTP update threshold, in seconds. This field is applied only if the 'enabled' field is set to 'passive'. "
	::= { mibipGlobalProfileEntry 52 }

    ipGlobalProfile-SntpInfo-UpdateInterval	OBJECT-TYPE
	SYNTAX	INTEGER
	ACCESS	read-write
	STATUS	mandatory
	DESCRIPTION	"SNTP update interval, in seconds, for up to 31 days."
	::= { mibipGlobalProfileEntry 87 }

    ipGlobalProfile-DnsListSize	OBJECT-TYPE
	SYNTAX	INTEGER
	ACCESS	read-write
	STATUS	mandatory
	DESCRIPTION	"DNS List Size."
	::= { mibipGlobalProfileEntry 53 }

    ipGlobalProfile-ClientPrimaryDnsServer	OBJECT-TYPE
	SYNTAX	IpAddress
	ACCESS	read-write
	STATUS	mandatory
	DESCRIPTION	"Default user IP address of the primary DNS server."
	::= { mibipGlobalProfileEntry 54 }

    ipGlobalProfile-ClientSecondaryDnsServer	OBJECT-TYPE
	SYNTAX	IpAddress
	ACCESS	read-write
	STATUS	mandatory
	DESCRIPTION	"Default user IP address of the secondary DNS server. This server is used when the primary is not available."
	::= { mibipGlobalProfileEntry 55 }

    ipGlobalProfile-AllowAsClientDnsInfo	OBJECT-TYPE
	SYNTAX	INTEGER {
		    false (1),
		    true (2)
		}
	ACCESS	read-write
	STATUS	mandatory
	DESCRIPTION	"This flag controls if main DNS info should be allowed as Client DNS info."
	::= { mibipGlobalProfileEntry 56 }

    ipGlobalProfile-DnsLocalTable-Enabled	OBJECT-TYPE
	SYNTAX	INTEGER {
		    no (1),
		    yes (2)
		}
	ACCESS	read-write
	STATUS	mandatory
	DESCRIPTION	"Use the DNS Fallback Table in case a regular DNS lookup fails"
	::= { mibipGlobalProfileEntry 57 }

    ipGlobalProfile-DnsLocalTable-AutoUpdate	OBJECT-TYPE
	SYNTAX	INTEGER {
		    no (1),
		    yes (2)
		}
	ACCESS	read-write
	STATUS	mandatory
	DESCRIPTION	"Update the DNS Fallback Table from a successful DNS lookup"
	::= { mibipGlobalProfileEntry 58 }

    ipGlobalProfile-MulticastForwarding	OBJECT-TYPE
	SYNTAX	INTEGER {
		    no (1),
		    yes (2)
		}
	ACCESS	read-write
	STATUS	mandatory
	DESCRIPTION	"Multicast forwarding Enabled."
	::= { mibipGlobalProfileEntry 59 }

    ipGlobalProfile-MboneProfile	OBJECT-TYPE
	SYNTAX	DisplayString
	ACCESS	read-write
	STATUS	mandatory
	DESCRIPTION	"MBONE Wan interface."
	::= { mibipGlobalProfileEntry 60 }

    ipGlobalProfile-MboneLanInterface-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibipGlobalProfileEntry 61 }

    ipGlobalProfile-MboneLanInterface-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibipGlobalProfileEntry 62 }

    ipGlobalProfile-MboneLanInterface-PhysicalAddress-ItemNumber	OBJECT-TYPE
	SYNTAX	INTEGER
	ACCESS	read-write
	STATUS	mandatory
	DESCRIPTION	"A number that specifies an addressable entity within the context of shelf and slot."
	::= { mibipGlobalProfileEntry 63 }

    ipGlobalProfile-MboneLanInterface-LogicalItem	OBJECT-TYPE
	SYNTAX	INTEGER
	ACCESS	read-write
	STATUS	mandatory
	DESCRIPTION	"A number that specifies an addressable logical entity within the context of a physical address."
	::= { mibipGlobalProfileEntry 64 }

    ipGlobalProfile-MulticastHbeatAddr	OBJECT-TYPE
	SYNTAX	IpAddress
	ACCESS	read-write
	STATUS	mandatory
	DESCRIPTION	"Multicast heart beat address."
	::= { mibipGlobalProfileEntry 65 }

    ipGlobalProfile-MulticastHbeatPort	OBJECT-TYPE
	SYNTAX	INTEGER
	ACCESS	read-write
	STATUS	mandatory
	DESCRIPTION	"Multicast heart beat port."
	::= { mibipGlobalProfileEntry 66 }

    ipGlobalProfile-MulticastHbeatSlotTime	OBJECT-TYPE
	SYNTAX	INTEGER
	ACCESS	read-write
	STATUS	mandatory
	DESCRIPTION	"Multicast heart beat time."
	::= { mibipGlobalProfileEntry 67 }

    ipGlobalProfile-MulticastHbeatNumberSlot	OBJECT-TYPE
	SYNTAX	INTEGER
	ACCESS	read-write
	STATUS	mandatory
	DESCRIPTION	"Multicast heart beat slot length."
	::= { mibipGlobalProfileEntry 68 }

    ipGlobalProfile-MulticastHbeatAlarmThreshold	OBJECT-TYPE
	SYNTAX	INTEGER
	ACCESS	read-write
	STATUS	mandatory
	DESCRIPTION	"Multicast heart beat alarm threshold."
	::= { mibipGlobalProfileEntry 69 }

    ipGlobalProfile-MulticastHbeatSrcAddr	OBJECT-TYPE
	SYNTAX	IpAddress
	ACCESS	read-write
	STATUS	mandatory
	DESCRIPTION	"Multicast heart beat source address."
	::= { mibipGlobalProfileEntry 70 }

    ipGlobalProfile-MulticastHbeatSrcAddrMask	OBJECT-TYPE
	SYNTAX	IpAddress
	ACCESS	read-write
	STATUS	mandatory
	DESCRIPTION	"Multicast heart beat source address mask."
	::= { mibipGlobalProfileEntry 71 }

    ipGlobalProfile-SecDomainName	OBJECT-TYPE
	SYNTAX	DisplayString
	ACCESS	read-write
	STATUS	mandatory
	DESCRIPTION	"The secondary DNS domain name assigned to this unit."
	::= { mibipGlobalProfileEntry 72 }

    ipGlobalProfile-MulticastMemberTimeout	OBJECT-TYPE
	SYNTAX	INTEGER
	ACCESS	read-write
	STATUS	mandatory
	DESCRIPTION	"Multicast membership time out in seconds"
	::= { mibipGlobalProfileEntry 73 }

    ipGlobalProfile-Finger	OBJECT-TYPE
	SYNTAX	INTEGER {
		    no (1),
		    yes (2)
		}
	ACCESS	read-write
	STATUS	mandatory
	DESCRIPTION	"Enable remote finger."
	::= { mibipGlobalProfileEntry 74 }

    ipGlobalProfile-IgnoreIcmpRedirects	OBJECT-TYPE
	SYNTAX	INTEGER {
		    no (1),
		    yes (2)
		}
	ACCESS	read-write
	STATUS	mandatory
	DESCRIPTION	"If TRUE, incoming ICMP redirects will be ignored, otherwise, they will be processed."
	::= { mibipGlobalProfileEntry 75 }

    ipGlobalProfile-IcmpReplyDirectedBcast	OBJECT-TYPE
	SYNTAX	INTEGER {
		    no (1),
		    yes (2)
		}
	ACCESS	read-write
	STATUS	mandatory
	DESCRIPTION	"reply directed bcast ICMP requests or not."
	::= { mibipGlobalProfileEntry 76 }

    ipGlobalProfile-SendIcmpDestUnreachable	OBJECT-TYPE
	SYNTAX	INTEGER {
		    no (1),
		    yes (2)
		}
	ACCESS	read-write
	STATUS	mandatory
	DESCRIPTION	"Send ICMP destination unreachable messages or not."
	::= { mibipGlobalProfileEntry 77 }

    ipGlobalProfile-GlobalVrouter	OBJECT-TYPE
	SYNTAX	DisplayString
	ACCESS	read-write
	STATUS	mandatory
	DESCRIPTION	"Specifies the global VRouter."
	::= { mibipGlobalProfileEntry 78 }

    ipGlobalProfile-RouterId	OBJECT-TYPE
	SYNTAX	IpAddress
	ACCESS	read-write
	STATUS	mandatory
	DESCRIPTION	"Specifies the router id."
	::= { mibipGlobalProfileEntry 79 }

    ipGlobalProfile-DefaultFilterCacheTime	OBJECT-TYPE
	SYNTAX	INTEGER
	ACCESS	read-write
	STATUS	mandatory
	DESCRIPTION	"The default cache time (in minutes) for RADIUS filter profiles. A value of 0 means that by default, filter profiles are not cached."
	::= { mibipGlobalProfileEntry 80 }

    ipGlobalProfile-DefaultPrtCacheTime	OBJECT-TYPE
	SYNTAX	INTEGER
	ACCESS	read-write
	STATUS	mandatory
	DESCRIPTION	"The default cache time (in minutes) for RADIUS private route table profiles. A value of 0 means that by default, private route table profiles will not be cached."
	::= { mibipGlobalProfileEntry 81 }

    ipGlobalProfile-TcpSynFloodProtect	OBJECT-TYPE
	SYNTAX	INTEGER {
		    no (1),
		    yes (2)
		}
	ACCESS	read-write
	STATUS	mandatory
	DESCRIPTION	"Flush old tcp sockets that are in a TCPS_SYNRCVD state, under a heavy TCP-SYN flooding."
	::= { mibipGlobalProfileEntry 82 }

    ipGlobalProfile-ThrottleNoPortMatchUdpTrafficOnSlot	OBJECT-TYPE
	SYNTAX	INTEGER {
		    no (1),
		    yes (2)
		}
	ACCESS	read-write
	STATUS	mandatory
	DESCRIPTION	"Throttle UDP traffic that does not match existing UDP ports on slot card."
	::= { mibipGlobalProfileEntry 83 }

    ipGlobalProfile-IpsecOptions-Enabled	OBJECT-TYPE
	SYNTAX	INTEGER {
		    no (1),
		    yes (2)
		}
	ACCESS	read-write
	STATUS	mandatory
	DESCRIPTION	"IPSec can be disabled on a profile by setting this field to no."
	::= { mibipGlobalProfileEntry 88 }

    ipGlobalProfile-IpsecOptions-SecurityPolicyDatabase	OBJECT-TYPE
	SYNTAX	DisplayString
	ACCESS	read-write
	STATUS	mandatory
	DESCRIPTION	"The name of the IPSec SPD profile to be used."
	::= { mibipGlobalProfileEntry 89 }

    ipGlobalProfile-DnsCacheEnable	OBJECT-TYPE
	SYNTAX	INTEGER {
		    no (1),
		    yes (2)
		}
	ACCESS	read-write
	STATUS	mandatory
	DESCRIPTION	"Cache DNS answers received from server."
	::= { mibipGlobalProfileEntry 90 }

    ipGlobalProfile-DnsAutoUpdateInterval	OBJECT-TYPE
	SYNTAX	INTEGER
	ACCESS	read-write
	STATUS	mandatory
	DESCRIPTION	"The time interval(in seconds) between successive updates of Permanent entries in DNS cache."
	::= { mibipGlobalProfileEntry 91 }

    ipGlobalProfile-MboneTimeout	OBJECT-TYPE
	SYNTAX	INTEGER
	ACCESS	read-write
	STATUS	mandatory
	DESCRIPTION	"Primary MBONE time out in seconds. A value of 0 disables timeout."
	::= { mibipGlobalProfileEntry 92 }

    ipGlobalProfile-Action-o	OBJECT-TYPE
	SYNTAX	INTEGER {
		    noAction (1),
		    createProfile (2),
		    deleteProfile (3)
		}
	ACCESS	read-write
	STATUS	mandatory
	DESCRIPTION	""
	::= { mibipGlobalProfileEntry 84 }


	-- The mibipGlobalProfile__mbone_backup table
	--
	-- This table contains parameters for the mibipGlobalProfile__mbone_backup profile
	--

    mibipGlobalProfile-MboneBackupTable	OBJECT-TYPE
	SYNTAX		SEQUENCE OF MibipGlobalProfile-MboneBackupEntry
	ACCESS		not-accessible
	STATUS		mandatory
	DESCRIPTION	"A list of mibipGlobalProfile__mbone_backup profile entries."
	::= { mibipGlobalProfile 9 }

    mibipGlobalProfile-MboneBackupEntry	OBJECT-TYPE
	SYNTAX		MibipGlobalProfile-MboneBackupEntry
	ACCESS		not-accessible
	STATUS		mandatory
	DESCRIPTION	"A mibipGlobalProfile__mbone_backup entry containing objects that
			 maps to the parameters of mibipGlobalProfile__mbone_backup profile."
	INDEX		{ ipGlobalProfile-MboneBackup-Index-o, ipGlobalProfile-MboneBackup-Index1-o }
	::= { mibipGlobalProfile-MboneBackupTable 1 }

    MibipGlobalProfile-MboneBackupEntry ::=
	SEQUENCE {
	    ipGlobalProfile-MboneBackup-Index-o
		INTEGER,
	    ipGlobalProfile-MboneBackup-Index1-o
		INTEGER,
	    ipGlobalProfile-MboneBackup-Enabled
		INTEGER,
	    ipGlobalProfile-MboneBackup-MboneProfile
		DisplayString,
	    ipGlobalProfile-MboneBackup-MboneLanInterface-PhysicalAddress-Shelf
		INTEGER,
	    ipGlobalProfile-MboneBackup-MboneLanInterface-PhysicalAddress-Slot
		INTEGER,
	    ipGlobalProfile-MboneBackup-MboneLanInterface-PhysicalAddress-ItemNumber
		INTEGER,
	    ipGlobalProfile-MboneBackup-MboneLanInterface-LogicalItem
		INTEGER,
	    ipGlobalProfile-MboneBackup-MboneTimeout
		INTEGER
	}

    ipGlobalProfile-MboneBackup-Index-o	OBJECT-TYPE
	SYNTAX	INTEGER
	ACCESS	read-only
	STATUS	mandatory
	DESCRIPTION	""
	::= { mibipGlobalProfile-MboneBackupEntry 1 }

    ipGlobalProfile-MboneBackup-Index1-o	OBJECT-TYPE
	SYNTAX	INTEGER
	ACCESS	read-only
	STATUS	mandatory
	DESCRIPTION	""
	::= { mibipGlobalProfile-MboneBackupEntry 2 }

    ipGlobalProfile-MboneBackup-Enabled	OBJECT-TYPE
	SYNTAX	INTEGER {
		    no (1),
		    yes (2)
		}
	ACCESS	read-write
	STATUS	mandatory
	DESCRIPTION	"Specifies if this MBONE profile is enabled."
	::= { mibipGlobalProfile-MboneBackupEntry 3 }

    ipGlobalProfile-MboneBackup-MboneProfile	OBJECT-TYPE
	SYNTAX	DisplayString
	ACCESS	read-write
	STATUS	mandatory
	DESCRIPTION	"MBONE Wan interface."
	::= { mibipGlobalProfile-MboneBackupEntry 4 }

    ipGlobalProfile-MboneBackup-MboneLanInterface-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibipGlobalProfile-MboneBackupEntry 5 }

    ipGlobalProfile-MboneBackup-MboneLanInterface-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibipGlobalProfile-MboneBackupEntry 6 }

    ipGlobalProfile-MboneBackup-MboneLanInterface-PhysicalAddress-ItemNumber	OBJECT-TYPE
	SYNTAX	INTEGER
	ACCESS	read-write
	STATUS	mandatory
	DESCRIPTION	"A number that specifies an addressable entity within the context of shelf and slot."
	::= { mibipGlobalProfile-MboneBackupEntry 7 }

    ipGlobalProfile-MboneBackup-MboneLanInterface-LogicalItem	OBJECT-TYPE
	SYNTAX	INTEGER
	ACCESS	read-write
	STATUS	mandatory
	DESCRIPTION	"A number that specifies an addressable logical entity within the context of a physical address."
	::= { mibipGlobalProfile-MboneBackupEntry 8 }

    ipGlobalProfile-MboneBackup-MboneTimeout	OBJECT-TYPE
	SYNTAX	INTEGER
	ACCESS	read-write
	STATUS	mandatory
	DESCRIPTION	"MBONE time out in seconds. A value of 0 disables timeout."
	::= { mibipGlobalProfile-MboneBackupEntry 9 }


	-- The mibipGlobalProfile__dns_local_table__table_config table
	--
	-- This table contains parameters for the mibipGlobalProfile__dns_local_table__table_config profile
	--

    mibipGlobalProfile-DnsLocalTable-TableConfigTable	OBJECT-TYPE
	SYNTAX		SEQUENCE OF MibipGlobalProfile-DnsLocalTable-TableConfigEntry
	ACCESS		not-accessible
	STATUS		mandatory
	DESCRIPTION	"A list of mibipGlobalProfile__dns_local_table__table_config profile entries."
	::= { mibipGlobalProfile 2 }

    mibipGlobalProfile-DnsLocalTable-TableConfigEntry	OBJECT-TYPE
	SYNTAX		MibipGlobalProfile-DnsLocalTable-TableConfigEntry
	ACCESS		not-accessible
	STATUS		mandatory
	DESCRIPTION	"A mibipGlobalProfile__dns_local_table__table_config entry containing objects that
			 maps to the parameters of mibipGlobalProfile__dns_local_table__table_config profile."
	INDEX		{ ipGlobalProfile-DnsLocalTable-TableConfig-Index-o, ipGlobalProfile-DnsLocalTable-TableConfig-Index1-o }
	::= { mibipGlobalProfile-DnsLocalTable-TableConfigTable 1 }

    MibipGlobalProfile-DnsLocalTable-TableConfigEntry ::=
	SEQUENCE {
	    ipGlobalProfile-DnsLocalTable-TableConfig-Index-o
		INTEGER,
	    ipGlobalProfile-DnsLocalTable-TableConfig-Index1-o
		INTEGER,
	    ipGlobalProfile-DnsLocalTable-TableConfig-HostName
		DisplayString,
	    ipGlobalProfile-DnsLocalTable-TableConfig-IpAddress
		IpAddress
	}

    ipGlobalProfile-DnsLocalTable-TableConfig-Index-o	OBJECT-TYPE
	SYNTAX	INTEGER
	ACCESS	read-only
	STATUS	mandatory
	DESCRIPTION	""
	::= { mibipGlobalProfile-DnsLocalTable-TableConfigEntry 1 }

    ipGlobalProfile-DnsLocalTable-TableConfig-Index1-o	OBJECT-TYPE
	SYNTAX	INTEGER
	ACCESS	read-only
	STATUS	mandatory
	DESCRIPTION	""
	::= { mibipGlobalProfile-DnsLocalTable-TableConfigEntry 2 }

    ipGlobalProfile-DnsLocalTable-TableConfig-HostName	OBJECT-TYPE
	SYNTAX	DisplayString
	ACCESS	read-write
	STATUS	mandatory
	DESCRIPTION	"Host name."
	::= { mibipGlobalProfile-DnsLocalTable-TableConfigEntry 3 }

    ipGlobalProfile-DnsLocalTable-TableConfig-IpAddress	OBJECT-TYPE
	SYNTAX	IpAddress
	ACCESS	read-write
	STATUS	mandatory
	DESCRIPTION	"IP address of host."
	::= { mibipGlobalProfile-DnsLocalTable-TableConfigEntry 4 }


	-- The mibipGlobalProfile__sntp_info__host table
	--
	-- This table contains parameters for the mibipGlobalProfile__sntp_info__host profile
	--

    mibipGlobalProfile-SntpInfo-HostTable	OBJECT-TYPE
	SYNTAX		SEQUENCE OF MibipGlobalProfile-SntpInfo-HostEntry
	ACCESS		not-accessible
	STATUS		mandatory
	DESCRIPTION	"A list of mibipGlobalProfile__sntp_info__host profile entries."
	::= { mibipGlobalProfile 3 }

    mibipGlobalProfile-SntpInfo-HostEntry	OBJECT-TYPE
	SYNTAX		MibipGlobalProfile-SntpInfo-HostEntry
	ACCESS		not-accessible
	STATUS		mandatory
	DESCRIPTION	"A mibipGlobalProfile__sntp_info__host entry containing objects that
			 maps to the parameters of mibipGlobalProfile__sntp_info__host profile."
	INDEX		{ ipGlobalProfile-SntpInfo-Host-Index-o, ipGlobalProfile-SntpInfo-Host-Index1-o }
	::= { mibipGlobalProfile-SntpInfo-HostTable 1 }

    MibipGlobalProfile-SntpInfo-HostEntry ::=
	SEQUENCE {
	    ipGlobalProfile-SntpInfo-Host-Index-o
		INTEGER,
	    ipGlobalProfile-SntpInfo-Host-Index1-o
		INTEGER,
	    ipGlobalProfile-SntpInfo-Host
		IpAddress
	}

    ipGlobalProfile-SntpInfo-Host-Index-o	OBJECT-TYPE
	SYNTAX	INTEGER
	ACCESS	read-only
	STATUS	mandatory
	DESCRIPTION	""
	::= { mibipGlobalProfile-SntpInfo-HostEntry 1 }

    ipGlobalProfile-SntpInfo-Host-Index1-o	OBJECT-TYPE
	SYNTAX	INTEGER
	ACCESS	read-only
	STATUS	mandatory
	DESCRIPTION	""
	::= { mibipGlobalProfile-SntpInfo-HostEntry 2 }

    ipGlobalProfile-SntpInfo-Host	OBJECT-TYPE
	SYNTAX	IpAddress
	ACCESS	read-write
	STATUS	mandatory
	DESCRIPTION	"The IP Address of the SNTP host."
	::= { mibipGlobalProfile-SntpInfo-HostEntry 3 }


	-- The mibipGlobalProfile__bootp_relay__bootp_servers table
	--
	-- This table contains parameters for the mibipGlobalProfile__bootp_relay__bootp_servers profile
	--

    mibipGlobalProfile-BootpRelay-BootpServersTable	OBJECT-TYPE
	SYNTAX		SEQUENCE OF MibipGlobalProfile-BootpRelay-BootpServersEntry
	ACCESS		not-accessible
	STATUS		mandatory
	DESCRIPTION	"A list of mibipGlobalProfile__bootp_relay__bootp_servers profile entries."
	::= { mibipGlobalProfile 4 }

    mibipGlobalProfile-BootpRelay-BootpServersEntry	OBJECT-TYPE
	SYNTAX		MibipGlobalProfile-BootpRelay-BootpServersEntry
	ACCESS		not-accessible
	STATUS		mandatory
	DESCRIPTION	"A mibipGlobalProfile__bootp_relay__bootp_servers entry containing objects that
			 maps to the parameters of mibipGlobalProfile__bootp_relay__bootp_servers profile."
	INDEX		{ ipGlobalProfile-BootpRelay-BootpServers-Index-o, ipGlobalProfile-BootpRelay-BootpServers-Index1-o }
	::= { mibipGlobalProfile-BootpRelay-BootpServersTable 1 }

    MibipGlobalProfile-BootpRelay-BootpServersEntry ::=
	SEQUENCE {
	    ipGlobalProfile-BootpRelay-BootpServers-Index-o
		INTEGER,
	    ipGlobalProfile-BootpRelay-BootpServers-Index1-o
		INTEGER,
	    ipGlobalProfile-BootpRelay-BootpServers
		IpAddress
	}

    ipGlobalProfile-BootpRelay-BootpServers-Index-o	OBJECT-TYPE
	SYNTAX	INTEGER
	ACCESS	read-only
	STATUS	mandatory
	DESCRIPTION	""
	::= { mibipGlobalProfile-BootpRelay-BootpServersEntry 1 }

    ipGlobalProfile-BootpRelay-BootpServers-Index1-o	OBJECT-TYPE
	SYNTAX	INTEGER
	ACCESS	read-only
	STATUS	mandatory
	DESCRIPTION	""
	::= { mibipGlobalProfile-BootpRelay-BootpServersEntry 2 }

    ipGlobalProfile-BootpRelay-BootpServers	OBJECT-TYPE
	SYNTAX	IpAddress
	ACCESS	read-write
	STATUS	mandatory
	DESCRIPTION	"List of server addresses where BOOTP packets will be forwarded to."
	::= { mibipGlobalProfile-BootpRelay-BootpServersEntry 3 }


	-- The mibipGlobalProfile__pool_name table
	--
	-- This table contains parameters for the mibipGlobalProfile__pool_name profile
	--

    mibipGlobalProfile-PoolNameTable	OBJECT-TYPE
	SYNTAX		SEQUENCE OF MibipGlobalProfile-PoolNameEntry
	ACCESS		not-accessible
	STATUS		mandatory
	DESCRIPTION	"A list of mibipGlobalProfile__pool_name profile entries."
	::= { mibipGlobalProfile 5 }

    mibipGlobalProfile-PoolNameEntry	OBJECT-TYPE
	SYNTAX		MibipGlobalProfile-PoolNameEntry
	ACCESS		not-accessible
	STATUS		mandatory
	DESCRIPTION	"A mibipGlobalProfile__pool_name entry containing objects that
			 maps to the parameters of mibipGlobalProfile__pool_name profile."
	INDEX		{ ipGlobalProfile-PoolName-Index-o, ipGlobalProfile-PoolName-Index1-o }
	::= { mibipGlobalProfile-PoolNameTable 1 }

    MibipGlobalProfile-PoolNameEntry ::=
	SEQUENCE {
	    ipGlobalProfile-PoolName-Index-o
		INTEGER,
	    ipGlobalProfile-PoolName-Index1-o
		INTEGER,
	    ipGlobalProfile-PoolName
		DisplayString
	}

    ipGlobalProfile-PoolName-Index-o	OBJECT-TYPE
	SYNTAX	INTEGER
	ACCESS	read-only
	STATUS	mandatory
	DESCRIPTION	""
	::= { mibipGlobalProfile-PoolNameEntry 1 }

    ipGlobalProfile-PoolName-Index1-o	OBJECT-TYPE
	SYNTAX	INTEGER
	ACCESS	read-only
	STATUS	mandatory
	DESCRIPTION	""
	::= { mibipGlobalProfile-PoolNameEntry 2 }

    ipGlobalProfile-PoolName	OBJECT-TYPE
	SYNTAX	DisplayString
	ACCESS	read-write
	STATUS	mandatory
	DESCRIPTION	"The name of this pool"
	::= { mibipGlobalProfile-PoolNameEntry 3 }


	-- The mibipGlobalProfile__assign_count table
	--
	-- This table contains parameters for the mibipGlobalProfile__assign_count profile
	--

    mibipGlobalProfile-AssignCountTable	OBJECT-TYPE
	SYNTAX		SEQUENCE OF MibipGlobalProfile-AssignCountEntry
	ACCESS		not-accessible
	STATUS		mandatory
	DESCRIPTION	"A list of mibipGlobalProfile__assign_count profile entries."
	::= { mibipGlobalProfile 6 }

    mibipGlobalProfile-AssignCountEntry	OBJECT-TYPE
	SYNTAX		MibipGlobalProfile-AssignCountEntry
	ACCESS		not-accessible
	STATUS		mandatory
	DESCRIPTION	"A mibipGlobalProfile__assign_count entry containing objects that
			 maps to the parameters of mibipGlobalProfile__assign_count profile."
	INDEX		{ ipGlobalProfile-AssignCount-Index-o, ipGlobalProfile-AssignCount-Index1-o }
	::= { mibipGlobalProfile-AssignCountTable 1 }

    MibipGlobalProfile-AssignCountEntry ::=
	SEQUENCE {
	    ipGlobalProfile-AssignCount-Index-o
		INTEGER,
	    ipGlobalProfile-AssignCount-Index1-o
		INTEGER,
	    ipGlobalProfile-AssignCount
		INTEGER
	}

    ipGlobalProfile-AssignCount-Index-o	OBJECT-TYPE
	SYNTAX	INTEGER
	ACCESS	read-only
	STATUS	mandatory
	DESCRIPTION	""
	::= { mibipGlobalProfile-AssignCountEntry 1 }

    ipGlobalProfile-AssignCount-Index1-o	OBJECT-TYPE
	SYNTAX	INTEGER
	ACCESS	read-only
	STATUS	mandatory
	DESCRIPTION	""
	::= { mibipGlobalProfile-AssignCountEntry 2 }

    ipGlobalProfile-AssignCount	OBJECT-TYPE
	SYNTAX	INTEGER
	ACCESS	read-write
	STATUS	mandatory
	DESCRIPTION	"The number of host addresses in the above. pool. The addresses are contiguous."
	::= { mibipGlobalProfile-AssignCountEntry 3 }


	-- The mibipGlobalProfile__pool_base_address table
	--
	-- This table contains parameters for the mibipGlobalProfile__pool_base_address profile
	--

    mibipGlobalProfile-PoolBaseAddressTable	OBJECT-TYPE
	SYNTAX		SEQUENCE OF MibipGlobalProfile-PoolBaseAddressEntry
	ACCESS		not-accessible
	STATUS		mandatory
	DESCRIPTION	"A list of mibipGlobalProfile__pool_base_address profile entries."
	::= { mibipGlobalProfile 7 }

    mibipGlobalProfile-PoolBaseAddressEntry	OBJECT-TYPE
	SYNTAX		MibipGlobalProfile-PoolBaseAddressEntry
	ACCESS		not-accessible
	STATUS		mandatory
	DESCRIPTION	"A mibipGlobalProfile__pool_base_address entry containing objects that
			 maps to the parameters of mibipGlobalProfile__pool_base_address profile."
	INDEX		{ ipGlobalProfile-PoolBaseAddress-Index-o, ipGlobalProfile-PoolBaseAddress-Index1-o }
	::= { mibipGlobalProfile-PoolBaseAddressTable 1 }

    MibipGlobalProfile-PoolBaseAddressEntry ::=
	SEQUENCE {
	    ipGlobalProfile-PoolBaseAddress-Index-o
		INTEGER,
	    ipGlobalProfile-PoolBaseAddress-Index1-o
		INTEGER,
	    ipGlobalProfile-PoolBaseAddress
		IpAddress
	}

    ipGlobalProfile-PoolBaseAddress-Index-o	OBJECT-TYPE
	SYNTAX	INTEGER
	ACCESS	read-only
	STATUS	mandatory
	DESCRIPTION	""
	::= { mibipGlobalProfile-PoolBaseAddressEntry 1 }

    ipGlobalProfile-PoolBaseAddress-Index1-o	OBJECT-TYPE
	SYNTAX	INTEGER
	ACCESS	read-only
	STATUS	mandatory
	DESCRIPTION	""
	::= { mibipGlobalProfile-PoolBaseAddressEntry 2 }

    ipGlobalProfile-PoolBaseAddress	OBJECT-TYPE
	SYNTAX	IpAddress
	ACCESS	read-write
	STATUS	mandatory
	DESCRIPTION	"The base address of a pool of addresses we can use to assign to clients."
	::= { mibipGlobalProfile-PoolBaseAddressEntry 3 }


	-- The mibipGlobalProfile__dhcp_server__static_address table
	--
	-- This table contains parameters for the mibipGlobalProfile__dhcp_server__static_address profile
	--

    mibipGlobalProfile-DhcpServer-StaticAddressTable	OBJECT-TYPE
	SYNTAX		SEQUENCE OF MibipGlobalProfile-DhcpServer-StaticAddressEntry
	ACCESS		not-accessible
	STATUS		mandatory
	DESCRIPTION	"A list of mibipGlobalProfile__dhcp_server__static_address profile entries."
	::= { mibipGlobalProfile 8 }

    mibipGlobalProfile-DhcpServer-StaticAddressEntry	OBJECT-TYPE
	SYNTAX		MibipGlobalProfile-DhcpServer-StaticAddressEntry
	ACCESS		not-accessible
	STATUS		mandatory
	DESCRIPTION	"A mibipGlobalProfile__dhcp_server__static_address entry containing objects that
			 maps to the parameters of mibipGlobalProfile__dhcp_server__static_address profile."
	INDEX		{ ipGlobalProfile-DhcpServer-StaticAddress-Index-o, ipGlobalProfile-DhcpServer-StaticAddress-Index1-o }
	::= { mibipGlobalProfile-DhcpServer-StaticAddressTable 1 }

    MibipGlobalProfile-DhcpServer-StaticAddressEntry ::=
	SEQUENCE {
	    ipGlobalProfile-DhcpServer-StaticAddress-Index-o
		INTEGER,
	    ipGlobalProfile-DhcpServer-StaticAddress-Index1-o
		INTEGER,
	    ipGlobalProfile-DhcpServer-StaticAddress-IpAddress
		IpAddress,
	    ipGlobalProfile-DhcpServer-StaticAddress-EthernetAddress
		DisplayString
	}

    ipGlobalProfile-DhcpServer-StaticAddress-Index-o	OBJECT-TYPE
	SYNTAX	INTEGER
	ACCESS	read-only
	STATUS	mandatory
	DESCRIPTION	""
	::= { mibipGlobalProfile-DhcpServer-StaticAddressEntry 1 }

    ipGlobalProfile-DhcpServer-StaticAddress-Index1-o	OBJECT-TYPE
	SYNTAX	INTEGER
	ACCESS	read-only
	STATUS	mandatory
	DESCRIPTION	""
	::= { mibipGlobalProfile-DhcpServer-StaticAddressEntry 2 }

    ipGlobalProfile-DhcpServer-StaticAddress-IpAddress	OBJECT-TYPE
	SYNTAX	IpAddress
	ACCESS	read-write
	STATUS	mandatory
	DESCRIPTION	"Static address."
	::= { mibipGlobalProfile-DhcpServer-StaticAddressEntry 3 }

    ipGlobalProfile-DhcpServer-StaticAddress-EthernetAddress	OBJECT-TYPE
	SYNTAX	DisplayString
	ACCESS	read-write
	STATUS	mandatory
	DESCRIPTION	"Ethernet address of the host."
	::= { mibipGlobalProfile-DhcpServer-StaticAddressEntry 4 }

END
