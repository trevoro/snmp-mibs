INTEL-CSU-HW-MIB DEFINITIONS ::= BEGIN

-- Copyright (C) 1998 Intel Corporation. All rights reserved.
--
-- Private CSU Hardware Statistics MIB, 10-Dec-1998
--
-- This MIB provides objects for the CSU hardware data.
-- It provides significant value-add to the counters
-- identified in the standard DS1 MIB RFC1406, and is
-- independant of RFC1406.
--
--
-- Change History:
-- 10-Dec-98 (DRG) Initial revision
-- 10-Mar-99 (DRG) Changed structure to as shown below
-- 07-May-99 (DRG) Removed ChannelMonitor Table.
-- 07-May-99 (DRG) Extended InfoTable with DS0Monitor as 2 strings.
-- 07-May-99 (DRG) Extended ConfigTable with Fractional table as string

--
--     + csuInfoTable  (1 index, Interface#)
--          + obj1
--          + obj2
--
--     +  csuConfigTable (1 index, Interface#)
--          + obj1
--          + obj2
--
--     +  csuFractionalTable (2 indeces, Interface#, channel#) 
--          + obj1
--          + obj2
--          !!!!(redundant 07May99, retained for bwd compatibility )!!!

IMPORTS
    OBJECT-TYPE                 FROM RFC-1212
    Counter,enterprises,private FROM RFC1155-SMI
    DisplayString               FROM RFC1213-MIB
    mib2ext                     FROM INTEL-GEN-MIB;

    csudsu          OBJECT IDENTIFIER ::= { mib2ext 36 }
    csu             OBJECT IDENTIFIER ::= { csudsu 1 }

--------------  CSU Info Table ---------------------

     csuInfoTable OBJECT-TYPE
         SYNTAX  SEQUENCE OF CSUInfoEntry
         ACCESS  not-accessible
         STATUS  mandatory
         DESCRIPTION
            "The CSU Information table."
        ::= { csu 1 }

     csuInfoEntry OBJECT-TYPE
         SYNTAX  CSUInfoEntry
         ACCESS  not-accessible
         STATUS  mandatory
         DESCRIPTION
            "An entry in the CSU Information table."
        INDEX   { csuInfoLineIndex }
        ::= { csuInfoTable 1 }

        CSUInfoEntry ::=
            SEQUENCE {
                csuInfoLineIndex 
                     INTEGER,
                csuAlarm 
                     INTEGER,
                csuReceiveLevel 
                     INTEGER,
                csuLoopbackState 
                     INTEGER,
                csuLossofsynchronization 
                     Counter,
                csuChangeofFrameAlignment 
                     Counter,
                csuEightZeroDetect 
                     Counter,
                csuSixteenZeroDetect 
                     Counter,
                csuSeverelyErroredFramingEvent 
                     Counter,
                csuB8ZSCodeWordDetect 
                     Counter,
                csuFrameBitError 
                     Counter,
                csuReceivePulseDensityViolation 
                     Counter,
                csuTransmitPulseDensityViolation 
                     Counter,
                csuJitterAttenuatorLimitTrip 
                     Counter,
                csuLossofReceiveClock 
                     Counter,
                csuFramerReceiveCarrierLoss 
                     Counter,
                csuLineCodeViolationCount 
                     Counter,
                csuPathCodeViolationCount 
                     Counter,
                csuMultiframesOutofSyncCount 
                     Counter,
                csuCRC6errors 
                     Counter,
                csuErrorRate 
                    DisplayString,
                csuLinkState
                    INTEGER,
                csuErrorsThisSecond
                    Counter,
                csuPercentEFS
                    INTEGER,
                csuTXChannelPayload 
                    DisplayString,
                csuRXChannelPayload 
                    DisplayString,
                csuDetectedChannelMap
                    DisplayString,
                csuYellowAlarmCount
                    Counter,
                csuAISDefects
                    Counter
        }


        csuInfoLineIndex OBJECT-TYPE
            SYNTAX  INTEGER (1..2147483647)
            ACCESS  read-only
            STATUS  mandatory
            DESCRIPTION
               "The index value which uniquely identifies the CSU 
               interface  to which this entry is applicable."
               ::= { csuInfoEntry 1 }

        csuAlarm OBJECT-TYPE
            SYNTAX INTEGER {
                        csuAlarmNone(1),
                        csuAlarmRED(2),
                        csuAlarmBLUE(4),
                        csuAlarmYELLOW(8),
                        csuAlarmOUTOFFRAMING(16)
                }
            ACCESS read-only
            STATUS mandatory
            DESCRIPTION 
            "The currently active alarm condition, if any. 
            
            Red alarm  corresponds to a Loss Of Signal (LOS), and most
            commonly occurs when the cable is unplugged or broken.
            
            Blue alarm indicates that the local equipment is properly
            connected but that the carrier CSU is sending a unique data
            pattern, indicating that it has lost its remote data source.
            
            Yellow alarm indicates that the local equipment is receiving
            a valid signal, but this signal indicates that the carrier
            CSU cannot frmae to a signal from us. This is normal for up
            to 30 seconds after connection, but if it persists indicates
            that there is a break in the T1 connection in the direction
            toward the carrier.

            Out Of Framing is any other condition severe enough that the
            local CSU cannot lock onto the signal from the carrier CSU.
            This may be because of mismatched configurations. Likely
            candidates are Line Coding and Framing Format. If these are
            correctly set at both ends, the line should be tested by the
            T1 service provider."
            ::= { csuInfoEntry 2 }

        csuReceiveLevel OBJECT-TYPE
            SYNTAX INTEGER {csuReceiveLevelPlus2ToMinus7Point5(1),
						    csuReceiveLevelMinus7Point5ToMinus15(2),
						    csuReceiveLevelMinus15ToMinus22point5(3),
						    csuReceiveLevelLessThanMinus22Point5(4)
			                }
            ACCESS read-only
            STATUS mandatory
            DESCRIPTION
            "The currently detected signal strength.
            1:+2 to -7.5db
            2:-7.5 to -15db
            3:-15 to -22.5db
            4: < -22.5 db"
            ::= { csuInfoEntry 3 }

        csuLoopbackState OBJECT-TYPE
            SYNTAX INTEGER { 
                            csuLoopbackNone(1),
                            csuLoopbackLocalPayload(2),
                            csuLoopbackLocalLine(3),
                            csuLoopbackLocalChannel(4),
                            csuLoopbackRemotePayload(5),
                            csuLoopbackRemoteLine(6),
                            csuLoopbackRemoteChannel(7)
                            }
            ACCESS read-only
            STATUS mandatory
            DESCRIPTION 
            "This variable identifies the current active loopback, if
            any."
            ::= { csuInfoEntry 4 }

        csuLossofsynchronization OBJECT-TYPE
            SYNTAX Counter
            ACCESS read-only
            STATUS mandatory
            DESCRIPTION 
            "A count of the number of seconds during which a Loss of 
            synchronization has been triggered"
            ::= { csuInfoEntry 5 }

        csuChangeofFrameAlignment OBJECT-TYPE
            SYNTAX Counter
            ACCESS read-only
            STATUS mandatory
            DESCRIPTION 
            "A count of the number of times that there has been a change
            of Frame Alignment"
            ::= { csuInfoEntry 6 }

        csuEightZeroDetect OBJECT-TYPE
            SYNTAX Counter
            ACCESS read-only
            STATUS mandatory
            DESCRIPTION 
            "A count of the number of times that a string of 8 
            contiguous zeros has been detected"
            ::= { csuInfoEntry 7 }

        csuSixteenZeroDetect OBJECT-TYPE
            SYNTAX Counter
            ACCESS read-only
            STATUS mandatory
            DESCRIPTION 
            "A count of the number of times that a string of 16
            contiguous zeros has been detected"
            ::= { csuInfoEntry 8 }

        csuSeverelyErroredFramingEvent OBJECT-TYPE
            SYNTAX Counter
            ACCESS read-only
            STATUS mandatory
            DESCRIPTION 
            "A count of number of severely Severely Errored Framing
            Events"
            ::= { csuInfoEntry 9 }

        csuB8ZSCodeWordDetect OBJECT-TYPE
            SYNTAX Counter
            ACCESS read-only
            STATUS mandatory
            DESCRIPTION 
            "A count of the number of times that a B8ZS Code Word has
            been detected"
            ::= { csuInfoEntry 10}

        csuFrameBitError OBJECT-TYPE
            SYNTAX Counter
            ACCESS read-only
            STATUS mandatory
            DESCRIPTION 
            "A count of Frame Bit Errors"
            ::= { csuInfoEntry 11 }

        csuReceivePulseDensityViolation OBJECT-TYPE
            SYNTAX Counter
            ACCESS read-only
            STATUS mandatory
            DESCRIPTION 
            "A count of Receive Pulse Density Violations"
            ::= { csuInfoEntry 12 }

        csuTransmitPulseDensityViolation OBJECT-TYPE
            SYNTAX Counter
            ACCESS read-only
            STATUS mandatory
            DESCRIPTION 
            "A count of Transmit Pulse Density Violations"
            ::= { csuInfoEntry 13 }

        csuJitterAttenuatorLimitTrip OBJECT-TYPE
            SYNTAX Counter
            ACCESS read-only
            STATUS mandatory
            DESCRIPTION 
            "A count of Jitter Attenuator Limit Trips"
            ::= { csuInfoEntry 14 }

        csuLossofReceiveClock OBJECT-TYPE
            SYNTAX Counter
            ACCESS read-only
            STATUS mandatory
            DESCRIPTION 
            "Loss of Receive Clock"
            ::= { csuInfoEntry 15 }

        csuFramerReceiveCarrierLoss OBJECT-TYPE
            SYNTAX Counter
            ACCESS read-only
            STATUS mandatory
            DESCRIPTION 
            "A count of the number of times that a Framer Receive
            Carrier Loss has ocurred. Because a Framer Receive Carrier
            Loss is an LOS indicator, this also counts the number of
            times that the Red alam state has been entered."
            ::= { csuInfoEntry 16 }

        csuLineCodeViolationCount OBJECT-TYPE
            SYNTAX Counter
            ACCESS read-only
            STATUS mandatory
            DESCRIPTION "A count of Line Code Violations"
            ::= { csuInfoEntry 17 }

        csuPathCodeViolationCount OBJECT-TYPE
            SYNTAX Counter
            ACCESS read-only
            STATUS mandatory
            DESCRIPTION "A count of Path Code Violations"
            ::= { csuInfoEntry 18 }

        csuMultiframesOutofSyncCount OBJECT-TYPE
            SYNTAX Counter
            ACCESS read-only
            STATUS mandatory
            DESCRIPTION 
            "A count of the number of Multiframes which have passed
            without being able to sucessfully reframe."
            ::= { csuInfoEntry 19 }

        csuCRC6errors OBJECT-TYPE
            SYNTAX Counter
            ACCESS read-only
            STATUS mandatory
            DESCRIPTION "A count of CRC6 errors"
            ::= { csuInfoEntry 20 }

        csuErrorRate OBJECT-TYPE
            SYNTAX DisplayString  (SIZE (0..255))
            ACCESS read-only
            STATUS mandatory
            DESCRIPTION 
            "The CSU error rate. This variable describes a rate in
            scientific notation."
            ::= { csuInfoEntry 21}

        csuLinkState OBJECT-TYPE
            SYNTAX INTEGER {
                        csuLinkStateUp(1),
                        csuLinkStateDown(2)
            }
            ACCESS read-only
            STATUS mandatory
            DESCRIPTION 
            "The state of the protocol stack using the CSU"
            ::= { csuInfoEntry 22 }

        csuErrorsThisSecond OBJECT-TYPE
            SYNTAX Counter
            ACCESS read-only
            STATUS mandatory
            DESCRIPTION 
            "The number of physical bit errors detected in the last
            second"
            ::= { csuInfoEntry 23 }


        csuPercentEFS OBJECT-TYPE
            SYNTAX INTEGER
            ACCESS read-only
            STATUS mandatory
            DESCRIPTION 
            "The number of error free seconds as a percentage of the
            total available seconds"
            ::= { csuInfoEntry 24 }

        csuTXChannelPayload OBJECT-TYPE
            SYNTAX DisplayString  (SIZE (0..255))
            ACCESS read-only
            STATUS mandatory
            DESCRIPTION 
            "Transmit channel payloads, channels 1 through 24"
            ::= { csuInfoEntry 25}


        csuRXChannelPayload OBJECT-TYPE
            SYNTAX DisplayString  (SIZE (0..255))
            ACCESS read-only
            STATUS mandatory
            DESCRIPTION 
            "Receive channel payloads, channels 1 through 24"
            ::= { csuInfoEntry 26}


        csuDetectedChannelMap OBJECT-TYPE
            SYNTAX DisplayString  (SIZE (0..255))
            ACCESS read-only
            STATUS mandatory
            DESCRIPTION 
            "The detected channel map. Each channel maps into one BYTE,
            starting with channel one in the first byte. A value of 0
            indicates that channel activity has been detected ON, 1
            indicates that the channel is detected OFF, and 2 that the
            channel state has not yet been determined."
            ::= { csuInfoEntry 27}

        csuYellowAlarmCount OBJECT-TYPE
            SYNTAX Counter
            ACCESS read-only
            STATUS mandatory
            DESCRIPTION 
            "A count of the number of Yellow alarms"
            ::= { csuInfoEntry 28 }


        csuAISDefects OBJECT-TYPE
            SYNTAX Counter
            ACCESS read-only
            STATUS mandatory
            DESCRIPTION 
            "A count of the number of AIS Defects"
            ::= { csuInfoEntry 29 }


--------------  CSU Configuration Table ---------------------

     csuConfigTable OBJECT-TYPE
         SYNTAX  SEQUENCE OF CSUConfigEntry
         ACCESS  not-accessible
         STATUS  mandatory
         DESCRIPTION
            "The CSU Configuration table."
        ::= { csu 2 }

     csuConfigEntry OBJECT-TYPE
         SYNTAX  CSUConfigEntry
         ACCESS  not-accessible
         STATUS  mandatory
         DESCRIPTION
        "An entry in the CSU Configuration table."
        INDEX   { csuConfigLineIndex }
        ::= { csuConfigTable 1 }

        CSUConfigEntry ::=
            SEQUENCE {
                csuConfigLineIndex 
                     INTEGER,
                csuChannelBandwidth 
                     INTEGER,
                csuDataInversion 
                     INTEGER,
                csuDataCoding 
                     INTEGER,
                csuTimingMode 
                       INTEGER,
                csuLineBuildOut 
                       INTEGER,
                csuLineCode 
                       INTEGER,
                csuPulseDensityEnforcer 
                       INTEGER,
                csuFramingFormat 
                       INTEGER,
                csuJapaneseCRC6 
                       INTEGER,
                csuReceiverSensitivity 
                       INTEGER,
                csuFDLidleCode 
                       INTEGER,
                csuANSIPRMEnable 
                       INTEGER,
                csuANSIPRMaddress 
                       INTEGER,
                csuATTresponseEnable 
                       INTEGER,
                csuATTresponseaddress 
                       INTEGER,
                csuAllocatedChannelMap 
                        DisplayString

        }

        csuConfigLineIndex OBJECT-TYPE
            SYNTAX  INTEGER (1..2147483647)
            ACCESS  read-only
            STATUS  mandatory
            DESCRIPTION
            "The index value which uniquely identifies the CSU interface
            to which this entry is applicable."
       ::= { csuConfigEntry 1 }

        csuChannelBandwidth OBJECT-TYPE
            SYNTAX INTEGER {
                        csu64kbps(1),
                        csu56kbps(2),
                        csuAutoBandwidth(3)
          }
            ACCESS read-only
            STATUS mandatory
            DESCRIPTION " "
            ::= { csuConfigEntry 2 }

        csuDataInversion OBJECT-TYPE
            SYNTAX INTEGER {
                        csuNotInverted(1),
                        csuInverted(2),
                        csuAutoInverted(3)
          }
            ACCESS read-only
            STATUS mandatory
            DESCRIPTION " "
            ::= { csuConfigEntry 3 }

        csuDataCoding OBJECT-TYPE
            SYNTAX INTEGER {
                        csuNRZ(1),
                        csuNRZI(2)
          }
            ACCESS read-only
            STATUS mandatory
            DESCRIPTION " "
            ::= { csuConfigEntry 4 }

        csuTimingMode OBJECT-TYPE
            SYNTAX INTEGER {
                        csuNetworkTiming(1),
                        csuLoopTiming(2)
          }
            ACCESS read-only
            STATUS mandatory
            DESCRIPTION " "
            ::= { csuConfigEntry 5 }

        csuLineBuildOut OBJECT-TYPE
            SYNTAX INTEGER {
                    csu0DB(1),
                    csu75DB(2),
                    csu15DB(3),
                    csu225DB(4),
                    csu0to133(5),
                    csu133to266(6),
                    csu266to399(7),
                    csu399to533(8),
                    csu533to655(9)
          }
            ACCESS read-only
            STATUS mandatory
            DESCRIPTION 
            "Line Build out values: to be interpreted as follows:
            csu0DB(1)           0        LBO 0 dB
            csu75DB(2)          1        LBO -7.5 dB
            csu15(3)            2        LBO -15 dB
            csu225(4)           3        LBO -22.5 dB
            csu0_133(5)         4        LBO 0 to 133 feet 
            csu133_266(6)       5        LBO 133 to 266 feet
            csu266_399(7)       6        LBO 266 to 399 feet
            csu399_533(8)       7        LBO 399 to 533 feet
            csu533_655(9)       8        LBO 533 to 655 feet "
            ::= { csuConfigEntry 6 }

        csuLineCode OBJECT-TYPE
            SYNTAX INTEGER {
                        csuB8ZS(1),
                        csuAMI(2),
                        csuAutoLineCoding(3)
          }
            ACCESS read-only
            STATUS mandatory
            DESCRIPTION " "
            ::= { csuConfigEntry 7 }

        csuPulseDensityEnforcer OBJECT-TYPE
            SYNTAX INTEGER {
                        csuPDEnforceOFF(1),
                        csuPDEnforceON(2)
          }
            ACCESS read-only
            STATUS mandatory
            DESCRIPTION " "
            ::= { csuConfigEntry 8 }

        csuFramingFormat OBJECT-TYPE
            SYNTAX INTEGER {
                        csuESF(1),
                        csuD4(2),
                        csuAutoFraming(3)
          }
            ACCESS read-only
            STATUS mandatory
            DESCRIPTION " "
            ::= { csuConfigEntry 9 }

        csuJapaneseCRC6 OBJECT-TYPE
            SYNTAX INTEGER {
                        csuJapanCRCDisable (1),
                        csuJapanCRCEnable(2),
                        csuAutoBandwidth(3)
          }
            ACCESS read-only
            STATUS mandatory
            DESCRIPTION " "
            ::= { csuConfigEntry 10}

        csuReceiverSensitivity OBJECT-TYPE
            SYNTAX INTEGER {
                        csuSensitivityExtended(1),
                        csuSensitivityNormal(2)
          }
            ACCESS read-only
            STATUS mandatory
            DESCRIPTION " "
            ::= { csuConfigEntry 11 }

        csuFDLidleCode OBJECT-TYPE
            SYNTAX INTEGER {
                        csuFDLIdleIsFlags(1),
                        csuFdlIdleIsIdles(2)
          }
            ACCESS read-only
            STATUS mandatory
            DESCRIPTION " "
            ::= { csuConfigEntry 12 }

        csuANSIPRMEnable OBJECT-TYPE
            SYNTAX INTEGER {
                        csuANSIPRMEnabled(1),
                        csuANSIPRMDisabled(2)
          }
            ACCESS read-only
            STATUS mandatory
            DESCRIPTION " "
            ::= { csuConfigEntry 13 }

        csuANSIPRMaddress OBJECT-TYPE
            SYNTAX INTEGER {
                        csuANSIPrm0x38(1),
                        csuANSIPrm0x3a(2)
          }
            ACCESS read-only
            STATUS mandatory
            DESCRIPTION " "
            ::= { csuConfigEntry 14 }

        csuATTresponseEnable OBJECT-TYPE
            SYNTAX INTEGER {
                        csuATTResponseEnabled(1),
                        csuATTResponseDisabled(2)
          }
            ACCESS read-only
            STATUS mandatory
            DESCRIPTION " "
            ::= { csuConfigEntry 15 }

        csuATTresponseaddress OBJECT-TYPE
            SYNTAX INTEGER {
                        csuATTResponseBoth(1),
                        csuATTResponseCSU(2),
                        csuATTResponseDSU(3)
          }
            ACCESS read-only
            STATUS mandatory
            DESCRIPTION " "
            ::= { csuConfigEntry 16 }


        csuAllocatedChannelMap OBJECT-TYPE
            SYNTAX DisplayString  (SIZE (0..255))
            ACCESS read-only
            STATUS mandatory
            DESCRIPTION 
            "The allocated channel map. Each channel maps into one 
            BYTE, starting with channel one in the first byte. A value
            indicates that channel is configured ON, and 1 indicates 
            that the channel is configured OFF."
            ::= { csuConfigEntry 17}

--------------  CSU Fractional Table ---------------------

     csuFracTable OBJECT-TYPE
         SYNTAX  SEQUENCE OF CSUFracEntry
         ACCESS  not-accessible
         STATUS  mandatory
         DESCRIPTION
            "The CSU Fractional table."
        ::= { csu 3 }


     csuFracEntry OBJECT-TYPE
         SYNTAX  CSUFracEntry
         ACCESS  not-accessible
         STATUS  mandatory
         DESCRIPTION
         "An entry in the CSU Fractional table."
        INDEX   { csuFracLineIndex, csuFracNumber }
        ::= { csuFracTable 1 }

        CSUFracEntry ::=
            SEQUENCE {
                csuFracLineIndex
                    INTEGER,
                csuFracNumber
                    INTEGER,
                csuFracInUse
                    INTEGER,
                csuFracDetected
                    INTEGER
            }

        csuFracLineIndex OBJECT-TYPE
            SYNTAX  INTEGER (1..2147483647)
            ACCESS  read-only
            STATUS  mandatory
            DESCRIPTION
            "The index value which uniquely identifies the DS1 interface
            to which this entry is applicable. The interface identified
            by a particular value of this index is the same interface as
            identified by the same value a csuLineIndex object
            instance."
            ::= { csuFracEntry 1 }


         csuFracNumber OBJECT-TYPE
             SYNTAX  INTEGER (1..31)
             ACCESS  read-only
             STATUS  mandatory
             DESCRIPTION
                "The channel number for this entry."
            ::= { csuFracEntry 2 }


         csuFracInUse OBJECT-TYPE
            SYNTAX INTEGER {
                        csuChannelInUse(1),
                        csuChannelNotInUse(2)
            }
            ACCESS read-only
            STATUS mandatory
            DESCRIPTION 
            "Indicates whether this channel has been configured as part
            of the fractional arrangement."
            ::= { csuFracEntry 3 }

         csuFracDetected OBJECT-TYPE
            SYNTAX INTEGER {
                        csuChannelInUse(1),
                        csuChannelNotInUse(2),
                        csuChannelUnknown(3)
            }
            ACCESS read-only
            STATUS mandatory
            DESCRIPTION 
            "Indicates the result of channel autodetection. A value of
            InUse or NotInUse should match the setting of configuration
            for this channel"
            ::= { csuFracEntry 4 }

END
