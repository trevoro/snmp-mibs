PDN-RADIUS-MIB DEFINITIONS ::= BEGIN

-- Version :  0.1 DRAFT
-- Enterprise radius mib
-- Copyright (C) 2000 Paradyne Corporation.

-- Created by : Wayne Jadoo / Prakash Easwar
 
 IMPORTS
 DisplayString
 FROM SNMPv2-TC
 IpAddress
 FROM RFC1155-SMI
 OBJECT-TYPE
 FROM RFC-1212
 TRAP-TYPE
 FROM RFC-1215
 pdn-radius
 FROM PDN-HEADER-MIB
 ;

sysDevRadiusMIBObjects OBJECT IDENTIFIER ::= { pdn-radius 1 }
sysDevRadiusMIBTraps   OBJECT IDENTIFIER ::= { pdn-radius 2 }

-- 3.2.3. Radius Security
-- MCC-rq 150-180: A new group is added into the Hotwire System MIB

sysDevRadiusAuthEnable OBJECT-TYPE
    SYNTAX INTEGER {
        disable (1),
        enable (2)
    }
    ACCESS read-write
    STATUS mandatory
    DESCRIPTION
        "Enable and disable RADIUS Authentication."
    ::= { sysDevRadiusMIBObjects 1 }

sysDevRadiusAuthTimeout OBJECT-TYPE
    SYNTAX INTEGER (3..30)
    ACCESS read-write
    STATUS mandatory
    DESCRIPTION
        "This object corresponds to the maximum response
         time of the RADIUS Server."
    ::= { sysDevRadiusMIBObjects 2 }

sysDevRadiusAuthAttempts OBJECT-TYPE
    SYNTAX INTEGER (1..3)
    ACCESS read-write
    STATUS mandatory
    DESCRIPTION
        "This object corresponds to the number of retries
         in the event of authentication timeout."
    ::= { sysDevRadiusMIBObjects 3 }

sysDevRadiusAuthConfigTable OBJECT-TYPE
    SYNTAX SEQUENCE OF SysDevRadiusAuthConfigEntry
    ACCESS not-accessible
    STATUS mandatory
    DESCRIPTION
        "This table contains variables that facilitate
         the configuration of RADIUS authentication servers."
    ::= { sysDevRadiusMIBObjects 4 }

sysDevRadiusAuthConfigEntry OBJECT-TYPE
    SYNTAX SysDevRadiusAuthConfigEntry
    ACCESS not-accessible
    STATUS mandatory
    DESCRIPTION
        "An entry containing RADIUS Authentication Server
         configuration."
    INDEX { sysDevRadiusAuthServerIndex }
     ::= { sysDevRadiusAuthConfigTable 1 }

SysDevRadiusAuthConfigEntry ::= SEQUENCE {
    sysDevRadiusAuthServerIndex INTEGER,
    sysDevRadiusAuthServerAddress IpAddress,
    sysDevRadiusAuthServerPort INTEGER (0..65535),
    sysDevRadiusAuthSecret DisplayString (SIZE(6..32))
}

sysDevRadiusAuthServerIndex OBJECT-TYPE
    SYNTAX INTEGER
    ACCESS read-write
    STATUS mandatory
    DESCRIPTION
        "This object corresponds to the Index to the
         RADIUS server Configuration table."
    ::= { sysDevRadiusAuthConfigEntry 1 }

sysDevRadiusAuthServerAddress OBJECT-TYPE
    SYNTAX IpAddress
    ACCESS read-write
    STATUS mandatory
    DESCRIPTION
        "This object corresponds to the IP address of the
         RADIUS server."
    ::= { sysDevRadiusAuthConfigEntry 2 }

sysDevRadiusAuthServerPort OBJECT-TYPE
    SYNTAX INTEGER (0..65535)
    ACCESS read-write
    STATUS mandatory
    DESCRIPTION
        "This object corresponds to the UDP Port that the
         RADIUS server will accept Access-Request."
    ::= { sysDevRadiusAuthConfigEntry 3 }

sysDevRadiusAuthSecret OBJECT-TYPE
    SYNTAX DisplayString (SIZE(6..32))
    ACCESS read-only
    STATUS mandatory
    DESCRIPTION
        "This object corresponds to the RADIUS secret used
         by RADIUS server and NAS."
    ::= { sysDevRadiusAuthConfigEntry 4 }


END
