--    @(#)3604base.mib	9.1 10/16/98   
	DYNATECHCOMMUNICATIONS-MIB DEFINITIONS ::= BEGIN



	IMPORTS

		enterprises

			FROM RFC1155-SMI

		OBJECT-TYPE

			FROM RFC-1212;



	-- The purpose of this file is to be a base for the MIBS

	-- for all Dynatech Communications Products.

	-- Room is being left (hopefully) for all of the various

	-- Product Lines to be incorporated here eventually.







	dynatechCommunications	OBJECT IDENTIFIER ::= { enterprises 384 }





	-- No actual object leaves are expected to be defined here

	-- Just the bases for the different MIBS to build upon.



	-- The first node under Dynatech is for the products



	dynaCommProducts OBJECT IDENTIFIER ::= { dynatechCommunications 1 }



	-- Each product line should take a node here as a base

	-- Each product would then be built upon the node for its

	-- product line.



	cpx  OBJECT IDENTIFIER ::= { dynaCommProducts 1 }

	dnms OBJECT IDENTIFIER ::= { dynaCommProducts 2 }





	-- This node is for more general Dynatech objects.  Not specific to

	-- one product.



	dynaCommGeneral  OBJECT IDENTIFIER ::= { dynatechCommunications 2 }



	-- Node for documentation



	dynaCommDoc	OBJECT IDENTIFIER ::= { dynatechCommunications 3 }



	END
