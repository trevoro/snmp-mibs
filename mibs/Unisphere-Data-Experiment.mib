-- *****************************************************************************
-- Unisphere Networks Data Products SNMP Experimental MIB Registry.
--
-- Copyright (c) 2000, 2001 Unisphere Networks, Inc.  All rights reserved.
-- *****************************************************************************

Unisphere-Data-Experiment DEFINITIONS ::= BEGIN

IMPORTS
    MODULE-IDENTITY,
    OBJECT-IDENTITY
        FROM SNMPv2-SMI
    usExperiment
        FROM Unisphere-SMI;

usDataExperiment MODULE-IDENTITY
    LAST-UPDATED "200106202036Z"  -- 20-Jun-01 04:36 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The object identifiers for experimental MIBs for the Unisphere
        Networks, Inc. data communications products.  This is the top-level
        object identifier registry for SNMP modules containing experimental MIB
        definitions.  Experimental MIBs are defined as:

        1) IETF work-in-process MIBs which have not been assigned a permanent
           object identifier by the IANA.

        2) Unisphere work-in-process MIBs that have not achieved final
           production quality or field experience.

        NOTE: Support for MIBs under the this OID subtree is temporary and
              changes to objects may occur without notice."
    -- Revision History
    REVISION    "200106202036Z"  -- 20-Jun-01 04:36 PM EDT  - RX 4.0
    DESCRIPTION
        "Added OID for the SONET APS-MIB."
    REVISION    "200010242100Z"  -- 24-Oct-00  5:00 PM EDT  - RX 3.0
    DESCRIPTION
        "The initial release of this management information module."
    ::= { usExperiment 2 }

-- +++++++++++++++++++++++++++++++++++++++++++++++++++++++++++++++++++++++++++++
-- Experimental MIB OID assignments.
-- +++++++++++++++++++++++++++++++++++++++++++++++++++++++++++++++++++++++++++++

usdDvmrpExperiment OBJECT-IDENTITY
    STATUS      current
    DESCRIPTION
        "The object identifier used to anchor the experimental IETF draft for
        the Distance Vector Multicast Routing Protocol (DVMRP) MIB."
    REFERENCE
        "IETF Inter-Domain Multicast Routing (idmr) Working Group document:
        draft-ietf-idmr-dvmrp-mib-11.txt."
    ::= { usDataExperiment 1 }

usdSonetApsExperiment OBJECT-IDENTITY
    STATUS      current
    DESCRIPTION
        "The object identifier used to anchor the experimental IETF draft for
        the SONET linear Automatic Protection Switching (APS) MIB."
    REFERENCE
        "IETF AToM MIB (atommib) Working Group document:
        draft-ietf-atommib-sonetaps-mib-05.txt."
    ::= { usDataExperiment 2 }

END
