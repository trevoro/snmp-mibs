-- extracted from draft-stephan-ippm-mib-02.txt
-- at Fri May 14 06:20:51 2004

   IPPM-MIB DEFINITIONS ::= BEGIN 
    
   IMPORTS 
        MODULE-IDENTITY, 
        NOTIFICATION-TYPE, 
        OBJECT-TYPE, 
        Integer32, 
        Counter32, 
        experimental 
                FROM SNMPv2-SMI                  
        OwnerString 
                FROM RMON-MIB 
        protocolDir 
                FROM RMON2-MIB 
        DisplayString, 
        TimeStamp, 
        DateAndTime, 
        TruthValue, 
        RowStatus, 
        StorageType, 
        TEXTUAL-CONVENTION 
                FROM SNMPv2-TC 
        MODULE-COMPLIANCE, 
        OBJECT-GROUP, 
        NOTIFICATION-GROUP 
                FROM SNMPv2-CONF; 
    
    
   ippmMib MODULE-IDENTITY 
       LAST-UPDATED "200202011200Z"    -- Feb 1, 2002 
        ORGANIZATION    "France Telecom - R&D" 
        CONTACT-INFO 
        "Postal : Emile Stephan 
        France Telecom - R&D, Dpt. CPN 
        2, Avenue Pierre Marzin 
        Technopole Anticipa 
        22307 Lannion Cedex 
        FRANCE 
        Tel: + 33 2 96 05 36 10 
        E-mail: emile.stephan@francetelecom.com" 
        DESCRIPTION      
   " This memo defines a portion of the Management Information Base 
   (MIB) for use with network management protocols in TCP/IP-based 
   internets. In particular, It defines a registry of the IPPM working 
   group metrics and specifies the objects used for managing IPPM 
   metrics measures, pushing alarms and reporting the measures results. 
   " 
       REVISION "200107051500Z"    -- July 2001 
       DESCRIPTION 
           "The creation of the IPPM-MIB corresponds to the draft-
   stephan-ippm-mib-00.txt posted in July 2001. The IPPM-MIB was 
   partially presented during the IPPM WG meeting of London. 
    
   Two main issues were identified during the 52 th IETF meetings in 
   SLC: 
    
        + There is a need for a common IPPM metric registry; 
        + There is a short term need for the reporting part of the IPPM-
   MIB; 
        " 
       REVISION "200201051500Z"    -- Jan 2002 
       DESCRIPTION 
          "This release corresponds to draft-stephan-ippm-mib-01.txt 
          posted in January 2002. This draft added sections which 
          presents: 
            
           + The different measurement architectures; 
           + The integration of the IPPM-MIB in a measurement software; 
           + The use of the IPPM-MIB for reporting. 
            
          The new items created in this release are: 
            
           + Fields in the ippmOwnersTable to control the access of an 
            owner to the measures. 
           + The table ippmResultSharingTable to manage the access of an 
            owner to the results of the measure. 
            
           All the control tables are optional or read only in reporting 
            mode. 
           "     
       REVISION "200202011200Z"    -- Feb 2002 
       DESCRIPTION 
           "The current release corresponds to draft-stephan-ippm-mib-
   02.txt posted in February 2002. It added a section to present the 
   IPPM metrics registry. 
    
          The new items created in this release are: 
            
           + TC IppmReportDefinition and IppmStandardMetrics; 
           + The registry of the IPPM metrics; 
           + The ippmReportSetupTable and the ippmReportTable; 
           + The notification tree. 
           "     
         
        --  
        -- to be assigned by IANA 
        --  
        ::= { experimental 10000 } 
         
   -- 
   -- registry 
   -- 
    
   metrics      OBJECT IDENTIFIER       ::= { ippmMib 1 }  
    
   rfc          OBJECT IDENTIFIER       ::= { metrics 1 }  
   draft        OBJECT IDENTIFIER       ::= { metrics 2 }  
   id           OBJECT IDENTIFIER       ::= { metrics 3 }  
    
   -- 
   -- metrics registry from RFC of the IPPM WG 
   -- 
    
    
   instantaneousUnidirectionalConnectivity OBJECT IDENTIFIER::={rfc 1} 
   instantaneousBidirectionalConnectivity OBJECT IDENTIFIER ::={rfc 2} 
   intervalUnidirectionalConnectivity OBJECT IDENTIFIER ::= { rfc 3 } 
   intervalBidirectionalConnectivity OBJECT IDENTIFIER ::= { rfc  4 } 
   intervalTemporalConnectivity      OBJECT IDENTIFIER ::= { rfc  5 } 
   onewayDelay                       OBJECT IDENTIFIER ::= { rfc  6 } 
   onewayDelayPoissonStream        OBJECT IDENTIFIER ::= { rfc  7 } 
   onewayDelayPercentile            OBJECT IDENTIFIER ::= { rfc  8 } 
   onewayDelayMedian                OBJECT IDENTIFIER ::= { rfc  9 } 
   onewayDelayMinimum               OBJECT IDENTIFIER ::= { rfc 10 } 
   onewayDelayInversePercentile    OBJECT IDENTIFIER ::= { rfc 11 } 
   onewayPacketLoss                 OBJECT IDENTIFIER ::= { rfc 12 } 
   onewayPacketLossPoissonStream  OBJECT IDENTIFIER ::= { rfc 13 } 
   onewayPacketLossAverage         OBJECT IDENTIFIER ::= { rfc 14 } 
   roundtripDelay                    OBJECT IDENTIFIER ::= { rfc 15 } 
   roundtripDelayPoissonStream     OBJECT IDENTIFIER ::= { rfc 16 } 
   roundtripDelayPercentile         OBJECT IDENTIFIER ::= { rfc 17 } 
   roundtripDelayMedian             OBJECT IDENTIFIER ::= { rfc 18 } 
   roundtripDelayMinimum            OBJECT IDENTIFIER ::= { rfc 19 } 
   roundtripDelayInversePercentile OBJECT IDENTIFIER ::= { rfc 20 } 
    
   -- 
   -- metrics registry from draft of the IPPM WG 
   -- 
    
   -- 
   -- metrics registry from individual draft 
   -- 
    
   -- 
   -- TEXTUAL-CONVENTION 
   -- 
   TimeUnit ::= TEXTUAL-CONVENTION     
       STATUS       current 
       DESCRIPTION 
        "A list of time units." 
        SYNTAX  INTEGER { 
                year(1), 
                month(2), 
                week(3), 
                day(4), 
                hour(5), 
                second(6), 
                ms(7), 
                us(8), 
                ns(9) 
        } 
   -- 
   -- 
   -- A absolute, GMT timer using UTC like convention. 
   -- 
   -- 
        
   GMTDateAndTime ::= TEXTUAL-CONVENTION     
       DISPLAY-HINT "1d-1d-1d,1d:1d:1d,2d" 
       STATUS       current 
       DESCRIPTION 
                "A date-time specification. 
                 
                field  octets  contents                  range 
                -----  ------  --------                  ----- 
                1       1    year*                     0..255 
                2       2    month                     1..12 
                3       3    day                       1..31 
                4       4    hour                      0..23 
                5       5    minutes                   0..59 
                6       6    seconds                   0..59 
                7      7-8   1/10 milliseconds         0..9999 
                 
                *Notes: 0 stands for year 2000. 
                 
                For example, '0102192015100500' represent 8:15pm, 10 
                seconds and 50 ms GMT on 19 February 2001 and is 
                displayed as 01-02-19,20:15:10,0500" 
       SYNTAX       OCTET STRING (SIZE (8)) 
        
        
        
   GmtTimeFilter ::= TEXTUAL-CONVENTION 
        STATUS        current 
        DESCRIPTION 
                "GmtTimeFilter TC is inspired by the TimeFilter defined 
                in the RMON2. The reference of the time of TimeFilter is 
                the local value of sysUptime while GmtTimeFilter uses a 
                absolute reference of time. 
                 
                GmtTimeFilter is intended to be used for the index of a 
                table. It allows an application to download only those 
                rows changed since a particular time. A row is 
                considered changed if the value of any object in the row 
                changes or if the row is created or deleted. 
                 
                Each new conceptual row will be associated with the 
                timeMark instance which was created at the value of 
                ippmTimeSysTimer. 
                 
                It is intended to provide an absolute timestamp index 
                for the result of measures. Typically to each singleton 
                produced by an IPPM measure is associated the timemark 
                corresponding to the moment of the measure. 
                 
                illustrations: 
                 
                Consider the 2 tables measureTable and resultTable 
                 
                measureTable OBJECT-TYPE 
                SYNTAX     SEQUENCE OF MeasureEntry 
                MAX-ACCESS not-accessible 
                STATUS     current 
                DESCRIPTION '' 
                ::= { fooMib 1 } 
                INDEX { measureIndex } 
                 
                resultTable OBJECT-TYPE 
                SYNTAX     SEQUENCE OF ResultEntry 
                MAX-ACCESS not-accessible 
                STATUS     current 
                DESCRIPTION '' 
                ::= { fooMib 2 } 
                INDEX { measureIndex, resultTimeMark } 
                 
                ResultEntry { 
                   resultTimeMark  TimeFilter, 
                   resultCounts    Counter 
                } 
                 
                Should there be two measure rows in the measure table 
                (measureIndex == 1, measureIndex == 2) which produced 
                results asynchronously (e.g. made at Poisson intervals 
                or sibling) and log them in the result table. 
                Measure 1 produced the result 34 at time 
                0102192015100500 GMT, while row 2 produced the value 54 
                most recently (10ms later) at time 0102192015100600 GMT, 
                and both rows are updated on several later occasions 
                such that the current values are 37 and 53 respectively.  
                 
                Then the following resultCounts instances would exist. 
                 
                resultCounts.1.0102192015100500  34 
                resultCounts.2.0102192015100600  54 
                resultCounts.1.0102192015100950  65 
                resultCounts.1.0102192015100600  57 
                resultCounts.2.0102192015100800  48 
                resultCounts.2.0102192015100850  53 
                resultCounts.1.0102192015110050  49 
                resultCounts.1.0102192015110200  37 
                 
                The following get-bulk explains how a NMS retrieves the 
                results of the measures. 
                 
                get-bulk(nonRptrs=1, maxReps=10, resultCounts.1); 
                returns: 
                        resultCounts.1.0102192015100500 == 34 
                        resultCounts.1.0102192015100950 == 65 
                        resultCounts.1.0102192015100600 == 57 
                        resultCounts.1.0102192015110050 == 49 
                        resultCounts.1.0102192015110200 == 37 
                        # return lexigraphically-next two MIB instances 
                 
                get-bulk(nonRptrs=0, maxReps=2, 
                resultCounts.1.0102192015100600, 
                resultCounts.2.0102192015100600); 
                returns: 
                        resultCounts.1.0102192015100950 == 65 
                        resultCounts.2.0102192015100800 == 48 
                        resultCounts.1.0102192015100600 == 57 
                        resultCounts.2.0102192015100850 == 53 
                 
                 
                get-bulk(nonRptrs=0, maxReps=2, 
                resultCounts.1.0102192015110200, 
                resultCounts.2.0102192015110200); 
                returns: 
                        return lexigraphically-next two MIB instances 
                        no 'resultTable' counter values at all are 
                returned because neither counter has been updated since 
                time 0102192015110200 
                " 
       SYNTAX    GMTDateAndTime 

   TypeP  ::= TEXTUAL-CONVENTION     
       DISPLAY-HINT "1d." 
       STATUS       current 
       DESCRIPTION 
                "This textual convention is used to describe the 
                protocols encapsulation list of a packet, and is used as 
                the value of the SYNTAX clause for the type of the Src 
                and Dst of a IPPM measure. The RFC2895 specifies a macro 
                for the definition of protocols identifiers while its 
                companion document, the RFC2896 defines a set of 
                protocols identifiers. 
                 
                Notes: An IPPM TypeP does not differ from RMON2 
                Protocols identifiers but TypeP usage in IPPM MIB 
                differs from Protocol identifier usage in RMON2. A IPPM 
                measure is active so generally TypeP does not describe 
                the link layer (i.e. ether2...). Valid Internet packets 
                are sent from Src to Dst. Then the choice of the link 
                layer relies on the Internet stack.  
                 
                For example, the RFC2896 defines the protocol identifier 
                '16.0.0.0.1.0.0.8.0.0.0.0.6.0.0.0.23.3.0.0.0' which 
                represents ether2.ip.tcp.telnet and the protocol 
                identifier 16.0.0.0.1.0.0.8.0.0.0.0.4.0.0.0.17.3.0.0.0 
                which stands for ether2.ip.ipip4.udp. The corresponding 
                TypeP are '12.0.0.8.0.0.0.0.6.0.0.0.23.3.0.0.0' 
                (ip.tcp.telnet) and 12.0.0.8.0.0.0.0.4.0.0.0.17.3.0.0.0 
                (ip.ipip4.udp)." 
       SYNTAX       OCTET STRING 
    
        
   IppmReportDefinition ::= TEXTUAL-CONVENTION 
   STATUS        current 
   DESCRIPTION 
        "IppmReportDefinition is intended to be used for the description 
   of a report of results of a measure.  
         
        By default all the results of a measure belong to the report of 
   this measure. 
         
        The first step of the report elaboration set up triggers on the 
   value of the measure and on the distribution over time of the events 
   generated by these triggers.  
         
        The measure results corresponding to an event are reported 
   periodically or sent in alarms as soon as the event appears. 
                 
        The end of description describe housekeeping tasks. 
         
        An action if performed if the corresponding bit is set to 1. 
        onSingleton(1): 
               The actions are performed each time a new result of the 
               measure occurs.  
    
        onMeasureCycle(2): 
               The actions are performed on the results of the measure 
               at the end of each cycle of measure. 
    
        onMeasureCompletion(3): 
               The actions are performed on the results of the measure 
               at the end of the measure. 
    
        reportOnlyUptoDownMetricResults(4): 
               Report the contiguous results which are on opposite sides 
               of the metric threshold. 
    
        reportOnlyExceededEventsDuration(5): 
              Report the current result of a serie of contiguous 
              results which exceed the metric threshold when the 
              duration of the serie is over the events duration 
              threshold seconds.  
                 
        inIppmReportTable(6): 
                store the report in the local ippmReportTable.  
                 
        inSNMPTrapPDU(7): 
                Send the report using a SNMP-Trap-PDU. 
    
        inSNMPv2TrapPDU(8): 
                Send the report using a SNMPv2-Trap-PDU. 
    
        inInformRequestPDU(9): 
                Send the report using a SNMP InformRequest-PDU. 
    
        inEmail(10): 
                Send the report using an email.  
    
        inSMS(11): 
                Send the report using a SMS. 
    
        clearHistory(12): 
               Remove all the results corresponding to this measure 
                from the ippmHistoryTable. 
    
        clearReport(13): 
               Remove all the results corresponding to this measure 
               from the ippmReportTable. 
        " 
         
        SYNTAX BITS { 
                none(0),        -- reserved 
                onSingleton(1), 
                onMeasureCycle(2), 
                onMeasureCompletion(3), 
                reportOnlyUptoDownMetricResults(4), 
                reportOnlyExceededEventsDuration(5), 
                inIppmReportTable(6), 
                inSNMPTrapPDU(7), 
                inSNMPv2TrapPDU(8), 
                inInformRequestPDU(9), 
                inEmail(10), 
                inSMS(11), 
                clearHistory(12), 
                clearReport(13) 
        }     
    
    
    
   IppmStandardMetrics ::= TEXTUAL-CONVENTION 
        STATUS        current 
        DESCRIPTION 
        "The definition of the standardized IPPM metrics. 
        if the draftMetrics bit is set then the other bits describe a WG 
   draft metric identifiers. 
        " 
        SYNTAX BITS { 
                draftMetrics(0), 
                instantaneousUnidirectionalConnectivity(1),  
                instantaneousBidirectionalConnectivity(2),  
                intervalUnidirectionalConnectivity(3),  
                intervalBidirectionalConnectivity(4),  
                intervalTemporalConnectivity(5),  
                onewayDelay(6),  
                onewayDelayPoissonStream(7),  
                onewayDelayPercentile(8),  
                onewayDelayMedian(9),  
                onewayDelayMinimum(10),  
                onewayDelayInversePercentile(11),  
                onewayPacketLoss(12),  
                onewayPacketLossPoissonStream(13),  
                onewayPacketLossAverage(14),  
                roundtripDelay(15),  
                roundtripDelayPoissonStream(16),  
                roundtripDelayPercentile(17),  
                roundtripDelayMedian(18),  
                roundtripDelayMinimum(19),  
                roundtripDelayInversePercentile(20) 
        } 
   -- IPPM Mib objects definitions 
    
   ippmCompliances      OBJECT IDENTIFIER       ::= { ippmMib 2 } 
   ippmOwnersGroup      OBJECT IDENTIFIER       ::= { ippmMib 3 } 
   ippmSystemGroup      OBJECT IDENTIFIER       ::= { ippmMib 4 } 
   ippmMeasureGroup     OBJECT IDENTIFIER       ::= { ippmMib 5 } 
   ippmHistoryGroup     OBJECT IDENTIFIER       ::= { ippmMib 6 } 
   ippmNetworkMeasureGroup      OBJECT IDENTIFIER ::= { ippmMib 7 } 
   ippmAggregatedMeasureGroup   OBJECT IDENTIFIER ::= { ippmMib 8 } 
   ippmReportGroup              OBJECT IDENTIFIER ::= { ippmMib 9 } 
   ippmNotifications            OBJECT IDENTIFIER ::= { ippmMib 10 } 
    
    
   --  
   -- ippmOwnersGroup 
   --  
   -- The ippmOwnersGroup objects are in charge of the management 
   -- of the access of the owners to the measurements. 
   --  
   -- 
   ippmOwnersControlTable OBJECT-TYPE 
        SYNTAX     SEQUENCE OF IppmOwnersControlEntry 
        MAX-ACCESS not-accessible 
        STATUS     current 
        DESCRIPTION 
                "A NMS entity wishing to create and activate remote Ippm 
                measurements in an agent must previously be registered 
                in the ippmOwnersControlTable using the conceptual row 
                mechanism described in the RMON2.  
                 
                The control of the access to the results of the measures 
                is managed in the table ippmResultSharing. 
                " 
        ::= { ippmOwnersGroup 1 } 
    
   ippmOwnersControlEntry OBJECT-TYPE 
        SYNTAX     IppmOwnersControlEntry 
        MAX-ACCESS not-accessible 
        STATUS     current 
        DESCRIPTION 
                "The description of the resources the agent granted to a 
                SNMP application. 
                 
                For example, an instance of ippmOwnersControlOwner with 
                an OwnerString 'acme', which represents the 14th owner 
                created in ippmOwnersControlTable would be named 
                ippmOwnersControlEntryOwner.14. 
                 
                Notes: 
                 
                The ippmOwnersControlIndex value is a local index 
                managed directly by the agent. It is not used in anyway 
                in the other IPPM tables." 
                 
        INDEX { ippmOwnersControlIndex } 
        ::= { ippmOwnersControlTable 1 } 
       
   IppmOwnersControlEntry ::= SEQUENCE { 
        ippmOwnersControlOwner          OwnerString, 
        ippmOwnersControlIndex          Integer32, 
        ippmOwnersControlGrantedMetrics IppmStandardMetrics, 
        ippmOwnersControlGrantedRules   BITS, 
        ippmOwnersControlIpAddress      DisplayString, 
        ippmOwnersControlEmail          DisplayString, 
        ippmOwnersControlSMS            DisplayString, 
        ippmOwnersControlStatus         OwnerString 
   } 
    
   ippmOwnersControlIndex OBJECT-TYPE 
        SYNTAX Integer32 (1.. 65535) 
        MAX-ACCESS read-create 
        STATUS     current 
        DESCRIPTION 
                "An arbitrary index that only identify an entry in this 
   table" 
        ::= { ippmOwnersControlEntry 1 } 
    
   ippmOwnersControlOwner OBJECT-TYPE 
        SYNTAX     OwnerString 
        MAX-ACCESS read-create 
        STATUS     current 
        DESCRIPTION 
                "The owner described by this entry." 
        ::= { ippmOwnersControlEntry 2 } 
    
    
   ippmOwnersControlGrantedMetrics OBJECT-TYPE 
        SYNTAX     IppmStandardMetrics 
        MAX-ACCESS read-create 
        STATUS     current 
        DESCRIPTION 
                " Defines the metrics granted to an owner." 
        ::= { ippmOwnersControlEntry 3 } 
    
   ippmOwnersControlGrantedRules OBJECT-TYPE 
        SYNTAX     BITS { 
                all(0), 
                readonly(1), 
                permanent(2), 
                sender(2), 
                receive(3), 
                report(4), 
                alarm(5) 
   } 
        MAX-ACCESS read-create 
        STATUS     current 
        DESCRIPTION 
        "Defines the rules this owner may act as in the current IPPM MIB 
   instance. 
        all(0): 
                The owner is granted with all the rules. 
        readonly(1): 
                The measures (not only the metrics) allowed to this 
   owner are setup by the manager of the point of measure. The owner can 
   not add new measures for these metrics. The creation and the 
   configuration of the measures corresponding to these metrics are 
   managed by the manager of the point of measure. 
        permanent(2): 
                The measures (not only the metrics) allowed to this 
   owner are determined by the manager of the point of measure. The 
   owner can not add new measures for these metrics. The creation and 
   the first configuration of the measures corresponding to these 
   metrics are managed by the manager of the point of measure. The owner 
   may modify the measures parameters of the entries of the 
   corresponding ippmMeasureEntry which access is read-write. 
                Typically that permits the owner to suspend the 
   measures, to change the begin and end of the measures. 
    
        sender(3): 
                The owner may only activate measures for theses metrics 
   that send packets from the current point of measure. This flag is 
   only suitable for network measures. It shall be ignored for derived 
   metrics. 
        receiver(2): 
                The owner may only activate measures for theses metrics 
   that receive packets on the current point of measure. This flag is 
   only suitable for network measures. It shall be ignored for derived 
   metrics. Such control increases the security. The owner may not 
   generate packets from the probe. 
    
        report(4): 
                The owner may setup aggregated metrics on the measures 
   corresponding to these metrics. 
    
        alarm(5): 
                The owner may setup alarms on the results of the 
   measures metrics.  
    
    
   e.g.:  
        if the owner Acme is granted with the metric Instantaneous-
   Unidirectional-Connectivity as a Receiver in the current point of 
   measure, then Acme can not setup a Instantaneous-Unidirectional-
   Connectivity to another point of measure.  
        " 
        DEFVAL { 1 } 
        ::= { ippmOwnersControlEntry 4 } 

   ippmOwnersControlIpAddress OBJECT-TYPE 
        SYNTAX     DisplayString 
        MAX-ACCESS read-create 
        STATUS     current 
        DESCRIPTION 
                "The IP address of the NMS corresponding to this owner. 
   The address is human readable and is represented  using the dot 
   format." 
        ::= { ippmOwnersControlEntry 5 } 
         
   ippmOwnersControlEmail OBJECT-TYPE 
        SYNTAX     DisplayString 
        MAX-ACCESS read-create 
        STATUS     current 
        DESCRIPTION 
                "The email address of the NMS corresponding to this 
   owner." 
        ::= { ippmOwnersControlEntry 6 } 
         
   ippmOwnersControlSMS OBJECT-TYPE 
        SYNTAX     DisplayString 
        MAX-ACCESS read-create 
        STATUS     current 
        DESCRIPTION 
                "The SMS phone number of the NMS corresponding to this 
   owner." 
        ::= { ippmOwnersControlEntry 7 } 
         
   ippmOwnersControlStatus OBJECT-TYPE 
        SYNTAX     RowStatus 
        MAX-ACCESS read-create 
        STATUS     current 
        DESCRIPTION 
                "The status of this table entry." 
        ::= { ippmOwnersControlEntry 8 } 
         
-- 
--      ippmResultSharingTable 
-- 
    
   ippmResultSharingTable OBJECT-TYPE 
        SYNTAX     SEQUENCE OF IppmResultSharingEntry 
        MAX-ACCESS not-accessible 
        STATUS     current 
        DESCRIPTION 
                " ippmResultSharingTable controls finely the access of 
                an owner to the measure results of other owners. An 
                owner may grant another to read the result of its 
                measure. 
                Entries may exist in ippmResultSharingTable even is the 
                measures to be shared are not yet defined. Deleting a 
                measure entry in the ippmMeasureTable does not delete 
                the entries corresponding to this measure in the 
                ippmResultSharingTable. 
                 
                IppmResultSharingTable is optional. If this table is not 
                implemented then the owner has only access to its 
                measure results." 
    
   ::= { ippmOwnersGroup 2 } 
    
   ippmResultSharingEntry OBJECT-TYPE 
        SYNTAX     IppmResultSharingEntry 
        MAX-ACCESS not-accessible 
        STATUS     current 
        DESCRIPTION 
                "An entry allows an owner to read the results of a 
                measure owned by another owner. 
                It permits 2 typical usages: 
                        creating derived measurements on these results; 
                        reading the results from a remote NMS. 
                  
                Example: if acme.12 is a One-way-Delay(6) measure 
                        Acme may allows Peter to make derived metrics 
                        On the results of this measure. 
                " 
                 
        INDEX { ippmResultSharingOwner, ippmResultSharingIndex} 
        ::= { ippmResultSharingTable 1 } 
       
    
   IppmResultSharingEntry ::= SEQUENCE { 
        ippmResultSharingOwner          OwnerString, 
        ippmResultSharingIndex          Integer32, 
        ippmResultSharingMeasureOwner   OwnerString, 
        ippmResultSharingMeasureIndex   Integer32, 
        ippmResultSharingGrantedOwner   OwnerString, 
        ippmResultSharingStatus         RowStatus 
   }     
   ippmResultSharingOwner OBJECT-TYPE 
        SYNTAX OwnerString 
        MAX-ACCESS read-create 
        STATUS     current 
        DESCRIPTION 
                " The owner of this result control entry. Typically the 
   owner which created this conceptual row." 
        ::= { ippmResultSharingEntry 1 } 
    
    
   ippmResultSharingIndex OBJECT-TYPE 
        SYNTAX Integer32 (1.. 65535) 
        MAX-ACCESS read-create 
        STATUS     current 
        DESCRIPTION 
                " The index of this result control entry. The value is 
   managed by the owner. On creation a SNMP error 'inconsistentValue' is 
   returned if this value is already in use by this owner." 
        ::= { ippmResultSharingEntry 2 } 
    
    
   ippmResultSharingMeasureOwner OBJECT-TYPE 
        SYNTAX OwnerString 
        MAX-ACCESS read-create 
        STATUS     current 
        DESCRIPTION 
                "The owner of the measure to be shared. The couple 
   ippmResultSharingMeasureOwner, ippmResultSharingMeasureIndex 
   identifies absolutely a measure" 
        ::= { ippmResultSharingEntry 3 } 
    
   ippmResultSharingMeasureIndex OBJECT-TYPE 
        SYNTAX Integer32 (1.. 65535) 
        MAX-ACCESS read-create 
        STATUS     current 
        DESCRIPTION 
                "The index of the measure to be shared." 
        ::= { ippmResultSharingEntry 4 } 
    
   ippmResultSharingGrantedOwner OBJECT-TYPE 
        SYNTAX OwnerString 
        MAX-ACCESS read-only 
        STATUS     current 
        DESCRIPTION 
    
                "The owner which is granted to access to the result of 
   the measure described by the couple ippmResultSharingMeasureOwner, 
   ippmResultSharingMeasureIndex." 
        ::= { ippmResultSharingEntry 5 } 
    
   ippmResultSharingStatus OBJECT-TYPE 
        SYNTAX RowStatus 
        MAX-ACCESS read-only 
        STATUS     current 
        DESCRIPTION 
                " The status of this table entry. Once the entry status 
   is set to active." 
        ::= { ippmResultSharingEntry 6 } 
    
    
   --  
   -- ippmSystemGroup 
   --  
   -- 
    
    
   ippmSystemTimer OBJECT-TYPE 
        SYNTAX GMTDateAndTime 
        MAX-ACCESS read-only 
        STATUS     current 
        DESCRIPTION 
                "The current time of the system." 
        ::= { ippmSystemGroup 1 } 
         
         
   ippmSystemSynchonizationType OBJECT-TYPE 
        SYNTAX INTEGER  { 
                other(0), 
                ntp(1), 
                gps(2), 
                cdma(4) 
        } 
        MAX-ACCESS read-only 
        STATUS     current 
        DESCRIPTION 
                "ippmSystemSynchonizationType describes the mechanism  
                used to synchronise the system.  
                 
                other  
                        The synchronisation process must be defined  
                extensively in the ippmSystemSynchonizationDescription.  
                 
                ntp  
                       The system is synchronised using the network  
                time protocol. The NTP synchronisation must be described  
                finely in the ippmSystemSynchonizationDescription.  
                 
                gps  
                       The system is synchronised using the GPS clocks.  
                 
                cdma  
                       The system is synchronised using the CDMA 
                clocks.      
                " 
        ::= { ippmSystemGroup 2 } 
    
   ippmSystemSynchonizationDescription OBJECT-TYPE 
        SYNTAX DisplayString 
        MAX-ACCESS read-only 
        STATUS     current 
        DESCRIPTION 
                "The description of the synchronization process." 
        ::= { ippmSystemGroup 3 } 

   ippmSystemClockResolution OBJECT-TYPE 
        SYNTAX     Integer32 
        MAX-ACCESS read-only 
        STATUS     current 
        DESCRIPTION 
                "ippmSystemClockResolution provides the precision of the 
                clock used for the measures. The unit is 1/10 of 
                millisecond. For example, the clock on an old Unix host 
                might advance only once every 10 msec, and thus have a 
                resolution of only 10 msec." 
    
        ::= { ippmSystemGroup 4 } 
         
   ippmSystemSynchronisationTime OBJECT-TYPE 
        SYNTAX DateAndTime 
        MAX-ACCESS read-only 
        STATUS     current 
        DESCRIPTION 
                "The time when occurs the last synchronisation of the 
                clock. The last synchronisation must be set even if the 
                synchronisation is not automatic." 
        ::= { ippmSystemGroup 5 } 
         
   ippmSystemClockAccuracy OBJECT-TYPE 
        SYNTAX     Integer32 
        MAX-ACCESS read-only 
        STATUS     current 
        DESCRIPTION 
                "The most recent accuracy of the clock computed. The 
                accuracy must be compute even if the synchronisation is 
                not automatic." 
        ::= { ippmSystemGroup 6 } 
         
   ippmSystemClockSkew OBJECT-TYPE 
        SYNTAX     Integer32 
        MAX-ACCESS read-only 
        STATUS     current 
        DESCRIPTION 
                "The most recent skew of the clock computed. The 
                ippmSystemSkew must be compute even if the 
                synchronisation is not automatic." 
        ::= { ippmSystemGroup 7 } 
    
    
   ippmSystemPrevClockAccuracy OBJECT-TYPE 
        SYNTAX     Integer32 
        MAX-ACCESS read-only 
        STATUS     current 
        DESCRIPTION 
                "The previous accuracy of the clock measured. The 
                ippmSystemPrevClockAccuracy must be computed even if the 
                synchronisation is not automatic." 
        ::= { ippmSystemGroup 8 } 
         
   ippmSystemPrevClockSkew OBJECT-TYPE 
        SYNTAX     Integer32 
        MAX-ACCESS read-only 
        STATUS     current 
        DESCRIPTION 
                "The previous skew of the clock measured. The 
                ippmSystemPrevClockSkew must be computed even if the 
                synchronisation is not automatic." 
        ::= { ippmSystemGroup 9 } 
         
    
   -- 
    
   -- 
   --  
   -- ippmMeasureGroup 
   --  
   --  
   -- 
    
   ippmMetricTable OBJECT-TYPE 
        SYNTAX     SEQUENCE OF IppmMetricEntry 
        MAX-ACCESS not-accessible 
        STATUS     current 
        DESCRIPTION 
                "This table describes the current implementation. This 
                table is mandatory. Each IPPM standardized metric must 
                be described in the table.  
                In reporting mode the entries of this table may be not 
                accessible. It means that the table is handle internally 
                by the measure software. 
                " 
        ::= { ippmMeasureGroup 1 } 
         
   ippmMetricEntry OBJECT-TYPE 
        SYNTAX     IppmMetricEntry 
        MAX-ACCESS not-accessible 
        STATUS     current 
        DESCRIPTION 
                "An entry describes the static capabilities of a metric 
                implementation." 
        INDEX { ippmMetricIndex } 
        ::= { ippmMetricTable 1 } 
         
   IppmMetricEntry ::= 
        SEQUENCE { 
                ippmMetricIndex           Integer32, 
                ippmMetricCapabilities    INTEGER, 
                ippmMetricUnit            INTEGER, 
                ippmMetricDescription     DisplayString, 
                ippmMetricMaxHistorySize  Integer32 
        } 
         
   ippmMetricIndex OBJECT-TYPE 
        SYNTAX Integer32 (1.. 65535) 
        MAX-ACCESS read-only 
        STATUS     current 
        DESCRIPTION 
        "ippmMetricIndex defines an unambiguous index for each 
        standardized metric. Its value is the value of the node of the 
        metric in the IPPM-MIB metrics registry ippmMib.metrics.rfc. 
        Each metric registered in the standard registry must be present 
        in this table. 
        This index is used to identify the metric performed among the 
        IPPM-MIB entities involved in the measure. 
        Example: 
        The index of the metric onewayPacketLossAverage which is 
        registered as ippmMib.metrics.rfc.onewayPacketLossAverage will 
        always have the value 14." 
        ::= { ippmMetricEntry 1 } 
    
         
   ippmMetricCapabilities OBJECT-TYPE 
        SYNTAX INTEGER { 
                notImplemented(0), 
                implemented(1) 
        } 
        MAX-ACCESS read-only 
        STATUS     current 
        DESCRIPTION 
                "notImplemented 
                        the metric is not implemented. 
                implemented 
                        the metric is implemented." 
        DEFVAL { implemented } 
        ::= { ippmMetricEntry 2 } 
    
   ippmMetricUnit OBJECT-TYPE 
        SYNTAX INTEGER { 
                noUnit(0), 
                second(1), 
                ms(2), 
                us(3), 
                ns(4), 
                percentage(5), 
                packets(6), 
                byte(6), 
                kbyte(7), 
                megabyte(8) 
        } 
        MAX-ACCESS read-only 
        STATUS     current 
        DESCRIPTION 
                "The unit used in the current entity for the results of 
                the measure of this metric." 
        ::= { ippmMetricEntry 3 } 
    
   ippmMetricDescription OBJECT-TYPE 
        SYNTAX DisplayString 
        MAX-ACCESS read-only 
        STATUS     current 
        DESCRIPTION 
                "A textual description of the metric implementation." 
   ::= { ippmMetricEntry 4 } 
    
   ippmMetricMaxHistorySize OBJECT-TYPE 
        SYNTAX Integer32 
        MAX-ACCESS read-only 
        STATUS current 
        DESCRIPTION 
                "Specifies the maximal number of results that a metric 
   measure can save in the ippmHistoryTable." 
   ::= { ippmMetricEntry 5 } 
    
    
    
   -- 
   -- ippmMeasureTable 
   -- 
   --    
         
   ippmMeasureTable OBJECT-TYPE 
        SYNTAX     SEQUENCE OF IppmMeasureEntry 
        MAX-ACCESS not-accessible 
        STATUS     current 
        DESCRIPTION 
                "The table of all the IPPM measures which are running in 
                the device. They may not be active. 
                 
                a measure consists in a subset of metrics to compute. 
                The results of the measure may be  saved in the 
                ippmHistoryTable. The configuration of the measure sets 
                the size of the history requested in 
                ippmMeasureHystorySize. 
                 
                The maximal number of MIB objects to be collected in the 
                portion of ippmHistoryTable associated with this metric 
                depends the value of the ippmMetricMaxHistorySize. 
                The value of each metric ippmMeasureHystorySize must not 
                be over the value of ippmMetricMaxHistorySize 
                corresponding to this metric in ippmMetricTable. 
                 
                In reporting mode the entries of this table may be not 
                accessible. It means that the table is handle internally 
                by the measure software. 
                " 
        ::= { ippmMeasureGroup 2 }       
    
   ippmMeasureEntry OBJECT-TYPE 
        SYNTAX     IppmMeasureEntry 
        MAX-ACCESS not-accessible 
        STATUS     current 
        DESCRIPTION 
                "A SNMP entity wishing to create and activate a 
                measurement adds a new entry in the ippmMeasureTable. 
                 
                Typically the configuration operation set the values of 
                the conceptual row parameters using an  unused owner 
                index and sets the status of the row to createAndGo.  
                 
                An SNMP error 'inconsistentValue' is returned if the 
                owner index is out of range." 
        INDEX { ippmMeasureOwner, ippmMeasureIndex } 
        ::= { ippmMeasureTable 1 } 
    
   IppmMeasureEntry ::= 
        SEQUENCE { 
                ippmMeasureOwner                OwnerString, 
                ippmMeasureIndex                Integer32, 
                ippmMeasureName                 DisplayString, 
                ippmMeasureMetrics              IppmStandardMetrics, 
                ippmMeasureBeginTime            GMTDateAndTime,  
                ippmMeasureClockPeriodUnit      TimeUnit,        
                ippmMeasureClockPeriod          Integer32,       
                ippmMeasureDurationUnit         TimeUnit, 
                ippmMeasureDuration             Integer32,       
                ippmMeasureHystorySize          Integer32,       
                ippmMeasureStorageType          StorageType,     
                ippmMeasureStatus               RowStatus 
        } 
    
   ippmMeasureOwner OBJECT-TYPE 
        SYNTAX     OwnerString 
        MAX-ACCESS read-create 
        STATUS     current 
        DESCRIPTION 
                "The owner who has configured this entry." 
        DEFVAL { "acme" } 
        ::= { ippmMeasureEntry 1 } 
    
   ippmMeasureIndex OBJECT-TYPE 
        SYNTAX Integer32 (1.. 65535) 
        MAX-ACCESS read-create 
        STATUS     current 
        DESCRIPTION 
                "The owner index of the measure. The value is managed by 
                the owner. An SNMP error 'inconsistentValue' is returned 
                if this value is already in use by this owner." 
        ::= { ippmMeasureEntry 2 } 
    
   ippmMeasureName OBJECT-TYPE 
        SYNTAX DisplayString 
        MAX-ACCESS read-create 
        STATUS     current 
        DESCRIPTION 
                "The name of the instance of the metric. It illustrates 
                the specificity of the metric and includes the metric 
                and the typeP. 
                 
                example: IP-port-HTTP-connectivity" 
        ::= { ippmMeasureEntry 3 } 
    
    
 
   ippmMeasureMetrics OBJECT-TYPE 
        SYNTAX IppmStandardMetrics 
        MAX-ACCESS read-create 
        STATUS     current 
        DESCRIPTION 
                "Defines the metrics to compute within this measure. A 
                measure may be configured for the result of different 
                metrics singletons to be archive in the 
                ippmHistoryTable. The ippmMetricIndex of the created 
                result has the value of the bit index of the 
                corresponding ippmMeasureMetrics as explained above in 
                the ippmMetricIndex definition. 
                 
                Example: 
                A measure asking for One-way-Delay(6) and One-way-
                Packet-Loss(12) generated a flow of singletons which are 
                logged in the ippmHistoryTable. The singletons created 
                for the One-way-Delay measure have a value of 
                ippmMetricIndex of 6 while the created singletons for 
                the One-way-Packet-Loss measure have a value of 
                ippmMetricIndex of 12." 
           DEFVAL { { one-way-Delay, one-way-Packet-Loss } } 
        ::= { ippmMeasureEntry 4 } 

   ippmMeasureBeginTime OBJECT-TYPE 
        SYNTAX GMTDateAndTime 
        MAX-ACCESS read-create 
        STATUS     current 
        DESCRIPTION 
                "Specifies the time at which the measure starts." 
        ::= { ippmMeasureEntry 5 } 
                                 
    
   ippmMeasureClockPeriodUnit OBJECT-TYPE 
        SYNTAX TimeUnit 
        MAX-ACCESS read-create 
        STATUS     current 
        DESCRIPTION 
                "Specifies the unit of the measure period." 
        DEFVAL { second } 
        ::= { ippmMeasureEntry 6 } 
    
   ippmMeasureClockPeriod OBJECT-TYPE 
        SYNTAX     Integer32 
        MAX-ACCESS read-create 
        STATUS     current 
        DESCRIPTION 
                "Specifies the among of time between 2 sampling 
                intervals.  
                 
                Notes:  
                This interval generates a flow of periodical instants 
                which may be transformed as a flow of unpredictable 
                instants of measure by the 
                ippmNetworkMeasureClockPattern." 
        DEFVAL { 60 }  
        ::= { ippmMeasureEntry 7 } 
    
    
   ippmMeasureDurationUnit OBJECT-TYPE 
        SYNTAX TimeUnit 
    
        MAX-ACCESS read-create 
        STATUS     current 
        DESCRIPTION 
                "Specifies the unit of the measure duration." 
        DEFVAL { second } 
        ::= { ippmMeasureEntry 8 } 
    
   ippmMeasureDuration OBJECT-TYPE 
        SYNTAX     Integer32 
        MAX-ACCESS read-create 
        STATUS     current 
        DESCRIPTION 
                "Specifies the duration of the measure." 

        DEFVAL { 120 } 
        ::= { ippmMeasureEntry 9 } 
    
   ippmMeasureHystorySize OBJECT-TYPE 
        SYNTAX     Integer32 
        MAX-ACCESS read-create 
        STATUS     current 
        DESCRIPTION 
                "Specifies the maximum number of results saved for each 
                metric of this measure. The history of each metric is 
                managed as a circular table. The newest result overwrite 
                the oldest one when the history granted to this metric 
                measure is full. 
                 
                The management of the results may be optimized if 
                synchronized with the reports steps of this measure.  
                " 
        DEFVAL { 120 } 
        ::= { ippmMeasureEntry 10 } 
    
   ippmMeasureStorageType OBJECT-TYPE 
        SYNTAX     StorageType 
          MAX-ACCESS  read-create 
          STATUS      current 
          DESCRIPTION 
           "This object defines whether this row and the measure 
            controlled by this row are kept in volatile storage and 
            lost upon reboot or if this row is backed up by 
            non-volatile or permanent storage. 
             Possible values are: other(1), volatile(2), nonVolatile(3), 
        permanent(4), readOnly(5)" 
        DEFVAL { nonVolatile } 
        ::= { ippmMeasureEntry 11 } 
 
 
   ippmMeasureStatus OBJECT-TYPE 
        SYNTAX     RowStatus 
        MAX-ACCESS read-create 
        STATUS     current 
        DESCRIPTION 
                "The status of this table entry. Once the entry status 
                is set to active, the associate entry cannot be 
                modified." 
        DEFVAL { createAndGo }  
        ::= { ippmMeasureEntry 12 } 
    
   --  
   -- ippmHistoryGroup 
   --  
   --  
   -- 
   -- ippmHistoryTable 
   -- 
    
    
   ippmHistoryTable OBJECT-TYPE 
        SYNTAX     SEQUENCE OF IppmHistoryEntry 
        MAX-ACCESS not-accessible 
        STATUS     current 
        DESCRIPTION 
                "The table of the results of the measures." 
    
        ::= { ippmHistoryGroup 1 } 
    
    
    
   ippmHistoryEntry OBJECT-TYPE 
        SYNTAX     IppmHistoryEntry 
        MAX-ACCESS not-accessible 
        STATUS     current 
        DESCRIPTION 
         
                "An ippmHistoryEntry entry is one of the result of an 
                measure identified by the index members ippmMeasureOwner 
                and ippmMeasureIndex. 
                 
                In the index : 
                         
                        + ippmMeasureOwner and ippmMeasureIndex identify 
                the ippmMeasureEntry on whose behalf this entry was 
                created; 
                        + ippmMetricIndex identifies the ippmMetricEntry 
                of the metric to measure; 
                        + ippmLogTimeMark value is the absolute time 
                when the result of the metric was measured.  
                 
                The ippmHistoryTimeMark value is the absolute time when 
                the ippmHistoryValue was performed. 
                 
                IppmHistoryValue is the value of the metric measured at 
                the time ippmHistoryTimeMark. 
                 
                Example:  
                A one way delay measure is created by the entity 'acme' 
                using the owner index 1 and setting the 6th bit 
                (corresponding to One-way-Delay) of ippmMeasureMetrics 
                to 1. 
                Consider that the result of the one way delay measured 
                for acme on the day 15 of June at 8h20mn 10s 10ms is 23. 
                The result is identified as the singleton 
                ippmHistoryValue.acme.1.6.0106150820100100 and stored 
                with value 23. 
                 
                Its value may be retrieved using a get-
                next(ippmHistoryValue.acme.1.6.0106150820100099) which 
                returns (ippmHistoryValue.acme.1.6.0106150820100100 == 
                23). The ippmMetricIndex value of '6' corresponds to the 
                6th metric of ippmMetricTable which is Type-P-One-way-
                Delay.  
                " 
        INDEX { ippmMeasureOwner, ippmMeasureIndex, ippmMetricIndex, 
   ippmHistoryTimeMark }  
        ::= { ippmHistoryTable 1 } 
    
   IppmHistoryEntry ::= 
        SEQUENCE { 
                ippmHistoryTimeMark     GMTDateAndTime, 
                ippmHistoryValue        Integer32                
        } 
   ippmHistoryTimeMark OBJECT-TYPE 
        SYNTAX GMTDateAndTime 
        MAX-ACCESS read-only 
        STATUS     current 
        DESCRIPTION 
        "The instant of the measure of the result." 
        ::= { ippmHistoryEntry 1 } 
    
   ippmHistoryValue OBJECT-TYPE 
        SYNTAX Integer32 
        MAX-ACCESS read-only 
        STATUS     current 
        DESCRIPTION 
    
                "The value of the measure." 
        ::= { ippmHistoryEntry 2 } 
    
    
    
    
    
   -- 
   -- ippmNetworkMeasureGroup 
   -- 
    
    
   -- 
   -- 
   -- ippmNetworkMeasureTable 
   -- 
   --    
   ippmNetworkMeasureTable OBJECT-TYPE 
        SYNTAX     SEQUENCE OF IppmNetworkMeasureEntry 
        MAX-ACCESS not-accessible 
        STATUS     current 
        DESCRIPTION 
                "A entry is a measure which performs network measures 
                and provides a flow of results. 
                 
                This table extends the ippmMeasureTable. A network 
                measure is a specific measure. 
                 
                It performs several metrics measure per packet exchange. 
                Each step of a measure produces a singleton result per 
                metric. The time of the measure and the value of the 
                metric are saved in the ippmHistoryTable." 
        ::= { ippmNetworkMeasureGroup 1 }        
         
   ippmNetworkMeasureEntry OBJECT-TYPE 
        SYNTAX     IppmNetworkMeasureEntry 
        MAX-ACCESS not-accessible 
        STATUS     current 
        DESCRIPTION 
                "A SNMP entity wishing to create and activate a network 
                measure adds a new entry in the ippmMeasureTable and in 
                IppmNetworkMeasureTable. 
                 
                Typically the configuration operation set both the 
                values of the new ippmMeasureEntry and of the new 
                IppmNetworkMeasureEntry and sets the status of the row 
                to createAndGo.  
                 
                An SNMP error 'inconsistentValue' is returned if the 
                index is out of range. 
                 
                The ippmMeasureMetrics is set to a list of metrics to be 
                computed from the same raw packet exchange. Each step of 
                measure delivers a singleton per chosen metric. Results 
                are timestamped and saved in the ippmHistoryTable." 
        INDEX { ippmMeasureOwner, ippmMeasureIndex } 
        ::= { ippmNetworkMeasureTable 1 } 
         
   IppmNetworkMeasureEntry ::= 
        SEQUENCE { 
                ippmNetworkMeasureSrcTypeP              TypeP, 
                ippmNetworkMeasureSrc                   OCTET STRING, 
                ippmNetworkMeasureDstTypeP              TypeP, 
                ippmNetworkMeasureDst                   OCTET STRING,    
                ippmNetworkMeasureClockPattern          OCTET STRING, 
                ippmNetworkMeasureTimeoutDelay          Integer32, 
                ippmNetworkMeasureL3PacketSize          Integer32, 
                ippmNetworkMeasureDataPattern           OCTET STRING 

        } 
    
   ippmNetworkMeasureSrcTypeP OBJECT-TYPE 
        SYNTAX TypeP 
        MAX-ACCESS read-create 
        STATUS     current 
        DESCRIPTION 
                "Defines the type P of the source address of the packets 
                sent by the measure." 
        DEFVAL { '04000080001000'H } -- ->ip: 4.0.0.8.0.1.0 
        ::= { ippmNetworkMeasureEntry 1 } 
                 
   ippmNetworkMeasureSrc OBJECT-TYPE 
        SYNTAX OCTET STRING 
        MAX-ACCESS read-create 
        STATUS     current 
        DESCRIPTION 
                "Specifies the address of the source of the measure. 
                 
                It is represented as an octet string with specific 
                semantics and length as identified by the 
                ippmNetworkMeasureSrcTypeP. 
                 
                For example, if the ippmNetworkMeasureSrcTypeP indicates 
                an encapsulation of 'ip', this object length is 4, 
                followed by the 4 octets of the IP address, in network 
                byte order." 
        DEFVAL { '04C0210415'H } -- -> ip: 192.33.4.21         
        ::= { ippmNetworkMeasureEntry 2} 
         
   ippmNetworkMeasureDstTypeP OBJECT-TYPE 
        SYNTAX TypeP 
        MAX-ACCESS read-create 
        STATUS     current 
        DESCRIPTION 
                "Defines the type P of the destination address of the 
   packets sent by the measure." 
        DEFVAL { '04000080001000'H } -- ->ip: 4.0.0.8.0.1.0 
        ::= { ippmNetworkMeasureEntry 3 } 
                 
   ippmNetworkMeasureDst OBJECT-TYPE 
        SYNTAX OCTET STRING 
        MAX-ACCESS read-create 
        STATUS     current 
        DESCRIPTION 
                "Specifies the address of the destination of the 
                measure. 
                 
                It is represented as an octet string with specific 
                semantics and length as identified by the 
                ippmNetworkMeasureDstTypeP. 
                For example, if the ippmNetworkMeasureDstTypeP indicates 
                an encapsulation of 'ip', this object length is 4, 
                followed by the 4 octets of the IP address, in network 
                byte order." 
        DEFVAL { '04C0220414'H } -- -> ip: 192.34.4.20         
        ::= { ippmNetworkMeasureEntry 4 } 
                 
   ippmNetworkMeasureClockPattern OBJECT-TYPE 
        SYNTAX OCTET STRING  
        MAX-ACCESS read-create 
        STATUS     current 
        DESCRIPTION 
                "This cyclic clock shapes the profile of the instants of 
                measurement according to an arbitrary distribution law. 
                The clock resolution is ippmMeasureClockPeriod. The bits 
                of the clock set to the value 1 determine the valid 
                instants of measurement. A measure is to be processed if 
                and only if the current bit value is 1.          
                This pseudo-random clock pattern allows the 
                configuration by the NMS of numerous kind of sampling 
                law such as periodic or Poisson." 
        DEFVAL { 11111111} -- 100% periodic 
        ::= { ippmNetworkMeasureEntry 5 } 
         
   ippmNetworkMeasureTimeoutDelay OBJECT-TYPE 
        SYNTAX     Integer32 
        MAX-ACCESS read-create 
        STATUS     current 
        -- UNITS        "Milliseconds" 
        DESCRIPTION 
                "Specifies the delay after which the packet is 
   considered lost." 
        DEFVAL { 1 } 
        ::= { ippmNetworkMeasureEntry 6 } 
    
   ippmNetworkMeasureL3PacketSize OBJECT-TYPE 
        SYNTAX     Integer32 
        MAX-ACCESS read-create 
        STATUS     current 
        DESCRIPTION 
                "Specifies the size of the packets send at the last 
                network layer in the sense of the TypeP definition." 
        DEFVAL { 64 } 
        ::= { ippmNetworkMeasureEntry 7 }        
    
   ippmNetworkMeasureDataPattern OBJECT-TYPE 
        SYNTAX     OCTET STRING 
        MAX-ACCESS read-create 
        STATUS     current 
        DESCRIPTION 
                "The current field defines the round robin pattern used 
                to fill the packet." 
        DEFVAL { 'FF'H } 
        ::= { ippmNetworkMeasureEntry 8 }                        
    
    
 
   -- 
   -- 
   -- ippmAggregatedMeasureGroup 
   -- 
   --    
   -- 
   -- 
   -- ippmAggregatedMeasureTable 
   -- 
   --    
         
   ippmAggregatedMeasureTable OBJECT-TYPE 
        SYNTAX     SEQUENCE OF IppmAggregatedMeasureEntry 
        MAX-ACCESS not-accessible 
        STATUS     current 
        DESCRIPTION 
                " This table extends the ippmMeasureTable. 
                A aggregated measure summarizes the results of previous 
                network or aggregated measures. The results may saved in 
                the ippmHistoryTable. 
                 
                Each step of the measure computation produces a 
                singleton result per metric." 
        ::= { ippmAggregatedMeasureGroup 1 }     
         
   ippmAggregatedMeasureEntry OBJECT-TYPE 
        SYNTAX     IppmAggregatedMeasureEntry 
        MAX-ACCESS not-accessible 
        STATUS     current 
        DESCRIPTION 
        "A SNMP entity wishing to create and activate a statistic 
        measure adds a new entry in the ippmMeasureTable and in 
        ippmAggregatedMeasureTable. 
         
        Typically the configuration operation sets both the values of 
        the new ippmMeasureEntry and of the new 
        IppmAggregatedMeasureEntry and sets the status of the row to 
        createAndGo.  
         
        The ippmMeasureMetrics defines the metric to compute. 
        The results of the measure to summarize are identified by 
        ippmAggregatedMeasureHistoryOwner, 
        IppmAggregatedMeasureHistoryOwnerIndex and 
        ippmAggregatedMeasureHistoryMetric 
        The aggregated task starts at ippmMeasureBeginTime and end after 
        ippmMeasureDuration. A aggregated result is performed and saved 
        in the ippmHistoryTable for each ippmMeasureClockPeriod.  
        " 
        INDEX { ippmMeasureOwner, ippmMeasureIndex } 
        ::= { ippmAggregatedMeasureTable 1 } 
         
    
   IppmAggregatedMeasureEntry ::= 
        SEQUENCE { 
                ippmAggregatedMeasureHistoryOwner       OwnerString, 
                ippmAggregatedMeasureHistoryOwnerIndex  Integer32, 
                ippmAggregatedMeasureHistoryMetric      Integer32 
        } 
         
    
   ippmAggregatedMeasureHistoryOwner OBJECT-TYPE 
        SYNTAX OwnerString 
        MAX-ACCESS read-create 
        STATUS     current 
        DESCRIPTION 
                "The owner of the measure to summarize. " 
        ::= { ippmAggregatedMeasureEntry 1 } 
                 
   ippmAggregatedMeasureHistoryOwnerIndex OBJECT-TYPE 
        SYNTAX Integer32 (1.. 65535) 
        MAX-ACCESS read-create 
        STATUS     current 
        DESCRIPTION 
                "The owner index of the measure to summarize. " 
        ::= { ippmAggregatedMeasureEntry 2 } 
                                 
   ippmAggregatedMeasureHistoryMetric OBJECT-TYPE 
        SYNTAX Integer32 
        MAX-ACCESS read-create 
        STATUS     current 
        DESCRIPTION 
                "The metric of the measure to summarize. " 
        ::= { ippmAggregatedMeasureEntry 3 } 
    
    
   --            
   -- ippmReportGroup 
   -- 
    
   -- 
   -- 
   -- ippmReportSetupTable 
   -- 
   --    
   ippmReportSetupTable OBJECT-TYPE 
        SYNTAX     SEQUENCE OF IppmReportSetupEntry 
        MAX-ACCESS not-accessible 
        STATUS     current 
        DESCRIPTION 
   "The ippmReportSetupTable is a list of definition of reports. It 
   defines the results of a network or aggregated measures which are to 
   report. A report is saved in the ippmReportTable or sent to an 
   application using a SNMP Trap, a SNMP inform PDU, an email or a SMS. 
   The reporting task is not a batch action processed at the end of the 
   measure. It is coupled with threshold detections and event filtering 
   to deliver application level events and data while preserving 
   scalability.  
    
   It extends the definition of a measure: the definition of an measure 
   may include the definition of a report." 
        ::= { ippmReportGroup 1 } 
         
   ippmReportSetupEntry OBJECT-TYPE 
        SYNTAX     IppmReportSetupEntry 
        MAX-ACCESS not-accessible 
        STATUS     current 
        DESCRIPTION 
   "The report applies on the results of the measure which is extended 
   by the current report definition. 
    
   Typically the creation or a report sets both the values of the new 
   measure and those of the new IppmReportSetupEntry. 
   The ippmReportSetupDefinition describes the data and the events to 
   include in the report. The definition consists in a list of tasks to 
   perform on the results of the measure." 
        INDEX { ippmMeasureOwner, ippmMeasureIndex } 
        ::= { ippmReportSetupTable 1 } 
         
   IppmReportSetupEntry ::= 
        SEQUENCE { 
                ippmReportSetupDefinition       IppmReportDefinition, 
                ippmReportSetupMetricThreshold   
        Integer32, 
                ippmReportSetupEventsDurationThreshold  Integer32, 
         
                ippmReportSetupNMS                      DisplayString 
        } 
                    
   ippmReportSetupDefinition OBJECT-TYPE 
        SYNTAX IppmReportDefinition 
        MAX-ACCESS read-create 
        STATUS     current 
        DESCRIPTION 
        "The description of the events and actions which participate to 
   the elaboration of the report. 
        Send the report using the type of message selected by the bits 8 
   to 12. The report consists in the results of the measure which have 
   been saved in the ippmReportTable. If the onEventSendReport(7) bit is 
   unset the report is not saved.  
         
        The message sent is a notification defined in the 
   ippmNotifications node. The notification sent depends on the step of 
   the measure: 
    
                + Singleton events are sent using the notification 
   ippmSingletonAlarm; 
                + Exceeded events duration are sent using the 
   notification ippmEventsDurationExceededAlarm; 
                + A report of a cycle of measure is sent using the 
   notification ippmCycleOfMeasureReport; 
                + A report of a complete measure is sent using the 
   notification ippmCompletedMeasureReport; 
                 
        Example 1: 
        The setup of an alarm to be sent to the owner in a SNMP Trap 
   each time the staircase crosses the metric threshold value of 5: 
    
                ippmReportSetupMetricThreshold 5 
                ippmReportSetupDefinition { 
                        onSingleton(1), 
                        reportOnlyUptoDownMetricResults(4), 
                        inSNMPTrapPDU(8) 
                } 
    
        Example 2: 
        The setup of a report to be sent to the owner in a SNMP 
   informRequestPDU per measure cycle. It reports the staircase values 
   corresponding to a metric threshold of 5: 
    
                ippmReportSetupMetricThreshold 5 
                ippmReportSetupDefinition { 
                        onMeasureCycle(2), 
                        reportOnlyUptoDownMetricResults(4), 
                        inInformRequestPDU(10), 
                        clearHistory(13) 
                } 
    
        Default report: 
        The default report provides the control protocol with an 
   implicit mechanism to forward the result of a cycle of measure to the 
   owner of the measure while deleting the results from the 
   ippmHistoryTable on reception of the response to the InformRequestPDU 
   : 
                ippmReportSetupDefinition { 
                        onMeasureCycle(2), 
                        inInformRequestPDU(10), 
                        clearHistory(13) 
                } 
        " 
        DEFVAL { { onMeasureCycle, inInformRequestPDU, clearHistory } }
        ::= { ippmReportSetupEntry 1 } 
    
   ippmReportSetupMetricThreshold OBJECT-TYPE 
        SYNTAX Integer32 
        MAX-ACCESS read-create 
        STATUS     current 
        DESCRIPTION 
        "An event is generated when the result of the measure exceeds 
   the value of ippmReportSetupMetricThreshold. 
        The threshold has the same unit as the metric. The metric unit 
   is recorded in the object ippmMetricsUnit of this metric entry in the 
   ippmMetricTable. 
        " 
        ::= { ippmReportSetupEntry 2 } 
    
   ippmReportSetupEventsDurationThreshold OBJECT-TYPE 
        SYNTAX Integer32 
       UNITS      "Seconds" 
        MAX-ACCESS read-create 
        STATUS     current 
        DESCRIPTION 
        "An event is generated when the duration of a serie of results 
   which are continuously over the metric threshold cross over the 
   duration of the ippmReportSetupEventsDurationThreshold. 
        " 
        DEFVAL { 15 } 
        ::= { ippmReportSetupEntry 3 } 
         
   ippmReportSetupNMS OBJECT-TYPE 
        SYNTAX DisplayString 
        MAX-ACCESS read-create 
        STATUS     current 
        DESCRIPTION 
        "The recipient of the report may be provided in the setup. By 
   default the recipient of the report is the owner of the measure. Its 
   addresses are recorded in the ippmOwnersTable.        
        " 
        ::= { ippmReportSetupEntry 4 }   
         
         
   -- 
   -- ippmReportTable 
   -- 
   ippmReportTable OBJECT-TYPE 
        SYNTAX     SEQUENCE OF IppmReportEntry 
        MAX-ACCESS not-accessible 
        STATUS     current 
        DESCRIPTION 
                "The ippmReportTable logs the results of the reports. 
   The results consist in a subset of the results of a measure as 
   described in the report definition. The activation of a up and down 
   filtering in the report definition limits the results logged to those 
   corresponding to major events. 
                Excepted these points the ippmReportTable is identical 
   to the ippmHistoryTable. 
                " 
    
        ::= { ippmReportGroup 2 } 
    
    
   ippmReportEntry OBJECT-TYPE 
        SYNTAX     IppmReportEntry 
        MAX-ACCESS not-accessible 
        STATUS     current 
        DESCRIPTION 
   "A report is a list of results of a measure. This sample is 
   associated with the ippmReportSetupEntry which has set up the report. 
   An ippmReportEntry entry is one of the results of an measure to 
   report. The measure and the report definition are identified by the 
   index members ippmMeasureOwner and ippmMeasureIndex.  
    
   in the index : 
         
        + ippmMeasureOwner and ippmMeasureIndex identify the 
   ippmMeasureEntry and the ippmReportSetupEntry on whose behalf this 
   report was created; 
        + ippmMetricIndex identifies the ippmMetricEntry of the metric 
   measured; 
        + ippmReportTimeMark value is the absolute time when the value 
   of the metric was measured.  
         
         
        The ippmReportTimeMark value is the absolute time when the 
   ippmHistoryValue was performed. 
        IppmHistoryValue is the value of the metric measured at the time 
   ippmReportTimeMark. 
        " 
        INDEX { ippmMeasureOwner, ippmMeasureIndex, ippmMetricIndex, 
   ippmReportTimeMark }  
        ::= { ippmReportTable 1 } 
    
   IppmReportEntry ::= 
        SEQUENCE { 
                ippmReportTimeMark      GMTDateAndTime, 
                ippmReportValue Integer32                
        } 
   ippmReportTimeMark OBJECT-TYPE 
        SYNTAX GMTDateAndTime 
        MAX-ACCESS read-only 
        STATUS     current 
        DESCRIPTION 
   "The instant of the measure of the result." 
        ::= { ippmReportEntry 1 } 
    
   ippmReportValue OBJECT-TYPE 
        SYNTAX Integer32 
        MAX-ACCESS read-only 
        STATUS     current 
        DESCRIPTION 
    
                "The value." 
        ::= { ippmReportEntry 2 } 
    
    
   --            
   -- ippmNotifications 
   -- 
    
    
    
    
    
   ippmSingletonAlarm    NOTIFICATION-TYPE 
        OBJECTS      { 
                ippmReportSetupDefinition, 
                ippmReportSetupMetricThreshold, 
                ippmMetricUnit, 
                ippmHistoryValue 
        } 
        STATUS       current 
        DESCRIPTION 
                "A notification sent because 2 contiguous results are on 
                opposite sides of the metric threshold value. 
                The index of the included ippmReportSetupMetricThreshold 
                object identifies 
                the ippmMeasureEntry and the ippmResultSetupEntry that 
                specified the threshold.  
                 
                The notification contains the instances of the 
                ippmReportValue object which raised the threshold. The 
                ippmHistoryTimeMark of the index identifies the time the 
                event occurs. 
                " 
        ::= { ippmNotifications 1 } 

   ippmEventsDurationExceededAlarm    NOTIFICATION-TYPE 
        OBJECTS      {  
                ippmReportSetupDefinition, 
                ippmReportSetupEventsDurationThreshold, 
                ippmMetricUnit, 
                ippmHistoryValue 
        } 
        STATUS       current 
        DESCRIPTION 
                "A notification sent when the duration of contiguous 
                raising ippmReportSetupMetricThreshold exceeds the 
                ippmReportSetupEventsDurationThreshold value. The index 
                of the included ippmReportSetupDefinition object 
                identifies 
                the ippmMeasureEntry and the ippmResultSetupEntry that 
                specified the report.  
                 
                The notification contains the instances of the 
                ippmReportValue objects saved in the ippmReportTable for 
                this report. The ippmHistoryTimeMark of the index 
                identifies the time theses measures results where 
                performed. 
                " 
        ::= { ippmNotifications 2 }          
    
    
   ippmCycleOfMeasureReport    NOTIFICATION-TYPE 
        OBJECTS      {  
                ippmReportSetupDefinition, 
                ippmMetricUnit, 
                ippmHistoryValue 
        } 
        STATUS       current 
        DESCRIPTION 
                "A notification sent when a measure cycle completes.  
                The index of the included ippmReportSetupDefinition 
                object identifies 
                the ippmMeasureEntry and the ippmResultSetupEntry that 
                specified the report.  
                 
                The notification contains the instances of the 
                ippmReportValue objects saved in the ippmReportTable for 
                this measure cycle. The ippmHistoryTimeMark of the index 
                identifies the time the measures where performed. 
                " 
   ::= { ippmNotifications 3 }       
    
    
   ippmCompletedMeasureReport    NOTIFICATION-TYPE 
        OBJECTS      {  
                ippmReportSetupDefinition, 
                ippmMetricUnit, 
                ippmHistoryValue 
        } 
        STATUS       current 
        DESCRIPTION 
                "A notification sent when a measure completes.  
                The index of the included ippmReportSetupDefinition 
                object identifies 
                the ippmMeasureEntry and the ippmResultSetupEntry that 
                specified the report.  
                 
                The notification contains the instances of the 
                ippmReportValue objects saved in the ippmReportTable for 
                this measure cycle. The ippmHistoryTimeMark of the index 
                identifies the time the measures where performed. 
                " 
        ::= { ippmNotifications 4 }          
    
    
    
   --            
   -- Compliance statements 
   -- 
    
   ippmCompliance         MODULE-COMPLIANCE 
        STATUS             current 
        DESCRIPTION 
                "The compliance statement for SNMP entities which 
                implement the IPPM MIB" 
        MODULE -- this module 
        MANDATORY-GROUPS { ippmSystemGroup, ippmMeasureGroup, 
   ippmNetworkMeasureGroup, ippmHistoryGroup } 
      ::= { ippmCompliances 1 } 
    
   END 

--  
-- 
--    "Copyright (C) The Internet Society (2001). All Rights Reserved. 
--     
--    This document and translations of it may be copied and furnished to 
--    others, and derivative works that comment on or otherwise explain it 
--    or assist its implementation may be prepared, copied, published and 
--    distributed, in whole or in part, without restriction of any kind, 
--    provided that the above copyright notice and this paragraph are 
--    included on all such copies and derivative works. However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE.
