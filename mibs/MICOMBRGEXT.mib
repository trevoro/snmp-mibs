--
-- Modified as per comments from Rajesh,S Dated: 05-24-96
-- MIB Version Dated: 05-31-96
--
-- MIB Revision : 1.0 dated 1-17-97
-- Change Desc. : None. 
--
-- MIB Revision : 1.1 dated 4-22-97
-- Added access privilages to capabilities field. - Sanjeev Gaur
-- 
-- MIB Revision : 1.2 dated 10-7-97
-- Change Desc. : Replaced MPA with 4400. - B. Jafari. 
-- 
-- *** RELEASE 3.0 ***
-- MIB Revision : 1.3 dated 6-25-98
-- Change Desc. : Removed and/or replaced "4400" with 
--				  "access device" wherever possible.
--				  Obsoleted counter reset table,
--				  mcmBrgPortCntrZeroTable, and objects
--				  mcmBrgStpCounterZero and 
--				  mcmBrgTpCounterZero. -A. Llanes
--
-- *** RELEASE 3.1 ***
-- MIB Revision : 1.4 dated 1-19-99
-- Change Desc. : Modify description of nvmBrgConfPortType object to indicate
--                the supported enumerations for clarification. Fixed under
--                SR10159671. -M.Ly
--
-- MIB Revision : 1.5 dated 2-08-99
-- Change Desc. : Modify description of (mcm/nvm)BrgEtFilterUpper and Lower Range 
--				  object to indicate the limit range of 0 to 65535. Fixed under
--                SR#10223168. -A.Llanes

    MICOMBRGEXT DEFINITIONS ::= BEGIN

    IMPORTS
	     micom-oscar 
		     FROM MICOM-OSCAR-MIB
             OBJECT-TYPE
                     FROM RFC-1212;



          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).


    --  This MIB module uses the extended OBJECT-TYPE macro as
    --  defined in [13]


    --  this is the MIB module for MICOM Bridge objects


   mcmBrg    OBJECT IDENTIFIER ::= { micom-oscar 6 }


 -- MICOM Bridge Parameters Group

 -- The implementation of this group is mandatory for all RLR systems. 
 -- This group consists of objects pertaining to the Bridge System
 -- parameters.

   mcmBrgGlobalParamGroup    OBJECT IDENTIFIER ::= { mcmBrg 1 }

mcmBrgIPBridged OBJECT-TYPE
	SYNTAX	INTEGER { bridged(1), routed(2) }
	ACCESS	read-only
	STATUS	mandatory
	DESCRIPTION
	  "NAME = ;
	   DESC = IP is being bridged or Routed.;
	   HELP = Is IP being Bridged or Routed?;
	   CAPABILITIES = NET_CFG, VPN_CFG;"
	::= { mcmBrgGlobalParamGroup 1 }

mcmBrgNumInterfaces OBJECT-TYPE
	SYNTAX	INTEGER
	ACCESS	read-only
	STATUS	mandatory
	DESCRIPTION
	  "NAME = ;
	   DESC = The number of ports(ethernet & wan) \
                  that the access device has.;
	   HELP = The number of ports this bridge has.;
	   CAPABILITIES = NET_CFG, VPN_CFG;"
	::= { mcmBrgGlobalParamGroup 2 }

mcmBrgSpanEnable OBJECT-TYPE
	SYNTAX	INTEGER { enabled(1), disabled(2) }
	ACCESS	read-only
	STATUS	mandatory
	DESCRIPTION
	  "NAME = ;
	   DESC = The current state of the Spanning \
                  tree Algorithm on the access device.;
	   HELP = Spanning-Tree Algorithm Enabled?;
	   CAPABILITIES = NET_CFG, VPN_CFG;"
	::= { mcmBrgGlobalParamGroup 3 }

 
mcmBrgSpoofEnable OBJECT-TYPE
        SYNTAX  INTEGER { enabled(1), disabled(2) }
        ACCESS  read-only
        STATUS  mandatory
        DESCRIPTION
          "NAME = ;
           DESC = IP-ARP spoofing -when enabled, access device \
                  intercepts most ARP bcasts and handle them locally \
                  to reduce the amount of bcast pkts fwded across WAN.;
           HELP = IP-ARP Spoofing Enabled?;
           CAPABILITIES = NET_CFG, VPN_CFG;"
        ::= { mcmBrgGlobalParamGroup 4 }
 

mcmBrgAgeTime OBJECT-TYPE
        SYNTAX  INTEGER (10..1000000)
        ACCESS  read-only
        STATUS  mandatory
        DESCRIPTION
          "NAME = ;
           DESC = Aging time for dynamically learned devices \
                  in forwarding Table.;
           HELP = The timeout period in seconds for aging \
                  out dynamically learned forwarding \
                  information. 802.1D-1990 recommends \
                  a default of 300 seconds. Mirror object \
                  of dot1dTpAgingTime.;
           CAPABILITIES = NET_CFG, VPN_CFG;"
        ::= { mcmBrgGlobalParamGroup 5 }



   mcmBrgMiscParamGroup    OBJECT IDENTIFIER ::= { mcmBrg 2 }

 

mcmBrgDebugEnable OBJECT-TYPE
	SYNTAX	INTEGER { enabled(1), disabled(2) }
	ACCESS	read-write
	STATUS	mandatory
	DESCRIPTION
	  "NAME = ;
	   DESC = The access device capability to generate controlled \
                  number of debugging messages to CLI for \
                  the purpose of debugging some bridge \
                  status.; 
	   HELP = Bridge Debugging Enabled?;
	   CAPABILITIES = NET_CFG, VPN_DISP;"
	::= { mcmBrgMiscParamGroup 1 }

mcmBrgSpanDebugEnable OBJECT-TYPE
	SYNTAX	INTEGER { enabled(1), disabled(2) }
	ACCESS	read-write
	STATUS	mandatory
	DESCRIPTION
	  "NAME = ;
	   DESC = The access device capability to debug spanning \
                  tree algorithm.;
	   HELP = Spanning-Tree Debugging Enabled?;
	   CAPABILITIES = NET_CFG, VPN_DISP;"
	::= { mcmBrgMiscParamGroup 2 }


mcmBrgSpoofCacheAge OBJECT-TYPE
        SYNTAX  INTEGER(60..1800)
	ACCESS	read-write
	STATUS	mandatory
	DESCRIPTION
	  "NAME = ;
	   DESC = The aging time for entries in the ARP Spoof\
                  cache table to specified by the cache timeout \
                  to make room for active entries.;
	   HELP = The Aging Time for the ARP Spoof Cache.;
	   CAPABILITIES = NET_CFG, VPN_CFG;"
	::= { mcmBrgMiscParamGroup 3 }

mcmBrgSpoofThresholdAge OBJECT-TYPE
        SYNTAX  INTEGER(10..120)
	ACCESS	read-write
	STATUS	mandatory
	DESCRIPTION
	  "NAME = ;
	   DESC = The Aging Time for the ARP Spoofcache Threshold \
                  in seconds.(60 .. 1800 sec).;
	   HELP = The Aging Time for the ARP Spoof Threshold.;
	   CAPABILITIES = NET_CFG, VPN_CFG;"
	::= { mcmBrgMiscParamGroup 4 }

mcmBrgSpoofThresholdCount OBJECT-TYPE
        SYNTAX  INTEGER(5..30)
	ACCESS	read-write
	STATUS	mandatory
	DESCRIPTION
	  "NAME = ;
	   DESC = The ARP Spoof Threshold count- allows \
                  the max number of consecutive outstanding \
                  ARP request per destination node.;
	   HELP = The ARP Spoof Threshold count.;
	   CAPABILITIES = NET_CFG, VPN_CFG;"
	::= { mcmBrgMiscParamGroup 5 }



	-- MICOM Bridge Port Config Table.

mcmBrgConfPortTable OBJECT-TYPE
              SYNTAX  SEQUENCE OF McmBrgConfPortEntry
              ACCESS  not-accessible
              STATUS  mandatory
	DESCRIPTION
	  "NAME = ;
	   DESC = A config Table that contains port-specific \
                  information for the access device Bridge \
				  Configuration information.;
	   HELP = ;
	   CAPABILITIES = NET_CFG, VPN_CFG;"
              ::= { mcmBrg 3 }

          mcmBrgConfPortEntry OBJECT-TYPE
              SYNTAX  McmBrgConfPortEntry
              ACCESS  not-accessible
              STATUS  mandatory
	DESCRIPTION
	  "NAME = ;
	   DESC = Configuration parameter information maintained by \
                  each Port that are being used by the access \ 
                  device.;
	   HELP = ;
	   CAPABILITIES = ;"
              INDEX   { mcmBrgConfPortIndex }
              ::= { mcmBrgConfPortTable 1 }

          McmBrgConfPortEntry ::=
              SEQUENCE {
                  mcmBrgConfPortIndex
                      INTEGER,
                  mcmBrgConfPortPPA
                      INTEGER,
                  mcmBrgConfPortType
                      INTEGER,
                  mcmBrgConfPortMacFilterFlag
                      INTEGER,
                  mcmBrgConfPortEtFilterFlag
                      INTEGER,
                  mcmBrgConfPortSapFilterFlag
                      INTEGER,
                  mcmBrgConfPortMacInclExcl
                      INTEGER,
                  mcmBrgConfPortEtInclExcl
                      INTEGER,
                  mcmBrgConfPortSapInclExcl
                      INTEGER
              }

mcmBrgConfPortIndex OBJECT-TYPE
	SYNTAX	INTEGER
	ACCESS	read-only
	STATUS	mandatory
	DESCRIPTION
	  "NAME = ;
	   DESC = The Port Index to which this entry pertains.;
	   HELP = ;
	   CAPABILITIES = ;"
	::= { mcmBrgConfPortEntry 1 }

mcmBrgConfPortPPA OBJECT-TYPE
	SYNTAX	INTEGER
	ACCESS	read-only
	STATUS	mandatory
	DESCRIPTION
	  "NAME = ;
	   DESC =  The Protocol Point of Access to which \
                  this entry pertains.;
	   HELP = ;
	   CAPABILITIES = ;"
	::= { mcmBrgConfPortEntry 2 }

mcmBrgConfPortType OBJECT-TYPE
	SYNTAX	INTEGER {
		ethernet(1),
		wan(2),
		frameRelay(3),
		internal(4)
	}
	ACCESS	read-only
	STATUS	mandatory
	DESCRIPTION
	  "NAME = ;
	   DESC = The Type of the interface this port \
                  is attached to.;
	   HELP = ;
	   CAPABILITIES = ;"
	::= { mcmBrgConfPortEntry 3 }


mcmBrgConfPortMacFilterFlag OBJECT-TYPE
	SYNTAX	INTEGER { enabled(1), disabled(2) }
	ACCESS	read-write
	STATUS	mandatory
	DESCRIPTION
	  "NAME = ;
	   DESC = When MAC address filtering is needed on a \
                  specific port, enable MAC filter Flag. \
                  Otherwise, disable the MAC Filetr Flag.;
	   HELP = Is MAC Filtering enabled?;
	   CAPABILITIES = ;"
	::= { mcmBrgConfPortEntry 4 }

mcmBrgConfPortEtFilterFlag OBJECT-TYPE
	SYNTAX	INTEGER { enabled(1), disabled(2) }
	ACCESS	read-write
	STATUS	mandatory
	DESCRIPTION
	  "NAME = ;
	   DESC = When E-type filtering is needed on a specific \
                  port, enable E-type filter Flag. Otherwise, \
                  disable E-type Filter Flag.;
	   HELP = Is E-type Filtering enabled?;
	   CAPABILITIES = ;"
	::= { mcmBrgConfPortEntry 5 }

mcmBrgConfPortSapFilterFlag OBJECT-TYPE
	SYNTAX	INTEGER { enabled(1), disabled(2) }
	ACCESS	read-write
	STATUS	mandatory
	DESCRIPTION
	  "NAME = ;
	   DESC = When SAP filtering is needed on a specific \
                  port, enable SAP filter flag. Otherwise, \
                  disable the SAP filter flag.;
	   HELP = Is SAP Filtering enabled?;
	   CAPABILITIES = ;"
	::= { mcmBrgConfPortEntry 6 }

mcmBrgConfPortMacInclExcl OBJECT-TYPE
	SYNTAX	INTEGER { inclusive(1), exclusive(2) }
	ACCESS	read-write
	STATUS	mandatory
	DESCRIPTION
	  "NAME = ;
	   DESC = If Inclusive MAC filtering is set, only \
                  addresses in the table are filtered/discarded.\
                  If Exclusive, allow only addresses in the \
                  table to be accepted/learned.;
	   HELP = Inclusive or Exclusive Mac Filtering?;
	   CAPABILITIES = ;"
	::= { mcmBrgConfPortEntry 7 }

mcmBrgConfPortEtInclExcl OBJECT-TYPE
	SYNTAX	INTEGER { inclusive(1), exclusive(2) }
	ACCESS	read-write
	STATUS	mandatory
	DESCRIPTION
	  "NAME = ;
	   DESC =  If Inclusive E-Type filtering is set, only \
                   E-Type in the table are filtered/discarded.\
                   If Exclusive, allow only E-Type in the \ 
                   table to be accepted/learned.;
	   HELP = Inclusive or Exclusive Et Filtering?;
	   CAPABILITIES = ;"
	::= { mcmBrgConfPortEntry 8 }

mcmBrgConfPortSapInclExcl OBJECT-TYPE
	SYNTAX	INTEGER { inclusive(1), exclusive(2) }
	ACCESS	read-write
	STATUS	mandatory
	DESCRIPTION
	  "NAME = ;
	   DESC = If Inclusive Sap Type filtering is set, only \
                  Sap Types in the Table are filtered/discarded. \
                  If Exclusive, allow only Sap Types in the \ 
                  table to be accepted/learned.;
	   HELP = Inclusive or Exclusive Sap Filtering?;
	   CAPABILITIES = ;"
	::= { mcmBrgConfPortEntry 9 }


	-- MICOM Bridge MAC Filter Table.

mcmBrgMacFilterTable OBJECT-TYPE
              SYNTAX  SEQUENCE OF McmBrgMacFilterEntry
              ACCESS  not-accessible
              STATUS  mandatory
	DESCRIPTION
	  "NAME = ;
	   DESC = A table that contains port-specific \
                  information for the access device MAC Filter \
                  info including the source & destination.;
	   HELP = ;
	   CAPABILITIES = NET_CFG, VPN_CFG;"
              ::= { mcmBrg 4 }

          mcmBrgMacFilterEntry OBJECT-TYPE
              SYNTAX  McmBrgMacFilterEntry
              ACCESS  not-accessible
              STATUS  mandatory
	DESCRIPTION
	  "NAME = ;
	   DESC = MAC Filter parameter information maintained by \
                  every port that the access device uses.;
	   HELP = ;
	   CAPABILITIES = ;"
              INDEX   { mcmBrgMacFilterPortIndex, mcmBrgMacFilterNumber }
              ::= { mcmBrgMacFilterTable 1 }

          McmBrgMacFilterEntry ::=
              SEQUENCE {
                  mcmBrgMacFilterPortIndex
                      INTEGER,
                  mcmBrgMacFilterNumber
                      INTEGER,
                  mcmBrgMacAddress
                      MacAddress,
                  mcmBrgMacType
                      INTEGER
	}



mcmBrgMacFilterPortIndex OBJECT-TYPE
        SYNTAX  INTEGER(1..16)
	ACCESS	read-write
	STATUS	mandatory
	DESCRIPTION
	  "NAME = ;
	   DESC = The Port Index particular to this entry.;
	   HELP = ;
	   CAPABILITIES = ;"
	::= { mcmBrgMacFilterEntry 1 }

mcmBrgMacFilterNumber OBJECT-TYPE
        SYNTAX  INTEGER(1..32)
        ACCESS  read-write
        STATUS  mandatory
        DESCRIPTION
          "NAME = ;
           DESC = The Filter number associated with the entry.;
           HELP = ;
           CAPABILITIES = ;"
        ::= { mcmBrgMacFilterEntry 2 }
 

mcmBrgMacAddress OBJECT-TYPE
	SYNTAX	MacAddress
	ACCESS	read-write
	STATUS	mandatory
	DESCRIPTION
	  "NAME = ;
	   DESC = The MAC address(HW address) that needs to be \
                  filtered.;
	   HELP = ;
	   CAPABILITIES = ;"
	::= { mcmBrgMacFilterEntry 3 }

mcmBrgMacType OBJECT-TYPE
	SYNTAX	INTEGER { 
		source(1),
		destination(2),
		invalid(3) 
	}
	ACCESS	read-write
	STATUS	mandatory
	DESCRIPTION
	  "NAME = ;
	   DESC = Filter based on source MAC address or \
                  destination MAC address.;
	   HELP = The type of the MAC Address. By setting \
		  it to invalid	one can invalidate the \
		  entry.;
	   CAPABILITIES = ;"
	::= { mcmBrgMacFilterEntry 4 }

	-- MICOM Bridge E-Type Filter Table.

mcmBrgEtFilterTable OBJECT-TYPE
              SYNTAX  SEQUENCE OF McmBrgEtFilterEntry
              ACCESS  not-accessible
              STATUS  mandatory
	DESCRIPTION
	  "NAME = ;
	   DESC = A table that contains port-specific \
                  information for the access device \
				  E-type Filter.;
	   HELP = 
	   CAPABILITIES = NET_CFG, VPN_CFG;"
              ::= { mcmBrg 5 }

          mcmBrgEtFilterEntry OBJECT-TYPE
              SYNTAX  McmBrgEtFilterEntry
              ACCESS  not-accessible
              STATUS  mandatory
	DESCRIPTION
	  "NAME = ;
	   DESC = A list of information maintained by \
                  each port about the access device \
				  E-type Filter parameters for that port.;
	   HELP = 
	   CAPABILITIES = ;"
              INDEX   { mcmBrgEtFilterPortIndex , mcmBrgEtFilterNumber }
              ::= { mcmBrgEtFilterTable 1 }

          McmBrgEtFilterEntry ::=
              SEQUENCE {
                  mcmBrgEtFilterPortIndex
                      INTEGER,
                  mcmBrgEtFilterNumber
                      INTEGER,
                  mcmBrgEtFilterStatus
                      INTEGER,
                  mcmBrgEtFilterEType
                      INTEGER,
                  mcmBrgEtFilterUpperRange
                      INTEGER,
                  mcmBrgEtFilterLowerRange
                      INTEGER
	}

mcmBrgEtFilterPortIndex OBJECT-TYPE
        SYNTAX  INTEGER(1..16) 
        ACCESS  read-write
        STATUS  mandatory
        DESCRIPTION
          "NAME = ;
           DESC = The port Index particular to this port.;
           HELP = ;
           CAPABILITIES = ;"
        ::= { mcmBrgEtFilterEntry 1 }
 


mcmBrgEtFilterNumber OBJECT-TYPE
        SYNTAX  INTEGER(1..32)
        ACCESS  read-write
        STATUS  mandatory
        DESCRIPTION
          "NAME = ;
           DESC =  The Filter number associated with the \
                   port Index.; 
           HELP = ;
           CAPABILITIES = ;"
        ::= { mcmBrgEtFilterEntry 2 }

mcmBrgEtFilterStatus OBJECT-TYPE
	SYNTAX	INTEGER { singular(1), range(2), invalid(3) }
	ACCESS	read-write
	STATUS	mandatory
	DESCRIPTION
	  "NAME = ;
	   DESC = An indication as to whether the filter \^M
               is specified as a single e-type or as a range of \
               as a range of e-types.; ;
	   HELP = 
           HELP = Setting the value tp invalid, has the effect of \
                  the entry,;
	   CAPABILITIES = ;"
	::= { mcmBrgEtFilterEntry 3 }

mcmBrgEtFilterEType OBJECT-TYPE
        SYNTAX  INTEGER (1536..65535)
	ACCESS	read-write
	STATUS	mandatory
	DESCRIPTION
	  "NAME = ;
	   DESC = The singular e-type to be filtered.;
           HELP = The value of this object is valid only \
		  if the mcmBrgEtFilterStatus (above) \
		  is singular.;
	   CAPABILITIES = ;"
	::= { mcmBrgEtFilterEntry 4 }

mcmBrgEtFilterUpperRange OBJECT-TYPE
	SYNTAX	INTEGER (1536..65535)
	ACCESS	read-write
	STATUS	mandatory
	DESCRIPTION
	  "NAME = ;
	   DESC = 
           DESC = The Upper Range of the E-type to be \
              filtered. Range is between  0 - 65535.; 
           HELP = This object is valid only if the \
                  mcmBrgEtFilterStatus (above) is range.;
	   CAPABILITIES = ;"
	::= { mcmBrgEtFilterEntry 5 }

mcmBrgEtFilterLowerRange OBJECT-TYPE
	SYNTAX	INTEGER (1536..65535)
	ACCESS	read-write
	STATUS	mandatory
	DESCRIPTION
	  "NAME = ;
	   DESC = The lower Range of the E-type to be \
                  filtered. Range is between 0 - 65535.;
           HELP = This object is valid only \
                  if the mcmBrgEtFilterStatus (above) \
                  is range.;
	   CAPABILITIES = ;"
	::= { mcmBrgEtFilterEntry 6 }


	-- MICOM Bridge SAP Filter Table.

mcmBrgSapFilterTable OBJECT-TYPE
              SYNTAX  SEQUENCE OF McmBrgSapFilterEntry
              ACCESS  not-accessible
              STATUS  mandatory
	DESCRIPTION
	  "NAME = ;
	   DESC = A table that contains port-specific \
                  information for the access device E-type \
                  Filter information. (Operational);
       HELP = ;
	   CAPABILITIES = NET_CFG, VPN_CFG;"
              ::= { mcmBrg 6 }

          mcmBrgSapFilterEntry OBJECT-TYPE
              SYNTAX  McmBrgSapFilterEntry
              ACCESS  not-accessible
              STATUS  mandatory
	DESCRIPTION
	  "NAME = ;
	   DESC = A list of information maintained by \
                  every port about the access device E-type Filter \
                  parameters for that port. (Operational);
       HELP = ;
	   CAPABILITIES = ;"
              INDEX   { mcmBrgSapFilterPortIndex , mcmBrgSapFilterNumber }
              ::= { mcmBrgSapFilterTable 1 }

          McmBrgSapFilterEntry ::=
              SEQUENCE {
                  mcmBrgSapFilterPortIndex
                      INTEGER,
                  mcmBrgSapFilterNumber
                      INTEGER,
                  mcmBrgSapFilterStatus
                      INTEGER,
                  mcmBrgSapFilterEType
                      INTEGER,
                  mcmBrgSapFilterUpperRange
                      INTEGER,
                  mcmBrgSapFilterLowerRange
                      INTEGER
	}

 
mcmBrgSapFilterPortIndex OBJECT-TYPE
        SYNTAX  INTEGER(1..16)
        ACCESS  read-write
        STATUS  mandatory
        DESCRIPTION
          "NAME = ;
           DESC = ;
           HELP = The Port Index to which this entry pertains.;
           CAPABILITIES = ;"
        ::= { mcmBrgSapFilterEntry 1 }
 

mcmBrgSapFilterNumber OBJECT-TYPE
        SYNTAX  INTEGER(1..32)
        ACCESS  read-write
        STATUS  mandatory
        DESCRIPTION
          "NAME = ;
           DESC = The Filter number associated with the \
                  port Index.;
           HELP = ;
           CAPABILITIES = ;"
        ::= { mcmBrgSapFilterEntry 2 }
 

mcmBrgSapFilterStatus OBJECT-TYPE
	SYNTAX	INTEGER { singular(1), range(2), invalid(3) }
	ACCESS	read-write
	STATUS	mandatory
	DESCRIPTION
	  "NAME = ;
	   DESC = An indication as to whether the filter \
                  is specified as a single e-type or \
                  as a range of e-types.;
           HELP = Setting the value to invalid has the \
                  effect of deleteing the entry.;;
	   CAPABILITIES = ;"
	::= { mcmBrgSapFilterEntry 3 }

mcmBrgSapFilterEType OBJECT-TYPE
	SYNTAX	INTEGER(0..65535)
	ACCESS	read-write
	STATUS	mandatory
	DESCRIPTION
	  "NAME = ;
	   DESC = The singular e-type to be filtered.; 
           HELP = The value of this object is valid only \
                  if the mcmBrgSapFilterStatus (above) \
                  is singular.;
	   CAPABILITIES = ;"
	::= { mcmBrgSapFilterEntry 4 }

mcmBrgSapFilterUpperRange OBJECT-TYPE
	SYNTAX	INTEGER (0..65535)
	ACCESS	read-write
	STATUS	mandatory
	DESCRIPTION
	  "NAME = ;
	   DESC = The Upper Range of the E-type to be \
                  filtered.;
           HELP = This object is valid only if the \
                  mcmBrgSapFilterStatus (above) \
                  is range.;
	   CAPABILITIES = ;"
	::= { mcmBrgSapFilterEntry 5 }

mcmBrgSapFilterLowerRange OBJECT-TYPE
	SYNTAX	INTEGER (0..65535)
	ACCESS	read-write
	STATUS	mandatory
	DESCRIPTION
	  "NAME = ;
	   DESC = The lower Range of the E-type to be \
                  filtered.;
           HELP = This object is valid only if the \
                  mcmBrgSapFilterStatus (above) \
                  is range.;
	   CAPABILITIES = ;"
	::= { mcmBrgSapFilterEntry 6 }


   nvmBrgGlobalParamGroup    OBJECT IDENTIFIER ::= { mcmBrg 7 }

nvmBrgIPBridged OBJECT-TYPE
	SYNTAX	INTEGER { bridged(1), routed(2) }
	ACCESS	read-write
	STATUS	mandatory
	DESCRIPTION
	  "NAME = ;
	   DESC = IP is being bridged or Routed in the access device.;
           HELP = ;
	   CAPABILITIES = NET_CFG, VPN_CFG;"
	::= { nvmBrgGlobalParamGroup 1 }

nvmBrgNumInterfaces OBJECT-TYPE
	SYNTAX	INTEGER(1..16)
	ACCESS	read-write
	STATUS	mandatory
	DESCRIPTION
	  "NAME = ;
	   DESC = The number of ethernet and WAN ports that \
                  the access device has.;
           HELP = ;
	   CAPABILITIES = NET_CFG, VPN_CFG;"
	::= { nvmBrgGlobalParamGroup 2 }

nvmBrgSpanEnable OBJECT-TYPE
	SYNTAX	INTEGER { enabled(1), disabled(2) }
	ACCESS	read-write
	STATUS	mandatory
	DESCRIPTION
	  "NAME = ;
	   DESC = The current state of the Spanning \
                  tree Algorithm on the access device is enabled \
                  or disabled.;
           HELP = ;
	   CAPABILITIES = NET_CFG, VPN_CFG;"
	::= { nvmBrgGlobalParamGroup 3 }

nvmBrgSpoofEnable OBJECT-TYPE
	SYNTAX	INTEGER { enabled(1), disabled(2) }
	ACCESS	read-write
	STATUS	mandatory
	DESCRIPTION
	  "NAME = ;
	   DESC = IP-ARP spoofing -when enabled,access device intercepts\
                  most ARP bcasts and handle them locally to \
                  reduce the amount of bcast pkts fwded across WAN.;
           HELP = ;
	   CAPABILITIES = NET_CFG, VPN_CFG;"
	::= { nvmBrgGlobalParamGroup 4 }



nvmBrgAgeTime OBJECT-TYPE
        SYNTAX  INTEGER (10..1000000)
        ACCESS  read-write
        STATUS  mandatory
        DESCRIPTION
          "NAME = ;
           DESC = Aging time for dynamically learned devices \
                  in forwarding Table.; 
           HELP = The timeout period in seconds for aging \
                  out dynamically learned forwarding \
                  information. 802.1D-1990 recommends \
                  a default of 300 seconds. Mirror object \
                  of dot1dTpAgingTime.;
           CAPABILITIES = NET_CFG, VPN_CFG;"
        ::= { nvmBrgGlobalParamGroup 5 }


   nvmBrgMiscParamGroup    OBJECT IDENTIFIER ::= { mcmBrg 8 }






nvmBrgDebugEnable OBJECT-TYPE
	SYNTAX	INTEGER { enabled(1), disabled(2) }
	ACCESS	read-write
	STATUS	mandatory
	DESCRIPTION
	  "NAME = ;
	   DESC = The access device's capability to generate controlled \
                  number of debugging messages to CLI for \
                  the purpose of debugging some bridge \
                  status.;
           HELP = Bridge Debugging Enabled?;
	   CAPABILITIES = NET_CFG, VPN_DISP;"
	::= { nvmBrgMiscParamGroup 1 }

nvmBrgSpanDebugEnable OBJECT-TYPE
	SYNTAX	INTEGER { enabled(1), disabled(2) }
	ACCESS	read-write
	STATUS	mandatory
	DESCRIPTION
	  "NAME = ;
	   DESC = The access device's capability to debug spanning \
                  tree algorithm.;
           HELP = Spanning-Tree Debugging Enabled?;
	   CAPABILITIES = NET_CFG, VPN_DISP;"
	::= { nvmBrgMiscParamGroup 2 }

nvmBrgSpoofCacheAge OBJECT-TYPE
	SYNTAX	INTEGER(60..1800)
	ACCESS	read-write
	STATUS	mandatory
	DESCRIPTION
	  "NAME = ;
	   DESC = The aging time for entries in the ARP Spoof\
                  cache table to specified by the cache timeout \
                  to make room for active entries.;
           HELP = The Aging Time for the ARP Spoof Cache.;
	   CAPABILITIES = NET_CFG, VPN_CFG;"
	::= { nvmBrgMiscParamGroup 3 }

nvmBrgSpoofThresholdAge OBJECT-TYPE
	SYNTAX	INTEGER(10..120)
	ACCESS	read-write
	STATUS	mandatory
	DESCRIPTION
	  "NAME = ;
	   DESC = The Aging Time for the ARP Spoofcache Threshold \
                      in seconds.(60 .. 1800 sec);
           HELP = The Aging Time for the ARP Spoof Threshold.;
	   CAPABILITIES = NET_CFG, VPN_CFG;"
	::= { nvmBrgMiscParamGroup 4 }

nvmBrgSpoofThresholdCount OBJECT-TYPE
	SYNTAX	INTEGER(5..30)
	ACCESS	read-write
	STATUS	mandatory
	DESCRIPTION
	  "NAME = ;
	   DESC = The ARP Spoof Threshold count- allows \
                  the max number of consecutive outstanding \
                  ARP request per dest node.;
           HELP = The ARP Spoof Threshold count.;
	   CAPABILITIES = NET_CFG, VPN_CFG;"
	::= { nvmBrgMiscParamGroup 5 }


   nvmBrgStpParamGroup    OBJECT IDENTIFIER ::= { mcmBrg 9 }

nvmBrgPriority OBJECT-TYPE
	SYNTAX	INTEGER (0..65535)
	ACCESS	read-write
	STATUS	mandatory
	DESCRIPTION
	  "NAME = ;
	   DESC = The value of the write-able portion \
                  of the Bridge ID, i.e., the first two \
                  octets of the (8 octet long) Bridge ID.; 
           HELP = The other (last) 6 octets of the \
                  Bridge ID are given by the value of \
                  dot1dBaseBridgeAddress. This is Mirror \
                  object to dot1dStpPriority.;
	   CAPABILITIES = NET_CFG, VPN_CFG;"
	::= { nvmBrgStpParamGroup 1 }

nvmBrgMaxAge OBJECT-TYPE
	SYNTAX	Timeout (600..4000)
	ACCESS	read-write
	STATUS	mandatory
	DESCRIPTION
	  "NAME = ;
	   DESC = The maximum age of Spanning Tree Protocol \
		  information learned from the network \
		  on any port before it is discarded, \
		  in units of hundredths of a second.; 
           HELP = This is the programmed value of the \
		  dot1dStpBridgeMaxAge.;
	   CAPABILITIES = NET_CFG, VPN_CFG;"
	::= { nvmBrgStpParamGroup 2 }

nvmBrgFwdDelay OBJECT-TYPE
	SYNTAX	Timeout (400..3000)
	ACCESS	read-write
	STATUS	mandatory
	DESCRIPTION
	  "NAME = ;
	   DESC = The value that all bridges use for \
                  ForwardDelay when this bridge is \
                  acting as the root.;
           HELP = Note that 802.1D-1990 specifies that \
                  the range for this parameter is related \
                  to the value of dot1dStpBridgeMaxAge. \
                  The granularity of this timer is specified \
                  by 802.1D-1990 to be 1 second. An agent \
                  may return a badValue error if a set \
                  is attempted to a value which is not \
                  a whole number of seconds. Mirror object \
                  of dot1dStpBridgeForwardDelay;
	   CAPABILITIES = NET_CFG, VPN_CFG;"
	::= { nvmBrgStpParamGroup  3 }

nvmBrgHelloTime OBJECT-TYPE
	SYNTAX	Timeout (100..1000)
	ACCESS	read-write
	STATUS	mandatory
	DESCRIPTION
	  "NAME = ;
	   DESC = The value that all bridges use for HelloTime \
                  when this bridge is acting as the root.;
           HELP = The granularity of this timer is specified \
                  by 802.1D- 1990 to be 1 second.  An \
                  agent may return a badValue error if \
                  a set is attempted to a value which \
                  is not a whole number of seconds. Mirror \
                  object of dot1dStpBridgeHelloTime.;
	   CAPABILITIES = NET_CFG, VPN_CFG;"
	::= { nvmBrgStpParamGroup 4 }



	-- MICOM Bridge Port Config Table.

nvmBrgConfPortTable OBJECT-TYPE
              SYNTAX  SEQUENCE OF NvmBrgConfPortEntry
              ACCESS  not-accessible
              STATUS  mandatory
	DESCRIPTION
	  "NAME = ;
	   DESC = A config table that contains port-specific \
                  information for tha access device Bridge Configuration \
                  information.;
           HELP = A table that contains port-specific \
                  information for the access device Biidge Config \
                  information.;
	   CAPABILITIES = NET_CFG, VPN_CFG;"
              ::= { mcmBrg 10 }

          nvmBrgConfPortEntry OBJECT-TYPE
              SYNTAX  NvmBrgConfPortEntry
              ACCESS  not-accessible
              STATUS  mandatory
	DESCRIPTION
	  "NAME = ;
	   DESC = A list of information maintained by \
                  each Port that are being used by the access device, \
                  about conf. parameters for that port.;
	   HELP = ;
	   CAPABILITIES = ;"
              INDEX   { nvmBrgConfPortIndex }
              ::= { nvmBrgConfPortTable 1 }

          NvmBrgConfPortEntry ::=
              SEQUENCE {
                  nvmBrgConfPortIndex
                      INTEGER,
                  nvmBrgConfPortType
                      INTEGER,
                  nvmBrgConfPortEnable
                      INTEGER,
                  nvmBrgConfPortPriority
                      INTEGER,
                  nvmBrgConfPortPathCost
                      INTEGER,
                  nvmBrgConfPortMacFilterFlag
                      INTEGER,
                  nvmBrgConfPortEtFilterFlag
                      INTEGER,
                  nvmBrgConfPortSapFilterFlag
                      INTEGER,
                  nvmBrgConfPortMacInclExcl
                      INTEGER,
                  nvmBrgConfPortEtInclExcl
                      INTEGER,
                  nvmBrgConfPortSapInclExcl
                      INTEGER
              }

nvmBrgConfPortIndex OBJECT-TYPE
	SYNTAX	INTEGER(1..16)
	ACCESS	read-write
	STATUS	mandatory
	DESCRIPTION
	  "NAME = ;
	   DESC = The Port Index to which this entry pertains.;
	   HELP = ;
	   CAPABILITIES = ;"
	::= { nvmBrgConfPortEntry 1 }

nvmBrgConfPortType OBJECT-TYPE
        SYNTAX  INTEGER {
                ethernet(1),
                wan(2),
                frameRelay(3),
                internal(4)
        }
        ACCESS  read-write
        STATUS  mandatory
        DESCRIPTION
          "NAME = ;
           DESC = The Type of the interface this port \
                  is attached to. \
	          This object only supported enumerations of \
                  ethernet and frameRelay.;
           HELP = ;
           CAPABILITIES = ;"
        ::= { nvmBrgConfPortEntry 2 }
          
nvmBrgConfPortEnable OBJECT-TYPE
	SYNTAX	INTEGER { enabled(1), disabled(2), invalid(3) }
	ACCESS	read-write
	STATUS	mandatory
	DESCRIPTION
	  "NAME = ;
	   DESC = The status of the Port is enabled/disabled.;
	   HELP = Mirror object of dot1dStpPortEnable.;
	   CAPABILITIES = ;"
	::= { nvmBrgConfPortEntry 3 }

nvmBrgConfPortPriority OBJECT-TYPE
        SYNTAX  INTEGER (0..255)
        ACCESS  read-write
        STATUS  mandatory
        DESCRIPTION
          "NAME = ;
           DESC = The value of the priority field which \
                  is contained in the first (in network \
                  byte order) octet of the port ID.;
           HELP = It's the mirror object of dot1dStpPortPriority.;
           CAPABILITIES = ;"
        ::= { nvmBrgConfPortEntry 4 }
 
nvmBrgConfPortPathCost OBJECT-TYPE
        SYNTAX  INTEGER (1..65535)
        ACCESS  read-write
        STATUS  mandatory
        DESCRIPTION
          "NAME = ;
           DESC = The contribution of this port to the \
                  path cost of paths towards the spanning \
                  tree root which include this port.;
           HELP = 802.1D-1990 recommends that the default \
                  value of this parameter be in inverse \
                  proportion to the speed of the attached \
                  LAN. Mirror object of dot1dStpPortPathCost.;
           CAPABILITIES = ;"
        ::= { nvmBrgConfPortEntry 5 }
        

nvmBrgConfPortMacFilterFlag OBJECT-TYPE
	SYNTAX	INTEGER { enabled(1), disabled(2) }
	ACCESS	read-write
	STATUS	mandatory
	DESCRIPTION
	  "NAME = ;
	   DESC = When MAC address filtering is needed on a \
                  specific port, enable MAC filter Flag. Otherwise, \
                  disable the MAC Filetr Flag.;
           HELP = Is MAC Filtering enabled?;
	   CAPABILITIES = ;"
	::= { nvmBrgConfPortEntry 6 }

nvmBrgConfPortEtFilterFlag OBJECT-TYPE
	SYNTAX	INTEGER { enabled(1), disabled(2) }
	ACCESS	read-write
	STATUS	mandatory
	DESCRIPTION
	  "NAME = ;
	   DESC = When E-type filtering is needed on a specific \
                  port, enable E-type filter Flag. Otherwise,When \
                  disable E-type Filter Flag.;
           HELP = Is E-type Filtering enabled?;
	   CAPABILITIES = ;"
	::= { nvmBrgConfPortEntry 7 }

nvmBrgConfPortSapFilterFlag OBJECT-TYPE
	SYNTAX	INTEGER { enabled(1), disabled(2) }
	ACCESS	read-write
	STATUS	mandatory
	DESCRIPTION
	  "NAME = ;
	   DESC = When SAP filtering is needed on a specific \
                  port, enable SAP filter flag. Otherwise, \
                  disable the SAP filter flag.;
           HELP = Is SAP Filtering enabled?;
	   CAPABILITIES = ;"
	::= { nvmBrgConfPortEntry 8 }


nvmBrgConfPortMacInclExcl OBJECT-TYPE
        SYNTAX  INTEGER { inclusive(1), exclusive(2) }
        ACCESS  read-write
        STATUS  mandatory
        DESCRIPTION
          "NAME = ;
           DESC = ;
           HELP = Inclusive or Exclusive Mac Filtering?;
           CAPABILITIES = ;"
        ::= { nvmBrgConfPortEntry 9 }


nvmBrgConfPortEtInclExcl OBJECT-TYPE
	SYNTAX	INTEGER { inclusive(1), exclusive(2) }
	ACCESS	read-write
	STATUS	mandatory
	DESCRIPTION
	  "NAME = ;
	   DESC = ;
	   HELP = Inclusive or Exclusive Et Filtering?;
	   CAPABILITIES = ;"
	::= { nvmBrgConfPortEntry 10 }

nvmBrgConfPortSapInclExcl OBJECT-TYPE
	SYNTAX	INTEGER { inclusive(1), exclusive(2) }
	ACCESS	read-write
	STATUS	mandatory
	DESCRIPTION
	  "NAME = ;
	   DESC = ;
	   HELP = Inclusive or Exclusive Sap Filtering?;
	   CAPABILITIES = ;"
	::= { nvmBrgConfPortEntry 11 }


	-- MICOM Bridge MAC Filter Table.

nvmBrgMacFilterTable OBJECT-TYPE
              SYNTAX  SEQUENCE OF NvmBrgMacFilterEntry
              ACCESS  not-accessible
              STATUS  mandatory
	DESCRIPTION
	  "NAME = ;
	   DESC = ;
	   HELP = A table that contains port-specific \
		  information for the access device MAC Filter \
		  information.;
	   CAPABILITIES = NET_CFG, VPN_CFG;"
              ::= { mcmBrg 11 }

          nvmBrgMacFilterEntry OBJECT-TYPE
              SYNTAX  NvmBrgMacFilterEntry
              ACCESS  not-accessible
              STATUS  mandatory
	DESCRIPTION
	  "NAME = ;
	   DESC = ;
	   HELP = A list of information maintained by \
		  every port about the access device MAC Filter \
		  parameters for that port.;
	   CAPABILITIES = ;"
              INDEX   { nvmBrgMacFilterPortIndex , nvmBrgMacFilterNumber}
              ::= { nvmBrgMacFilterTable 1 }

          NvmBrgMacFilterEntry ::=
              SEQUENCE {
                  nvmBrgMacFilterPortIndex
                      INTEGER,
                  nvmBrgMacFilterNumber
                      INTEGER,
                  nvmBrgMacAddress
                      MacAddress,
                  nvmBrgMacType
                      INTEGER
	}

                                       
nvmBrgMacFilterPortIndex OBJECT-TYPE
        SYNTAX  INTEGER(1..16)
        ACCESS  read-only
        STATUS  mandatory
        DESCRIPTION
          "NAME = ;
           DESC = ;
           HELP = The Port Index to which this entry pertains.;
           CAPABILITIES = ;"
        ::= { nvmBrgMacFilterEntry 1 }

 
nvmBrgMacFilterNumber OBJECT-TYPE
        SYNTAX  INTEGER(1..32)
        ACCESS  read-only
        STATUS  mandatory
        DESCRIPTION
          "NAME = ;
           DESC = ;
           HELP = The Port Index to which this entry pertains.;
           CAPABILITIES = ;"
        ::= { nvmBrgMacFilterEntry 2 }
 

nvmBrgMacAddress OBJECT-TYPE
	SYNTAX	MacAddress
	ACCESS	read-only
	STATUS	mandatory
	DESCRIPTION
	  "NAME = ;
	   DESC = ;
	   HELP = The MAC Address which needs to be filtered.;
	   CAPABILITIES = ;"
	::= { nvmBrgMacFilterEntry 3 }

nvmBrgMacType OBJECT-TYPE
        SYNTAX  INTEGER {
                source(1),
                destination(2),
                invalid(3)
        }
	ACCESS	read-only
	STATUS	mandatory
	DESCRIPTION
	  "NAME = ;
	   DESC = ;
	   HELP = The type of the MAC Address. By setting \
		  it to invalid	one can invalidate the \
		  entry.;
	   CAPABILITIES = ;"
	::= { nvmBrgMacFilterEntry 4 }

	-- MICOM Bridge E-Type Filter Table.

nvmBrgEtFilterTable OBJECT-TYPE
              SYNTAX  SEQUENCE OF NvmBrgEtFilterEntry
              ACCESS  not-accessible
              STATUS  mandatory
	DESCRIPTION
	  "NAME = ;
	   DESC =  DESC = A table that contains port-specific \
                  information for the access device E-type Filter.;
           HELP = ;
	   CAPABILITIES = NET_CFG, VPN_CFG;"
              ::= { mcmBrg 12 }

          nvmBrgEtFilterEntry OBJECT-TYPE
              SYNTAX  NvmBrgEtFilterEntry
              ACCESS  not-accessible
              STATUS  mandatory
	DESCRIPTION
	  "NAME = ;
	   DESC = A list of information maintained by \
                  each port about the access device E-type Filter \
                  parameters for that port.;
	   Help = ;
           CAPABILITIES = ;"
              INDEX   { nvmBrgEtFilterPortIndex , nvmBrgEtFilterNumber}
              ::= { nvmBrgEtFilterTable 1 }

          NvmBrgEtFilterEntry ::=
              SEQUENCE {
                  nvmBrgEtFilterPortIndex
                      INTEGER,
                  nvmBrgEtFilterNumber
                      INTEGER,
                  nvmBrgEtFilterStatus
                      INTEGER,
                  nvmBrgEtFilterEType
                      INTEGER,
                  nvmBrgEtFilterUpperRange
                      INTEGER,
                  nvmBrgEtFilterLowerRange
                      INTEGER
	}


nvmBrgEtFilterPortIndex OBJECT-TYPE
	SYNTAX	INTEGER(1..16)
	ACCESS	read-only
	STATUS	mandatory
	DESCRIPTION
	  "NAME = ;
	   DESC = The port Index particular to this port.;
	   HELP = ;
	   CAPABILITIES = ;"
	::= { nvmBrgEtFilterEntry 1 }

nvmBrgEtFilterNumber OBJECT-TYPE
        SYNTAX  INTEGER(1..32)
        ACCESS  read-only
        STATUS  mandatory
        DESCRIPTION
          "NAME = ;
           DESC =  The Filter number associated with the \
                   port Index.;
           HELP = ;
           CAPABILITIES = ;"
        ::= { nvmBrgEtFilterEntry 2 }

          
nvmBrgEtFilterStatus OBJECT-TYPE
	SYNTAX	INTEGER { singular(1), range(2), invalid(3) }
	ACCESS	read-only
	STATUS	mandatory
	DESCRIPTION
	  "NAME = ;
	   DESC = An indication as to whether the filter \
                  is specified as a single e-type or \
                  as a range of e-types.; 
           HELP = Setting the value to invalid has the \
                  the effect of deleting the entry.;
	   CAPABILITIES = ;"
	::= { nvmBrgEtFilterEntry 3 }

nvmBrgEtFilterEType OBJECT-TYPE
	SYNTAX	INTEGER(1536..65535)
	ACCESS	read-only
	STATUS	mandatory
	DESCRIPTION
	  "NAME = ;
	   DESC = The singular e-type to be filters.;
           HELP = The value of this object is valid only \
                  if the mcmBrgEtFilterStatus (above) \
                      is singular.;
	   CAPABILITIES = ;"
	::= { nvmBrgEtFilterEntry 4 }

nvmBrgEtFilterUpperRange OBJECT-TYPE
	SYNTAX	INTEGER (1536..65535)
	ACCESS	read-only
	STATUS	mandatory
	DESCRIPTION
	  "NAME = ;
	   DESC = The Upper Range of the E-type to be \
                  filtered. Range is between 0 - 65535.; 
           HELP = This object is valid only if the \
                  mcmBrgEtFilterStatus (above) is range.;
	   CAPABILITIES = ;"
	::= { nvmBrgEtFilterEntry 5 }

nvmBrgEtFilterLowerRange OBJECT-TYPE
	SYNTAX	INTEGER (1536..65535)
	ACCESS	read-only
	STATUS	mandatory
	DESCRIPTION
	  "NAME = ;
	   DESC = The lower Range of the E-type to be \
                  filtered. Range is between 0 - 65535.;
           HELP = This object is valid only \
                  if the mcmBrgEtFilterStatus (above) \
                  is range.;
	   CAPABILITIES = ;"
	::= { nvmBrgEtFilterEntry 6 }


	-- MICOM Bridge SAP Filter Table.

nvmBrgSapFilterTable OBJECT-TYPE
              SYNTAX  SEQUENCE OF NvmBrgSapFilterEntry
              ACCESS  not-accessible
              STATUS  mandatory
	DESCRIPTION
	  "NAME = ;
	   DESC = A table that contains port-specific \
                  information for the access device E-type \
                  Filter information.;
	   HELP = ;
	   CAPABILITIES = NET_CFG, VPN_CFG;"
              ::= { mcmBrg 13 }

          nvmBrgSapFilterEntry OBJECT-TYPE
              SYNTAX  NvmBrgSapFilterEntry
              ACCESS  not-accessible
              STATUS  mandatory
	DESCRIPTION
	  "NAME = ;
	   DESC = A list of information maintained by \
                  every port about the access device E-type Filter \
                  parameters for that port.;
	   HELP = ;
	   CAPABILITIES = ;"
              INDEX   { nvmBrgSapFilterPortIndex , nvmBrgSapFilterNumber}
              ::= { nvmBrgSapFilterTable 1 }

          NvmBrgSapFilterEntry ::=
              SEQUENCE {
                  nvmBrgSapFilterPortIndex
                      INTEGER,
                  nvmBrgSapFilterNumber
                      INTEGER,
                  nvmBrgSapFilterStatus
                      INTEGER,
                  nvmBrgSapFilterEType
                      INTEGER,
                  nvmBrgSapFilterUpperRange
                      INTEGER,
                  nvmBrgSapFilterLowerRange
                      INTEGER
	}

 
                                       
nvmBrgSapFilterPortIndex OBJECT-TYPE
        SYNTAX  INTEGER(1..16)
        ACCESS  read-write
        STATUS  mandatory
        DESCRIPTION
          "NAME = ;
           DESC = The Port Index to which this entry pertains.;
           HELP = ;
           CAPABILITIES = ;"
        ::= { nvmBrgSapFilterEntry 1 }
 

nvmBrgSapFilterNumber OBJECT-TYPE
        SYNTAX  INTEGER(1..32)
        ACCESS  read-write
        STATUS  mandatory
        DESCRIPTION
          "NAME = ;
           DESC = The Filter number associated with the \
                  port Index.;
           HELP = ;
           CAPABILITIES = ;"
        ::= { nvmBrgSapFilterEntry 2 }
 

nvmBrgSapFilterStatus OBJECT-TYPE
	SYNTAX	INTEGER { singular(1), range(2), invalid(3) }
	ACCESS	read-write
	STATUS	mandatory
	DESCRIPTION
	  "NAME = ;
	   DESC = An indication as to whether the filter \
                  is specified as a single e-type or \
                  as a range of e-types.;
           HELP = Setting the value to invalid has the \
                  effect of deleteing the entry.;
	   CAPABILITIES = ;"
	::= { nvmBrgSapFilterEntry 3 }

nvmBrgSapFilterEType OBJECT-TYPE
	SYNTAX	INTEGER(0..65535)
	ACCESS	read-write
	STATUS	mandatory
	DESCRIPTION
	  "NAME = ;
	   DESC = The singular e-type to be filtered. \
           HELP = The value of this object is valid only \
                  if the mcmBrgSapFilterStatus (above) \
                  is singular.;
	   CAPABILITIES = ;"
	::= { nvmBrgSapFilterEntry 4 }

nvmBrgSapFilterUpperRange OBJECT-TYPE
	SYNTAX	INTEGER (0..65535)
	ACCESS	read-write
	STATUS	mandatory
	DESCRIPTION
	  "NAME = ;
	   DESC = The Upper Range of the E-type to be \
                  filtered.;
           HELP = This object is valid only if the \
                  mcmBrgSapFilterStatus (above) \
                  is range.;
	   CAPABILITIES = ;"
	::= { nvmBrgSapFilterEntry 5 }

nvmBrgSapFilterLowerRange OBJECT-TYPE
	SYNTAX	INTEGER (0..65535)
	ACCESS	read-write
	STATUS	mandatory
	DESCRIPTION
	  "NAME = ;
	   DESC = The lower Range of the E-type to be \
                  filtered.;
           HELP = This object is valid only if the \
                  mcmBrgSapFilterStatus (above) \
                  is range.;
	   CAPABILITIES = ;"
	::= { nvmBrgSapFilterEntry 6 }


  -- The Counter Reset Group


mcmBrgCntr OBJECT IDENTIFIER ::= { mcmBrg 14 }


mcmBrgPortCntrZeroTable OBJECT-TYPE
              SYNTAX  SEQUENCE OF McmBrgPortCntrZeroEntry
              ACCESS  not-accessible
              STATUS  obsolete 
	DESCRIPTION
	  "NAME = ;
       DESC = This object was obsoleted as of release \
	      3.0; and is included here only to support \
	      backwards compatibility for software \
	      versions prior to release 3.0. \
		  A table that contains port-specific \
          information for access device Port Counter \
          Zeroing.;
           HELP =;
	   CAPABILITIES = NET_CFG, VPN_CFG;"
              ::= { mcmBrgCntr 1 }

          mcmBrgPortCntrZeroEntry OBJECT-TYPE
              SYNTAX  McmBrgPortCntrZeroEntry
              ACCESS  not-accessible
              STATUS  obsolete
	DESCRIPTION
	  "NAME = ;
       DESC = This object was obsoleted as of release \
	      3.0; and is included here only to support \
	      backwards compatibility for software \
	      versions prior to release 3.0. \
	      A list of information maintained by \
          every port about the access device E-type Filter \
          parameters for that port.;
           HELP = ;
	   CAPABILITIES = ;"
              INDEX   { mcmBrgPortCntrZeroIndex }
              ::= { mcmBrgPortCntrZeroTable 1 }

          McmBrgPortCntrZeroEntry ::=
              SEQUENCE {
                  mcmBrgPortCntrZeroIndex
                      INTEGER,
                  mcmBrgBasePortCounterZero
                      INTEGER,
                  mcmBrgStpPortCounterZero
                      INTEGER,
                  mcmBrgTpPortCounterZero
                      INTEGER
	}


mcmBrgPortCntrZeroIndex OBJECT-TYPE
	SYNTAX	INTEGER(1..16)
	ACCESS	read-write
	STATUS	obsolete
	DESCRIPTION
	  "NAME = ;
       DESC = This object was obsoleted as of release \
	      3.0; and is included here only to support \
	      backwards compatibility for software \
	      versions prior to release 3.0. \
	      The Port Index to which this entry pertains.;
	   HELP = ;
           CAPABILITIES = ;"
	::= { mcmBrgPortCntrZeroEntry 1 }

mcmBrgBasePortCounterZero OBJECT-TYPE
        SYNTAX  INTEGER { reset(1) }
	ACCESS	write-only
        STATUS  obsolete
	DESCRIPTION
	  "NAME = ;
       DESC = This object was obsoleted as of release \
	      3.0; and is included here only to support \
	      backwards compatibility for software \
	      versions prior to release 3.0. \
	      When set to reset, the Base port Counters \
          should be zeroed out.;
	   HELP = ;
	   CAPABILITIES = ;"
        ::= { mcmBrgPortCntrZeroEntry 2 }

mcmBrgStpPortCounterZero OBJECT-TYPE
        SYNTAX  INTEGER { reset(1) }
	ACCESS	write-only
        STATUS  obsolete
	DESCRIPTION
	  "NAME = ;
       DESC = This object was obsoleted as of release \
	      3.0; and is included here only to support \
	      backwards compatibility for software \
	      versions prior to release 3.0. \
	      When set to reset, the spanning Tree port \
          counters will be zeroed out.;
           HELP = ;
	   CAPABILITIES = ;"
        ::= { mcmBrgPortCntrZeroEntry 3 }

mcmBrgTpPortCounterZero OBJECT-TYPE
        SYNTAX  INTEGER { reset(1) }
	ACCESS	write-only
        STATUS  obsolete
	DESCRIPTION
	  "NAME = ;
       DESC = This object was obsoleted as of release \
	      3.0; and is included here only to support \
	      backwards compatibility for software \
	      versions prior to release 3.0. \
	      When set to reset, the Transparent port \
          counters will be zeroed out.;
           HELP = ;
	   CAPABILITIES = ;"
        ::= { mcmBrgPortCntrZeroEntry 4 }


   mcmBrgCounterZero    OBJECT IDENTIFIER ::= { mcmBrgCntr 2 }


mcmBrgStpCounterZero OBJECT-TYPE
        SYNTAX  INTEGER { reset(1) }
	ACCESS	write-only
        STATUS  obsolete
	DESCRIPTION
	  "NAME = ;
       DESC = This object was obsoleted as of release \
	      3.0; and is included here only to support \
	      backwards compatibility for software \
	      versions prior to release 3.0. \
	      When set to reset, the spanning Tree port \
          counters will be zeroed out.;
           HELP = ;
	   CAPABILITIES = ;"
        ::= { mcmBrgCounterZero 1 }

mcmBrgTpCounterZero OBJECT-TYPE
        SYNTAX  INTEGER { reset(1) }
	ACCESS	write-only
        STATUS  obsolete
	DESCRIPTION
	  "NAME = ;
       DESC = This object was obsoleted as of release \
	      3.0; and is included here only to support \
	      backwards compatibility for software \
	      versions prior to release 3.0. \
	      When set to reset, the Transparent port \
          counters will be zeroed out.;
	   HELP = ;
	   CAPABILITIES = ;"
        ::= { mcmBrgCounterZero 2 }

END
