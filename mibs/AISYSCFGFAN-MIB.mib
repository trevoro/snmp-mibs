AISYSCFGFAN-MIB DEFINITIONS ::= BEGIN

IMPORTS
    MODULE-IDENTITY, NOTIFICATION-TYPE, OBJECT-TYPE,
    Integer32,
    enterprises
					FROM SNMPv2-SMI
    DisplayString
    					FROM SNMPv2-TC;

    aii OBJECT IDENTIFIER ::= {enterprises 539}
    aiSysCfg OBJECT IDENTIFIER ::= {aii 32}

aiSysCfgFan MODULE-IDENTITY
    LAST-UPDATED "200104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for fans."
    REVISION "200104301700Z"
    DESCRIPTION "The initial revision of this module."
    ::= { aiSysCfg 4 }

-- Object definitions (Using "aiSCFan" prefix)

aiSCFanTrapInfo OBJECT IDENTIFIER ::= { aiSysCfgFan 0 }

aiSCFanTrapFail NOTIFICATION-TYPE
    OBJECTS	{ aiSCFanIndex,
		  aiSCFanStatus }
    STATUS      current
    DESCRIPTION
	"Trap sent when a fan goes into a failure mode."
    ::= { aiSCFanTrapInfo 1 }

aiSCFanTrapOk NOTIFICATION-TYPE
    OBJECTS	{ aiSCFanIndex,
		  aiSCFanStatus }
    STATUS      current
    DESCRIPTION
	"Trap sent when a fan reverts from a failure mode."
    ::= { aiSCFanTrapInfo 2 }

aiSCFanAgregateStatus OBJECT-TYPE
    SYNTAX	INTEGER {okay(1), trouble(2)}
    MAX-ACCESS	read-only
    STATUS	current
    DESCRIPTION
	"Aggregate status of all fan units in the system."
    ::= { aiSysCfgFan 1 }

aiSCFanTable OBJECT-TYPE
    SYNTAX      SEQUENCE OF AiSCFanEntry
    MAX-ACCESS  not-accessible
    STATUS      current
    DESCRIPTION
	"A table of information on each fan in the system."
    ::= { aiSysCfgFan 2 }

aiSCFanEntry OBJECT-TYPE
    SYNTAX	AiSCFanEntry
    MAX-ACCESS	not-accessible
    STATUS	current
    DESCRIPTION
	"Information on a given fan."
    INDEX { aiSCFanIndex }
    ::= { aiSCFanTable 1 }

AiSCFanEntry ::=
    SEQUENCE {
	aiSCFanIndex			Integer32,
	aiSCFanDescription		DisplayString,
	aiSCFanStatus			INTEGER
    }

aiSCFanIndex OBJECT-TYPE
    SYNTAX	Integer32 (1..2147483647)
    MAX-ACCESS	read-only
    STATUS	current
    DESCRIPTION
	"Self referential index into this table."
    ::= { aiSCFanEntry 1 }

aiSCFanDescription OBJECT-TYPE
    SYNTAX	DisplayString (SIZE (0..255))
    MAX-ACCESS	read-only
    STATUS	current
    DESCRIPTION
	"Description of the fan to which this table entry refers."
    ::= { aiSCFanEntry 2 }

aiSCFanStatus OBJECT-TYPE
    SYNTAX	INTEGER {okay(1), fail(2)}
    MAX-ACCESS	read-only
    STATUS	current
    DESCRIPTION
	"Status of the fan unit."
    ::= { aiSCFanEntry 3 }

END
