-- ODS ENC Enterprise Specific MIB (April 6, 1992) 

-- In addition to the ODS MIB, the ENC agent also
-- supports several objects under enterprises.23.

ODS-ENC-MIB DEFINITIONS ::= BEGIN

IMPORTS
	enterprises, NetworkAddress, IpAddress, Counter, Gauge,
		TimeTicks, OBJECT-TYPE FROM RFC1155-SMI
		DisplayString, PhysAddress FROM SNMPv2-TC
	snmp FROM RFC1158-MIB;


ods				OBJECT IDENTIFIER ::= { enterprises 50 }
enc				OBJECT IDENTIFIER ::= { ods 1 }
encMib2			OBJECT IDENTIFIER ::= { enc 2 }
encSystem		OBJECT IDENTIFIER ::= { encMib2 1 }
encAdmin		OBJECT IDENTIFIER ::= { encMib2 2 }
encBox			OBJECT IDENTIFIER ::= { encSystem 1 }
encCards		OBJECT IDENTIFIER ::= { encSystem 2 }
encPorts		OBJECT IDENTIFIER ::= { encSystem 3 }
encExper		OBJECT IDENTIFIER ::= { enc 3 }
encProtos		OBJECT IDENTIFIER ::= { encExper 1 }
boxProtos		OBJECT IDENTIFIER ::= { encProtos 1 }
addrProtos		OBJECT IDENTIFIER ::= { encProtos 2 }

-- --------------------------------------------------------

-- The box group contains objects pertaining to the
-- concentrator as a whole.

boxId OBJECT-TYPE
	SYNTAX	INTEGER {
			ods296(5),		-- 3x4-slot ethernet system
			ods292(6),		--  4-slot ethernet system
			ods295(7),		-- 12-slot ethernet system
			ods290-red(9),	-- 12-slot ethernet system
			ods293-red(10),	-- 3x4-slot ethernet system
			ods258(11),		--  4-slot ethernet system
			ods293(12),		-- 3x4-slot ethernet system
			ods291(13),		--  5-slot ethernet system
			ods290(14),		-- 12-slot ethernet system
			ods263(134),	--  8-port ethernet star
			ods261(135),	-- 16-port ethernet star
			ods251(139),	-- 16-port ethernet star
			ods243(142),	--  8-port ethernet star
			ods241(143)		-- 16-port ethernet star
		}
	ACCESS	read-only
	STATUS	mandatory
	DESCRIPTION
			"The type of chassis used in the concentrator. 
			For modular concentrators, the hardware is
			further qualifed by the value of cardId for each
			card installed in the concentrator."
	::= { encBox 1 }

boxDescr OBJECT-TYPE
	SYNTAX	DisplayString (SIZE (0..255))
	ACCESS	read-only
	STATUS	mandatory
	DESCRIPTION
			"A textual description of the chassis including
			the ODS model number, media type and number of
			slots.  For modular concentrators, the hardware
			is further qualified by the value of cardDescr
			for each card installed in the concentrator."
	::= { encBox 2 }

boxNetworkMode OBJECT-TYPE
	SYNTAX	INTEGER {
			local(1),
			network(2)
		}
	ACCESS	read-only
	STATUS	deprecated
	DESCRIPTION
			"The state of the network interface port.  If the
			value is network(2), the concentrator may be cas-
			caded off of another network.  Regardless of the
			value, the concentrator may also be connected to
			other networks via normal interface ports.
			
			Note that the functionality previously provided by
			this object has been superceded by portOperStatus
			and portAdminStatus as all external connections on
			the concentrator are available through the portTable.
			This object may be deleted from future versions of
			the MIB."
	::= { encBox 3 }

boxPowerStatus OBJECT-TYPE
	SYNTAX	INTEGER
	ACCESS	read-only
	STATUS	mandatory
	DESCRIPTION
			"The state of the power supplies in the concentrator.  
			The value is a sum.  For each power supply P, in the 
			range 1 through 2, that is operational, 2 raised to 
			(P - 1) is added to the sum.  For example, if both 
			power supplies are good, the value is 3 (2^0 + 2^1).  
			In contrast, if power supply 2 is bad, the value is 
			1 (2^0).  Note that the value will be NULL for those
			concentrators which can not access the power supply 
			status."
	::= { encBox 20 }

boxNumAddresses OBJECT-TYPE
	SYNTAX	INTEGER
	ACCESS	read-only
	STATUS	mandatory
	DESCRIPTION
			"The number of unique, physical, source and dest-
			ination addresses contained in non-errored packets
			received by the concentrator.  Note that this object
			is not maintained if the value of adminAddrStat-
			Enable is disabled(2)."
	::= { encBox 7 }

boxGoodPackets OBJECT-TYPE
	SYNTAX	Counter
	ACCESS	read-only
	STATUS	mandatory
	DESCRIPTION
			"The number of non-errored packets received by
			the concentrator.  Note that this object is not
			maintained if the value of adminPktStatEnable is
			disabled(2)."
	::= { encBox 5 }

boxGoodOctets OBJECT-TYPE
	SYNTAX	Counter
	ACCESS	read-only
	STATUS	mandatory
	DESCRIPTION
			"The number of octets contained in non-errored
			packets received by the concentrator.  Note that
			this object is not maintained if the value of 
			adminPktStatEnable is disabled(2)."
	::= { encBox 6 }

boxCrcErrors OBJECT-TYPE
	SYNTAX	Counter
	ACCESS	read-only
	STATUS	mandatory
	DESCRIPTION
			"The number of packets received by the concen-
			trator which had CRC errors.  Note that this object
			is not maintained if the value of adminPktStat-
			Enable is disabled(2)."
	::= { encBox 10 }

boxAlignErrors OBJECT-TYPE
	SYNTAX	Counter
	ACCESS	read-only
	STATUS	mandatory
	DESCRIPTION
			"The number of packets received by the concen-
			trator which had frame alignment errors.  Note
			that this object is not maintained if the value
			of adminPktStatEnable is disabled(2)."
	::= { encBox 11 }

boxFragErrors OBJECT-TYPE
	SYNTAX	Counter
	ACCESS	read-only
	STATUS	mandatory
	DESCRIPTION
			"The number of packets received by the concen-
			trator which contained fewer than 64 octets.  Note
			that this object is not maintained if the value of
			adminPktStatEnable is disabled(2)."
	::= { encBox 12 }

boxPacketThresh OBJECT-TYPE
	SYNTAX	Gauge
	ACCESS	read-write
	STATUS	mandatory
	DESCRIPTION
			"A threshold for monitoring the number of non-
			errored packets received by the concentrator.  If
			the measured number of packets per second equals
			or exceeds this value, a box-class trap will be
			sent to each network manager defined in the
			adminTrapTable.  Monitoring of this threshold is
			disabled if the value is zero or if the value of
			adminPktStatEnable is disabled(2).

			When reported in a trap, the measured number of
			non-errored packets per second received by the
			concentrator."
	::= { encBox 13 }

boxOctetThresh OBJECT-TYPE
	SYNTAX	Gauge
	ACCESS	read-write
	STATUS	mandatory
	DESCRIPTION
			"A threshold for monitoring the number of octets
			contained in non-errored packets received by the
			concentrator.  If the measured number of octets
			per second equals or exceeds this value, a box-
			class trap will be sent to each network manager
			defined in the adminTrapTable.  Monitoring of this
			threshold is disabled if the value is zero or if
			the value of adminPktStatEnable is disabled(2).

			When reported in a trap, the measured number of
			octets per second contained in non-errored
			packets received by the concentrator."
	::= { encBox 19 }

boxCrcThresh OBJECT-TYPE
	SYNTAX	Gauge
	ACCESS	read-write
	STATUS	mandatory
	DESCRIPTION
			"A threshold for monitoring the number of packets
			received by the concentrator which had CRC errors.
			If the measured number of packets per second
			equals or exceeds this value, a box-class trap
			will be sent to each network manager defined in
			the adminTrapTable.  Monitoring of this threshold
			is disabled if the value is zero or if the value
			of adminPktStatEnable is disabled(2).

			When reported in a trap, the measured number of
			packets per second received by the concentrator
			which had CRC errors."
	::= { encBox 14 }

boxAlignThresh OBJECT-TYPE
	SYNTAX	Gauge
	ACCESS	read-write
	STATUS	mandatory
	DESCRIPTION
			"A threshold for monitoring the number of packets
			received by the concentrator which had frame
			alignment errors.  If the measured number of
			packets per second equals or exceeds this value,
			a box-class trap will be sent to each network
			manager defined in the adminTrapTable.  Monitor-
			ing of this threshold is disabled if the value is
			zero or if the value of adminPktStatEnable is
			disabled(2).

			When reported in a trap, the measured number of
			packets per second received by the concentrator
			which had frame alignment errors."
	::= { encBox 15 }

boxFragThresh OBJECT-TYPE
	SYNTAX	Gauge
	ACCESS	read-write
	STATUS	mandatory
	DESCRIPTION
			"A threshold for monitoring the number of packets
			received by the concentrator which contained
			fewer than 64 octets.  If the measured number of
			packets per second equals or exceeds this value,
			a box-class trap will be sent to each network
			manager defined in the adminTrapTable.  Monitor-
			ing of this threshold is disabled if the value is
			zero or if the value of adminPktStatEnable is
			disabled(2).

			When reported in a trap, the measured number of
			packets per second received by the concentrator
			which contained fewer than 64 octets."
	::= { encBox 16 }

boxMissedPackets OBJECT-TYPE
	SYNTAX	Counter
	ACCESS	read-only
	STATUS	mandatory
	DESCRIPTION
			"The number of packets received by the concen-
			trator which could not be processed by the agent
			due to excessive network traffic."
	::= { encBox 9 }

boxLostPackets OBJECT-TYPE
	SYNTAX	Counter
	ACCESS	read-only
	STATUS	mandatory
	DESCRIPTION
			"The number of packets received by the concen-
			trator which could not be attributed to a card
			and port by the agent.  This object is not main-
			tained if the value of adminPktStatEnable is
			disabled(2)."
	::= { encBox 8 }

-- --------------------------------------------------------

-- The box protocol group contains objects related to the
-- protocols used in packets received by the concentrator.

bpUnkPackets OBJECT-TYPE
	SYNTAX	Counter
	ACCESS	read-only
	STATUS	mandatory
	DESCRIPTION
			"The number of non-errored packets received by
			the concentrator having an unknown protocol type.
			Note that this object is not maintained if the
			value of adminProtStatEnable is disabled(2)."
	::= { boxProtos 1 }

bpIPPackets OBJECT-TYPE
	SYNTAX	Counter
	ACCESS	read-only
	STATUS	mandatory
	DESCRIPTION
			"The number of non-errored packets received by
			the concentrator having a DOD (IP, ARP, RARP)
			protocol type.  Note that this object is not 
			maintained if the value of adminProtStatEnable 
			is disabled(2)."
	::= { boxProtos 2 }

bpISOPackets OBJECT-TYPE
	SYNTAX	Counter
	ACCESS	read-only
	STATUS	mandatory
	DESCRIPTION
			"The number of non-errored packets received by
			the concentrator having an ISO protocol type.  
			Note that this object is not maintained if the
			value of adminProtStatEnable is disabled(2)."
	::= { boxProtos 3 }

bpDECPackets OBJECT-TYPE
	SYNTAX	Counter
	ACCESS	read-only
	STATUS	mandatory
	DESCRIPTION
			"The number of non-errored packets received by
			the concentrator having a DEC protocol type.  
			Note that this object is not maintained if the
			value of adminProtStatEnable is disabled(2)."
	::= { boxProtos 4 }

bpNWPackets OBJECT-TYPE
	SYNTAX	Counter
	ACCESS	read-only
	STATUS	mandatory
	DESCRIPTION
			"The number of non-errored packets received by
			the concentrator having a NetWare protocol type.  
			Note that this object is not maintained if the
			value of adminProtStatEnable is disabled(2)."
	::= { boxProtos 5 }

bpATPackets OBJECT-TYPE
	SYNTAX	Counter
	ACCESS	read-only
	STATUS	mandatory
	DESCRIPTION
			"The number of non-errored packets received by
			the concentrator having an AppleTalk protocol
			type.  Note that this object is not maintained if
			the value of adminProtStatEnable is disabled(2)."
	::= { boxProtos 6 }

bpXNSPackets OBJECT-TYPE
	SYNTAX	Counter
	ACCESS	read-only
	STATUS	mandatory
	DESCRIPTION
			"The number of non-errored packets received by
			the concentrator having an XNS protocol type.  
			Note that this object is not maintained if the
			value of adminProtStatEnable is disabled(2)."
	::= { boxProtos 7 }

bpSNAPackets OBJECT-TYPE
	SYNTAX	Counter
	ACCESS	read-only
	STATUS	mandatory
	DESCRIPTION
			"The number of non-errored packets received by
			the concentrator having an SNA protocol type.  
			Note that this object is not maintained if the
			value of adminProtStatEnable is disabled(2)."
	::= { boxProtos 8 }

bpUnkOctets OBJECT-TYPE
	SYNTAX	Counter
	ACCESS	read-only
	STATUS	mandatory
	DESCRIPTION
			"The number of octets contained in non-errored
			packets received by the concentrator having an
			unknown protocol type.  Note that this object is
			not maintained if the value of adminProtStatEnable
			is disabled(2)."
	::= { boxProtos 9 }

bpIPOctets OBJECT-TYPE
	SYNTAX	Counter
	ACCESS	read-only
	STATUS	mandatory
	DESCRIPTION
			"The number of octets contained in non-errored
			packets received by the concentrator having a DOD
			(IP, ARP, RARP) protocol type.  Note that this
			object is not maintained if the value of admin-
			ProtStatEnable is disabled(2)."
	::= { boxProtos 10 }

bpISOOctets OBJECT-TYPE
	SYNTAX	Counter
	ACCESS	read-only
	STATUS	mandatory
	DESCRIPTION
			"The number of octets contained in non-errored
			packets received by the concentrator having an
			ISO protocol type.  Note that this object is not
			maintained if the value of adminProtStatEnable
			is disabled(2)."
	::= { boxProtos 11 }

bpDECOctets OBJECT-TYPE
	SYNTAX	Counter
	ACCESS	read-only
	STATUS	mandatory
	DESCRIPTION
			"The number of octets contained in non-errored
			packets received by the concentrator having a
			DEC protocol type.  Note that this object is not
			maintained if the value of adminProtStatEnable
			is disabled(2)."
	::= { boxProtos 12 }

bpNWOctets OBJECT-TYPE
	SYNTAX	Counter
	ACCESS	read-only
	STATUS	mandatory
	DESCRIPTION
			"The number of octets contained in non-errored
			packets received by the concentrator having a
			NetWare protocol type.  Note that this object is
			not maintained if the value of adminProtStatEnable
			is disabled(2)."
	::= { boxProtos 13 }

bpATOctets OBJECT-TYPE
	SYNTAX	Counter
	ACCESS	read-only
	STATUS	mandatory
	DESCRIPTION
			"The number of octets contained in non-errored
			packets received by the concentrator having an
			AppleTalk protocol type.  Note that this object is
			not maintained if the value of adminProtStatEnable
			is disabled(2)."
	::= { boxProtos 14 }

bpXNSOctets OBJECT-TYPE
	SYNTAX	Counter
	ACCESS	read-only
	STATUS	mandatory
	DESCRIPTION
			"The number of octets contained in non-errored
			packets received by the concentrator having an
			XNS protocol type.  Note that this object is not 
			maintained if the value of adminProtStatEnable
			is disabled(2)."
	::= { boxProtos 15 }

bpSNAOctets OBJECT-TYPE
	SYNTAX	Counter
	ACCESS	read-only
	STATUS	mandatory
	DESCRIPTION
			"The number of octets contained in non-errored
			packets received by the concentrator having an
			SNA protocol type.  Note that this object is not
			maintained if the value of adminProtStatEnable
			is disabled(2)."
	::= { boxProtos 16 }

-- --------------------------------------------------------

-- The box address table contains address-related data for
-- each physical address contained in non-errored packets
-- received by the concentrator.  When the table is full,
-- the addresses with the least recent activity are replaced
-- by any newer addresses.

boxAddressTable OBJECT-TYPE
	SYNTAX	SEQUENCE OF BoxAddressEntry
	ACCESS	not-accessible
	STATUS	mandatory
	DESCRIPTION
			"A list of address entries for each physical
			address contained in non-errored packets received
			by the concentrator.  The number of entries is
			given by the value of boxNumAddresses.  Note that
			no entries are maintained if the value of admin-
			AddrStatEnable is disabled(2)."
	::= { encBox 18 }

boxAddressEntry OBJECT-TYPE
	SYNTAX	BoxAddressEntry
	ACCESS	not-accessible
	STATUS	mandatory
	DESCRIPTION
			"An address entry containing objects pertaining
			to a physical address contained in non-errored
			packets received by the concentrator."
	INDEX	{ batPhysAddress }
	::= { boxAddressTable 1 }

BoxAddressEntry ::= SEQUENCE {
	batPhysAddress	PhysAddress,
	batFirstPacket	TimeTicks,
	batLastPacket	TimeTicks,
	batGoodPackets	Counter,
	batGoodOctets	Counter,
	batCard			INTEGER,
	batPort			INTEGER,
	batDelete		INTEGER,
	batGoodPacketsTo Counter,
	batGoodOctetsTo	Counter,
	batFirstPacketTo TimeTicks,
	batLastPacketTo	TimeTicks,
	batLastIpAddress IpAddress
}

batCard OBJECT-TYPE
	SYNTAX	INTEGER
	ACCESS	read-only
	STATUS	mandatory
	DESCRIPTION
			"The card on which the most recent, non-errored
			packet having the address as source was received.
			The card identified by this value is the same
			card as identified by the same value of cardIndex.
			Note that the value will be NULL for addresses
			which have not transmitted packets."
	::= { boxAddressEntry 6 }

batPort OBJECT-TYPE
	SYNTAX	INTEGER
	ACCESS	read-only
	STATUS	mandatory
	DESCRIPTION
			"The port on which the most recent, non-errored
			packet having the address as source was received.
			The port identified by this value is the same
			port as identified by the same value of portIndex.
			Note that the value will be NULL for addresses
			which have not transmitted packets."
	::= { boxAddressEntry 7 }

batPhysAddress OBJECT-TYPE
	SYNTAX	PhysAddress (SIZE (6))
	ACCESS	read-only
	STATUS	mandatory
	DESCRIPTION
			"The physical address for this entry.

			When reported in a trap, the physical address
			relevant to the trap."
	::= { boxAddressEntry 1 }

batLastIpAddress OBJECT-TYPE
	SYNTAX	IpAddress
	ACCESS	read-only
	STATUS	mandatory
	DESCRIPTION
			"The source network address used in the most
			recent IP packet received by the concentrator
			having the address as source.  Note that the
			value will be NULL for addresses which have not
			transmitted any IP packets or if the value of
			adminIpCheckEnable is disabled(2)."
	::= { boxAddressEntry 13 }

batGoodPackets OBJECT-TYPE
	SYNTAX	Counter
	ACCESS	read-only
	STATUS	mandatory
	DESCRIPTION
			"The number of non-errored packets received by
			the concentrator having the address as source."
	::= { boxAddressEntry 4 }

batGoodOctets OBJECT-TYPE
	SYNTAX	Counter
	ACCESS	read-only
	STATUS	mandatory
	DESCRIPTION
			"The number of octets contained in non-errored
			packets received by the concentrator having the
			address as source."
	::= { boxAddressEntry 5 }

batFirstPacket OBJECT-TYPE
	SYNTAX	TimeTicks
	ACCESS	read-only
	STATUS	mandatory
	DESCRIPTION
			"The value of sysUpTime at the time the first
			packet having the address as source was 
			received by the concentrator.  Note that the
			value will be NULL for addresses which have not
			transmitted packets."
	::= { boxAddressEntry 2 }

batLastPacket OBJECT-TYPE
	SYNTAX	TimeTicks
	ACCESS	read-only
	STATUS	mandatory
	DESCRIPTION
			"The value of sysUpTime at the time the most
			recent packet having the address as source was
			received by the concentrator.  Note that the
			value will be NULL for addresses which have not
			transmitted packets."
	::= { boxAddressEntry 3 }

batGoodPacketsTo OBJECT-TYPE
	SYNTAX	Counter
	ACCESS	read-only
	STATUS	mandatory
	DESCRIPTION
			"The number of non-errored packets received by
			the concentrator having the address as dest-
			ination."
	::= { boxAddressEntry 9 }

batGoodOctetsTo OBJECT-TYPE
	SYNTAX	Counter
	ACCESS	read-only
	STATUS	mandatory
	DESCRIPTION
			"The number of octets contained in non-errored
			packets received by the concentrator having the
			address as destination."
	::= { boxAddressEntry 10 }

batFirstPacketTo OBJECT-TYPE
	SYNTAX	TimeTicks
	ACCESS	read-only
	STATUS	mandatory
	DESCRIPTION
			"The value of sysUpTime at the time the first
			packet having the address as destination was
			received by the concentrator.  Note that the
			value will be NULL for addresses which have not
			been sent packets."
	::= { boxAddressEntry 11 }

batLastPacketTo OBJECT-TYPE
	SYNTAX	TimeTicks
	ACCESS	read-only
	STATUS	mandatory
	DESCRIPTION
			"The value of sysUpTime at the time the most
			recent packet having the address as destination
			was received by the concentrator.  Note that the
			value will be NULL for addresses which have not
			been sent packets."
	::= { boxAddressEntry 12 }

batDelete OBJECT-TYPE
	SYNTAX	INTEGER
	ACCESS	write-only
	STATUS	mandatory
	DESCRIPTION
			"Setting this object to any legal, ASN.1 value
			deletes the entry for the address."
	::= { boxAddressEntry 8 }

-- --------------------------------------------------------

-- The protocol address table contains protocol-related
-- objects for each address contained in non-errored packets
-- received by the concentrator.

addrProtoTable OBJECT-TYPE
	SYNTAX	SEQUENCE OF AddrProtoEntry
	ACCESS	not-accessible
	STATUS	mandatory
	DESCRIPTION
			"A list of protocol entries for each physical
			address contained in non-errored packets received
			by the concentrator.  The number of entries is
			given by the value of boxNumAddresses.  Note that
			no entries are maintained if the value of admin-
			AddrStatEnable is disabled(2)."
	::= { addrProtos 1 }

addrProtoEntry OBJECT-TYPE
	SYNTAX	AddrProtoEntry
	ACCESS	not-accessible
	STATUS	mandatory
	DESCRIPTION
			"A protocol entry containing objects pertaining
			to a physical address contained in non-errored
			packets received by the concentrator."
	INDEX	{ apPhysAddress }
	::= { addrProtoTable 1 }

AddrProtoEntry ::= SEQUENCE {
	apUnkPackets	Counter,
	apIPPackets		Counter,
	apISOPackets	Counter,
	apDECPackets	Counter,
	apNWPackets		Counter,
	apATPackets		Counter,
	apXNSPackets	Counter,
	apSNAPackets	Counter,
	apUnkOctets		Counter,
	apIPOctets		Counter,
	apISOOctets		Counter,
	apDECOctets		Counter,
	apNWOctets		Counter,
	apATOctets		Counter,
	apXNSOctets		Counter,
	apSNAOctets		Counter,
	apPhysAddress	PhysAddress
}

apPhysAddress OBJECT-TYPE
	SYNTAX	PhysAddress (SIZE (6))
	ACCESS	read-only
	STATUS	mandatory
	DESCRIPTION
			"The physical address for this entry."
	::= { addrProtoEntry 17 }

apUnkPackets OBJECT-TYPE
	SYNTAX	Counter
	ACCESS	read-only
	STATUS	mandatory
	DESCRIPTION
			"The number of non-errored packets received by
			the concentrator having the address as source and
			an unknown protocol type.  Note that this object
			is not maintained if the value of adminProtStat-
			Enable is disabled(2)."
	::= { addrProtoEntry 1 }

apIPPackets OBJECT-TYPE
	SYNTAX	Counter
	ACCESS	read-only
	STATUS	mandatory
	DESCRIPTION
			"The number of non-errored packets received by
			the concentrator having the address as source and
			a DOD (IP, ARP, RARP) protocol type.  Note that
			this object is not maintained if the value of
			adminProtStatEnable is disabled(2)."
	::= { addrProtoEntry 2 }

apISOPackets OBJECT-TYPE
	SYNTAX	Counter
	ACCESS	read-only
	STATUS	mandatory
	DESCRIPTION
			"The number of non-errored packets received by
			the concentrator having the address as source and
			an ISO protocol type.  Note that this object is
			not maintained if the value of adminProtStatEnable
			is disabled(2)."
	::= { addrProtoEntry 3 }

apDECPackets OBJECT-TYPE
	SYNTAX	Counter
	ACCESS	read-only
	STATUS	mandatory
	DESCRIPTION
			"The number of non-errored packets received by
			the concentrator having the address as source and 
			a DEC protocol type.  Note that this object is not
			maintained if the value of adminProtStatEnable is
			disabled(2)."
	::= { addrProtoEntry 4 }

apNWPackets OBJECT-TYPE
	SYNTAX	Counter
	ACCESS	read-only
	STATUS	mandatory
	DESCRIPTION
			"The number of non-errored packets received by
			the concentrator having the address as source and
			a NetWare protocol type.  Note that this object is
			not maintained if the value of adminProtStatEnable
			is disabled(2)."
	::= { addrProtoEntry 5 }

apATPackets OBJECT-TYPE
	SYNTAX	Counter
	ACCESS	read-only
	STATUS	mandatory
	DESCRIPTION
			"The number of non-errored packets received by
			the concentrator having the address as source and
			an AppleTalk protocol type.  Note that this object
			is not maintained if the value of adminProtStat-
			Enable is disabled(2)."
	::= { addrProtoEntry 6 }

apXNSPackets OBJECT-TYPE
	SYNTAX	Counter
	ACCESS	read-only
	STATUS	mandatory
	DESCRIPTION
			"The number of non-errored packets received by
			the concentrator having the address as source and
			an XNS protocol type.  Note that this object is
			not maintained if the value of adminProtStatEnable
			is disabled(2)."
	::= { addrProtoEntry 7 }

apSNAPackets OBJECT-TYPE
	SYNTAX	Counter
	ACCESS	read-only
	STATUS	mandatory
	DESCRIPTION
			"The number of non-errored packets received by
			the concentrator having the address as source and
			an SNA protocol type.  Note that this object is
			not maintained if the value of adminProtStatEnable
			is disabled(2)."
	::= { addrProtoEntry 8 }

apUnkOctets OBJECT-TYPE
	SYNTAX	Counter
	ACCESS	read-only
	STATUS	mandatory
	DESCRIPTION
			"The number of octets contained in non-errored
			packets received by the concentrator having the 
			address as source and an unknown protocol type.  
			Note that this object is not maintained if the
			value of adminProtStatEnable is disabled(2)."
	::= { addrProtoEntry 9 }

apIPOctets OBJECT-TYPE
	SYNTAX	Counter
	ACCESS	read-only
	STATUS	mandatory
	DESCRIPTION
			"The number of octets contained in non-errored
			packets received by the concentrator having the 
			address as source and a DOD (IP, ARP, RARP)
			protocol type.  Note that this object is not
			maintained if the value of adminProtStatEnable
			is disabled(2)."
	::= { addrProtoEntry 10 }

apISOOctets OBJECT-TYPE
	SYNTAX	Counter
	ACCESS	read-only
	STATUS	mandatory
	DESCRIPTION
			"The number of octets contained in non-errored
			packets received by the concentrator having the 
			address as source and an ISO protocol type.  Note
			that this object is not maintained if the value
			of adminProtStatEnable is disabled(2)."
	::= { addrProtoEntry 11 }

apDECOctets OBJECT-TYPE
	SYNTAX	Counter
	ACCESS	read-only
	STATUS	mandatory
	DESCRIPTION
			"The number of octets contained in non-errored
			packets received by the concentrator having the 
			address as source and a DEC protocol type.  Note
			that this object is not maintained if the value
			of adminProtStatEnable is disabled(2)."
	::= { addrProtoEntry 12 }

apNWOctets OBJECT-TYPE
	SYNTAX	Counter
	ACCESS	read-only
	STATUS	mandatory
	DESCRIPTION
			"The number of octets contained in non-errored
			packets received by the concentrator having the 
			address as source and a NetWare protocol type.  
			Note that this object is not maintained if the
			value of adminProtStatEnable is disabled(2)."
	::= { addrProtoEntry 13 }

apATOctets OBJECT-TYPE
	SYNTAX	Counter
	ACCESS	read-only
	STATUS	mandatory
	DESCRIPTION
			"The number of octets contained in non-errored
			packets received by the concentrator having the 
			address as source and an AppleTalk protocol type.
			Note that this object is not maintained if the
			value of adminProtStatEnable is disabled(2)."
	::= { addrProtoEntry 14 }

apXNSOctets OBJECT-TYPE
	SYNTAX	Counter
	ACCESS	read-only
	STATUS	mandatory
	DESCRIPTION
			"The number of octets contained in non-errored
			packets received by the concentrator having the 
			address as source and an XNS protocol type.  Note
			that this object is not maintained if the value
			of adminProtStatEnable is disabled(2)."
	::= { addrProtoEntry 15 }

apSNAOctets OBJECT-TYPE
	SYNTAX	Counter
	ACCESS	read-only
	STATUS	mandatory
	DESCRIPTION
			"The number of octets contained in non-errored
			packets received by the concentrator having the 
			address as source and an SNA protocol type.  Note
			that this object is not maintained if the value
			of adminProtStatEnable is disabled(2)."
	::= { addrProtoEntry 16 }

-- --------------------------------------------------------

cardNumSlots OBJECT-TYPE
	SYNTAX	INTEGER
	ACCESS	read-only
	STATUS	mandatory
	DESCRIPTION
			"The number of slots in the concentrator.  For
			modular concentrators, this value is the maximum
			number of cards that can be installed.  For
			non-modular concentrators, the value is always
			two (card one contains the user ports and card
			two contains the network port)."
	::= { encCards 1 }

cardNumCards OBJECT-TYPE
	SYNTAX	INTEGER
	ACCESS	read-only
	STATUS	mandatory
	DESCRIPTION
			"The number of cards actually installed in the
			concentrator.  For non-modular concentrators, the
			value is always two (card one contains the user
			ports and card two contains the network port)."
	::= { encCards 2 }

-- The card table contains information pertaining to each
-- card installed in the concentrator.  The size of the
-- table may change dynamically as old cards are removed
-- or new ones are installed.

cardTable OBJECT-TYPE
	SYNTAX	SEQUENCE OF CardEntry
	ACCESS	not-accessible
	STATUS	mandatory
	DESCRIPTION
			"A list of card entries for each card installed in
			the concentrator.  The number of entries is given
			by the value of cardNumCards."
	::= { encCards 3 }

cardEntry OBJECT-TYPE
	SYNTAX	CardEntry
	ACCESS	not-accessible
	STATUS	mandatory
	DESCRIPTION
			"A card entry containing objects pertaining to a
			card installed in the concentrator."
	INDEX	{ cardIndex }
	::= { cardTable 1 }

CardEntry ::= SEQUENCE {
	cardIndex		INTEGER,
	cardId			INTEGER,
	cardDescr		DisplayString,
	cardOperStatus	INTEGER,
	cardAdminStatus	INTEGER,
	cardGoodPackets	Counter,
	cardGoodOctets	Counter,
	cardNumAddresses Counter,
	cardCrcErrors	Counter,
	cardAlignErrors	Counter,
	cardFragErrors	Counter,
	cardPacketThresh Gauge,
	cardCrcThresh	Gauge,
	cardAlignThresh	Gauge,
	cardFragThresh	Gauge,
	cardNumPorts	INTEGER,
	cardOctetThresh	Gauge,
	cardNetworkMode	INTEGER
}

cardIndex OBJECT-TYPE
	SYNTAX	INTEGER
	ACCESS	read-only
	STATUS	mandatory
	DESCRIPTION
			"The slot in which the card is installed.  This
			value uniquely identifies the card.  Its value
			ranges between 1 and the value of cardNumSlots.

			When reported in a trap, the card relevant to the
			trap."
	::= { cardEntry 1 }

cardId OBJECT-TYPE
	SYNTAX	INTEGER {
			ods294-e(1),		-- SNMP management card
			ods294-8(4),		-- network timing card
			ods294-7(5),		-- network timing card
			ods294-9(6),		-- timing/management card
			ods294-btC(8),		-- 12-port 10baseT card
			ods294-fr(9),		-- 12-port FOIRL card
			ods294-fo(10),		-- 12-port fiber-optic card
			ods294-aui(11),		-- 12-port AUI card
			ods294-tp(12),		-- 12-port twisted-pair card
			ods294-btB(13),		-- 12-port 10baseT card
			ods294-bts(14),		-- 12-port 10baseT card
			ods294-btm(15),		-- 12-port 10baseT card
			ods294-tn(24),		--  8-port thin-net card
			ods294-ts8(27),		--  8-port terminal server card
			ods294-ts16(28),	-- 16-port terminal server card
			ods294-br(29),		-- ethernet bridge card
			ods294-sam(30),		-- 12-port 10baseT card
			ods294-tfr(31),		-- 12-port 10baseT/FOIRL card
			ods294-trf(45),		-- fiber-optic token ring card
			ods294-tr9(46),		-- DB9 token ring card
			ods294-rj(47),		-- RJ-45 token ring card
			ods294-rc(59),		-- token ring interface card
			starnet(128),		-- ethernet star network port
			ods263(134),		--  8-port tristed-pair star
			ods261(135),		-- 16-port twisted-pair star
			ods251(139),		-- 16-port AUI star
			ods243(142),		--  8-port fiber-optic star
			ods241(143)			-- 16-port fiber-optic star
		}
	ACCESS	read-only
	STATUS	mandatory
	DESCRIPTION
			"The type of card installed in the concentrator.
			For non-modular concentrators, the value is the
			same as that of boxId."
	::= { cardEntry 2 }

cardDescr OBJECT-TYPE
	SYNTAX	DisplayString (SIZE (0..255))
	ACCESS	read-only
	STATUS	mandatory
	DESCRIPTION
			"A textual description of the card including the
			ODS model number, media type and number of
			ports.  For non-modular concentrators, the value
			is the same as that of boxDescr."
	::= { cardEntry 3 }

cardOperStatus OBJECT-TYPE
	SYNTAX	INTEGER {
			up(1),
			down(2)
		}
	ACCESS	read-only
	STATUS	deprecated
	DESCRIPTION
			"The current operational state of the card.  Note
			that this object currently has no meaning and may
			be deleted from future versions of the MIB."
	::= { cardEntry 4 }

cardAdminStatus OBJECT-TYPE
	SYNTAX	INTEGER {
			up(1),
			down(2)
		}
	ACCESS	read-write
	STATUS	deprecated
	DESCRIPTION
			"The desired state of the card.  Note that this
			object currently has no meaning and may be deleted
			from future versions of the MIB."
	::= { cardEntry 5 }

cardNetworkMode OBJECT-TYPE
	SYNTAX	INTEGER {
			unsupported(1),
			connected(2),
			stand-alone(3)
		}
	ACCESS	read-write
	STATUS	mandatory
	DESCRIPTION
			"The state of the back-plane connection on the
			card.  If the value is stand-alone(3), the ports
			on the card form a separate, isolated network
			from the rest of the cards in the concentrator. 
			If the value is unsupported(1), the card is
			always connected and can not be changed."
	::= { cardEntry 18 }

cardNumPorts OBJECT-TYPE
	SYNTAX	INTEGER
	ACCESS	read-only
	STATUS	mandatory
	DESCRIPTION
			"The number of configurable ports on the card. 
			For some cards, the value may be zero."
	::= { cardEntry 16 }

cardNumAddresses OBJECT-TYPE
	SYNTAX	Counter
	ACCESS	read-only
	STATUS	mandatory
	DESCRIPTION
			"The number of unique, physical, source addresses
			contained in non-errored packets received on the
			card.  Note that this object is not maintained if
			the value of adminAddrStatEnable is disabled(2)."
	::= { cardEntry 8 }

cardGoodPackets OBJECT-TYPE
	SYNTAX	Counter
	ACCESS	read-only
	STATUS	mandatory
	DESCRIPTION
			"The number of non-errored packets received on the
			card.  Note that this object is not maintained if 
			the value of adminPktStatEnable is disabled(2)."
	::= { cardEntry 6 }

cardGoodOctets OBJECT-TYPE
	SYNTAX	Counter
	ACCESS	read-only
	STATUS	mandatory
	DESCRIPTION
			"The number of octets contained in non-errored
			packets received on the card.  Note that this object
			is not maintained if the value of adminPktStatEnable
			is disabled(2)."
	::= { cardEntry 7 }

cardCrcErrors OBJECT-TYPE
	SYNTAX	Counter
	ACCESS	read-only
	STATUS	mandatory
	DESCRIPTION
			"The number of packets received on the card which
			had CRC errors.  Note that this object is not
			maintained if the value of adminPktStatEnable is
			disabled(2)."
	::= { cardEntry 9 }

cardAlignErrors OBJECT-TYPE
	SYNTAX	Counter
	ACCESS	read-only
	STATUS	mandatory
	DESCRIPTION
			"The number of packets received on the card which
			had frame alignment errors.  Note that this object 
			is not maintained if the value of adminPktStatEnable
			is disabled(2)."
	::= { cardEntry 10 }

cardFragErrors OBJECT-TYPE
	SYNTAX	Counter
	ACCESS	read-only
	STATUS	mandatory
	DESCRIPTION
			"The number of packets received on the card which
			contained fewer than 64 octets.  Note that this
			object is not maintained if the value of admin-
			PktStatEnable is disabled(2)."
	::= { cardEntry 11 }

cardPacketThresh OBJECT-TYPE
	SYNTAX	Gauge
	ACCESS	read-write
	STATUS	mandatory
	DESCRIPTION
			"A threshold for monitoring the number of non-
			errored packets received on the card.  If the
			measured number of packets per second equals or
			exceeds this value, a card-class trap will be
			sent to each network manager defined in the
			adminTrapTable.  Monitoring of this threshold is
			disabled if the value is zero or if the value of
			adminPktStatEnable is disabled(2).

			When reported in a trap, the measured number of
			non-errored packets per second received on the
			card."
	::= { cardEntry 12 }

cardOctetThresh OBJECT-TYPE
	SYNTAX	Gauge
	ACCESS	read-write
	STATUS	mandatory
	DESCRIPTION
			"A threshold for monitoring the number of octets
			contained in non-errored packets received on the
			card.  If the measured number of octets per
			second equals or exceeds this value, a card-class
			trap will be sent to each network manager defined
			in the adminTrapTable.  Monitoring of this
			threshold is disabled if the value is zero or if
			the value of adminPktStatEnable is disabled(2).

			When reported in a trap, the measured number of
			octets per second contained in non-errored second
			received on the card."
	::= { cardEntry 17 }

cardCrcThresh OBJECT-TYPE
	SYNTAX	Gauge
	ACCESS	read-write
	STATUS	mandatory
	DESCRIPTION
			"A threshold for monitoring the number of packets
			received on the card which had CRC errors.  If
			the measured number of packets per second equals
			or exceeds this value, a card-class trap will be
			sent to each network manager defined in the
			adminTrapTable.  Monitoring of this threshold is
			disabled if the value is zero or if the value of
			adminPktStatEnable is disabled(2).

			When reported in a trap, the measured number of
			packets per second received on the card which had
			CRC errors."
	::= { cardEntry 13 }

cardAlignThresh OBJECT-TYPE
	SYNTAX	Gauge
	ACCESS	read-write
	STATUS	mandatory
	DESCRIPTION
			"A threshold for monitoring the number of packets
			received on the card which had frame alignment
			errors.  If the measured number of packets per
			second equals or exceeds this value, a card-class
			trap will be sent to each network manager defined
			in the adminTrapTable.  Monitoring of this
			threshold is disabled if the value is zero or if
			the value of adminPktStatEnable is disabled(2).

			When reported in a trap, the measured number of
			packets per second received on the card which had
			frame alignment errors."
	::= { cardEntry 14 }

cardFragThresh OBJECT-TYPE
	SYNTAX	Gauge
	ACCESS	read-write
	STATUS	mandatory
	DESCRIPTION
			"A threshold for monitoring the number of packets
			received on the card which contained fewer than
			64 octets.  If the measured number of packets per
			second equals or exceeds this value, a card-class
			trap will be sent to each network manager defined
			in the adminTrapTable.  Monitoring of this
			threshold is disabled if the value is zero or if 
			the value of adminPktStatEnable is disabled(2).

			When reported in a trap, the measured number of
			packets per second received on the card which
			contained fewer than 64 octets."
	::= { cardEntry 15 }

-- --------------------------------------------------------

-- The port table contains information pertaining to each
-- configurable port in the concentrator.  The size of the
-- table may change dynamically as old cards are removed
-- or new ones are installed.

portTable OBJECT-TYPE
	SYNTAX	SEQUENCE OF PortEntry
	ACCESS	not-accessible
	STATUS	mandatory
	DESCRIPTION
			"A list of port entries for each interface port in
			the concentrator.  The number of entries is given
			by the sum of cardNumPorts for each card in the
			cardTable."
	::= { encPorts 1 }

portEntry OBJECT-TYPE
	SYNTAX	PortEntry
	ACCESS	not-accessible
	STATUS	mandatory
	DESCRIPTION
			"A port entry containing objects pertaining to an
			interface port in the concentrator."
	INDEX	{ portCard, portIndex }
	::= { portTable 1 }

PortEntry ::= SEQUENCE {
	portCard		INTEGER,
	portIndex		INTEGER,
	portOperStatus	INTEGER,
	portAdminStatus	INTEGER,
	portGoodPackets	Counter,
	portGoodOctets	Counter,
	portNumAddresses Counter,
	portCrcErrors	Counter,
	portAlignErrors	Counter,
	portFragErrors	Counter,
	portPacketThresh Gauge,
	portCrcThresh	Gauge,
	portAlignThresh	Gauge,
	portFragThresh	Gauge,
	portOctetThresh	Gauge,
	portLinkStatus	INTEGER,
	portAutoOffEnable INTEGER,
	portAddrTrapEnable INTEGER
}

portCard OBJECT-TYPE
	SYNTAX	INTEGER
	ACCESS	read-only
	STATUS	mandatory
	DESCRIPTION
			"The card on which the port exists.  The card
			identified by this value is the same card as
			identified by the same value of cardIndex.

			When reported in a trap, the card relevant to the
			trap."
	::= { portEntry 1 }

portIndex OBJECT-TYPE
	SYNTAX	INTEGER
	ACCESS	read-only
	STATUS	mandatory
	DESCRIPTION
			"An integer which uniquely identifes this port on
			the card.  Its value ranges between 1 and the
			value of cardNumPorts for the card.

			When reported in a trap, the port relevant to the
			trap."
	::= { portEntry 2 }

portOperStatus OBJECT-TYPE
	SYNTAX	INTEGER {
			up(1),
			down(2)
		}
	ACCESS	read-only
	STATUS	mandatory
	DESCRIPTION
			"The current operational state of the port.  If
			the value is down(2), no data is passed through
			the port."
	::= { portEntry 3 }

portAdminStatus OBJECT-TYPE
	SYNTAX	INTEGER {
			up(1),
			down(2)
		}
	ACCESS	read-write
	STATUS	mandatory
	DESCRIPTION
			"The desired state of the port.  If the value is
			down(2), no data is passed through the port.

			When reported in a trap, the new state of the
			port.  If the value is down(2), the port was
			turned off as a result of the auto-shutoff
			feature being enabled."
	::= { portEntry 4 }

portLinkStatus OBJECT-TYPE
	SYNTAX	INTEGER {
			unsupported(1),
			link-good(2),
			partitioned(3),
			no-link(4)
		}
	ACCESS	read-only
	STATUS	mandatory
	DESCRIPTION
			"The link status for the port.  For media types
			that do not support link status, the value is
			always unsupported(1).

			When reported in a trap, the new link status of
			the port."
	::= { portEntry 16 }

portAutoOffEnable OBJECT-TYPE
	SYNTAX	INTEGER {
			enabled(1),
			disabled(2)
		}
	ACCESS	read-write
	STATUS	mandatory
	DESCRIPTION
			"The state of the auto-shutoff feature for the
			port.  If the value is enabled(1), the value of
			portAdminStatus for the port will be changed to
			down(1) whenever a port threshold is exceeded."
	::= { portEntry 17 }

portAddrTrapEnable OBJECT-TYPE
	SYNTAX	INTEGER {
			enabled(1),
			disabled(2)
		}
	ACCESS	read-write
	STATUS	mandatory
	DESCRIPTION
			"The state of the new-address detection feature
			for the port.  If the value is enabled(1), a
			newAddressTrap will be generated whenever a new,
			physical, source address is contained in a packet
			received by the concentrator on the port."
	::= { portEntry 18 }

portNumAddresses OBJECT-TYPE
	SYNTAX	Counter
	ACCESS	read-only
	STATUS	mandatory
	DESCRIPTION
			"The number of unique, physical, source addresses
			contained in non-errored packets received on the
			port.  Note that this object is not maintained if 
			the value of adminAddrStatEnable is disabled(2)."
	::= { portEntry 7 }

portGoodPackets OBJECT-TYPE
	SYNTAX	Counter
	ACCESS	read-only
	STATUS	mandatory
	DESCRIPTION
			"The number of non-errored packets received on the
			port.  Note that this object is not maintained if 
			the value of adminPktStatEnable is disabled(2)."
	::= { portEntry 5 }

portGoodOctets OBJECT-TYPE
	SYNTAX	Counter
	ACCESS	read-only
	STATUS	mandatory
	DESCRIPTION
			"The number of octets contained in non-errored
			packets received on the port.  Note that this object
			is not maintained if the value of adminPktStatEnable 
			is disabled(2)."
	::= { portEntry 6 }

portCrcErrors OBJECT-TYPE
	SYNTAX	Counter
	ACCESS	read-only
	STATUS	mandatory
	DESCRIPTION
			"The number of packets received on the port which
			had CRC errors.  Note that this object is not
			maintained if the value of adminPktStatEnable is
			disabled(2)."
	::= { portEntry 8 }

portAlignErrors OBJECT-TYPE
	SYNTAX	Counter
	ACCESS	read-only
	STATUS	mandatory
	DESCRIPTION
			"The number of packets received on the port which
			had frame alignment errors.  Note that this object 
			is not maintained if the value of adminPktStatEnable
			is disabled(2)."
	::= { portEntry 9 }

portFragErrors OBJECT-TYPE
	SYNTAX	Counter
	ACCESS	read-only
	STATUS	mandatory
	DESCRIPTION
			"The number of packets received on the port which
			contained fewer than 64 octets.  Note that this 
			object is not maintained if the value of admin-
			PktStatEnable is disabled(2)."
	::= { portEntry 10 }

portPacketThresh OBJECT-TYPE
	SYNTAX	Gauge
	ACCESS	read-write
	STATUS	mandatory
	DESCRIPTION
			"A threshold for monitoring the number of non-
			errored packets received on the port.  If the
			measured number of packets per second equals or
			exceeds this value, a port-class trap will be
			sent to each network manager defined in the
			adminTrapTable.  Monitoring of this threshold is
			disabled if the value is zero or if the value of
			adminPktStatEnable is disabled(2).

			When reported in a trap, the measured number of
			non-errored packets per second received on the
			port."
	::= { portEntry 11 }

portOctetThresh OBJECT-TYPE
	SYNTAX	Gauge
	ACCESS	read-write
	STATUS	mandatory
	DESCRIPTION
			"A threshold for monitoring the number of octets
			contained in non-errored packets received on the
			port.  If the measured number of octets per
			second equals or exceeds this value, a port-class
			trap will be sent to each network manager defined
			in the adminTrapTable.  Monitoring of this
			threshold is disabled if the value is zero or if 
			the value of adminPktStatEnable is disabled(2).

			When reported in a trap, the measured number of
			octets per second contained in non-errored second
			received on the port."
	::= { portEntry 15 }

portCrcThresh OBJECT-TYPE
	SYNTAX	Gauge
	ACCESS	read-write
	STATUS	mandatory
	DESCRIPTION
			"A threshold for monitoring the number of packets
			received on the port which had CRC errors.  If
			the measured number of packets per second equals
			or exceeds this value, a port-class trap will be
			sent to each network manager defined in the
			adminTrapTable.  Monitoring of this threshold is
			disabled if the value is zero or if the value of
			adminPktStatEnable is disabled(2).

			When reported in a trap, the measured number of
			packets per secondreceived on the port which had
			CRC errors."
	::= { portEntry 12 }

portAlignThresh OBJECT-TYPE
	SYNTAX	Gauge
	ACCESS	read-write
	STATUS	mandatory
	DESCRIPTION
			"A threshold for monitoring the number of packets
			received on the port which had frame alignment
			errors.  If the measured number of packets per
			second equals or exceeds this value, a port-class
			trap will be sent to each network manager defined
			in the adminTrapTable.  Monitoring of this
			threshold is disabled if the value is zero or if 
			the value of adminPktStatEnable is disabled(2).

			When reported in a trap, the measured number of
			packets per second received on the port which had
			frame alignment errors."
	::= { portEntry 13 }

portFragThresh OBJECT-TYPE
	SYNTAX	Gauge
	ACCESS	read-write
	STATUS	mandatory
	DESCRIPTION
			"A threshold for monitoring the number of packets
			received on the port which contained fewer than
			64 octets.  If the measured number of packets per
			second equals or exceeds this value, a port-class
			trap will be sent to each network manager defined
			in the adminTrapTable.  Monitoring of this
			threshold is disabled if the value is zero or if 
			the value of adminPktStatEnable is disabled(2).

			When reported in a trap, the measured number of
			packets per second received on the port which
			contained fewer than 64 octets."
	::= { portEntry 14 }

-- --------------------------------------------------------

-- The admin group contains objects pertaining to
-- administration of the agent.

adminReboot OBJECT-TYPE
	SYNTAX	INTEGER
	ACCESS	write-only
	STATUS	mandatory
	DESCRIPTION
			"Setting this object to any legal, ASN.1 value
			recycles the management agent in the concentrator."
	::= { encAdmin 16 }

adminLocalTime OBJECT-TYPE
	SYNTAX	OCTET STRING
	ACCESS	read-write
	STATUS	mandatory
	DESCRIPTION
			"The local time of day at the concentrator.  The
			value is a string of three binary-coded-decimal
			octets in the form HH MM SS, where HH is the hour
			(24 hour format), MM is the minutes and SS is the
			seconds.

			The local time of day is only used for out-of-
			band management via the asynchronous port on the
			concentrator."
	::= { encAdmin 1 }

adminLocalDate OBJECT-TYPE
	SYNTAX	OCTET STRING
	ACCESS	read-write
	STATUS	mandatory
	DESCRIPTION
			"The local date at the concentrator.  The value is
			a string of three binary-coded-decimal octets in
			the form YY MM DD, where YY is the year, MM is
			the month and DD is the day.

			The local date is only used for out-of-band
			management via the asynchronous port on the
			concentrator."
	::= { encAdmin 2 }

adminSecureTerm OBJECT-TYPE
	SYNTAX	INTEGER {
			secured(1),
			unsecured(2)
		}
	ACCESS	read-write
	STATUS	mandatory
	DESCRIPTION
			"The status of the out-of-band interface.  If the
			value is secured(1), the user is be required to
			enter a super-user level community name before any
			management functions can be accessed."
	::= { encAdmin 17 }

adminPrivilege OBJECT-TYPE
	SYNTAX	INTEGER {
			read-only(1),
			read-write(2),
			super-user(3)
		}
	ACCESS	read-only
	STATUS	mandatory
	DESCRIPTION
			"The access privilege afforded the community name
			used in the requesting PDU.  This value allows a
			network manager to easily determine its ability
			to read and write protected objects."
	::= { encAdmin 9 }

adminTrapId OBJECT-TYPE
	SYNTAX	INTEGER
	ACCESS	read-only
	STATUS	mandatory
	DESCRIPTION
			"The number of unique traps generated by the agent
			since it was reset.

			When reported in a trap, an integer which
			uniquely identifies the trap."
	::= { encAdmin 7 }

adminTrapAddress OBJECT-TYPE
	SYNTAX	IpAddress
	ACCESS	not-accessible
	STATUS	mandatory
	DESCRIPTION
			"When reported in a trap, the source IP address
			of a PDU which resulted in an authentication
			failure."
	::= { encAdmin 8 }

adminPktStatEnable OBJECT-TYPE
	SYNTAX	INTEGER {
			enabled(1),
			disabled(2)
		}
	ACCESS	read-write
	STATUS	mandatory
	DESCRIPTION
			"The state of the packet statistics collection
			feature.  If the value is enabled(1), the
			management agent will maintain statistics for all
			packets received by the concentrator on a box,
			card and port basis.

			The value is normally enabled(1).  It should only
			be set to disabled(2) during periods of excessively
			high network traffic when the management agent must
			remain available for other management activities."
	::= { encAdmin 12 }

adminAddrStatEnable OBJECT-TYPE
	SYNTAX	INTEGER {
			enabled(1),
			disabled(2)
		}
	ACCESS	read-write
	STATUS	mandatory
	DESCRIPTION
			"The state of the address statistics collection
			feature.  If the value is enabled(1), the manage-
			ment agent will maintain statistics for all packets
			received by the concentrator on a physical, source
			and destination address basis.

			The value is normally enabled(1) but can be set to
			disabled(2) when address-related statistics are not
			needed.  It should be set to disabled(2) during
			periods of excessively high network traffic when the
			management agent must remain available for other
			management activities."
	::= { encAdmin 13 }

adminProtStatEnable OBJECT-TYPE
	SYNTAX	INTEGER {
			enabled(1),
			disabled(2)
		}
	ACCESS	read-write
	STATUS	mandatory
	DESCRIPTION
			"The state of the protocol statistics collection
			feature.  If the value is enabled(1), the manage-
			ment agent will maintain statistics for all packets
			received by the concentrator on a top-level protocol
			basis.

			The value is normally disabled(2).  It should only
			be set to enabled(1) when protocol-related statis-
			tics are needed as it adversely affects performance
			of the management agent in the concetrator."
	::= { encAdmin 14 }

adminIpCheckEnable OBJECT-TYPE
	SYNTAX	INTEGER {
			enabled(1),
			disabled(2)
		}
	ACCESS	read-write
	STATUS	mandatory
	DESCRIPTION
			"The state of the IP address detection feature.  If
			the value is enabled(1) and the value of adminAddr-
			StatEnable is also enabled(1), the management agent
			will detect the IP address used by each physical
			source address in any TCP/IP packets received by the
			concentrator.

			The value is normally disabled(2).  It should only
			be set to enabled(1) when protocol-related statis-
			tics are needed as it adversely affects performance
			of the management agent in the concetrator."
	::= { encAdmin 15 }

-- --------------------------------------------------------

-- The admin access table contains mappings of community
-- names to access privileges.  Use of this table allows
-- several network management stations to have differing
-- levels of access to the agent.
-- 
-- The current access privileges are as follows:
-- 
-- read-only:	writable objects can not be written,
--				protected objects can not be read.
-- read-write:	some writable objects can be written,
--				protected objects can not be read.
-- super-user:	all writable objects can be written,
--				protected objects can be read and
--				written.

accMaxEntries OBJECT-TYPE
	SYNTAX	INTEGER
	ACCESS	read-only
	STATUS	mandatory
	DESCRIPTION
			"The maximum number of access privilege entries
			allowed in adminAccessTable."
	::= { encAdmin 10 }

adminAccessTable OBJECT-TYPE
	SYNTAX	SEQUENCE OF AdminAccessEntry
	ACCESS	not-accessible
	STATUS	mandatory
	DESCRIPTION
			"A list of access entries mapping community names
			into access privileges.  The maximum number of
			entries is given by accMaxEntries."
	::= { encAdmin 5 }

adminAccessEntry OBJECT-TYPE
	SYNTAX	AdminAccessEntry
	ACCESS	not-accessible
	STATUS	mandatory
	DESCRIPTION
			"An access entry which maps a community name into
			an access privilege."
	INDEX	{ accIndex }
	::= { adminAccessTable 1 }

AdminAccessEntry ::= SEQUENCE {
	accIndex		INTEGER,
	accCommunity	OCTET STRING,
	accPrivilege	INTEGER,
	accDelete		INTEGER
}

accIndex OBJECT-TYPE
	SYNTAX	INTEGER
	ACCESS	read-only
	STATUS	mandatory
	DESCRIPTION
			"An integer which uniquely identifies this entry."
	::= { adminAccessEntry 1 }

accCommunity OBJECT-TYPE
	SYNTAX	OCTET STRING
	ACCESS	read-write
	STATUS	mandatory
	DESCRIPTION
			"The community name for the entry.
			
			Setting this object to a null string effectively
			invalidates the entry.  However, accDelete should
			be used to delete entries as it resets all
			parameters to default settings."
	DEFVAL	{ "" }
	::= { adminAccessEntry 2 }

accPrivilege OBJECT-TYPE
	SYNTAX	INTEGER {
			read-only(1),
			read-write(2),
			super-user(3)
		}
	ACCESS	read-write
	STATUS	mandatory
	DESCRIPTION
			"The access privilege afforded the community name
			in the entry."
	DEFVAL	{ read-only }
	::= { adminAccessEntry 3 }

accDelete OBJECT-TYPE
	SYNTAX	INTEGER
	ACCESS	write-only
	STATUS	mandatory
	DESCRIPTION
			"Setting this object to any legal, ASN.1 value
			deletes the entry for the community name."
	::= { adminAccessEntry 4 }

-- --------------------------------------------------------

-- The admin trap table contains entries for each network
-- manager which receives traps from the agent.  Each class
-- of trap can be individaully enabled or diabled.

trapMaxEntries OBJECT-TYPE
	SYNTAX	INTEGER
	ACCESS	read-only
	STATUS	mandatory
	DESCRIPTION
			"The maximum number of network manager entries
			allowed in adminTrapTable."
	::= { encAdmin 11 }

adminTrapTable OBJECT-TYPE
	SYNTAX	SEQUENCE OF AdminTrapEntry
	ACCESS	not-accessible
	STATUS	mandatory
	DESCRIPTION
			"A list of trap entries for each network manager
			which receives traps from the agent.  The maximum
			number of entries is given by trapMaxEntries."
	::= { encAdmin 6 }

adminTrapEntry OBJECT-TYPE
	SYNTAX	AdminTrapEntry
	ACCESS	not-accessible
	STATUS	mandatory
	DESCRIPTION
			"A trap entry containing objects pertaining to a
			network manager which receives traps from the
			agent."
	INDEX	{ trapDestAddress }
	::= { adminTrapTable 1 }

AdminTrapEntry ::= SEQUENCE {
	trapCommunity		OCTET STRING,
	trapDestAddress		IpAddress,
	trapBoxEnable		INTEGER,
	trapCardEnable		INTEGER,
	trapPortEnable		INTEGER,
	trapAddrEnable		INTEGER,
	trapStdEnable		INTEGER,
	trapDelete			INTEGER
}

trapDestAddress OBJECT-TYPE
	SYNTAX	IpAddress
	ACCESS	read-write
	STATUS	mandatory
	DESCRIPTION
			"The IP address of the management station to
			receive traps.
			
			Note that setting this object to a value of
			all zeros effectively invalidates the entry.
			However, trapDelete should be used to delete
			entries as it resets all parameters to default
			settings."
	::= { adminTrapEntry 3 }

trapCommunity OBJECT-TYPE
	SYNTAX	OCTET STRING
	ACCESS	read-write
	STATUS	mandatory
	DESCRIPTION
			"The community name used in traps sent to the
			management station."
	DEFVAL	{ "" }
	::= { adminTrapEntry 2 }

trapStdEnable OBJECT-TYPE
	SYNTAX	INTEGER {
			enabled(1),
			disabled(2)
		}
	ACCESS	read-write
	STATUS	mandatory
	DESCRIPTION
			"The state of the standard-class trap enable for
			the management station.  If the value is
			disabled(2), standard SNMP traps will not be
			sent."
	DEFVAL	{ disabled }
	::= { adminTrapEntry 8 }

trapBoxEnable OBJECT-TYPE
	SYNTAX	INTEGER {
			enabled(1),
			disabled(2)
		}
	ACCESS	read-write
	STATUS	mandatory
	DESCRIPTION
			"The state of the box-class trap enable for the
			management station.  If the value is disabled(2),
			box-class traps will not be sent."
	DEFVAL	{ disabled }
	::= { adminTrapEntry 4 }

trapCardEnable OBJECT-TYPE
	SYNTAX	INTEGER {
			enabled(1),
			disabled(2)
		}
	ACCESS	read-write
	STATUS	mandatory
	DESCRIPTION
			"The state of the card-class trap enable for the
			management station.  If the value is disabled(2),
			card-class traps will not be sent."
	DEFVAL	{ disabled }
	::= { adminTrapEntry 5 }

trapPortEnable OBJECT-TYPE
	SYNTAX	INTEGER {
			enabled(1),
			disabled(2)
		}
	ACCESS	read-write
	STATUS	mandatory
	DESCRIPTION
			"The state of the port-class trap enable for the
			management station.  If the value is disabled(2),
			port-class traps will not be sent."
	DEFVAL	{ disabled }
	::= { adminTrapEntry 6 }

trapAddrEnable OBJECT-TYPE
	SYNTAX	INTEGER {
			enabled(1),
			disabled(2)
		}
	ACCESS	read-write
	STATUS	mandatory
	DESCRIPTION
			"The state of the address-class trap enable for
			the management station.  If the value is
			disabled(2), address- class traps will not be
			sent."
	DEFVAL	{ disabled }
	::= { adminTrapEntry 7 }

trapDelete OBJECT-TYPE
	SYNTAX	INTEGER
	ACCESS	write-only
	STATUS	mandatory
	DESCRIPTION
			"Setting this object to any legal, ASN.1 value
			deletes the entry for the management station."
	::= { adminTrapEntry 9 }

 
END
