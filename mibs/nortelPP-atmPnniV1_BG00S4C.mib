Nortel-Magellan-Passport-AtmPnniMIB
DEFINITIONS ::= BEGIN



IMPORTS

      OBJECT-TYPE
   FROM RFC-1212

      passportMIBs
   FROM Nortel-Magellan-Passport-UsefulDefinitionsMIB

      Counter32,
      DisplayString,
      StorageType,
      RowStatus,
      Gauge32,
      Integer32,
      Unsigned32
   FROM Nortel-Magellan-Passport-StandardTextualConventionsMIB

      Hex,
      NonReplicated,
      HexString,
      FixedPoint1,
      AsciiStringIndex
   FROM Nortel-Magellan-Passport-TextualConventionsMIB

      atmIfVptIndex,
      atmIfVpt,
      atmIfIndex,
      atmIf
   FROM Nortel-Magellan-Passport-AtmCoreMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmPnni Enterprise MIB."

atmPnniMIB OBJECT IDENTIFIER ::= { passportMIBs 72 }










-- AtmIf/n VirtualPathTerminator/m Pnni
-- This component represents a virtual ATM Private Network-
-- Network Interface (PNNI) interface. If this component is 
-- provisioned, neither a Uni nor a Iisp component can be provisioned 
-- under the same Vpt component. Also, the ARtg Pnni component and 
-- the ConfiguredNode component corresponding to the participation 
-- of this node in a lowest level peer group must both exist if a Pnni 
-- component is to be provisioned under a Vpt component. If this 
-- component is deleted, then all associated Vcc components are 
-- deleted.

atmIfVptPnni OBJECT IDENTIFIER ::= { atmIfVpt 7 }



atmIfVptPnniRowStatusTable OBJECT-TYPE
   SYNTAX     SEQUENCE OF AtmIfVptPnniRowStatusEntry
   ACCESS     not-accessible
   STATUS     mandatory
   DESCRIPTION
     "This entry controls the addition and deletion of 
      atmIfVptPnni components."
::= { atmIfVptPnni 1 }

atmIfVptPnniRowStatusEntry OBJECT-TYPE
   SYNTAX     AtmIfVptPnniRowStatusEntry
   ACCESS     not-accessible
   STATUS     mandatory
   DESCRIPTION
     "A single entry in the table represents a single 
      atmIfVptPnni component."
   INDEX {
      atmIfIndex,
      atmIfVptIndex,
      atmIfVptPnniIndex }
::= { atmIfVptPnniRowStatusTable 1 }

AtmIfVptPnniRowStatusEntry ::= SEQUENCE {
   atmIfVptPnniRowStatus
      RowStatus,
   atmIfVptPnniComponentName
      DisplayString,
   atmIfVptPnniStorageType
      StorageType,
   atmIfVptPnniIndex
      NonReplicated }

atmIfVptPnniRowStatus OBJECT-TYPE
   SYNTAX     RowStatus 
   ACCESS     read-write
   STATUS     mandatory
   DESCRIPTION
     "This variable is used as the basis for SNMP naming of
      atmIfVptPnni components.
      These components can be added and deleted."
::= { atmIfVptPnniRowStatusEntry 1 }

atmIfVptPnniComponentName OBJECT-TYPE
   SYNTAX     DisplayString 
   ACCESS     read-only
   STATUS     mandatory
   DESCRIPTION
     "This variable provides the component's string name for
      use with the ASCII Console Interface"
::= { atmIfVptPnniRowStatusEntry 2 }

atmIfVptPnniStorageType OBJECT-TYPE
   SYNTAX     StorageType 
   ACCESS     read-only
   STATUS     mandatory
   DESCRIPTION
     "This variable represents the storage type value for the
      atmIfVptPnni tables."
::= { atmIfVptPnniRowStatusEntry 4 }

atmIfVptPnniIndex OBJECT-TYPE
   SYNTAX     NonReplicated 
   ACCESS     not-accessible
   STATUS     mandatory
   DESCRIPTION
     "This variable represents the index for the atmIfVptPnni tables."
::= { atmIfVptPnniRowStatusEntry 10 }

atmIfVptPnniProvTable OBJECT-TYPE
   SYNTAX     SEQUENCE OF AtmIfVptPnniProvEntry
   ACCESS     not-accessible
   STATUS     mandatory
   DESCRIPTION
     "This group contains the provisionable attributes for the Pnni
      component."
::= { atmIfVptPnni 10 }

atmIfVptPnniProvEntry OBJECT-TYPE
   SYNTAX     AtmIfVptPnniProvEntry
   ACCESS     not-accessible
   STATUS     mandatory
   DESCRIPTION
     "An entry in the atmIfVptPnniProvTable."
   INDEX {
      atmIfIndex,
      atmIfVptIndex,
      atmIfVptPnniIndex }
::= { atmIfVptPnniProvTable 1 }

AtmIfVptPnniProvEntry ::= SEQUENCE {
   atmIfVptPnniSoftPvcRetryPeriod
      Unsigned32,
   atmIfVptPnniSoftPvpAndPvcRetryPeriod
      Unsigned32,
   atmIfVptPnniSoftPvpAndPvcHoldOffTime
      Unsigned32 }

atmIfVptPnniSoftPvcRetryPeriod OBJECT-TYPE
   SYNTAX     Unsigned32 (20..999999)
   ACCESS     read-write
   STATUS     obsolete
   DESCRIPTION
     "This attribute represents the time in seconds to wait between call 
      setup retries. The resolution is to the nearest 10 seconds. 
      This attribute has been obsoleted and is replaced by the 
      softPvpAndPvcRetryPeriod attribute."
   DEFVAL     { 60 }
::= { atmIfVptPnniProvEntry 1 }

atmIfVptPnniSoftPvpAndPvcRetryPeriod OBJECT-TYPE
   SYNTAX     Unsigned32 (20..999999)
   ACCESS     read-write
   STATUS     mandatory
   DESCRIPTION
     "This attribute represents the time in seconds to wait between soft 
      PVP or soft PVC call  setup retries. The resolution is to the nearest 
      10 seconds."
   DEFVAL     { 60 }
::= { atmIfVptPnniProvEntry 2 }

atmIfVptPnniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { atmIfVptPnniProvEntry 5 }

atmIfVptPnniAdminWeightsTable OBJECT-TYPE
   SYNTAX     SEQUENCE OF AtmIfVptPnniAdminWeightsEntry
   ACCESS     not-accessible
   STATUS     mandatory
   DESCRIPTION
     "This group contains the provisionable administrative weights for the 
      Pnni component. These weights will be used by Generic 
      Connection Admission Control (GCAC) if administrative weight is 
      the selected optimization criterion."
::= { atmIfVptPnni 11 }

atmIfVptPnniAdminWeightsEntry OBJECT-TYPE
   SYNTAX     AtmIfVptPnniAdminWeightsEntry
   ACCESS     not-accessible
   STATUS     mandatory
   DESCRIPTION
     "An entry in the atmIfVptPnniAdminWeightsTable."
   INDEX {
      atmIfIndex,
      atmIfVptIndex,
      atmIfVptPnniIndex }
::= { atmIfVptPnniAdminWeightsTable 1 }

AtmIfVptPnniAdminWeightsEntry ::= SEQUENCE {
   atmIfVptPnniCbrWeight
      Unsigned32,
   atmIfVptPnniRtVbrWeight
      Unsigned32,
   atmIfVptPnniNrtVbrWeight
      Unsigned32,
   atmIfVptPnniUbrWeight
      Unsigned32 }

atmIfVptPnniCbrWeight OBJECT-TYPE
   SYNTAX     Unsigned32 (0..4294967295)
   ACCESS     read-write
   STATUS     mandatory
   DESCRIPTION
     "This attribute specifies the administrative weight assigned for 
      setting up switched calls with a service category of Constant Bit 
      Rate (CBR) for this PNNI interface. The value specified will be 
      used by Generic Connection Admission Control (GCAC) if 
      administrative weight is the selected optimization criterion; the 
      higher the value, the less desirable the link will be in path selection."
   DEFVAL     { 5040 }
::= { atmIfVptPnniAdminWeightsEntry 1 }

atmIfVptPnniRtVbrWeight OBJECT-TYPE
   SYNTAX     Unsigned32 (0..4294967295)
   ACCESS     read-write
   STATUS     mandatory
   DESCRIPTION
     "This attribute specifies the administrative weight assigned for 
      setting up switched calls with a service category of Real-Time 
      Variable Bit Rate (RT-VBR) for this PNNI interface. The value 
      specified will be used by Generic Connection Admission Control 
      (GCAC) if administrative weight is the selected optimization 
      criterion; the higher the value, the less desirable the link will be in 
      path selection."
   DEFVAL     { 5040 }
::= { atmIfVptPnniAdminWeightsEntry 2 }

atmIfVptPnniNrtVbrWeight OBJECT-TYPE
   SYNTAX     Unsigned32 (0..4294967295)
   ACCESS     read-write
   STATUS     mandatory
   DESCRIPTION
     "This attribute specifies the administrative weight assigned for 
      setting up switched calls with a service category of Non Real-Time 
      Variable Bit Rate (NRT-VBR) for this PNNI interface. The value 
      specified will be used by Generic Connection Admission Control 
      (GCAC) if administrative weight is the selected optimization 
      criterion; the higher the value, the less desirable the link will be in 
      path selection."
   DEFVAL     { 5040 }
::= { atmIfVptPnniAdminWeightsEntry 3 }

atmIfVptPnniUbrWeight OBJECT-TYPE
   SYNTAX     Unsigned32 (0..4294967295)
   ACCESS     read-write
   STATUS     mandatory
   DESCRIPTION
     "This attribute specifies the administrative weight assigned for 
      setting up switched calls with a service category of Unspecified Bit 
      Rate (UBR) for this PNNI interface. The value specified will be 
      used by Generic Connection Admission Control (GCAC) if 
      administrative weight is the selected optimization criterion; the 
      higher the value, the less desirable the link will be in path selection."
   DEFVAL     { 5040 }
::= { atmIfVptPnniAdminWeightsEntry 4 }

atmIfVptPnniAcctOptTable OBJECT-TYPE
   SYNTAX     SEQUENCE OF AtmIfVptPnniAcctOptEntry
   ACCESS     not-accessible
   STATUS     mandatory
   DESCRIPTION
     "This group contains the provisionable attributes for accounting."
::= { atmIfVptPnni 12 }

atmIfVptPnniAcctOptEntry OBJECT-TYPE
   SYNTAX     AtmIfVptPnniAcctOptEntry
   ACCESS     not-accessible
   STATUS     mandatory
   DESCRIPTION
     "An entry in the atmIfVptPnniAcctOptTable."
   INDEX {
      atmIfIndex,
      atmIfVptIndex,
      atmIfVptPnniIndex }
::= { atmIfVptPnniAcctOptTable 1 }

AtmIfVptPnniAcctOptEntry ::= SEQUENCE {
   atmIfVptPnniAccountCollection
      OCTET STRING,
   atmIfVptPnniAccountConnectionType
      INTEGER,
   atmIfVptPnniAccountClass
      Unsigned32,
   atmIfVptPnniServiceExchange
      Unsigned32 }

atmIfVptPnniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { atmIfVptPnniAcctOptEntry 1 }

atmIfVptPnniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { atmIfVptPnniAcctOptEntry 2 }

atmIfVptPnniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { atmIfVptPnniAcctOptEntry 3 }

atmIfVptPnniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { atmIfVptPnniAcctOptEntry 4 }

atmIfVptPnniOperationalTable OBJECT-TYPE
   SYNTAX     SEQUENCE OF AtmIfVptPnniOperationalEntry
   ACCESS     not-accessible
   STATUS     mandatory
   DESCRIPTION
     "This group contains the operational attributes for a Pnni component."
::= { atmIfVptPnni 13 }

atmIfVptPnniOperationalEntry OBJECT-TYPE
   SYNTAX     AtmIfVptPnniOperationalEntry
   ACCESS     not-accessible
   STATUS     mandatory
   DESCRIPTION
     "An entry in the atmIfVptPnniOperationalTable."
   INDEX {
      atmIfIndex,
      atmIfVptIndex,
      atmIfVptPnniIndex }
::= { atmIfVptPnniOperationalTable 1 }

AtmIfVptPnniOperationalEntry ::= SEQUENCE {
   atmIfVptPnniPortId
      Unsigned32 }

atmIfVptPnniPortId OBJECT-TYPE
   SYNTAX     Unsigned32 (0..4294967295)
   ACCESS     read-only
   STATUS     mandatory
   DESCRIPTION
     "This attribute indicates the port id of the PNNI interface, which is 
      the parent AtmIf's instance number."
::= { atmIfVptPnniOperationalEntry 1 }

atmIfVptPnniVProvTable OBJECT-TYPE
   SYNTAX     SEQUENCE OF AtmIfVptPnniVProvEntry
   ACCESS     not-accessible
   STATUS     mandatory
   DESCRIPTION
     "This group contains the provisionable attributes for the Pnni 
      component which are specific to virtual PNNI interfaces."
::= { atmIfVptPnni 14 }

atmIfVptPnniVProvEntry OBJECT-TYPE
   SYNTAX     AtmIfVptPnniVProvEntry
   ACCESS     not-accessible
   STATUS     mandatory
   DESCRIPTION
     "An entry in the atmIfVptPnniVProvTable."
   INDEX {
      atmIfIndex,
      atmIfVptIndex,
      atmIfVptPnniIndex }
::= { atmIfVptPnniVProvTable 1 }

AtmIfVptPnniVProvEntry ::= SEQUENCE {
   atmIfVptPnniVpci
      Unsigned32 }

atmIfVptPnniVpci OBJECT-TYPE
   SYNTAX     Unsigned32 (0..255)
   ACCESS     read-write
   STATUS     mandatory
   DESCRIPTION
     "This attribute specifies the Virtual Path Connection Identifier 
      (VPCI) to be used between this signalling entity and its peer. The 
      VPCI of the peer virtual PNNI must have the same value for 
      switched connections to be set up across the interface."
   DEFVAL     { 0 }
::= { atmIfVptPnniVProvEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

atmIfVptPnniSig OBJECT IDENTIFIER ::= { atmIfVptPnni 2 }



atmIfVptPnniSigRowStatusTable OBJECT-TYPE
   SYNTAX     SEQUENCE OF AtmIfVptPnniSigRowStatusEntry
   ACCESS     not-accessible
   STATUS     mandatory
   DESCRIPTION
     "This entry controls the addition and deletion of 
      atmIfVptPnniSig components."
::= { atmIfVptPnniSig 1 }

atmIfVptPnniSigRowStatusEntry OBJECT-TYPE
   SYNTAX     AtmIfVptPnniSigRowStatusEntry
   ACCESS     not-accessible
   STATUS     mandatory
   DESCRIPTION
     "A single entry in the table represents a single 
      atmIfVptPnniSig component."
   INDEX {
      atmIfIndex,
      atmIfVptIndex,
      atmIfVptPnniIndex,
      atmIfVptPnniSigIndex }
::= { atmIfVptPnniSigRowStatusTable 1 }

AtmIfVptPnniSigRowStatusEntry ::= SEQUENCE {
   atmIfVptPnniSigRowStatus
      RowStatus,
   atmIfVptPnniSigComponentName
      DisplayString,
   atmIfVptPnniSigStorageType
      StorageType,
   atmIfVptPnniSigIndex
      NonReplicated }

atmIfVptPnniSigRowStatus OBJECT-TYPE
   SYNTAX     RowStatus 
   ACCESS     read-only
   STATUS     mandatory
   DESCRIPTION
     "This variable is used as the basis for SNMP naming of
      atmIfVptPnniSig components.
      These components cannot be added nor deleted."
::= { atmIfVptPnniSigRowStatusEntry 1 }

atmIfVptPnniSigComponentName OBJECT-TYPE
   SYNTAX     DisplayString 
   ACCESS     read-only
   STATUS     mandatory
   DESCRIPTION
     "This variable provides the component's string name for
      use with the ASCII Console Interface"
::= { atmIfVptPnniSigRowStatusEntry 2 }

atmIfVptPnniSigStorageType OBJECT-TYPE
   SYNTAX     StorageType 
   ACCESS     read-only
   STATUS     mandatory
   DESCRIPTION
     "This variable represents the storage type value for the
      atmIfVptPnniSig tables."
::= { atmIfVptPnniSigRowStatusEntry 4 }

atmIfVptPnniSigIndex OBJECT-TYPE
   SYNTAX     NonReplicated 
   ACCESS     not-accessible
   STATUS     mandatory
   DESCRIPTION
     "This variable represents the index for the atmIfVptPnniSig tables."
::= { atmIfVptPnniSigRowStatusEntry 10 }

atmIfVptPnniSigProvTable OBJECT-TYPE
   SYNTAX     SEQUENCE OF AtmIfVptPnniSigProvEntry
   ACCESS     not-accessible
   STATUS     mandatory
   DESCRIPTION
     "This attribute group contains the provisionable attributes for the 
      Signalling component."
::= { atmIfVptPnniSig 10 }

atmIfVptPnniSigProvEntry OBJECT-TYPE
   SYNTAX     AtmIfVptPnniSigProvEntry
   ACCESS     not-accessible
   STATUS     mandatory
   DESCRIPTION
     "An entry in the atmIfVptPnniSigProvTable."
   INDEX {
      atmIfIndex,
      atmIfVptIndex,
      atmIfVptPnniIndex,
      atmIfVptPnniSigIndex }
::= { atmIfVptPnniSigProvTable 1 }

AtmIfVptPnniSigProvEntry ::= SEQUENCE {
   atmIfVptPnniSigVci
      Unsigned32,
   atmIfVptPnniSigAddressConversion
      INTEGER }

atmIfVptPnniSigVci OBJECT-TYPE
   SYNTAX     Unsigned32 (0..65535)
   ACCESS     read-write
   STATUS     mandatory
   DESCRIPTION
     "This attribute specifies the signalling channel number."
   DEFVAL     { 5 }
::= { atmIfVptPnniSigProvEntry 1 }

atmIfVptPnniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { atmIfVptPnniSigProvEntry 2 }

atmIfVptPnniSigStateTable OBJECT-TYPE
   SYNTAX     SEQUENCE OF AtmIfVptPnniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVptPnniSig 11 }

atmIfVptPnniSigStateEntry OBJECT-TYPE
   SYNTAX     AtmIfVptPnniSigStateEntry
   ACCESS     not-accessible
   STATUS     mandatory
   DESCRIPTION
     "An entry in the atmIfVptPnniSigStateTable."
   INDEX {
      atmIfIndex,
      atmIfVptIndex,
      atmIfVptPnniIndex,
      atmIfVptPnniSigIndex }
::= { atmIfVptPnniSigStateTable 1 }

AtmIfVptPnniSigStateEntry ::= SEQUENCE {
   atmIfVptPnniSigAdminState
      INTEGER,
   atmIfVptPnniSigOperationalState
      INTEGER,
   atmIfVptPnniSigUsageState
      INTEGER }

atmIfVptPnniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVptPnniSigStateEntry 1 }

atmIfVptPnniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVptPnniSigStateEntry 2 }

atmIfVptPnniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVptPnniSigStateEntry 3 }

atmIfVptPnniSigOperTable OBJECT-TYPE
   SYNTAX     SEQUENCE OF AtmIfVptPnniSigOperEntry
   ACCESS     not-accessible
   STATUS     mandatory
   DESCRIPTION
     "This attribute contains the operational attributes for the 
      AtmSignalling component."
::= { atmIfVptPnniSig 12 }

atmIfVptPnniSigOperEntry OBJECT-TYPE
   SYNTAX     AtmIfVptPnniSigOperEntry
   ACCESS     not-accessible
   STATUS     mandatory
   DESCRIPTION
     "An entry in the atmIfVptPnniSigOperTable."
   INDEX {
      atmIfIndex,
      atmIfVptIndex,
      atmIfVptPnniIndex,
      atmIfVptPnniSigIndex }
::= { atmIfVptPnniSigOperTable 1 }

AtmIfVptPnniSigOperEntry ::= SEQUENCE {
   atmIfVptPnniSigLastTxCauseCode
      Unsigned32,
   atmIfVptPnniSigLastTxDiagCode
      Hex,
   atmIfVptPnniSigLastRxCauseCode
      Unsigned32,
   atmIfVptPnniSigLastRxDiagCode
      Hex }

atmIfVptPnniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { atmIfVptPnniSigOperEntry 1 }

atmIfVptPnniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfVptPnniSigOperEntry 2 }

atmIfVptPnniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { atmIfVptPnniSigOperEntry 3 }

atmIfVptPnniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfVptPnniSigOperEntry 4 }

atmIfVptPnniSigStatsTable OBJECT-TYPE
   SYNTAX     SEQUENCE OF AtmIfVptPnniSigStatsEntry
   ACCESS     not-accessible
   STATUS     mandatory
   DESCRIPTION
     "This attribute group contains the statistics associated with the 
      AtmSignalling component."
::= { atmIfVptPnniSig 13 }

atmIfVptPnniSigStatsEntry OBJECT-TYPE
   SYNTAX     AtmIfVptPnniSigStatsEntry
   ACCESS     not-accessible
   STATUS     mandatory
   DESCRIPTION
     "An entry in the atmIfVptPnniSigStatsTable."
   INDEX {
      atmIfIndex,
      atmIfVptIndex,
      atmIfVptPnniIndex,
      atmIfVptPnniSigIndex }
::= { atmIfVptPnniSigStatsTable 1 }

AtmIfVptPnniSigStatsEntry ::= SEQUENCE {
   atmIfVptPnniSigCurrentConnections
      Counter32,
   atmIfVptPnniSigPeakConnections
      Gauge32,
   atmIfVptPnniSigSuccessfulConnections
      Counter32,
   atmIfVptPnniSigFailedConnections
      Counter32,
   atmIfVptPnniSigTxPdus
      Counter32,
   atmIfVptPnniSigRxPdus
      Counter32,
   atmIfVptPnniSigCurrentPmpConnections
      Gauge32,
   atmIfVptPnniSigPeakPmpConnections
      Gauge32,
   atmIfVptPnniSigSuccessfulPmpConnections
      Counter32,
   atmIfVptPnniSigFailedPmpConnections
      Counter32,
   atmIfVptPnniSigNewCurrentConnections
      Gauge32 }

atmIfVptPnniSigCurrentConnections OBJECT-TYPE
   SYNTAX     Counter32 
   ACCESS     read-only
   STATUS     obsolete
   DESCRIPTION
     "This attribute indicates the total number of currently active 
      connections."
::= { atmIfVptPnniSigStatsEntry 1 }

atmIfVptPnniSigPeakConnections OBJECT-TYPE
   SYNTAX     Gauge32 (0..4294967295)
   ACCESS     read-only
   STATUS     mandatory
   DESCRIPTION
     "This attribute indicates the high water mark of active point-to-
      point and point-to-multipoint connections."
::= { atmIfVptPnniSigStatsEntry 2 }

atmIfVptPnniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { atmIfVptPnniSigStatsEntry 3 }

atmIfVptPnniSigFailedConnections OBJECT-TYPE
   SYNTAX     Counter32 
   ACCESS     read-only
   STATUS     mandatory
   DESCRIPTION
     "This attribute counts the total number of switched connections that 
      were not successfully established.The counter wraps to 0 when the 
      maximum value is exceeded."
::= { atmIfVptPnniSigStatsEntry 4 }

atmIfVptPnniSigTxPdus OBJECT-TYPE
   SYNTAX     Counter32 
   ACCESS     read-only
   STATUS     mandatory
   DESCRIPTION
     "This attribute counts the number of transmitted signalling 
      PDUs.The counter wraps to 0 when the maximum value is 
      exceeded."
::= { atmIfVptPnniSigStatsEntry 5 }

atmIfVptPnniSigRxPdus OBJECT-TYPE
   SYNTAX     Counter32 
   ACCESS     read-only
   STATUS     mandatory
   DESCRIPTION
     "This attribute counts the number of received signalling PDUs.The 
      counter wraps to 0 when the maximum value is exceeded."
::= { atmIfVptPnniSigStatsEntry 6 }

atmIfVptPnniSigCurrentPmpConnections OBJECT-TYPE
   SYNTAX     Gauge32 (0..4294967295)
   ACCESS     read-only
   STATUS     mandatory
   DESCRIPTION
     "This attribute indicates the number of currently active point-to-
      multipoint connections."
::= { atmIfVptPnniSigStatsEntry 7 }

atmIfVptPnniSigPeakPmpConnections OBJECT-TYPE
   SYNTAX     Gauge32 (0..4294967295)
   ACCESS     read-only
   STATUS     mandatory
   DESCRIPTION
     "This attribute indicates the high water mark of active point-to-
      multipoint connections."
::= { atmIfVptPnniSigStatsEntry 8 }

atmIfVptPnniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { atmIfVptPnniSigStatsEntry 9 }

atmIfVptPnniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { atmIfVptPnniSigStatsEntry 10 }

atmIfVptPnniSigNewCurrentConnections OBJECT-TYPE
   SYNTAX     Gauge32 (0..4294967295)
   ACCESS     read-only
   STATUS     mandatory
   DESCRIPTION
     "This attribute indicates the total number of currently active point-to-
      point and point-to-multipoint connections."
::= { atmIfVptPnniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfVptPnniSigVcd OBJECT IDENTIFIER ::= { atmIfVptPnniSig 2 }



atmIfVptPnniSigVcdRowStatusTable OBJECT-TYPE
   SYNTAX     SEQUENCE OF AtmIfVptPnniSigVcdRowStatusEntry
   ACCESS     not-accessible
   STATUS     mandatory
   DESCRIPTION
     "This entry controls the addition and deletion of 
      atmIfVptPnniSigVcd components."
::= { atmIfVptPnniSigVcd 1 }

atmIfVptPnniSigVcdRowStatusEntry OBJECT-TYPE
   SYNTAX     AtmIfVptPnniSigVcdRowStatusEntry
   ACCESS     not-accessible
   STATUS     mandatory
   DESCRIPTION
     "A single entry in the table represents a single 
      atmIfVptPnniSigVcd component."
   INDEX {
      atmIfIndex,
      atmIfVptIndex,
      atmIfVptPnniIndex,
      atmIfVptPnniSigIndex,
      atmIfVptPnniSigVcdIndex }
::= { atmIfVptPnniSigVcdRowStatusTable 1 }

AtmIfVptPnniSigVcdRowStatusEntry ::= SEQUENCE {
   atmIfVptPnniSigVcdRowStatus
      RowStatus,
   atmIfVptPnniSigVcdComponentName
      DisplayString,
   atmIfVptPnniSigVcdStorageType
      StorageType,
   atmIfVptPnniSigVcdIndex
      NonReplicated }

atmIfVptPnniSigVcdRowStatus OBJECT-TYPE
   SYNTAX     RowStatus 
   ACCESS     read-write
   STATUS     mandatory
   DESCRIPTION
     "This variable is used as the basis for SNMP naming of
      atmIfVptPnniSigVcd components.
      These components can be added and deleted."
::= { atmIfVptPnniSigVcdRowStatusEntry 1 }

atmIfVptPnniSigVcdComponentName OBJECT-TYPE
   SYNTAX     DisplayString 
   ACCESS     read-only
   STATUS     mandatory
   DESCRIPTION
     "This variable provides the component's string name for
      use with the ASCII Console Interface"
::= { atmIfVptPnniSigVcdRowStatusEntry 2 }

atmIfVptPnniSigVcdStorageType OBJECT-TYPE
   SYNTAX     StorageType 
   ACCESS     read-only
   STATUS     mandatory
   DESCRIPTION
     "This variable represents the storage type value for the
      atmIfVptPnniSigVcd tables."
::= { atmIfVptPnniSigVcdRowStatusEntry 4 }

atmIfVptPnniSigVcdIndex OBJECT-TYPE
   SYNTAX     NonReplicated 
   ACCESS     not-accessible
   STATUS     mandatory
   DESCRIPTION
     "This variable represents the index for the atmIfVptPnniSigVcd tables."
::= { atmIfVptPnniSigVcdRowStatusEntry 10 }

atmIfVptPnniSigVcdProvTable OBJECT-TYPE
   SYNTAX     SEQUENCE OF AtmIfVptPnniSigVcdProvEntry
   ACCESS     not-accessible
   STATUS     mandatory
   DESCRIPTION
     "This group contains the provisionable traffic attributes for a control 
      channel."
::= { atmIfVptPnniSigVcd 10 }

atmIfVptPnniSigVcdProvEntry OBJECT-TYPE
   SYNTAX     AtmIfVptPnniSigVcdProvEntry
   ACCESS     not-accessible
   STATUS     mandatory
   DESCRIPTION
     "An entry in the atmIfVptPnniSigVcdProvTable."
   INDEX {
      atmIfIndex,
      atmIfVptIndex,
      atmIfVptPnniIndex,
      atmIfVptPnniSigIndex,
      atmIfVptPnniSigVcdIndex }
::= { atmIfVptPnniSigVcdProvTable 1 }

AtmIfVptPnniSigVcdProvEntry ::= SEQUENCE {
   atmIfVptPnniSigVcdTrafficDescType
      INTEGER,
   atmIfVptPnniSigVcdAtmServiceCategory
      INTEGER,
   atmIfVptPnniSigVcdQosClass
      INTEGER,
   atmIfVptPnniSigVcdTrafficShaping
      INTEGER,
   atmIfVptPnniSigVcdUnshapedTransmitQueueing
      INTEGER,
   atmIfVptPnniSigVcdUsageParameterControl
      INTEGER }

atmIfVptPnniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfVptPnniSigVcdProvEntry 1 }

atmIfVptPnniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfVptPnniSigVcdProvEntry 3 }

atmIfVptPnniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfVptPnniSigVcdProvEntry 21 }

atmIfVptPnniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfVptPnniSigVcdProvEntry 50 }

atmIfVptPnniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfVptPnniSigVcdProvEntry 60 }

atmIfVptPnniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfVptPnniSigVcdProvEntry 70 }

atmIfVptPnniSigVcdTdpTable OBJECT-TYPE
   SYNTAX     SEQUENCE OF AtmIfVptPnniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfVptPnniSigVcd 387 }

atmIfVptPnniSigVcdTdpEntry OBJECT-TYPE
   SYNTAX     AtmIfVptPnniSigVcdTdpEntry
   ACCESS     not-accessible
   STATUS     mandatory
   DESCRIPTION
     "An entry in the atmIfVptPnniSigVcdTdpTable."
   INDEX {
      atmIfIndex,
      atmIfVptIndex,
      atmIfVptPnniIndex,
      atmIfVptPnniSigIndex,
      atmIfVptPnniSigVcdIndex,
      atmIfVptPnniSigVcdTdpIndex }
::= { atmIfVptPnniSigVcdTdpTable 1 }

AtmIfVptPnniSigVcdTdpEntry ::= SEQUENCE {
   atmIfVptPnniSigVcdTdpIndex
      Integer32,
   atmIfVptPnniSigVcdTdpValue
      Unsigned32 }

atmIfVptPnniSigVcdTdpIndex OBJECT-TYPE
   SYNTAX     Integer32 (1..5)
   ACCESS     not-accessible
   STATUS     mandatory
   DESCRIPTION
     "This variable represents the atmIfVptPnniSigVcdTdpTable
      specific index for the atmIfVptPnniSigVcdTdpTable."
::= { atmIfVptPnniSigVcdTdpEntry 1 }

atmIfVptPnniSigVcdTdpValue OBJECT-TYPE
   SYNTAX     Unsigned32 (0..2147483647)
   ACCESS     read-write
   STATUS     mandatory
   DESCRIPTION
     "This variable represents an individual value for the
      atmIfVptPnniSigVcdTdpTable."
::= { atmIfVptPnniSigVcdTdpEntry 2 }


-- AtmIf/n Pnni RoutingControlChannel
-- AtmIf/n Vpt/m Pnni RoutingControlChannel
-- 
-- This component represents the Routing Control Channel (RCC) 
-- associated with a PNNI interface. The RCC is used to exchange 
-- routing information between nodes in a peer group.

atmIfVptPnniRcc OBJECT IDENTIFIER ::= { atmIfVptPnni 3 }



atmIfVptPnniRccRowStatusTable OBJECT-TYPE
   SYNTAX     SEQUENCE OF AtmIfVptPnniRccRowStatusEntry
   ACCESS     not-accessible
   STATUS     mandatory
   DESCRIPTION
     "This entry controls the addition and deletion of 
      atmIfVptPnniRcc components."
::= { atmIfVptPnniRcc 1 }

atmIfVptPnniRccRowStatusEntry OBJECT-TYPE
   SYNTAX     AtmIfVptPnniRccRowStatusEntry
   ACCESS     not-accessible
   STATUS     mandatory
   DESCRIPTION
     "A single entry in the table represents a single 
      atmIfVptPnniRcc component."
   INDEX {
      atmIfIndex,
      atmIfVptIndex,
      atmIfVptPnniIndex,
      atmIfVptPnniRccIndex }
::= { atmIfVptPnniRccRowStatusTable 1 }

AtmIfVptPnniRccRowStatusEntry ::= SEQUENCE {
   atmIfVptPnniRccRowStatus
      RowStatus,
   atmIfVptPnniRccComponentName
      DisplayString,
   atmIfVptPnniRccStorageType
      StorageType,
   atmIfVptPnniRccIndex
      NonReplicated }

atmIfVptPnniRccRowStatus OBJECT-TYPE
   SYNTAX     RowStatus 
   ACCESS     read-only
   STATUS     mandatory
   DESCRIPTION
     "This variable is used as the basis for SNMP naming of
      atmIfVptPnniRcc components.
      These components cannot be added nor deleted."
::= { atmIfVptPnniRccRowStatusEntry 1 }

atmIfVptPnniRccComponentName OBJECT-TYPE
   SYNTAX     DisplayString 
   ACCESS     read-only
   STATUS     mandatory
   DESCRIPTION
     "This variable provides the component's string name for
      use with the ASCII Console Interface"
::= { atmIfVptPnniRccRowStatusEntry 2 }

atmIfVptPnniRccStorageType OBJECT-TYPE
   SYNTAX     StorageType 
   ACCESS     read-only
   STATUS     mandatory
   DESCRIPTION
     "This variable represents the storage type value for the
      atmIfVptPnniRcc tables."
::= { atmIfVptPnniRccRowStatusEntry 4 }

atmIfVptPnniRccIndex OBJECT-TYPE
   SYNTAX     NonReplicated 
   ACCESS     not-accessible
   STATUS     mandatory
   DESCRIPTION
     "This variable represents the index for the atmIfVptPnniRcc tables."
::= { atmIfVptPnniRccRowStatusEntry 10 }

atmIfVptPnniRccProvTable OBJECT-TYPE
   SYNTAX     SEQUENCE OF AtmIfVptPnniRccProvEntry
   ACCESS     not-accessible
   STATUS     mandatory
   DESCRIPTION
     "This group contains the generic provisionable attributes of an Rcc 
      component."
::= { atmIfVptPnniRcc 10 }

atmIfVptPnniRccProvEntry OBJECT-TYPE
   SYNTAX     AtmIfVptPnniRccProvEntry
   ACCESS     not-accessible
   STATUS     mandatory
   DESCRIPTION
     "An entry in the atmIfVptPnniRccProvTable."
   INDEX {
      atmIfIndex,
      atmIfVptIndex,
      atmIfVptPnniIndex,
      atmIfVptPnniRccIndex }
::= { atmIfVptPnniRccProvTable 1 }

AtmIfVptPnniRccProvEntry ::= SEQUENCE {
   atmIfVptPnniRccVci
      Unsigned32 }

atmIfVptPnniRccVci OBJECT-TYPE
   SYNTAX     Unsigned32 (0..65535)
   ACCESS     read-write
   STATUS     mandatory
   DESCRIPTION
     "This attribute specifies the VCI for the Routing Control Channel 
      (RCC). It is not recommended that the value be changed from the 
      default of 18 unless absolutely necessary. If a different VCI is 
      specified, ensure that the RCC at the far end is provisioned to use 
      the same VCI, otherwise the RCC will not come up."
   DEFVAL     { 18 }
::= { atmIfVptPnniRccProvEntry 1 }

atmIfVptPnniRccHlParmsTable OBJECT-TYPE
   SYNTAX     SEQUENCE OF AtmIfVptPnniRccHlParmsEntry
   ACCESS     not-accessible
   STATUS     mandatory
   DESCRIPTION
     "This group contains the provisionable Hello protocol parameters for 
      an Rcc component."
::= { atmIfVptPnniRcc 11 }

atmIfVptPnniRccHlParmsEntry OBJECT-TYPE
   SYNTAX     AtmIfVptPnniRccHlParmsEntry
   ACCESS     not-accessible
   STATUS     mandatory
   DESCRIPTION
     "An entry in the atmIfVptPnniRccHlParmsTable."
   INDEX {
      atmIfIndex,
      atmIfVptIndex,
      atmIfVptPnniIndex,
      atmIfVptPnniRccIndex }
::= { atmIfVptPnniRccHlParmsTable 1 }

AtmIfVptPnniRccHlParmsEntry ::= SEQUENCE {
   atmIfVptPnniRccHelloHoldDown
      FixedPoint1,
   atmIfVptPnniRccHelloInterval
      Unsigned32,
   atmIfVptPnniRccHelloInactivityFactor
      Unsigned32 }

atmIfVptPnniRccHelloHoldDown OBJECT-TYPE
   SYNTAX     FixedPoint1 (0..655350)
   ACCESS     read-write
   STATUS     mandatory
   DESCRIPTION
     "This attribute is used to limit the rate at which this node sends out 
      Hello packets. Specifically, it specifies the minimum time between 
      successive Hellos.
      
      A value of 0 specifies that the value provisioned for the 
      helloHoldDown attribute of the ARtg Pnni component should be 
      used."
   DEFVAL     { 0 }
::= { atmIfVptPnniRccHlParmsEntry 1 }

atmIfVptPnniRccHelloInterval OBJECT-TYPE
   SYNTAX     Unsigned32 (0..65535)
   ACCESS     read-write
   STATUS     mandatory
   DESCRIPTION
     "This attribute specifies the duration of the Hello Timer. Every 
      helloInterval seconds, this node will send out a Hello packet to the 
      neighbor node, subject to the helloHoldDown timer having expired 
      at least once since the last Hello packet was sent.
      
      A value of 0 specifies that the value provisioned for the 
      helloInterval attribute of the ARtg Pnni component should be used."
   DEFVAL     { 0 }
::= { atmIfVptPnniRccHlParmsEntry 2 }

atmIfVptPnniRccHelloInactivityFactor OBJECT-TYPE
   SYNTAX     Unsigned32 (0..65535)
   ACCESS     read-write
   STATUS     mandatory
   DESCRIPTION
     "This attribute specifies the number of Hello intervals allowed to 
      pass without receiving a Hello from the neighbor node, before an 
      attempt is made to re-stage. The hello inactivity timer is enabled in 
      the oneWayInside, twoWayInside, oneWayOutside, 
      twoWayOutside and commonOutside hello states (see the 
      helloState attribute on the Rcc component for a description of these 
      states). Note that the value for the Hello interval used in the 
      calculation is the one specified in the Hello packet from the 
      neighbor node.
      
      A value of 0 specifies that the value provisioned for the 
      helloInactivityFactor attribute of the ARtg Pnni component should 
      be used.
      DESCRIPTION"
   DEFVAL     { 0 }
::= { atmIfVptPnniRccHlParmsEntry 3 }

atmIfVptPnniRccStateTable OBJECT-TYPE
   SYNTAX     SEQUENCE OF AtmIfVptPnniRccStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVptPnniRcc 12 }

atmIfVptPnniRccStateEntry OBJECT-TYPE
   SYNTAX     AtmIfVptPnniRccStateEntry
   ACCESS     not-accessible
   STATUS     mandatory
   DESCRIPTION
     "An entry in the atmIfVptPnniRccStateTable."
   INDEX {
      atmIfIndex,
      atmIfVptIndex,
      atmIfVptPnniIndex,
      atmIfVptPnniRccIndex }
::= { atmIfVptPnniRccStateTable 1 }

AtmIfVptPnniRccStateEntry ::= SEQUENCE {
   atmIfVptPnniRccAdminState
      INTEGER,
   atmIfVptPnniRccOperationalState
      INTEGER,
   atmIfVptPnniRccUsageState
      INTEGER }

atmIfVptPnniRccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVptPnniRccStateEntry 1 }

atmIfVptPnniRccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVptPnniRccStateEntry 2 }

atmIfVptPnniRccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVptPnniRccStateEntry 3 }

atmIfVptPnniRccOperTable OBJECT-TYPE
   SYNTAX     SEQUENCE OF AtmIfVptPnniRccOperEntry
   ACCESS     not-accessible
   STATUS     mandatory
   DESCRIPTION
     "This group contains the operational attributes for an Rcc 
      component."
::= { atmIfVptPnniRcc 13 }

atmIfVptPnniRccOperEntry OBJECT-TYPE
   SYNTAX     AtmIfVptPnniRccOperEntry
   ACCESS     not-accessible
   STATUS     mandatory
   DESCRIPTION
     "An entry in the atmIfVptPnniRccOperTable."
   INDEX {
      atmIfIndex,
      atmIfVptIndex,
      atmIfVptPnniIndex,
      atmIfVptPnniRccIndex }
::= { atmIfVptPnniRccOperTable 1 }

AtmIfVptPnniRccOperEntry ::= SEQUENCE {
   atmIfVptPnniRccType
      INTEGER,
   atmIfVptPnniRccNegotiatedVersion
      INTEGER,
   atmIfVptPnniRccHelloState
      INTEGER,
   atmIfVptPnniRccRemoteNodeId
      HexString,
   atmIfVptPnniRccRemotePortId
      Unsigned32 }

atmIfVptPnniRccType OBJECT-TYPE
   SYNTAX     INTEGER  {
                 unknown(0),
                 lowestLevelHorizLink(1),
                 lowestLevelOutsideLink(2),
                 horizontalLinkToLGN(3),
                 uplink(4) }
   ACCESS     read-only
   STATUS     mandatory
   DESCRIPTION
     "This attribute indicates the role of this link in the PNNI hierarchy.
      The following values are possible:
      
      unknown: the Hello protocol has not yet determined the role of the 
      link.
      
      lowestLevelHorizLink: the link is a horizontal link between two 
      lowest level nodes.
      
      lowestLevelOutsideLink: the link is an outside link between two 
      border nodes.
      
      horizontalLinkToLgn: the link is a horizontal link to a Logical 
      Group Node (LGN).
      
      uplink: the link is a uplink to a higher level LGN."
::= { atmIfVptPnniRccOperEntry 1 }

atmIfVptPnniRccNegotiatedVersion OBJECT-TYPE
   SYNTAX     INTEGER  {
                 unsupported(0),
                 version1point0(1) }
   ACCESS     read-only
   STATUS     mandatory
   DESCRIPTION
     "This attribute indicates the PNNI version negotiated with the 
      neighbor node."
::= { atmIfVptPnniRccOperEntry 2 }

atmIfVptPnniRccHelloState OBJECT-TYPE
   SYNTAX     INTEGER  {
                 notApplicable(0),
                 down(1),
                 attempt(2),
                 oneWayInside(3),
                 twoWayInside(4),
                 oneWayOutside(5),
                 twoWayOutside(6),
                 commonOutside(7) }
   ACCESS     read-only
   STATUS     mandatory
   DESCRIPTION
     "This attribute indicates the state of the Hello protocol exchange over 
      this link. The following are the possible values for this attribute:
      
      down: the link is down; no PNNI routing packets will be sent over 
      or received over such a link. This is the initial state of the Hello 
      Finite State Machine, and can also be reached when lower-level 
      protocols have indicated that the link is not usable.
      
      attempt: no Hello packets or Hello packets, with mismatch 
      information, have been received recently from the neighbor. 
      Attempts are made to contact the neighbor node by sending out 
      Hello packets every helloInterval seconds.
      
      oneWayInside: Hello packets have been recently received from the 
      neighbor and it has been established that both nodes are members of 
      the same peer group, but the remote node ID and remote port ID in 
      the neighbor's Hello packets were set to zero. A Hello packet is sent 
      to the neighbor and the Hello timer is restarted.
      
      twoWayInside: Bidirectional communication over this link between 
      this node and the neighbor node has been achieved.
      
      oneWayOutside: Hello packets have been recently received from 
      the neighbor and it has been established that both nodes are 
      members of a different peer group, but the remote node ID and 
      remote port ID in the neighbor's Hello packets were set to zero.
      
      twoWayOutside: Hellos have recently been received from the 
      neighbor indicating that the neighbor node belongs to a different 
      peer group. The correct remote node ID and remote port ID fields 
      were included in the Hello packet, but the nodal hierarchy list did 
      not include any common peer group. This state can also be reached 
      if a hierarchy mismatch occurs while in the commonOutside state.
      
      commonOutside: A common level of the routing hierarchy has been 
      found, in addition to achieving full bi-directional communication 
      between the two nodes."
::= { atmIfVptPnniRccOperEntry 3 }

atmIfVptPnniRccRemoteNodeId OBJECT-TYPE
   SYNTAX     HexString (SIZE (22))
   ACCESS     read-only
   STATUS     mandatory
   DESCRIPTION
     "This attribute indicates the neighbor node's node id."
::= { atmIfVptPnniRccOperEntry 4 }

atmIfVptPnniRccRemotePortId OBJECT-TYPE
   SYNTAX     Unsigned32 (0..4294967295)
   ACCESS     read-only
   STATUS     mandatory
   DESCRIPTION
     "This attribute indicates the neighbor node's port id."
::= { atmIfVptPnniRccOperEntry 5 }

atmIfVptPnniRccStatsTable OBJECT-TYPE
   SYNTAX     SEQUENCE OF AtmIfVptPnniRccStatsEntry
   ACCESS     not-accessible
   STATUS     mandatory
   DESCRIPTION
     "This group contains the statistical attributes for an Rcc component."
::= { atmIfVptPnniRcc 14 }

atmIfVptPnniRccStatsEntry OBJECT-TYPE
   SYNTAX     AtmIfVptPnniRccStatsEntry
   ACCESS     not-accessible
   STATUS     mandatory
   DESCRIPTION
     "An entry in the atmIfVptPnniRccStatsTable."
   INDEX {
      atmIfIndex,
      atmIfVptIndex,
      atmIfVptPnniIndex,
      atmIfVptPnniRccIndex }
::= { atmIfVptPnniRccStatsTable 1 }

AtmIfVptPnniRccStatsEntry ::= SEQUENCE {
   atmIfVptPnniRccHelloPacketsRx
      Counter32,
   atmIfVptPnniRccHelloPacketsTx
      Counter32,
   atmIfVptPnniRccMismatchedHelloPacketsRx
      Counter32,
   atmIfVptPnniRccBadHelloPacketsRx
      Counter32 }

atmIfVptPnniRccHelloPacketsRx OBJECT-TYPE
   SYNTAX     Counter32 
   ACCESS     read-only
   STATUS     mandatory
   DESCRIPTION
     "This attribute counts the total number of Hello packets received 
      across this RCC, including bad and mismatched Hello packets. The 
      counter wraps when it exceeds the maximum value."
::= { atmIfVptPnniRccStatsEntry 1 }

atmIfVptPnniRccHelloPacketsTx OBJECT-TYPE
   SYNTAX     Counter32 
   ACCESS     read-only
   STATUS     mandatory
   DESCRIPTION
     "This attribute counts the total number of Hello packets transmitted 
      across this RCC. The counter wraps when it exceeds the maximum 
      value."
::= { atmIfVptPnniRccStatsEntry 2 }

atmIfVptPnniRccMismatchedHelloPacketsRx OBJECT-TYPE
   SYNTAX     Counter32 
   ACCESS     read-only
   STATUS     mandatory
   DESCRIPTION
     "This attribute counts the total number of mismatched Hello packets 
      received over this RCC. The counter wraps when it exceeds the 
      maximum value."
::= { atmIfVptPnniRccStatsEntry 3 }

atmIfVptPnniRccBadHelloPacketsRx OBJECT-TYPE
   SYNTAX     Counter32 
   ACCESS     read-only
   STATUS     mandatory
   DESCRIPTION
     "This attribute counts the total number of bad Hello packets received 
      over this RCC. The counter wraps when it exceeds the maximum 
      value."
::= { atmIfVptPnniRccStatsEntry 4 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfVptPnniRccVcd OBJECT IDENTIFIER ::= { atmIfVptPnniRcc 2 }



atmIfVptPnniRccVcdRowStatusTable OBJECT-TYPE
   SYNTAX     SEQUENCE OF AtmIfVptPnniRccVcdRowStatusEntry
   ACCESS     not-accessible
   STATUS     mandatory
   DESCRIPTION
     "This entry controls the addition and deletion of 
      atmIfVptPnniRccVcd components."
::= { atmIfVptPnniRccVcd 1 }

atmIfVptPnniRccVcdRowStatusEntry OBJECT-TYPE
   SYNTAX     AtmIfVptPnniRccVcdRowStatusEntry
   ACCESS     not-accessible
   STATUS     mandatory
   DESCRIPTION
     "A single entry in the table represents a single 
      atmIfVptPnniRccVcd component."
   INDEX {
      atmIfIndex,
      atmIfVptIndex,
      atmIfVptPnniIndex,
      atmIfVptPnniRccIndex,
      atmIfVptPnniRccVcdIndex }
::= { atmIfVptPnniRccVcdRowStatusTable 1 }

AtmIfVptPnniRccVcdRowStatusEntry ::= SEQUENCE {
   atmIfVptPnniRccVcdRowStatus
      RowStatus,
   atmIfVptPnniRccVcdComponentName
      DisplayString,
   atmIfVptPnniRccVcdStorageType
      StorageType,
   atmIfVptPnniRccVcdIndex
      NonReplicated }

atmIfVptPnniRccVcdRowStatus OBJECT-TYPE
   SYNTAX     RowStatus 
   ACCESS     read-write
   STATUS     mandatory
   DESCRIPTION
     "This variable is used as the basis for SNMP naming of
      atmIfVptPnniRccVcd components.
      These components can be added and deleted."
::= { atmIfVptPnniRccVcdRowStatusEntry 1 }

atmIfVptPnniRccVcdComponentName OBJECT-TYPE
   SYNTAX     DisplayString 
   ACCESS     read-only
   STATUS     mandatory
   DESCRIPTION
     "This variable provides the component's string name for
      use with the ASCII Console Interface"
::= { atmIfVptPnniRccVcdRowStatusEntry 2 }

atmIfVptPnniRccVcdStorageType OBJECT-TYPE
   SYNTAX     StorageType 
   ACCESS     read-only
   STATUS     mandatory
   DESCRIPTION
     "This variable represents the storage type value for the
      atmIfVptPnniRccVcd tables."
::= { atmIfVptPnniRccVcdRowStatusEntry 4 }

atmIfVptPnniRccVcdIndex OBJECT-TYPE
   SYNTAX     NonReplicated 
   ACCESS     not-accessible
   STATUS     mandatory
   DESCRIPTION
     "This variable represents the index for the atmIfVptPnniRccVcd tables."
::= { atmIfVptPnniRccVcdRowStatusEntry 10 }

atmIfVptPnniRccVcdProvTable OBJECT-TYPE
   SYNTAX     SEQUENCE OF AtmIfVptPnniRccVcdProvEntry
   ACCESS     not-accessible
   STATUS     mandatory
   DESCRIPTION
     "This group contains the provisionable traffic attributes for a control 
      channel."
::= { atmIfVptPnniRccVcd 10 }

atmIfVptPnniRccVcdProvEntry OBJECT-TYPE
   SYNTAX     AtmIfVptPnniRccVcdProvEntry
   ACCESS     not-accessible
   STATUS     mandatory
   DESCRIPTION
     "An entry in the atmIfVptPnniRccVcdProvTable."
   INDEX {
      atmIfIndex,
      atmIfVptIndex,
      atmIfVptPnniIndex,
      atmIfVptPnniRccIndex,
      atmIfVptPnniRccVcdIndex }
::= { atmIfVptPnniRccVcdProvTable 1 }

AtmIfVptPnniRccVcdProvEntry ::= SEQUENCE {
   atmIfVptPnniRccVcdTrafficDescType
      INTEGER,
   atmIfVptPnniRccVcdAtmServiceCategory
      INTEGER,
   atmIfVptPnniRccVcdQosClass
      INTEGER,
   atmIfVptPnniRccVcdTrafficShaping
      INTEGER,
   atmIfVptPnniRccVcdUnshapedTransmitQueueing
      INTEGER,
   atmIfVptPnniRccVcdUsageParameterControl
      INTEGER }

atmIfVptPnniRccVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfVptPnniRccVcdProvEntry 1 }

atmIfVptPnniRccVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfVptPnniRccVcdProvEntry 3 }

atmIfVptPnniRccVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfVptPnniRccVcdProvEntry 21 }

atmIfVptPnniRccVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfVptPnniRccVcdProvEntry 50 }

atmIfVptPnniRccVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfVptPnniRccVcdProvEntry 60 }

atmIfVptPnniRccVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfVptPnniRccVcdProvEntry 70 }

atmIfVptPnniRccVcdTdpTable OBJECT-TYPE
   SYNTAX     SEQUENCE OF AtmIfVptPnniRccVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfVptPnniRccVcd 387 }

atmIfVptPnniRccVcdTdpEntry OBJECT-TYPE
   SYNTAX     AtmIfVptPnniRccVcdTdpEntry
   ACCESS     not-accessible
   STATUS     mandatory
   DESCRIPTION
     "An entry in the atmIfVptPnniRccVcdTdpTable."
   INDEX {
      atmIfIndex,
      atmIfVptIndex,
      atmIfVptPnniIndex,
      atmIfVptPnniRccIndex,
      atmIfVptPnniRccVcdIndex,
      atmIfVptPnniRccVcdTdpIndex }
::= { atmIfVptPnniRccVcdTdpTable 1 }

AtmIfVptPnniRccVcdTdpEntry ::= SEQUENCE {
   atmIfVptPnniRccVcdTdpIndex
      Integer32,
   atmIfVptPnniRccVcdTdpValue
      Unsigned32 }

atmIfVptPnniRccVcdTdpIndex OBJECT-TYPE
   SYNTAX     Integer32 (1..5)
   ACCESS     not-accessible
   STATUS     mandatory
   DESCRIPTION
     "This variable represents the atmIfVptPnniRccVcdTdpTable
      specific index for the atmIfVptPnniRccVcdTdpTable."
::= { atmIfVptPnniRccVcdTdpEntry 1 }

atmIfVptPnniRccVcdTdpValue OBJECT-TYPE
   SYNTAX     Unsigned32 (0..2147483647)
   ACCESS     read-write
   STATUS     mandatory
   DESCRIPTION
     "This variable represents an individual value for the
      atmIfVptPnniRccVcdTdpTable."
::= { atmIfVptPnniRccVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

atmIfVptPnniAddr OBJECT IDENTIFIER ::= { atmIfVptPnni 4 }



atmIfVptPnniAddrRowStatusTable OBJECT-TYPE
   SYNTAX     SEQUENCE OF AtmIfVptPnniAddrRowStatusEntry
   ACCESS     not-accessible
   STATUS     mandatory
   DESCRIPTION
     "This entry controls the addition and deletion of 
      atmIfVptPnniAddr components."
::= { atmIfVptPnniAddr 1 }

atmIfVptPnniAddrRowStatusEntry OBJECT-TYPE
   SYNTAX     AtmIfVptPnniAddrRowStatusEntry
   ACCESS     not-accessible
   STATUS     mandatory
   DESCRIPTION
     "A single entry in the table represents a single 
      atmIfVptPnniAddr component."
   INDEX {
      atmIfIndex,
      atmIfVptIndex,
      atmIfVptPnniIndex,
      atmIfVptPnniAddrAddressIndex,
      atmIfVptPnniAddrAddressTypeIndex }
::= { atmIfVptPnniAddrRowStatusTable 1 }

AtmIfVptPnniAddrRowStatusEntry ::= SEQUENCE {
   atmIfVptPnniAddrRowStatus
      RowStatus,
   atmIfVptPnniAddrComponentName
      DisplayString,
   atmIfVptPnniAddrStorageType
      StorageType,
   atmIfVptPnniAddrAddressIndex
      AsciiStringIndex,
   atmIfVptPnniAddrAddressTypeIndex
      INTEGER }

atmIfVptPnniAddrRowStatus OBJECT-TYPE
   SYNTAX     RowStatus 
   ACCESS     read-write
   STATUS     mandatory
   DESCRIPTION
     "This variable is used as the basis for SNMP naming of
      atmIfVptPnniAddr components.
      These components can be added and deleted."
::= { atmIfVptPnniAddrRowStatusEntry 1 }

atmIfVptPnniAddrComponentName OBJECT-TYPE
   SYNTAX     DisplayString 
   ACCESS     read-only
   STATUS     mandatory
   DESCRIPTION
     "This variable provides the component's string name for
      use with the ASCII Console Interface"
::= { atmIfVptPnniAddrRowStatusEntry 2 }

atmIfVptPnniAddrStorageType OBJECT-TYPE
   SYNTAX     StorageType 
   ACCESS     read-only
   STATUS     mandatory
   DESCRIPTION
     "This variable represents the storage type value for the
      atmIfVptPnniAddr tables."
::= { atmIfVptPnniAddrRowStatusEntry 4 }

atmIfVptPnniAddrAddressIndex OBJECT-TYPE
   SYNTAX     AsciiStringIndex (SIZE (1..40))
   ACCESS     not-accessible
   STATUS     mandatory
   DESCRIPTION
     "This variable represents an index for the atmIfVptPnniAddr tables."
::= { atmIfVptPnniAddrRowStatusEntry 10 }

atmIfVptPnniAddrAddressTypeIndex OBJECT-TYPE
   SYNTAX     INTEGER  {
                 primary(0),
                 alternate(1),
                 registered(2),
                 default(3) }
   ACCESS     not-accessible
   STATUS     mandatory
   DESCRIPTION
     "This variable represents an index for the atmIfVptPnniAddr tables."
::= { atmIfVptPnniAddrRowStatusEntry 11 }

atmIfVptPnniAddrOperTable OBJECT-TYPE
   SYNTAX     SEQUENCE OF AtmIfVptPnniAddrOperEntry
   ACCESS     not-accessible
   STATUS     mandatory
   DESCRIPTION
     "This attribute group contains the operational attributes for the 
      Address component."
::= { atmIfVptPnniAddr 10 }

atmIfVptPnniAddrOperEntry OBJECT-TYPE
   SYNTAX     AtmIfVptPnniAddrOperEntry
   ACCESS     not-accessible
   STATUS     mandatory
   DESCRIPTION
     "An entry in the atmIfVptPnniAddrOperTable."
   INDEX {
      atmIfIndex,
      atmIfVptIndex,
      atmIfVptPnniIndex,
      atmIfVptPnniAddrAddressIndex,
      atmIfVptPnniAddrAddressTypeIndex }
::= { atmIfVptPnniAddrOperTable 1 }

AtmIfVptPnniAddrOperEntry ::= SEQUENCE {
   atmIfVptPnniAddrScope
      INTEGER,
   atmIfVptPnniAddrReachability
      INTEGER }

atmIfVptPnniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { atmIfVptPnniAddrOperEntry 1 }

atmIfVptPnniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { atmIfVptPnniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

atmIfVptPnniAddrTermSP OBJECT IDENTIFIER ::= { atmIfVptPnniAddr 2 }



atmIfVptPnniAddrTermSPRowStatusTable OBJECT-TYPE
   SYNTAX     SEQUENCE OF AtmIfVptPnniAddrTermSPRowStatusEntry
   ACCESS     not-accessible
   STATUS     mandatory
   DESCRIPTION
     "This entry controls the addition and deletion of 
      atmIfVptPnniAddrTermSP components."
::= { atmIfVptPnniAddrTermSP 1 }

atmIfVptPnniAddrTermSPRowStatusEntry OBJECT-TYPE
   SYNTAX     AtmIfVptPnniAddrTermSPRowStatusEntry
   ACCESS     not-accessible
   STATUS     mandatory
   DESCRIPTION
     "A single entry in the table represents a single 
      atmIfVptPnniAddrTermSP component."
   INDEX {
      atmIfIndex,
      atmIfVptIndex,
      atmIfVptPnniIndex,
      atmIfVptPnniAddrAddressIndex,
      atmIfVptPnniAddrAddressTypeIndex,
      atmIfVptPnniAddrTermSPIndex }
::= { atmIfVptPnniAddrTermSPRowStatusTable 1 }

AtmIfVptPnniAddrTermSPRowStatusEntry ::= SEQUENCE {
   atmIfVptPnniAddrTermSPRowStatus
      RowStatus,
   atmIfVptPnniAddrTermSPComponentName
      DisplayString,
   atmIfVptPnniAddrTermSPStorageType
      StorageType,
   atmIfVptPnniAddrTermSPIndex
      NonReplicated }

atmIfVptPnniAddrTermSPRowStatus OBJECT-TYPE
   SYNTAX     RowStatus 
   ACCESS     read-write
   STATUS     mandatory
   DESCRIPTION
     "This variable is used as the basis for SNMP naming of
      atmIfVptPnniAddrTermSP components.
      These components can be added and deleted."
::= { atmIfVptPnniAddrTermSPRowStatusEntry 1 }

atmIfVptPnniAddrTermSPComponentName OBJECT-TYPE
   SYNTAX     DisplayString 
   ACCESS     read-only
   STATUS     mandatory
   DESCRIPTION
     "This variable provides the component's string name for
      use with the ASCII Console Interface"
::= { atmIfVptPnniAddrTermSPRowStatusEntry 2 }

atmIfVptPnniAddrTermSPStorageType OBJECT-TYPE
   SYNTAX     StorageType 
   ACCESS     read-only
   STATUS     mandatory
   DESCRIPTION
     "This variable represents the storage type value for the
      atmIfVptPnniAddrTermSP tables."
::= { atmIfVptPnniAddrTermSPRowStatusEntry 4 }

atmIfVptPnniAddrTermSPIndex OBJECT-TYPE
   SYNTAX     NonReplicated 
   ACCESS     not-accessible
   STATUS     mandatory
   DESCRIPTION
     "This variable represents the index for the atmIfVptPnniAddrTermSP tables."
::= { atmIfVptPnniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

atmIfVptPnniAddrPnniInfo OBJECT IDENTIFIER ::= { atmIfVptPnniAddr 3 }



atmIfVptPnniAddrPnniInfoRowStatusTable OBJECT-TYPE
   SYNTAX     SEQUENCE OF AtmIfVptPnniAddrPnniInfoRowStatusEntry
   ACCESS     not-accessible
   STATUS     mandatory
   DESCRIPTION
     "This entry controls the addition and deletion of 
      atmIfVptPnniAddrPnniInfo components."
::= { atmIfVptPnniAddrPnniInfo 1 }

atmIfVptPnniAddrPnniInfoRowStatusEntry OBJECT-TYPE
   SYNTAX     AtmIfVptPnniAddrPnniInfoRowStatusEntry
   ACCESS     not-accessible
   STATUS     mandatory
   DESCRIPTION
     "A single entry in the table represents a single 
      atmIfVptPnniAddrPnniInfo component."
   INDEX {
      atmIfIndex,
      atmIfVptIndex,
      atmIfVptPnniIndex,
      atmIfVptPnniAddrAddressIndex,
      atmIfVptPnniAddrAddressTypeIndex,
      atmIfVptPnniAddrPnniInfoIndex }
::= { atmIfVptPnniAddrPnniInfoRowStatusTable 1 }

AtmIfVptPnniAddrPnniInfoRowStatusEntry ::= SEQUENCE {
   atmIfVptPnniAddrPnniInfoRowStatus
      RowStatus,
   atmIfVptPnniAddrPnniInfoComponentName
      DisplayString,
   atmIfVptPnniAddrPnniInfoStorageType
      StorageType,
   atmIfVptPnniAddrPnniInfoIndex
      NonReplicated }

atmIfVptPnniAddrPnniInfoRowStatus OBJECT-TYPE
   SYNTAX     RowStatus 
   ACCESS     read-write
   STATUS     mandatory
   DESCRIPTION
     "This variable is used as the basis for SNMP naming of
      atmIfVptPnniAddrPnniInfo components.
      These components can be added and deleted."
::= { atmIfVptPnniAddrPnniInfoRowStatusEntry 1 }

atmIfVptPnniAddrPnniInfoComponentName OBJECT-TYPE
   SYNTAX     DisplayString 
   ACCESS     read-only
   STATUS     mandatory
   DESCRIPTION
     "This variable provides the component's string name for
      use with the ASCII Console Interface"
::= { atmIfVptPnniAddrPnniInfoRowStatusEntry 2 }

atmIfVptPnniAddrPnniInfoStorageType OBJECT-TYPE
   SYNTAX     StorageType 
   ACCESS     read-only
   STATUS     mandatory
   DESCRIPTION
     "This variable represents the storage type value for the
      atmIfVptPnniAddrPnniInfo tables."
::= { atmIfVptPnniAddrPnniInfoRowStatusEntry 4 }

atmIfVptPnniAddrPnniInfoIndex OBJECT-TYPE
   SYNTAX     NonReplicated 
   ACCESS     not-accessible
   STATUS     mandatory
   DESCRIPTION
     "This variable represents the index for the atmIfVptPnniAddrPnniInfo tables."
::= { atmIfVptPnniAddrPnniInfoRowStatusEntry 10 }

atmIfVptPnniAddrPnniInfoProvTable OBJECT-TYPE
   SYNTAX     SEQUENCE OF AtmIfVptPnniAddrPnniInfoProvEntry
   ACCESS     not-accessible
   STATUS     mandatory
   DESCRIPTION
     "This attribute group contains the provisioned attributes relating to 
      PNNI for a PnniInfo component."
::= { atmIfVptPnniAddrPnniInfo 10 }

atmIfVptPnniAddrPnniInfoProvEntry OBJECT-TYPE
   SYNTAX     AtmIfVptPnniAddrPnniInfoProvEntry
   ACCESS     not-accessible
   STATUS     mandatory
   DESCRIPTION
     "An entry in the atmIfVptPnniAddrPnniInfoProvTable."
   INDEX {
      atmIfIndex,
      atmIfVptIndex,
      atmIfVptPnniIndex,
      atmIfVptPnniAddrAddressIndex,
      atmIfVptPnniAddrAddressTypeIndex,
      atmIfVptPnniAddrPnniInfoIndex }
::= { atmIfVptPnniAddrPnniInfoProvTable 1 }

AtmIfVptPnniAddrPnniInfoProvEntry ::= SEQUENCE {
   atmIfVptPnniAddrPnniInfoScope
      INTEGER,
   atmIfVptPnniAddrPnniInfoReachability
      INTEGER }

atmIfVptPnniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { atmIfVptPnniAddrPnniInfoProvEntry 1 }

atmIfVptPnniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { atmIfVptPnniAddrPnniInfoProvEntry 2 }


-- AtmIf/n Pnni
-- This component represents an ATM Private Network-Network 
-- Interface (PNNI) interface. If this component is provisioned, the 
-- Uni or Iisp component cannot be provisioned under the same AtmIf 
-- component. Also, the Artg Pnni component and the 
-- ConfiguredNode component corresponding to the participation of 
-- the this node in a lowest level peer group must already exist before 
-- provisioning Pnni under an AtmIf component. If this component is 
-- deleted, then all associated Vcc components are deleted.

atmIfPnni OBJECT IDENTIFIER ::= { atmIf 96 }



atmIfPnniRowStatusTable OBJECT-TYPE
   SYNTAX     SEQUENCE OF AtmIfPnniRowStatusEntry
   ACCESS     not-accessible
   STATUS     mandatory
   DESCRIPTION
     "This entry controls the addition and deletion of 
      atmIfPnni components."
::= { atmIfPnni 1 }

atmIfPnniRowStatusEntry OBJECT-TYPE
   SYNTAX     AtmIfPnniRowStatusEntry
   ACCESS     not-accessible
   STATUS     mandatory
   DESCRIPTION
     "A single entry in the table represents a single 
      atmIfPnni component."
   INDEX {
      atmIfIndex,
      atmIfPnniIndex }
::= { atmIfPnniRowStatusTable 1 }

AtmIfPnniRowStatusEntry ::= SEQUENCE {
   atmIfPnniRowStatus
      RowStatus,
   atmIfPnniComponentName
      DisplayString,
   atmIfPnniStorageType
      StorageType,
   atmIfPnniIndex
      NonReplicated }

atmIfPnniRowStatus OBJECT-TYPE
   SYNTAX     RowStatus 
   ACCESS     read-write
   STATUS     mandatory
   DESCRIPTION
     "This variable is used as the basis for SNMP naming of
      atmIfPnni components.
      These components can be added and deleted."
::= { atmIfPnniRowStatusEntry 1 }

atmIfPnniComponentName OBJECT-TYPE
   SYNTAX     DisplayString 
   ACCESS     read-only
   STATUS     mandatory
   DESCRIPTION
     "This variable provides the component's string name for
      use with the ASCII Console Interface"
::= { atmIfPnniRowStatusEntry 2 }

atmIfPnniStorageType OBJECT-TYPE
   SYNTAX     StorageType 
   ACCESS     read-only
   STATUS     mandatory
   DESCRIPTION
     "This variable represents the storage type value for the
      atmIfPnni tables."
::= { atmIfPnniRowStatusEntry 4 }

atmIfPnniIndex OBJECT-TYPE
   SYNTAX     NonReplicated 
   ACCESS     not-accessible
   STATUS     mandatory
   DESCRIPTION
     "This variable represents the index for the atmIfPnni tables."
::= { atmIfPnniRowStatusEntry 10 }

atmIfPnniProvTable OBJECT-TYPE
   SYNTAX     SEQUENCE OF AtmIfPnniProvEntry
   ACCESS     not-accessible
   STATUS     mandatory
   DESCRIPTION
     "This group contains the provisionable attributes for the Pnni
      component."
::= { atmIfPnni 10 }

atmIfPnniProvEntry OBJECT-TYPE
   SYNTAX     AtmIfPnniProvEntry
   ACCESS     not-accessible
   STATUS     mandatory
   DESCRIPTION
     "An entry in the atmIfPnniProvTable."
   INDEX {
      atmIfIndex,
      atmIfPnniIndex }
::= { atmIfPnniProvTable 1 }

AtmIfPnniProvEntry ::= SEQUENCE {
   atmIfPnniSoftPvcRetryPeriod
      Unsigned32,
   atmIfPnniSoftPvpAndPvcRetryPeriod
      Unsigned32,
   atmIfPnniSoftPvpAndPvcHoldOffTime
      Unsigned32 }

atmIfPnniSoftPvcRetryPeriod OBJECT-TYPE
   SYNTAX     Unsigned32 (20..999999)
   ACCESS     read-write
   STATUS     obsolete
   DESCRIPTION
     "This attribute represents the time in seconds to wait between call 
      setup retries. The resolution is to the nearest 10 seconds. 
      This attribute has been obsoleted and is replaced by the 
      softPvpAndPvcRetryPeriod attribute."
   DEFVAL     { 60 }
::= { atmIfPnniProvEntry 1 }

atmIfPnniSoftPvpAndPvcRetryPeriod OBJECT-TYPE
   SYNTAX     Unsigned32 (20..999999)
   ACCESS     read-write
   STATUS     mandatory
   DESCRIPTION
     "This attribute represents the time in seconds to wait between soft 
      PVP or soft PVC call  setup retries. The resolution is to the nearest 
      10 seconds."
   DEFVAL     { 60 }
::= { atmIfPnniProvEntry 2 }

atmIfPnniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { atmIfPnniProvEntry 5 }

atmIfPnniAdminWeightsTable OBJECT-TYPE
   SYNTAX     SEQUENCE OF AtmIfPnniAdminWeightsEntry
   ACCESS     not-accessible
   STATUS     mandatory
   DESCRIPTION
     "This group contains the provisionable administrative weights for the 
      Pnni component. These weights will be used by Generic 
      Connection Admission Control (GCAC) if administrative weight is 
      the selected optimization criterion."
::= { atmIfPnni 11 }

atmIfPnniAdminWeightsEntry OBJECT-TYPE
   SYNTAX     AtmIfPnniAdminWeightsEntry
   ACCESS     not-accessible
   STATUS     mandatory
   DESCRIPTION
     "An entry in the atmIfPnniAdminWeightsTable."
   INDEX {
      atmIfIndex,
      atmIfPnniIndex }
::= { atmIfPnniAdminWeightsTable 1 }

AtmIfPnniAdminWeightsEntry ::= SEQUENCE {
   atmIfPnniCbrWeight
      Unsigned32,
   atmIfPnniRtVbrWeight
      Unsigned32,
   atmIfPnniNrtVbrWeight
      Unsigned32,
   atmIfPnniUbrWeight
      Unsigned32 }

atmIfPnniCbrWeight OBJECT-TYPE
   SYNTAX     Unsigned32 (0..4294967295)
   ACCESS     read-write
   STATUS     mandatory
   DESCRIPTION
     "This attribute specifies the administrative weight assigned for 
      setting up switched calls with a service category of Constant Bit 
      Rate (CBR) for this PNNI interface. The value specified will be 
      used by Generic Connection Admission Control (GCAC) if 
      administrative weight is the selected optimization criterion; the 
      higher the value, the less desirable the link will be in path selection."
   DEFVAL     { 5040 }
::= { atmIfPnniAdminWeightsEntry 1 }

atmIfPnniRtVbrWeight OBJECT-TYPE
   SYNTAX     Unsigned32 (0..4294967295)
   ACCESS     read-write
   STATUS     mandatory
   DESCRIPTION
     "This attribute specifies the administrative weight assigned for 
      setting up switched calls with a service category of Real-Time 
      Variable Bit Rate (RT-VBR) for this PNNI interface. The value 
      specified will be used by Generic Connection Admission Control 
      (GCAC) if administrative weight is the selected optimization 
      criterion; the higher the value, the less desirable the link will be in 
      path selection."
   DEFVAL     { 5040 }
::= { atmIfPnniAdminWeightsEntry 2 }

atmIfPnniNrtVbrWeight OBJECT-TYPE
   SYNTAX     Unsigned32 (0..4294967295)
   ACCESS     read-write
   STATUS     mandatory
   DESCRIPTION
     "This attribute specifies the administrative weight assigned for 
      setting up switched calls with a service category of Non Real-Time 
      Variable Bit Rate (NRT-VBR) for this PNNI interface. The value 
      specified will be used by Generic Connection Admission Control 
      (GCAC) if administrative weight is the selected optimization 
      criterion; the higher the value, the less desirable the link will be in 
      path selection."
   DEFVAL     { 5040 }
::= { atmIfPnniAdminWeightsEntry 3 }

atmIfPnniUbrWeight OBJECT-TYPE
   SYNTAX     Unsigned32 (0..4294967295)
   ACCESS     read-write
   STATUS     mandatory
   DESCRIPTION
     "This attribute specifies the administrative weight assigned for 
      setting up switched calls with a service category of Unspecified Bit 
      Rate (UBR) for this PNNI interface. The value specified will be 
      used by Generic Connection Admission Control (GCAC) if 
      administrative weight is the selected optimization criterion; the 
      higher the value, the less desirable the link will be in path selection."
   DEFVAL     { 5040 }
::= { atmIfPnniAdminWeightsEntry 4 }

atmIfPnniAcctOptTable OBJECT-TYPE
   SYNTAX     SEQUENCE OF AtmIfPnniAcctOptEntry
   ACCESS     not-accessible
   STATUS     mandatory
   DESCRIPTION
     "This group contains the provisionable attributes for accounting."
::= { atmIfPnni 12 }

atmIfPnniAcctOptEntry OBJECT-TYPE
   SYNTAX     AtmIfPnniAcctOptEntry
   ACCESS     not-accessible
   STATUS     mandatory
   DESCRIPTION
     "An entry in the atmIfPnniAcctOptTable."
   INDEX {
      atmIfIndex,
      atmIfPnniIndex }
::= { atmIfPnniAcctOptTable 1 }

AtmIfPnniAcctOptEntry ::= SEQUENCE {
   atmIfPnniAccountCollection
      OCTET STRING,
   atmIfPnniAccountConnectionType
      INTEGER,
   atmIfPnniAccountClass
      Unsigned32,
   atmIfPnniServiceExchange
      Unsigned32 }

atmIfPnniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { atmIfPnniAcctOptEntry 1 }

atmIfPnniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { atmIfPnniAcctOptEntry 2 }

atmIfPnniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { atmIfPnniAcctOptEntry 3 }

atmIfPnniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { atmIfPnniAcctOptEntry 4 }

atmIfPnniOperationalTable OBJECT-TYPE
   SYNTAX     SEQUENCE OF AtmIfPnniOperationalEntry
   ACCESS     not-accessible
   STATUS     mandatory
   DESCRIPTION
     "This group contains the operational attributes for a Pnni component."
::= { atmIfPnni 13 }

atmIfPnniOperationalEntry OBJECT-TYPE
   SYNTAX     AtmIfPnniOperationalEntry
   ACCESS     not-accessible
   STATUS     mandatory
   DESCRIPTION
     "An entry in the atmIfPnniOperationalTable."
   INDEX {
      atmIfIndex,
      atmIfPnniIndex }
::= { atmIfPnniOperationalTable 1 }

AtmIfPnniOperationalEntry ::= SEQUENCE {
   atmIfPnniPortId
      Unsigned32 }

atmIfPnniPortId OBJECT-TYPE
   SYNTAX     Unsigned32 (0..4294967295)
   ACCESS     read-only
   STATUS     mandatory
   DESCRIPTION
     "This attribute indicates the port id of the PNNI interface, which is 
      the parent AtmIf's instance number."
::= { atmIfPnniOperationalEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

atmIfPnniSig OBJECT IDENTIFIER ::= { atmIfPnni 2 }



atmIfPnniSigRowStatusTable OBJECT-TYPE
   SYNTAX     SEQUENCE OF AtmIfPnniSigRowStatusEntry
   ACCESS     not-accessible
   STATUS     mandatory
   DESCRIPTION
     "This entry controls the addition and deletion of 
      atmIfPnniSig components."
::= { atmIfPnniSig 1 }

atmIfPnniSigRowStatusEntry OBJECT-TYPE
   SYNTAX     AtmIfPnniSigRowStatusEntry
   ACCESS     not-accessible
   STATUS     mandatory
   DESCRIPTION
     "A single entry in the table represents a single 
      atmIfPnniSig component."
   INDEX {
      atmIfIndex,
      atmIfPnniIndex,
      atmIfPnniSigIndex }
::= { atmIfPnniSigRowStatusTable 1 }

AtmIfPnniSigRowStatusEntry ::= SEQUENCE {
   atmIfPnniSigRowStatus
      RowStatus,
   atmIfPnniSigComponentName
      DisplayString,
   atmIfPnniSigStorageType
      StorageType,
   atmIfPnniSigIndex
      NonReplicated }

atmIfPnniSigRowStatus OBJECT-TYPE
   SYNTAX     RowStatus 
   ACCESS     read-only
   STATUS     mandatory
   DESCRIPTION
     "This variable is used as the basis for SNMP naming of
      atmIfPnniSig components.
      These components cannot be added nor deleted."
::= { atmIfPnniSigRowStatusEntry 1 }

atmIfPnniSigComponentName OBJECT-TYPE
   SYNTAX     DisplayString 
   ACCESS     read-only
   STATUS     mandatory
   DESCRIPTION
     "This variable provides the component's string name for
      use with the ASCII Console Interface"
::= { atmIfPnniSigRowStatusEntry 2 }

atmIfPnniSigStorageType OBJECT-TYPE
   SYNTAX     StorageType 
   ACCESS     read-only
   STATUS     mandatory
   DESCRIPTION
     "This variable represents the storage type value for the
      atmIfPnniSig tables."
::= { atmIfPnniSigRowStatusEntry 4 }

atmIfPnniSigIndex OBJECT-TYPE
   SYNTAX     NonReplicated 
   ACCESS     not-accessible
   STATUS     mandatory
   DESCRIPTION
     "This variable represents the index for the atmIfPnniSig tables."
::= { atmIfPnniSigRowStatusEntry 10 }

atmIfPnniSigProvTable OBJECT-TYPE
   SYNTAX     SEQUENCE OF AtmIfPnniSigProvEntry
   ACCESS     not-accessible
   STATUS     mandatory
   DESCRIPTION
     "This attribute group contains the provisionable attributes for the 
      Signalling component."
::= { atmIfPnniSig 10 }

atmIfPnniSigProvEntry OBJECT-TYPE
   SYNTAX     AtmIfPnniSigProvEntry
   ACCESS     not-accessible
   STATUS     mandatory
   DESCRIPTION
     "An entry in the atmIfPnniSigProvTable."
   INDEX {
      atmIfIndex,
      atmIfPnniIndex,
      atmIfPnniSigIndex }
::= { atmIfPnniSigProvTable 1 }

AtmIfPnniSigProvEntry ::= SEQUENCE {
   atmIfPnniSigVci
      Unsigned32,
   atmIfPnniSigAddressConversion
      INTEGER }

atmIfPnniSigVci OBJECT-TYPE
   SYNTAX     Unsigned32 (0..65535)
   ACCESS     read-write
   STATUS     mandatory
   DESCRIPTION
     "This attribute specifies the signalling channel number."
   DEFVAL     { 5 }
::= { atmIfPnniSigProvEntry 1 }

atmIfPnniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { atmIfPnniSigProvEntry 2 }

atmIfPnniSigStateTable OBJECT-TYPE
   SYNTAX     SEQUENCE OF AtmIfPnniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfPnniSig 11 }

atmIfPnniSigStateEntry OBJECT-TYPE
   SYNTAX     AtmIfPnniSigStateEntry
   ACCESS     not-accessible
   STATUS     mandatory
   DESCRIPTION
     "An entry in the atmIfPnniSigStateTable."
   INDEX {
      atmIfIndex,
      atmIfPnniIndex,
      atmIfPnniSigIndex }
::= { atmIfPnniSigStateTable 1 }

AtmIfPnniSigStateEntry ::= SEQUENCE {
   atmIfPnniSigAdminState
      INTEGER,
   atmIfPnniSigOperationalState
      INTEGER,
   atmIfPnniSigUsageState
      INTEGER }

atmIfPnniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfPnniSigStateEntry 1 }

atmIfPnniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfPnniSigStateEntry 2 }

atmIfPnniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfPnniSigStateEntry 3 }

atmIfPnniSigOperTable OBJECT-TYPE
   SYNTAX     SEQUENCE OF AtmIfPnniSigOperEntry
   ACCESS     not-accessible
   STATUS     mandatory
   DESCRIPTION
     "This attribute contains the operational attributes for the 
      AtmSignalling component."
::= { atmIfPnniSig 12 }

atmIfPnniSigOperEntry OBJECT-TYPE
   SYNTAX     AtmIfPnniSigOperEntry
   ACCESS     not-accessible
   STATUS     mandatory
   DESCRIPTION
     "An entry in the atmIfPnniSigOperTable."
   INDEX {
      atmIfIndex,
      atmIfPnniIndex,
      atmIfPnniSigIndex }
::= { atmIfPnniSigOperTable 1 }

AtmIfPnniSigOperEntry ::= SEQUENCE {
   atmIfPnniSigLastTxCauseCode
      Unsigned32,
   atmIfPnniSigLastTxDiagCode
      Hex,
   atmIfPnniSigLastRxCauseCode
      Unsigned32,
   atmIfPnniSigLastRxDiagCode
      Hex }

atmIfPnniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { atmIfPnniSigOperEntry 1 }

atmIfPnniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfPnniSigOperEntry 2 }

atmIfPnniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { atmIfPnniSigOperEntry 3 }

atmIfPnniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfPnniSigOperEntry 4 }

atmIfPnniSigStatsTable OBJECT-TYPE
   SYNTAX     SEQUENCE OF AtmIfPnniSigStatsEntry
   ACCESS     not-accessible
   STATUS     mandatory
   DESCRIPTION
     "This attribute group contains the statistics associated with the 
      AtmSignalling component."
::= { atmIfPnniSig 13 }

atmIfPnniSigStatsEntry OBJECT-TYPE
   SYNTAX     AtmIfPnniSigStatsEntry
   ACCESS     not-accessible
   STATUS     mandatory
   DESCRIPTION
     "An entry in the atmIfPnniSigStatsTable."
   INDEX {
      atmIfIndex,
      atmIfPnniIndex,
      atmIfPnniSigIndex }
::= { atmIfPnniSigStatsTable 1 }

AtmIfPnniSigStatsEntry ::= SEQUENCE {
   atmIfPnniSigCurrentConnections
      Counter32,
   atmIfPnniSigPeakConnections
      Gauge32,
   atmIfPnniSigSuccessfulConnections
      Counter32,
   atmIfPnniSigFailedConnections
      Counter32,
   atmIfPnniSigTxPdus
      Counter32,
   atmIfPnniSigRxPdus
      Counter32,
   atmIfPnniSigCurrentPmpConnections
      Gauge32,
   atmIfPnniSigPeakPmpConnections
      Gauge32,
   atmIfPnniSigSuccessfulPmpConnections
      Counter32,
   atmIfPnniSigFailedPmpConnections
      Counter32,
   atmIfPnniSigNewCurrentConnections
      Gauge32 }

atmIfPnniSigCurrentConnections OBJECT-TYPE
   SYNTAX     Counter32 
   ACCESS     read-only
   STATUS     obsolete
   DESCRIPTION
     "This attribute indicates the total number of currently active 
      connections."
::= { atmIfPnniSigStatsEntry 1 }

atmIfPnniSigPeakConnections OBJECT-TYPE
   SYNTAX     Gauge32 (0..4294967295)
   ACCESS     read-only
   STATUS     mandatory
   DESCRIPTION
     "This attribute indicates the high water mark of active point-to-
      point and point-to-multipoint connections."
::= { atmIfPnniSigStatsEntry 2 }

atmIfPnniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { atmIfPnniSigStatsEntry 3 }

atmIfPnniSigFailedConnections OBJECT-TYPE
   SYNTAX     Counter32 
   ACCESS     read-only
   STATUS     mandatory
   DESCRIPTION
     "This attribute counts the total number of switched connections that 
      were not successfully established.The counter wraps to 0 when the 
      maximum value is exceeded."
::= { atmIfPnniSigStatsEntry 4 }

atmIfPnniSigTxPdus OBJECT-TYPE
   SYNTAX     Counter32 
   ACCESS     read-only
   STATUS     mandatory
   DESCRIPTION
     "This attribute counts the number of transmitted signalling 
      PDUs.The counter wraps to 0 when the maximum value is 
      exceeded."
::= { atmIfPnniSigStatsEntry 5 }

atmIfPnniSigRxPdus OBJECT-TYPE
   SYNTAX     Counter32 
   ACCESS     read-only
   STATUS     mandatory
   DESCRIPTION
     "This attribute counts the number of received signalling PDUs.The 
      counter wraps to 0 when the maximum value is exceeded."
::= { atmIfPnniSigStatsEntry 6 }

atmIfPnniSigCurrentPmpConnections OBJECT-TYPE
   SYNTAX     Gauge32 (0..4294967295)
   ACCESS     read-only
   STATUS     mandatory
   DESCRIPTION
     "This attribute indicates the number of currently active point-to-
      multipoint connections."
::= { atmIfPnniSigStatsEntry 7 }

atmIfPnniSigPeakPmpConnections OBJECT-TYPE
   SYNTAX     Gauge32 (0..4294967295)
   ACCESS     read-only
   STATUS     mandatory
   DESCRIPTION
     "This attribute indicates the high water mark of active point-to-
      multipoint connections."
::= { atmIfPnniSigStatsEntry 8 }

atmIfPnniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { atmIfPnniSigStatsEntry 9 }

atmIfPnniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { atmIfPnniSigStatsEntry 10 }

atmIfPnniSigNewCurrentConnections OBJECT-TYPE
   SYNTAX     Gauge32 (0..4294967295)
   ACCESS     read-only
   STATUS     mandatory
   DESCRIPTION
     "This attribute indicates the total number of currently active point-to-
      point and point-to-multipoint connections."
::= { atmIfPnniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfPnniSigVcd OBJECT IDENTIFIER ::= { atmIfPnniSig 2 }



atmIfPnniSigVcdRowStatusTable OBJECT-TYPE
   SYNTAX     SEQUENCE OF AtmIfPnniSigVcdRowStatusEntry
   ACCESS     not-accessible
   STATUS     mandatory
   DESCRIPTION
     "This entry controls the addition and deletion of 
      atmIfPnniSigVcd components."
::= { atmIfPnniSigVcd 1 }

atmIfPnniSigVcdRowStatusEntry OBJECT-TYPE
   SYNTAX     AtmIfPnniSigVcdRowStatusEntry
   ACCESS     not-accessible
   STATUS     mandatory
   DESCRIPTION
     "A single entry in the table represents a single 
      atmIfPnniSigVcd component."
   INDEX {
      atmIfIndex,
      atmIfPnniIndex,
      atmIfPnniSigIndex,
      atmIfPnniSigVcdIndex }
::= { atmIfPnniSigVcdRowStatusTable 1 }

AtmIfPnniSigVcdRowStatusEntry ::= SEQUENCE {
   atmIfPnniSigVcdRowStatus
      RowStatus,
   atmIfPnniSigVcdComponentName
      DisplayString,
   atmIfPnniSigVcdStorageType
      StorageType,
   atmIfPnniSigVcdIndex
      NonReplicated }

atmIfPnniSigVcdRowStatus OBJECT-TYPE
   SYNTAX     RowStatus 
   ACCESS     read-write
   STATUS     mandatory
   DESCRIPTION
     "This variable is used as the basis for SNMP naming of
      atmIfPnniSigVcd components.
      These components can be added and deleted."
::= { atmIfPnniSigVcdRowStatusEntry 1 }

atmIfPnniSigVcdComponentName OBJECT-TYPE
   SYNTAX     DisplayString 
   ACCESS     read-only
   STATUS     mandatory
   DESCRIPTION
     "This variable provides the component's string name for
      use with the ASCII Console Interface"
::= { atmIfPnniSigVcdRowStatusEntry 2 }

atmIfPnniSigVcdStorageType OBJECT-TYPE
   SYNTAX     StorageType 
   ACCESS     read-only
   STATUS     mandatory
   DESCRIPTION
     "This variable represents the storage type value for the
      atmIfPnniSigVcd tables."
::= { atmIfPnniSigVcdRowStatusEntry 4 }

atmIfPnniSigVcdIndex OBJECT-TYPE
   SYNTAX     NonReplicated 
   ACCESS     not-accessible
   STATUS     mandatory
   DESCRIPTION
     "This variable represents the index for the atmIfPnniSigVcd tables."
::= { atmIfPnniSigVcdRowStatusEntry 10 }

atmIfPnniSigVcdProvTable OBJECT-TYPE
   SYNTAX     SEQUENCE OF AtmIfPnniSigVcdProvEntry
   ACCESS     not-accessible
   STATUS     mandatory
   DESCRIPTION
     "This group contains the provisionable traffic attributes for a control 
      channel."
::= { atmIfPnniSigVcd 10 }

atmIfPnniSigVcdProvEntry OBJECT-TYPE
   SYNTAX     AtmIfPnniSigVcdProvEntry
   ACCESS     not-accessible
   STATUS     mandatory
   DESCRIPTION
     "An entry in the atmIfPnniSigVcdProvTable."
   INDEX {
      atmIfIndex,
      atmIfPnniIndex,
      atmIfPnniSigIndex,
      atmIfPnniSigVcdIndex }
::= { atmIfPnniSigVcdProvTable 1 }

AtmIfPnniSigVcdProvEntry ::= SEQUENCE {
   atmIfPnniSigVcdTrafficDescType
      INTEGER,
   atmIfPnniSigVcdAtmServiceCategory
      INTEGER,
   atmIfPnniSigVcdQosClass
      INTEGER,
   atmIfPnniSigVcdTrafficShaping
      INTEGER,
   atmIfPnniSigVcdUnshapedTransmitQueueing
      INTEGER,
   atmIfPnniSigVcdUsageParameterControl
      INTEGER }

atmIfPnniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfPnniSigVcdProvEntry 1 }

atmIfPnniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfPnniSigVcdProvEntry 3 }

atmIfPnniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfPnniSigVcdProvEntry 21 }

atmIfPnniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfPnniSigVcdProvEntry 50 }

atmIfPnniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfPnniSigVcdProvEntry 60 }

atmIfPnniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfPnniSigVcdProvEntry 70 }

atmIfPnniSigVcdTdpTable OBJECT-TYPE
   SYNTAX     SEQUENCE OF AtmIfPnniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfPnniSigVcd 387 }

atmIfPnniSigVcdTdpEntry OBJECT-TYPE
   SYNTAX     AtmIfPnniSigVcdTdpEntry
   ACCESS     not-accessible
   STATUS     mandatory
   DESCRIPTION
     "An entry in the atmIfPnniSigVcdTdpTable."
   INDEX {
      atmIfIndex,
      atmIfPnniIndex,
      atmIfPnniSigIndex,
      atmIfPnniSigVcdIndex,
      atmIfPnniSigVcdTdpIndex }
::= { atmIfPnniSigVcdTdpTable 1 }

AtmIfPnniSigVcdTdpEntry ::= SEQUENCE {
   atmIfPnniSigVcdTdpIndex
      Integer32,
   atmIfPnniSigVcdTdpValue
      Unsigned32 }

atmIfPnniSigVcdTdpIndex OBJECT-TYPE
   SYNTAX     Integer32 (1..5)
   ACCESS     not-accessible
   STATUS     mandatory
   DESCRIPTION
     "This variable represents the atmIfPnniSigVcdTdpTable
      specific index for the atmIfPnniSigVcdTdpTable."
::= { atmIfPnniSigVcdTdpEntry 1 }

atmIfPnniSigVcdTdpValue OBJECT-TYPE
   SYNTAX     Unsigned32 (0..2147483647)
   ACCESS     read-write
   STATUS     mandatory
   DESCRIPTION
     "This variable represents an individual value for the
      atmIfPnniSigVcdTdpTable."
::= { atmIfPnniSigVcdTdpEntry 2 }


-- AtmIf/n Pnni RoutingControlChannel
-- AtmIf/n Vpt/m Pnni RoutingControlChannel
-- 
-- This component represents the Routing Control Channel (RCC) 
-- associated with a PNNI interface. The RCC is used to exchange 
-- routing information between nodes in a peer group.

atmIfPnniRcc OBJECT IDENTIFIER ::= { atmIfPnni 3 }



atmIfPnniRccRowStatusTable OBJECT-TYPE
   SYNTAX     SEQUENCE OF AtmIfPnniRccRowStatusEntry
   ACCESS     not-accessible
   STATUS     mandatory
   DESCRIPTION
     "This entry controls the addition and deletion of 
      atmIfPnniRcc components."
::= { atmIfPnniRcc 1 }

atmIfPnniRccRowStatusEntry OBJECT-TYPE
   SYNTAX     AtmIfPnniRccRowStatusEntry
   ACCESS     not-accessible
   STATUS     mandatory
   DESCRIPTION
     "A single entry in the table represents a single 
      atmIfPnniRcc component."
   INDEX {
      atmIfIndex,
      atmIfPnniIndex,
      atmIfPnniRccIndex }
::= { atmIfPnniRccRowStatusTable 1 }

AtmIfPnniRccRowStatusEntry ::= SEQUENCE {
   atmIfPnniRccRowStatus
      RowStatus,
   atmIfPnniRccComponentName
      DisplayString,
   atmIfPnniRccStorageType
      StorageType,
   atmIfPnniRccIndex
      NonReplicated }

atmIfPnniRccRowStatus OBJECT-TYPE
   SYNTAX     RowStatus 
   ACCESS     read-only
   STATUS     mandatory
   DESCRIPTION
     "This variable is used as the basis for SNMP naming of
      atmIfPnniRcc components.
      These components cannot be added nor deleted."
::= { atmIfPnniRccRowStatusEntry 1 }

atmIfPnniRccComponentName OBJECT-TYPE
   SYNTAX     DisplayString 
   ACCESS     read-only
   STATUS     mandatory
   DESCRIPTION
     "This variable provides the component's string name for
      use with the ASCII Console Interface"
::= { atmIfPnniRccRowStatusEntry 2 }

atmIfPnniRccStorageType OBJECT-TYPE
   SYNTAX     StorageType 
   ACCESS     read-only
   STATUS     mandatory
   DESCRIPTION
     "This variable represents the storage type value for the
      atmIfPnniRcc tables."
::= { atmIfPnniRccRowStatusEntry 4 }

atmIfPnniRccIndex OBJECT-TYPE
   SYNTAX     NonReplicated 
   ACCESS     not-accessible
   STATUS     mandatory
   DESCRIPTION
     "This variable represents the index for the atmIfPnniRcc tables."
::= { atmIfPnniRccRowStatusEntry 10 }

atmIfPnniRccProvTable OBJECT-TYPE
   SYNTAX     SEQUENCE OF AtmIfPnniRccProvEntry
   ACCESS     not-accessible
   STATUS     mandatory
   DESCRIPTION
     "This group contains the generic provisionable attributes of an Rcc 
      component."
::= { atmIfPnniRcc 10 }

atmIfPnniRccProvEntry OBJECT-TYPE
   SYNTAX     AtmIfPnniRccProvEntry
   ACCESS     not-accessible
   STATUS     mandatory
   DESCRIPTION
     "An entry in the atmIfPnniRccProvTable."
   INDEX {
      atmIfIndex,
      atmIfPnniIndex,
      atmIfPnniRccIndex }
::= { atmIfPnniRccProvTable 1 }

AtmIfPnniRccProvEntry ::= SEQUENCE {
   atmIfPnniRccVci
      Unsigned32 }

atmIfPnniRccVci OBJECT-TYPE
   SYNTAX     Unsigned32 (0..65535)
   ACCESS     read-write
   STATUS     mandatory
   DESCRIPTION
     "This attribute specifies the VCI for the Routing Control Channel 
      (RCC). It is not recommended that the value be changed from the 
      default of 18 unless absolutely necessary. If a different VCI is 
      specified, ensure that the RCC at the far end is provisioned to use 
      the same VCI, otherwise the RCC will not come up."
   DEFVAL     { 18 }
::= { atmIfPnniRccProvEntry 1 }

atmIfPnniRccHlParmsTable OBJECT-TYPE
   SYNTAX     SEQUENCE OF AtmIfPnniRccHlParmsEntry
   ACCESS     not-accessible
   STATUS     mandatory
   DESCRIPTION
     "This group contains the provisionable Hello protocol parameters for 
      an Rcc component."
::= { atmIfPnniRcc 11 }

atmIfPnniRccHlParmsEntry OBJECT-TYPE
   SYNTAX     AtmIfPnniRccHlParmsEntry
   ACCESS     not-accessible
   STATUS     mandatory
   DESCRIPTION
     "An entry in the atmIfPnniRccHlParmsTable."
   INDEX {
      atmIfIndex,
      atmIfPnniIndex,
      atmIfPnniRccIndex }
::= { atmIfPnniRccHlParmsTable 1 }

AtmIfPnniRccHlParmsEntry ::= SEQUENCE {
   atmIfPnniRccHelloHoldDown
      FixedPoint1,
   atmIfPnniRccHelloInterval
      Unsigned32,
   atmIfPnniRccHelloInactivityFactor
      Unsigned32 }

atmIfPnniRccHelloHoldDown OBJECT-TYPE
   SYNTAX     FixedPoint1 (0..655350)
   ACCESS     read-write
   STATUS     mandatory
   DESCRIPTION
     "This attribute is used to limit the rate at which this node sends out 
      Hello packets. Specifically, it specifies the minimum time between 
      successive Hellos.
      
      A value of 0 specifies that the value provisioned for the 
      helloHoldDown attribute of the ARtg Pnni component should be 
      used."
   DEFVAL     { 0 }
::= { atmIfPnniRccHlParmsEntry 1 }

atmIfPnniRccHelloInterval OBJECT-TYPE
   SYNTAX     Unsigned32 (0..65535)
   ACCESS     read-write
   STATUS     mandatory
   DESCRIPTION
     "This attribute specifies the duration of the Hello Timer. Every 
      helloInterval seconds, this node will send out a Hello packet to the 
      neighbor node, subject to the helloHoldDown timer having expired 
      at least once since the last Hello packet was sent.
      
      A value of 0 specifies that the value provisioned for the 
      helloInterval attribute of the ARtg Pnni component should be used."
   DEFVAL     { 0 }
::= { atmIfPnniRccHlParmsEntry 2 }

atmIfPnniRccHelloInactivityFactor OBJECT-TYPE
   SYNTAX     Unsigned32 (0..65535)
   ACCESS     read-write
   STATUS     mandatory
   DESCRIPTION
     "This attribute specifies the number of Hello intervals allowed to 
      pass without receiving a Hello from the neighbor node, before an 
      attempt is made to re-stage. The hello inactivity timer is enabled in 
      the oneWayInside, twoWayInside, oneWayOutside, 
      twoWayOutside and commonOutside hello states (see the 
      helloState attribute on the Rcc component for a description of these 
      states). Note that the value for the Hello interval used in the 
      calculation is the one specified in the Hello packet from the 
      neighbor node.
      
      A value of 0 specifies that the value provisioned for the 
      helloInactivityFactor attribute of the ARtg Pnni component should 
      be used.
      DESCRIPTION"
   DEFVAL     { 0 }
::= { atmIfPnniRccHlParmsEntry 3 }

atmIfPnniRccStateTable OBJECT-TYPE
   SYNTAX     SEQUENCE OF AtmIfPnniRccStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfPnniRcc 12 }

atmIfPnniRccStateEntry OBJECT-TYPE
   SYNTAX     AtmIfPnniRccStateEntry
   ACCESS     not-accessible
   STATUS     mandatory
   DESCRIPTION
     "An entry in the atmIfPnniRccStateTable."
   INDEX {
      atmIfIndex,
      atmIfPnniIndex,
      atmIfPnniRccIndex }
::= { atmIfPnniRccStateTable 1 }

AtmIfPnniRccStateEntry ::= SEQUENCE {
   atmIfPnniRccAdminState
      INTEGER,
   atmIfPnniRccOperationalState
      INTEGER,
   atmIfPnniRccUsageState
      INTEGER }

atmIfPnniRccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfPnniRccStateEntry 1 }

atmIfPnniRccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfPnniRccStateEntry 2 }

atmIfPnniRccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfPnniRccStateEntry 3 }

atmIfPnniRccOperTable OBJECT-TYPE
   SYNTAX     SEQUENCE OF AtmIfPnniRccOperEntry
   ACCESS     not-accessible
   STATUS     mandatory
   DESCRIPTION
     "This group contains the operational attributes for an Rcc 
      component."
::= { atmIfPnniRcc 13 }

atmIfPnniRccOperEntry OBJECT-TYPE
   SYNTAX     AtmIfPnniRccOperEntry
   ACCESS     not-accessible
   STATUS     mandatory
   DESCRIPTION
     "An entry in the atmIfPnniRccOperTable."
   INDEX {
      atmIfIndex,
      atmIfPnniIndex,
      atmIfPnniRccIndex }
::= { atmIfPnniRccOperTable 1 }

AtmIfPnniRccOperEntry ::= SEQUENCE {
   atmIfPnniRccType
      INTEGER,
   atmIfPnniRccNegotiatedVersion
      INTEGER,
   atmIfPnniRccHelloState
      INTEGER,
   atmIfPnniRccRemoteNodeId
      HexString,
   atmIfPnniRccRemotePortId
      Unsigned32 }

atmIfPnniRccType OBJECT-TYPE
   SYNTAX     INTEGER  {
                 unknown(0),
                 lowestLevelHorizLink(1),
                 lowestLevelOutsideLink(2),
                 horizontalLinkToLGN(3),
                 uplink(4) }
   ACCESS     read-only
   STATUS     mandatory
   DESCRIPTION
     "This attribute indicates the role of this link in the PNNI hierarchy.
      The following values are possible:
      
      unknown: the Hello protocol has not yet determined the role of the 
      link.
      
      lowestLevelHorizLink: the link is a horizontal link between two 
      lowest level nodes.
      
      lowestLevelOutsideLink: the link is an outside link between two 
      border nodes.
      
      horizontalLinkToLgn: the link is a horizontal link to a Logical 
      Group Node (LGN).
      
      uplink: the link is a uplink to a higher level LGN."
::= { atmIfPnniRccOperEntry 1 }

atmIfPnniRccNegotiatedVersion OBJECT-TYPE
   SYNTAX     INTEGER  {
                 unsupported(0),
                 version1point0(1) }
   ACCESS     read-only
   STATUS     mandatory
   DESCRIPTION
     "This attribute indicates the PNNI version negotiated with the 
      neighbor node."
::= { atmIfPnniRccOperEntry 2 }

atmIfPnniRccHelloState OBJECT-TYPE
   SYNTAX     INTEGER  {
                 notApplicable(0),
                 down(1),
                 attempt(2),
                 oneWayInside(3),
                 twoWayInside(4),
                 oneWayOutside(5),
                 twoWayOutside(6),
                 commonOutside(7) }
   ACCESS     read-only
   STATUS     mandatory
   DESCRIPTION
     "This attribute indicates the state of the Hello protocol exchange over 
      this link. The following are the possible values for this attribute:
      
      down: the link is down; no PNNI routing packets will be sent over 
      or received over such a link. This is the initial state of the Hello 
      Finite State Machine, and can also be reached when lower-level 
      protocols have indicated that the link is not usable.
      
      attempt: no Hello packets or Hello packets, with mismatch 
      information, have been received recently from the neighbor. 
      Attempts are made to contact the neighbor node by sending out 
      Hello packets every helloInterval seconds.
      
      oneWayInside: Hello packets have been recently received from the 
      neighbor and it has been established that both nodes are members of 
      the same peer group, but the remote node ID and remote port ID in 
      the neighbor's Hello packets were set to zero. A Hello packet is sent 
      to the neighbor and the Hello timer is restarted.
      
      twoWayInside: Bidirectional communication over this link between 
      this node and the neighbor node has been achieved.
      
      oneWayOutside: Hello packets have been recently received from 
      the neighbor and it has been established that both nodes are 
      members of a different peer group, but the remote node ID and 
      remote port ID in the neighbor's Hello packets were set to zero.
      
      twoWayOutside: Hellos have recently been received from the 
      neighbor indicating that the neighbor node belongs to a different 
      peer group. The correct remote node ID and remote port ID fields 
      were included in the Hello packet, but the nodal hierarchy list did 
      not include any common peer group. This state can also be reached 
      if a hierarchy mismatch occurs while in the commonOutside state.
      
      commonOutside: A common level of the routing hierarchy has been 
      found, in addition to achieving full bi-directional communication 
      between the two nodes."
::= { atmIfPnniRccOperEntry 3 }

atmIfPnniRccRemoteNodeId OBJECT-TYPE
   SYNTAX     HexString (SIZE (22))
   ACCESS     read-only
   STATUS     mandatory
   DESCRIPTION
     "This attribute indicates the neighbor node's node id."
::= { atmIfPnniRccOperEntry 4 }

atmIfPnniRccRemotePortId OBJECT-TYPE
   SYNTAX     Unsigned32 (0..4294967295)
   ACCESS     read-only
   STATUS     mandatory
   DESCRIPTION
     "This attribute indicates the neighbor node's port id."
::= { atmIfPnniRccOperEntry 5 }

atmIfPnniRccStatsTable OBJECT-TYPE
   SYNTAX     SEQUENCE OF AtmIfPnniRccStatsEntry
   ACCESS     not-accessible
   STATUS     mandatory
   DESCRIPTION
     "This group contains the statistical attributes for an Rcc component."
::= { atmIfPnniRcc 14 }

atmIfPnniRccStatsEntry OBJECT-TYPE
   SYNTAX     AtmIfPnniRccStatsEntry
   ACCESS     not-accessible
   STATUS     mandatory
   DESCRIPTION
     "An entry in the atmIfPnniRccStatsTable."
   INDEX {
      atmIfIndex,
      atmIfPnniIndex,
      atmIfPnniRccIndex }
::= { atmIfPnniRccStatsTable 1 }

AtmIfPnniRccStatsEntry ::= SEQUENCE {
   atmIfPnniRccHelloPacketsRx
      Counter32,
   atmIfPnniRccHelloPacketsTx
      Counter32,
   atmIfPnniRccMismatchedHelloPacketsRx
      Counter32,
   atmIfPnniRccBadHelloPacketsRx
      Counter32 }

atmIfPnniRccHelloPacketsRx OBJECT-TYPE
   SYNTAX     Counter32 
   ACCESS     read-only
   STATUS     mandatory
   DESCRIPTION
     "This attribute counts the total number of Hello packets received 
      across this RCC, including bad and mismatched Hello packets. The 
      counter wraps when it exceeds the maximum value."
::= { atmIfPnniRccStatsEntry 1 }

atmIfPnniRccHelloPacketsTx OBJECT-TYPE
   SYNTAX     Counter32 
   ACCESS     read-only
   STATUS     mandatory
   DESCRIPTION
     "This attribute counts the total number of Hello packets transmitted 
      across this RCC. The counter wraps when it exceeds the maximum 
      value."
::= { atmIfPnniRccStatsEntry 2 }

atmIfPnniRccMismatchedHelloPacketsRx OBJECT-TYPE
   SYNTAX     Counter32 
   ACCESS     read-only
   STATUS     mandatory
   DESCRIPTION
     "This attribute counts the total number of mismatched Hello packets 
      received over this RCC. The counter wraps when it exceeds the 
      maximum value."
::= { atmIfPnniRccStatsEntry 3 }

atmIfPnniRccBadHelloPacketsRx OBJECT-TYPE
   SYNTAX     Counter32 
   ACCESS     read-only
   STATUS     mandatory
   DESCRIPTION
     "This attribute counts the total number of bad Hello packets received 
      over this RCC. The counter wraps when it exceeds the maximum 
      value."
::= { atmIfPnniRccStatsEntry 4 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfPnniRccVcd OBJECT IDENTIFIER ::= { atmIfPnniRcc 2 }



atmIfPnniRccVcdRowStatusTable OBJECT-TYPE
   SYNTAX     SEQUENCE OF AtmIfPnniRccVcdRowStatusEntry
   ACCESS     not-accessible
   STATUS     mandatory
   DESCRIPTION
     "This entry controls the addition and deletion of 
      atmIfPnniRccVcd components."
::= { atmIfPnniRccVcd 1 }

atmIfPnniRccVcdRowStatusEntry OBJECT-TYPE
   SYNTAX     AtmIfPnniRccVcdRowStatusEntry
   ACCESS     not-accessible
   STATUS     mandatory
   DESCRIPTION
     "A single entry in the table represents a single 
      atmIfPnniRccVcd component."
   INDEX {
      atmIfIndex,
      atmIfPnniIndex,
      atmIfPnniRccIndex,
      atmIfPnniRccVcdIndex }
::= { atmIfPnniRccVcdRowStatusTable 1 }

AtmIfPnniRccVcdRowStatusEntry ::= SEQUENCE {
   atmIfPnniRccVcdRowStatus
      RowStatus,
   atmIfPnniRccVcdComponentName
      DisplayString,
   atmIfPnniRccVcdStorageType
      StorageType,
   atmIfPnniRccVcdIndex
      NonReplicated }

atmIfPnniRccVcdRowStatus OBJECT-TYPE
   SYNTAX     RowStatus 
   ACCESS     read-write
   STATUS     mandatory
   DESCRIPTION
     "This variable is used as the basis for SNMP naming of
      atmIfPnniRccVcd components.
      These components can be added and deleted."
::= { atmIfPnniRccVcdRowStatusEntry 1 }

atmIfPnniRccVcdComponentName OBJECT-TYPE
   SYNTAX     DisplayString 
   ACCESS     read-only
   STATUS     mandatory
   DESCRIPTION
     "This variable provides the component's string name for
      use with the ASCII Console Interface"
::= { atmIfPnniRccVcdRowStatusEntry 2 }

atmIfPnniRccVcdStorageType OBJECT-TYPE
   SYNTAX     StorageType 
   ACCESS     read-only
   STATUS     mandatory
   DESCRIPTION
     "This variable represents the storage type value for the
      atmIfPnniRccVcd tables."
::= { atmIfPnniRccVcdRowStatusEntry 4 }

atmIfPnniRccVcdIndex OBJECT-TYPE
   SYNTAX     NonReplicated 
   ACCESS     not-accessible
   STATUS     mandatory
   DESCRIPTION
     "This variable represents the index for the atmIfPnniRccVcd tables."
::= { atmIfPnniRccVcdRowStatusEntry 10 }

atmIfPnniRccVcdProvTable OBJECT-TYPE
   SYNTAX     SEQUENCE OF AtmIfPnniRccVcdProvEntry
   ACCESS     not-accessible
   STATUS     mandatory
   DESCRIPTION
     "This group contains the provisionable traffic attributes for a control 
      channel."
::= { atmIfPnniRccVcd 10 }

atmIfPnniRccVcdProvEntry OBJECT-TYPE
   SYNTAX     AtmIfPnniRccVcdProvEntry
   ACCESS     not-accessible
   STATUS     mandatory
   DESCRIPTION
     "An entry in the atmIfPnniRccVcdProvTable."
   INDEX {
      atmIfIndex,
      atmIfPnniIndex,
      atmIfPnniRccIndex,
      atmIfPnniRccVcdIndex }
::= { atmIfPnniRccVcdProvTable 1 }

AtmIfPnniRccVcdProvEntry ::= SEQUENCE {
   atmIfPnniRccVcdTrafficDescType
      INTEGER,
   atmIfPnniRccVcdAtmServiceCategory
      INTEGER,
   atmIfPnniRccVcdQosClass
      INTEGER,
   atmIfPnniRccVcdTrafficShaping
      INTEGER,
   atmIfPnniRccVcdUnshapedTransmitQueueing
      INTEGER,
   atmIfPnniRccVcdUsageParameterControl
      INTEGER }

atmIfPnniRccVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfPnniRccVcdProvEntry 1 }

atmIfPnniRccVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfPnniRccVcdProvEntry 3 }

atmIfPnniRccVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfPnniRccVcdProvEntry 21 }

atmIfPnniRccVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfPnniRccVcdProvEntry 50 }

atmIfPnniRccVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfPnniRccVcdProvEntry 60 }

atmIfPnniRccVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfPnniRccVcdProvEntry 70 }

atmIfPnniRccVcdTdpTable OBJECT-TYPE
   SYNTAX     SEQUENCE OF AtmIfPnniRccVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfPnniRccVcd 387 }

atmIfPnniRccVcdTdpEntry OBJECT-TYPE
   SYNTAX     AtmIfPnniRccVcdTdpEntry
   ACCESS     not-accessible
   STATUS     mandatory
   DESCRIPTION
     "An entry in the atmIfPnniRccVcdTdpTable."
   INDEX {
      atmIfIndex,
      atmIfPnniIndex,
      atmIfPnniRccIndex,
      atmIfPnniRccVcdIndex,
      atmIfPnniRccVcdTdpIndex }
::= { atmIfPnniRccVcdTdpTable 1 }

AtmIfPnniRccVcdTdpEntry ::= SEQUENCE {
   atmIfPnniRccVcdTdpIndex
      Integer32,
   atmIfPnniRccVcdTdpValue
      Unsigned32 }

atmIfPnniRccVcdTdpIndex OBJECT-TYPE
   SYNTAX     Integer32 (1..5)
   ACCESS     not-accessible
   STATUS     mandatory
   DESCRIPTION
     "This variable represents the atmIfPnniRccVcdTdpTable
      specific index for the atmIfPnniRccVcdTdpTable."
::= { atmIfPnniRccVcdTdpEntry 1 }

atmIfPnniRccVcdTdpValue OBJECT-TYPE
   SYNTAX     Unsigned32 (0..2147483647)
   ACCESS     read-write
   STATUS     mandatory
   DESCRIPTION
     "This variable represents an individual value for the
      atmIfPnniRccVcdTdpTable."
::= { atmIfPnniRccVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

atmIfPnniAddr OBJECT IDENTIFIER ::= { atmIfPnni 4 }



atmIfPnniAddrRowStatusTable OBJECT-TYPE
   SYNTAX     SEQUENCE OF AtmIfPnniAddrRowStatusEntry
   ACCESS     not-accessible
   STATUS     mandatory
   DESCRIPTION
     "This entry controls the addition and deletion of 
      atmIfPnniAddr components."
::= { atmIfPnniAddr 1 }

atmIfPnniAddrRowStatusEntry OBJECT-TYPE
   SYNTAX     AtmIfPnniAddrRowStatusEntry
   ACCESS     not-accessible
   STATUS     mandatory
   DESCRIPTION
     "A single entry in the table represents a single 
      atmIfPnniAddr component."
   INDEX {
      atmIfIndex,
      atmIfPnniIndex,
      atmIfPnniAddrAddressIndex,
      atmIfPnniAddrAddressTypeIndex }
::= { atmIfPnniAddrRowStatusTable 1 }

AtmIfPnniAddrRowStatusEntry ::= SEQUENCE {
   atmIfPnniAddrRowStatus
      RowStatus,
   atmIfPnniAddrComponentName
      DisplayString,
   atmIfPnniAddrStorageType
      StorageType,
   atmIfPnniAddrAddressIndex
      AsciiStringIndex,
   atmIfPnniAddrAddressTypeIndex
      INTEGER }

atmIfPnniAddrRowStatus OBJECT-TYPE
   SYNTAX     RowStatus 
   ACCESS     read-write
   STATUS     mandatory
   DESCRIPTION
     "This variable is used as the basis for SNMP naming of
      atmIfPnniAddr components.
      These components can be added and deleted."
::= { atmIfPnniAddrRowStatusEntry 1 }

atmIfPnniAddrComponentName OBJECT-TYPE
   SYNTAX     DisplayString 
   ACCESS     read-only
   STATUS     mandatory
   DESCRIPTION
     "This variable provides the component's string name for
      use with the ASCII Console Interface"
::= { atmIfPnniAddrRowStatusEntry 2 }

atmIfPnniAddrStorageType OBJECT-TYPE
   SYNTAX     StorageType 
   ACCESS     read-only
   STATUS     mandatory
   DESCRIPTION
     "This variable represents the storage type value for the
      atmIfPnniAddr tables."
::= { atmIfPnniAddrRowStatusEntry 4 }

atmIfPnniAddrAddressIndex OBJECT-TYPE
   SYNTAX     AsciiStringIndex (SIZE (1..40))
   ACCESS     not-accessible
   STATUS     mandatory
   DESCRIPTION
     "This variable represents an index for the atmIfPnniAddr tables."
::= { atmIfPnniAddrRowStatusEntry 10 }

atmIfPnniAddrAddressTypeIndex OBJECT-TYPE
   SYNTAX     INTEGER  {
                 primary(0),
                 alternate(1),
                 registered(2),
                 default(3) }
   ACCESS     not-accessible
   STATUS     mandatory
   DESCRIPTION
     "This variable represents an index for the atmIfPnniAddr tables."
::= { atmIfPnniAddrRowStatusEntry 11 }

atmIfPnniAddrOperTable OBJECT-TYPE
   SYNTAX     SEQUENCE OF AtmIfPnniAddrOperEntry
   ACCESS     not-accessible
   STATUS     mandatory
   DESCRIPTION
     "This attribute group contains the operational attributes for the 
      Address component."
::= { atmIfPnniAddr 10 }

atmIfPnniAddrOperEntry OBJECT-TYPE
   SYNTAX     AtmIfPnniAddrOperEntry
   ACCESS     not-accessible
   STATUS     mandatory
   DESCRIPTION
     "An entry in the atmIfPnniAddrOperTable."
   INDEX {
      atmIfIndex,
      atmIfPnniIndex,
      atmIfPnniAddrAddressIndex,
      atmIfPnniAddrAddressTypeIndex }
::= { atmIfPnniAddrOperTable 1 }

AtmIfPnniAddrOperEntry ::= SEQUENCE {
   atmIfPnniAddrScope
      INTEGER,
   atmIfPnniAddrReachability
      INTEGER }

atmIfPnniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { atmIfPnniAddrOperEntry 1 }

atmIfPnniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { atmIfPnniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

atmIfPnniAddrTermSP OBJECT IDENTIFIER ::= { atmIfPnniAddr 2 }



atmIfPnniAddrTermSPRowStatusTable OBJECT-TYPE
   SYNTAX     SEQUENCE OF AtmIfPnniAddrTermSPRowStatusEntry
   ACCESS     not-accessible
   STATUS     mandatory
   DESCRIPTION
     "This entry controls the addition and deletion of 
      atmIfPnniAddrTermSP components."
::= { atmIfPnniAddrTermSP 1 }

atmIfPnniAddrTermSPRowStatusEntry OBJECT-TYPE
   SYNTAX     AtmIfPnniAddrTermSPRowStatusEntry
   ACCESS     not-accessible
   STATUS     mandatory
   DESCRIPTION
     "A single entry in the table represents a single 
      atmIfPnniAddrTermSP component."
   INDEX {
      atmIfIndex,
      atmIfPnniIndex,
      atmIfPnniAddrAddressIndex,
      atmIfPnniAddrAddressTypeIndex,
      atmIfPnniAddrTermSPIndex }
::= { atmIfPnniAddrTermSPRowStatusTable 1 }

AtmIfPnniAddrTermSPRowStatusEntry ::= SEQUENCE {
   atmIfPnniAddrTermSPRowStatus
      RowStatus,
   atmIfPnniAddrTermSPComponentName
      DisplayString,
   atmIfPnniAddrTermSPStorageType
      StorageType,
   atmIfPnniAddrTermSPIndex
      NonReplicated }

atmIfPnniAddrTermSPRowStatus OBJECT-TYPE
   SYNTAX     RowStatus 
   ACCESS     read-write
   STATUS     mandatory
   DESCRIPTION
     "This variable is used as the basis for SNMP naming of
      atmIfPnniAddrTermSP components.
      These components can be added and deleted."
::= { atmIfPnniAddrTermSPRowStatusEntry 1 }

atmIfPnniAddrTermSPComponentName OBJECT-TYPE
   SYNTAX     DisplayString 
   ACCESS     read-only
   STATUS     mandatory
   DESCRIPTION
     "This variable provides the component's string name for
      use with the ASCII Console Interface"
::= { atmIfPnniAddrTermSPRowStatusEntry 2 }

atmIfPnniAddrTermSPStorageType OBJECT-TYPE
   SYNTAX     StorageType 
   ACCESS     read-only
   STATUS     mandatory
   DESCRIPTION
     "This variable represents the storage type value for the
      atmIfPnniAddrTermSP tables."
::= { atmIfPnniAddrTermSPRowStatusEntry 4 }

atmIfPnniAddrTermSPIndex OBJECT-TYPE
   SYNTAX     NonReplicated 
   ACCESS     not-accessible
   STATUS     mandatory
   DESCRIPTION
     "This variable represents the index for the atmIfPnniAddrTermSP tables."
::= { atmIfPnniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

atmIfPnniAddrPnniInfo OBJECT IDENTIFIER ::= { atmIfPnniAddr 3 }



atmIfPnniAddrPnniInfoRowStatusTable OBJECT-TYPE
   SYNTAX     SEQUENCE OF AtmIfPnniAddrPnniInfoRowStatusEntry
   ACCESS     not-accessible
   STATUS     mandatory
   DESCRIPTION
     "This entry controls the addition and deletion of 
      atmIfPnniAddrPnniInfo components."
::= { atmIfPnniAddrPnniInfo 1 }

atmIfPnniAddrPnniInfoRowStatusEntry OBJECT-TYPE
   SYNTAX     AtmIfPnniAddrPnniInfoRowStatusEntry
   ACCESS     not-accessible
   STATUS     mandatory
   DESCRIPTION
     "A single entry in the table represents a single 
      atmIfPnniAddrPnniInfo component."
   INDEX {
      atmIfIndex,
      atmIfPnniIndex,
      atmIfPnniAddrAddressIndex,
      atmIfPnniAddrAddressTypeIndex,
      atmIfPnniAddrPnniInfoIndex }
::= { atmIfPnniAddrPnniInfoRowStatusTable 1 }

AtmIfPnniAddrPnniInfoRowStatusEntry ::= SEQUENCE {
   atmIfPnniAddrPnniInfoRowStatus
      RowStatus,
   atmIfPnniAddrPnniInfoComponentName
      DisplayString,
   atmIfPnniAddrPnniInfoStorageType
      StorageType,
   atmIfPnniAddrPnniInfoIndex
      NonReplicated }

atmIfPnniAddrPnniInfoRowStatus OBJECT-TYPE
   SYNTAX     RowStatus 
   ACCESS     read-write
   STATUS     mandatory
   DESCRIPTION
     "This variable is used as the basis for SNMP naming of
      atmIfPnniAddrPnniInfo components.
      These components can be added and deleted."
::= { atmIfPnniAddrPnniInfoRowStatusEntry 1 }

atmIfPnniAddrPnniInfoComponentName OBJECT-TYPE
   SYNTAX     DisplayString 
   ACCESS     read-only
   STATUS     mandatory
   DESCRIPTION
     "This variable provides the component's string name for
      use with the ASCII Console Interface"
::= { atmIfPnniAddrPnniInfoRowStatusEntry 2 }

atmIfPnniAddrPnniInfoStorageType OBJECT-TYPE
   SYNTAX     StorageType 
   ACCESS     read-only
   STATUS     mandatory
   DESCRIPTION
     "This variable represents the storage type value for the
      atmIfPnniAddrPnniInfo tables."
::= { atmIfPnniAddrPnniInfoRowStatusEntry 4 }

atmIfPnniAddrPnniInfoIndex OBJECT-TYPE
   SYNTAX     NonReplicated 
   ACCESS     not-accessible
   STATUS     mandatory
   DESCRIPTION
     "This variable represents the index for the atmIfPnniAddrPnniInfo tables."
::= { atmIfPnniAddrPnniInfoRowStatusEntry 10 }

atmIfPnniAddrPnniInfoProvTable OBJECT-TYPE
   SYNTAX     SEQUENCE OF AtmIfPnniAddrPnniInfoProvEntry
   ACCESS     not-accessible
   STATUS     mandatory
   DESCRIPTION
     "This attribute group contains the provisioned attributes relating to 
      PNNI for a PnniInfo component."
::= { atmIfPnniAddrPnniInfo 10 }

atmIfPnniAddrPnniInfoProvEntry OBJECT-TYPE
   SYNTAX     AtmIfPnniAddrPnniInfoProvEntry
   ACCESS     not-accessible
   STATUS     mandatory
   DESCRIPTION
     "An entry in the atmIfPnniAddrPnniInfoProvTable."
   INDEX {
      atmIfIndex,
      atmIfPnniIndex,
      atmIfPnniAddrAddressIndex,
      atmIfPnniAddrAddressTypeIndex,
      atmIfPnniAddrPnniInfoIndex }
::= { atmIfPnniAddrPnniInfoProvTable 1 }

AtmIfPnniAddrPnniInfoProvEntry ::= SEQUENCE {
   atmIfPnniAddrPnniInfoScope
      INTEGER,
   atmIfPnniAddrPnniInfoReachability
      INTEGER }

atmIfPnniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { atmIfPnniAddrPnniInfoProvEntry 1 }

atmIfPnniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { atmIfPnniAddrPnniInfoProvEntry 2 }




-- 
-- Version and Compliance statements
-- 



-- Object-Group Statement:
-- A list of all current accessible leaf objects.

-- OBJECTS { atmIfPnniAccountConnectionType,
--           atmIfPnniAddrComponentName,
--           atmIfVptPnniRccHelloInactivityFactor,
--           atmIfPnniAddrPnniInfoStorageType,
--           atmIfVptPnniSigUsageState,
--           atmIfVptPnniRccVcdTrafficShaping,
--           atmIfPnniRccHelloHoldDown,
--           atmIfPnniSigVcdStorageType,
--           atmIfVptPnniRccHelloPacketsRx,
--           atmIfPnniRccMismatchedHelloPacketsRx,
--           atmIfVptPnniSigTxPdus,
--           atmIfVptPnniAddrScope,
--           atmIfVptPnniSigVcdQosClass,
--           atmIfPnniRccVcdStorageType,
--           atmIfVptPnniSigLastTxDiagCode,
--           atmIfPnniPortId,
--           atmIfPnniSigComponentName,
--           atmIfVptPnniSigOperationalState,
--           atmIfPnniRccType,
--           atmIfVptPnniRtVbrWeight,
--           atmIfVptPnniSigCurrentPmpConnections,
--           atmIfPnniRccVcdTrafficDescType,
--           atmIfPnniRccHelloInactivityFactor,
--           atmIfPnniRccVcdRowStatus,
--           atmIfVptPnniAddrTermSPComponentName,
--           atmIfVptPnniSigVcdComponentName,
--           atmIfPnniRtVbrWeight,
--           atmIfVptPnniSoftPvpAndPvcRetryPeriod,
--           atmIfPnniSigVcdRowStatus,
--           atmIfVptPnniAddrPnniInfoComponentName,
--           atmIfPnniRccStorageType,
--           atmIfVptPnniRccType,
--           atmIfPnniAccountCollection,
--           atmIfVptPnniSigRxPdus,
--           atmIfPnniAddrStorageType,
--           atmIfPnniStorageType,
--           atmIfVptPnniRccVcdStorageType,
--           atmIfVptPnniSigLastRxDiagCode,
--           atmIfPnniRccRemoteNodeId,
--           atmIfPnniRccVcdTdpValue,
--           atmIfVptPnniSigFailedConnections,
--           atmIfVptPnniSigLastTxCauseCode,
--           atmIfVptPnniSigPeakPmpConnections,
--           atmIfPnniSigSuccessfulPmpConnections,
--           atmIfPnniSigVcdTrafficShaping,
--           atmIfVptPnniRccBadHelloPacketsRx,
--           atmIfPnniAddrReachability,
--           atmIfPnniAddrPnniInfoReachability,
--           atmIfPnniAddrTermSPStorageType,
--           atmIfVptPnniSigSuccessfulConnections,
--           atmIfVptPnniRccRowStatus,
--           atmIfVptPnniRccVci,
--           atmIfVptPnniCbrWeight,
--           atmIfPnniRccHelloState,
--           atmIfPnniAddrRowStatus,
--           atmIfVptPnniSigNewCurrentConnections,
--           atmIfPnniSigVcdUsageParameterControl,
--           atmIfVptPnniRccVcdUnshapedTransmitQueueing,
--           atmIfPnniNrtVbrWeight,
--           atmIfVptPnniRccVcdRowStatus,
--           atmIfVptPnniRccRemotePortId,
--           atmIfPnniSigRxPdus,
--           atmIfPnniSigStorageType,
--           atmIfPnniSoftPvpAndPvcHoldOffTime,
--           atmIfVptPnniSigAddressConversion,
--           atmIfVptPnniComponentName,
--           atmIfVptPnniSigStorageType,
--           atmIfVptPnniSigVcdTrafficShaping,
--           atmIfPnniSoftPvpAndPvcRetryPeriod,
--           atmIfVptPnniVpci,
--           atmIfVptPnniSigVcdStorageType,
--           atmIfPnniAddrPnniInfoScope,
--           atmIfPnniSigAdminState,
--           atmIfVptPnniAccountClass,
--           atmIfVptPnniRccHelloHoldDown,
--           atmIfPnniUbrWeight,
--           atmIfPnniServiceExchange,
--           atmIfVptPnniAccountConnectionType,
--           atmIfVptPnniSigVcdTdpValue,
--           atmIfPnniRccComponentName,
--           atmIfPnniRccVcdQosClass,
--           atmIfVptPnniAddrPnniInfoStorageType,
--           atmIfVptPnniSigFailedPmpConnections,
--           atmIfPnniRccOperationalState,
--           atmIfPnniSigRowStatus,
--           atmIfPnniSigPeakPmpConnections,
--           atmIfPnniAddrPnniInfoRowStatus,
--           atmIfPnniAddrTermSPRowStatus,
--           atmIfVptPnniRccMismatchedHelloPacketsRx,
--           atmIfVptPnniSigVci,
--           atmIfVptPnniRccVcdComponentName,
--           atmIfPnniRccVcdComponentName,
--           atmIfPnniSigTxPdus,
--           atmIfPnniRccVcdUsageParameterControl,
--           atmIfVptPnniAddrComponentName,
--           atmIfVptPnniSigVcdUnshapedTransmitQueueing,
--           atmIfVptPnniPortId,
--           atmIfVptPnniSigComponentName,
--           atmIfVptPnniSigVcdRowStatus,
--           atmIfVptPnniRccVcdTrafficDescType,
--           atmIfVptPnniSigLastRxCauseCode,
--           atmIfPnniSigUsageState,
--           atmIfPnniRccVcdTrafficShaping,
--           atmIfPnniRccHelloInterval,
--           atmIfPnniSigPeakConnections,
--           atmIfVptPnniAddrPnniInfoRowStatus,
--           atmIfPnniRccHelloPacketsRx,
--           atmIfVptPnniRccVcdUsageParameterControl,
--           atmIfPnniSigFailedConnections,
--           atmIfPnniRccVcdUnshapedTransmitQueueing,
--           atmIfPnniAddrScope,
--           atmIfVptPnniRccStorageType,
--           atmIfPnniSigVcdAtmServiceCategory,
--           atmIfVptPnniAccountCollection,
--           atmIfVptPnniAddrTermSPStorageType,
--           atmIfPnniSigVcdQosClass,
--           atmIfPnniSigOperationalState,
--           atmIfVptPnniAddrStorageType,
--           atmIfVptPnniStorageType,
--           atmIfPnniSigCurrentPmpConnections,
--           atmIfVptPnniRccVcdAtmServiceCategory,
--           atmIfPnniAddrTermSPComponentName,
--           atmIfPnniSigVcdComponentName,
--           atmIfPnniSigLastTxDiagCode,
--           atmIfVptPnniSigSuccessfulPmpConnections,
--           atmIfPnniRccHelloPacketsTx,
--           atmIfVptPnniRccAdminState,
--           atmIfVptPnniAddrReachability,
--           atmIfPnniRccRowStatus,
--           atmIfPnniAddrPnniInfoComponentName,
--           atmIfVptPnniSigVcdTrafficDescType,
--           atmIfPnniRccAdminState,
--           atmIfVptPnniRccRemoteNodeId,
--           atmIfPnniRowStatus,
--           atmIfVptPnniRccNegotiatedVersion,
--           atmIfVptPnniRccVcdTdpValue,
--           atmIfPnniSigSuccessfulConnections,
--           atmIfPnniSigFailedPmpConnections,
--           atmIfVptPnniSigVcdUsageParameterControl,
--           atmIfVptPnniRowStatus,
--           atmIfPnniSigVcdUnshapedTransmitQueueing,
--           atmIfVptPnniNrtVbrWeight,
--           atmIfPnniRccVcdAtmServiceCategory,
--           atmIfPnniSigLastTxCauseCode,
--           atmIfVptPnniAddrPnniInfoReachability,
--           atmIfVptPnniSoftPvpAndPvcHoldOffTime,
--           atmIfVptPnniRccUsageState,
--           atmIfVptPnniSigPeakConnections,
--           atmIfVptPnniAddrRowStatus,
--           atmIfVptPnniSigVcdAtmServiceCategory,
--           atmIfVptPnniAddrPnniInfoScope,
--           atmIfPnniRccUsageState,
--           atmIfPnniRccVci,
--           atmIfPnniCbrWeight,
--           atmIfPnniSigVci,
--           atmIfVptPnniServiceExchange,
--           atmIfPnniSigNewCurrentConnections,
--           atmIfVptPnniRccVcdQosClass,
--           atmIfVptPnniRccHelloPacketsTx,
--           atmIfPnniRccNegotiatedVersion,
--           atmIfVptPnniSigAdminState,
--           atmIfPnniSigVcdTrafficDescType,
--           atmIfVptPnniRccOperationalState,
--           atmIfPnniRccRemotePortId,
--           atmIfPnniSigLastRxDiagCode,
--           atmIfVptPnniUbrWeight,
--           atmIfVptPnniAddrTermSPRowStatus,
--           atmIfPnniSigAddressConversion,
--           atmIfPnniComponentName,
--           atmIfVptPnniSigRowStatus,
--           atmIfPnniSigVcdTdpValue,
--           atmIfPnniAccountClass,
--           atmIfVptPnniRccHelloState,
--           atmIfPnniSigLastRxCauseCode,
--           atmIfVptPnniRccComponentName,
--           atmIfPnniRccBadHelloPacketsRx,
--           atmIfVptPnniRccHelloInterval }
-- STATUS  mandatory
-- DESCRIPTION
--   "A list of all current accessible leaf objects."

atmPnniGroup OBJECT IDENTIFIER ::= { atmPnniMIB 1 }
atmPnniGroupBE OBJECT IDENTIFIER ::= { atmPnniGroup 5 }
atmPnniGroupBE00 OBJECT IDENTIFIER ::= { atmPnniGroupBE 1 }
atmPnniGroupBE00A OBJECT IDENTIFIER ::= { atmPnniGroupBE00 2 }



-- Agent-Capabilities Statement:

-- PRODUCT-RELEASE "Passport Release 7.0 AtmPnni."
-- STATUS          mandatory
-- DESCRIPTION     "AtmPnni MIB: MIB Version BE00A,
--                  Software Version BG00S4C."
-- SUPPORTS        Nortel-Magellan-Passport-AtmPnniMIB
--    INCLUDES     { atmPnniGroupBE00A }

atmPnniCapabilities OBJECT IDENTIFIER ::= { atmPnniMIB 3 }
atmPnniCapabilitiesBE OBJECT IDENTIFIER ::= { atmPnniCapabilities 5 }
atmPnniCapabilitiesBE00 OBJECT IDENTIFIER ::= { atmPnniCapabilitiesBE 1 }
atmPnniCapabilitiesBE00A OBJECT IDENTIFIER ::= { atmPnniCapabilitiesBE00 2 }





END
