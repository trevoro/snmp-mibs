Wellfleet-BOOTP-MIB DEFINITIONS ::= BEGIN

-- Created by mdl2asn version 3.1
-- Creation date: Wed Aug 30 16:38:38 EDT 1995


    IMPORTS

      IpAddress, Counter
        FROM RFC1155-SMI
      OBJECT-TYPE
        FROM RFC-1212
      DisplayString
        FROM RFC1213-MIB
      wfBootpGroup
        FROM Wellfleet-COMMON-MIB;


    wfBootpClientGroup     OBJECT IDENTIFIER ::= { wfBootpGroup 1 }
    wfBootpServerGroup     OBJECT IDENTIFIER ::= { wfBootpGroup 2 }
    wfBootpRelayAgentGroup OBJECT IDENTIFIER ::= { wfBootpGroup 3 }


    wfBootpRelayIntfTable OBJECT-TYPE
        SYNTAX	SEQUENCE OF WfBootpRelayIntfEntry
        ACCESS	not-accessible
        STATUS	mandatory
        DESCRIPTION
                "This table contains per-interface configuration information 
                for BOOTP relay agent operation"
        ::= { wfBootpRelayAgentGroup 1 }

    wfBootpRelayIntfEntry OBJECT-TYPE
        SYNTAX	WfBootpRelayIntfEntry
        ACCESS	not-accessible
        STATUS	mandatory
        DESCRIPTION
                "a BOOTP relay agent interface description"
        INDEX	{ wfBootpRelayIntfAddress }
        ::= { wfBootpRelayIntfTable 1 }

    WfBootpRelayIntfEntry ::= SEQUENCE {
    	    wfBootpRelayIntfDelete
    		INTEGER,
    	    wfBootpRelayIntfDisable
    		INTEGER,
    	    wfBootpRelayIntfState
    		INTEGER,
    	    wfBootpRelayIntfAddress
    		IpAddress,
    	    wfBootpRelayIntfHops
    		INTEGER,
    	    wfBootpRelayIntfSeconds
    		INTEGER,
    	    wfBootpRelayIntfOpDrops
    		Counter,
    	    wfBootpRelayIntfRequests
    		Counter,
    	    wfBootpRelayIntfTranReqs
    		Counter,
    	    wfBootpRelayIntfHopsDrops
    		Counter,
    	    wfBootpRelayIntfBcastDrops
    		Counter,
    	    wfBootpRelayIntfSecDrops
    		Counter,
    	    wfBootpRelayIntfReplies
    		Counter,
    	    wfBootpRelayIntfGiaddrDrops
    		Counter,
    	    wfBootpRelayIntfResrcDrops
    		Counter,
    	    wfBootpRelayIntfPassThroughMode
    		INTEGER,
    	    wfBootpRelayIntfUdpSktDrops
    		Counter,
    	    wfBootpRelayIntfTooShortDrops
    		Counter,
    	    wfBootpRelayIntfFltrDrops
    		Counter,
            wfBootpRelayIntfPri
                INTEGER,
            wfBootpRelayIntfDhcpSvrDsbl
                INTEGER,
            wfBootpRelayIntfDhcpSvDnDrps
                Counter,
	    wfBootpRelayIntfArpCache
                INTEGER,
            wfBootpRelayIntfBufLimit
                INTEGER,
            wfBootpRelayIntfBufDrops
                Counter
        }

    wfBootpRelayIntfDelete OBJECT-TYPE
        SYNTAX	INTEGER {
    		    created(1),
    		    deleted(2)
    		}
        ACCESS	read-write
        STATUS	mandatory
        DESCRIPTION
                "Create/Delete: if set to delete, the BOOTP relay agent is
                removed from this network interface"
        DEFVAL	{ created }
        ::= { wfBootpRelayIntfEntry 1 }

    wfBootpRelayIntfDisable OBJECT-TYPE
        SYNTAX	INTEGER {
    		    enabled(1),
    		    disabled(2)
    		}
        ACCESS	read-write
        STATUS	mandatory
        DESCRIPTION
                "Enable/Disable: controls whether the BOOTP relay agent is
                enabled or disabled on this network interface"
        DEFVAL	{ enabled }
        ::= { wfBootpRelayIntfEntry 2 }

    wfBootpRelayIntfState OBJECT-TYPE
        SYNTAX	INTEGER {
    		    up(1),
    		    down(2),
    		    init(3),
    		    invalid(4),
    		    notpres(5)
    		}
        ACCESS	read-only
        STATUS	mandatory
        DESCRIPTION
                "the state if the BOOTP relay agent on this interface"
        DEFVAL	{ notpres }
        ::= { wfBootpRelayIntfEntry 3 }

    wfBootpRelayIntfAddress OBJECT-TYPE
        SYNTAX	IpAddress
        ACCESS	read-only
        STATUS	mandatory
        DESCRIPTION
                "network interface address"
        ::= { wfBootpRelayIntfEntry 4 }

    wfBootpRelayIntfHops OBJECT-TYPE
        SYNTAX	INTEGER(1..16)
        ACCESS	read-write
        STATUS	mandatory
        DESCRIPTION
                "maximum hop count. BOOTREQUESTs with a larger hops field 
                will be dropped"
        DEFVAL	{ 4 }
        ::= { wfBootpRelayIntfEntry 5 }

    wfBootpRelayIntfSeconds OBJECT-TYPE
        SYNTAX	INTEGER(0..65535)
        ACCESS	read-write
        STATUS	mandatory
        DESCRIPTION
                "minimum seconds. BOOTREQUESTs with a smaller seconds field will
                be dropped"
        DEFVAL	{ 0 }
        ::= { wfBootpRelayIntfEntry 6 }

    wfBootpRelayIntfOpDrops OBJECT-TYPE
        SYNTAX	Counter
        ACCESS	read-only
        STATUS	mandatory
        DESCRIPTION
                "the total number of BOOTP packets received on this interface
                that were dropped because of an invalid operation field"
        ::= { wfBootpRelayIntfEntry 7 }

    wfBootpRelayIntfRequests OBJECT-TYPE
        SYNTAX	Counter
        ACCESS	read-only
        STATUS	mandatory
        DESCRIPTION
                "the total number of BOOTREQUEST packets received on this
                interface"
        ::= { wfBootpRelayIntfEntry 8 }

    wfBootpRelayIntfTranReqs OBJECT-TYPE
        SYNTAX	Counter
        ACCESS	read-only
        STATUS	mandatory
        DESCRIPTION
                "the total number of forwarded BOOTREQUEST packets received on
                this interface that contained a non-zero value in the gateway
                IP address field. This interface did not act as a relay agent
                for these packets"
        ::= { wfBootpRelayIntfEntry 9 }

    wfBootpRelayIntfHopsDrops OBJECT-TYPE
        SYNTAX	Counter
        ACCESS	read-only
        STATUS	mandatory
        DESCRIPTION
                "the total number of forwarded BOOTREQUEST packets received on
                this interface that were dropped due to a hops field that was
                too large"
        ::= { wfBootpRelayIntfEntry 10 }

    wfBootpRelayIntfBcastDrops OBJECT-TYPE
        SYNTAX	Counter
        ACCESS	read-only
        STATUS	mandatory
        DESCRIPTION
                "the total number of forwarded BOOTREQUEST packets received on
                this interface that were dropped due to a destination IP
                address that was not 255.255.255.255"
        ::= { wfBootpRelayIntfEntry 11 }

    wfBootpRelayIntfSecDrops OBJECT-TYPE
        SYNTAX	Counter
        ACCESS	read-only
        STATUS	mandatory
        DESCRIPTION
                "the total number of forwarded BOOTREQUEST packets received on
                this interface that were dropped due to a seconds field that
                was too small"
        ::= { wfBootpRelayIntfEntry 12 }

    wfBootpRelayIntfReplies OBJECT-TYPE
        SYNTAX	Counter
        ACCESS	read-only
        STATUS	mandatory
        DESCRIPTION
                "the total number of BOOTPREPLY packets received that were
                addressed to this interface"
        ::= { wfBootpRelayIntfEntry 13 }

    wfBootpRelayIntfGiaddrDrops OBJECT-TYPE
        SYNTAX	Counter
        ACCESS	read-only
        STATUS	mandatory
        DESCRIPTION
                "the total number of BOOTPREPLY packets received that were
                addressed to this interface and dropped because the giaddr
                field was not the same as the interface's address"
        ::= { wfBootpRelayIntfEntry 14 }

    wfBootpRelayIntfResrcDrops OBJECT-TYPE
        SYNTAX	Counter
        ACCESS	read-only
        STATUS	mandatory
        DESCRIPTION
                "the total number of BOOTPREPLY packets received that were
                addressed to this interface and dropped because sufficient
                resources were not available"
        ::= { wfBootpRelayIntfEntry 15 }

    wfBootpRelayIntfPassThroughMode OBJECT-TYPE
        SYNTAX	INTEGER {
    		    bootp(1),
    		    bootp-dhcp(2),
    		    dhcp(3)
    		}
        ACCESS	read-write
        STATUS	mandatory
        DESCRIPTION
                "The ACCEPTANCE mode for this interface: Bootp Requests only,
                both Bootp Requests and Bootp Requests containing DHCP
                messages, or Bootp Requests containing DHCP messages only."
        DEFVAL	{ bootp }
        ::= { wfBootpRelayIntfEntry 16 }

    wfBootpRelayIntfUdpSktDrops OBJECT-TYPE
        SYNTAX	Counter
        ACCESS	read-only
        STATUS	mandatory
        DESCRIPTION
                "The total number of BOOTP packets received that were addressed
                to this interface and dropped because the UDP socket field is 
                not BOOTPS (67)."
        ::= { wfBootpRelayIntfEntry 17 }

    wfBootpRelayIntfTooShortDrops OBJECT-TYPE
        SYNTAX	Counter
        ACCESS	read-only
        STATUS	mandatory
        DESCRIPTION
                "The total number of BOOTP packets received that were addressed
                to this interface and dropped because the UDP length field is 
                too short."
        ::= { wfBootpRelayIntfEntry 18 }

    wfBootpRelayIntfFltrDrops OBJECT-TYPE
        SYNTAX	Counter
        ACCESS	read-only
        STATUS	mandatory
        DESCRIPTION
                "The total number of BOOTPREQUEST packets received that were
                addressed to this interface and dropped because this type of 
                packet is filtered off by the Pass Through Mode"
        ::= { wfBootpRelayIntfEntry 19 }

    wfBootpRelayIntfPri OBJECT-TYPE
        SYNTAX  INTEGER(0..16)
        ACCESS  read-write
        STATUS  mandatory
        DESCRIPTION
                "Indicates priority of the interface on a multinetted interface"
        DEFVAL  { 0 }
        ::= { wfBootpRelayIntfEntry 20 }

    wfBootpRelayIntfDhcpSvrDsbl OBJECT-TYPE
        SYNTAX INTEGER {
                   enabled(1),
                   disabled(2)
               }
        ACCESS read-write
        STATUS mandatory
        DESCRIPTION
               "Enable/Disable: controls whether the DHCP Server is
               enabled or disabled on this network interface."
        DEFVAL { disabled }
        ::= { wfBootpRelayIntfEntry 21 }

   wfBootpRelayIntfDhcpSvDnDrps OBJECT-TYPE
        SYNTAX  Counter
        ACCESS  read-only
        STATUS  mandatory
        DESCRIPTION
                  "The total number of BOOTPREQUEST packets received that
                   were addressed to this interface and dropped because this
                   packet was a DHCP packet that should have been handled by 
                   the DHCP Server subsystem, but the subsystem was down."
       ::= { wfBootpRelayIntfEntry 22 }

    wfBootpRelayIntfArpCache OBJECT-TYPE
        SYNTAX	INTEGER {
    		    enabled(1),
    		    disabled(2)
    		}
        ACCESS	read-write
        STATUS	mandatory
        DESCRIPTION
                "Enable/Disable: controls whether the BOOTP relay agent will 
                add/update an ARP entry based on the information contained
                in a BOOTP reply message (not applicable for DHCP)"
        DEFVAL	{ disabled }
        ::= { wfBootpRelayIntfEntry 23 }

    wfBootpRelayIntfBufLimit OBJECT-TYPE
        SYNTAX  INTEGER (4..1000)
        ACCESS  read-write
        STATUS  mandatory
        DESCRIPTION
                "The total unprocessed number of BOOTP/DHCP request/reply
                packets allowed in this interface. See CR147895-1 for detail"
        DEFVAL  { 10 }
        ::= { wfBootpRelayIntfEntry 24 }
 
    wfBootpRelayIntfBufDrops OBJECT-TYPE
        SYNTAX  Counter
        ACCESS  read-only
        STATUS  mandatory
        DESCRIPTION
                "The total number of BOOTP request/reply packets dropped
                due to the wfBootpRelayIntfBufLimit is arrived."
        ::= { wfBootpRelayIntfEntry 25 }

    wfBootpRelayFwdTable OBJECT-TYPE
        SYNTAX	SEQUENCE OF WfBootpRelayFwdEntry
        ACCESS	not-accessible
        STATUS	mandatory
        DESCRIPTION
                "for a BOOTP relay agent on a given interface, this table 
                contains the list of interfaces through which that agent 
                will forward BOOTREQUEST packets"
        ::= { wfBootpRelayAgentGroup 2 }

    wfBootpRelayFwdEntry OBJECT-TYPE
        SYNTAX	WfBootpRelayFwdEntry
        ACCESS	not-accessible
        STATUS	mandatory
        DESCRIPTION
                "a BOOTP forwarding description"
        INDEX	{ wfBootpRelayFwdAgentIntf,
    		  wfBootpRelayFwdOutIntf }
        ::= { wfBootpRelayFwdTable 1 }

    WfBootpRelayFwdEntry ::= SEQUENCE {
    	    wfBootpRelayFwdDelete
    		INTEGER,
    	    wfBootpRelayFwdDisable
    		INTEGER,
    	    wfBootpRelayFwdAgentIntf
    		IpAddress,
    	    wfBootpRelayFwdOutIntf
    		IpAddress,
    	    wfBootpRelayFwdPassThroughMode
    		INTEGER,
    	    wfBootpRelayFwdOutReqPkts
    		Counter
        }

    wfBootpRelayFwdDelete OBJECT-TYPE
        SYNTAX	INTEGER {
    		    created(1),
    		    deleted(2)
    		}
        ACCESS	read-write
        STATUS	mandatory
        DESCRIPTION
                "Create/Delete: if set to delete, the forwarding entry is
                removed from the table"
        DEFVAL	{ created }
        ::= { wfBootpRelayFwdEntry 1 }

    wfBootpRelayFwdDisable OBJECT-TYPE
        SYNTAX	INTEGER {
    		    enabled(1),
    		    disabled(2)
    		}
        ACCESS	read-write
        STATUS	mandatory
        DESCRIPTION
                "Enable/Disable: controls whether the the forwarding entry is
                active or not"
        DEFVAL	{ enabled }
        ::= { wfBootpRelayFwdEntry 2 }

    wfBootpRelayFwdAgentIntf OBJECT-TYPE
        SYNTAX	IpAddress
        ACCESS	read-only
        STATUS	mandatory
        DESCRIPTION
                "relay agent's network interface address"
        ::= { wfBootpRelayFwdEntry 3 }

    wfBootpRelayFwdOutIntf OBJECT-TYPE
        SYNTAX	IpAddress
        ACCESS	read-only
        STATUS	mandatory
        DESCRIPTION
                "outbound network interface address"
        ::= { wfBootpRelayFwdEntry 4 }

    wfBootpRelayFwdPassThroughMode OBJECT-TYPE
        SYNTAX	INTEGER {
    		    bootp(1),
    		    bootp-dhcp(2),
    		    dhcp(3)
    		}
        ACCESS	read-write
        STATUS	mandatory
        DESCRIPTION
                "The PROPAGATION mode for this interface: Bootp Requests only,
                both Bootp Requests and Bootp Requests containing DHCP
                messages, or Bootp Requests containing DHCP messages only."
        DEFVAL	{ bootp }
        ::= { wfBootpRelayFwdEntry 5 }

    wfBootpRelayFwdOutReqPkts OBJECT-TYPE
        SYNTAX	Counter
        ACCESS	read-only
        STATUS	mandatory
        DESCRIPTION
                "The total number of BOOTPREQUEST packets relayed out of this
                forwarding entry."
        ::= { wfBootpRelayFwdEntry 6 }

    wfBootpClientIntfTable OBJECT-TYPE
        SYNTAX	SEQUENCE OF WfBootpClientIntfEntry
        ACCESS	not-accessible
        STATUS	mandatory
        DESCRIPTION
                "for a BOOTP relay agent on a given interface, this table
                contains the list of DLCI-IP address assignments."
        ::= { wfBootpClientGroup 1 }

    wfBootpClientIntfEntry OBJECT-TYPE
        SYNTAX	WfBootpClientIntfEntry
        ACCESS	not-accessible
        STATUS	mandatory
        DESCRIPTION
                "a BOOTP client interface description"
        INDEX	{ wfBootpClientIntfAddress,
    		  wfBootpClientIntfDlci }
        ::= { wfBootpClientIntfTable 1 }

    WfBootpClientIntfEntry ::= SEQUENCE {
    	    wfBootpClientIntfDelete
    		INTEGER,
    	    wfBootpClientIntfDlci
    		INTEGER,
    	    wfBootpClientIntfAddress
    		IpAddress
        }

    wfBootpClientIntfDelete OBJECT-TYPE
        SYNTAX	INTEGER {
    		    created(1),
    		    deleted(2)
    		}
        ACCESS	read-write
        STATUS	mandatory
        DESCRIPTION
                "Flag to indicate BOOTP client interface instance deletion"
        DEFVAL	{ created }
        ::= { wfBootpClientIntfEntry 1 }

    wfBootpClientIntfDlci OBJECT-TYPE
        SYNTAX	INTEGER
        ACCESS	read-only
        STATUS	mandatory
        DESCRIPTION
                "The DLCI for the virtual circuit used by this BOOTP client"
        ::= { wfBootpClientIntfEntry 2 }

    wfBootpClientIntfAddress OBJECT-TYPE
        SYNTAX	IpAddress
        ACCESS	read-only
        STATUS	mandatory
        DESCRIPTION
                "The IP address for the interface used by this BOOTP client"
        ::= { wfBootpClientIntfEntry 3 }

    wfBootpRelayPrefServTable OBJECT-TYPE
        SYNTAX	SEQUENCE OF WfBootpRelayPrefServEntry
        ACCESS	not-accessible
        STATUS	mandatory
        DESCRIPTION
                "This table contains Preferred Server configuration 
                information for configured Bootp Relay Agents."
        ::= { wfBootpRelayAgentGroup 3 }

    wfBootpRelayPrefServEntry OBJECT-TYPE
        SYNTAX	WfBootpRelayPrefServEntry
        ACCESS	not-accessible
        STATUS	mandatory
        DESCRIPTION
                "a BOOTP relay Preferred Server description"
        INDEX	{ wfBootpRelayPrefServAgentAddress,
    		  wfBootpRelayPrefServTargetAddress }
        ::= { wfBootpRelayPrefServTable 1 }

    WfBootpRelayPrefServEntry ::= SEQUENCE {
    	    wfBootpRelayPrefServDelete
    		INTEGER,
    	    wfBootpRelayPrefServDisable
    		INTEGER,
    	    wfBootpRelayPrefServAgentAddress
    		IpAddress,
    	    wfBootpRelayPrefServTargetAddress
    		IpAddress,
    	    wfBootpRelayPrefServTargetName
    		DisplayString,
    	    wfBootpRelayPrefServRequestMode
    		INTEGER,
    	    wfBootpRelayPrefServOutReqPkts
    		Counter
        }

    wfBootpRelayPrefServDelete OBJECT-TYPE
        SYNTAX	INTEGER {
    		    created(1),
    		    deleted(2)
    		}
        ACCESS	read-write
        STATUS	mandatory
        DESCRIPTION
                "Create/Delete: if set to delete, the static entry is
                removed from the table"
        DEFVAL	{ created }
        ::= { wfBootpRelayPrefServEntry 1 }

    wfBootpRelayPrefServDisable OBJECT-TYPE
        SYNTAX	INTEGER {
    		    enabled(1),
    		    disabled(2)
    		}
        ACCESS	read-write
        STATUS	mandatory
        DESCRIPTION
                "Enable/Disable: controls whether the static entry is included
                in the list of preferred servers for this interface or not."
        DEFVAL	{ enabled }
        ::= { wfBootpRelayPrefServEntry 2 }

    wfBootpRelayPrefServAgentAddress OBJECT-TYPE
        SYNTAX	IpAddress
        ACCESS	read-only
        STATUS	mandatory
        DESCRIPTION
                "relay agent's IP address"
        ::= { wfBootpRelayPrefServEntry 3 }

    wfBootpRelayPrefServTargetAddress OBJECT-TYPE
        SYNTAX	IpAddress
        ACCESS	read-only
        STATUS	mandatory
        DESCRIPTION
                "Target Server(s) address, either unicast or multicast"
        ::= { wfBootpRelayPrefServEntry 4 }

    wfBootpRelayPrefServTargetName OBJECT-TYPE
        SYNTAX	DisplayString
        ACCESS	read-write
        STATUS	mandatory
        DESCRIPTION
                "Target Server(s) host name"
        ::= { wfBootpRelayPrefServEntry 5 }

    wfBootpRelayPrefServRequestMode OBJECT-TYPE
        SYNTAX	INTEGER {
    		    bootp(1),
    		    bootp-dhcp(2),
    		    dhcp(3)
    		}
        ACCESS	read-write
        STATUS	mandatory
        DESCRIPTION
                "The PROPAGATION mode for this preferred server: Bootp 
                Requests only, both Bootp Requests and Bootp Requests 
                containing DHCP messages, or Bootp Requests containing 
                DHCP messages only."
        DEFVAL	{ bootp }
        ::= { wfBootpRelayPrefServEntry 6 }

    wfBootpRelayPrefServOutReqPkts OBJECT-TYPE
        SYNTAX	Counter
        ACCESS	read-only
        STATUS	mandatory
        DESCRIPTION
                "The total number of BOOTPREQUEST packets relayed to this
                preferred server."
        ::= { wfBootpRelayPrefServEntry 7 }

    END  -- Wellfleet-BOOTP-MIB
