ACC-ASPORT DEFINITIONS ::= BEGIN

    IMPORTS
	 OBJECT-TYPE FROM RFC1155-SMI
	 TRAP-TYPE FROM RFC-1215
    	 accTrapLogSeqNum FROM ACC-SYSTEM
	accBRG, DisplayString, RowStatus, IfIndex, SmdsAddress
             FROM ACC-MIB;
-- Async Port (Console) Group
      accAsPort         OBJECT IDENTIFIER ::= { accBRG 10 }
        accConsole      OBJECT IDENTIFIER ::= { accAsPort 2 }
          accConsoleParms  OBJECT IDENTIFIER ::= { accConsole 1 }
	  accConsoleSpeed	OBJECT-TYPE   
			SYNTAX	INTEGER
			ACCESS	read-write
			STATUS	mandatory
			DESCRIPTION
                          " Baud rate for this port;
                            {1200, 2400, 4800, 7200, 9600 } are permitted."
			::= { accConsoleParms 5 }
          accNaTraps       OBJECT IDENTIFIER ::= { accConsoleParms 6 }
	  accNaTrapMsg	OBJECT-TYPE
                        SYNTAX  DisplayString
                        ACCESS  read-write
                        STATUS  mandatory
                        DESCRIPTION
                          " TrapMessage for Na Traps; "
                        ::= { accNaTraps 1 }

       accSwLevlTrap 	TRAP-TYPE
        ENTERPRISE        accNaTraps 
        VARIABLES       { accNaTrapMsg ,
                           accTrapLogSeqNum}
        DESCRIPTION
		" software has changed to requested level. 
		  it requires a reset for the changes to take place
SEVERITY-DEFAULT: Warning 
EVENTTYPE-DEFAULT: 10 
ADDITIONAL-TEXT-VARIABLES: { accTrapLogSeqNum,accNaTrapMsg }
PCAUSE-DEFAULT: 7 " 
 
        ::= 1
       accNaInvKeyTrap   TRAP-TYPE
        ENTERPRISE        accNaTraps 
        VARIABLES       { accNaTrapMsg ,
                           accTrapLogSeqNum}
        DESCRIPTION
		"Software reg key entered by use is not valid. 
SEVERITY-DEFAULT: Warning 
EVENTTYPE-DEFAULT: 10 
ADDITIONAL-TEXT-VARIABLES: { accTrapLogSeqNum,accNaTrapMsg }
PCAUSE-DEFAULT: 7 " 
 
        ::= 2
       accNaLogBufTrap   TRAP-TYPE
        ENTERPRISE        accNaTraps 
        VARIABLES       { accNaTrapMsg ,
                           accTrapLogSeqNum}
        DESCRIPTION
                "trap log buffer change requires a reset. 
SEVERITY-DEFAULT: Warning 
EVENTTYPE-DEFAULT: 10 
ADDITIONAL-TEXT-VARIABLES: { accTrapLogSeqNum,accNaTrapMsg }
PCAUSE-DEFAULT: 7 " 
 
        ::= 3
END
