VERILINK-ENTERPRISE-NCMDSU-MIB

        -- set up MIB-wide defaults
        -- all functions can use %n for object name and
        -- %t for object type, %p for parent name,
        -- %d for name of default-bearing node and %% for %

          DEFINITIONS ::= BEGIN

     IMPORTS
             Gauge
                     FROM RFC1155-SMI
              DisplayString
                     FROM RFC1213-MIB
             OBJECT-TYPE
                     FROM RFC-1212
	     ncm-dsu,ncm-dds,ncm-dbu
		     FROM 
             VERILINK-ENTERPRISE-NCMALARM-MIB;

             
                     
	  

 
     --  This MIB module uses the extended OBJECT-TYPE macro as
     --  defined in RFC 1212.
     --  This MIB module uses the TRAP-TYPE macro as
     --  defined in RFC 1215.


  


	-- ncm Dsu Common Table Common to DSU, DDS And DBU Cards           

	ncmdsuCommonTable OBJECT-TYPE
	  SYNTAX SEQUENCE OF NcmdsuCommonEntry
	  ACCESS not-accessible
	  STATUS mandatory
	  DESCRIPTION
	  "The ncmdsu information table."

	 --DEFAULT test-function dsucommon-test
          --DEFAULT next-function dsucommon-next


	  ::= { ncm-dsu 2000 }



     ncmdsuCommonEntry OBJECT-TYPE
	  SYNTAX NcmdsuCommonEntry
	  ACCESS not-accessible
	  STATUS mandatory
	  DESCRIPTION
	       "An entry in the ncmdsu information table."
	  INDEX   { ncmdsuNIDIndex, ncmdsuIndex }
	  ::= { ncmdsuCommonTable 1 }




     NcmdsuCommonEntry ::= SEQUENCE {

	     ncmdsuNIDIndex
		INTEGER,
	     ncmdsuIndex
		 INTEGER,
	     ncmdsuPortType
		 INTEGER,
	     ncmdsuPortLoopback
		 INTEGER,
	     ncmdsuPortTest
		 INTEGER
	     	 }





	  ncmdsuNIDIndex OBJECT-TYPE
	  SYNTAX  INTEGER 
	  ACCESS  read-only
	  STATUS  mandatory
	  ::= { ncmdsuCommonEntry 1 }



	ncmdsuIndex OBJECT-TYPE
	  SYNTAX  INTEGER 
	  ACCESS  read-only
	  STATUS  mandatory
	  --DEFAULT get-function    get-LineIndex

	  ::= { ncmdsuCommonEntry 2 }


     	ncmdsuPortType OBJECT-TYPE
	  SYNTAX INTEGER {

		       none(1),
		       v35(2),
		       rs-449(3),
		       eia530(4),
		       rS-232(5),
		       wrong-DIM(6),
		       unknown(7)

	       }
	  ACCESS read-only
	  STATUS mandatory
	  ::= { ncmdsuCommonEntry 3 }



       ncmdsuPortLoopback OBJECT-TYPE
	  SYNTAX INTEGER {

		       none(1),          -- no loopback
		       inband-loop(2),
		       local-loop(3),
                       sending-loop-up(4),
                       sending-loop-down(5),
                       verilink-loop-up(6),
                       verilink-loop-down(7),
                       local-loop-up(8),
                       local-loop-down(9),
                       v54-loop-up(10),
                       v54-loop-down(11),
                       dds-latching-loop-up(12),
                       dds-latching-loop-down(13),
                       dds-nonlatching-loop-up(14),
                       dds-nonlatching-loop-down(15),
                       ft1-loop-up(16),
                       ft1-loop-down(17)


	       }
	ACCESS read-write
	STATUS mandatory
	  ::= { ncmdsuCommonEntry 4 }



	ncmdsuPortTest OBJECT-TYPE
	  SYNTAX INTEGER {

		       no-test(1),
		       start-test(2),
		       run-ber-test(3),
		       stop-ber-test(4),	
		       test-511(5),
                       test-2047(6)
	

	       }
	  ACCESS read-write
	  STATUS mandatory
	  ::= { ncmdsuCommonEntry 5 }






	-- the ncm dsu Configuration Table

        ncmdsuConfigTable OBJECT-TYPE
        SYNTAX  SEQUENCE OF  NcmdsuConfigEntry
        ACCESS  not-accessible
        STATUS  mandatory
	DESCRIPTION
        "The ncmdsu Configuration table."

	--DEFAULT test-function dsu-test
        --DEFAULT next-function dsu-next
	



         ::= { ncm-dsu 2001 }

        ncmdsuConfigEntry OBJECT-TYPE
        SYNTAX  NcmdsuConfigEntry
        ACCESS  not-accessible
        STATUS  mandatory
        DESCRIPTION
        "An entry in the ncmdsu Configuration table."
         -- INDEX   { ncmdsuLineIndex }
         INDEX   { ncmdsuNIDConfigIndex, ncmdsuLineIndex }
         ::= { ncmdsuConfigTable 1 }


        NcmdsuConfigEntry ::=
         SEQUENCE {
             ncmdsuNIDConfigIndex
                INTEGER,
             ncmdsuLineIndex
                 INTEGER,
             ncmdsubus
                 INTEGER,
             ncmdsuPortChannel
                 DisplayString,
             ncmdsuPortConfiguration
                 INTEGER,
             ncmcsushelf
                INTEGER,
             ncmcsuslot
                INTEGER,
             ncmdsuAlarmEnable
                INTEGER,
             ncmdsuLosLead
                INTEGER,
	     ncmdsuTimingSource
		INTEGER,
	     ncmdsuDTESpeed
		INTEGER
             }



	ncmdsuNIDConfigIndex OBJECT-TYPE
             SYNTAX  INTEGER (1..'7fffffff'h)
             ACCESS  read-only
             STATUS  mandatory
             DESCRIPTION
                "This variable indicates the node id
                 value of the node."
               ::= { ncmdsuConfigEntry 1 }
 
        ncmdsuLineIndex OBJECT-TYPE
        SYNTAX  INTEGER
        ACCESS  read-only
        STATUS  mandatory
	 --DEFAULT get-function    get-LineIndex

        ::= { ncmdsuConfigEntry 2 }
 
        ncmdsubus OBJECT-TYPE
        SYNTAX INTEGER {
 
                       disabled(1),
                       busA(2),
                       busB(3),
                       busC(4)
 
               } 
          ACCESS read-write
          STATUS mandatory
          DESCRIPTION
          "The ncmdsu bus type for Port."
        ::= { ncmdsuConfigEntry 3 }
 
 
        ncmdsuPortChannel OBJECT-TYPE
        SYNTAX DisplayString (SIZE (0..255))
        ACCESS  read-write
        STATUS  mandatory
        DESCRIPTION
 
        "This variable indicates the channel assignment for the
        ncmdsu for the port."
        ::= { ncmdsuConfigEntry 4 }


	ncmdsuPortConfiguration OBJECT-TYPE
        SYNTAX INTEGER
        ACCESS  read-write
        STATUS mandatory
        DESCRIPTION
 
        "This variable indicates the configuration bits
        for port. The configuration can be set by setting the relevant
        bit to 1 and reset by setting the relevant bit to zero.
 
        Bit     Value   Name    Description
                0               set the ncmdsu port configuration to zero
        0       1       64k     set uses 8bits of data/64kbps.
        1       2       LEN     set enable loop code and loop commands
        2       4       INV     set invert the channelized data
        3       8       SCR     set to scramble channelized data.
        4       16      CLK1    DTE transmit clock select bits
        5       32      CLK2    DTE transmit clock select bits
        6       64      TU      set port as a timing unit
        7       128     ALM     set if DIU has to report alarms to SAM."
        
       ::= { ncmdsuConfigEntry 5 }
 
 
        ncmcsushelf OBJECT-TYPE
        SYNTAX INTEGER
        ACCESS  read-write
        STATUS mandatory
        DESCRIPTION
 
        "This variable indicates the csu shelf associated with
        the ncmdsu port."
        
        ::= { ncmdsuConfigEntry 6 }
 
 
        ncmcsuslot OBJECT-TYPE
        SYNTAX INTEGER
        ACCESS  read-write
        STATUS mandatory
        DESCRIPTION
 
        "This variable indicates the csu slot associated with
        the ncmdsu port."
        
        ::= { ncmdsuConfigEntry 7 }
 
 
        ncmdsuAlarmEnable OBJECT-TYPE
        SYNTAX INTEGER{
                nO(1),
                yES(2)
                      }
        ACCESS  read-write
        STATUS mandatory
        DESCRIPTION
 
        "This variable indicates whether the alarm is enabled or disabled for ncmdsu."
        
        ::= { ncmdsuConfigEntry 8 }



	ncmdsuLosLead OBJECT-TYPE
        SYNTAX INTEGER
        ACCESS  read-write
        STATUS mandatory
        DESCRIPTION

	"This variable indicates the DTE lead bits
        for port. The DTE leads can be set by setting the relevant
        bit to 1 and reset by setting the relevant bit to zero.

        Bit     Value   Name    Description
                0               set the ncmdsu port configuration to zero
        0       1       DTR     set uses DTR
        1       2       RTS     set uses RTS
        2       4       DSR     set uses DSR
        3       8       CTS     set uses CTS
        4       16      DCD     set uses DCD
        5       32      LOS     use both bits: bits set to use for alarm
        6       64      LOS     0 = Disable LOS detect, 1=use RTS , 2 = DTR
        7       128     DDSMode set for 56k DDS ."

        ::= { ncmdsuConfigEntry 9 }


        ncmdsuTimingSource OBJECT-TYPE
        SYNTAX INTEGER{
		none(1),
               	port1(2),
		port2(3),
		cSU(4) 
                      }
        ACCESS  read-write
        STATUS mandatory
        DESCRIPTION
 
        "This variable indicates the T1 timing source for ncmdsu."
         
        ::= { ncmdsuConfigEntry 10 }
 

	ncmdsuDTESpeed OBJECT-TYPE
        SYNTAX INTEGER{
		none(1),
		mode-64k(2),
		mode-56k(3),
		mode-38-4(4),
		mode-19-2(5),
		mode-9-6(6),
		mode-4-8(7),
		mode-2-4(8)
			
               }
        ACCESS  read-write
        STATUS mandatory
        DESCRIPTION
 
        "This variable indicates DTE Speed control and speeds 38.4k or below holds good for the DIU2131 card type."
         
        ::= { ncmdsuConfigEntry 11 }




	 -- ncmdsutable



        ncmdsustatTable OBJECT-TYPE
        SYNTAX SEQUENCE OF NcmdsustatEntry
        ACCESS not-accessible
        STATUS mandatory
	DESCRIPTION
               "The ncm dsu  stat  table."


	--DEFAULT test-function dsucommon-test
        --DEFAULT next-function dsucommon-next
	

        ::= { ncm-dsu 2003 }


        ncmdsustatEntry OBJECT-TYPE
        SYNTAX NcmdsustatEntry
        ACCESS not-accessible
        STATUS mandatory
        DESCRIPTION
               "An entry in the ncm dsu stat table."
        INDEX   { ncmdsuNIDstatIndex, ncmdsustatIndex }
        ::= { ncmdsustatTable 1 }


        NcmdsustatEntry ::= SEQUENCE {

	     ncmdsuNIDstatIndex
		 INTEGER,
             ncmdsustatIndex
                 INTEGER,
             ncmdsuPortLowbattery
                 INTEGER,
             ncmdsuPortLOSstatus
                 INTEGER,
             ncmdsuPortblockerrorcounter
                 Gauge,
             ncmdsuPortTestSeconds
                 Gauge,
             ncmdsuPortrateper8000
                 INTEGER,
             ncmdsuPortLeadStatus1
                 INTEGER,
             ncmdsuPortLeadStatus2
                 INTEGER,
             ncmdbuPrimaryLineStatus
                INTEGER,
             ncmdbuLineStatus
                INTEGER,
             ncmdbuSwitchBy
                INTEGER,
             ncmdbuReceivedCode
                INTEGER,
             ncmdsuPortTestResults
                INTEGER,
             ncmdsuPortDiagStatus
                INTEGER
		}



	ncmdsuNIDstatIndex OBJECT-TYPE
        SYNTAX  INTEGER
        ACCESS  read-only
        STATUS  mandatory
	DESCRIPTION
		"This object specifies the node id of the node."
         ::= { ncmdsustatEntry 1 }


	ncmdsustatIndex OBJECT-TYPE
        SYNTAX  INTEGER
        ACCESS  read-only
        STATUS  mandatory
 
         ::= { ncmdsustatEntry 2 }
 
 
        ncmdsuPortLowbattery OBJECT-TYPE
        SYNTAX INTEGER {
                        not-low-battery(1),
                        low-battery(2)
                
               }
        ACCESS read-only
        STATUS mandatory
        DESCRIPTION
               "The ncmdsu Lowbattery status for Port."
        ::= { ncmdsustatEntry 3 }
 

	ncmdsuPortLOSstatus OBJECT-TYPE
        SYNTAX INTEGER {
 
                       not-Los-status(1),
                       los-status(2)
                
               }
        ACCESS read-only
        STATUS mandatory
        DESCRIPTION
               "The ncmdsu LOS status for Port."
        ::= { ncmdsustatEntry 4 }
 
         
 
        ncmdsuPortblockerrorcounter OBJECT-TYPE
        SYNTAX Gauge
        ACCESS read-only
        STATUS mandatory
        DESCRIPTION
 
        "The number of block errors produced on port."
 
        ::= {ncmdsustatEntry 5 }
 
 
        ncmdsuPortTestSeconds OBJECT-TYPE
        SYNTAX Gauge
        ACCESS read-only
        STATUS mandatory
        DESCRIPTION
 
        "The number of errors produced by a test on port."
 
        ::= {ncmdsustatEntry 6 }
        
        ncmdsuPortrateper8000 OBJECT-TYPE
        SYNTAX INTEGER
        ACCESS read-only
        STATUS mandatory
        DESCRIPTION
 
        "The rate/8000 on port."
 
        ::= {ncmdsustatEntry 7 }


	ncmdsuPortLeadStatus1 OBJECT-TYPE
        SYNTAX  INTEGER
        ACCESS  read-only
        STATUS  mandatory
        DESCRIPTION
 
        "This variable indicates the Lead Status (part 1)
         of the port.
 
        The various bit positions are:
        Bit     Value   Name
        0       1       DTR (1 = on; 0 = off)
        1       2       RTS
        2       4       DSR
        3       8       CTS
        4       16      DCD
        5       32      TXD
        6       64      RXD
        7       128     Lead status available bit."
         
          ::= { ncmdsustatEntry 8 }
 
        ncmdsuPortLeadStatus2 OBJECT-TYPE
        SYNTAX  INTEGER
        ACCESS  read-only
        STATUS  mandatory
        DESCRIPTION
 
        "This variable indicates the Lead Status (part 2)
         of the port.The lead status2 is bit mapped.

	The various bit positions are:
        BIT     Value   Name
        0       0       no-loop
        0       1       local-loop
        1       2       remote-loop
        2       4       test-mode."
 
 
         ::= { ncmdsustatEntry 9 }
         
	ncmdbuPrimaryLineStatus OBJECT-TYPE
         SYNTAX  INTEGER
                 {
                oK(1),
                aSC(2),
                lOF(3),
                cD(4),
                uSER(5),
                yEL(6),
                bER(7),
                aLLONE(8),
                lOS(9)
 
                 
                        }
                
        ACCESS  read-only
        STATUS  mandatory
        DESCRIPTION
 
        "This variable indicates the Primary Line Status of the ncmdbu. "
        
        
         ::= { ncmdsustatEntry 10 }
 
 
         ncmdbuLineStatus OBJECT-TYPE
         SYNTAX  INTEGER
                 {
                sTANDBY(1),
                aCTIVE(2),
                eRROR(3)
                
                        }
                
        ACCESS  read-only
        STATUS  mandatory
        DESCRIPTION
 
        "This variable indicates the ncmdbu Line Status of the ncmdbu. "
        
        
         ::= { ncmdsustatEntry 11 }
 
 
 
 
        ncmdbuSwitchBy OBJECT-TYPE
         SYNTAX  INTEGER
                 {
                nONE(1),
                aSC(2),
                lOF(3),
                cD(4),
                uSER(5),
                yEL(6),
                bER(7),
                aLLONE(8),
                lOS(9)
 
                 
                        }
	ACCESS  read-only
        STATUS  mandatory
        DESCRIPTION
 
        "This variable indicates the cause of the ncmdbu switching. "
        
        
         ::= { ncmdsustatEntry 12 }
 
 
        ncmdbuReceivedCode OBJECT-TYPE
        SYNTAX  INTEGER
        ACCESS  read-only
        STATUS  mandatory
        DESCRIPTION
 
        "This variable indicates the ncmdbu  received code in hex. "
        
        
         ::= { ncmdsustatEntry 13 }
 
 
 
        ncmdsuPortTestResults OBJECT-TYPE
          SYNTAX INTEGER
          ACCESS read-only
          STATUS mandatory
          DESCRIPTION
               "The number of errors produced by a test on port ."
          ::= { ncmdsustatEntry 14  }
 
 
        ncmdsuPortDiagStatus OBJECT-TYPE
        SYNTAX  INTEGER
        ACCESS  read-only
        STATUS  mandatory
        DESCRIPTION
 
        "This variable indicates the Diagnostic Status
         of the port.
 
        The various bit positions are:
        Bit     Value   Name
        0       1       Reserved
        1       2       Reserved
        2       4       Reserved
        3       8       Sending Test Code
        4       16      Sending loopdown code
        5       32      Sending loopup code
        6       64      far end looped
        7       128     Near end looped."
         
          ::= { ncmdsustatEntry 15 }



	 -- the ncm dds Main Configuration Table

	ncmddsMainConfigTable OBJECT-TYPE
        SYNTAX  SEQUENCE OF  NcmddsMainConfigEntry
        ACCESS  not-accessible
        STATUS  mandatory
	DESCRIPTION
        "The ncmdds Main Configuration table."


	--DEFAULT test-function dds-test
        --DEFAULT next-function dds-next
	 


         ::= { ncm-dds 5000 }


	ncmddsMainConfigEntry OBJECT-TYPE
        SYNTAX  NcmddsMainConfigEntry
        ACCESS  not-accessible
        STATUS  mandatory
        DESCRIPTION
        "An entry in the ncmdds Main Configuration table."
         INDEX   { ncmddsNIDMainConfigIndex, ncmddsMainLineIndex }
         ::= { ncmddsMainConfigTable 1 }


        NcmddsMainConfigEntry ::=
         SEQUENCE {
             ncmddsNIDMainConfigIndex
                INTEGER,
             ncmddsMainLineIndex
                 INTEGER,
             ncmddsdsubus
                 INTEGER,
             ncmddsPortChannel
                 DisplayString,
             ncmddsPortConfiguration
                 INTEGER,
             ncmddscsushelf
                INTEGER,
             ncmddscsuslot
                INTEGER,
             ncmddsLosLead
                INTEGER
             }


	 ncmddsNIDMainConfigIndex OBJECT-TYPE
             SYNTAX  INTEGER (1..'7fffffff'h)
             ACCESS  read-only
             STATUS  mandatory
             DESCRIPTION
                "This variable indicates the node id
                 value of the node."
               ::= { ncmddsMainConfigEntry 1 }

 
        ncmddsMainLineIndex OBJECT-TYPE
        SYNTAX  INTEGER
        ACCESS  read-only
        STATUS  mandatory

        ::= { ncmddsMainConfigEntry 2 }
 
        ncmddsdsubus OBJECT-TYPE
        SYNTAX INTEGER {
 
                       disabled(1),
                       busA(2),
                       busB(3),
                       busC(4)
 
               } 
          ACCESS read-write
          STATUS mandatory
          DESCRIPTION
          "The ncmdsu bus type for Port."
        ::= { ncmddsMainConfigEntry 3 }
 
 
        ncmddsPortChannel OBJECT-TYPE
        SYNTAX DisplayString (SIZE (0..255))
        ACCESS  read-write
        STATUS  mandatory
        DESCRIPTION
 
        "This variable indicates the channel assignment for the
        ncmdsu for the port."
        ::= { ncmddsMainConfigEntry 4 }



	ncmddsPortConfiguration OBJECT-TYPE
        SYNTAX INTEGER
        ACCESS  read-write
        STATUS mandatory
        DESCRIPTION
 
        "This variable indicates the configuration bits
        for port. The configuration can be set by setting the relevant
        bit to 1 and reset by setting the relevant bit to zero.
 
        Bit     Value   Name    Description
                0               set the ncmdsu port configuration to zero
        0       1       64k     set uses 8bits of data/64kbps.
        1       2       LEN     set enable loop code and loop commands
        2       4       INV     set invert the channelized data
        3       8       SCR     set to scramble channelized data.
        4       16      CLK1    DTE transmit clock select bits
        5       32      CLK2    DTE transmit clock select bits
        6       64      TU      set port as a timing unit
        7       128     ALM     set if DIU has to report alarms to SAM."
         
       ::= { ncmddsMainConfigEntry 5 }
 
 
        ncmddscsushelf OBJECT-TYPE
        SYNTAX INTEGER
        ACCESS  read-write
        STATUS mandatory
        DESCRIPTION
 
        "This variable indicates the csu shelf associated with
        the ncmdsu port."
         
        ::= { ncmddsMainConfigEntry 6 }
 
 
        ncmddscsuslot OBJECT-TYPE
        SYNTAX INTEGER
        ACCESS  read-write
        STATUS mandatory
        DESCRIPTION
 
        "This variable indicates the csu slot associated with
        the ncmdsu port."
         
        ::= { ncmddsMainConfigEntry 7 }
 


 
        ncmddsLosLead OBJECT-TYPE
        SYNTAX INTEGER
        ACCESS  read-write
        STATUS mandatory
        DESCRIPTION
 
        "This variable indicates the DTE lead bits
        for port. The DTE leads can be set by setting the relevant
        bit to 1 and reset by setting the relevant bit to zero.
 
        Bit     Value   Name    Description
                0               set the ncmdsu port configuration to zero
        0       1       DTR     set uses DTR
        1       2       RTS     set uses RTS
        2       4       DSR     set uses DSR
        3       8       CTS     set uses CTS
        4       16      DCD     set uses DCD
        5       32      LOS     use both bits: bits set to use for alarm
        6       64      LOS     0 = Disable LOS detect, 1=use RTS , 2 = DTR
        7       128     DDSMode set for 56k DDS ."
 
        ::= { ncmddsMainConfigEntry 8 }



		

--	ncm dds Config Table

         ncmddsConfigTable OBJECT-TYPE
             SYNTAX  SEQUENCE OF NcmddsConfigEntry
             ACCESS  not-accessible
             STATUS  mandatory
	     DESCRIPTION
                "The ncmdds Configuration table."

		

	     --DEFAULT test-function dds-test
              --DEFAULT next-function dds-next
				



 
             ::= { ncm-dds 5001  }


         ncmddsConfigEntry OBJECT-TYPE
             SYNTAX  NcmddsConfigEntry
             ACCESS  not-accessible
             STATUS  mandatory
             DESCRIPTION
                "An entry in the ncmdds Configuration table."
            INDEX   {  ncmddsNIDConfigIndex, ncmddsConfigLineIndex }
            ::= { ncmddsConfigTable 1 }


         NcmddsConfigEntry ::=
             SEQUENCE {

             ncmddsNIDConfigIndex
		INTEGER,	
             ncmddsConfigLineIndex
                 INTEGER,
             ncmddsPortLoopEnable
                 INTEGER,
             ncmddsPortReceiveLoopCode
                 INTEGER,
             ncmddsPortRemoteLoopCode
                 INTEGER,
             ncmddsPortAlarmEnable
                 INTEGER,
             ncmddsPortAlarmClearDelayTime
                 INTEGER,
             ncmddsPortAbnormalStationCodeThreshold
                 INTEGER,
             ncmddsPortControlModeIdleThreshold
                 INTEGER,
             ncmddsPortMuxOutofSyncThreshold
                 INTEGER,
             ncmddsPortUnAssignedMuxChannelThreshold
                INTEGER,
             ncmddsPortGroup1Codes
                 INTEGER,
             ncmddsPort56KStatus
                INTEGER,
             ncmddsPortReceived56KCode
                INTEGER,
             ncmddsmode
                INTEGER,
             ncmddsLatchingLoopbackType
                INTEGER,
             ncmddsLatchingLoopbackDevNo
                INTEGER
         }

	 ncmddsNIDConfigIndex OBJECT-TYPE
          SYNTAX  INTEGER
          ACCESS  read-only
          STATUS  mandatory
	  DESCRIPTION
	 "This variable specifies the node id."
 
          ::= { ncmddsConfigEntry 1 }
	


	 ncmddsConfigLineIndex OBJECT-TYPE
          SYNTAX  INTEGER
          ACCESS  read-only
          STATUS  mandatory
	  DESCRIPTION
	  "This variable specifies the Line index."
          ::= { ncmddsConfigEntry 2 }
 
 
         
        ncmddsPortLoopEnable OBJECT-TYPE
        SYNTAX  INTEGER {
                disable(1),
                enable(2)
	} 
        ACCESS  read-write
        STATUS  mandatory
        DESCRIPTION
	"This variable indicates the loop enable bits
        for port. The loop enable can be set by setting the relevant
        bit to 1 and reset by setting the relevant bit to zero.
 
        Bit     Value      Description
                0          no-loop
        0       1          enable ncmdds loop
        1       2          enable v54 loop
        2       4          enable ft1 loop
        3       8          enable verilink loop
        4       16      
        5       32        
        6       64      
        7       128    	  ."
         
        ::= { ncmddsConfigEntry 3 }
 
 
        ncmddsPortReceiveLoopCode OBJECT-TYPE
        SYNTAX  INTEGER {
                dSU(1),
                channel(2)
           }
 
        ACCESS  read-write
        STATUS  mandatory
        DESCRIPTION
        "This variable indicates the Receive ncmdds loop code
         of the port 1."
 
        ::= { ncmddsConfigEntry 4 }



	ncmddsPortRemoteLoopCode OBJECT-TYPE
        SYNTAX  INTEGER {
                v54(1),
                fTI(2),
                verilink(3)
         }
 
        ACCESS  read-write
        STATUS  mandatory
        DESCRIPTION
        "This variable indicates the Receive ncmdds loop code
         of the port."
 
        ::= { ncmddsConfigEntry 5 }
 
        ncmddsPortAlarmEnable OBJECT-TYPE
        SYNTAX  INTEGER {
                disable(1),
                enable(2)
	} 
        ACCESS  read-write
        STATUS  mandatory
        DESCRIPTION

	 "This variable indicates the Alarm enable which is bit mapped
         of the port.
        BIT     Value     Description
        0       0        no-loop
        0       1        alarm-on-loop
        1       2        alarm-on-test
                3        both   "
 
        ::= { ncmddsConfigEntry 6 }



	ncmddsPortAlarmClearDelayTime OBJECT-TYPE
        SYNTAX  INTEGER
        ACCESS  read-write
        STATUS  mandatory
        DESCRIPTION
 
        "This variable indicates the Alarmcleardelaytime
        of the port."
 
        ::= { ncmddsConfigEntry 7 }
 
 
 
        ncmddsPortAbnormalStationCodeThreshold OBJECT-TYPE
        SYNTAX  INTEGER
        ACCESS  read-write
        STATUS  mandatory
        DESCRIPTION
 
        "This variable indicates the AbnormalStationCodethreshold
         of the port."
 
        ::= { ncmddsConfigEntry 8 }
 
 
        ncmddsPortControlModeIdleThreshold OBJECT-TYPE
        SYNTAX  INTEGER
        ACCESS  read-write
        STATUS  mandatory
        DESCRIPTION
 
        "This variable indicates the ControlModeIdlethreshold
         of the port."
 
        ::= { ncmddsConfigEntry 9 }
 
 
        ncmddsPortMuxOutofSyncThreshold OBJECT-TYPE
        SYNTAX  INTEGER
        ACCESS  read-write
        STATUS  mandatory
        DESCRIPTION
 
        "This variable indicates the MuxoutofSyncthreshold
         of the port."
 
        ::= { ncmddsConfigEntry 10 }
 
        ncmddsPortUnAssignedMuxChannelThreshold OBJECT-TYPE
        SYNTAX  INTEGER
        ACCESS  read-write
        STATUS  mandatory
        DESCRIPTION
 
        "This variable indicates the UnassignedMuxChannelthreshold
         of the port."
 
        ::= { ncmddsConfigEntry 11 }
 
 	ncmddsPortGroup1Codes OBJECT-TYPE
        SYNTAX  INTEGER
        ACCESS  read-write
        STATUS  mandatory
        DESCRIPTION
 
        "This variable indicates the port1Group1ncmddsCodes
         of the port."
 
        ::= { ncmddsConfigEntry 12 }

        
         
	ncmddsPort56KStatus OBJECT-TYPE
        SYNTAX  INTEGER
        ACCESS  read-only
        STATUS  mandatory
        DESCRIPTION
 
        "This variable indicates the 56K ncmdds Status
         of the port.
 
          The various bit positions are:
          0     Abnormal Station code(1 = Yes, 0 = No)
          1     Control Mode Idle
          2     Mux-Out-of-Sync
          3     Unassigned Mux Chan
          4     Group 1 ncmdds Codes       Test            Test
          5     Test in Progress  { 0 } Verilink   {0} 511
          6     Test in Progress  { 0 }            {1}
          7     ncmdds mode enabled "
        
        ::= { ncmddsConfigEntry 13 }
 
         
        
        ncmddsPortReceived56KCode OBJECT-TYPE
        SYNTAX INTEGER
	{
                umc(1),
                tip(2),
                ta(3),
                ma(4),
                rc(5),
                bl(6),
                lbe(7),
                fev(8),
                asc(9),
                oos(10),
                cmi(11),
                tc(12)
        }

        ACCESS read-only
        STATUS mandatory
        DESCRIPTION
 
        "This variable specifies the received 56K ncmdds code.Some specitic 
	values indicate the specific testing error.
        Value   Testing Error
        1       UMC
        2       TIP
        3       TA
        4       MA
        5       RC
        6       BL
        7       LBE
        8       FEV
        9       ASC
        10      OOS
        11      CMI
        12      TC"
 
        ::= {ncmddsConfigEntry 14 }
 
 
        ncmddsmode OBJECT-TYPE
        SYNTAX INTEGER
                        {
                        mode-56k(1),
                        mode-64k(2),
                        mode-56kncmdds(3)
                        }
        ACCESS read-write
        STATUS mandatory
        DESCRIPTION
 
        "This variable specifies the mode of ncmdds."
 
        ::= {ncmddsConfigEntry 15 }

	ncmddsLatchingLoopbackType OBJECT-TYPE
        SYNTAX INTEGER  {
                        chan-loop-up(1),
                        dsu-loop-up(2),
                        ocu-loop-up(3),
                        chan-loop-dn(4),
			none(5)
                        }
        ACCESS read-write
        STATUS mandatory
        DESCRIPTION
 
        "This variable specifies the latching loop up type of dds."
        ::= {ncmddsConfigEntry 16 }
 
        ncmddsLatchingLoopbackDevNo OBJECT-TYPE
        SYNTAX INTEGER  
        ACCESS read-write
        STATUS mandatory
        DESCRIPTION
 
        "This variable specifies the device number to receive code.
	 Range is 0 to 7, where 0 is the first device. 
	 Used only for DS0-Data Port loopback option of Latching
	 Loopback Type Object. No signifiance right now."
 
        ::= {ncmddsConfigEntry 17 }



-- the ncm dbu Main Configuration Table

        ncmdbuMainConfigTable OBJECT-TYPE
        SYNTAX  SEQUENCE OF  NcmdbuMainConfigEntry
        ACCESS  not-accessible
        STATUS  mandatory
	DESCRIPTION
        "The ncm dbu Main Configuration table."


	--DEFAULT test-function dbu-test
        --DEFAULT next-function dbu-next
	


         ::= { ncm-dbu 4000 }


        ncmdbuMainConfigEntry OBJECT-TYPE
        SYNTAX  NcmdbuMainConfigEntry
        ACCESS  not-accessible
        STATUS  mandatory
        DESCRIPTION
        "An entry in the ncm dbu Main Configuration table."
         INDEX   { ncmdbuNIDMainConfigIndex, ncmdbuMainLineIndex }
         ::= { ncmdbuMainConfigTable 1 }


        NcmdbuMainConfigEntry ::=
         SEQUENCE {
             ncmdbuNIDMainConfigIndex
                INTEGER,
             ncmdbuMainLineIndex
                 INTEGER,
             ncmdbudsubus
                 INTEGER,
             ncmdbuPortChannel
                 DisplayString,
             ncmdbuPortConfiguration
                 INTEGER,
             ncmdbucsushelf
                INTEGER,
             ncmdbucsuslot
                INTEGER,
             ncmdbuLosLead
                INTEGER
             }
                

	 ncmdbuNIDMainConfigIndex OBJECT-TYPE
             SYNTAX  INTEGER (1..'7fffffff'h)
             ACCESS  read-only
             STATUS  mandatory
             DESCRIPTION
                "This variable indicates the node id
                 value of the node."
               ::= { ncmdbuMainConfigEntry 1 }
                
 
        ncmdbuMainLineIndex OBJECT-TYPE
        SYNTAX  INTEGER
        ACCESS  read-only
        STATUS  mandatory
	--DEFAULT get-function    get-LineIndex

 
        ::= { ncmdbuMainConfigEntry 2 }
 
        ncmdbudsubus OBJECT-TYPE
        SYNTAX INTEGER {
                       disabled(1),
                       busA(2),
                       busB(3),
                       busC(4)
               } 
          ACCESS read-write
          STATUS mandatory
          DESCRIPTION
          "The ncmdsu bus type for Port."
        ::= { ncmdbuMainConfigEntry 3 }
 
 
        ncmdbuPortChannel OBJECT-TYPE
        SYNTAX DisplayString (SIZE (0..255))
        ACCESS  read-write
        STATUS  mandatory
        DESCRIPTION
 
        "This variable indicates the channel assignment for the
        ncmdbu for the port."
        ::= { ncmdbuMainConfigEntry 4 }
 
	ncmdbuPortConfiguration OBJECT-TYPE
        SYNTAX INTEGER
        ACCESS  read-write
        STATUS mandatory
        DESCRIPTION
 
        "This variable indicates the configuration bits
        for port. The configuration can be set by setting the relevant
        bit to 1 and reset by setting the relevant bit to zero.
 
        Bit     Value   Name    Description
                0               set the ncmdsu port configuration to zero
        0       1       64k     set uses 8bits of data/64kbps.
        1       2       LEN     set enable loop code and loop commands
        2       4       INV     set invert the channelized data
        3       8       SCR     set to scramble channelized data.
        4       16      CLK1    DTE transmit clock select bits
        5       32      CLK2    DTE transmit clock select bits
        6       64      TU      set port as a timing unit
        7       128     ALM     set if DIU has to report alarms to SAM."
         
       ::= { ncmdbuMainConfigEntry 5 }
        
 
        ncmdbucsushelf OBJECT-TYPE
        SYNTAX INTEGER
        ACCESS  read-write
        STATUS mandatory
        DESCRIPTION
 
        "This variable indicates the csu shelf associated with
        the ncmdbu port."
         
        ::= { ncmdbuMainConfigEntry 6 }
 
 
        ncmdbucsuslot OBJECT-TYPE
        SYNTAX INTEGER
        ACCESS  read-write
        STATUS mandatory
        DESCRIPTION
 
        "This variable indicates the csu slot associated with
        the ncmdbu port."
         
        ::= { ncmdbuMainConfigEntry 7 }
 

	ncmdbuLosLead OBJECT-TYPE
        SYNTAX INTEGER
        ACCESS  read-write
        STATUS mandatory
        DESCRIPTION
 
        "This variable indicates the DTE lead bits
        for port. The DTE leads can be set by setting the relevant
        bit to 1 and reset by setting the relevant bit to zero.
 
        Bit     Value   Name    Description
                0               set the ncmdsu port configuration to zero
        0       1       DTR     set uses DTR
        1       2       RTS     set uses RTS
        2       4       DSR     set uses DSR
        3       8       CTS     set uses CTS
        4       16      DCD     set uses DCD
        5       32      LOS     use both bits: bits set to use for alarm
        6       64      LOS     0 = Disable LOS detect, 1=use RTS , 2 = DTR
        7       128     DDSMode set for 56k DDS ."
 
        ::= { ncmdbuMainConfigEntry 8 }
 



	 -- the ncmdbu Configuration Table

         ncmdbuConfigTable OBJECT-TYPE
             SYNTAX  SEQUENCE OF NcmdbuConfigEntry
             ACCESS  not-accessible
             STATUS  mandatory
	     DESCRIPTION
                "The ncm dbu Configuration table."


	      --DEFAULT test-function dbu-test
             --DEFAULT next-function dbu-next
	
             ::= { ncm-dbu 4001 }

 
        ncmdbuConfigEntry OBJECT-TYPE
             SYNTAX  NcmdbuConfigEntry
             ACCESS  not-accessible
             STATUS  mandatory
             DESCRIPTION
                "An entry in the ncmdbu Configuration table."
            INDEX   { ncmdbuNIDConfigIndex, ncmdbuLineIndex }
            ::= { ncmdbuConfigTable 1 }
 
 
        NcmdbuConfigEntry ::=
             SEQUENCE {
 
	     ncmdbuNIDConfigIndex
		INTEGER,
             ncmdbuLineIndex
                 INTEGER,
             ncmdbuAllOnesSwitchOverTime
                INTEGER,
             ncmdbuSwitchOnBERThresholdExceeded
                INTEGER,
             ncmdbuDialBackupMode
                INTEGER,
             ncmdbuBackupConnection
                INTEGER,
             ncmdbumode   
                INTEGER,
	     ncmdbuLoopType
		INTEGER
                                                
                         }


	 ncmdbuNIDConfigIndex OBJECT-TYPE
          SYNTAX  INTEGER
          ACCESS  read-only
          STATUS  mandatory
	  DESCRIPTION
	 "This variable specifies the node id."
           ::= { ncmdbuConfigEntry 1 }

 
         ncmdbuLineIndex OBJECT-TYPE
          SYNTAX  INTEGER
          ACCESS  read-only
          STATUS  mandatory
	  --DEFAULT get-function    get-LineIndex

 
          ::= { ncmdbuConfigEntry 2 }


 	ncmdbuAllOnesSwitchOverTime OBJECT-TYPE
         SYNTAX  INTEGER
         ACCESS  read-write
         STATUS  mandatory
         DESCRIPTION
 
         "This variable indicates the all ones duration in seconds for
          the ncmdbu."
 
         ::= { ncmdbuConfigEntry 3 }
 
 
        ncmdbuSwitchOnBERThresholdExceeded OBJECT-TYPE
         SYNTAX  INTEGER
                        {
                         nO(1),
                         yES(2)
                        }
         ACCESS  read-write
         STATUS  mandatory
         DESCRIPTION
 
         "This variable indicates whether the ncmdbu is switched on for BER Threshold
          exceeded."
 
         ::= { ncmdbuConfigEntry 4 }
 
 
        ncmdbuDialBackupMode OBJECT-TYPE
         SYNTAX  INTEGER
                        {
                         manual-manual(1),
                         automatic-automatic(2),
                         automatic-manual(3)
                        }
                        
         ACCESS  read-write
         STATUS  mandatory
         DESCRIPTION
 
         "This variable indicates the dial backup mode for the ncmdbu."
 
         ::= { ncmdbuConfigEntry 5 }
 
 
        ncmdbuBackupConnection OBJECT-TYPE
         SYNTAX  INTEGER
                        {
                         none(1),
                         deactivate(2),
                         activate(3)
                         }
                        
         ACCESS  read-write
         STATUS  mandatory
         DESCRIPTION
 
         "This variable indicates the whether the backup connection is activated or not."
 
         ::= { ncmdbuConfigEntry 6 }
 

	 ncmdbumode OBJECT-TYPE
         SYNTAX INTEGER
                        {
                        mode-56k(1),
                        mode-64k(2),
                        mode-56kncmdds(3)
                        }
        ACCESS read-write
        STATUS mandatory
        DESCRIPTION
 
        "This variable specifies the mode of ncmdbu."
 
        ::= {ncmdbuConfigEntry 7 }


	ncmdbuLoopType OBJECT-TYPE
         SYNTAX INTEGER
                        {
                        fT1(1)
                        }
        ACCESS read-write
        STATUS mandatory
        DESCRIPTION
 
        "This variable specifies the Loop Type on RL EIA ."
 
        ::= {ncmdbuConfigEntry 8 }


	
 


END
