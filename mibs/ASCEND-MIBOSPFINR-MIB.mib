--			Ascend mibospfinr MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBOSPFINR-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibospfAreaRangeProfile  OBJECT IDENTIFIER ::= { configuration 97}

	-- The mibospfAreaRangeProfile table
	--
	-- This table contains parameters for the mibospfAreaRangeProfile profile
	--

    mibospfAreaRangeProfileTable	OBJECT-TYPE
	SYNTAX		SEQUENCE OF MibospfAreaRangeProfileEntry
	ACCESS		not-accessible
	STATUS		mandatory
	DESCRIPTION	"A list of mibospfAreaRangeProfile profile entries."
	::= { mibospfAreaRangeProfile 1 }

    mibospfAreaRangeProfileEntry	OBJECT-TYPE
	SYNTAX		MibospfAreaRangeProfileEntry
	ACCESS		not-accessible
	STATUS		mandatory
	DESCRIPTION	"A mibospfAreaRangeProfile entry containing objects that
			 maps to the parameters of mibospfAreaRangeProfile profile."
	INDEX		{ ospfAreaRangeProfile-Name }
	::= { mibospfAreaRangeProfileTable 1 }

    MibospfAreaRangeProfileEntry ::=
	SEQUENCE {
	    ospfAreaRangeProfile-Name
		DisplayString,
	    ospfAreaRangeProfile-AreaId
		IpAddress,
	    ospfAreaRangeProfile-AreaNetworkAddr
		IpAddress,
	    ospfAreaRangeProfile-AreaNetworkMask
		IpAddress,
	    ospfAreaRangeProfile-Advertize
		INTEGER,
	    ospfAreaRangeProfile-Action-o
		INTEGER
	}

    ospfAreaRangeProfile-Name	OBJECT-TYPE
	SYNTAX	DisplayString
	ACCESS	read-only
	STATUS	mandatory
	DESCRIPTION	"The name of this profile."
	::= { mibospfAreaRangeProfileEntry 1 }

    ospfAreaRangeProfile-AreaId	OBJECT-TYPE
	SYNTAX	IpAddress
	ACCESS	read-write
	STATUS	mandatory
	DESCRIPTION	"Ospf area id for this area range."
	::= { mibospfAreaRangeProfileEntry 2 }

    ospfAreaRangeProfile-AreaNetworkAddr	OBJECT-TYPE
	SYNTAX	IpAddress
	ACCESS	read-write
	STATUS	mandatory
	DESCRIPTION	"Ospf area network address."
	::= { mibospfAreaRangeProfileEntry 3 }

    ospfAreaRangeProfile-AreaNetworkMask	OBJECT-TYPE
	SYNTAX	IpAddress
	ACCESS	read-write
	STATUS	mandatory
	DESCRIPTION	"Ospf area network mask."
	::= { mibospfAreaRangeProfileEntry 4 }

    ospfAreaRangeProfile-Advertize	OBJECT-TYPE
	SYNTAX	INTEGER {
		    no (1),
		    yes (2)
		}
	ACCESS	read-write
	STATUS	mandatory
	DESCRIPTION	"Indication of whether this area is to advertize."
	::= { mibospfAreaRangeProfileEntry 5 }

    ospfAreaRangeProfile-Action-o	OBJECT-TYPE
	SYNTAX	INTEGER {
		    noAction (1),
		    createProfile (2),
		    deleteProfile (3)
		}
	ACCESS	read-write
	STATUS	mandatory
	DESCRIPTION	""
	::= { mibospfAreaRangeProfileEntry 6 }

END
