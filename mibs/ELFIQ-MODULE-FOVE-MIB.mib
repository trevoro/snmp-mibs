ELFIQ-MODULE-FOVE-MIB DEFINITIONS ::= BEGIN

	IMPORTS
      	MODULE-IDENTITY, OBJECT-TYPE, Integer32, Unsigned32,
      	IpAddress, NOTIFICATION-TYPE				FROM SNMPv2-SMI
		TEXTUAL-CONVENTION, DisplayString,
		MacAddress								FROM SNMPv2-TC
		MODULE-COMPLIANCE, OBJECT-GROUP,
		NOTIFICATION-GROUP						FROM SNMPv2-CONF
		snmpTraps								FROM SNMPv2-MIB
		common,commonConformance     			FROM ELFIQ-INC-MIB
		commonComponent,commonNotification   	FROM ELFIQ-MODULE-COMMON-MIB;

--
-- A brief description and update information about this mib.
--

foveInfo                    MODULE-IDENTITY
    LAST-UPDATED "0902190000Z"        -- 09 Feb 2009, midnight
    ORGANIZATION "Elfiq Inc."
    CONTACT-INFO "
              Author:     Elfiq Network
              postal:     Montreal, QC H3B3A7
                                     CANADA
              email:      support@elfiq.com
              phone:      +1-514-667-0611
                        "
    DESCRIPTION  "This is the standard standard component of the common failover elfiq module"
    ::= { commonComponent 2 }

--
-- 3) This is the part for the component fove
--

FoveIndex ::= TEXTUAL-CONVENTION
	DISPLAY-HINT	"d"
	STATUS 			current
	DESCRIPTION 
				" A unique value, greater than zero, for each fove component "
	SYNTAX		Integer32 (0..5)

foveIntNumber	OBJECT-TYPE
	SYNTAX      Integer32 (0..16)
	MAX-ACCESS  read-only
	STATUS      current
	DESCRIPTION
           "The number of failover interface used and configured on your elfiq product"
	::= { foveInfo 1 }

-- the fove table which contains information about its component details

foveTable 			OBJECT-TYPE
	SYNTAX 			SEQUENCE OF FoveEntry
	MAX-ACCESS		not-accessible
	STATUS			current
	DESCRIPTION	
				"This is a list of fove interfaces entries. The number of fove interfaces used is given by the value of foveIntNumber."
	::= { foveInfo 2 }

foveEntry			OBJECT-TYPE
	SYNTAX			FoveEntry
	MAX-ACCESS		not-accessible
	STATUS 			current
	DESCRIPTION	
				" An entry containing fove sub-component."
	INDEX	{ foveIntIndex }
	::= { foveTable 1 }

FoveEntry ::=
	SEQUENCE {
		foveIntIndex			FoveIndex,
		foveIntUsed				DisplayString,
		foveIntType				INTEGER,
		foveLocalState			INTEGER,
		foveRemoteId			Unsigned32,
		foveRemoteSeq			Unsigned32,
		foveRemoteState			INTEGER,
		foveRemoteMgmtIP		IpAddress,
		foveRemoteIfName		DisplayString,
		foveRemoteLastL2FoMSec	Unsigned32,
		foveRemoteMac			MacAddress,
		foveVIPStatus			INTEGER,
		foveVIP					IpAddress
	}

foveIntIndex		OBJECT-TYPE
	SYNTAX      	FoveIndex
	MAX-ACCESS  	read-only
	STATUS      	current
	DESCRIPTION
           "The fove interface index"
	::= { foveEntry 1 }

foveIntUsed			OBJECT-TYPE
	SYNTAX      	DisplayString (SIZE (0..16))
	MAX-ACCESS  	read-only
	STATUS      	current
	DESCRIPTION
           "This variable corresponds to the interface of this entry used in failover mode"
	::= { foveEntry 2 }

foveIntType			OBJECT-TYPE
	SYNTAX      	INTEGER { 
						management(1),
						critical(2)
						}
	MAX-ACCESS  read-only
	STATUS      current
	DESCRIPTION
           "This variable describes the interface type of this entry used in failover mode"
	::= { foveEntry 3 }

foveLocalState		OBJECT-TYPE
	SYNTAX      	INTEGER { 
						negociation(1),
						master(2),
						slave(3),
						failure(4),
						dead(5),
						paused(6),
						managementfailure(7)
						}
	MAX-ACCESS  read-only
	STATUS      current
	DESCRIPTION
           "The is the current state in failover mode of your elfiq product"
	::= { foveEntry 4 }

foveRemoteId		OBJECT-TYPE
	SYNTAX      	Unsigned32
	MAX-ACCESS  	read-only
	STATUS      	current
	DESCRIPTION
           "The is the remote identification of the peer configured in failover 
					mode with your elfiq product"
	::= { foveEntry 5 }

foveRemoteSeq		OBJECT-TYPE
	SYNTAX      	Unsigned32
	MAX-ACCESS  	read-only
	STATUS      	current
	DESCRIPTION
           "This is the remote sequence number  of the peer configured in failover 
					mode with your elfiq product"
	::= { foveEntry 6 }

foveRemoteState	OBJECT-TYPE
	SYNTAX      	INTEGER { 
						negociation(1),
						master(2),
						slave(3),
						failure(4),
						dead(5),
						paused(6),
						managementfailure(7)
						}
	MAX-ACCESS 		read-only
	STATUS      	current
	DESCRIPTION
           "This is the remote state of the peer configured in failover 
					mode with your elfiq product"
	::= { foveEntry 7 }

foveRemoteMgmtIP	OBJECT-TYPE
	SYNTAX      	IpAddress
	MAX-ACCESS  	read-only
	STATUS      	current
	DESCRIPTION
           "This is the remote management ip address of the peer configured in failover 
					mode with your elfiq product"
	::= { foveEntry 8 }

foveRemoteIfName	OBJECT-TYPE
	SYNTAX      	DisplayString (SIZE (0..16))
	MAX-ACCESS  	read-only
	STATUS      	current
	DESCRIPTION
            "This variable corresponds to the remote interface name of the peer configured in failover 
					mode with your elfiq product"
	::= { foveEntry 9 }

foveRemoteLastL2FoMSec		OBJECT-TYPE
	SYNTAX      			Unsigned32 
	MAX-ACCESS  			read-only
	STATUS      			current
	DESCRIPTION
           "This is the delay in ms when your product received the last sequence number sent by the peer configured 
				in failover mode with your elfiq product"
	::= { foveEntry 10 }

foveRemoteMac			OBJECT-TYPE
	SYNTAX      		MacAddress
	MAX-ACCESS  		read-only
	STATUS      		current
	DESCRIPTION
            "This is the mac address of the peer interface configured in failover 
					mode with your elfiq product"
	::= { foveEntry 11 }

foveVIPStatus			OBJECT-TYPE
	SYNTAX      		INTEGER { 
							enable(1),
							disable(2)
						}
	MAX-ACCESS  		read-only
	STATUS      		current
	DESCRIPTION
            "This is the virtual ip status of your elfiq product"
	::= { foveEntry 12 }

foveVIP					OBJECT-TYPE
	SYNTAX      		IpAddress
	MAX-ACCESS  		read-only
	STATUS      		current
	DESCRIPTION
            "This is the virtual ip address of your elfiq product"
	::= { foveEntry 13 }

-- Notification

--

foveNotification 		OBJECT IDENTIFIER ::= { commonNotification 2 }

--

foveStatusChanged 	NOTIFICATION-TYPE
    OBJECTS 		{ foveLocalState, foveRemoteState, foveVIPStatus, foveVIP }
    STATUS    		current
    DESCRIPTION
        "This notification is sent every time the fove's product state changes ( master , slave , ...) "
    ::= { foveNotification 1 }



-- Define object group conformance

foveGroups	OBJECT IDENTIFIER ::= { commonConformance 2 }

	 systInfoGroup    OBJECT-GROUP
          OBJECTS {
		foveIntNumber,
		foveIntIndex,
		foveIntUsed,
		foveIntType,
		foveLocalState,
		foveRemoteId,
		foveRemoteSeq,
		foveRemoteState,
		foveRemoteMgmtIP,
		foveRemoteIfName,
		foveRemoteLastL2FoMSec,
		foveRemoteMac,
		foveVIPStatus,
		foveVIP
       }
          STATUS     current
          DESCRIPTION
              "A collection of objects providing fove information"
      ::= { foveGroups 1 }

foveNotificationGroup    NOTIFICATION-GROUP
          NOTIFICATIONS {
             foveStatusChanged
       }
          STATUS     current
          DESCRIPTION
              "A collection of objects notification corresponding to your products changes"
      ::= { foveGroups 2 }




END
