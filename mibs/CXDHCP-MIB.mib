--
-- DHCP / BOOTP Relay Agent Table
--

CXDHCP-MIB DEFINITIONS ::= BEGIN

    IMPORTS
      Counter
    FROM RFC1155-SMI
      IpAddress
    FROM RFC1155-SMI
      OBJECT-TYPE                     
    FROM RFC-1212
      cxCfgIp
    FROM CXProduct-SMI;

--
-- DHCP / BOOTP Relay Agent Table
--

     cxCfgDhcpRATable OBJECT-TYPE
      SYNTAX  SEQUENCE OF CxCfgDhcpRAEntry
      ACCESS  not-accessible
      STATUS  mandatory
      DESCRIPTION
"Provides the configuration for a BOOTP / DHCP Relay Agenr.

The table contains one default entry (row) which can be modified."
    ::= { cxCfgIp 4 }


     cxCfgDhcpRAEntry OBJECT-TYPE
    SYNTAX  CxCfgDhcpRAEntry
    ACCESS  not-accessible
    STATUS  mandatory
    DESCRIPTION
"Identifies the configuration of a Relay Agent table."

    INDEX   { cxCfgDhcpRAIndex }
    ::= { cxCfgDhcpRATable 1 }

     CxCfgDhcpRAEntry ::=
    SEQUENCE {
-- Parameters
   cxCfgDhcpRAIndex
       INTEGER,        
   cxCfgDhcpRASrvAddr
       IpAddress,
-- Control
   cxCfgDhcpRARowStatus
       INTEGER,
-- Statistics
   cxCfgDhcpRAStatTx
       Counter,
   cxCfgDhcpRAStatRx
       Counter
    }

      cxCfgDhcpRAIndex  OBJECT-TYPE
     SYNTAX  INTEGER (1..32)
     ACCESS  read-write
     STATUS  mandatory
     DESCRIPTION 
"Determines the number used to index the Relay Agent entry table. 

Range of Values: From 1 - 32

Default Value: None

Configuration Changed: Administrative"

    ::= { cxCfgDhcpRAEntry 1 }


     cxCfgDhcpRASrvAddr OBJECT-TYPE
    SYNTAX  IpAddress
    ACCESS  read-write
    STATUS  mandatory
    DESCRIPTION
"The IP Address of the DHCP or BOOTP Server the IP Address of another
 Relay Agent, a unique IP number.

Default Value: None "
    ::= { cxCfgDhcpRAEntry 2 }

     cxCfgDhcpRARowStatus  OBJECT-TYPE
    SYNTAX  INTEGER {
       invalid (1),
       valid (2)
          }
    ACCESS  read-write
    STATUS  mandatory
    DESCRIPTION 
"Determines the status of the objects in a table row.

Options:
invalid (1): Row is flagged. After next reset the values will be disabled
and the row will be deleted from the table.

valid (2): Values are enabled.

Default Value: (2)

Configuration Changed: Administrative"

    ::= { cxCfgDhcpRAEntry 10 }


     cxCfgDhcpRAStatTx OBJECT-TYPE
    SYNTAX  Counter
    ACCESS  read-only
    STATUS  mandatory
    DESCRIPTION
"The number of DHCP or BOOTP frames transmitted."
    ::= { cxCfgDhcpRAEntry 20 }


     cxCfgDhcpRAStatRx OBJECT-TYPE
    SYNTAX  Counter
    ACCESS  read-only
    STATUS  mandatory
    DESCRIPTION
"The number of DHCP or BOOTP frames recieved."
    ::= { cxCfgDhcpRAEntry 21 }

END
