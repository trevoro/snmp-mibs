PANDATEL-FHFLS-MODEM-MIB DEFINITIONS ::= BEGIN

 -- This is the private mib group section for the FHFL-S modems.
 -- Because these modems must be installed in the PANDATEL modem rack
 -- the PANDATEL-MODEM-MIB also applies.

 -- Ver.1.01    Sep.13.1999

        IMPORTS
                enterprises
                        FROM RFC1155-SMI
                DisplayString
                        FROM RFC1213-MIB
                OBJECT-TYPE
                        FROM RFC-1212
                mdmSpecifics, device-id
                        FROM PANDATEL-MODEM-MIB;

-- ********************** THE MDM-FHFLS SUBTREE ******************************

-- the specific identifier is identical to the modem type integer
-- of the FHFL-S modem entries in the PANDATEL-MODEM-MIB mdmModemTable.

fhfls-modem      OBJECT IDENTIFIER ::= { device-id 103 }     -- chassis-mib

fhfls            OBJECT IDENTIFIER ::= { mdmSpecifics 103 }  -- this subtree

fhflsModemTable OBJECT-TYPE
        SYNTAX  SEQUENCE OF FhflsTableEntry
        ACCESS  not-accessible
        STATUS  mandatory
        DESCRIPTION
                "The table of all FHFL-S modems in this housing."
        ::= { fhfls 1 }

fhflsTableEntry OBJECT-TYPE
        SYNTAX  FhflsTableEntry
        ACCESS  not-accessible
        STATUS  mandatory
        DESCRIPTION
                "The index of the table."
        INDEX   { mdmRack, mdmModem, mdmPosition }
        ::= { fhflsModemTable 1 }

FhflsTableEntry ::= SEQUENCE {
        mdmRack
                INTEGER,
        mdmModem
                INTEGER,
        mdmPosition
                INTEGER,
        mdmModemName
                DisplayString,
        mdmInterfaceEmulationMode
                INTEGER,
        mdmModemProperty
                INTEGER,
        mdmClockSystem
                INTEGER,
        mdmClockSource
                INTEGER,
        mdmDataRate
                INTEGER,
        mdmRemoteAccessMode
                INTEGER,
        mdmForcedRemoteAccess
                INTEGER,
        mdmClockRecovery
                INTEGER,
        mdmInterfaceAlarmCondition
                INTEGER,
        mdmLineAlarmCondition
                INTEGER
        }

mdmRack OBJECT-TYPE
        SYNTAX  INTEGER
        ACCESS  read-only
        STATUS  mandatory
        DESCRIPTION
                "The index of the rack where the modem is installed."
        ::= { fhflsTableEntry 1 }

mdmModem OBJECT-TYPE
        SYNTAX  INTEGER
        ACCESS  read-only
        STATUS  mandatory
        DESCRIPTION
                "This variable displays the slot number where the
                 corresponding modem is installed in the rack."
        ::= { fhflsTableEntry 2 }

mdmPosition OBJECT-TYPE
        SYNTAX  INTEGER {
                local       (1),
                remote      (2)
                }
        ACCESS  read-only
        STATUS  mandatory
        DESCRIPTION
                "This variable displays the location of the corresponding
                 modem: 'local' or 'remote'.
                 The modem which is plugged into a managed rack is 'local',
                 the counterpart is 'remote'."
        ::= { fhflsTableEntry 3 }

mdmModemName OBJECT-TYPE
        SYNTAX  DisplayString
        ACCESS  read-only
        STATUS  mandatory
        DESCRIPTION
                "A verbal name of this modem."
        ::= { fhflsTableEntry 5 }

mdmInterfaceEmulationMode OBJECT-TYPE
        SYNTAX  INTEGER {
                other           (1),
                te              (4),
                nt              (5),
                not-available   (100)
        }
        ACCESS  read-only
        STATUS  mandatory
        DESCRIPTION
                "Interface mode of the unit: 'te' or 'nt'."
        ::= { fhflsTableEntry 6 }

mdmModemProperty OBJECT-TYPE
        SYNTAX  INTEGER {
                other                   (1),
                stm1-oc3-coax           (14),
                sts3-oc3		(15),
                unknown                 (99)
        }
        ACCESS  read-only
        STATUS  mandatory
        DESCRIPTION
                "The speed class of the unit: STM-1/OC-3."
        ::= { fhflsTableEntry 7 }

mdmClockSystem OBJECT-TYPE
        SYNTAX  INTEGER {
                other       (1),
                dual        (2),
                single      (3)
        }
        ACCESS  read-only
        STATUS  mandatory
        DESCRIPTION
                "The clock system of the link."
        ::= { fhflsTableEntry 23 }

mdmClockSource OBJECT-TYPE
        SYNTAX  INTEGER {
                other       (1),
                internal    (2),
                remote      (3),
                external    (4)
        }
        ACCESS  read-only
        STATUS  mandatory
        DESCRIPTION
                "The clock source of the link."
        ::= { fhflsTableEntry 24 }

mdmDataRate OBJECT-TYPE
        SYNTAX  INTEGER {
                other       (1)
        }
        ACCESS  read-only
        STATUS  mandatory
        DESCRIPTION
                "The data rate at the interface in bits per seconds."
        ::= { fhflsTableEntry 25 }

mdmRemoteAccessMode OBJECT-TYPE
        SYNTAX  INTEGER {
                other       (1),
                disable     (2),
                enable      (5)
        }
        ACCESS  read-write
        STATUS  mandatory
        DESCRIPTION
                "The possibility of remote management: 'enabled' or 'disabled'.
                 Once disabled remote management, it is not possible to enable
                 it at the remote unit."
        ::= { fhflsTableEntry 64 }

mdmForcedRemoteAccess OBJECT-TYPE
        SYNTAX  INTEGER {
                off         (1),
                on          (2)
        }
        ACCESS  read-write
        STATUS  mandatory
        DESCRIPTION
                "Activation of remote management: 'on' or 'off'.
                 Status 'on' enables management of remote unit. During this
                 process the link is restricted to management data. The
                 transmission of user data is interrupted.
                 Status 'off' disables management of remote unit. The link
                 transmits user data."
        ::= { fhflsTableEntry 65 }

mdmClockRecovery OBJECT-TYPE
        SYNTAX  INTEGER {
                other               (1),
                disable             (2),
                stm1-oc3-155mbps    (3),
                stm4-oc12-622mbps   (4),
                not-available       (100)
        }
        ACCESS  read-only
        STATUS  mandatory
        DESCRIPTION
                "The clock recovery and data retiming at interface and line port."
        ::= { fhflsTableEntry 70 }

mdmInterfaceAlarmCondition OBJECT-TYPE
        SYNTAX  INTEGER {
                other                             (1),
                disable                           (2),
                no-link-signal                    (3),
                no-clock-signal                   (6),
                no-clock-signal-or-no-link-signal (7),
                not-available                     (100)
        }
        ACCESS  read-write
        STATUS  mandatory
        DESCRIPTION
                "The alarm trigger mode at interface port."
        ::= { fhflsTableEntry 98 }

mdmLineAlarmCondition OBJECT-TYPE
        SYNTAX  INTEGER {
                other                             (1),
                disable                           (2),
                no-link-signal                    (3),
                laser-fail                        (4),
                no-link-signal-or-laser-fail      (5),
                no-clock-signal                   (6),
                no-clock-signal-or-no-link-signal (7),
                no-clock-signal-or-laser-fail     (8),
                all                               (9),
                not-available                     (100)
        }
        ACCESS  read-write
        STATUS  mandatory
        DESCRIPTION
                "The alarm trigger mode at line port."
        ::= { fhflsTableEntry 99 }

END
