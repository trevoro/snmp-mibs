-- $Id: ms.mib,v 29.2 1998/01/01 00:57:56 jfan Exp $

--
-- Aug 04, 1997 rm   Initial creation
--


ASCEND-MULTI-SHELF-MIB DEFINITIONS ::= BEGIN

    IMPORTS
            multiShelf
                FROM ASCEND-MIB
            Counter
                FROM RFC1155-SMI
            OBJECT-TYPE
                FROM RFC-1212;

    myShelfNumber OBJECT-TYPE
        SYNTAX  INTEGER
        ACCESS  read-only
        STATUS  mandatory
        DESCRIPTION
           "The shelf number associated with the system."
       ::= { multiShelf 1 }

    myShelfOperation OBJECT-TYPE
        SYNTAX  INTEGER {
            other(1),
            slave(2),
            master(3)
        }
        ACCESS  read-only
        STATUS  mandatory
        DESCRIPTION
           "The operation mode of this shelf of a multi-shelf configuration."
       ::= { multiShelf 2 }

    masterShelfNumber OBJECT-TYPE
        SYNTAX  INTEGER
        ACCESS  read-only
        STATUS  mandatory
        DESCRIPTION
           "The shelf number of the master of the multi-shelf configuration."
       ::= { multiShelf 3 }

    multiShelfTableSize OBJECT-TYPE
        SYNTAX  INTEGER
        ACCESS  read-only
        STATUS  mandatory
        DESCRIPTION
           "The maximum number of entries in the multiShelfTable."
       ::= { multiShelf 4 }

    multiShelfTable OBJECT-TYPE
        SYNTAX  SEQUENCE OF MultiShelfEntry
        ACCESS  not-accessible
        STATUS  mandatory
        DESCRIPTION
           "The multi-shelf table."
       ::= { multiShelf 5 }

    multiShelfEntry OBJECT-TYPE
        SYNTAX  MultiShelfEntry
        ACCESS  not-accessible
        STATUS  mandatory
        DESCRIPTION
           "An entry in the multi-shelf table."
       INDEX   { multiShelfIndex }
       ::= { multiShelfTable 1 }

    MultiShelfEntry ::=
        SEQUENCE {
            multiShelfIndex
                INTEGER,
            multiShelfState
                INTEGER,
            multiShelfResentFrames
                Counter,
            multiShelfNLinkUp
                Counter,
            multiShelfTxQs
                INTEGER,
            multiShelfTxSeq
                INTEGER,
            multiShelfRxSeq
                INTEGER,
            multiShelfTimerValue
                INTEGER
    }

    multiShelfIndex OBJECT-TYPE
        SYNTAX  INTEGER
        ACCESS  read-only
        STATUS  mandatory
        DESCRIPTION
                "The index of the multi-shelf entry. The destination shelf
                number of the multi-shelf system."
       ::= { multiShelfEntry 1 }

    multiShelfState OBJECT-TYPE
        SYNTAX  INTEGER {
            idle(1),               --  no connection
            outGoing(2),           --  intermediate state
            inComing(3),           --  intermediate state
            up(4)                  --  connected
        }
        ACCESS  read-only
        STATUS  mandatory
        DESCRIPTION
                "The state of the destination multi-shelf system."
       ::= { multiShelfEntry 2 }

    multiShelfResentFrames OBJECT-TYPE
        SYNTAX  Counter
        ACCESS  read-only
        STATUS  mandatory
        DESCRIPTION
                "The number of times frames were resent to the destination
                shelf number."
       ::= { multiShelfEntry 3 }

    multiShelfNLinkUp OBJECT-TYPE
        SYNTAX  Counter
        ACCESS  read-only
        STATUS  mandatory
        DESCRIPTION
                "The number of times the data link to the destination
                shelf number has gone up and down."
       ::= { multiShelfEntry 4 }

    multiShelfTxQs OBJECT-TYPE
        SYNTAX  INTEGER
        ACCESS  read-only
        STATUS  mandatory
        DESCRIPTION
                "The current frames in the transmit queue to
                the destination shelf number."
       ::= { multiShelfEntry 5 }

    multiShelfTxSeq OBJECT-TYPE
        SYNTAX  INTEGER
        ACCESS  read-only
        STATUS  mandatory
        DESCRIPTION
                "The next transmit sequence number to
                the destination shelf number."
       ::= { multiShelfEntry 6 }

    multiShelfRxSeq OBJECT-TYPE
        SYNTAX  INTEGER
        ACCESS  read-only
        STATUS  mandatory
        DESCRIPTION
                "The next receive sequence number from
                the destination shelf number."
       ::= { multiShelfEntry 7 }

    multiShelfTimerValue OBJECT-TYPE
        SYNTAX  INTEGER
        ACCESS  read-only
        STATUS  mandatory
        DESCRIPTION
                "The timer value in seconds associated with the
                data link to the destination shelf number."
       ::= { multiShelfEntry 8 }


    multiShelfStateTrapState OBJECT-TYPE
        SYNTAX  INTEGER { enabled(1), disabled(2) }
        ACCESS   read-write
        STATUS   mandatory
        DESCRIPTION
           "This variable  indicates  whether  the  master system
           produces the multiShelfStateChange trap."
        DEFVAL { enabled }
     ::= { multiShelf 6 }

END
