-- ****************************************************************************
-- HP NSA PCI MIB
-- March 4, 1997
--
-- Copyright Hewlett-Packard Company 1994-1997.
-- All rights reserved.
--
-- The information in this document is subject to change without notice.
--
-- The HP enterprise number is 11. The ASN.1 prefix to, and including,
-- the HP enterprise ID is 1.3.6.1.4.1.11.
--
-- ****************************************************************************
-- Summary of objects in the HP NSA PCI Information MIB
-- ****************************************************************************
-- hp                                           (1.3.6.1.4.1.11)
--    nm                                        (hp.2)
--       hpnsa                                  (nm.23)
--          hpnsaPci Group                      (hpnsa.10)
--             hpnsaPciMibRev Group             (hpnsa.10.1)
--                hpnsaPciMibRevMajor           (hpnsa.10.1.1)
--                hpnsaPciMibRevMinor           (hpnsa.10.1.2)
--             hpnsaPciAgent Group              (hpnsa.10.2)
--                hpnsaPciAgentTable            (hpnsa.10.2.1)
--                   hpnsaPciAgentEntry         (hpnsa.10.2.1.1)
--                      hpnsaPciAgentIndex      (hpnsa.10.2.1.1.1)
--                      hpnsaPciAgentName       (hpnsa.10.2.1.1.2)
--                      hpnsaPciAgentVersion    (hpnsa.10.2.1.1.3)
--                      hpnsaPciAgentDate       (hpnsa.10.2.1.1.4)
--             hpnsaPciBios Group               (hpnsa.10.3)
--                hpnsaPciBiosPresent           (hpnsa.10.3.1)
--                hpnsaPciBiosVersion           (hpnsa.10.3.2)
--                hpnsaPciBuses                 (hpnsa.10.3.3)
--             hpnsaPciConfig Group             (hpnsa.10.4)
--                hpnsaPciTable                 (hpnsa.10.4.1)
--                   hpnsaPciEntry              (hpnsa.10.4.1.1)
--                      hpnsaPciBusIndex        (hpnsa.10.4.1.1.1)
--                      hpnsaPciDeviceIndex     (hpnsa.10.4.1.1.2)
--                      hpnsaPciFunctionIndex   (hpnsa.10.4.1.1.3)
--                      hpnsaPciVendorId        (hpnsa.10.4.1.1.4)
--                      hpnsaPciDeviceId        (hpnsa.10.4.1.1.5)
--                      hpnsaPciRevisionId      (hpnsa.10.4.1.1.6)
--                      hpnsaPciHeaderType      (hpnsa.10.4.1.1.7)
--                      hpnsaPciClassCode       (hpnsa.10.4.1.1.8)
--                      hpnsaPciCommand         (hpnsa.10.4.1.1.9)
--                      hpnsaPciStatus          (hpnsa.10.4.1.1.10)
--                      hpnsaPciCacheLineSize   (hpnsa.10.4.1.1.11)
--                      hpnsaPciLatencyTimer    (hpnsa.10.4.1.1.12)
--                      hpnsaPciBist            (hpnsa.10.4.1.1.13)
--                      hpnsaPciInterruptLine   (hpnsa.10.4.1.1.14)
--                      hpnsaPciInterruptPin    (hpnsa.10.4.1.1.15)
--                      hpnsaPciMaxLat          (hpnsa.10.4.1.1.16)
--                      hpnsaPciMinGnt          (hpnsa.10.4.1.1.17)
--                      hpnsaPciBaseAddrRegs    (hpnsa.10.4.1.1.18)
--                      hpnsaPciExpRomBaseAddr  (hpnsa.10.4.1.1.19)
--                      hpnsaPciDeviceSpecific  (hpnsa.10.4.1.1.20)
--
-- The PCI group provides a set of tables that detail the
-- configuration information regarding the PCI configuration.
--
-- Implementation of the hpnsaPci group is optional.
-- The hpnsaPci group should be included on any system with an PCI
-- bus architecture.
--
-- ****************************************************************************

HPNSAPCI-MIB DEFINITIONS ::= BEGIN
   IMPORTS
      enterprises    FROM RFC1155-SMI
      DisplayString  FROM RFC1213-MIB
      OBJECT-TYPE    FROM RFC-1212;

   hp                  OBJECT IDENTIFIER ::= { enterprises 11 }
   nm                  OBJECT IDENTIFIER ::= { hp 2 }
   hpnsa               OBJECT IDENTIFIER ::= { nm 23 }
   hpnsaPci            OBJECT IDENTIFIER ::= { hpnsa 10 }
   hpnsaPciMibRev      OBJECT IDENTIFIER ::= { hpnsaPci 1 }
   hpnsaPciAgent       OBJECT IDENTIFIER ::= { hpnsaPci 2 }
   hpnsaPciBios        OBJECT IDENTIFIER ::= { hpnsaPci 3 }
   hpnsaPciConfig      OBJECT IDENTIFIER ::= { hpnsaPci 4 }

-- ****************************************************************************
-- HP NSA PCI Information MIB Revision
-- ===================================
--
-- hp                                           (1.3.6.1.4.1.11)
--    nm                                        (hp.2)
--       hpnsa                                  (nm.23)
--          hpnsaPci Group                      (hpnsa.10)
--             hpnsaPciMibRev Group             (hpnsa.10.1)
--                hpnsaPciMibRevMajor           (hpnsa.10.1.1)
--                hpnsaPciMibRevMinor           (hpnsa.10.1.2)
--
-- Implementation of the MibRev group is mandatory for all HPNSA Agents
-- supporting the HP PCI System Information MIB.
--
-- An HPNSA Agent conforming to this document will return a
-- hpnsaPciMibRevMajor of 1 and a hpnsaPciMibRevMinor of 0.
--
-- ****************************************************************************

   hpnsaPciMibRevMajor OBJECT-TYPE
      SYNTAX INTEGER (1..65535)
      ACCESS read-only
      STATUS mandatory
      DESCRIPTION
	 "The major revision level of the MIB."
   ::= { hpnsaPciMibRev 1 }

   hpnsaPciMibRevMinor OBJECT-TYPE
      SYNTAX INTEGER (0..65535)
      ACCESS read-only
      STATUS mandatory
      DESCRIPTION
	 "The minor revision level of the MIB."
   ::= { hpnsaPciMibRev 2 }

-- ****************************************************************************
-- HP NSA PCI Info MIB Agent Information
-- =====================================
--
-- hp                                           (1.3.6.1.4.1.11)
--    nm                                        (hp.2)
--       hpnsa                                  (nm.23)
--          hpnsaPci Group                      (hpnsa.10)
--             hpnsaPciAgent Group              (hpnsa.10.2)
--                hpnsaPciAgentTable            (hpnsa.10.2.1)
--                   hpnsaPciAgentEntry         (hpnsa.10.2.1.1)
--                      hpnsaPciAgentIndex      (hpnsa.10.2.1.1.1)
--                      hpnsaPciAgentName       (hpnsa.10.2.1.1.2)
--                      hpnsaPciAgentVersion    (hpnsa.10.2.1.1.3)
--                      hpnsaPciAgentDate       (hpnsa.10.2.1.1.4)
--
-- Implementation of the PCI Agent group is mandatory for all HPNSA Agents
-- supporting the HP PCI Information MIB.
--
-- ****************************************************************************

   hpnsaPciAgentTable OBJECT-TYPE
      SYNTAX SEQUENCE OF HPnsaPciAgentEntry
      ACCESS not-accessible
      STATUS mandatory
      DESCRIPTION
	 "A table of SNMP agents that satisfy requests for this MIB."
   ::= { hpnsaPciAgent 1 }

   hpnsaPciAgentEntry OBJECT-TYPE
      SYNTAX HPnsaPciAgentEntry
      ACCESS not-accessible
      STATUS mandatory
      DESCRIPTION
	 "A description of the agent/agents that access PCI information."
      INDEX { hpnsaPciAgentIndex }
   ::= { hpnsaPciAgentTable 1 }

   HPnsaPciAgentEntry ::= SEQUENCE {
      hpnsaPciAgentIndex       INTEGER,
      hpnsaPciAgentName        DisplayString,
      hpnsaPciAgentVersion     DisplayString,
      hpnsaPciAgentDate        OCTET STRING
   }

   hpnsaPciAgentIndex OBJECT-TYPE
      SYNTAX INTEGER (0..255)
      ACCESS read-only
      STATUS mandatory
      DESCRIPTION
	 "A unique index for this agent."
   ::= { hpnsaPciAgentEntry 1 }

   hpnsaPciAgentName OBJECT-TYPE
      SYNTAX DisplayString (SIZE (0..255))
      ACCESS read-only
      STATUS mandatory
      DESCRIPTION
	 "Name of the agent/agents satisfying SNMP requests for this MIB."
   ::= { hpnsaPciAgentEntry 2 }

   hpnsaPciAgentVersion OBJECT-TYPE
      SYNTAX DisplayString (SIZE (0..10))
      ACCESS read-only
      STATUS mandatory
      DESCRIPTION
	 "Version number of the agent/agents satisfying SNMP requests for
	 this MIB."
   ::= { hpnsaPciAgentEntry 3 }

   hpnsaPciAgentDate OBJECT-TYPE
      SYNTAX OCTET STRING (SIZE (7))
      ACCESS read-only
      STATUS mandatory
      DESCRIPTION
	 "The date on which this agent was created.

	 field  octets  contents                  range
	 -------------------------------------------------
	    1       1    years since 1900          0..255
	    2       2    month                     1..12
	    3       3    day                       1..31
	    4       4    hour                      0..23
	    5       5    minute                    0..59
	    6       6    second                    0..59"
   ::= { hpnsaPciAgentEntry 4 }

-- ****************************************************************************
-- HP NSA PCI BIOS MIB Information
-- ===============================
--
-- hp                                           (1.3.6.1.4.1.11)
--    nm                                        (hp.2)
--       hpnsa                                  (nm.23)
--          hpnsaPci Group                      (hpnsa.10)
--             hpnsaPciBios Group               (hpnsa.10.3)
--                hpnsaPciBiosPresent           (hpnsa.10.3.1)
--                hpnsaPciBiosVersion           (hpnsa.10.3.2)
--                hpnsaPciBuses                 (hpnsa.10.3.3)
--
-- ****************************************************************************

   hpnsaPciBiosPresent OBJECT-TYPE
      SYNTAX INTEGER {
	 notPresent(0),
	 present(1)
      }
      ACCESS read-only
      STATUS mandatory
      DESCRIPTION
	 "Identifies whether PCI BIOS is present.
	 0 = not present, 1 = PCI BIOS present."
   ::= { hpnsaPciBios 1 }

   hpnsaPciBiosVersion OBJECT-TYPE
      SYNTAX INTEGER
      ACCESS read-only
      STATUS mandatory
      DESCRIPTION
	 "The PCI BIOS version number:
	 low byte = minor version, high byte = major version."
   ::= { hpnsaPciBios 2 }

   hpnsaPciBuses OBJECT-TYPE
      SYNTAX INTEGER (0..255)
      ACCESS read-only
      STATUS mandatory
      DESCRIPTION
	 "Number of PCI buses in the system"
   ::= { hpnsaPciBios 3 }

-- ****************************************************************************
-- HP NSA PCI Configuration Table
-- ==============================
--
-- hp                                           (1.3.6.1.4.1.11)
--    nm                                        (hp.2)
--       hpnsa                                  (nm.23)
--          hpnsaPci Group                      (hpnsa.10)
--             hpnsaPciConfig Group             (hpnsa.10.4)
--                hpnsaPciTable                 (hpnsa.10.4.1)
--                   hpnsaPciEntry              (hpnsa.10.4.1.1)
--                      hpnsaPciBusIndex        (hpnsa.10.4.1.1.1)
--                      hpnsaPciDeviceIndex     (hpnsa.10.4.1.1.2)
--                      hpnsaPciFunctionIndex   (hpnsa.10.4.1.1.3)
--                      hpnsaPciVendorId        (hpnsa.10.4.1.1.4)
--                      hpnsaPciDeviceId        (hpnsa.10.4.1.1.5)
--                      hpnsaPciRevisionId      (hpnsa.10.4.1.1.6)
--                      hpnsaPciHeaderType      (hpnsa.10.4.1.1.7)
--                      hpnsaPciClassCode       (hpnsa.10.4.1.1.8)
--                      hpnsaPciCommand         (hpnsa.10.4.1.1.9)
--                      hpnsaPciStatus          (hpnsa.10.4.1.1.10)
--                      hpnsaPciCacheLineSize   (hpnsa.10.4.1.1.11)
--                      hpnsaPciLatencyTimer    (hpnsa.10.4.1.1.12)
--                      hpnsaPciBist            (hpnsa.10.4.1.1.13)
--                      hpnsaPciInterruptLine   (hpnsa.10.4.1.1.14)
--                      hpnsaPciInterruptPin    (hpnsa.10.4.1.1.15)
--                      hpnsaPciMaxLat          (hpnsa.10.4.1.1.16)
--                      hpnsaPciMinGnt          (hpnsa.10.4.1.1.17)
--                      hpnsaPciBaseAddrRegs    (hpnsa.10.4.1.1.18)
--                      hpnsaPciExpRomBaseAddr  (hpnsa.10.4.1.1.19)
--                      hpnsaPciDeviceSpecific  (hpnsa.10.4.1.1.20)
--
-- Implementation of the PCI Config Table is mandatory for all
-- HPNSA Agents supporting the HP PCI information MIB.
--
-- ****************************************************************************

   hpnsaPciTable OBJECT-TYPE
      SYNTAX SEQUENCE OF HpnsaPciEntry
      ACCESS not-accessible
      STATUS mandatory
      DESCRIPTION
	 "A list of PCI device/functions entries."
   ::= { hpnsaPciConfig 1 }

   hpnsaPciEntry OBJECT-TYPE
      SYNTAX HpnsaPciEntry
      ACCESS not-accessible
      STATUS mandatory
      DESCRIPTION
	 "A description of an PCI device/function."
      INDEX { hpnsaPciBusIndex, hpnsaPciDeviceIndex,
	 hpnsaPciFunctionIndex }
   ::= { hpnsaPciTable 1 }

   HpnsaPciEntry ::= SEQUENCE {
      hpnsaPciBusIndex              INTEGER (0..255),        -- mandatory
      hpnsaPciDeviceIndex           INTEGER (0..31),         -- mandatory
      hpnsaPciFunctionIndex         INTEGER (0..7),          -- mandatory
      hpnsaPciVendorId              INTEGER,                 -- mandatory
      hpnsaPciDeviceId              INTEGER,                 -- mandatory
      hpnsaPciRevisionId            INTEGER,                 -- mandatory
      hpnsaPciHeaderType            INTEGER (0..255),        -- mandatory
      hpnsaPciClassCode             OCTET STRING (SIZE (3)), -- mandatory
      hpnsaPciCommand               INTEGER,                 -- r/w?
      hpnsaPciStatus                INTEGER,                 -- r/w to reset?
      hpnsaPciCacheLineSize         INTEGER (0..255),        -- r/w?
      hpnsaPciLatencyTimer          INTEGER (0..255),
      hpnsaPciBist                  INTEGER (0..255),        -- r/w?
      hpnsaPciInterruptLine         INTEGER (0..255),
      hpnsaPciInterruptPin          INTEGER (0..255),
      hpnsaPciMaxLat                INTEGER (0..255),
      hpnsaPciMinGnt                INTEGER (0..255),
      hpnsaPciBaseAddrRegs          OCTET STRING (SIZE (24)),
      hpnsaPciExpRomBaseAddr        OCTET STRING (SIZE (4)),
      hpnsaPciDeviceSpecific        OCTET STRING (SIZE (192))
    }

   hpnsaPciBusIndex OBJECT-TYPE
      SYNTAX INTEGER (0..255)
      ACCESS read-only
      STATUS mandatory
      DESCRIPTION
	 "The PCI Bus number that this entry describes."
   ::= { hpnsaPciEntry 1 }

   hpnsaPciDeviceIndex OBJECT-TYPE
      SYNTAX INTEGER (0..31)
      ACCESS read-only
      STATUS mandatory
      DESCRIPTION
	 "The PCI device or slot number that this entry describes."
   ::= { hpnsaPciEntry 2 }

   hpnsaPciFunctionIndex OBJECT-TYPE
      SYNTAX INTEGER (0..7)
      ACCESS read-only
      STATUS mandatory
      DESCRIPTION
	 "The PCI function that this entry describes."
   ::= { hpnsaPciEntry 3 }

   hpnsaPciVendorId OBJECT-TYPE
      SYNTAX INTEGER {
	ati-technologies-inc                       (4098),
	ulsi-systems                               (4099),
	vlsi-technology-inc                        (4100),
	avance-logics-inc                          (4101),
	reply-group                                (4102),
	netframe-systems-inc                       (4103),
	epson                                      (4104),
	phoenix-technologies                       (4106),
	national-semiconductor                     (4107),
	tseng-labs-inc                             (4108),
	ast-research-inc                           (4109),
	weitek                                     (4110),
	video-logic-ltd                            (4112),
	dec                                        (4113),
	micronics-computers-inc                    (4114),
	cirrus-logic                               (4115),
	ibm                                        (4116),
	icl-personal-systems                       (4118),
	spea-software-ag                           (4119),
	unisys-systems                             (4120),
	elitegroup-computer-sys                    (4121),
	ncr                                        (4122),
	vitesse-semiconductor                      (4123),
	western-digital                            (4124),
	american-megatrends                        (4126),
	picture-tel                                (4127),
	hitachi-computer-products                  (4128),
	oki-electric-industry                      (4129),
	advanced-micro-devices                     (4130),
	trident-microsystems                       (4131),
	zenith-data-systems                        (4132),
	acer-incorporated                          (4133),
	dell-computer-corporation                  (4136),
	siemens-nixdorf-is-ag                      (4137),
	matrox                                     (4139),
	chips-and-technologies                     (4140),
	wyse-technology                            (4141),
	olivetti-advanced-technology               (4142),
	toshiba-america-elect                     (4143),
	tmc-research                               (4144),
	miro-computer-products-ag                  (4145),
	compaq                                     (4146),
	nec-corporation                            (4147),
	burndy-corporation                         (4148),
	comp-comm-resh-lab                     (4149),
	future-domain                              (4150),
	hitachi-micro-systems                      (4151),
	amp-inc                                   (4152),
	silicon-integrated-system                  (4153),
	seiko-epson-corporation                    (4154),
	tatung-co-of-america                      (4155),
	hewlett-packard                            (4156),
	solliday-engineering                       (4158),
	logic-modeling                             (4159),
	kubota-pacific-computer-inc               (4160),
	computrend                                 (4161),
	pc-technology-inc                          (4162),
	asustek-computer-inc                     (4163),
	distributed-processing-technology          (4164),
	opti                                       (4165),
	ipc-corporation-ltd                      (4166),
	genoa-systems-corp                         (4167),
	elsa-gmbh                                  (4168),
	fountain-technology                        (4169),
	sgs-thomson-microelectric                  (4170),
	buslogic                                   (4171),
	texas-instruments                          (4172),
	sony-corporation                           (4173),
	oak-technology-inc                        (4174),
	co-time-computer-ltd                       (4175),
	winbond-electronics-corp                   (4176),
	anigma-inc                               (4177),
	young-micro-systems                        (4178),
	hitachi-ltd                               (4180),
	efar-microsystems                          (4181),
	icl                                        (4182),
	motorola-computer                          (4183),
	electronics-telec-rsh                   (4184),
	teknor-microsystems                        (4185),
	promise-technology                         (4186),
	foxconn-international                      (4187),
	wipro-infotech-limited                     (4188),
	number-9-computer-company                  (4189),
	vtech-computers-limites                   (4190),
	infotronic-america-inc                     (4191),
	united-microelectronics                    (4192),
	i-t-t                                     (4193),
	maspar-computer-corp                       (4194),
	ocean-office-automation                    (4195),
	alcatel-cit                                (4196),
	texas-microsystems                         (4197),
	picopower-technology                       (4198),
	mitsubishi-electronics                     (4199),
	diversified-technology                     (4200),
	mylex-corporation                          (4201),
	aten-research-inc                          (4202),
	apple-computer-inc                        (4203),
	madge-networks                             (4203),
	hyundai-electronics-ameri                  (4204),
	sequent                                    (4205),
	dfi-inc                                   (4206),
	city-gate-development-ltd                  (4207),
	daewoo-telecom-ltd                         (4208),
	mitac                                      (4209),
	git-co-ltd                                 (4210),
	yamaha-corporation                         (4211),
	nexgen-microsysteme                        (4212),
	advanced-integration-res                  (4213),
	chaintech-computer-co-ltd                  (4214),
	q-logic                                    (4215),
	cyrix-corporation                          (4216),
	i-bus                                      (4217),
	networth                                   (4218),
	gateway-2000                               (4219),
	goldstar-co-ltd                          (4220),
	leadtek-research-inc                      (4221),
	interphase-corporation                     (4222),
	data-technology-corporation                (4223),
	contaq-microsystems-inc                   (4224),
	supermac-technology-inc                    (4225),
	efa-corporation-of-america                 (4226),
	forex-computer-corporation                 (4227),
	parador                                    (4228),
	tulip-computers-int-bv                   (4229),
	j-bond-computer-systems                   (4230),
	cache-computer                             (4231),
	microcomputer-systems-m-son               (4232),
	data-general-corporation                   (4233),
	bit3-computer                              (4234),
	oakleigh-systems-inc                      (4236),
	olicom                                     (4237),
	systemsoft-corporation                     (4239),
	encore-computer-corporation                (4240),
	intergraph-corporation                     (4241),
	diamond-computer-systems                   (4242),
	national-instruments                       (4243),
	first-intl-computers                      (4244),
	cmd-technology-inc                         (4245),
	alacron                                    (4246),
	appian-technology-inc                     (4247),
	quantum-designs-hk-ltd                   (4248),
	samsung-electronics-co-ltd               (4249),
	packard-bell                               (4250),
	gemlight-computer-ltd                     (4251),
	megachips-corporation                      (4252),
	zida-technologies-ltd                     (4253),
	brooktree-corporation                      (4254),
	trigem-computer-inc                       (4255),
	meidensha-corporation                      (4256),
	juko-electronics-ind-co-ltd              (4257),
	quantum-corporation                        (4258),
	everex-systems-inc                         (4259),
	globe-manufacturing-sales                  (4260),
	racal-interlan                             (4261),
	informtech-industrial-ltd                 (4262),
	benchmarq-microelectronics                 (4263),
	sierra-semiconductor                       (4264),
	silicon-graphics                           (4265),
	acc-microelectronics-corp                 (4266),
	digicom                                    (4267),
	honeywell-iasd                             (4268),
	symphony-labs                              (4269),
	cornerstone-technology                     (4270),
	micro-computer-sysytems-inc                (4271),
	cardexpert-technology                      (4272),
	cabletron-systems-inc                      (4273),
	raytheon-company                           (4274),
	databook-inc                               (4275),
	stb-systems-inc                            (4276),
	plx-technology                             (4277),
	three-3com-corporation                           (4279),
	standard-microsystems-corporation          (4280),
	acer-labs                                  (4281),
	mitsubishi-electronics-corp               (4282),
	dapha-electronics-corporation              (4283),
	advanced-logic-research-inc                (4284),
	surecom-technology                         (4285),
	tsenglabs-international-co                (4286),
	most-inc                                   (4287),
	boca-research-inc                         (4288),
	icm-co-ltd                              (4289),
	auspex-systems-inc                        (4290),
	samsung-semiconductors                     (4291),
	award-software-intl-inc                  (4292),
	xerox-corporation                          (4293),
	rambus-inc                                (4294),
	media-vision                               (4295),
	neomagic-corporation                       (4296),
	dataexpert-corporation                     (4297),
	fujitsu                                    (4298),
	omron-corporation                          (4299),
	mentor-arc-inc                             (4300),
	advanced-system-products                   (4301),
	radius-inc                                (4302),
	citicorp-tti                               (4303),
	fujitsu-limited                            (4304),
	future-systems                            (4305),
	molex-incorporated                         (4306),
	jabil-circuit-inc                          (4307),
	hualon-microelectronics                    (4308),
	autologic-inc                             (4309),
	cetia                                      (4310),
	advanced-peripherals-labs                  (4312),
	macronix-international-co-ltd           (4313),
	thomas-conrad-corporation                  (4314),
	rohm-research                              (4315),
	cern-ecp-edu                               (4316),
	evans-sutherland                         (4317),
	nvidia-corporation                         (4318),
	emulex-corporation                         (4319),
	integrated-micro-solutions-inc            (4320),
	tekram-technology-co-ltd                 (4321),
	aptix-corporation                          (4322),
	newbridge-microsystems                     (4323),
	tandem-computers                           (4324),
	micro-industries-corporation               (4325),
	gainbery-computer-products-inc            (4326),
	vadem                                      (4327),
	applied-micro-circuits-corporation         (4328),
	alps-electric-co-ltd                     (4329),
	integraphics-systems                       (4330),
	artists-graphics                           (4331),
	realtek-semiconductor-co-ltd            (4332),
	ascii-corporation                          (4333),
	xilinx-corporation                         (4334),
	racore-computer-products-inc             (4335),
	peritek-corporation                        (4336),
	tyan-computer                              (4337),
	achme-computer-inc                        (4338),
	alaris-inc                               (4339),
	s-mos-systems                              (4340),
	nkk-corporation                            (4341),
	creative-electronic-systems-sa             (4342),
	matsushita-electric-industrial-co-ltd   (4343),
	altos-india-ltd                            (4344),
	pc-direct                                  (4345),
	truevision                                 (4346),
	thesys-ges-f-mikroelektronik-mgh         (4347),
	i-o-data-device-inc                      (4348),
	soyo-technology-co-ltd                  (4349),
	fast-electronic-gmbh                       (4350),
	ncube                                      (4351),
	jazz-multimedia                            (4352),
	initio-corporation                         (4353),
	creative-labs                              (4354),
	triones-technologies-inc                 (4355),
	rasterops                                  (4356),
	sigma-designs-inc                         (4357),
	via-technologies-inc                     (4358),
	stratus-computer                           (4359),
	proteon-inc                              (4360),
	cogent-data-technologies                   (4361),
	xenon-microsystems                         (4363),
	mini-max-technology-inc                  (4364),
	znyx-advanced-systems                      (4365),
	cpu-technology                             (4366),
	ross-technology                            (4367),
	powerhouse-systems                         (4368),
	santa-cruz-operation                       (4369),
	rockwell-network-systems                   (4370),
	accton-technology-corporation              (4371),
	atmel-corp                                 (4372),
	three-3dlabs                                     (4373),
	data-translation                           (4374),
	datacube-inc                              (4375),
	berg-electronics                           (4376),
	vortex-computersysteme-gmbh                (4377),
	efficent-networks-inc                    (4378),
	teledyne-electronic-systems                (4379),
	tricord-systems-inc                      (4380),
	integrated-device-tech                     (4381),
	eldec-corporaton                           (4382),
	prescision-digital-images                  (4383),
	emc-corporation                            (4384),
	zilog                                      (4385),
	multi-tech-systems-inc                   (4386),
	leutron-vision-ag                          (4388),
	eurocore                                   (4389),
	vigra                                      (4389),
	firmworks                                  (4393),
	hermes-electronics-co-ltd               (4394),
	linotype-hell-ag                         (4395),
	ravicad                                    (4397),
	infomedia-microelectronics-inc            (4398),
	imaging-technology-inc                     (4399),
	computervision                             (4400),
	philips-semiconductors                     (4401),
	mitel-corp                                 (4402),
	eicon-technology-corporation               (4403),
	mercury-computer-systems-inc               (4404),
	fuji-xerox-co-ltd                          (4405),
	momentum-data-systems                      (4406),
	cisco-systems-inc                          (4407),
	ziatech-corporation                        (4408),
	dynamic-pictures-inc                       (4409),
	fwb-inc                                    (4410),
	cyclone-micro                              (4412),
	leading-edge-products-inc                  (4413),
	sanyo-electric-co                          (4414),
	equinox-systems                            (4415),
	intervoice-inc                             (4416),
	crest-microsystem-inc                      (4417),
	alliance-semiconductor-corporation         (4418),
	netpower-inc                              (4419),
	cincinnati-milacron                        (4420),
	workbit-corp                               (4421),
	force-computers                            (4422),
	interface-corp                             (4423),
	schneider-koch-co                       (4424),
	win-system-corporation                     (4425),
	vmic                                       (4426),
	canopus-co-ltd                           (4427),
	annabooks                                  (4428),
	ic-corporation                             (4429),
	nikon-systems-inc                          (4430),
	digi-international                         (4431),
	thinking-machines-corp                     (4432),
	jae-electronics-inc                       (4433),
	megatek                                    (4434),
	land-win-electronic-corp                   (4435),
	melco-inc                                  (4436),
	pine-technology-ltd                        (4437),
	periscope-engineering                      (4438),
	s3-inc                                    (21299),
	netpower                                   (22272)
      }
      ACCESS read-only
      STATUS mandatory
      DESCRIPTION
	 "Identifies the manufacturer of the device. 0xFFFF is an
	 invalid value for a vendor ID.

		Vendor ID       Manufacturer
		---------       ------------
		  XXXX          Hewlett-Packard Co."
   ::= { hpnsaPciEntry 4 }

   hpnsaPciDeviceId OBJECT-TYPE
      SYNTAX INTEGER
      ACCESS read-only
      STATUS mandatory
      DESCRIPTION
	 "Identifies the particular device. This identier is allocated
	 by the vendor.

		Device ID       Description
		---------       ------------
		  XXXX          Blah! Blah!"
	::= { hpnsaPciEntry 5 }

   hpnsaPciRevisionId OBJECT-TYPE
      SYNTAX INTEGER
      ACCESS read-only
      STATUS mandatory
      DESCRIPTION
	 "Specifies a device specific revision identifier."
   ::= { hpnsaPciEntry 6 }

   hpnsaPciHeaderType OBJECT-TYPE
      SYNTAX INTEGER (0..255)
      ACCESS read-only
      STATUS mandatory
      DESCRIPTION
	 "Idendifies the layout of bytes 10h-3Fh in configuration
	 space and whether or not the device contains multiple
	 functions.

	 Bit 7:    1=multi-function device, 0=single function
	 Bit 6-0:  Defines layout, 0 is only layout defined,
		   all other values are reserved."
   ::= { hpnsaPciEntry 7 }

   hpnsaPciClassCode OBJECT-TYPE
      SYNTAX OCTET STRING (SIZE (3))      
      ACCESS read-only
      STATUS mandatory
      DESCRIPTION
	 "Identifies the generic function of the device.

	Base    Sub-    Prog
	Class   Class   If.    Meaning
	-----   -----   -----  -------
	 00h                   Device built before Class Code
				  definitions were finalized.
		 00h     00h   All currently implemented devices
				  except VGA compatible devices.
		 01h     00h   VGA compatible device

	 01h                   Mass Storage controller
		 00h     00h      SCSI bus controller
		 01h     00h      IDE controller
		 02h     00h      Floppy disk controller
		 03h     00h      IPI bus controller
		 80h     00h      Other mass storage controller

	 02h                   Network controller
		 00h    00h       Ethernet controller
		 01h    00h       Token Ring controller
		 02h    00h       FDDI controller
		 80h    00h       Other network controller

	 03h                   Display controller
		 00h    00h       VGA compatible controller
		 01h    00h       XGA controller
		 80h    00h       Other display controller

	 04h                   Multimedia device
		 00h    00h       Video
		 01h    00h       Audio
		 80h    00h       Other multimedia device

	 05h                   Memory controller
		 00h    00h       RAM
		 01h    00h       Flash
		 80h    00h       Other memory controller

	 06h                   Bridge device
		 00h    00h       Host bridge
		 01h    00h       ISA bridge
		 02h    00h       EISA bridge
		 03h    00h       MC bridge
		 04h    00h       PCI-to-PCI bridge
		 05h    00h       PCMCIA bridge
		 80h    00h       Other bridge device

	 07h-FEh               Reserved
	 FFh                   Device does not fit in any
				 defined classes."
   ::= { hpnsaPciEntry 8 }

   hpnsaPciCommand OBJECT-TYPE
      SYNTAX INTEGER
      ACCESS read-only
      STATUS mandatory
      DESCRIPTION
	 "Provides course control over a device's ability to generate
	 and respond to PCI cylces.

	 Bit     Description
	 ---     ------------
	  0      IO Space
	  1      Memory Space
	  2      Bus Master
	  3      Special Cycles
	  4      Memory Write and Invlaidate Enable
	  5      VGA Palette snoop
	  6      Parity Error Response
	  7      Wait cycle control
	  8      SERR# enable
	  9      Fast Back-to-Back Enable
	10-15    Reserved"

   ::= { hpnsaPciEntry 9 }

   hpnsaPciStatus OBJECT-TYPE
      SYNTAX INTEGER
      ACCESS read-only
      STATUS mandatory
      DESCRIPTION
	 "Status information for PCI bus related events.

	 Bit     Description
	 ---     ------------
	 0-6     Reserved
	  7      Fast Back-to-Back Capable
	  8      Data Parity Detected
	 9-10    DEVSEL timing; 00=fast, 01=medium, 10=slow
	 11      Signal Target Abort
	 12      Received Target Abort
	 13      Received Master Abort
	 14      Signaled System Error
	 15      Detected Parity Error"
   ::= { hpnsaPciEntry 10 }

   hpnsaPciCacheLineSize OBJECT-TYPE
      SYNTAX INTEGER (0..255)
      ACCESS read-only
      STATUS mandatory
      DESCRIPTION
	 "Specifies the system cache line size in units of 32-bit words."
   ::= { hpnsaPciEntry 11 }

   hpnsaPciLatencyTimer OBJECT-TYPE
      SYNTAX INTEGER (0..255)
      ACCESS read-only
      STATUS mandatory
      DESCRIPTION
	 "Specifies, in units of PCI bus clocks, the value of the
	 Latency Timer for this PCI bus master."
      ::= { hpnsaPciEntry 12 }

   hpnsaPciBist OBJECT-TYPE
      SYNTAX INTEGER (0..255)
      ACCESS read-only
      STATUS mandatory
      DESCRIPTION
	 "This optional register is used for control and status
	 of Built-in Self Test. Devices that don't support BIST
	 must always return a value of 0.

	 Bit     Description
	 ---     ------------
	  7      0=BIST not supported, 1=BIST supported
	  6      Wrtie a 1 to invoke BIST. Devices resets the
		 bit when BIST is complet. Software should fail
		 device if BIST is not complete after 2 seconds.
	 5-4     Reserved
	 3-0     0=Device passed test, non-zero= device-specific
		 failure code."
   ::= { hpnsaPciEntry 13 }

   hpnsaPciInterruptLine OBJECT-TYPE
      SYNTAX INTEGER (0..255)
      ACCESS read-only
      STATUS mandatory
      DESCRIPTION
	 "Communicates interrupt line routing information. The value
	 in this register tells which input of the system interrupt
	 contoller(s) the device's interrupt pin is connected to."
   ::= { hpnsaPciEntry 14 }

   hpnsaPciInterruptPin OBJECT-TYPE
      SYNTAX INTEGER (0..255)
      ACCESS read-only
      STATUS mandatory
      DESCRIPTION
	 "Tells which interrupt pin the device uses."
   ::= { hpnsaPciEntry 15 }

   hpnsaPciMaxLat OBJECT-TYPE
      SYNTAX INTEGER (0..255)
      ACCESS read-only
      STATUS mandatory
      DESCRIPTION
	 "Specifies how often the device needs to gain access to
	 the PCI bus."
   ::= { hpnsaPciEntry 16 }

   hpnsaPciMinGnt OBJECT-TYPE
      SYNTAX INTEGER (0..255)
      ACCESS read-only
      STATUS mandatory
      DESCRIPTION
	 "Specifies how long a burst period the device needs assuming
	 a clock rate of 33MHz."
   ::= { hpnsaPciEntry 17 }

   hpnsaPciBaseAddrRegs OBJECT-TYPE
      SYNTAX OCTET STRING (SIZE (24))
      ACCESS read-only
      STATUS mandatory
      DESCRIPTION
	 "Base address mapping registers for memory and IO. Refer
	 to the PCI specification for the format."
   ::= { hpnsaPciEntry 18 }

   hpnsaPciExpRomBaseAddr OBJECT-TYPE
      SYNTAX OCTET STRING (SIZE (4))
      ACCESS read-only
      STATUS mandatory
      DESCRIPTION
	 "4-byte register is defined to handle the base address
	 and size information for an expansion ROM.

	 Bit     Description
	 ---     ------------
	31-11    Expansion ROM Base Address (upper 21 bits)
	10-1     Reserved
	  0      0 = address decoding is disabled and no access
		     to this space are allowed.
		 1 = address decoding enabled."
   ::= { hpnsaPciEntry 19 }

   hpnsaPciDeviceSpecific OBJECT-TYPE
      SYNTAX OCTET STRING (SIZE (192))
      ACCESS read-only
      STATUS mandatory
      DESCRIPTION
	 "Device specific configuration space."
   ::= { hpnsaPciEntry 20 }

END
