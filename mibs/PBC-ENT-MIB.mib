--
-- PBC-ENT-MIB.mib
-- MIB generated by MG-SOFT Visual MIB Builder Version 3.0 Build 253
-- Tuesday, October 08, 2002 at 13:00:44
--

	PBC-ENT-MIB DEFINITIONS ::= BEGIN
 
		IMPORTS
			enterprises			
				FROM RFC1155-SMI			
			MODULE-IDENTITY, OBJECT-IDENTITY			
				FROM SNMPv2-SMI;
	
	
		pacificBroadband MODULE-IDENTITY 
			LAST-UPDATED "200109251842Z"		-- September 25, 2001 at 18:42 GMT
			ORGANIZATION 
				"Juniper Networks, Inc"
			CONTACT-INFO 
				"Juniper Technical Assistance Center
				Juniper Networks, Inc.
				1194 N. Mathilda Avenue
				Sunnyvale, CA 94089
				E-mail: support@juniper.net
				Phone:  1 888 JUNIPER
				"
			DESCRIPTION 
				"This module defines the enterprise managed object space
				for cable products from Juniper Networks, Inc.
				(C)opyright 2001, Juniper Networks, Inc."
			REVISION "200210081238Z"		-- October 08, 2002 at 12:38 GMT
			DESCRIPTION
				"G10 CMTS Miscellaneous R2.1.3 Functional Enhancements Functional Specification.
				"
			REVISION "200209251730Z"		-- September 25, 2002 at 17:30 GMT
			DESCRIPTION
				"EME v1.9"
			REVISION "200209231847Z"		-- September 23, 2002 at 18:47 GMT
			DESCRIPTION
				"EME-Functional Spec v1.8
				CME-Functional Spec v1.1"
			::= { enterprises 5987 }
		
	
--
-- Node definitions
--
	
		-- 1.3.6.1.4.1.5987.1
		pbcRegs OBJECT-IDENTITY
			STATUS current
			DESCRIPTION 
				"Sub-tree for PBC registrations"
			::= { pacificBroadband 1 }
		
		-- 1.3.6.1.4.1.5987.1.1
		pbcModuleRegs OBJECT-IDENTITY
			STATUS current
			DESCRIPTION 
				"Sub-tree to register the values assigned to
				modules with the MODULE-IDENTITY construct"
			::= { pbcRegs 1 }
		
		-- 1.3.6.1.4.1.5987.2
		pbcManagement OBJECT-IDENTITY
			STATUS current
			DESCRIPTION 
				"Assorted common management MIBs go here."
			::= { pacificBroadband 2 }
		
		-- 1.3.6.1.4.1.5987.3
		pbcProducts OBJECT-IDENTITY
			STATUS current
			DESCRIPTION 
				"Sub-tree for product-specific object and
				event definitions"
			::= { pacificBroadband 3 }
		
		-- 1.3.6.1.4.1.5987.4
		pbcCaps OBJECT-IDENTITY
			STATUS current
			DESCRIPTION 
				"Sub-tree for agent profiles (defined
				with AGENT-CAPABILITIES construct)"
			::= { pacificBroadband 4 }
		
		-- 1.3.6.1.4.1.5987.5
		pbcReqs OBJECT-IDENTITY
			STATUS current
			DESCRIPTION 
				"Sub-tree for management application requirements
				(defined with MODULE-COMPLIANCE construct)"
			::= { pacificBroadband 5 }
		
		-- 1.3.6.1.4.1.5987.6
		pbcExpr OBJECT-IDENTITY
			STATUS current
			DESCRIPTION 
				"Sub-tree for experimental definitions"
			::= { pacificBroadband 6 }
		
	
	END

--
-- PBC-ENT-MIB.mib
--
