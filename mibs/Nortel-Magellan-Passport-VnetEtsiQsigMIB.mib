Nortel-Magellan-Passport-VnetEtsiQsigMIB
DEFINITIONS ::= BEGIN



IMPORTS

      OBJECT-TYPE
   FROM RFC-1212

      passportMIBs
   FROM Nortel-Magellan-Passport-UsefulDefinitionsMIB

      DisplayString,
      StorageType,
      RowStatus,
      Unsigned32
   FROM Nortel-Magellan-Passport-StandardTextualConventionsMIB

      NonReplicated,
      Link
   FROM Nortel-Magellan-Passport-TextualConventionsMIB

      sigChanIndex,
      sigChan
   FROM Nortel-Magellan-Passport-VoiceNetworkingMIB;




-- LAST-UPDATED   "9904150000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VnetEtsiQsig Enterprise MIB."

vnetEtsiQsigMIB OBJECT IDENTIFIER ::= { passportMIBs 110 }










-- SigChan/n EtsiQsig
-- The EtsiQsig component defines the operational characteristics of 
-- the signalling channel's connection to the external equipment.

sigChanEQsig OBJECT IDENTIFIER ::= { sigChan 2 }



sigChanEQsigRowStatusTable OBJECT-TYPE
   SYNTAX     SEQUENCE OF SigChanEQsigRowStatusEntry
   ACCESS     not-accessible
   STATUS     mandatory
   DESCRIPTION
     "This entry controls the addition and deletion of 
      sigChanEQsig components."
::= { sigChanEQsig 1 }

sigChanEQsigRowStatusEntry OBJECT-TYPE
   SYNTAX     SigChanEQsigRowStatusEntry
   ACCESS     not-accessible
   STATUS     mandatory
   DESCRIPTION
     "A single entry in the table represents a single 
      sigChanEQsig component."
   INDEX {
      sigChanIndex,
      sigChanEQsigIndex }
::= { sigChanEQsigRowStatusTable 1 }

SigChanEQsigRowStatusEntry ::= SEQUENCE {
   sigChanEQsigRowStatus
      RowStatus,
   sigChanEQsigComponentName
      DisplayString,
   sigChanEQsigStorageType
      StorageType,
   sigChanEQsigIndex
      NonReplicated }

sigChanEQsigRowStatus OBJECT-TYPE
   SYNTAX     RowStatus 
   ACCESS     read-write
   STATUS     mandatory
   DESCRIPTION
     "This variable is used as the basis for SNMP naming of
      sigChanEQsig components.
      These components can be added and deleted."
::= { sigChanEQsigRowStatusEntry 1 }

sigChanEQsigComponentName OBJECT-TYPE
   SYNTAX     DisplayString 
   ACCESS     read-only
   STATUS     mandatory
   DESCRIPTION
     "This variable provides the component's string name for
      use with the ASCII Console Interface"
::= { sigChanEQsigRowStatusEntry 2 }

sigChanEQsigStorageType OBJECT-TYPE
   SYNTAX     StorageType 
   ACCESS     read-only
   STATUS     mandatory
   DESCRIPTION
     "This variable represents the storage type value for the
      sigChanEQsig tables."
::= { sigChanEQsigRowStatusEntry 4 }

sigChanEQsigIndex OBJECT-TYPE
   SYNTAX     NonReplicated 
   ACCESS     not-accessible
   STATUS     mandatory
   DESCRIPTION
     "This variable represents the index for the sigChanEQsig tables."
::= { sigChanEQsigRowStatusEntry 10 }

sigChanEQsigL2Table OBJECT-TYPE
   SYNTAX     SEQUENCE OF SigChanEQsigL2Entry
   ACCESS     not-accessible
   STATUS     mandatory
   DESCRIPTION
     "This group specifies the provisionable layer 2 attributes of the 
      Q.931 ITU-T protocol."
::= { sigChanEQsig 11 }

sigChanEQsigL2Entry OBJECT-TYPE
   SYNTAX     SigChanEQsigL2Entry
   ACCESS     not-accessible
   STATUS     mandatory
   DESCRIPTION
     "An entry in the sigChanEQsigL2Table."
   INDEX {
      sigChanIndex,
      sigChanEQsigIndex }
::= { sigChanEQsigL2Table 1 }

SigChanEQsigL2Entry ::= SEQUENCE {
   sigChanEQsigT23
      Unsigned32,
   sigChanEQsigT200
      Unsigned32,
   sigChanEQsigN200
      Unsigned32,
   sigChanEQsigT203
      Unsigned32,
   sigChanEQsigCircuitSwitchedK
      Unsigned32 }

sigChanEQsigT23 OBJECT-TYPE
   SYNTAX     Unsigned32 (1..15)
   ACCESS     read-write
   STATUS     mandatory
   DESCRIPTION
     "This attribute specifies the layer 2 enable request timer."
   DEFVAL     { 10 }
::= { sigChanEQsigL2Entry 1 }

sigChanEQsigT200 OBJECT-TYPE
   SYNTAX     Unsigned32 (1..20)
   ACCESS     read-write
   STATUS     mandatory
   DESCRIPTION
     "This attribute specifies the maximum time between a layer 2 frame 
      and its acknowledgment."
   DEFVAL     { 1 }
::= { sigChanEQsigL2Entry 2 }

sigChanEQsigN200 OBJECT-TYPE
   SYNTAX     Unsigned32 (1..8)
   ACCESS     read-write
   STATUS     mandatory
   DESCRIPTION
     "This attribute specifies the maximum number of re-transmissions of 
      a layer 2 frame."
   DEFVAL     { 3 }
::= { sigChanEQsigL2Entry 3 }

sigChanEQsigT203 OBJECT-TYPE
   SYNTAX     Unsigned32 (2..40)
   ACCESS     read-write
   STATUS     mandatory
   DESCRIPTION
     "This attribute specifies the maximum time for which layer 2 frames 
      may be absent. Expiry triggers a check on whether the far end is 
      alive."
   DEFVAL     { 10 }
::= { sigChanEQsigL2Entry 4 }

sigChanEQsigCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { sigChanEQsigL2Entry 6 }

sigChanEQsigL3Table OBJECT-TYPE
   SYNTAX     SEQUENCE OF SigChanEQsigL3Entry
   ACCESS     not-accessible
   STATUS     mandatory
   DESCRIPTION
     "This group represents the provisionable Layer 3 timer attributes of 
      the ETSI Qsig protocol."
::= { sigChanEQsig 12 }

sigChanEQsigL3Entry OBJECT-TYPE
   SYNTAX     SigChanEQsigL3Entry
   ACCESS     not-accessible
   STATUS     mandatory
   DESCRIPTION
     "An entry in the sigChanEQsigL3Table."
   INDEX {
      sigChanIndex,
      sigChanEQsigIndex }
::= { sigChanEQsigL3Table 1 }

SigChanEQsigL3Entry ::= SEQUENCE {
   sigChanEQsigT309
      Unsigned32,
   sigChanEQsigT310
      Unsigned32 }

sigChanEQsigT309 OBJECT-TYPE
   SYNTAX     Unsigned32 (15..120)
   ACCESS     read-write
   STATUS     mandatory
   DESCRIPTION
     "This attribute specifies the data link failure timer; used to ride out 
      temporary failures."
   DEFVAL     { 90 }
::= { sigChanEQsigL3Entry 3 }

sigChanEQsigT310 OBJECT-TYPE
   SYNTAX     Unsigned32 (10..120)
   ACCESS     read-write
   STATUS     mandatory
   DESCRIPTION
     "This attribute specifies the call proceeding state timer."
   DEFVAL     { 30 }
::= { sigChanEQsigL3Entry 4 }

sigChanEQsigProvTable OBJECT-TYPE
   SYNTAX     SEQUENCE OF SigChanEQsigProvEntry
   ACCESS     not-accessible
   STATUS     mandatory
   DESCRIPTION
     "This group defines the general options of the D-channel signalling 
      link."
::= { sigChanEQsig 13 }

sigChanEQsigProvEntry OBJECT-TYPE
   SYNTAX     SigChanEQsigProvEntry
   ACCESS     not-accessible
   STATUS     mandatory
   DESCRIPTION
     "An entry in the sigChanEQsigProvTable."
   INDEX {
      sigChanIndex,
      sigChanEQsigIndex }
::= { sigChanEQsigProvTable 1 }

SigChanEQsigProvEntry ::= SEQUENCE {
   sigChanEQsigSide
      INTEGER,
   sigChanEQsigMaxNonCallConcurrent
      Unsigned32,
   sigChanEQsigOverlapSendingEnabled
      INTEGER,
   sigChanEQsigOverlapReceivingEnabled
      INTEGER }

sigChanEQsigSide OBJECT-TYPE
   SYNTAX     INTEGER  {
                 network(1),
                 user(2) }
   ACCESS     read-write
   STATUS     mandatory
   DESCRIPTION
     "This attribute specifies whether the interface is the network or user 
      side of the connection. The parameter applies to both the layer 2 
      and layer 3 of the interface. If this attribute is set to network, then 
      the interface is master during channel negotiation. If this attribute is 
      set to user, then the interface is slave during channel negotiation."
   DEFVAL     { network }
::= { sigChanEQsigProvEntry 1 }

sigChanEQsigMaxNonCallConcurrent OBJECT-TYPE
   SYNTAX     Unsigned32 (1..30)
   ACCESS     read-write
   STATUS     mandatory
   DESCRIPTION
     "This attribute specifies the maximum number of simultaneous active 
      non-call messages that are allowed."
   DEFVAL     { 30 }
::= { sigChanEQsigProvEntry 2 }

sigChanEQsigOverlapSendingEnabled OBJECT-TYPE
   SYNTAX     INTEGER  {
                 enabled(0),
                 disabled(1) }
   ACCESS     read-write
   STATUS     mandatory
   DESCRIPTION
     "This attribute specifies whether overlap sending to the PBX is 
      enabled."
   DEFVAL     { enabled }
::= { sigChanEQsigProvEntry 3 }

sigChanEQsigOverlapReceivingEnabled OBJECT-TYPE
   SYNTAX     INTEGER  {
                 enabled(0),
                 disabled(1) }
   ACCESS     read-write
   STATUS     mandatory
   DESCRIPTION
     "This attribute specifies whether overlap receiving from the PBX is 
      enabled."
   DEFVAL     { enabled }
::= { sigChanEQsigProvEntry 4 }

sigChanEQsigStateTable OBJECT-TYPE
   SYNTAX     SEQUENCE OF SigChanEQsigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanEQsig 14 }

sigChanEQsigStateEntry OBJECT-TYPE
   SYNTAX     SigChanEQsigStateEntry
   ACCESS     not-accessible
   STATUS     mandatory
   DESCRIPTION
     "An entry in the sigChanEQsigStateTable."
   INDEX {
      sigChanIndex,
      sigChanEQsigIndex }
::= { sigChanEQsigStateTable 1 }

SigChanEQsigStateEntry ::= SEQUENCE {
   sigChanEQsigAdminState
      INTEGER,
   sigChanEQsigOperationalState
      INTEGER,
   sigChanEQsigUsageState
      INTEGER }

sigChanEQsigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanEQsigStateEntry 1 }

sigChanEQsigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanEQsigStateEntry 2 }

sigChanEQsigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanEQsigStateEntry 3 }

sigChanEQsigStatsTable OBJECT-TYPE
   SYNTAX     SEQUENCE OF SigChanEQsigStatsEntry
   ACCESS     not-accessible
   STATUS     mandatory
   DESCRIPTION
     "This group provides the operational components for the EtsiQsig 
      component."
::= { sigChanEQsig 15 }

sigChanEQsigStatsEntry OBJECT-TYPE
   SYNTAX     SigChanEQsigStatsEntry
   ACCESS     not-accessible
   STATUS     mandatory
   DESCRIPTION
     "An entry in the sigChanEQsigStatsTable."
   INDEX {
      sigChanIndex,
      sigChanEQsigIndex }
::= { sigChanEQsigStatsTable 1 }

SigChanEQsigStatsEntry ::= SEQUENCE {
   sigChanEQsigTotalCallsToIf
      Unsigned32,
   sigChanEQsigTotalCallsFromIf
      Unsigned32,
   sigChanEQsigNonCallAssocSessionsToIf
      Unsigned32,
   sigChanEQsigNonCallAssocSessionsFromIf
      Unsigned32 }

sigChanEQsigTotalCallsToIf OBJECT-TYPE
   SYNTAX     Unsigned32 (0..4294967295)
   ACCESS     read-only
   STATUS     mandatory
   DESCRIPTION
     "This attribute counts the total number of calls that have been made 
      to the interface. The value wraps when it reaches its maximum."
   DEFVAL     { 0 }
::= { sigChanEQsigStatsEntry 2 }

sigChanEQsigTotalCallsFromIf OBJECT-TYPE
   SYNTAX     Unsigned32 (0..4294967295)
   ACCESS     read-only
   STATUS     mandatory
   DESCRIPTION
     "This attribute counts the total number of calls from the interface. 
      The value wraps when it reaches its maximum."
   DEFVAL     { 0 }
::= { sigChanEQsigStatsEntry 3 }

sigChanEQsigNonCallAssocSessionsToIf OBJECT-TYPE
   SYNTAX     Unsigned32 (0..4294967295)
   ACCESS     read-only
   STATUS     mandatory
   DESCRIPTION
     "This attribute counts the total number of non-call associated 
      sessions to the interface. The value wraps when it reaches its 
      maximum."
   DEFVAL     { 0 }
::= { sigChanEQsigStatsEntry 4 }

sigChanEQsigNonCallAssocSessionsFromIf OBJECT-TYPE
   SYNTAX     Unsigned32 (0..4294967295)
   ACCESS     read-only
   STATUS     mandatory
   DESCRIPTION
     "This attribute counts the total number of non-call associated 
      sessions from the interface. The value wraps when it reaches its 
      maximum."
   DEFVAL     { 0 }
::= { sigChanEQsigStatsEntry 5 }

sigChanEQsigOperTable OBJECT-TYPE
   SYNTAX     SEQUENCE OF SigChanEQsigOperEntry
   ACCESS     not-accessible
   STATUS     mandatory
   DESCRIPTION
     "This group provides the operational attributes for the EtsiQsig 
      protocol."
::= { sigChanEQsig 16 }

sigChanEQsigOperEntry OBJECT-TYPE
   SYNTAX     SigChanEQsigOperEntry
   ACCESS     not-accessible
   STATUS     mandatory
   DESCRIPTION
     "An entry in the sigChanEQsigOperTable."
   INDEX {
      sigChanIndex,
      sigChanEQsigIndex }
::= { sigChanEQsigOperTable 1 }

SigChanEQsigOperEntry ::= SEQUENCE {
   sigChanEQsigActiveChannels
      Unsigned32,
   sigChanEQsigActiveVoiceChannels
      Unsigned32,
   sigChanEQsigActiveDataChannels
      Unsigned32,
   sigChanEQsigPeakActiveChannels
      Unsigned32,
   sigChanEQsigPeakActiveVoiceChannels
      Unsigned32,
   sigChanEQsigPeakActiveDataChannels
      Unsigned32,
   sigChanEQsigDChanStatus
      INTEGER }

sigChanEQsigActiveChannels OBJECT-TYPE
   SYNTAX     Unsigned32 (0..128)
   ACCESS     read-only
   STATUS     mandatory
   DESCRIPTION
     "This attribute indicates the number of currently active channels. 
      This includes data and voice channels."
   DEFVAL     { 0 }
::= { sigChanEQsigOperEntry 1 }

sigChanEQsigActiveVoiceChannels OBJECT-TYPE
   SYNTAX     Unsigned32 (0..128)
   ACCESS     read-only
   STATUS     mandatory
   DESCRIPTION
     "This attribute indicates the number of channels that are currently 
      carrying voice."
   DEFVAL     { 0 }
::= { sigChanEQsigOperEntry 2 }

sigChanEQsigActiveDataChannels OBJECT-TYPE
   SYNTAX     Unsigned32 (0..128)
   ACCESS     read-only
   STATUS     mandatory
   DESCRIPTION
     "This attribute indicates the number of channels that are currently 
      carrying data. This does not include modem data."
   DEFVAL     { 0 }
::= { sigChanEQsigOperEntry 3 }

sigChanEQsigPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { sigChanEQsigOperEntry 4 }

sigChanEQsigPeakActiveVoiceChannels OBJECT-TYPE
   SYNTAX     Unsigned32 (0..128)
   ACCESS     read-only
   STATUS     mandatory
   DESCRIPTION
     "This attribute indicates the maximum number of voice channels that 
      have been active on this signalling channel during the last polling 
      period."
   DEFVAL     { 0 }
::= { sigChanEQsigOperEntry 5 }

sigChanEQsigPeakActiveDataChannels OBJECT-TYPE
   SYNTAX     Unsigned32 (0..128)
   ACCESS     read-only
   STATUS     mandatory
   DESCRIPTION
     "This attribute indicates the maximum number of data channels that 
      have been active on this signalling channel during the last polling 
      period."
   DEFVAL     { 0 }
::= { sigChanEQsigOperEntry 6 }

sigChanEQsigDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being 
      rei-initialized."
::= { sigChanEQsigOperEntry 7 }

sigChanEQsigToolsTable OBJECT-TYPE
   SYNTAX     SEQUENCE OF SigChanEQsigToolsEntry
   ACCESS     not-accessible
   STATUS     mandatory
   DESCRIPTION
     "This contains a series of operational attributes which turn on and off 
      several kinds of tracing."
::= { sigChanEQsig 17 }

sigChanEQsigToolsEntry OBJECT-TYPE
   SYNTAX     SigChanEQsigToolsEntry
   ACCESS     not-accessible
   STATUS     mandatory
   DESCRIPTION
     "An entry in the sigChanEQsigToolsTable."
   INDEX {
      sigChanIndex,
      sigChanEQsigIndex }
::= { sigChanEQsigToolsTable 1 }

SigChanEQsigToolsEntry ::= SEQUENCE {
   sigChanEQsigTracing
      OCTET STRING }

sigChanEQsigTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously.  
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { sigChanEQsigToolsEntry 1 }

sigChanEQsigEQsigSpecificProvTable OBJECT-TYPE
   SYNTAX     SEQUENCE OF SigChanEQsigEQsigSpecificProvEntry
   ACCESS     not-accessible
   STATUS     mandatory
   DESCRIPTION
     "This group provides EtsiQsig protocol specific provisioning."
::= { sigChanEQsig 18 }

sigChanEQsigEQsigSpecificProvEntry OBJECT-TYPE
   SYNTAX     SigChanEQsigEQsigSpecificProvEntry
   ACCESS     not-accessible
   STATUS     mandatory
   DESCRIPTION
     "An entry in the sigChanEQsigEQsigSpecificProvTable."
   INDEX {
      sigChanIndex,
      sigChanEQsigIndex }
::= { sigChanEQsigEQsigSpecificProvTable 1 }

SigChanEQsigEQsigSpecificProvEntry ::= SEQUENCE {
   sigChanEQsigMsgSegmentation
      INTEGER,
   sigChanEQsigE1ChannelNumbers
      INTEGER }

sigChanEQsigMsgSegmentation OBJECT-TYPE
   SYNTAX     INTEGER  {
                 enabled(0),
                 disabled(1) }
   ACCESS     read-write
   STATUS     mandatory
   DESCRIPTION
     "This attribute allows users to enable/disable the EtsiQsig message 
      segmentation service."
   DEFVAL     { disabled }
::= { sigChanEQsigEQsigSpecificProvEntry 1 }

sigChanEQsigE1ChannelNumbers OBJECT-TYPE
   SYNTAX     INTEGER  {
                 skip16(1),
                 contiguous(2) }
   ACCESS     read-write
   STATUS     mandatory
   DESCRIPTION
     "This attribute is applicable to E1 interfaces only. It specifies the 
      mapping scheme between channel numbers (identified in Layer 3 
      messages) and timeslot numbers on the E1 link.
      When the attribute value is skip16, channel numbers map directly to 
      actual E1 timeslots; therefore only channel numbers 1 - 15 and 17 - 
      31 are expected.
      When the value is contiguous, channel numbers from 1 - 30 are 
      expected, and the following mapping is used: channels 1 - 15 are 
      mapped to timeslots 1 - 15, and channels 16 - 30 are mapped to 
      timeslots 17 - 31.
      On T1 interfaces, channel numbers are always expected in the range 
      1 - 23."
   DEFVAL     { skip16 }
::= { sigChanEQsigEQsigSpecificProvEntry 2 }

sigChanEQsigEQsigSpecificOpTable OBJECT-TYPE
   SYNTAX     SEQUENCE OF SigChanEQsigEQsigSpecificOpEntry
   ACCESS     not-accessible
   STATUS     mandatory
   DESCRIPTION
     "This group provides specific operational attributes for the Etsi Qsig 
      protocol."
::= { sigChanEQsig 19 }

sigChanEQsigEQsigSpecificOpEntry OBJECT-TYPE
   SYNTAX     SigChanEQsigEQsigSpecificOpEntry
   ACCESS     not-accessible
   STATUS     mandatory
   DESCRIPTION
     "An entry in the sigChanEQsigEQsigSpecificOpTable."
   INDEX {
      sigChanIndex,
      sigChanEQsigIndex }
::= { sigChanEQsigEQsigSpecificOpTable 1 }

SigChanEQsigEQsigSpecificOpEntry ::= SEQUENCE {
   sigChanEQsigSegmentationAccepted
      Unsigned32,
   sigChanEQsigSegmentationFailed
      Unsigned32 }

sigChanEQsigSegmentationAccepted OBJECT-TYPE
   SYNTAX     Unsigned32 (0..4294967295)
   ACCESS     read-only
   STATUS     mandatory
   DESCRIPTION
     "This attribute counts the total number of times a long Etsi Qsig 
      message has been received from a PBX and forwarded to a Passport 
      subnet. The value wraps when it reaches its maximum."
   DEFVAL     { 0 }
::= { sigChanEQsigEQsigSpecificOpEntry 1 }

sigChanEQsigSegmentationFailed OBJECT-TYPE
   SYNTAX     Unsigned32 (0..4294967295)
   ACCESS     read-only
   STATUS     mandatory
   DESCRIPTION
     "This attribute counts the total number of times a long Etsi Qsig 
      message has been received from a PBX and could not be forwarded 
      as is to a Passport subnet due to end-to-end incompatibility. The 
      value wraps when it reaches its maximum."
   DEFVAL     { 0 }
::= { sigChanEQsigEQsigSpecificOpEntry 2 }


-- SigChan/n EQsig Framer
-- 
-- The Framer component controls link layer framing for application 
-- components sending and receiving data on a link interface. It is also 
-- through Framer, that an application component is associated with a 
-- specific hardware link interface.
-- 
-- The Framer component provides provisionable attributes related to 
-- data path aspects of the hardware interface (such as crc and frame 
-- length). The Framer component also provides a provisionable 
-- attribute which binds the application component to a specific 
-- hardware component.
-- 
-- The Framer component contains operational attributes for link 
-- interface data path statistics (such as frame counts and aborts).
-- 

sigChanEQsigFramer OBJECT IDENTIFIER ::= { sigChanEQsig 2 }



sigChanEQsigFramerRowStatusTable OBJECT-TYPE
   SYNTAX     SEQUENCE OF SigChanEQsigFramerRowStatusEntry
   ACCESS     not-accessible
   STATUS     mandatory
   DESCRIPTION
     "This entry controls the addition and deletion of 
      sigChanEQsigFramer components."
::= { sigChanEQsigFramer 1 }

sigChanEQsigFramerRowStatusEntry OBJECT-TYPE
   SYNTAX     SigChanEQsigFramerRowStatusEntry
   ACCESS     not-accessible
   STATUS     mandatory
   DESCRIPTION
     "A single entry in the table represents a single 
      sigChanEQsigFramer component."
   INDEX {
      sigChanIndex,
      sigChanEQsigIndex,
      sigChanEQsigFramerIndex }
::= { sigChanEQsigFramerRowStatusTable 1 }

SigChanEQsigFramerRowStatusEntry ::= SEQUENCE {
   sigChanEQsigFramerRowStatus
      RowStatus,
   sigChanEQsigFramerComponentName
      DisplayString,
   sigChanEQsigFramerStorageType
      StorageType,
   sigChanEQsigFramerIndex
      NonReplicated }

sigChanEQsigFramerRowStatus OBJECT-TYPE
   SYNTAX     RowStatus 
   ACCESS     read-only
   STATUS     mandatory
   DESCRIPTION
     "This variable is used as the basis for SNMP naming of
      sigChanEQsigFramer components.
      These components cannot be added nor deleted."
::= { sigChanEQsigFramerRowStatusEntry 1 }

sigChanEQsigFramerComponentName OBJECT-TYPE
   SYNTAX     DisplayString 
   ACCESS     read-only
   STATUS     mandatory
   DESCRIPTION
     "This variable provides the component's string name for
      use with the ASCII Console Interface"
::= { sigChanEQsigFramerRowStatusEntry 2 }

sigChanEQsigFramerStorageType OBJECT-TYPE
   SYNTAX     StorageType 
   ACCESS     read-only
   STATUS     mandatory
   DESCRIPTION
     "This variable represents the storage type value for the
      sigChanEQsigFramer tables."
::= { sigChanEQsigFramerRowStatusEntry 4 }

sigChanEQsigFramerIndex OBJECT-TYPE
   SYNTAX     NonReplicated 
   ACCESS     not-accessible
   STATUS     mandatory
   DESCRIPTION
     "This variable represents the index for the sigChanEQsigFramer tables."
::= { sigChanEQsigFramerRowStatusEntry 10 }

sigChanEQsigFramerProvTable OBJECT-TYPE
   SYNTAX     SEQUENCE OF SigChanEQsigFramerProvEntry
   ACCESS     not-accessible
   STATUS     mandatory
   DESCRIPTION
     "This group contains the base provisioning data for the Framer 
      component. Application or hardware interface specific provisioning 
      data is contained in other provisionable Framer groups."
::= { sigChanEQsigFramer 10 }

sigChanEQsigFramerProvEntry OBJECT-TYPE
   SYNTAX     SigChanEQsigFramerProvEntry
   ACCESS     not-accessible
   STATUS     mandatory
   DESCRIPTION
     "An entry in the sigChanEQsigFramerProvTable."
   INDEX {
      sigChanIndex,
      sigChanEQsigIndex,
      sigChanEQsigFramerIndex }
::= { sigChanEQsigFramerProvTable 1 }

SigChanEQsigFramerProvEntry ::= SEQUENCE {
   sigChanEQsigFramerInterfaceName
      Link }

sigChanEQsigFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { sigChanEQsigFramerProvEntry 1 }

sigChanEQsigFramerStateTable OBJECT-TYPE
   SYNTAX     SEQUENCE OF SigChanEQsigFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanEQsigFramer 12 }

sigChanEQsigFramerStateEntry OBJECT-TYPE
   SYNTAX     SigChanEQsigFramerStateEntry
   ACCESS     not-accessible
   STATUS     mandatory
   DESCRIPTION
     "An entry in the sigChanEQsigFramerStateTable."
   INDEX {
      sigChanIndex,
      sigChanEQsigIndex,
      sigChanEQsigFramerIndex }
::= { sigChanEQsigFramerStateTable 1 }

SigChanEQsigFramerStateEntry ::= SEQUENCE {
   sigChanEQsigFramerAdminState
      INTEGER,
   sigChanEQsigFramerOperationalState
      INTEGER,
   sigChanEQsigFramerUsageState
      INTEGER }

sigChanEQsigFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanEQsigFramerStateEntry 1 }

sigChanEQsigFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanEQsigFramerStateEntry 2 }

sigChanEQsigFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanEQsigFramerStateEntry 3 }

sigChanEQsigFramerStatsTable OBJECT-TYPE
   SYNTAX     SEQUENCE OF SigChanEQsigFramerStatsEntry
   ACCESS     not-accessible
   STATUS     mandatory
   DESCRIPTION
     "This group contains the operational statistics data for a Framer 
      component."
::= { sigChanEQsigFramer 13 }

sigChanEQsigFramerStatsEntry OBJECT-TYPE
   SYNTAX     SigChanEQsigFramerStatsEntry
   ACCESS     not-accessible
   STATUS     mandatory
   DESCRIPTION
     "An entry in the sigChanEQsigFramerStatsTable."
   INDEX {
      sigChanIndex,
      sigChanEQsigIndex,
      sigChanEQsigFramerIndex }
::= { sigChanEQsigFramerStatsTable 1 }

SigChanEQsigFramerStatsEntry ::= SEQUENCE {
   sigChanEQsigFramerFrmToIf
      Unsigned32,
   sigChanEQsigFramerFrmFromIf
      Unsigned32,
   sigChanEQsigFramerOctetFromIf
      Unsigned32,
   sigChanEQsigFramerAborts
      Unsigned32,
   sigChanEQsigFramerCrcErrors
      Unsigned32,
   sigChanEQsigFramerLrcErrors
      Unsigned32,
   sigChanEQsigFramerNonOctetErrors
      Unsigned32,
   sigChanEQsigFramerOverruns
      Unsigned32,
   sigChanEQsigFramerUnderruns
      Unsigned32,
   sigChanEQsigFramerLargeFrmErrors
      Unsigned32 }

sigChanEQsigFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { sigChanEQsigFramerStatsEntry 1 }

sigChanEQsigFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { sigChanEQsigFramerStatsEntry 2 }

sigChanEQsigFramerOctetFromIf OBJECT-TYPE
   SYNTAX     Unsigned32 (0..4294967295)
   ACCESS     read-only
   STATUS     mandatory
   DESCRIPTION
     "The number of bytes received from the link interface by Framer."
   DEFVAL     { 0 }
::= { sigChanEQsigFramerStatsEntry 3 }

sigChanEQsigFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { sigChanEQsigFramerStatsEntry 4 }

sigChanEQsigFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { sigChanEQsigFramerStatsEntry 5 }

sigChanEQsigFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { sigChanEQsigFramerStatsEntry 6 }

sigChanEQsigFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { sigChanEQsigFramerStatsEntry 7 }

sigChanEQsigFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { sigChanEQsigFramerStatsEntry 8 }

sigChanEQsigFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { sigChanEQsigFramerStatsEntry 9 }

sigChanEQsigFramerLargeFrmErrors OBJECT-TYPE
   SYNTAX     Unsigned32 (0..4294967295)
   ACCESS     read-only
   STATUS     mandatory
   DESCRIPTION
     "This attribute counts the total number of frames received which 
      were too large (longer than 500 bytes).
      This count wraps to zero after reaching its maximum value."
   DEFVAL     { 0 }
::= { sigChanEQsigFramerStatsEntry 10 }




-- 
-- Version and Compliance statements
-- 



-- Object-Group Statement:
-- A list of all current accessible leaf objects.

-- OBJECTS { sigChanEQsigFramerInterfaceName,
--           sigChanEQsigComponentName,
--           sigChanEQsigT23,
--           sigChanEQsigPeakActiveDataChannels,
--           sigChanEQsigTracing,
--           sigChanEQsigFramerCrcErrors,
--           sigChanEQsigStorageType,
--           sigChanEQsigFramerOperationalState,
--           sigChanEQsigFramerStorageType,
--           sigChanEQsigT200,
--           sigChanEQsigE1ChannelNumbers,
--           sigChanEQsigT309,
--           sigChanEQsigMsgSegmentation,
--           sigChanEQsigFramerLrcErrors,
--           sigChanEQsigOperationalState,
--           sigChanEQsigT203,
--           sigChanEQsigFramerFrmFromIf,
--           sigChanEQsigFramerOctetFromIf,
--           sigChanEQsigDChanStatus,
--           sigChanEQsigFramerAdminState,
--           sigChanEQsigNonCallAssocSessionsToIf,
--           sigChanEQsigFramerUnderruns,
--           sigChanEQsigCircuitSwitchedK,
--           sigChanEQsigOverlapReceivingEnabled,
--           sigChanEQsigActiveChannels,
--           sigChanEQsigAdminState,
--           sigChanEQsigFramerUsageState,
--           sigChanEQsigFramerRowStatus,
--           sigChanEQsigActiveVoiceChannels,
--           sigChanEQsigUsageState,
--           sigChanEQsigT310,
--           sigChanEQsigFramerLargeFrmErrors,
--           sigChanEQsigRowStatus,
--           sigChanEQsigFramerFrmToIf,
--           sigChanEQsigOverlapSendingEnabled,
--           sigChanEQsigMaxNonCallConcurrent,
--           sigChanEQsigFramerOverruns,
--           sigChanEQsigNonCallAssocSessionsFromIf,
--           sigChanEQsigPeakActiveVoiceChannels,
--           sigChanEQsigFramerAborts,
--           sigChanEQsigPeakActiveChannels,
--           sigChanEQsigSegmentationFailed,
--           sigChanEQsigFramerNonOctetErrors,
--           sigChanEQsigActiveDataChannels,
--           sigChanEQsigSegmentationAccepted,
--           sigChanEQsigFramerComponentName,
--           sigChanEQsigTotalCallsFromIf,
--           sigChanEQsigSide,
--           sigChanEQsigN200,
--           sigChanEQsigTotalCallsToIf }
-- STATUS  mandatory
-- DESCRIPTION
--   "A list of all current accessible leaf objects."

vnetEtsiQsigGroup OBJECT IDENTIFIER ::= { vnetEtsiQsigMIB 1 }
vnetEtsiQsigGroupBE OBJECT IDENTIFIER ::= { vnetEtsiQsigGroup 5 }
vnetEtsiQsigGroupBE01 OBJECT IDENTIFIER ::= { vnetEtsiQsigGroupBE 2 }
vnetEtsiQsigGroupBE01A OBJECT IDENTIFIER ::= { vnetEtsiQsigGroupBE01 2 }



-- Agent-Capabilities Statement:

-- PRODUCT-RELEASE "Passport Release 7.0 VnetEtsiQsig."
-- STATUS          mandatory
-- DESCRIPTION     "VnetEtsiQsig MIB: MIB Version BE01A,
--                  Software Version BG00S4C."
-- SUPPORTS        Nortel-Magellan-Passport-VnetEtsiQsigMIB
--    INCLUDES     { vnetEtsiQsigGroupBE01A }

vnetEtsiQsigCapabilities OBJECT IDENTIFIER ::= { vnetEtsiQsigMIB 3 }
vnetEtsiQsigCapabilitiesBE OBJECT IDENTIFIER ::= { vnetEtsiQsigCapabilities 5 }
vnetEtsiQsigCapabilitiesBE01 OBJECT IDENTIFIER ::= { vnetEtsiQsigCapabilitiesBE 2 }
vnetEtsiQsigCapabilitiesBE01A OBJECT IDENTIFIER ::= { vnetEtsiQsigCapabilitiesBE01 2 }





END
