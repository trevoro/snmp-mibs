-- This file is corresponding to Release 6.1.2.100 from 2001/09/26 00:00:00
-- (C)opyright 1991-1999 BinTec Communications AG, All Rights Reserved
--  $RCSfile: mibmsgbox,v $ 
-- $Revision: 1.7 $ 

BIANCA-BRICK-MSGBOX-MIB DEFINITIONS ::= BEGIN
 
        IMPORTS
		DisplayString FROM SNMPv2-TC
            Counter
                FROM RFC1155-SMI
 
            OBJECT-TYPE
                FROM RFC-1212
		BitValue, Date FROM BIANCA-BRICK-PPP-MIB;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    isdn	OBJECT IDENTIFIER 
	::= { bibo 2 }


	HexValue ::= INTEGER

        msgForwardTable OBJECT-TYPE
            SYNTAX  SEQUENCE OF MsgForwardEntry
            ACCESS  not-accessible
            STATUS  mandatory
            DESCRIPTION
		"The msgForwardTable contains information about the 
		behavior of the message box. You can configure which
		extensions are used to accept fax calls and how these
		faxes should be forwarded to the receiver.
                Deleting entries: An entry can be removed by assigning
		the value `delete' to its msgForwardPoll object."
	::= { isdn 13 }

	msgForwardEntry OBJECT-TYPE
            SYNTAX  MsgForwardEntry
            ACCESS  not-accessible
            STATUS  mandatory
            DESCRIPTION
		""
	    INDEX   { msgForwardExtension }
              ::= { msgForwardTable 1 }

	MsgForwardEntry ::=
            SEQUENCE {
		msgForwardExtension		DisplayString,
		msgForwardAddr			DisplayString,
		msgForwardDeleteAction		INTEGER,
		msgForwardDelay			INTEGER,
		msgForwardPoll			INTEGER,
		msgForwardPollPassword		DisplayString,
		msgForwardMaxRetries 		INTEGER,
		msgForwardState			INTEGER
            }

	msgForwardExtension OBJECT-TYPE
            SYNTAX  DisplayString
            ACCESS  read-write
            STATUS  mandatory

            DESCRIPTION
                "The extension of the incoming calls that is accepted
		by the message box. For this extension you also have to
		set the pabxExtDestination field in the pabxExtensionTable
		to `msg_box'."
	::= { msgForwardEntry 1 }

	msgForwardAddr OBJECT-TYPE
            SYNTAX  DisplayString
            ACCESS  read-write
            STATUS  mandatory

            DESCRIPTION
                "The Called Party Number that is used to send stored faxes.
		If this field is empty, stored faxes are not sent automatically
		to another number."
	::= { msgForwardEntry 2 }

	msgForwardDeleteAction OBJECT-TYPE
            SYNTAX  INTEGER { 
		delivered(1), 
		forwarded(2),
		polled(3)
	    }
            ACCESS  read-write
            STATUS  mandatory

            DESCRIPTION
                "This field defines when a fax message, that was sent 
		successfully, should be deleted. When set to `delivered'
		the fax will be deleted after it is sent anyway. 
		When set to `forwarded' it will be deleted immediately
		after it was sent successfully to the number specified
		in the msgForwardAddr field.
		When set to `polled', the fax is deleted after someone
		received the fax via fax polling."
	::= { msgForwardEntry 3 }

	msgForwardDelay OBJECT-TYPE
            SYNTAX  INTEGER ( 1..1209600 )
            ACCESS  read-write
            STATUS  mandatory

            DESCRIPTION
                "The time in seconds to wait before the message box tries
		or retries to send a stored fax to the msgForwardAddr."
	::= { msgForwardEntry 4 }

	msgForwardPoll OBJECT-TYPE
            SYNTAX  INTEGER { 
		enable(1), 
		disable(2), 
		delete(3)
	    }
            ACCESS  read-write
            STATUS  mandatory

            DESCRIPTION
                "To allow polling stored fax messages this value must be set
		to `enable'. When set to `disable' fax polling is not allowed.
		When set to delete, the table-entry will be deleted."
	::= { msgForwardEntry 5 }

	msgForwardPollPassword OBJECT-TYPE
            SYNTAX  DisplayString
            ACCESS  read-write
            STATUS  mandatory

            DESCRIPTION
                "The password you have to use if you like to poll a stored
		fax."
	::= { msgForwardEntry 6 }

	msgForwardMaxRetries OBJECT-TYPE
            SYNTAX  INTEGER ( 0..1000 )
            ACCESS  read-write
            STATUS  mandatory

            DESCRIPTION
                "Number of trials to forward a fax message to an 
		external fax station before the msgForwardState
		changes to the value `blocked'. A trial counts
		only when a connection could be established.
		When this field is set to zero, the state never
		changes to `blocked'."

	::= { msgForwardEntry 7 }

	msgForwardState OBJECT-TYPE
            SYNTAX  INTEGER { 
		enabled(1), 
		disabled(2),
		blocked(3)
	    }
            ACCESS  read-write
            STATUS  mandatory

            DESCRIPTION
		"Faxes are only forwarded to msgForwardAddr if the
		msgForwardState has the value `enabled'. The 
		msgForwardState is set automatically to `blocked'
		when the number of retries reaches msgForwardMaxRetries."

	::= { msgForwardEntry 8 }


        msgDirTable OBJECT-TYPE
            SYNTAX  SEQUENCE OF MsgDirEntry
            ACCESS  not-accessible
            STATUS  mandatory
            DESCRIPTION
		"The msgDirTable contains information for all FAX messages
		that are currently stored in the flash ROM.
                Deleting entries: An entry can be removed by assigning
		the value `delete' to its msgDirState object."
	::= { isdn 14 }

	msgDirEntry OBJECT-TYPE
            SYNTAX  MsgDirEntry
            ACCESS  not-accessible
            STATUS  mandatory
            DESCRIPTION
		""
	    INDEX   { msgDirExtension }
              ::= { msgDirTable 1 }

	MsgDirEntry ::=
            SEQUENCE {
		msgDirExtension		DisplayString,
		msgDirType		INTEGER,
		msgDirContent		DisplayString,
		msgDirTime		Date,
		msgDirDuration		INTEGER,
		msgDirSize		INTEGER,
		msgDirState		INTEGER
            }

	msgDirExtension OBJECT-TYPE
            SYNTAX  DisplayString
            ACCESS  read-only
            STATUS  mandatory

            DESCRIPTION
                "The called number when the fax was received."
	::= { msgDirEntry 1 }

	msgDirType OBJECT-TYPE
            SYNTAX  INTEGER { 
		none(1), 
		fax(2)
	    }
            ACCESS  read-only
            STATUS  mandatory

            DESCRIPTION
                "The msgDirType specifies which kind of data belongs
		to this msgDirTable entry"
	::= { msgDirEntry 2 }

	msgDirContent OBJECT-TYPE
            SYNTAX  DisplayString
            ACCESS  read-only
            STATUS  mandatory

            DESCRIPTION
                "The msgDirContent is a unique string to identify the
		msgDirTable entry. It contains the data type, a unique
		number and the number of the remote fax station"
	::= { msgDirEntry 3 }

	msgDirTime OBJECT-TYPE
            SYNTAX  Date 
            ACCESS  read-only
            STATUS  mandatory

            DESCRIPTION
                "The msgDirTime contains the date and time when the
		fax was received."
	::= { msgDirEntry 4 }

	msgDirDuration OBJECT-TYPE
            SYNTAX  INTEGER 
            ACCESS  read-only
            STATUS  mandatory

            DESCRIPTION
                "The msgDirDuration contains for fax messages the number
		of stored pages."
	::= { msgDirEntry 5 }

	msgDirSize OBJECT-TYPE
            SYNTAX  INTEGER 
            ACCESS  read-only
            STATUS  mandatory

            DESCRIPTION
                "The msgDirSize contains the number Bytes that are used
		to store this message in the flash ROM."
	::= { msgDirEntry 6 }

	msgDirState OBJECT-TYPE
            SYNTAX  INTEGER { 
		receiving(1), 
		received(2), 
		sent(3), 
		deleted(4),
		delete(5)
	    }
            ACCESS  read-write
            STATUS  mandatory

            DESCRIPTION
                "The state of the message. To delete a message, assign the
		value `delete' to this object, then the msgDirState will
		change to `deleted' and the memory that is used by this
		message will be available again after the next automatic
		reorganisation of the flash ROM."
	::= { msgDirEntry 7 }

END		-- of BIANCA-BRICK definitions
