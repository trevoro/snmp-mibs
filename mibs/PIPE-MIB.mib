PIPE-MIB DEFINITIONS ::= BEGIN

-- Allot communication V4.1 MIB
-- January 16, 2001

 
IMPORTS
    neStatistics		FROM NE-STAT-MIB
    OBJECT-TYPE		        FROM RFC-1212
    Counter		 	FROM RFC1155-SMI
    DisplayString		FROM SNMPv2-TC;
    

pipeStatMIB OBJECT IDENTIFIER ::= { neStatistics 2 }
pipeStat    OBJECT IDENTIFIER ::= { pipeStatMIB 1 }

--pipe statistic

pipeStatTable OBJECT-TYPE
      SYNTAX  SEQUENCE OF PipeEntry
      ACCESS  not-accessible
      STATUS  mandatory
      DESCRIPTION
         "A list of pipe entries."
      ::= { pipeStat 1 }

pipeEntry OBJECT-TYPE
      SYNTAX  PipeEntry
      ACCESS  not-accessible
      STATUS  mandatory
      DESCRIPTION
         "A pipe entry contains statistical objects for one pipe."
      INDEX   { pipePosition,
                pipeInstancePosition }
      ::= { pipeStatTable 1 }

PipeEntry ::= SEQUENCE {
        pipePosition                                      INTEGER,
        pipeInstancePosition                              INTEGER,

        pipeName                                          DisplayString,
        
        pipeByteCountIn                                   Counter,
        pipeByteCountOut                                  Counter,
	pipeByteCountTotal                                Counter,
	pipeLiveConnections                               Counter,
	pipeNewConnections                                Counter,
	pipePacketsIn                                     Counter,
	pipePacketsOut                                    Counter,
	pipePacketsTotal                                  Counter

	}

        
pipePosition  OBJECT-TYPE
    SYNTAX      INTEGER
    ACCESS  read-only
    STATUS      mandatory
    DESCRIPTION
        "Position of pipe in table"
    ::= { pipeEntry 1 }
              
pipeInstancePosition  OBJECT-TYPE
    SYNTAX      INTEGER
    ACCESS  read-only
    STATUS      mandatory
    DESCRIPTION
        "Position of pipe instance in group"
    ::= { pipeEntry 2 }
        
pipeName          OBJECT-TYPE
    SYNTAX      DisplayString
    ACCESS  read-only
    STATUS      mandatory
    DESCRIPTION
        "pipe name"
    ::= { pipeEntry 3 }

pipeByteCountIn   OBJECT-TYPE
    SYNTAX      Counter
    ACCESS  read-only
    STATUS      mandatory
    DESCRIPTION
        "Bytes in per pipe"
    ::= { pipeEntry 4 }

pipeByteCountOut   OBJECT-TYPE
    SYNTAX      Counter
    ACCESS  read-only
    STATUS      mandatory
    DESCRIPTION
        "Bytes out per pipe"
    ::= { pipeEntry 5 }

pipeByteCountTotal   OBJECT-TYPE
    SYNTAX      Counter
    ACCESS  read-only
    STATUS      mandatory
    DESCRIPTION
        "Total Bytes per pipe"
    ::= { pipeEntry 6 }


pipeLiveConnections   OBJECT-TYPE
    SYNTAX      Counter
    ACCESS  read-only
    STATUS      mandatory
    DESCRIPTION
        "Live Connections per pipe"
    ::= { pipeEntry 7 }

pipeNewConnections   OBJECT-TYPE
    SYNTAX      Counter
    ACCESS  read-only
    STATUS      mandatory
    DESCRIPTION
        "New Connections per pipe"
    ::= { pipeEntry 8 }

pipePacketsIn   OBJECT-TYPE
    SYNTAX      Counter
    ACCESS  read-only
    STATUS      mandatory
    DESCRIPTION
        "Packets in per pipe"
    ::= { pipeEntry 9 }

pipePacketsOut   OBJECT-TYPE
    SYNTAX      Counter
    ACCESS  read-only
    STATUS      mandatory
    DESCRIPTION
        "Packets out per pipe"
    ::= { pipeEntry 10 }

pipePacketsTotal   OBJECT-TYPE
    SYNTAX      Counter
    ACCESS  read-only
    STATUS      mandatory
    DESCRIPTION
        "Total Packets per pipe"
    ::= { pipeEntry 11 }



--trigger for pipe and vc catalogs update

-- pipeUpdateCatalogs OBJECT-TYPE
--       SYNTAX      INTEGER
--       MAX-ACCESS  read-write
--       STATUS      current
--       DESCRIPTION
--         "Set to 1 to re-read the policy catalogs."
--       ::= { pipeStat 2 }
 
END
