--			Ascend mibds1atmnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDS1ATMNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibds1AtmNetworkProfile  OBJECT IDENTIFIER ::= { configuration 25}

	-- The mibds1AtmNetworkProfile table
	--
	-- This table contains parameters for the mibds1AtmNetworkProfile profile
	--

    mibds1AtmNetworkProfileTable	OBJECT-TYPE
	SYNTAX		SEQUENCE OF Mibds1AtmNetworkProfileEntry
	ACCESS		not-accessible
	STATUS		mandatory
	DESCRIPTION	"A list of mibds1AtmNetworkProfile profile entries."
	::= { mibds1AtmNetworkProfile 1 }

    mibds1AtmNetworkProfileEntry	OBJECT-TYPE
	SYNTAX		Mibds1AtmNetworkProfileEntry
	ACCESS		not-accessible
	STATUS		mandatory
	DESCRIPTION	"A mibds1AtmNetworkProfile entry containing objects that
			 maps to the parameters of mibds1AtmNetworkProfile profile."
	INDEX		{ ds1AtmNetworkProfile-Shelf-o, ds1AtmNetworkProfile-Slot-o, ds1AtmNetworkProfile-Item-o }
	::= { mibds1AtmNetworkProfileTable 1 }

    Mibds1AtmNetworkProfileEntry ::=
	SEQUENCE {
	    ds1AtmNetworkProfile-Shelf-o
		INTEGER,
	    ds1AtmNetworkProfile-Slot-o
		INTEGER,
	    ds1AtmNetworkProfile-Item-o
		INTEGER,
	    ds1AtmNetworkProfile-Name
		DisplayString,
	    ds1AtmNetworkProfile-PhysicalAddress-Shelf
		INTEGER,
	    ds1AtmNetworkProfile-PhysicalAddress-Slot
		INTEGER,
	    ds1AtmNetworkProfile-PhysicalAddress-ItemNumber
		INTEGER,
	    ds1AtmNetworkProfile-Enabled
		INTEGER,
	    ds1AtmNetworkProfile-SparingMode
		INTEGER,
	    ds1AtmNetworkProfile-IgnoreLineup
		INTEGER,
	    ds1AtmNetworkProfile-LineConfig-FrameType
		INTEGER,
	    ds1AtmNetworkProfile-LineConfig-Encoding
		INTEGER,
	    ds1AtmNetworkProfile-LineConfig-NailedGroup
		INTEGER,
	    ds1AtmNetworkProfile-LineConfig-Loopback
		INTEGER,
	    ds1AtmNetworkProfile-LineConfig-ClockSource
		INTEGER,
	    ds1AtmNetworkProfile-LineConfig-ClockPriority
		INTEGER,
	    ds1AtmNetworkProfile-LineConfig-oFDL
		INTEGER,
	    ds1AtmNetworkProfile-LineConfig-SendCode
		INTEGER,
	    ds1AtmNetworkProfile-LineConfig-FrontEndType
		INTEGER,
	    ds1AtmNetworkProfile-LineConfig-LineLength
		INTEGER,
	    ds1AtmNetworkProfile-LineConfig-LineBuildOut
		INTEGER,
	    ds1AtmNetworkProfile-LineConfig-PcmMode
		INTEGER,
	    ds1AtmNetworkProfile-LineConfig-CosetEnabled
		INTEGER,
	    ds1AtmNetworkProfile-LineConfig-ScramblingEnabled
		INTEGER,
	    ds1AtmNetworkProfile-LineConfig-HecCorrectionEnabled
		INTEGER,
	    ds1AtmNetworkProfile-LineConfig-VpSwitchingVpi
		INTEGER,
	    ds1AtmNetworkProfile-LineConfig-ImaOptionConfig-TxlinkConfig-NeTxLid
		INTEGER,
	    ds1AtmNetworkProfile-LineConfig-ImaOptionConfig-TxlinkConfig-AddLinkCondTime
		INTEGER,
	    ds1AtmNetworkProfile-LineConfig-ImaOptionConfig-TxlinkConfig-LinkRecoveryType
		INTEGER,
	    ds1AtmNetworkProfile-LineConfig-ImaOptionConfig-TxlinkConfig-FaultClearingType
		INTEGER,
	    ds1AtmNetworkProfile-LineConfig-ImaOptionConfig-TxlinkConfig-FaultClearingTime
		INTEGER,
	    ds1AtmNetworkProfile-LineConfig-ImaOptionConfig-TxlinkConfig-Priority
		INTEGER,
	    ds1AtmNetworkProfile-LineConfig-ImaOptionConfig-RxlinkConfig-AddLinkCondTime
		INTEGER,
	    ds1AtmNetworkProfile-LineConfig-ImaOptionConfig-RxlinkConfig-LinkRecoveryType
		INTEGER,
	    ds1AtmNetworkProfile-LineConfig-ImaOptionConfig-RxlinkConfig-RecLinkCondTime
		INTEGER,
	    ds1AtmNetworkProfile-LineConfig-ImaOptionConfig-RxlinkConfig-RxLidLearningTime
		INTEGER,
	    ds1AtmNetworkProfile-LineConfig-ImaOptionConfig-RxlinkConfig-FaultClearingType
		INTEGER,
	    ds1AtmNetworkProfile-LineConfig-ImaOptionConfig-RxlinkConfig-FaultClearingTime
		INTEGER,
	    ds1AtmNetworkProfile-LineConfig-ImaOptionConfig-RxlinkConfig-InDefectIntTime
		INTEGER,
	    ds1AtmNetworkProfile-LineConfig-ImaOptionConfig-RxlinkConfig-OutDefectIntTime
		INTEGER,
	    ds1AtmNetworkProfile-LineConfig-ImaOptionConfig-RxlinkConfig-DefectRatio
		INTEGER,
	    ds1AtmNetworkProfile-LineConfig-StatusChangeTrapEnable
		INTEGER,
	    ds1AtmNetworkProfile-Action-o
		INTEGER
	}

    ds1AtmNetworkProfile-Shelf-o	OBJECT-TYPE
	SYNTAX	INTEGER
	ACCESS	read-only
	STATUS	mandatory
	DESCRIPTION	""
	::= { mibds1AtmNetworkProfileEntry 1 }

    ds1AtmNetworkProfile-Slot-o	OBJECT-TYPE
	SYNTAX	INTEGER
	ACCESS	read-only
	STATUS	mandatory
	DESCRIPTION	""
	::= { mibds1AtmNetworkProfileEntry 2 }

    ds1AtmNetworkProfile-Item-o	OBJECT-TYPE
	SYNTAX	INTEGER
	ACCESS	read-only
	STATUS	mandatory
	DESCRIPTION	""
	::= { mibds1AtmNetworkProfileEntry 3 }

    ds1AtmNetworkProfile-Name	OBJECT-TYPE
	SYNTAX	DisplayString
	ACCESS	read-write
	STATUS	mandatory
	DESCRIPTION	"Name of IMA Line Config profile."
	::= { mibds1AtmNetworkProfileEntry 4 }

    ds1AtmNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibds1AtmNetworkProfileEntry 5 }

    ds1AtmNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibds1AtmNetworkProfileEntry 6 }

    ds1AtmNetworkProfile-PhysicalAddress-ItemNumber	OBJECT-TYPE
	SYNTAX	INTEGER
	ACCESS	read-write
	STATUS	mandatory
	DESCRIPTION	"A number that specifies an addressable entity within the context of shelf and slot."
	::= { mibds1AtmNetworkProfileEntry 7 }

    ds1AtmNetworkProfile-Enabled	OBJECT-TYPE
	SYNTAX	INTEGER {
		    no (1),
		    yes (2)
		}
	ACCESS	read-write
	STATUS	mandatory
	DESCRIPTION	"TRUE if the line is enabled, otherwise FALSE."
	::= { mibds1AtmNetworkProfileEntry 8 }

    ds1AtmNetworkProfile-SparingMode	OBJECT-TYPE
	SYNTAX	INTEGER {
		    inactive (1),
		    manual (2),
		    automatic (3)
		}
	ACCESS	read-write
	STATUS	mandatory
	DESCRIPTION	"Port sparing operational mode for this port."
	::= { mibds1AtmNetworkProfileEntry 41 }

    ds1AtmNetworkProfile-IgnoreLineup	OBJECT-TYPE
	SYNTAX	INTEGER {
		    systemDefined (1),
		    no (2),
		    yes (3)
		}
	ACCESS	read-write
	STATUS	mandatory
	DESCRIPTION	"Ignore line up value for this port."
	::= { mibds1AtmNetworkProfileEntry 42 }

    ds1AtmNetworkProfile-LineConfig-FrameType	OBJECT-TYPE
	SYNTAX	INTEGER {
		    d4 (1),
		    esf (2),
		    g703 (3),
		    n-2ds (4)
		}
	ACCESS	read-write
	STATUS	mandatory
	DESCRIPTION	"The super-framing mode that is used on the physical link(s)."
	::= { mibds1AtmNetworkProfileEntry 9 }

    ds1AtmNetworkProfile-LineConfig-Encoding	OBJECT-TYPE
	SYNTAX	INTEGER {
		    ami (1),
		    b8zs (2),
		    hdb3 (3),
		    none (4)
		}
	ACCESS	read-write
	STATUS	mandatory
	DESCRIPTION	"The layer 1 line encoding used for the physical link(s)."
	::= { mibds1AtmNetworkProfileEntry 10 }

    ds1AtmNetworkProfile-LineConfig-NailedGroup	OBJECT-TYPE
	SYNTAX	INTEGER
	ACCESS	read-write
	STATUS	mandatory
	DESCRIPTION	"The group index to which this link belongs to"
	::= { mibds1AtmNetworkProfileEntry 11 }

    ds1AtmNetworkProfile-LineConfig-Loopback	OBJECT-TYPE
	SYNTAX	INTEGER {
		    noLoopback (1),
		    feLoopback (2),
		    lineLoopback (3),
		    remoteLoopback (4),
		    localLoopback (5)
		}
	ACCESS	read-write
	STATUS	mandatory
	DESCRIPTION	"Loopback mode."
	::= { mibds1AtmNetworkProfileEntry 12 }

    ds1AtmNetworkProfile-LineConfig-ClockSource	OBJECT-TYPE
	SYNTAX	INTEGER {
		    eligible (1),
		    notEligible (2)
		}
	ACCESS	read-write
	STATUS	mandatory
	DESCRIPTION	""
	::= { mibds1AtmNetworkProfileEntry 13 }

    ds1AtmNetworkProfile-LineConfig-ClockPriority	OBJECT-TYPE
	SYNTAX	INTEGER {
		    highPriority (2),
		    middlePriority (3),
		    lowPriority (4)
		}
	ACCESS	read-write
	STATUS	mandatory
	DESCRIPTION	"Clock priority assigned to the T1 line. Used to select particular lines as clock source."
	::= { mibds1AtmNetworkProfileEntry 14 }

    ds1AtmNetworkProfile-LineConfig-oFDL	OBJECT-TYPE
	SYNTAX	INTEGER {
		    none (1),
		    atNT (2),
		    ansi (3),
		    sprint (4)
		}
	ACCESS	read-write
	STATUS	mandatory
	DESCRIPTION	"Who's FDL are we using. Used only if frame-type is ESF - Ignored otherwise."
	::= { mibds1AtmNetworkProfileEntry 15 }

    ds1AtmNetworkProfile-LineConfig-SendCode	OBJECT-TYPE
	SYNTAX	INTEGER {
		    noCode (1),
		    lineCode (2),
		    payloadCode (3),
		    inbandloopCode (14),
		    resetCode (4),
		    qrsCode (5),
		    n-511Pattern (6),
		    n-3In24Pattern (7),
		    n-1In16Pattern (8),
		    allOnesPattern (9),
		    allZerosPattern (10),
		    altOnesZerosPattern (11),
		    dblAltOnesZerosPattern (12),
		    n-2Pow20Pattern (13)
		}
	ACCESS	read-write
	STATUS	mandatory
	DESCRIPTION	"The type of code to be sent across the DS1 interface."
	::= { mibds1AtmNetworkProfileEntry 43 }

    ds1AtmNetworkProfile-LineConfig-FrontEndType	OBJECT-TYPE
	SYNTAX	INTEGER {
		    shortHaul (1),
		    longHaul (2)
		}
	ACCESS	read-write
	STATUS	mandatory
	DESCRIPTION	"The front end type of the transceiver."
	::= { mibds1AtmNetworkProfileEntry 16 }

    ds1AtmNetworkProfile-LineConfig-LineLength	OBJECT-TYPE
	SYNTAX	INTEGER {
		    n-1133 (1),
		    n-134266 (2),
		    n-267399 (3),
		    n-400533 (4),
		    n-534655 (5)
		}
	ACCESS	read-write
	STATUS	mandatory
	DESCRIPTION	"The length of the physical line (for short haul lines)."
	::= { mibds1AtmNetworkProfileEntry 39 }

    ds1AtmNetworkProfile-LineConfig-LineBuildOut	OBJECT-TYPE
	SYNTAX	INTEGER {
		    n-0Db (1),
		    n-75Db (2),
		    n-15Db (3),
		    n-2255Db (4)
		}
	ACCESS	read-write
	STATUS	mandatory
	DESCRIPTION	"Line buildout value for CSU lines."
	::= { mibds1AtmNetworkProfileEntry 40 }

    ds1AtmNetworkProfile-LineConfig-PcmMode	OBJECT-TYPE
	SYNTAX	INTEGER {
		    isdn (24),
		    clearChannel (25)
		}
	ACCESS	read-write
	STATUS	mandatory
	DESCRIPTION	"Number of active channels: in PCM highway"
	::= { mibds1AtmNetworkProfileEntry 18 }

    ds1AtmNetworkProfile-LineConfig-CosetEnabled	OBJECT-TYPE
	SYNTAX	INTEGER {
		    no (1),
		    yes (2)
		}
	ACCESS	read-write
	STATUS	mandatory
	DESCRIPTION	"Selecting yes signifies that the ATM Forum polynomial (coset polynomial) be added to HEC before the HEC verification of a received cell. In the transmit direction, this selection enables generation of a HEC with the coset polynomial value. Selecting no signifies that the ATM Forum polynomial (coset polynomial) *not* be added to HEC before HEC verification of a received cell. In the transmit direction, selecting no enables generation of a HEC without the coset polynomial value. "
	::= { mibds1AtmNetworkProfileEntry 19 }

    ds1AtmNetworkProfile-LineConfig-ScramblingEnabled	OBJECT-TYPE
	SYNTAX	INTEGER {
		    no (1),
		    yes (2)
		}
	ACCESS	read-write
	STATUS	mandatory
	DESCRIPTION	"Selecting 'yes' enables the descrambling of received cells on the link. The payload of transmitted cells is scrambled. Selecting 'no' disables the descrambling of received cells on the link. The payload of transmitted cells is not scrambled. "
	::= { mibds1AtmNetworkProfileEntry 20 }

    ds1AtmNetworkProfile-LineConfig-HecCorrectionEnabled	OBJECT-TYPE
	SYNTAX	INTEGER {
		    no (1),
		    yes (2)
		}
	ACCESS	read-write
	STATUS	mandatory
	DESCRIPTION	"Selecting 'yes' enables correction of cells received with a single-bit error in the HEC. Selecting 'no' disables correction of cells received with a single-bit error in the HEC. "
	::= { mibds1AtmNetworkProfileEntry 21 }

    ds1AtmNetworkProfile-LineConfig-VpSwitchingVpi	OBJECT-TYPE
	SYNTAX	INTEGER
	ACCESS	read-write
	STATUS	mandatory
	DESCRIPTION	"The Vpi to be used for the VP switching. Rest of the valid VPIs in valid vpi-vci-range will be used for the VC switching. Changes in this range will take effect immediately. THE USER SHOULD BE VERY CAREFUL WHILE CHANGING THIS VALUE BECAUSE ALL CONNECTIONS ON THE LIM WHERE THIS PORT BELONGS WILL BE DROPPED IN ORDER TO MAKE THIS NEW VALUE EFFECTIVE IMMEDIATELY. Valid only when the port is in UNI mode"
	::= { mibds1AtmNetworkProfileEntry 22 }

    ds1AtmNetworkProfile-LineConfig-ImaOptionConfig-TxlinkConfig-NeTxLid	OBJECT-TYPE
	SYNTAX	INTEGER
	ACCESS	read-write
	STATUS	mandatory
	DESCRIPTION	"Transmit LID for the link"
	::= { mibds1AtmNetworkProfileEntry 23 }

    ds1AtmNetworkProfile-LineConfig-ImaOptionConfig-TxlinkConfig-AddLinkCondTime	OBJECT-TYPE
	SYNTAX	INTEGER
	ACCESS	read-write
	STATUS	mandatory
	DESCRIPTION	"Link conditioning timeout during link addition/insertion. Time in seconds"
	::= { mibds1AtmNetworkProfileEntry 24 }

    ds1AtmNetworkProfile-LineConfig-ImaOptionConfig-TxlinkConfig-LinkRecoveryType	OBJECT-TYPE
	SYNTAX	INTEGER {
		    manual (2),
		    slow (3),
		    fast (4)
		}
	ACCESS	read-write
	STATUS	mandatory
	DESCRIPTION	"Type of link recovery"
	::= { mibds1AtmNetworkProfileEntry 25 }

    ds1AtmNetworkProfile-LineConfig-ImaOptionConfig-TxlinkConfig-FaultClearingType	OBJECT-TYPE
	SYNTAX	INTEGER {
		    manual (2),
		    auto (3)
		}
	ACCESS	read-write
	STATUS	mandatory
	DESCRIPTION	"Auto/Manual"
	::= { mibds1AtmNetworkProfileEntry 26 }

    ds1AtmNetworkProfile-LineConfig-ImaOptionConfig-TxlinkConfig-FaultClearingTime	OBJECT-TYPE
	SYNTAX	INTEGER
	ACCESS	read-write
	STATUS	mandatory
	DESCRIPTION	"Time after which fault is cleared if fault-clearing-type set to auto"
	::= { mibds1AtmNetworkProfileEntry 27 }

    ds1AtmNetworkProfile-LineConfig-ImaOptionConfig-TxlinkConfig-Priority	OBJECT-TYPE
	SYNTAX	INTEGER
	ACCESS	read-write
	STATUS	mandatory
	DESCRIPTION	"Priority defined for TRL, automatically select highest priority link to become the TRL (maybe we can deduct this from the t1ClockSource priority"
	::= { mibds1AtmNetworkProfileEntry 28 }

    ds1AtmNetworkProfile-LineConfig-ImaOptionConfig-RxlinkConfig-AddLinkCondTime	OBJECT-TYPE
	SYNTAX	INTEGER
	ACCESS	read-write
	STATUS	mandatory
	DESCRIPTION	"Link conditioning timeout during link addition/insertion. Time in seconds"
	::= { mibds1AtmNetworkProfileEntry 29 }

    ds1AtmNetworkProfile-LineConfig-ImaOptionConfig-RxlinkConfig-LinkRecoveryType	OBJECT-TYPE
	SYNTAX	INTEGER {
		    manual (2),
		    slow (3),
		    fast (4)
		}
	ACCESS	read-write
	STATUS	mandatory
	DESCRIPTION	"Type of link recovery"
	::= { mibds1AtmNetworkProfileEntry 30 }

    ds1AtmNetworkProfile-LineConfig-ImaOptionConfig-RxlinkConfig-RecLinkCondTime	OBJECT-TYPE
	SYNTAX	INTEGER
	ACCESS	read-write
	STATUS	mandatory
	DESCRIPTION	"Link conditioning timeout during link recovery, "
	::= { mibds1AtmNetworkProfileEntry 31 }

    ds1AtmNetworkProfile-LineConfig-ImaOptionConfig-RxlinkConfig-RxLidLearningTime	OBJECT-TYPE
	SYNTAX	INTEGER
	ACCESS	read-write
	STATUS	mandatory
	DESCRIPTION	"Time to learn RX LID (in ICP cells)"
	::= { mibds1AtmNetworkProfileEntry 32 }

    ds1AtmNetworkProfile-LineConfig-ImaOptionConfig-RxlinkConfig-FaultClearingType	OBJECT-TYPE
	SYNTAX	INTEGER {
		    manual (2),
		    auto (3)
		}
	ACCESS	read-write
	STATUS	mandatory
	DESCRIPTION	"Auto/Manual"
	::= { mibds1AtmNetworkProfileEntry 33 }

    ds1AtmNetworkProfile-LineConfig-ImaOptionConfig-RxlinkConfig-FaultClearingTime	OBJECT-TYPE
	SYNTAX	INTEGER
	ACCESS	read-write
	STATUS	mandatory
	DESCRIPTION	"Time after which fault is cleared if fault-clearing-type set to auto"
	::= { mibds1AtmNetworkProfileEntry 34 }

    ds1AtmNetworkProfile-LineConfig-ImaOptionConfig-RxlinkConfig-InDefectIntTime	OBJECT-TYPE
	SYNTAX	INTEGER
	ACCESS	read-write
	STATUS	mandatory
	DESCRIPTION	"Time in milliseconds, if the defect is persistent for this time, the Rx Failed state machine enters the FAILED state"
	::= { mibds1AtmNetworkProfileEntry 35 }

    ds1AtmNetworkProfile-LineConfig-ImaOptionConfig-RxlinkConfig-OutDefectIntTime	OBJECT-TYPE
	SYNTAX	INTEGER
	ACCESS	read-write
	STATUS	mandatory
	DESCRIPTION	"Time in milliseconds, if the no defect condition persists for this time, the Rx Failed state machine leaves the FAILED state"
	::= { mibds1AtmNetworkProfileEntry 36 }

    ds1AtmNetworkProfile-LineConfig-ImaOptionConfig-RxlinkConfig-DefectRatio	OBJECT-TYPE
	SYNTAX	INTEGER
	ACCESS	read-write
	STATUS	mandatory
	DESCRIPTION	"Defect to No Defect ratio"
	::= { mibds1AtmNetworkProfileEntry 37 }

    ds1AtmNetworkProfile-LineConfig-StatusChangeTrapEnable	OBJECT-TYPE
	SYNTAX	INTEGER {
		    no (1),
		    yes (2)
		}
	ACCESS	read-write
	STATUS	mandatory
	DESCRIPTION	"When set to yes, a line status change trap is sent. NOTE: when the line status change results from a higher level line status change, i.e., ds3, then no trap for the ds1 are sent. The default setting is No."
	::= { mibds1AtmNetworkProfileEntry 44 }

    ds1AtmNetworkProfile-Action-o	OBJECT-TYPE
	SYNTAX	INTEGER {
		    noAction (1),
		    createProfile (2),
		    deleteProfile (3)
		}
	ACCESS	read-write
	STATUS	mandatory
	DESCRIPTION	""
	::= { mibds1AtmNetworkProfileEntry 38 }

END
