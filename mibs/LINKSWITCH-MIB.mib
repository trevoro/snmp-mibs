LINKSWITCH-MIB DEFINITIONS ::= BEGIN

-- This file describes the MIB supported by the
-- 3Com FMS and MSH LinkSwitch version 1.0.
--
-- revision history:
-- 05/23/94 Created.
-- 08/19/94 Add media sense and backup power supply ojbects.
-- 08/22/94 Add lsfddiPATHRingLatency object.
--
-- The LinkSwitch supports the standard "transmissions" MIB for FDDI and
-- IEEE 802.3 interfaces, the proposed standard "dot3" MIB for the
-- Ethernet interfaces, and the standard SMT/FDDI MIB for FDDI.

-- When an object's DESCRIPTION field includes the keyword DURABLE,
-- the object's value is retained across system reinitialization.
-- This MIB module uses the extended OBJECT-TYPE macro.
IMPORTS
   a3Com
      FROM A3Com-products-MIB
   Counter
      FROM RFC1155-SMI
   OBJECT-TYPE
      FROM RFC-1212
   DisplayString, PhysAddress
      FROM RFC1213-MIB;

-- a3Com             OBJECT IDENTIFIER ::= { enterprises 43 }
linkSwitch        OBJECT IDENTIFIER ::= { a3Com 17 }

lsSRFilterEnable   OBJECT-TYPE
      SYNTAX   INTEGER { true(1), false(2) }
      ACCESS   read-write
      STATUS   mandatory
      DESCRIPTION
               "When false, the Address Filter forwards Source Routed
                frames, that is, frames with a 1 in the MSB of the Source
                Address.  When true, the Address Filter does not forward
                Source Routed frames.  Default value is false.  DURABLE."
      ::= { linkSwitch 1 }

lsSegmentFilterEnable  OBJECT-TYPE
      SYNTAX   INTEGER { true(1), false(2) }
      ACCESS   read-write
      STATUS   mandatory
      DESCRIPTION
               "Controls action taken with Eth frames with source and
                destination stations on the same segment (i.e. port).
                When true, the Address Filter will not forward intra-segment
                frames.  When false, all frames received are forwarded.
                Default is true.  DURABLE."
      ::= { linkSwitch 2 }

lsMcastFilterEnable OBJECT-TYPE
      SYNTAX   INTEGER { true(1), false(2) }
      ACCESS   read-write
      STATUS   mandatory
      DESCRIPTION
               "When false, all frames with a Multicast Destination Address
                that does not match any Address Filter entry are forwarded 
                to all ports.  Those with a match are forwarded to port.
                When true, only frames with a Multicast Destination Address
                with a match in the Address Filter are forwarded to port.
                Default is false.  DURABLE."
      ::= { linkSwitch 3 }

lsLoopDetectAction  OBJECT-TYPE
      SYNTAX   INTEGER {
                  shutport(1),         -- shut down first port dup detected on
                  shuteths(2),         -- disable all ports, FDDI left up
                  shutunit(3),         -- shutdown the all media interfaces
                  no-action(4)         -- none of the preceding
                  }
      ACCESS   read-write
      STATUS   mandatory
      DESCRIPTION
               "If a station appears to be on two ports, Address Filter
                thrashing will occur.  Detection of this situation is
                possible, and this object controls the action to be taken
                when the situation is detected.  Default is shutport.  
                no-action means that no action will be taken, but this means
                Ethernet and FDDI networks will be flooded.  NOTE: control
                of traps indicating the condition is not affected.  DURABLE."
      ::= { linkSwitch 4 }

lsAddressAgingTimer  OBJECT-TYPE
      SYNTAX   Counter
      ACCESS   read-write
      STATUS   mandatory
      DESCRIPTION
               "A count of the seconds that will elapse before the Address
                Filter contents are 'aged' to remove entries which are not
                active.  Default is 1800, or 30 minutes.  Write 0 to stop
                aging process from occuring.  DURABLE."
      ::= { linkSwitch 5 }

lsIPEchoAgingHelp    OBJECT-TYPE
      SYNTAX   INTEGER { true(1), false(2) }
      ACCESS   read-write
      STATUS   mandatory
      DESCRIPTION
               "If true, an IP echo frame will be broadcast on the subnet,
                which will cause otherwise quiecient stations to become   
                active.  The rate is half of lsAddressAgingTimer.  DURABLE."
      ::= { linkSwitch 6 }

lsProdVerSW  OBJECT-TYPE
      SYNTAX   DisplayString (SIZE (1..4))
      ACCESS   read-only
      STATUS   mandatory
      DESCRIPTION
               "This describes the version of the software currently running.
                Returns a string in the form X.YZ, where X represents the
                major version, Y represents the minor version or revision,
                and Z represents the development level of the revision."
      ::= { linkSwitch 7 }

lsProdVerHW  OBJECT-TYPE
      SYNTAX   DisplayString (SIZE (1..4))
      ACCESS   read-only
      STATUS   mandatory
      DESCRIPTION
               "This describes the version of the hardware currently running.
                Returns a string in the form X.YZ, where X represents the
                major version, Y represents the minor version or revision,
                and Z represents the development level of the revision."
      ::= { linkSwitch 8 }

lsLEDstate   OBJECT-TYPE
      SYNTAX   OCTET STRING (SIZE (80))
      ACCESS   read-only
      STATUS   mandatory
      DESCRIPTION
               "A binary structure which describes the current state of all
                of the LEDs of an LinkSwitch.  Actual layout available on 
                request."
      ::= { linkSwitch 9 }

lsTestResult OBJECT-TYPE
      SYNTAX   INTEGER
      ACCESS   read-only
      STATUS   mandatory
      DESCRIPTION
               "When a test is initiated via lsAction, the result of the
                test is stored in this variable when the test has completed
                or failed.  The value varies by test, is set to one (other)
                at the start of the test."
      ::= { linkSwitch 10 }

lsAction     OBJECT-TYPE
      SYNTAX   INTEGER {
                  other(1),             -- none of the following
                  age-addr-table(2),    -- remove old entries for all ports
                  clear-addr-table(3),  -- clear table for all ports
                  disconnect-FDDI(4),   -- shut down the FDDI side
                  connect-FDDI(5),      -- start up the FDDI side
                  disconnect-Eth(6),    -- shut down the Eth side
                  connect-Eth(7),       -- start up the Eth side
                  test-fddipath(8),     -- run a path test on the FDDI side
                  test-ethports(9),     -- test all ports on the ETH side
                  test-lsfunc(10),      -- test the FDDI and ETH together
                  test-addr-filter(11)  -- test the Address Filtering Logic
                  }
      ACCESS   read-write
      STATUS   mandatory
      DESCRIPTION
               "Value when read will be other.  Writing a value to this object
                will result in the associated action taking place.  Note that
                it is possible to disconnect the management station from the
                LinkSwitch by issuing the disconnect-FDDI or disconnect-Eth actions,
                depending of course where the management station is connected
                to the LinkSwitch.  For those actions which are tests, the result is
                in lsTestResult.  If the action is disconnect-FDDI, the FDDI
                ring will function internally for inter-segment frames."
      ::= { linkSwitch 11 }

lsEportNumber OBJECT-TYPE
      SYNTAX   INTEGER
      ACCESS   read-only
      STATUS   mandatory
      DESCRIPTION
               "A count of the Ethernet Ports supported by this system."
      ::= { linkSwitch 12 }

lsEportTable OBJECT-TYPE
      SYNTAX   SEQUENCE OF LsEportEntry
      ACCESS   not-accessible
      STATUS   mandatory
      ::= { linkSwitch 13 }

lsEportEntry OBJECT-TYPE
      SYNTAX   LsEportEntry
      ACCESS   not-accessible
      STATUS   mandatory
      INDEX    { lsEportIndex }
      ::= { lsEportTable 1 }

LsEportEntry ::=
      SEQUENCE {
         lsEportIndex                INTEGER,
         lsEportEnable               INTEGER,
         lsEportActivate             INTEGER,
         lsEportLinkState            INTEGER,
         lsEportName                 DisplayString,
         lsEportSQETestEnable        INTEGER,
         lsEportLongPktsEnable       INTEGER,
         lsEportMCastFilterEnable    INTEGER,
         lsEportMCastRate            INTEGER,
         lsEportMCastBurstLimit      INTEGER,
         lsEportStationsNumber       INTEGER,
         lsEportSecsSinceLastClear   Counter,
         lsEportTestResult           INTEGER,
         lsEportAction               INTEGER,
         lsEportFtoEByteCts          Counter,
         lsEportEtoFByteCts          Counter,
         lsEportFtoEPacketCts        Counter,
         lsEportEtoFPacketCts        Counter,
         lsEportFtoEDropPktCts       Counter,
         lsEportEtoFDropPktCts       Counter,
         lsEportFtoEBusErrorCts      Counter,
         lsEportEtoFBusErrorCts      Counter,
         lsEportXMCastCts            Counter,
         lsEportXBCastCts            Counter,
         lsEportXDirectedCts         Counter,
         lsEportXDeferredCts         Counter,
         lsEportXLateCollCts         Counter,
         lsEportXCollAbortCts        Counter,
         lsEportXCSErrCts            Counter,
         lsEportXExcessDeferCts      Counter,
         lsEportXUnderrunCts         Counter,
         lsEportXSQETestFailCts      Counter,
         lsEportRMCastCts            Counter,
         lsEportRBCastCts            Counter,
         lsEportRDirectedCts         Counter,
         lsEportRAlignmentCts        Counter,
         lsEportRTooLongCts          Counter,
         lsEportRFCSErrorCts         Counter,
         lsEportROverrunCts          Counter
         }

lsEportIndex OBJECT-TYPE
      SYNTAX   INTEGER
      ACCESS   read-only
      STATUS   mandatory
      DESCRIPTION
               "The index of this table entry."
      ::= { lsEportEntry 1 }

lsEportEnable  OBJECT-TYPE
      SYNTAX   INTEGER { true(1), false(2) }
      ACCESS   read-write
      STATUS   mandatory
      DESCRIPTION
               "When false, port is in reset state, so no port (Ethernet)
                traffic will go through.  When enabled, functionality is
                further controlled by lsEportActivate and ifOperStatus.
                Default is true.  DURABLE."
      ::= { lsEportEntry 2 }


lsEportActivate OBJECT-TYPE
      SYNTAX   INTEGER { true(1), false(2) }
      ACCESS   read-write
      STATUS   mandatory
      DESCRIPTION
               "When true, port is shutdown but not reset, so counters will
                maintain values at time of deactivation.  Further
                functionality controlled by ifOperStatus.  Default is true."
      ::= { lsEportEntry 3 }

lsEportLinkState  OBJECT-TYPE
      SYNTAX   INTEGER {
                  other(1),
                  disabled(2),      -- port completely disabled
                  inactive(3),      -- port enabled, no traffic through
                  ready(4),         -- port enabled, ready to accept link
                  active(5),        -- port enabled, traffic through
                  shutdown(6)       -- error or loop condition forced state
                  }
      ACCESS   read-only
      STATUS   mandatory
      DESCRIPTION
               "Reports status of Link, as affected by lsEportEnable,
                lsEportActive, lsEportForwarding, and ifOperStatus."
      ::= { lsEportEntry 4 }

lsEportName  OBJECT-TYPE
      SYNTAX   DisplayString (SIZE (1..7))
      ACCESS   read-write
      STATUS   mandatory
      DESCRIPTION
               "Abstract name for port.  DURABLE."
      ::= { lsEportEntry 5 }

lsEportSQETestEnable  OBJECT-TYPE
      SYNTAX   INTEGER { true(1), false(2) }
      ACCESS   read-write
      STATUS   mandatory
      DESCRIPTION
               "When true, SQE test (heartbeat) will occur after each
                frame transmitted by Ethernet MAC.  Need not be disabled for
                those ports which are connected to a repeater because
                Eth ports have a MAC.  Default is true. DURABLE."
      ::= { lsEportEntry 6 }

lsEportLongPktsEnable  OBJECT-TYPE
      SYNTAX   INTEGER { true(1), false(2) }
      ACCESS   read-write
      STATUS   mandatory
      DESCRIPTION
               "When true, frames with lengths longer than Ethernet
                maximum will be allowed to go from FDDI to Ethernet and
                Ethernet to FDDI.  Default is false.  DURABLE."
      ::= { lsEportEntry 7 }

lsEportMCastFilterEnable  OBJECT-TYPE
      SYNTAX   INTEGER { true(1), false(2) }
      ACCESS   read-write
      STATUS   mandatory
      DESCRIPTION
               "When true, filtering will occur based on the values of
                lsEportMCastRate and lsEportMCastBurstLimit.  If false,
                there is no port-level filtering performed on multicasts.
                Default is false.  DURABLE."
      ::= { lsEportEntry 8 }

lsEportMCastRate   OBJECT-TYPE
      SYNTAX   INTEGER
      ACCESS   read-write
      STATUS   mandatory
      DESCRIPTION
               "The rate in frames/second that multicasts will not be
                allowed to exceed, when lsEportBcastFilterEnable is true.
                Must also set lsEportMCastBurstLimit to non-zero value.
                DURABLE."
      ::= { lsEportEntry 9 }

lsEportMCastBurstLimit  OBJECT-TYPE
      SYNTAX   INTEGER
      ACCESS   read-write
      STATUS   mandatory
      DESCRIPTION
               "This specifies the maximum number of multicasts that can
                be forwarded from FDDI to Ethernet port in a 'burst' before
                the lsEportBCastRate limit causes frames to be discarded
                Must also set lsEportMCastBurstLimit to non-zero value.
                If this to zero, all multicasts are discarded.  DURABLE."
      ::= { lsEportEntry 10 }

lsEportStationsNumber OBJECT-TYPE
      SYNTAX   INTEGER
      ACCESS   read-only 
      STATUS   mandatory
      DESCRIPTION
               "A count of stations whose Physical Address has been
                detected in the Source Address field of a frame which
                was transmitted by a station connected to this port."
      ::= { lsEportEntry 11 }

lsEportSecsSinceLastClear OBJECT-TYPE
      SYNTAX   Counter  
      ACCESS   read-only
      STATUS   mandatory
      DESCRIPTION
               "A count of seconds since last cleared counters for
                this port.  Use lsEportAction to clear the counters."
      ::= { lsEportEntry 12 }

lsEportTestResult OBJECT-TYPE
      SYNTAX   INTEGER (0..255)
      ACCESS   read-only
      STATUS   mandatory
      DESCRIPTION
               "When a test is initiated via lsEportAction, the result of
                the test is stored in this variable when the test has completed
                or failed.  The value varies by test, is set to one (other)
                at the start of the test."
      ::= { lsEportEntry 13 }

lsEportAction     OBJECT-TYPE
      SYNTAX   INTEGER {
                  other(1),                 -- none of the following
                  test-loopback(2),         -- test all ports on the ETH side
                  test-addrfilter(3),       -- test the Address Filtering Logic
                  zero-counters(4)          -- zero all internal (hardware) counters
                  }
      ACCESS   read-write
      STATUS   mandatory
      DESCRIPTION
               "Value when read will be other.  Writing a value to this object
                will result in the associated action taking place.  For those
                actions which are tests, the result is in lsEportTestResult."
      ::= { lsEportEntry 14 }

lsEportFtoEByteCts OBJECT-TYPE
      SYNTAX   Counter
      ACCESS   read-only
      STATUS   mandatory
      DESCRIPTION
               "A count of bytes that were forwarded from the FDDI MAC to the
                Ethernet through the Address Filter.  The count per frame
                includes the packet's bytes as received by the FDDI MAC (FCS
                removed), plus a number of overhead bytes used internally."
      REFERENCE
               "ieee8023IfTable.ieee8023OctetsTxOk"
      ::= { lsEportEntry 15 }

lsEportEtoFByteCts OBJECT-TYPE
      SYNTAX   Counter
      ACCESS   read-only
      STATUS   mandatory
      DESCRIPTION
               "A count of bytes that were forwarded from the Ethernet MAC
                to the Address Filter.  The count per packet includes the
                byte count indicated by the Ethernet MAC (without FCS),
                plus a number of overhead bytes used internally."
      REFERENCE
               "ieee8023IfTable.ieee8023OctetsRxOk"
      ::= { lsEportEntry 16 }

lsEportFtoEPacketCts OBJECT-TYPE
      SYNTAX   Counter
      ACCESS   read-only
      STATUS   mandatory
      DESCRIPTION
               "A count of frames that were forwarded from the FDDI MAC to the
                Ethernet MAC through the Address Filter.  The count is the
                number of frames that the Ethernet MAC was able to transmit."
      REFERENCE
               "ieee8023IfTable.ieee8023FrmsTxOk"
      ::= { lsEportEntry 17 }

lsEportEtoFPacketCts OBJECT-TYPE
      SYNTAX   Counter
      ACCESS   read-only
      STATUS   mandatory
      DESCRIPTION
               "A count of frames that were forwarded trom the Ethernet MAC
                to the Address Filter.  The count is the number of frames
                received without error by the Ethernet MAC.  Packets may be
                not-forwarded by the Address Filter and some may encounter
                error conditions, so it is necessary to subtract the value of
                lslEportEtoFDropPktCts for the true number of frames."
      REFERENCE
               "ieee8023IfTable.ieee8023FrmsRxOk"
      ::= { lsEportEntry 18 }

lsEportFtoEDropPktCts OBJECT-TYPE
      SYNTAX   Counter
      ACCESS   read-only
      STATUS   mandatory
      DESCRIPTION
               "A count of frames that were dropped as they went from the
                FDDI to the Ethernet through the Address Filter. Frames
                may be dropped due to resource constraints."
      ::= { lsEportEntry 19 }

lsEportEtoFDropPktCts OBJECT-TYPE
      SYNTAX   Counter
      ACCESS   read-only
      STATUS   mandatory
      DESCRIPTION
               "A count of frames that were dropped before reaching the FDDI
                MAC.  Include in this value are frames encountering resource
                constraints, as well as frames which did not need to be
                forwarded onto the FDDI (i.e., local intra-segment traffic)."
      ::= { lsEportEntry 20 }

lsEportFtoEBusErrorCts OBJECT-TYPE
      SYNTAX   Counter
      ACCESS   read-only
      STATUS   mandatory
      DESCRIPTION
               "A count of frames that encountered a Parity or FIFO Error   
                as they went from FDDI to the Ethernet."
      ::= { lsEportEntry 21 }

lsEportEtoFBusErrorCts OBJECT-TYPE
      SYNTAX   Counter
      ACCESS   read-only
      STATUS   mandatory
      DESCRIPTION
               "A count of frames that encountered a Parity or FIFO Error
                as they went from Ethernet to the FDDI."
      ::= { lsEportEntry 22 }

lsEportXMCastCts OBJECT-TYPE
      SYNTAX   Counter
      ACCESS   read-only
      STATUS   mandatory
      DESCRIPTION
               "A count of frames transmitted to a multicast address.
                Does not include frames sent to the broadcast address."
      REFERENCE
               "ieee8023IfTable.ieee8023McastFrmsTxOk"
      ::= { lsEportEntry 23 }

lsEportXBCastCts OBJECT-TYPE
      SYNTAX   Counter
      ACCESS   read-only
      STATUS   mandatory
      DESCRIPTION
               "A count of frames transmitted to a broadcast address.
                Does not include frames sent to the multicast address."
      REFERENCE
               "ieee8023IfTable.ieee8023McastFrmsTxOk"
      ::= { lsEportEntry 24 }

lsEportXDirectedCts OBJECT-TYPE
      SYNTAX   Counter
      ACCESS   read-only
      STATUS   mandatory
      DESCRIPTION
               "A count of frames transmitted that were not addressed to
                either the multicast or the broadcast address."
      ::= { lsEportEntry 25 }

lsEportXDeferredCts OBJECT-TYPE
      SYNTAX   Counter
      ACCESS   read-only
      STATUS   mandatory
      DESCRIPTION
               "A count of frames for which the first transmission attempt
                is delayed because the medium is busy.      The count
                does not include frames involved in collisions."
      REFERENCE
               "ieee8023IfTable.ieee8023DefTx"
      ::= { lsEportEntry 26 }

lsEportXLateCollCts OBJECT-TYPE
      SYNTAX   Counter
      ACCESS   read-only
      STATUS   mandatory
      DESCRIPTION
               "A count of times that a collision is detected later
                512 bit-times into the transmission of a packet.

                A late collision is also considered as a generic
                collision for purposes of other collision-related counters."
      REFERENCE
               "ieee8023IfTable.ieee8023LateColls"
      ::= { lsEportEntry 27 }

lsEportXCollAbortCts OBJECT-TYPE
      SYNTAX   Counter
      ACCESS   read-only
      STATUS   mandatory
      DESCRIPTION
               "A count of frames for which transmission fails due to
                excessive collisions."
      REFERENCE
               "ieee8023IfTable.ieee8023ExcessColls"
      ::= { lsEportEntry 28 }

lsEportXCSErrCts OBJECT-TYPE
      SYNTAX   Counter
      ACCESS   read-only
      STATUS   mandatory
      DESCRIPTION
               "A count of times that the carrier sense condition was
                lost or never asserted when attempting to transmit a frame."
      REFERENCE
               "ieee8023IfTable.ieee8023CsErrors"
      ::= { lsEportEntry 29 }

lsEportXExcessDeferCts OBJECT-TYPE
      SYNTAX   Counter
      ACCESS   read-only
      STATUS   mandatory
      DESCRIPTION
               "A count of times that the deferral time was excessive."
      REFERENCE
               "ieee8023IfTable.ieee8023ExcessDef"
      ::= { lsEportEntry 30 }

lsEportXUnderrunCts OBJECT-TYPE
      SYNTAX   Counter
      ACCESS   read-only
      STATUS   mandatory
      DESCRIPTION
               "A count of times that an underrun occured."
      ::= { lsEportEntry 31 }

lsEportXSQETestFailCts OBJECT-TYPE
      SYNTAX   Counter
      ACCESS   read-only
      STATUS   mandatory
      DESCRIPTION
               "A count of times that the SQE TEST ERROR
                message is generated by the PLS sublayer for a
                particular interface. The SQE TEST ERROR
                message is defined in section 7.2.2.2.4 of
                ANSI/IEEE 802.3-1985 and its generation is
                described in section 7.2.4.6 of the same
                document."
      REFERENCE
               "ieee8023IfTable.ieee8023SqeTestErrors"
      ::= { lsEportEntry 32 }

lsEportRMCastCts OBJECT-TYPE
      SYNTAX    Counter
      ACCESS    read-only
      STATUS    mandatory
      DESCRIPTION
               "A count of frames received with a multicast address.
                Does not include frames received with a broadcast address."
      REFERENCE
               "ieee8023IfTable.ieee8023McastFrmsRxOk"
      ::= { lsEportEntry 33 }

lsEportRBCastCts OBJECT-TYPE
      SYNTAX    Counter
      ACCESS    read-only
      STATUS    mandatory
      DESCRIPTION
               "A count of frames received with a broadcast address.
                Does not include frames received with a multicast address."
      REFERENCE
               "ieee8023IfTable.ieee8023McastFrmsRxOk"
      ::= { lsEportEntry 34 }

lsEportRDirectedCts OBJECT-TYPE
      SYNTAX    Counter
      ACCESS    read-only
      STATUS    mandatory
      DESCRIPTION
               "A count of frames received that were not addressed to
                either the multicast or the broadcast address."
      ::= { lsEportEntry 35 }

lsEportRAlignmentCts OBJECT-TYPE
      SYNTAX   Counter
      ACCESS   read-only
      STATUS   mandatory
      DESCRIPTION
               "A count of frames received on a particular
                interface that are not an integral number of
                octets in length and do not pass the FCS check.

                The count represented by an instance of this
                object is incremented when the 'alignment error'
                status is returned by the MAC service to the
                LLC (or other MAC user). Received frames for
                which multiple error conditions obtain are,
                according to the conventions of IEEE 802.3
                Layer Management, counted exclusively according
                to the error status presented to the LLC."
      REFERENCE
               "ieee8023IfTable.ieee8023AlignErrors"
      ::= { lsEportEntry 36 }

lsEportRTooLongCts OBJECT-TYPE
      SYNTAX   Counter
      ACCESS   read-only
      STATUS   mandatory
      DESCRIPTION
               "A count of frames which were received and also
                exceeded the maximum frame size."
      REFERENCE
               "ieee8023IfTable.ieee8023OorLengthFields"
      ::= { lsEportEntry 37 }

lsEportRFCSErrorCts OBJECT-TYPE
      SYNTAX   Counter
      ACCESS   read-only
      STATUS   mandatory
      DESCRIPTION
               "A count of frames received on a particular
                interface that are an integral number of octets
                in length but do not pass the FCS check.

                The count represented by an instance of this
                object is incremented when the frameCheckError
                status is returned by the MAC service to the
                LLC (or other MAC user). Received frames for
                which multiple error conditions obtain are,
                according to the conventions of IEEE 802.3
                Layer Management, counted exclusively according
                to the error status presented to the LLC."
      REFERENCE
               "ieee8023IfTable.ieee8023FcsErrors"
      ::= { lsEportEntry 38 }

lsEportROverrunCts OBJECT-TYPE
      SYNTAX   Counter
      ACCESS   read-only
      STATUS   mandatory
      DESCRIPTION
               "The number of frames which could not be stored by the
                Ethernet MAC due to internal resource constraints."
      ::= { lsEportEntry 39 }

lsStationsNumber OBJECT-TYPE
      SYNTAX   INTEGER
      ACCESS   read-only 
      STATUS   mandatory
      DESCRIPTION
               "A count of stations whose Physical Address has been
                detected in the Source Address field of a frame which 
                was transmitted by a station connected to an Ethernet port.
                Equals the total of all of the per-port stations counts."
      ::= { linkSwitch 14 }

lsStationsTable OBJECT-TYPE
      SYNTAX   SEQUENCE OF LsStationsEntry
      ACCESS   not-accessible
      STATUS   mandatory
      ::= { linkSwitch 15 }

lsStationsEntry OBJECT-TYPE
      SYNTAX   LsStationsEntry
      ACCESS   not-accessible
      STATUS   mandatory
      INDEX    { lsStationsPortIndex, lsStationsAddrIndex }
      ::= { lsStationsTable 1 }

LsStationsEntry ::=
      SEQUENCE {
         lsStationsPortIndex         INTEGER,
         lsStationsAddrIndex         INTEGER,
         lsStationsAddress           PhysAddress
         }

lsStationsPortIndex OBJECT-TYPE
      SYNTAX   INTEGER
      ACCESS   read-only
      STATUS   mandatory
      DESCRIPTION
               "The lsEportIndex of the port to which the addresses apply."
      ::= { lsStationsEntry 1 }

lsStationsAddrIndex OBJECT-TYPE
      SYNTAX   INTEGER
      ACCESS   read-only
      STATUS   mandatory
      DESCRIPTION
               "The index of this address within a row of the
                table lsStationsTable, where the row is selected
                by the value of lsStationsPortIndex."
      ::= { lsStationsEntry 2 }

lsStationsAddress OBJECT-TYPE
      SYNTAX   PhysAddress
      ACCESS   read-only
      STATUS   mandatory
      DESCRIPTION
               "A Physical Address which has been seen as a Source Address
                on this port since the last time the Address Filter was aged."
      ::= { lsStationsEntry 3 }

lsBusCts     OBJECT-TYPE
      SYNTAX   OCTET STRING (SIZE (192))
      ACCESS   read-only
      STATUS   mandatory
      DESCRIPTION
               "A binary structure which contains the FtoE and EtoF counters
                for all ls ports.  Actual layout available on request."
      ::= { linkSwitch 16 }

lsPortAMediaPresent OBJECT-TYPE
      SYNTAX   INTEGER {
                other(1),
                notpresent(2),          -- Port A Media not present
                fiberpresent(3),        -- Port A Fiber Media present
                fiberscpresent(4),      -- Port A Fiber SC Media present
                utppresent(5),          -- Port A UTP Media present
                stppresent(6)           -- Port A STP Media present
                }
      ACCESS    read-only
      STATUS    mandatory
      DESCRIPTION
               "Reports presence and type of FDDI Port A Media. For FMS
                LinkSwitch, only Fiber and UTP are supported."
      ::= { linkSwitch 17 }

lsPortBMediaPresent OBJECT-TYPE
      SYNTAX   INTEGER {
                other(1),
                notpresent(2),          -- Port B Media not present
                fiberpresent(3),        -- Port B Fiber Media present
                fiberscpresent(4),      -- Port B Fiber SC Media present
                utppresent(5),          -- Port B UTP Media present
                stppresent(6)           -- Port B STP Media present
                }
      ACCESS    read-only
      STATUS    mandatory
      DESCRIPTION
               "Reports presence and type of FDDI Port B Media. For FMS
                LinkSwitch, only Fiber and UTP are supported."
      ::= { linkSwitch 18 }

lsFMSBackupPSSense OBJECT-TYPE
      SYNTAX   INTEGER {
                  other(1),
                  notpresent(2),
                  goodstatus(3),
                  badstatus(4)
                  }
      ACCESS   read-only
      STATUS   mandatory
      DESCRIPTION
               "Reports the presence and status of the backup power
                supply on FMS LinkSwitch Only."
      ::= { linkSwitch 19 }

lsfddiPATHRingLatency OBJECT-TYPE
      SYNTAX   INTEGER
      ACCESS   read-only
      STATUS   mandatory
      DESCRIPTION
               "Reports the measurement (in 80 nanosecond ticks) of 
                total accumulated latency of the ring associated
                with the current path."
      ::= { linkSwitch 20 }
                 
END
