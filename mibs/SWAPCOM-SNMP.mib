SWAPCOM-SNMP	DEFINITIONS ::= BEGIN

	IMPORTS
		NOTIFICATION-TYPE, enterprises, MODULE-IDENTITY, OBJECT-TYPE, TimeTicks,
		IpAddress, Gauge32, Counter32, Counter64
			FROM SNMPv2-SMI
		MacAddress, TimeInterval, TruthValue, TestAndIncr,
		RowStatus, DisplayString, StorageType, DateAndTime
			FROM SNMPv2-TC;

swapcom	MODULE-IDENTITY
LAST-UPDATED	"200507131817Z"
ORGANIZATION	"SWAPCOM"
CONTACT-INFO	"support@swapcom.fr"
DESCRIPTION	"SWAPCOM SNMP MIB"
REVISION	"200507131817Z"
DESCRIPTION	""
::=	{	enterprises	11308 }

org	OBJECT IDENTIFIER
::=	{	iso	3 }

dod	OBJECT IDENTIFIER
::=	{	org	6 }

internet	OBJECT IDENTIFIER
::=	{	dod	1 }

private	OBJECT IDENTIFIER
::=	{	internet	4 }

enterprises	OBJECT IDENTIFIER
::=	{	private	1 }

snmp	OBJECT IDENTIFIER
::=	{	swapcom	2 }

platform	OBJECT IDENTIFIER
::=	{	snmp	1 }

notificationGroup	OBJECT IDENTIFIER
::=	{	platform  1 }

defaultNotification NOTIFICATION-TYPE
STATUS  current
DESCRIPTION "Use to send the notifications whose trap type is not defined"
::= {   notificationGroup  1 }

notificationMessage	OBJECT-TYPE
SYNTAX	DisplayString
MAX-ACCESS	not-accessible
STATUS	current
DESCRIPTION	 "This scalar leaf node would be present as one of the varbinds in the Trap to hold the notification message"
::=	{	notificationGroup	2 }

platformPlatformId	OBJECT-TYPE
SYNTAX	DisplayString
MAX-ACCESS	read-only
STATUS	current
DESCRIPTION	 ""
::=	{	platform	2 }

platformPlatformStatus	OBJECT-TYPE
SYNTAX	INTEGER { platform-initializing(0), platform-initialized(1), domains-initializing(2), started(3) }
MAX-ACCESS	read-only
STATUS	current
DESCRIPTION	 ""
::=	{	platform	3 }

platformStart NOTIFICATION-TYPE
STATUS  current
DESCRIPTION "This notification is sent when the platform is started"
::= {   platform  4 }

platformStop NOTIFICATION-TYPE
STATUS  current
DESCRIPTION "This notification is sent when the platform stops"
::= {   platform  5 }

platformVersion	OBJECT IDENTIFIER
::=	{	platform	6 }

platformVersionProductName	OBJECT-TYPE
SYNTAX	DisplayString
MAX-ACCESS	read-only
STATUS	current
DESCRIPTION	 ""
::=	{	platformVersion	1 }

platformVersionProductVersion	OBJECT-TYPE
SYNTAX	DisplayString
MAX-ACCESS	read-only
STATUS	current
DESCRIPTION	 ""
::=	{	platformVersion	2 }

platformVersionBuildNumber	OBJECT-TYPE
SYNTAX	INTEGER
MAX-ACCESS	read-only
STATUS	current
DESCRIPTION	 ""
::=	{	platformVersion	3 }

platformVersionBuildDate	OBJECT-TYPE
SYNTAX	DisplayString
MAX-ACCESS	read-only
STATUS	current
DESCRIPTION	 ""
::=	{	platformVersion	4 }

applicationVersion	OBJECT IDENTIFIER
::=	{	platform	7 }

applicationVersionProductName	OBJECT-TYPE
SYNTAX	DisplayString
MAX-ACCESS	read-only
STATUS	current
DESCRIPTION	 ""
::=	{	applicationVersion	1 }

applicationVersionProductVersion	OBJECT-TYPE
SYNTAX	DisplayString
MAX-ACCESS	read-only
STATUS	current
DESCRIPTION	 ""
::=	{	applicationVersion	2 }

applicationVersionBuildNumber	OBJECT-TYPE
SYNTAX	INTEGER
MAX-ACCESS	read-only
STATUS	current
DESCRIPTION	 ""
::=	{	applicationVersion	3 }

applicationVersionBuildDate	OBJECT-TYPE
SYNTAX	DisplayString
MAX-ACCESS	read-only
STATUS	current
DESCRIPTION	 ""
::=	{	applicationVersion	4 }

logger	OBJECT IDENTIFIER
::=	{	platform	8 }

unknownLog NOTIFICATION-TYPE
STATUS  current
DESCRIPTION "This notification is sent when a log with unknown level is sent"
::= {   logger  1 }

infoLog NOTIFICATION-TYPE
STATUS  current
DESCRIPTION "This notification is sent when a log with INFO level is sent"
::= {   logger  2 }

warnLog NOTIFICATION-TYPE
STATUS  current
DESCRIPTION "This notification is sent when a log with WARN level is sent"
::= {   logger  3 }

errorLog NOTIFICATION-TYPE
STATUS  current
DESCRIPTION "This notification is sent when a log with ERROR level is sent"
::= {   logger  4 }

fatalLog NOTIFICATION-TYPE
STATUS  current
DESCRIPTION "This notification is sent when a log with FATAL level is sent"
::= {   logger  5 }

remotePlatform	OBJECT IDENTIFIER
::=	{	platform	9 }

remotePlatformTable	OBJECT-TYPE
SYNTAX	SEQUENCE OF	RemotePlatformEntry
MAX-ACCESS	not-accessible
STATUS	current
DESCRIPTION	"Remote platform table"
::=	{	remotePlatform	1 }


remotePlatformEntry	OBJECT-TYPE
SYNTAX	RemotePlatformEntry
MAX-ACCESS	not-accessible
STATUS	current
DESCRIPTION	"The entry for remotePlatformTable"
INDEX {  remotePlatformPlatformId  }
::=	{	remotePlatformTable	1 }

RemotePlatformEntry	::=  SEQUENCE	{ remotePlatformPlatformId DisplayString, remotePlatformPlatformProtocol DisplayString, remotePlatformPlatformStatus INTEGER
}

remotePlatformPlatformId	OBJECT-TYPE
SYNTAX	DisplayString
MAX-ACCESS	read-only
STATUS	current
DESCRIPTION	 ""
::=	{	remotePlatformEntry	1 }

remotePlatformPlatformProtocol	OBJECT-TYPE
SYNTAX	DisplayString
MAX-ACCESS	read-only
STATUS	current
DESCRIPTION	 ""
::=	{	remotePlatformEntry	2 }

remotePlatformPlatformStatus	OBJECT-TYPE
SYNTAX	INTEGER { unknown(0), up(1), down(2) }
MAX-ACCESS	read-only
STATUS	current
DESCRIPTION	 ""
::=	{	remotePlatformEntry	3 }

remotePlatformUp NOTIFICATION-TYPE
STATUS  current
DESCRIPTION "This notification is sent when a remote platform is going to be up"
::= {   remotePlatform  2 }

remotePlatformDown NOTIFICATION-TYPE
STATUS  current
DESCRIPTION "This notification is sent when a remote platform is going to be down"
::= {   remotePlatform  3 }


END
