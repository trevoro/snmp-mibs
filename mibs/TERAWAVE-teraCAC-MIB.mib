TERAWAVE-teraCAC-MIB DEFINITIONS ::= BEGIN
        -- Created by sml2mib compiler 
        IMPORTS

 enterprises,  OBJECT-TYPE,  Counter,  Gauge,  TimeTicks
        FROM RFC1155-SMI;

terawave OBJECT IDENTIFIER ::=  { enterprises 4513 }

teraCACGroup OBJECT IDENTIFIER ::=  { terawave 19 }

teraCACSystemTablePar OBJECT IDENTIFIER ::=  { teraCACGroup 1 }

     -- teraCACSystemTable (special)

teraCACSystemTable OBJECT IDENTIFIER ::=  { teraCACSystemTablePar 1 }

teraLevel1UseSlotNumber OBJECT-TYPE
          SYNTAX INTEGER (1..20)
          ACCESS read-only
          STATUS mandatory
          DESCRIPTION
               ""
          ::= { teraCACSystemTable 1 }

teraUsePonIndex OBJECT-TYPE
          SYNTAX INTEGER (1..33)
          ACCESS read-only
          STATUS mandatory
          DESCRIPTION
               ""
          ::= { teraCACSystemTable 2 }

teraLevel2UseSlotNumber OBJECT-TYPE
          SYNTAX INTEGER (1..4)
          ACCESS read-only
          STATUS mandatory
          DESCRIPTION
               ""
          ::= { teraCACSystemTable 3 }

teraCACTablePar OBJECT IDENTIFIER ::=  { teraCACGroup 2 }

     -- teraCACTable (special)

teraCACTable OBJECT IDENTIFIER ::=  { teraCACTablePar 1 }

teraCACUpWeightrtVBR OBJECT-TYPE
          SYNTAX INTEGER (0..1000000)
          ACCESS read-write
          STATUS mandatory
          DESCRIPTION
               ""
          ::= { teraCACTable 1 }

teraCACUpWeightrtVBRpeak OBJECT-TYPE
          SYNTAX INTEGER (0..1000000)
          ACCESS read-write
          STATUS mandatory
          DESCRIPTION
               ""
          ::= { teraCACTable 2 }

teraCACUpWeightnrtVBR OBJECT-TYPE
          SYNTAX INTEGER (0..1000000)
          ACCESS read-write
          STATUS mandatory
          DESCRIPTION
               ""
          ::= { teraCACTable 3 }

teraCACUpWeightnrtVBRpeak OBJECT-TYPE
          SYNTAX INTEGER (0..1000000)
          ACCESS read-write
          STATUS mandatory
          DESCRIPTION
               ""
          ::= { teraCACTable 4 }

teraCACUpWeightUBR OBJECT-TYPE
          SYNTAX INTEGER (0..1000000)
          ACCESS read-write
          STATUS mandatory
          DESCRIPTION
               ""
          ::= { teraCACTable 5 }

teraCACUpWeightUBRMcr OBJECT-TYPE
          SYNTAX INTEGER (0..1000000)
          ACCESS read-write
          STATUS mandatory
          DESCRIPTION
               ""
          ::= { teraCACTable 6 }

teraCACUpWeightMeshGuar OBJECT-TYPE
          SYNTAX INTEGER (0..1000000)
          ACCESS read-write
          STATUS mandatory
          DESCRIPTION
               ""
          ::= { teraCACTable 7 }

teraCACUpWeightMeshMax OBJECT-TYPE
          SYNTAX INTEGER (0..1000000)
          ACCESS read-write
          STATUS mandatory
          DESCRIPTION
               ""
          ::= { teraCACTable 8 }

teraCACDownWeightrtVBR OBJECT-TYPE
          SYNTAX INTEGER (0..1000000)
          ACCESS read-write
          STATUS mandatory
          DESCRIPTION
               ""
          ::= { teraCACTable 9 }

teraCACDownWeightrtVBRpeak OBJECT-TYPE
          SYNTAX INTEGER (0..1000000)
          ACCESS read-write
          STATUS mandatory
          DESCRIPTION
               ""
          ::= { teraCACTable 10 }

teraCACDownWeightnrtVBR OBJECT-TYPE
          SYNTAX INTEGER (0..1000000)
          ACCESS read-write
          STATUS mandatory
          DESCRIPTION
               ""
          ::= { teraCACTable 11 }

teraCACDownWeightnrtVBRpeak OBJECT-TYPE
          SYNTAX INTEGER (0..1000000)
          ACCESS read-write
          STATUS mandatory
          DESCRIPTION
               ""
          ::= { teraCACTable 12 }

teraCACDownWeightUBR OBJECT-TYPE
          SYNTAX INTEGER (0..1000000)
          ACCESS read-write
          STATUS mandatory
          DESCRIPTION
               ""
          ::= { teraCACTable 13 }

teraCACDownWeightUBRMcr OBJECT-TYPE
          SYNTAX INTEGER (0..1000000)
          ACCESS read-write
          STATUS mandatory
          DESCRIPTION
               ""
          ::= { teraCACTable 14 }

teraCACDownWeightMeshGuar OBJECT-TYPE
          SYNTAX INTEGER (0..1000000)
          ACCESS read-write
          STATUS mandatory
          DESCRIPTION
               ""
          ::= { teraCACTable 15 }

teraCACDownWeightMeshMax OBJECT-TYPE
          SYNTAX INTEGER (0..1000000)
          ACCESS read-write
          STATUS mandatory
          DESCRIPTION
               ""
          ::= { teraCACTable 16 }

     -- teraLevel1UseUpStreamTable

teraLevel1UseUpStreamTable OBJECT-TYPE
     SYNTAX SEQUENCE OF TeraLevel1UseUpStreamTableEntryType
     ACCESS not-accessible
     STATUS mandatory
     DESCRIPTION
          " table teraLevel1UseUpStreamTable"
     ::= { teraCACGroup 3 }

teraLevel1UseUpStreamTableEntry OBJECT-TYPE
          SYNTAX TeraLevel1UseUpStreamTableEntryType
          ACCESS not-accessible
          STATUS mandatory
          DESCRIPTION
               " table entry teraLevel1UseUpStreamTableEntry "
          INDEX {                   teraLevel1UseSlotNumber }
     ::= { teraLevel1UseUpStreamTable 1 }

TeraLevel1UseUpStreamTableEntryType ::= SEQUENCE {
          teraLevel1UpStreamCBR   
             INTEGER,
          teraLevel1UpStreamrtVBR   
             INTEGER,
          teraLevel1UpStreamrtVBRpeak   
             INTEGER,
          teraLevel1UpStreamnrtVBR   
             INTEGER,
          teraLevel1UpStreamnrtVBRpeak   
             INTEGER,
          teraLevel1UpStreamUBR   
             INTEGER,
          teraLevel1UpStreamUBRMcr   
             INTEGER,
          teraLevel1UpStreamMeshGuar   
             INTEGER,
          teraLevel1UpStreamMeshMax   
             INTEGER,
          teraLevel1UpStreamDSlot   
             INTEGER,
          teraLevel1UpStreamMChan   
             INTEGER,
          teraLevel1UpStreamrtVBRWeighted   
             INTEGER,
          teraLevel1UpStreamrtVBRpeakWeighted   
             INTEGER,
          teraLevel1UpStreamnrtVBRWeighted   
             INTEGER,
          teraLevel1UpStreamnrtVBRpeakWeighted   
             INTEGER,
          teraLevel1UpStreamUBRWeighted   
             INTEGER,
          teraLevel1UpStreamUBRMcrWeighted   
             INTEGER,
          teraLevel1UpStreamMeshGuarWeighted   
             INTEGER,
          teraLevel1UpStreamMeshMaxWeighted   
             INTEGER,
          teraLevel1UpStreamCBRReservedBW4Rounding   
             INTEGER,
          teraLevel1UpStreamTotalScrUse   
             INTEGER,
          teraLevel1UpStreamTotalUse   
             INTEGER,
          teraLevel1UpStreamTotalWeightedUse   
             INTEGER,
          teraLevel1UpStreamTotalBWAvailableForVBROnly   
             INTEGER,
          teraLevel1UpStreamTotalBWAvailableForAny   
             INTEGER,
          teraLevel1UpStreamTotalBW   
             INTEGER
}

teraLevel1UpStreamCBR OBJECT-TYPE
          SYNTAX INTEGER
          ACCESS read-only
          STATUS mandatory
          DESCRIPTION
               ""
          ::= { teraLevel1UseUpStreamTableEntry 1 }

teraLevel1UpStreamrtVBR OBJECT-TYPE
          SYNTAX INTEGER
          ACCESS read-only
          STATUS mandatory
          DESCRIPTION
               ""
          ::= { teraLevel1UseUpStreamTableEntry 2 }

teraLevel1UpStreamrtVBRpeak OBJECT-TYPE
          SYNTAX INTEGER
          ACCESS read-only
          STATUS mandatory
          DESCRIPTION
               ""
          ::= { teraLevel1UseUpStreamTableEntry 3 }

teraLevel1UpStreamnrtVBR OBJECT-TYPE
          SYNTAX INTEGER
          ACCESS read-only
          STATUS mandatory
          DESCRIPTION
               ""
          ::= { teraLevel1UseUpStreamTableEntry 4 }

teraLevel1UpStreamnrtVBRpeak OBJECT-TYPE
          SYNTAX INTEGER
          ACCESS read-only
          STATUS mandatory
          DESCRIPTION
               ""
          ::= { teraLevel1UseUpStreamTableEntry 5 }

teraLevel1UpStreamUBR OBJECT-TYPE
          SYNTAX INTEGER
          ACCESS read-only
          STATUS mandatory
          DESCRIPTION
               ""
          ::= { teraLevel1UseUpStreamTableEntry 6 }

teraLevel1UpStreamUBRMcr OBJECT-TYPE
          SYNTAX INTEGER
          ACCESS read-only
          STATUS mandatory
          DESCRIPTION
               ""
          ::= { teraLevel1UseUpStreamTableEntry 7 }

teraLevel1UpStreamMeshGuar OBJECT-TYPE
          SYNTAX INTEGER
          ACCESS read-only
          STATUS mandatory
          DESCRIPTION
               ""
          ::= { teraLevel1UseUpStreamTableEntry 8 }

teraLevel1UpStreamMeshMax OBJECT-TYPE
          SYNTAX INTEGER
          ACCESS read-only
          STATUS mandatory
          DESCRIPTION
               ""
          ::= { teraLevel1UseUpStreamTableEntry 9 }

teraLevel1UpStreamDSlot OBJECT-TYPE
          SYNTAX INTEGER
          ACCESS read-only
          STATUS mandatory
          DESCRIPTION
               ""
          ::= { teraLevel1UseUpStreamTableEntry 10 }

teraLevel1UpStreamMChan OBJECT-TYPE
          SYNTAX INTEGER
          ACCESS read-only
          STATUS mandatory
          DESCRIPTION
               ""
          ::= { teraLevel1UseUpStreamTableEntry 11 }

teraLevel1UpStreamrtVBRWeighted OBJECT-TYPE
          SYNTAX INTEGER
          ACCESS read-only
          STATUS mandatory
          DESCRIPTION
               ""
          ::= { teraLevel1UseUpStreamTableEntry 12 }

teraLevel1UpStreamrtVBRpeakWeighted OBJECT-TYPE
          SYNTAX INTEGER
          ACCESS read-only
          STATUS mandatory
          DESCRIPTION
               ""
          ::= { teraLevel1UseUpStreamTableEntry 13 }

teraLevel1UpStreamnrtVBRWeighted OBJECT-TYPE
          SYNTAX INTEGER
          ACCESS read-only
          STATUS mandatory
          DESCRIPTION
               ""
          ::= { teraLevel1UseUpStreamTableEntry 14 }

teraLevel1UpStreamnrtVBRpeakWeighted OBJECT-TYPE
          SYNTAX INTEGER
          ACCESS read-only
          STATUS mandatory
          DESCRIPTION
               ""
          ::= { teraLevel1UseUpStreamTableEntry 15 }

teraLevel1UpStreamUBRWeighted OBJECT-TYPE
          SYNTAX INTEGER
          ACCESS read-only
          STATUS mandatory
          DESCRIPTION
               ""
          ::= { teraLevel1UseUpStreamTableEntry 16 }

teraLevel1UpStreamUBRMcrWeighted OBJECT-TYPE
          SYNTAX INTEGER
          ACCESS read-only
          STATUS mandatory
          DESCRIPTION
               ""
          ::= { teraLevel1UseUpStreamTableEntry 17 }

teraLevel1UpStreamMeshGuarWeighted OBJECT-TYPE
          SYNTAX INTEGER
          ACCESS read-only
          STATUS mandatory
          DESCRIPTION
               ""
          ::= { teraLevel1UseUpStreamTableEntry 18 }

teraLevel1UpStreamMeshMaxWeighted OBJECT-TYPE
          SYNTAX INTEGER
          ACCESS read-only
          STATUS mandatory
          DESCRIPTION
               ""
          ::= { teraLevel1UseUpStreamTableEntry 19 }

teraLevel1UpStreamCBRReservedBW4Rounding OBJECT-TYPE
          SYNTAX INTEGER
          ACCESS read-only
          STATUS mandatory
          DESCRIPTION
               ""
          ::= { teraLevel1UseUpStreamTableEntry 20 }

teraLevel1UpStreamTotalScrUse OBJECT-TYPE
          SYNTAX INTEGER
          ACCESS read-only
          STATUS mandatory
          DESCRIPTION
               ""
          ::= { teraLevel1UseUpStreamTableEntry 21 }

teraLevel1UpStreamTotalUse OBJECT-TYPE
          SYNTAX INTEGER
          ACCESS read-only
          STATUS mandatory
          DESCRIPTION
               ""
          ::= { teraLevel1UseUpStreamTableEntry 22 }

teraLevel1UpStreamTotalWeightedUse OBJECT-TYPE
          SYNTAX INTEGER
          ACCESS read-only
          STATUS mandatory
          DESCRIPTION
               ""
          ::= { teraLevel1UseUpStreamTableEntry 23 }

teraLevel1UpStreamTotalBWAvailableForVBROnly OBJECT-TYPE
          SYNTAX INTEGER
          ACCESS read-only
          STATUS mandatory
          DESCRIPTION
               ""
          ::= { teraLevel1UseUpStreamTableEntry 24 }

teraLevel1UpStreamTotalBWAvailableForAny OBJECT-TYPE
          SYNTAX INTEGER
          ACCESS read-only
          STATUS mandatory
          DESCRIPTION
               ""
          ::= { teraLevel1UseUpStreamTableEntry 25 }

teraLevel1UpStreamTotalBW OBJECT-TYPE
          SYNTAX INTEGER
          ACCESS read-only
          STATUS mandatory
          DESCRIPTION
               ""
          ::= { teraLevel1UseUpStreamTableEntry 26 }

     -- teraLevel1UseDownStreamTable

teraLevel1UseDownStreamTable OBJECT-TYPE
     SYNTAX SEQUENCE OF TeraLevel1UseDownStreamTableEntryType
     ACCESS not-accessible
     STATUS mandatory
     DESCRIPTION
          " table teraLevel1UseDownStreamTable"
     ::= { teraCACGroup 4 }

teraLevel1UseDownStreamTableEntry OBJECT-TYPE
          SYNTAX TeraLevel1UseDownStreamTableEntryType
          ACCESS not-accessible
          STATUS mandatory
          DESCRIPTION
               " table entry teraLevel1UseDownStreamTableEntry "
          INDEX {                   teraLevel1UseSlotNumber }
     ::= { teraLevel1UseDownStreamTable 1 }

TeraLevel1UseDownStreamTableEntryType ::= SEQUENCE {
          teraLevel1DownStreamCBR   
             INTEGER,
          teraLevel1DownStreamrtVBR   
             INTEGER,
          teraLevel1DownStreamrtVBRpeak   
             INTEGER,
          teraLevel1DownStreamnrtVBR   
             INTEGER,
          teraLevel1DownStreamnrtVBRpeak   
             INTEGER,
          teraLevel1DownStreamUBR   
             INTEGER,
          teraLevel1DownStreamUBRMcr   
             INTEGER,
          teraLevel1DownStreamMeshGuar   
             INTEGER,
          teraLevel1DownStreamMeshMax   
             INTEGER,
          teraLevel1DownStreamDSlot   
             INTEGER,
          teraLevel1DownStreamMChan   
             INTEGER,
          teraLevel1DownStreamrtVBRWeighted   
             INTEGER,
          teraLevel1DownStreamrtVBRpeakWeighted   
             INTEGER,
          teraLevel1DownStreamnrtVBRWeighted   
             INTEGER,
          teraLevel1DownStreamnrtVBRpeakWeighted   
             INTEGER,
          teraLevel1DownStreamUBRWeighted   
             INTEGER,
          teraLevel1DownStreamUBRMcrWeighted   
             INTEGER,
          teraLevel1DownStreamMeshGuarWeighted   
             INTEGER,
          teraLevel1DownStreamMeshMaxWeighted   
             INTEGER,
          teraLevel1DownStreamCBRReservedBW4Rounding   
             INTEGER,
          teraLevel1DownStreamTotalScrUse   
             INTEGER,
          teraLevel1DownStreamTotalUse   
             INTEGER,
          teraLevel1DownStreamTotalWeightedUse   
             INTEGER (0..1000),
          teraLevel1DownStreamTotalBWAvailableForVBROnly   
             INTEGER,
          teraLevel1DownStreamTotalBWAvailableForAny   
             INTEGER,
          teraLevel1DownStreamTotalBW   
             INTEGER
}

teraLevel1DownStreamCBR OBJECT-TYPE
          SYNTAX INTEGER
          ACCESS read-only
          STATUS mandatory
          DESCRIPTION
               ""
          ::= { teraLevel1UseDownStreamTableEntry 1 }

teraLevel1DownStreamrtVBR OBJECT-TYPE
          SYNTAX INTEGER
          ACCESS read-only
          STATUS mandatory
          DESCRIPTION
               ""
          ::= { teraLevel1UseDownStreamTableEntry 2 }

teraLevel1DownStreamrtVBRpeak OBJECT-TYPE
          SYNTAX INTEGER
          ACCESS read-only
          STATUS mandatory
          DESCRIPTION
               ""
          ::= { teraLevel1UseDownStreamTableEntry 3 }

teraLevel1DownStreamnrtVBR OBJECT-TYPE
          SYNTAX INTEGER
          ACCESS read-only
          STATUS mandatory
          DESCRIPTION
               ""
          ::= { teraLevel1UseDownStreamTableEntry 4 }

teraLevel1DownStreamnrtVBRpeak OBJECT-TYPE
          SYNTAX INTEGER
          ACCESS read-only
          STATUS mandatory
          DESCRIPTION
               ""
          ::= { teraLevel1UseDownStreamTableEntry 5 }

teraLevel1DownStreamUBR OBJECT-TYPE
          SYNTAX INTEGER
          ACCESS read-only
          STATUS mandatory
          DESCRIPTION
               ""
          ::= { teraLevel1UseDownStreamTableEntry 6 }

teraLevel1DownStreamUBRMcr OBJECT-TYPE
          SYNTAX INTEGER
          ACCESS read-only
          STATUS mandatory
          DESCRIPTION
               ""
          ::= { teraLevel1UseDownStreamTableEntry 7 }

teraLevel1DownStreamMeshGuar OBJECT-TYPE
          SYNTAX INTEGER
          ACCESS read-only
          STATUS mandatory
          DESCRIPTION
               ""
          ::= { teraLevel1UseDownStreamTableEntry 8 }

teraLevel1DownStreamMeshMax OBJECT-TYPE
          SYNTAX INTEGER
          ACCESS read-only
          STATUS mandatory
          DESCRIPTION
               ""
          ::= { teraLevel1UseDownStreamTableEntry 9 }

teraLevel1DownStreamDSlot OBJECT-TYPE
          SYNTAX INTEGER
          ACCESS read-only
          STATUS mandatory
          DESCRIPTION
               ""
          ::= { teraLevel1UseDownStreamTableEntry 10 }

teraLevel1DownStreamMChan OBJECT-TYPE
          SYNTAX INTEGER
          ACCESS read-only
          STATUS mandatory
          DESCRIPTION
               ""
          ::= { teraLevel1UseDownStreamTableEntry 11 }

teraLevel1DownStreamrtVBRWeighted OBJECT-TYPE
          SYNTAX INTEGER
          ACCESS read-only
          STATUS mandatory
          DESCRIPTION
               ""
          ::= { teraLevel1UseDownStreamTableEntry 12 }

teraLevel1DownStreamrtVBRpeakWeighted OBJECT-TYPE
          SYNTAX INTEGER
          ACCESS read-only
          STATUS mandatory
          DESCRIPTION
               ""
          ::= { teraLevel1UseDownStreamTableEntry 13 }

teraLevel1DownStreamnrtVBRWeighted OBJECT-TYPE
          SYNTAX INTEGER
          ACCESS read-only
          STATUS mandatory
          DESCRIPTION
               ""
          ::= { teraLevel1UseDownStreamTableEntry 14 }

teraLevel1DownStreamnrtVBRpeakWeighted OBJECT-TYPE
          SYNTAX INTEGER
          ACCESS read-only
          STATUS mandatory
          DESCRIPTION
               ""
          ::= { teraLevel1UseDownStreamTableEntry 15 }

teraLevel1DownStreamUBRWeighted OBJECT-TYPE
          SYNTAX INTEGER
          ACCESS read-only
          STATUS mandatory
          DESCRIPTION
               ""
          ::= { teraLevel1UseDownStreamTableEntry 16 }

teraLevel1DownStreamUBRMcrWeighted OBJECT-TYPE
          SYNTAX INTEGER
          ACCESS read-only
          STATUS mandatory
          DESCRIPTION
               ""
          ::= { teraLevel1UseDownStreamTableEntry 17 }

teraLevel1DownStreamMeshGuarWeighted OBJECT-TYPE
          SYNTAX INTEGER
          ACCESS read-only
          STATUS mandatory
          DESCRIPTION
               ""
          ::= { teraLevel1UseDownStreamTableEntry 18 }

teraLevel1DownStreamMeshMaxWeighted OBJECT-TYPE
          SYNTAX INTEGER
          ACCESS read-only
          STATUS mandatory
          DESCRIPTION
               ""
          ::= { teraLevel1UseDownStreamTableEntry 19 }

teraLevel1DownStreamCBRReservedBW4Rounding OBJECT-TYPE
          SYNTAX INTEGER
          ACCESS read-only
          STATUS mandatory
          DESCRIPTION
               ""
          ::= { teraLevel1UseDownStreamTableEntry 20 }

teraLevel1DownStreamTotalScrUse OBJECT-TYPE
          SYNTAX INTEGER
          ACCESS read-only
          STATUS mandatory
          DESCRIPTION
               ""
          ::= { teraLevel1UseDownStreamTableEntry 21 }

teraLevel1DownStreamTotalUse OBJECT-TYPE
          SYNTAX INTEGER
          ACCESS read-only
          STATUS mandatory
          DESCRIPTION
               ""
          ::= { teraLevel1UseDownStreamTableEntry 22 }

teraLevel1DownStreamTotalWeightedUse OBJECT-TYPE
          SYNTAX INTEGER (0..1000)
          ACCESS read-only
          STATUS mandatory
          DESCRIPTION
               ""
          ::= { teraLevel1UseDownStreamTableEntry 23 }

teraLevel1DownStreamTotalBWAvailableForVBROnly OBJECT-TYPE
          SYNTAX INTEGER
          ACCESS read-only
          STATUS mandatory
          DESCRIPTION
               ""
          ::= { teraLevel1UseDownStreamTableEntry 24 }

teraLevel1DownStreamTotalBWAvailableForAny OBJECT-TYPE
          SYNTAX INTEGER
          ACCESS read-only
          STATUS mandatory
          DESCRIPTION
               ""
          ::= { teraLevel1UseDownStreamTableEntry 25 }

teraLevel1DownStreamTotalBW OBJECT-TYPE
          SYNTAX INTEGER
          ACCESS read-only
          STATUS mandatory
          DESCRIPTION
               ""
          ::= { teraLevel1UseDownStreamTableEntry 26 }

     -- teraLevel2UseUpStreamTable

teraLevel2UseUpStreamTable OBJECT-TYPE
     SYNTAX SEQUENCE OF TeraLevel2UseUpStreamTableEntryType
     ACCESS not-accessible
     STATUS mandatory
     DESCRIPTION
          " table teraLevel2UseUpStreamTable"
     ::= { teraCACGroup 5 }

teraLevel2UseUpStreamTableEntry OBJECT-TYPE
          SYNTAX TeraLevel2UseUpStreamTableEntryType
          ACCESS not-accessible
          STATUS mandatory
          DESCRIPTION
               " table entry teraLevel2UseUpStreamTableEntry "
          INDEX {                   teraLevel1UseSlotNumber,                  teraUsePonIndex,                  teraLevel2UseSlotNumber }
     ::= { teraLevel2UseUpStreamTable 1 }

TeraLevel2UseUpStreamTableEntryType ::= SEQUENCE {
          teraLevel2UpStreamCBR   
             INTEGER,
          teraLevel2UpStreamrtVBR   
             INTEGER,
          teraLevel2UpStreamrtVBRpeak   
             INTEGER,
          teraLevel2UpStreamnrtVBR   
             INTEGER,
          teraLevel2UpStreamnrtVBRpeak   
             INTEGER,
          teraLevel2UpStreamUBR   
             INTEGER,
          teraLevel2UpStreamUBRMcr   
             INTEGER,
          teraLevel2UpStreamMeshGuar   
             INTEGER,
          teraLevel2UpStreamMeshMax   
             INTEGER,
          teraLevel2UpStreamDSlot   
             INTEGER,
          teraLevel2UpStreamMChan   
             INTEGER,
          teraLevel2UpStreamrtVBRWeighted   
             INTEGER (0..1000),
          teraLevel2UpStreamrtVBRpeakWeighted   
             INTEGER (0..1000),
          teraLevel2UpStreamnrtVBRWeighted   
             INTEGER (0..1000),
          teraLevel2UpStreamnrtVBRpeakWeighted   
             INTEGER (0..1000),
          teraLevel2UpStreamUBRWeighted   
             INTEGER (0..1000),
          teraLevel2UpStreamUBRMcrWeighted   
             INTEGER (0..1000),
          teraLevel2UpStreamMeshGuarWeighted   
             INTEGER (0..1000),
          teraLevel2UpStreamMeshMaxWeighted   
             INTEGER (0..1000),
          teraLevel2UpStreamTotalScrUse   
             INTEGER,
          teraLevel2UpStreamTotalUse   
             INTEGER,
          teraLevel2UpStreamTotalWeightedUse   
             INTEGER (0..1000),
          teraLevel2UpStreamTotalBW   
             INTEGER
}

teraLevel2UpStreamCBR OBJECT-TYPE
          SYNTAX INTEGER
          ACCESS read-only
          STATUS mandatory
          DESCRIPTION
               ""
          ::= { teraLevel2UseUpStreamTableEntry 1 }

teraLevel2UpStreamrtVBR OBJECT-TYPE
          SYNTAX INTEGER
          ACCESS read-only
          STATUS mandatory
          DESCRIPTION
               ""
          ::= { teraLevel2UseUpStreamTableEntry 2 }

teraLevel2UpStreamrtVBRpeak OBJECT-TYPE
          SYNTAX INTEGER
          ACCESS read-only
          STATUS mandatory
          DESCRIPTION
               ""
          ::= { teraLevel2UseUpStreamTableEntry 3 }

teraLevel2UpStreamnrtVBR OBJECT-TYPE
          SYNTAX INTEGER
          ACCESS read-only
          STATUS mandatory
          DESCRIPTION
               ""
          ::= { teraLevel2UseUpStreamTableEntry 4 }

teraLevel2UpStreamnrtVBRpeak OBJECT-TYPE
          SYNTAX INTEGER
          ACCESS read-only
          STATUS mandatory
          DESCRIPTION
               ""
          ::= { teraLevel2UseUpStreamTableEntry 5 }

teraLevel2UpStreamUBR OBJECT-TYPE
          SYNTAX INTEGER
          ACCESS read-only
          STATUS mandatory
          DESCRIPTION
               ""
          ::= { teraLevel2UseUpStreamTableEntry 6 }

teraLevel2UpStreamUBRMcr OBJECT-TYPE
          SYNTAX INTEGER
          ACCESS read-only
          STATUS mandatory
          DESCRIPTION
               ""
          ::= { teraLevel2UseUpStreamTableEntry 7 }

teraLevel2UpStreamMeshGuar OBJECT-TYPE
          SYNTAX INTEGER
          ACCESS read-only
          STATUS mandatory
          DESCRIPTION
               ""
          ::= { teraLevel2UseUpStreamTableEntry 8 }

teraLevel2UpStreamMeshMax OBJECT-TYPE
          SYNTAX INTEGER
          ACCESS read-only
          STATUS mandatory
          DESCRIPTION
               ""
          ::= { teraLevel2UseUpStreamTableEntry 9 }

teraLevel2UpStreamDSlot OBJECT-TYPE
          SYNTAX INTEGER
          ACCESS read-only
          STATUS mandatory
          DESCRIPTION
               ""
          ::= { teraLevel2UseUpStreamTableEntry 10 }

teraLevel2UpStreamMChan OBJECT-TYPE
          SYNTAX INTEGER
          ACCESS read-only
          STATUS mandatory
          DESCRIPTION
               ""
          ::= { teraLevel2UseUpStreamTableEntry 11 }

teraLevel2UpStreamrtVBRWeighted OBJECT-TYPE
          SYNTAX INTEGER (0..1000)
          ACCESS read-only
          STATUS mandatory
          DESCRIPTION
               ""
          ::= { teraLevel2UseUpStreamTableEntry 12 }

teraLevel2UpStreamrtVBRpeakWeighted OBJECT-TYPE
          SYNTAX INTEGER (0..1000)
          ACCESS read-only
          STATUS mandatory
          DESCRIPTION
               ""
          ::= { teraLevel2UseUpStreamTableEntry 13 }

teraLevel2UpStreamnrtVBRWeighted OBJECT-TYPE
          SYNTAX INTEGER (0..1000)
          ACCESS read-only
          STATUS mandatory
          DESCRIPTION
               ""
          ::= { teraLevel2UseUpStreamTableEntry 14 }

teraLevel2UpStreamnrtVBRpeakWeighted OBJECT-TYPE
          SYNTAX INTEGER (0..1000)
          ACCESS read-only
          STATUS mandatory
          DESCRIPTION
               ""
          ::= { teraLevel2UseUpStreamTableEntry 15 }

teraLevel2UpStreamUBRWeighted OBJECT-TYPE
          SYNTAX INTEGER (0..1000)
          ACCESS read-only
          STATUS mandatory
          DESCRIPTION
               ""
          ::= { teraLevel2UseUpStreamTableEntry 16 }

teraLevel2UpStreamUBRMcrWeighted OBJECT-TYPE
          SYNTAX INTEGER (0..1000)
          ACCESS read-only
          STATUS mandatory
          DESCRIPTION
               ""
          ::= { teraLevel2UseUpStreamTableEntry 17 }

teraLevel2UpStreamMeshGuarWeighted OBJECT-TYPE
          SYNTAX INTEGER (0..1000)
          ACCESS read-only
          STATUS mandatory
          DESCRIPTION
               ""
          ::= { teraLevel2UseUpStreamTableEntry 18 }

teraLevel2UpStreamMeshMaxWeighted OBJECT-TYPE
          SYNTAX INTEGER (0..1000)
          ACCESS read-only
          STATUS mandatory
          DESCRIPTION
               ""
          ::= { teraLevel2UseUpStreamTableEntry 19 }

teraLevel2UpStreamTotalScrUse OBJECT-TYPE
          SYNTAX INTEGER
          ACCESS read-only
          STATUS mandatory
          DESCRIPTION
               ""
          ::= { teraLevel2UseUpStreamTableEntry 20 }

teraLevel2UpStreamTotalUse OBJECT-TYPE
          SYNTAX INTEGER
          ACCESS read-only
          STATUS mandatory
          DESCRIPTION
               ""
          ::= { teraLevel2UseUpStreamTableEntry 21 }

teraLevel2UpStreamTotalWeightedUse OBJECT-TYPE
          SYNTAX INTEGER (0..1000)
          ACCESS read-only
          STATUS mandatory
          DESCRIPTION
               ""
          ::= { teraLevel2UseUpStreamTableEntry 22 }

teraLevel2UpStreamTotalBW OBJECT-TYPE
          SYNTAX INTEGER
          ACCESS read-only
          STATUS mandatory
          DESCRIPTION
               ""
          ::= { teraLevel2UseUpStreamTableEntry 23 }

     -- teraLevel2UseDownStreamTable

teraLevel2UseDownStreamTable OBJECT-TYPE
     SYNTAX SEQUENCE OF TeraLevel2UseDownStreamTableEntryType
     ACCESS not-accessible
     STATUS mandatory
     DESCRIPTION
          " table teraLevel2UseDownStreamTable"
     ::= { teraCACGroup 6 }

teraLevel2UseDownStreamTableEntry OBJECT-TYPE
          SYNTAX TeraLevel2UseDownStreamTableEntryType
          ACCESS not-accessible
          STATUS mandatory
          DESCRIPTION
               " table entry teraLevel2UseDownStreamTableEntry "
          INDEX {                   teraLevel1UseSlotNumber,                  teraUsePonIndex,                  teraLevel2UseSlotNumber }
     ::= { teraLevel2UseDownStreamTable 1 }

TeraLevel2UseDownStreamTableEntryType ::= SEQUENCE {
          teraLevel2DownStreamCBR   
             INTEGER,
          teraLevel2DownStreamrtVBR   
             INTEGER,
          teraLevel2DownStreamrtVBRpeak   
             INTEGER,
          teraLevel2DownStreamnrtVBR   
             INTEGER,
          teraLevel2DownStreamnrtVBRpeak   
             INTEGER,
          teraLevel2DownStreamUBR   
             INTEGER,
          teraLevel2DownStreamUBRMcr   
             INTEGER,
          teraLevel2DownStreamMeshGuar   
             INTEGER,
          teraLevel2DownStreamMeshMax   
             INTEGER,
          teraLevel2DownStreamDSlot   
             INTEGER,
          teraLevel2DownStreamMChan   
             INTEGER,
          teraLevel2DownStreamrtVBRWeighted   
             INTEGER (0..1000),
          teraLevel2DownStreamrtVBRpeakWeighted   
             INTEGER (0..1000),
          teraLevel2DownStreamnrtVBRWeighted   
             INTEGER,
          teraLevel2DownStreamnrtVBRpeakWeighted   
             INTEGER,
          teraLevel2DownStreamUBRWeighted   
             INTEGER,
          teraLevel2DownStreamUBRMcrWeighted   
             INTEGER,
          teraLevel2DownStreamMeshGuarWeighted   
             INTEGER,
          teraLevel2DownStreamMeshMaxWeighted   
             INTEGER,
          teraLevel2DownStreamTotalScrUse   
             INTEGER,
          teraLevel2DownStreamTotalUse   
             INTEGER,
          teraLevel2DownStreamTotalWeightedUse   
             INTEGER,
          teraLevel2DownStreamTotalBW   
             INTEGER
}

teraLevel2DownStreamCBR OBJECT-TYPE
          SYNTAX INTEGER
          ACCESS read-only
          STATUS mandatory
          DESCRIPTION
               ""
          ::= { teraLevel2UseDownStreamTableEntry 1 }

teraLevel2DownStreamrtVBR OBJECT-TYPE
          SYNTAX INTEGER
          ACCESS read-only
          STATUS mandatory
          DESCRIPTION
               ""
          ::= { teraLevel2UseDownStreamTableEntry 2 }

teraLevel2DownStreamrtVBRpeak OBJECT-TYPE
          SYNTAX INTEGER
          ACCESS read-only
          STATUS mandatory
          DESCRIPTION
               ""
          ::= { teraLevel2UseDownStreamTableEntry 3 }

teraLevel2DownStreamnrtVBR OBJECT-TYPE
          SYNTAX INTEGER
          ACCESS read-only
          STATUS mandatory
          DESCRIPTION
               ""
          ::= { teraLevel2UseDownStreamTableEntry 4 }

teraLevel2DownStreamnrtVBRpeak OBJECT-TYPE
          SYNTAX INTEGER
          ACCESS read-only
          STATUS mandatory
          DESCRIPTION
               ""
          ::= { teraLevel2UseDownStreamTableEntry 5 }

teraLevel2DownStreamUBR OBJECT-TYPE
          SYNTAX INTEGER
          ACCESS read-only
          STATUS mandatory
          DESCRIPTION
               ""
          ::= { teraLevel2UseDownStreamTableEntry 6 }

teraLevel2DownStreamUBRMcr OBJECT-TYPE
          SYNTAX INTEGER
          ACCESS read-only
          STATUS mandatory
          DESCRIPTION
               ""
          ::= { teraLevel2UseDownStreamTableEntry 7 }

teraLevel2DownStreamMeshGuar OBJECT-TYPE
          SYNTAX INTEGER
          ACCESS read-only
          STATUS mandatory
          DESCRIPTION
               ""
          ::= { teraLevel2UseDownStreamTableEntry 8 }

teraLevel2DownStreamMeshMax OBJECT-TYPE
          SYNTAX INTEGER
          ACCESS read-only
          STATUS mandatory
          DESCRIPTION
               ""
          ::= { teraLevel2UseDownStreamTableEntry 9 }

teraLevel2DownStreamDSlot OBJECT-TYPE
          SYNTAX INTEGER
          ACCESS read-only
          STATUS mandatory
          DESCRIPTION
               ""
          ::= { teraLevel2UseDownStreamTableEntry 10 }

teraLevel2DownStreamMChan OBJECT-TYPE
          SYNTAX INTEGER
          ACCESS read-only
          STATUS mandatory
          DESCRIPTION
               ""
          ::= { teraLevel2UseDownStreamTableEntry 11 }

teraLevel2DownStreamrtVBRWeighted OBJECT-TYPE
          SYNTAX INTEGER (0..1000)
          ACCESS read-only
          STATUS mandatory
          DESCRIPTION
               ""
          ::= { teraLevel2UseDownStreamTableEntry 12 }

teraLevel2DownStreamrtVBRpeakWeighted OBJECT-TYPE
          SYNTAX INTEGER (0..1000)
          ACCESS read-only
          STATUS mandatory
          DESCRIPTION
               ""
          ::= { teraLevel2UseDownStreamTableEntry 13 }

teraLevel2DownStreamnrtVBRWeighted OBJECT-TYPE
          SYNTAX INTEGER
          ACCESS read-only
          STATUS mandatory
          DESCRIPTION
               ""
          ::= { teraLevel2UseDownStreamTableEntry 14 }

teraLevel2DownStreamnrtVBRpeakWeighted OBJECT-TYPE
          SYNTAX INTEGER
          ACCESS read-only
          STATUS mandatory
          DESCRIPTION
               ""
          ::= { teraLevel2UseDownStreamTableEntry 15 }

teraLevel2DownStreamUBRWeighted OBJECT-TYPE
          SYNTAX INTEGER
          ACCESS read-only
          STATUS mandatory
          DESCRIPTION
               ""
          ::= { teraLevel2UseDownStreamTableEntry 16 }

teraLevel2DownStreamUBRMcrWeighted OBJECT-TYPE
          SYNTAX INTEGER
          ACCESS read-only
          STATUS mandatory
          DESCRIPTION
               ""
          ::= { teraLevel2UseDownStreamTableEntry 17 }

teraLevel2DownStreamMeshGuarWeighted OBJECT-TYPE
          SYNTAX INTEGER
          ACCESS read-only
          STATUS mandatory
          DESCRIPTION
               ""
          ::= { teraLevel2UseDownStreamTableEntry 18 }

teraLevel2DownStreamMeshMaxWeighted OBJECT-TYPE
          SYNTAX INTEGER
          ACCESS read-only
          STATUS mandatory
          DESCRIPTION
               ""
          ::= { teraLevel2UseDownStreamTableEntry 19 }

teraLevel2DownStreamTotalScrUse OBJECT-TYPE
          SYNTAX INTEGER
          ACCESS read-only
          STATUS mandatory
          DESCRIPTION
               ""
          ::= { teraLevel2UseDownStreamTableEntry 20 }

teraLevel2DownStreamTotalUse OBJECT-TYPE
          SYNTAX INTEGER
          ACCESS read-only
          STATUS mandatory
          DESCRIPTION
               ""
          ::= { teraLevel2UseDownStreamTableEntry 21 }

teraLevel2DownStreamTotalWeightedUse OBJECT-TYPE
          SYNTAX INTEGER
          ACCESS read-only
          STATUS mandatory
          DESCRIPTION
               ""
          ::= { teraLevel2UseDownStreamTableEntry 22 }

teraLevel2DownStreamTotalBW OBJECT-TYPE
          SYNTAX INTEGER
          ACCESS read-only
          STATUS mandatory
          DESCRIPTION
               ""
          ::= { teraLevel2UseDownStreamTableEntry 23 }

END
